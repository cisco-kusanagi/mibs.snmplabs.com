TIMESTEP-MIB 

DEFINITIONS ::= BEGIN

    IMPORTS
        MODULE-IDENTITY, OBJECT-TYPE, Counter32,
        Integer32, enterprises                  FROM SNMPv2-SMI
        DateAndTime, TimeStamp                  FROM SNMPv2-TC;

    timestep MODULE-IDENTITY
        LAST-UPDATED "9810210000Z"
        ORGANIZATION "Newbridge Corporation"
        CONTACT-INFO
                    " Newbridge Corporation
                      362 Terry Fox Drive
                      Kanata, ON  K0A 2H0
                      Canada

                      1-800-383-8211
                      tsupport@newbridge.com"

        DESCRIPTION
                    "The MIB module to describe local system information
                     of the Newbridge Permit family of IPSEC Gates."

        REVISION    "9810210000Z"
        DESCRIPTION
                    "Initial revision."
 	::= { enterprises 1022 }

   	permitGate OBJECT IDENTIFIER ::= { timestep 9 }

  	permitGateSerialNumber OBJECT-TYPE
        SYNTAX      OCTET STRING (SIZE (12))
        MAX-ACCESS  read-only
        STATUS      current
        DESCRIPTION
                    "The device serial number."
    ::= { permitGate 1 }

    permitGateCpuUtilInst OBJECT-TYPE
        SYNTAX      INTEGER(0..100)
        MAX-ACCESS  read-only
        STATUS      current
        DESCRIPTION
                    "The instantaneous CPU utilization."
    ::= { permitGate 2 }

    permitGateCpuUtilAvg1Min OBJECT-TYPE
        SYNTAX      INTEGER(0..100)
        MAX-ACCESS  read-only
        STATUS      current
        DESCRIPTION
                    "The one minute average of CPU utilization."
    ::= { permitGate 3 }

    permitGateCpuUtilAvg5Min OBJECT-TYPE
        SYNTAX      INTEGER(0..100)
        MAX-ACCESS  read-only
        STATUS      current
        DESCRIPTION
                    "The five minutes average of CPU utilization."
    ::= { permitGate 4 }

    permitGateLastConfigModifTime OBJECT-TYPE
        SYNTAX      TimeStamp
        MAX-ACCESS  read-only
        STATUS      current
        DESCRIPTION
                    "Time since boot that the last configuration
                     modification occured.
                     
                     If the configuration has not changed, then the 
                     value is 0."
    ::= { permitGate 5 }

    permitGateTotalRebootNum OBJECT-TYPE
        SYNTAX      Counter32
        MAX-ACCESS  read-only
        STATUS      current
        DESCRIPTION
                    "The number of times the machine has been rebooted."
    ::= { permitGate 6 }

    permitGateTotalVolMemory OBJECT-TYPE
        SYNTAX      Integer32
        MAX-ACCESS  read-only
        STATUS      current
        DESCRIPTION
                    "The total amount of volatile memory on the device
                     in bytes."
    ::= { permitGate 7 }

    permitGateFreeVolMemory OBJECT-TYPE
        SYNTAX      Integer32
        MAX-ACCESS  read-only
        STATUS      current
        DESCRIPTION
                    "The total amount of free volatile memory on the device
                     in bytes."
    ::= { permitGate 8 }

    permitGateEncDevStatus OBJECT-TYPE
        SYNTAX      INTEGER { up(0), down(1), notApplicable(2) }
        MAX-ACCESS  read-only
        STATUS      current
        DESCRIPTION
                    "The encryption device status."
    ::= { permitGate 9 }

    permitGateRandNumGenStatus OBJECT-TYPE
        SYNTAX      INTEGER { up(0), down(1), notApplicable(2) }
        MAX-ACCESS  read-only
        STATUS      current
        DESCRIPTION
                    "The random number generator status."
    ::= { permitGate 10 }

    permitGateCertExpDate OBJECT-TYPE
        SYNTAX      DateAndTime
        MAX-ACCESS  read-only
        STATUS      current
        DESCRIPTION
                    "The device's certificate expiration date."
    ::= { permitGate 11 }

	permitGateIfArpTable OBJECT-TYPE
		SYNTAX		SEQUENCE OF PermitGateIfArpEntry
		MAX-ACCESS	not-accessible
		STATUS		current
		DESCRIPTION
					"The (conceptual) table containing information
					 about the Permit/Gate interface entries"
	::= { permitGate 12 }

	permitGateIfArpEntry OBJECT-TYPE
		SYNTAX		PermitGateIfArpEntry
		MAX-ACCESS	not-accessible
		STATUS		current
		DESCRIPTION
					"An entry (conceptual row) containing on a particuliar
					 Permit/Gate interface"
		INDEX		{ permitGateIfArpIndex }
	::= { permitGateIfArpTable 1 }

	PermitGateIfArpEntry ::= SEQUENCE {
		permitGateIfArpIndex		Integer32,
	    permitGateIfArpInPkts	Counter32,
	    permitGateIfArpOutPkts	Counter32,
	    permitGateIfArpInOctets	Counter32,
	    permitGateIfArpOutOctets	Counter32
	}

	permitGateIfArpIndex OBJECT-TYPE
		SYNTAX		Integer32
		MAX-ACCESS	read-only
		STATUS		current
		DESCRIPTION	
					"A unique value, greater than zero for each
					 interface."
	::= { permitGateIfArpEntry 1 }

    permitGateIfArpInPkts OBJECT-TYPE
		SYNTAX		Counter32
        MAX-ACCESS  read-only
        STATUS  	current
        DESCRIPTION
                    "Arp protocol input packet count"
	::= { permitGateIfArpEntry 2 }

    permitGateIfArpOutPkts OBJECT-TYPE
        SYNTAX		Counter32
        MAX-ACCESS  read-only
        STATUS		current
        DESCRIPTION
                    "Arp protocol output packet count"
	::= { permitGateIfArpEntry 3 }

    permitGateIfArpInOctets OBJECT-TYPE
        SYNTAX		Counter32
        MAX-ACCESS  read-only
        STATUS		current
        DESCRIPTION
                    "Arp protocol input octet count"
	::= { permitGateIfArpEntry 4 }

    permitGateIfArpOutOctets OBJECT-TYPE
        SYNTAX		Counter32
        MAX-ACCESS  read-only
        STATUS		current
        DESCRIPTION
                    "Arp protocol output octet count"
	::= { permitGateIfArpEntry 5 }

END
