-- extracted from draft-sebastian-vitcpmib-00.txt
-- at Sat Nov 25 16:04:50 2000

   VI-IP-MIB DEFINITIONS ::= BEGIN

   IMPORTS

   OBJECT-TYPE                                  FROM RFC-1212
   Counter32, Gauge32, Integer32                FROM SNMPv2-SMI
   NOTIFICATION-TYPE                            FROM SNMPv2-SMI
   enterprises, NetworkAddress, IpAddress       FROM RFC1155-SMI
   Counter, ObjectName                          FROM RFC1155-SMI
   DisplayString                                FROM RFC1213-MIB;

   viIPMib MODULE-IDENTITY
       LAST-UPDATED "0011150655Z"
       ORGANIZATION ""
       CONTACT-INFO
               "          Bino Sebastian

                   Postal: Bino Sebastian
                           Giganet, Inc.
                           Concord Office Center
                           2352 Main Street
                           Concord, Massachusetts  01742
                           978.461.0402 (tel)
                           978.461.0430 (fax)
                           www.giganet.com

                      Tel: +1 978 461 0402
                      Fax: +1 978 461 0430

                   E-mail: bsebastian@giganet.com"
       DESCRIPTION
           "The MIB module to describe objects for virtual interface
           over TCP implementation."

       ::= { mib-2 XX }

   viIPMibObjects OBJECT IDENTIFIER ::= { viIPMib 1 }

   viaNodeConnection OBJECT IDENTIFIER ::= { viIPMibObjects 1 }

   VIANodeSystemName OBJECT-TYPE
       SYNTAX    DisplayString(SIZE (0..255))
       ACCESS    read-only
       STATUS    current
       DESCRIPTION
           "A string by which the node is identified in the cluster."
       ::= { viaNodeConnection 1 }

   VIACreated OBJECT-TYPE
       SYNTAX    Counter32
       ACCESS    read-only
       STATUS    current
       DESCRIPTION
           "The number of VIs have been created."
       ::= { viaNodeConnection 2 }

   VIAConnectRequest OBJECT-TYPE
       SYNTAX    Counter32
       ACCESS    read-only
       STATUS    current
       DESCRIPTION
           "The number of times Connect Request call is made."
       ::= { viaNodeConnection 3 }

   VIAConnectWait OBJECT-TYPE
       SYNTAX    Counter32
       ACCESS    read-only
       STATUS    current
       DESCRIPTION
           "The number of times Connect wait call is made."
       ::= { viaNodeConnection 4 }

   VIADisconnect OBJECT-TYPE
       SYNTAX    Counter32
       ACCESS    read-only
       STATUS    current
       DESCRIPTION
           "Number of times VI got disconnected with out any error."
       ::= { viaNodeConnection 5 }

   VIAConnectTimeOut OBJECT-TYPE
       SYNTAX    Counter32
       ACCESS    read-only
       STATUS    current
       DESCRIPTION
           "Number of times VI connect request got timed out."
       ::= { viaNodeConnection 6 }

   VIAConnected OBJECT-TYPE
       SYNTAX    Counter32
       ACCESS    read-only
       STATUS    current
       DESCRIPTION
           "Number of time VI got connected with out any error."
       ::= { viaNodeConnection 7 }

   VIACurrConnectPending OBJECT-TYPE
       SYNTAX    Gauge32
       ACCESS    read-only
       STATUS    current
       DESCRIPTION
           "The number of VIs for which connect request is pending."
       ::= { viaNodeConnection 8 }

   VIACurrConnectWaitPending OBJECT-TYPE
       SYNTAX    Gauge32
       ACCESS    read-only
       STATUS    current
       DESCRIPTION
           "The number of VIs for which connect wait request is
           pending."
       ::= { viaNodeConnection 9 }

   VIACurrConnected OBJECT-TYPE
       SYNTAX    Gauge32
       ACCESS    read-only
       STATUS    current
       DESCRIPTION
           "The number of VIs for which the current state is CONNECTED."
       ::= { viaNodeConnection 10 }

   VIACurrError OBJECT-TYPE
       SYNTAX    Gauge32
       ACCESS    read-only
       STATUS    current
       DESCRIPTION
           "The number of VIs for which the current state is ERROR"
       ::= { viaNodeConnection 11 }

   VIATotalError OBJECT-TYPE
       SYNTAX    Counter32
       ACCESS    read-only
       STATUS    current
       DESCRIPTION
           "The number of VIs which encountered error state."
       ::= { viaNodeConnection 12 }

   VIAInMsgs OBJECT-TYPE
       SYNTAX    Counter32
       ACCESS    read-only
       STATUS    current
       DESCRIPTION
           "The total number of incoming Messages received."
       ::= { viaNodeConnection 13 }

   VIAInRdma OBJECT-TYPE
       SYNTAX    Counter32
       ACCESS    read-only
       STATUS    current
       DESCRIPTION
           "The total number of incoming RDMA requests received."
       ::= { viaNodeConnection 14 }

   VIAInBytes OBJECT-TYPE
       SYNTAX    Counter32
       ACCESS    read-only
       STATUS    current
       DESCRIPTION
           "The total number of incoming bytes received, including
           those received in error. This count includes bytes received
           on currently established connections. This corresponds to
           the sum of bytes received through received messages,
           incoming RDMA writes and RDMA reads issued"
       ::= { viaNodeConnection 15 }

   VIAInRDMAReadBytes OBJECT-TYPE
       SYNTAX    Counter32
       ACCESS    read-only
       STATUS    current
       DESCRIPTION
           "The total number of incoming bytes received through RDMA
           read, including those received in error. This count includes
           bytes received on currently established connections."
       ::= { viaNodeConnection 16 }

   VIAInRDMAWriteBytes OBJECT-TYPE
       SYNTAX    Counter32
       ACCESS    read-only
       STATUS    current
       DESCRIPTION
           "The total number of bytes received through incoming RDMA
           writes, including those received in error. This count
           includes bytes received on currently established
           connections."
       ::= { viaNodeConnection 17 }

   VIAOutMsgs OBJECT-TYPE
       SYNTAX    Counter32
       ACCESS    read-only
       STATUS    current
       DESCRIPTION
           "The total number of Messages sent."
       ::= { viaNodeConnection 18 }

   VIAOutRdma OBJECT-TYPE
       SYNTAX    Counter32
       ACCESS    read-only
       STATUS    current
       DESCRIPTION
           "The total number of RDMA requests sent."
       ::= { viaNodeConnection 19 }

   VIAOutBytes OBJECT-TYPE
       SYNTAX    Counter32
       ACCESS    read-only
       STATUS    current
       DESCRIPTION
           "The total number of bytes sent, including those
           sent in error. This count includes bytes sent on
           currently established connections."
       ::= { viaNodeConnection 20 }

   VIAOutRDMAReadBytes OBJECT-TYPE
       SYNTAX    Counter32
       ACCESS    read-only
       STATUS    current
       DESCRIPTION
           "The total number of bytes sent through an incoming
           RDMA read request, including those sent in error.
           This count includes bytes sent on currently established
           connections."
       ::= { viaNodeConnection 21 }

   VIAOutRDMAWriteBytes OBJECT-TYPE
       SYNTAX    Counter32
       ACCESS    read-only
       STATUS    current
       DESCRIPTION
           "The total number of bytes sent through a RDMA write
           operation, including those sent in error. This count
           includes bytes sent on currently established connections."
       ::= { viaNodeConnection 22 }


   VIAConnTable OBJECT-TYPE
       SYNTAX    SEQUENCE OF VIAConnEntry
       ACCESS    not-accessible
       STATUS    current
       DESCRIPTION
           "A table containing VIA connection specific information."
       ::= { viaNodeConnection 23 }

   VIAConnEntry OBJECT-TYPE
       SYNTAX    VIAConnEntry
       ACCESS    not-accessible
       STATUS    current
       DESCRIPTION
           "A conceptual row of the VIAConnTable containing information
           about a particular current VIA connection. Each row of this
           table is transient, and it ceases to exist when the
           connection makes transition to the CLOSED state."
        INDEX    { VIAConnVINumber
       }
        ::= { VIAConnTable 1 }

   VIAConnEntry  ::= SEQUENCE {

       VIAConnState                 INTEGER,
       VIAConnVINumber              INTEGER,
       VIAConnRemoteNetAddress      IpAddress,
       VIAConnLocalNetAddress       IpAddress,
       VIAConnRemotePortNumber      INTEGER,
       VIAConnLocalPortNumber       INTEGER,
       VIAConnLocalDescriminator    Opaque,
       VIAConnRemoteDescriminator   Opaque,
       VIAConnLocalMaxTransferSize  INTEGER,
       VIAConnRemoteMaxTransferSize INTEGER,
       VIAConnLocalEnableRdmaWrite  INTEGER,
       VIAConnLocalEnableRdmaRead   INTEGER,
       VIAConnRemoteEnableRdmaWrite INTEGER,
       VIAConnRemoteEnableRdmaRead  INTEGER,
       VIAConnSentMessages          Counter32,
       VIAConnSentRdmaReadMessages  Counter32,
       VIAConnSentRdmaWriteMessages Counter32,
       VIAConnRcvdMessages          Counter32,
       VIAConnRcvdRdmaReadMessages  Counter32,
       VIAConnRcvdRdmaWriteMessages Counter32

       }

   VIAConnState OBJECT-TYPE
       SYNTAX   INTEGER {
            idle (1),
            pendingConnect(2),
            connected(3),
            error(4)
            }
       ACCESS             read-only
       STATUS             current
       DESCRIPTION
               "The state of this VIA connection
                Legal States:
                      Idle            1
                      Pending Connect 2
                      Connected       3
                      Error           4"
       ::= { VIAConnEntry 1 }

   VIAConnVINumber    OBJECT-TYPE
       SYNTAX        INTEGER
       ACCESS        read-only
       STATUS        current
       DESCRIPTION
           "A number which uniquely defines a connection."
       ::= { VIAConnEntry 2 }

   VIAConnRemoteNetAddress    OBJECT-TYPE
       SYNTAX        IpAddress
       ACCESS        read-only
       STATUS        current
       DESCRIPTION
           "IP address of the remote system of the connection."
       ::= { VIAConnEntry 3 }

   VIAConnLocalNetAddress OBJECT-TYPE
       SYNTAX      IpAddress
       ACCESS      read-only
       STATUS      current
       DESCRIPTION
           "Local IPadress of the connection."
       ::= { VIAConnEntry 4 }

   VIAConnRemotePortNumber    OBJECT-TYPE
       SYNTAX        INTEGER
       ACCESS        read-only
       STATUS        current
       DESCRIPTION
           "Remote TCP port number of the connection."
       ::= { VIAConnEntry 5 }

   VIAConnLocalPortNumber    OBJECT-TYPE
       SYNTAX        INTEGER
       ACCESS        read-only
       STATUS        current
       DESCRIPTION
           "Local TCP Portnumber of the connection."
       ::= { VIAConnEntry 6 }

   VIAConnLocalDescriminator    OBJECT-TYPE
       SYNTAX        OCTET STRING
       ACCESS        read-only
       STATUS        current
       DESCRIPTION
           "An identifier used by the local process to identify the
           VI connection."
       ::= { VIAConnEntry 7 }

   VIAConnRemoteDescriminator    OBJECT-TYPE
       SYNTAX        OCTET STRING
       ACCESS        read-only
       STATUS        current
       DESCRIPTION
           "An identifier used by the remote process to identify the
           VI connection."
       ::= { VIAConnEntry 8 }

   VIAConnLocalMaxTransferSize    OBJECT-TYPE
       SYNTAX        INTEGER
       ACCESS        read-only
       STATUS        current
       DESCRIPTION
           "The local limit on the maximum packet size that can be
           transfered through the connection."
       ::= { VIAConnEntry 9 }

   VIAConnRemoteMaxTransferSize OBJECT-TYPE
       SYNTAX        INTEGER
       ACCESS        read-only
       STATUS        current
       DESCRIPTION
           "The remote limit on the maximum packet size that can be
           transfered through the connection."
       ::= { VIAConnEntry 10 }

   VIAConnLocalEnableRdmaWrite    OBJECT-TYPE
       SYNTAX        INTEGER
       ACCESS        read-only
       STATUS        current
       DESCRIPTION
               "The value is 1 if remote DMA write is enabled
               in the local system otherwise, it is 0."
       ::= { VIAConnEntry 11 }

   VIAConnLocalEnableRdmaRead    OBJECT-TYPE
       SYNTAX        INTEGER
       ACCESS        read-only
       STATUS        current
       DESCRIPTION
               "The value is 1 if remote DMA read is enabled
               in the local system otherwise, it is 0."
       ::= { VIAConnEntry 12 }

   VIAConnRemoteEnableRdmaWrite    OBJECT-TYPE
       SYNTAX        INTEGER
       ACCESS        read-only
       STATUS        current
       DESCRIPTION
               "The value is 1 if remote DMA write is enabled
               in the remote system otherwise, it is 0."
       ::= { VIAConnEntry 13 }

   VIAConnRemoteEnableRdmaRead    OBJECT-TYPE
       SYNTAX        INTEGER
       ACCESS        read-only
       STATUS        current
       DESCRIPTION
               "The value is 1 if remote DMA read is enabled
               in the remote system otherwise, it is 0."
       ::= { VIAConnEntry 14 }

   VIAConnSentMessages    OBJECT-TYPE
       SYNTAX        Counter32
       ACCESS        read-only
       STATUS        current
       DESCRIPTION
               "Total number of messages sent through the connection."
       ::= { VIAConnEntry 15 }

   VIAConnSentRdmaReadMessages    OBJECT-TYPE
       SYNTAX        Counter32
       ACCESS        read-only
       STATUS        current
       DESCRIPTION
               "Total number of rdma read messages sent through the
               connection."
       ::= { VIAConnEntry 16 }

   VIAConnSentRdmaWriteMessages    OBJECT-TYPE
       SYNTAX        Counter32
       ACCESS        read-only
       STATUS        current
       DESCRIPTION
               "Total number of rdma write messages sent through the
               connection."
       ::= { VIAConnEntry 17 }

   VIAConnRcvdMessages    OBJECT-TYPE
       SYNTAX        Counter32
       ACCESS        read-only
       STATUS        current
       DESCRIPTION
               "Total number of messages received through the
               connection."
       ::= { VIAConnEntry 18 }

   VIAConnRcvdRdmaReadMessages    OBJECT-TYPE
       SYNTAX        Counter32
       ACCESS        read-only
       STATUS        current
       DESCRIPTION
               "Total number of rdma read messages received through the
               connection."
       ::= { VIAConnEntry 19 }

   VIAConnRcvdRdmaWriteMessages    OBJECT-TYPE
       SYNTAX        Counter32
       ACCESS        read-only
       STATUS        current
       DESCRIPTION
               "Total number of rdma write messages received through the
               connection."
       ::= { VIAConnEntry 20 }

   viaErrors OBJECT IDENTIFIER ::= { viIPMibObjects 2 }

   VIAErrPostDesc        OBJECT-TYPE
       SYNTAX          Counter32
       ACCESS          read-only
       STATUS          current
       DESCRIPTION
               "The total number of descriptors completed in error
               by NIC."
       ::= { viaErrors 1 }

   VIAErrConnLost        OBJECT-TYPE
       SYNTAX          Counter32
       ACCESS          read-only
       STATUS          current
       DESCRIPTION
               "The total number of Lost Connection errors. "
       ::= { viaErrors 2 }

   VIAErrRecvQEmpty    OBJECT-TYPE
       SYNTAX          Counter32
       ACCESS          read-only
       STATUS          current
       DESCRIPTION
               "The total number of errors due to an empty receive
               Queue."
       ::= { viaErrors 3 }

   VIAErrRdmawProt        OBJECT-TYPE
       SYNTAX          Counter32
       ACCESS          read-only
       STATUS          current
       DESCRIPTION
               "The total number of remote DMA write protection
               errors. "
       ::= { viaErrors 4 }

   VIAErrRdmarProt        OBJECT-TYPE
       SYNTAX          Counter32
       ACCESS          read-only
       STATUS          current
       DESCRIPTION
               "The total number of remote DMA read protection errors. "
       ::= { viaErrors 5 }

   VIAErrCompProt    OBJECT-TYPE
       SYNTAX          Counter32
       ACCESS          read-only
       STATUS          current
       DESCRIPTION
               "The total number of protection errors. "
       ::= { viaErrors 6 }

   VIAErrorThreshold OBJECT-TYPE
       SYNTAX            INTEGER
       ACCESS            read-write
       STATUS            current
       DESCRIPTION
           "Setting this threshold will cause a trap to be enabled
           such that if the total error exceeds error threshold set
           a VIANodeErrorsTrap trap will be generated. The trap will
           reset the error counter."
       ::= { viaErrors 7 }

   viaNicAttributes OBJECT IDENTIFIER ::= { viIPMibObjects 3 }

   VIANicTable        OBJECT-TYPE
       SYNTAX            SEQUENCE OF VIANicEntry
       ACCESS            not-accessible
       STATUS            current
       DESCRIPTION
               "A table containing VIA NIC specific information."
       ::= { viaNicAttributes 1}

   VIANicEntry        OBJECT-TYPE
       SYNTAX            VIANicEntry
       ACCESS            not-accessible
       STATUS            current
       DESCRIPTION
               "A conceptual row of the VIANicTable containing
                information about a particular VINic."

       INDEX    {    VIANicIndex }
       ::= { VIANicTable 1 }

   VIANicEntry ::= SEQUENCE {
               VIANicIndex               INTEGER,
               VIAName                   DisplayString,
               VIAHardwareVersion        DisplayString,
               VIAProviderVersion        DisplayString,
               VIANicAddress             PhysAddress,
               VIAThreadSafe             INTEGER,
               VIAMaxDiscriminatorLength INTEGER,
               VIAMaxRegisterBytes       INTEGER,
               VIAMaxRegisterRegions     INTEGER,
               VIAMaxRegisterBlockBytes  INTEGER,
               VIAMaxVI                  INTEGER,
               VIAMaxDescriptorsPerQueue INTEGER,
               VIAMaxSegmentsPerDesc     INTEGER,
               VIAMaxCQ                  INTEGER,
               VIAMaxCQEntries           INTEGER,
               VIAMaxTransferSize        INTEGER,
               VIANativeMTU              INTEGER,
               VIAMaxPTags               INTEGER,
               VIACurrRegisterBytes      INTEGER,
               VIACurrRegisterRegions    INTEGER,
               VIACurrVI                 INTEGER,
               VIACurrCQ                 INTEGER,
               VIACurrPTags              INTEGER,
               VIAConnectionListenPort   INTEGER
       }

   VIANicIndex        OBJECT-TYPE
       SYNTAX        INTEGER
       ACCESS        read-only
       STATUS        current
       DESCRIPTION
           "The index of the NIC in the NIC table."
       ::= { VIANicEntry 1 }

   VIAName            OBJECT-TYPE
       SYNTAX        DisplayString (SIZE (0..255))
       ACCESS        read-only
       STATUS        current
       DESCRIPTION
           "The symbolic name of the NIC device."
       ::= { VIANicEntry 2 }

   VIAHardwareVersion    OBJECT-TYPE
       SYNTAX        DisplayString (SIZE (0..255))
       ACCESS        read-only
       STATUS        current
       DESCRIPTION
           "The version of the VINIC described by this MIB."
       ::= { VIANicEntry 3 }

   VIAProviderVersion    OBJECT-TYPE
       SYNTAX        DisplayString (SIZE (0..255))
       ACCESS        read-only
       STATUS        current
       DESCRIPTION
           "The version of the VI provider."
       ::= { VIANicEntry 4 }

   VIANicAddress    OBJECT-TYPE
       SYNTAX        PhysAddress
       ACCESS        read-only
       STATUS        current
       DESCRIPTION
           "The Network address of the NIC."
       ::= { VIANicEntry 5 }

   VIAThreadSafe    OBJECT-TYPE
       SYNTAX       INTEGER
       ACCESS       read-only
       STATUS       current
       DESCRIPTION
           "1 if synchronisation model is thread safe else 0."
       ::= { VIANicEntry 6 }

   VIAMaxDiscriminatorLength    OBJECT-TYPE
       SYNTAX        INTEGER
       ACCESS        read-only
       STATUS        current
       DESCRIPTION
           "The maximum number of bytes that the VI provider allows
           for a connection descriminator."
       ::= { VIANicEntry 7 }

   VIAMaxRegisterBytes    OBJECT-TYPE
       SYNTAX        INTEGER
       ACCESS        read-only
       STATUS        current
       DESCRIPTION
           "Maximum number of bytes that can be registered by the
           VI user."
       ::= { VIANicEntry 8 }

   VIAMaxRegisterRegions    OBJECT-TYPE
       SYNTAX        INTEGER
       ACCESS        read-only
       STATUS        current
       DESCRIPTION
           "Maximum number of memory regions that can be registered by
           VI user."
       ::= { VIANicEntry 9 }

   VIAMaxRegisterBlockBytes    OBJECT-TYPE
       SYNTAX        INTEGER
       ACCESS        read-only
       STATUS        current
       DESCRIPTION
           "Largest contiguous block of memory that can be
           registered by VI user."
       ::= { VIANicEntry 10 }

   VIAMaxVI        OBJECT-TYPE
       SYNTAX        INTEGER
       ACCESS        read-only
       STATUS        current
       DESCRIPTION
           "The limit on the total number of VI instances this NIC
           can support."
       ::= { VIANicEntry 11 }

   VIAMaxDescriptorsPerQueue    OBJECT-TYPE
       SYNTAX        INTEGER
       ACCESS        read-only
       STATUS        current
       DESCRIPTION
           "Maximum Descriptors per VI Work Queue that this VI provider
           can support."
       ::= { VIANicEntry 12 }

   VIAMaxSegmentsPerDesc    OBJECT-TYPE
       SYNTAX        INTEGER
       ACCESS        read-only
       STATUS        current
       DESCRIPTION
           "Maximum number of segments per descriptor that this VI
           provider can support."
       ::= { VIANicEntry 13 }

   VIAMaxCQ        OBJECT-TYPE
       SYNTAX        INTEGER
       ACCESS        read-only
       STATUS        current
       DESCRIPTION
           "Maximum number of completion queues this VI provider
           can support."
       ::= { VIANicEntry 14 }

   VIAMaxCQEntries        OBJECT-TYPE
       SYNTAX        INTEGER
       ACCESS        read-only
       STATUS        current
       DESCRIPTION
           "Maximum number of Completion queue entries per
           completion queue that this VI provider can
           support."
       ::= { VIANicEntry 15 }

   VIAMaxTransferSize    OBJECT-TYPE
       SYNTAX        INTEGER
       ACCESS        read-only
       STATUS        current
       DESCRIPTION
           "The maximum transfer size supported by the VI Nic. The
            maximum transfer size is the amount of data that can
            be described by a single VI descriptor."
       ::= { VIANicEntry 16 }

   VIANativeMTU    OBJECT-TYPE
       SYNTAX        INTEGER
       ACCESS        read-only
       STATUS        current
       DESCRIPTION
           "The native MTU size of the underlying network. For
           frame-based networks, this could reflect its native
           frame size. For cell-based networks, it could reflect
           the MTU of the appropriate abstraction layer that it
           supports."
       ::= { VIANicEntry 17 }

   VIAMaxPTags        OBJECT-TYPE
       SYNTAX        INTEGER
       ACCESS        read-only
       STATUS        current
       DESCRIPTION
           "The maximum number of protection tags that are
           supported by this VI provider."
       ::= { VIANicEntry 18 }

   VIACurrRegisterBytes    OBJECT-TYPE
       SYNTAX        INTEGER
       ACCESS        read-only
       STATUS        current
       DESCRIPTION
           "Number of bytes registered by the VI user for this
           NIC."
       ::= { VIANicEntry 19 }

   VIACurrRegisterRegions    OBJECT-TYPE
       SYNTAX        INTEGER
       ACCESS        read-only
       STATUS        current
       DESCRIPTION
           "Number of memory regions that is registered by VI user
           for this NIC."
       ::= { VIANicEntry 20 }

   VIACurrVI        OBJECT-TYPE
       SYNTAX        INTEGER
       ACCESS        read-only
       STATUS        current
       DESCRIPTION
           "The current number of VI instances for this NIC."
       ::= { VIANicEntry 21 }

   VIACurrCQ        OBJECT-TYPE
       SYNTAX        INTEGER
       ACCESS        read-only
       STATUS        current
       DESCRIPTION
           "Current number of completion queues this VI provider
           has."
       ::= { VIANicEntry 22 }

   VIACurrPTags      OBJECT-TYPE
       SYNTAX        INTEGER
       ACCESS        read-only
       STATUS        current
       DESCRIPTION
           "Current Number of protection tags this VI provider has."
       ::= { VIANicEntry 23 }

   VIAConnectionListenPort        OBJECT-TYPE
       SYNTAX        INTEGER
       ACCESS        read-only
       STATUS        current
       DESCRIPTION
           "Port number on which VI server is listening for VI
            connection request."
       ::= { VIANicEntry 24 }


   viipTraps          OBJECT IDENTIFIER ::= { viIPMib 2 }

   VIANodeErrorsTrap    NOTIFICATION-TYPE
       ENTERPRISE        giganet
       VARIABLES        {
                       VIAErrPostDesc,
                       VIAErrConnLost,
                       VIAErrRecvQEmpty,
                       VIAErrVIOverrun,
                       VIAErrRdmawProt,
                       VIAErrRdmawData,
                       VIAErrRdmawAbort,
                       VIAErrCompProt,
                       viaErrors }
       DESCRIPTION
           "A VIANodeErrorsTrap trap signifies that the total number of
           errors exceeded the error threshold."
       ::= { viipTraps 1 }


   VIANodeUpTrap        NOTIFICATION-TYPE
          ENTERPRISE     giganet
          VARIABLES     { VIANodeSystemName }
          DESCRIPTION
          "A VIANodeUpTrap trap signifies a VIA Node is started
          and initialised successfully."
          ::= { viipTraps 2 }

   END
