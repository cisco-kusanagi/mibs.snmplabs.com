-- COPYRIGHT NOTICE
-- Copyright (c) Alteon Networks, Inc. 1996, 1997, 1998 
-- All rights reserved
-- 
-- 
-- HISTORY
-- $Log: alttrap.mib $
-- Revision ts60_mlin/5 1999/09/12 21:44:30 mlin
-- 	Rbind slbCurCfgVirtServiceRealPort for service up/down trap.
-- 
-- Revision ts60_mlin/4 1999/09/10 22:29:08 mlin
-- 	2233(partial) - Added real server service up/down traps.  2239 - fail to send filter-fired trap problem.
-- 
-- Revision ts60_mlin/2 1999/08/19 16:40:45 mlin
-- 	2212.  Enhanced SNMP TRAP contents s.a. gwIP, rserverIP, rserverName, sysName, sysLocation, sysContact as requested by AOL/CompuServ.
-- 
-- Revision 1.1.2.3  1999/02/05  00:45:13  mlin
-- 	MIB cleanup.  Changed some objects with more consistent and proper names.
-- 	[1999/02/05  00:45:03  mlin]
--
-- Revision 1.1.2.2  1998/10/13  21:20:29  mlin
-- 	Fixed alteon enterprise traps.
-- 	[1998/10/13  21:20:09  mlin]
-- 
-- Revision 1.1.2.1  1998/10/09  23:38:38  mlin
-- 	Added trap MIB.
-- 	[1998/10/09  18:46:30  mlin]
-- 
-- $EndLog$

-- SECTION 1: Top Level Definitions

-- Alteon enterprise trap MIB
-- Version 1.0.0
-- Date: 8/18/99

ALTEON-TRAP-MIB DEFINITIONS ::= BEGIN

IMPORTS
        TRAP-TYPE
                FROM RFC-1215
        sysName, sysLocation, sysContact
                FROM RFC1213-MIB
        altswitchTraps, ipCurCfgGwIndex, ipCurCfgGwAddr,
        slbCurCfgRealServerIndex, slbCurCfgRealServerIpAddr,
        slbCurCfgRealServerName, fltCurCfgIndx, fltCurCfgPortIndx,
        slbCurCfgVirtServiceRealPort
                FROM ALTEON-PRIVATE-MIBS;

-- SECTION 2: 

altSwPrimaryPowerSuppylFailure TRAP-TYPE
        ENTERPRISE      altswitchTraps
        DESCRIPTION
                "A altSwPrimaryPowerSuppylFailure trap signifies that the 
		 primary power supply failed."
        ::= 1   -- 0x01

altSwRedunPowerSuppylFailure TRAP-TYPE
        ENTERPRISE      altswitchTraps
        DESCRIPTION
                "A altSwRedunPowerSuppylFailure trap signifies that the 
		 redundant power supply failed."
        ::= 2   -- 0x02

altSwDefGwUp TRAP-TYPE
        ENTERPRISE      altswitchTraps
        VARIABLES       { ipCurCfgGwIndex,
                          ipCurCfgGwAddr,
                          sysName, sysLocation, sysContact }
        DESCRIPTION
                "A altSwDefGwUp trap signifies that the default
                 gateway is alive."
        ::= 3   -- 0x03

altSwDefGwDown TRAP-TYPE
        ENTERPRISE      altswitchTraps
        VARIABLES       { ipCurCfgGwIndex,
                          ipCurCfgGwAddr,
                          sysName, sysLocation, sysContact }
        DESCRIPTION
                "A altSwDefGwDown trap signifies that the default
                 gateway is down."
        ::= 4   -- 0x04

altSwDefGwInService TRAP-TYPE
        ENTERPRISE      altswitchTraps
        VARIABLES       { ipCurCfgGwIndex,
                          ipCurCfgGwAddr,
                          sysName, sysLocation, sysContact }
        DESCRIPTION
                "A altSwDefGwEnabled trap signifies that the default
                 gateway is up and in service."
        ::= 5   -- 0x05

altSwDefGwNotInService TRAP-TYPE
        ENTERPRISE      altswitchTraps
        VARIABLES       { ipCurCfgGwIndex,
                          ipCurCfgGwAddr,
                          sysName, sysLocation, sysContact }
        DESCRIPTION
                "A altSwDefGwDisabled trap signifies that the default
                 gateway is alive but not in service."
        ::= 6   -- 0x06

altSwSlbRealServerUp TRAP-TYPE
        ENTERPRISE      altswitchTraps
        VARIABLES       { slbCurCfgRealServerIndex,
                          slbCurCfgRealServerIpAddr,
                          slbCurCfgRealServerName,
                          sysName, sysLocation, sysContact }
        DESCRIPTION
                "A altSwSlbRealServerUp trap signifies that the real
                 server is up and operational."
        ::= 7   -- 0x07

altSwSlbRealServerDown TRAP-TYPE
        ENTERPRISE      altswitchTraps
        VARIABLES       { slbCurCfgRealServerIndex,
                          slbCurCfgRealServerIpAddr,
                          slbCurCfgRealServerName,
                          sysName, sysLocation, sysContact }
        DESCRIPTION
                "A altSwSlbRealServerDown trap signifies that the real
                 server is down and out of service."
        ::= 8   -- 0x08

altSwSlbRealServerMaxConnReached TRAP-TYPE
        ENTERPRISE      altswitchTraps
        VARIABLES       { slbCurCfgRealServerIndex,
                          slbCurCfgRealServerIpAddr,
                          slbCurCfgRealServerName,
                          sysName, sysLocation, sysContact }
        DESCRIPTION
                "A altSwSlbRealServerMaxConnReached trap signifies that the 
		 real server has reached maximum connections."
        ::= 9   -- 0x09

altSwSlbBkupRealServerAct TRAP-TYPE
        ENTERPRISE      altswitchTraps
        VARIABLES       { slbCurCfgRealServerIndex,
                          slbCurCfgRealServerIpAddr,
                          slbCurCfgRealServerName,
                          sysName, sysLocation, sysContact }
        DESCRIPTION
                "A altSwSlbBkupRealServerAct trap signifies that the 
		 backup real server is activated due to availablity of the
		 primary real server."
        ::= 10   -- 0x0A

altSwSlbBkupRealServerDeact TRAP-TYPE
        ENTERPRISE      altswitchTraps
        VARIABLES       { slbCurCfgRealServerIndex,
                          slbCurCfgRealServerIpAddr,
                          slbCurCfgRealServerName,
                          sysName, sysLocation, sysContact }
        DESCRIPTION
                "A altSwSlbBkupRealServerDeact trap signifies that the 
		 backup real server is deactivated due to the primary real 
		 server is available."
        ::= 11   -- 0x0B

altSwSlbBkupRealServerActOverflow TRAP-TYPE
        ENTERPRISE      altswitchTraps
        VARIABLES       { slbCurCfgRealServerIndex,
                          slbCurCfgRealServerIpAddr,
                          slbCurCfgRealServerName,
                          sysName, sysLocation, sysContact }
        DESCRIPTION
                "A altSwSlbBkupRealServerActOverflow trap signifies 
		 that the backup real server is deactivated due to the primary 
		 real server is overflowed."
        ::= 12   -- 0x0C

altSwSlbBkupRealServerDeactOverflow TRAP-TYPE
        ENTERPRISE      altswitchTraps
        VARIABLES       { slbCurCfgRealServerIndex,
                          slbCurCfgRealServerIpAddr,
                          slbCurCfgRealServerName,
                          sysName, sysLocation, sysContact }
        DESCRIPTION
                "A altSwSlbBkupRealServerDeactOverflow trap signifies 
		 that the backup real server is deactivated due to the primary 
		 real server is out from overflow situation."
        ::= 13   -- 0x0D

altSwSlbFailoverStandby TRAP-TYPE
        ENTERPRISE      altswitchTraps
        DESCRIPTION
                "A altSwSlbFailoverStandby trap signifies that the switch
		 is now a standby switch."
        ::= 14   -- 0x0E

altSwSlbFailoverActive TRAP-TYPE
        ENTERPRISE      altswitchTraps
        DESCRIPTION
                "A altSwSlbFailoverActive trap signifies that the switch
		 is now an active switch."
        ::= 15   -- 0x0F

altSwSlbFailoverSwitchUp TRAP-TYPE
        ENTERPRISE      altswitchTraps
        DESCRIPTION
                "A altSwSlbFailoverSwitchUp trap signifies that the failover
		 switch is alive."
        ::= 16   -- 0x10

altSwSlbFailoverSwitchDown TRAP-TYPE
        ENTERPRISE      altswitchTraps
        DESCRIPTION
                "A altSwSlbFailoverSwitchDown trap signifies that the failover
		 switch is down."
        ::= 17   -- 0x11

altSwfltFilterFired TRAP-TYPE
        ENTERPRISE      altswitchTraps
        VARIABLES       { fltCurCfgIndx, fltCurCfgPortIndx,
                          sysName, sysLocation, sysContact }
        DESCRIPTION
                "A altSwfltFilterFired trap signifies that the packet 
		 received on a switch port matches the filter rule."
        ::= 18   -- 0x12

altSwSlbRealServerServiceUp TRAP-TYPE
        ENTERPRISE      altswitchTraps
        VARIABLES       { slbCurCfgRealServerIndex,
                          slbCurCfgRealServerIpAddr,
                          slbCurCfgRealServerName,
                          slbCurCfgVirtServiceRealPort,
                          sysName, sysLocation, sysContact }
        DESCRIPTION    
                "A altSwSlbRealServerServiceUp trap signifies that the 
                 service port of the real server is up and operational."
        ::= 19   -- 0x13
 
altSwSlbRealServerServiceDown TRAP-TYPE
        ENTERPRISE      altswitchTraps
        VARIABLES       { slbCurCfgRealServerIndex,
                          slbCurCfgRealServerIpAddr,
                          slbCurCfgRealServerName,
                          slbCurCfgVirtServiceRealPort,
                          sysName, sysLocation, sysContact }
        DESCRIPTION    
                "A altSwSlbRealServerServiceDown trap signifies that the 
                 service port of the real server is down and out of service."
        ::= 20   -- 0x14

END
