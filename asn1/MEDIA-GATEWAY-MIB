-- extracted from draft-ietf-megaco-mib-01.txt
-- at Sat Nov 25 16:04:51 2000

MEDIA-GATEWAY-MIB DEFINITIONS ::= BEGIN

        IMPORTS MODULE-IDENTITY, OBJECT-TYPE, NOTIFICATION-TYPE,
            Unsigned32, Gauge32, Counter32, Counter64,
            TimeTicks, Integer32
        FROM SNMPv2-SMI
            TEXTUAL-CONVENTION, TAddress, DisplayString,
            DateAndTime
        FROM SNMPv2-TC
            MODULE-COMPLIANCE, OBJECT-GROUP
        FROM SNMPv2-CONF
            ifIndex, InterfaceIndex
        FROM IF-MIB
            IpAddress, TimeTicks
        FROM RFC1155-SMI;

        --groups in media gateway MIB



mediaGateway
        MODULE-IDENTITY
        mediaGatewaySystem OBJECT IDENTIFIER::= {mediaGateway 1}
        mediaGatewayConfiguration OBJECT IDENTIFIER::= {mediaGateway 2}
        mediaGatewayCapabilities OBJECT IDENTIFIER::= {mediaGateway 3}
        mediaGatewayConnections OBJECT IDENTIFIER::= {mediaGateway 4}
        mediaGatewayStatistics OBJECT IDENTIFIER::= {mediaGateway 5}
        mediaGatewayControls OBJECT IDENTIFIER::= {mediaGateway 6}
        mediaGatewayNotifications OBJECT IDENTIFIER::={mediaGateway 7 0}
        LAST-UPDATED "9910??1200Z" -- October ??, 1999
        ORGANIZATION " "
        CONTACT-INFO " "

    DESCRIPTION
        "The MIB Module supports the functions of media gateway."

    ::= { xxx 1 }

--
-- mediaGateway System Group
--

mediaGatewayNumLinks OBJECT-TYPE
        SYNTAX         INTEGER
        ACCESS         read-only
        STATUS         mandatory
        DESCRIPTION    "Number of media gateway links (link groups)
                  available in this system."
        ::= { mediaGatewaySystem 1 }

        --
        -- Configuration Group
        --

mediaGatewayMasterMGCaddress OBJECT-TYPE
            SYNTAX         TAddress
            MAX-ACCESS     read-write
            STATUS         current
            DESCRIPTION
                "The address of the master Media Gateway Controller."
                ::= { mediaGatewayConfiguration 1 }

mediaGatewayMaxTerminations OBJECT-TYPE
            SYNTAX         Integer32
            MAX-ACCESS     read-only
            STATUS         current
            DESCRIPTION
                "The maximum number of Terminations in a Context."
                ::= { mediaGatewayConfiguration 3 }

mediaGatewayActiveContext OBJECT-TYPE
            SYNTAX         Integer32
            MAX-ACCESS     read-only
            STATUS         current
            DESCRIPTION
                "The number of active contexts."
                ::= { mediaGatewayConfiguration 4 }

--
-- Connections Group
--

-- Context table

mediaGatewayContextTable OBJECT-TYPE
            SYNTAX         SEQUENCE OF MediaGatewayContextEntry
            MAX-ACCESS     not-accessible
            STATUS         current
            DESCRIPTION
                "This table contains context information
                for instances of a MEGACO protocol."
                ::= { mediaGatewayConnections 1}

mediaGatewayContextEntry OBJECT-TYPE
            SYNTAX         MediaGatewayContextEntry
            MAX-ACCESS     not-accessible
            STATUS         current
            DESCRIPTION
                "It contains objects that describe the contexts."
            INDEX          { mediaGatewayId,
            mediaGatewayContextId }
            ::= { mediaGatewayContextTable 1 }

MediaGatewayContextEntry::=
            SEQUENCE {
                mediaGatewayId
                    Integer32,
                mediaGatewayContextId
                    Integer32,
                mediaGatewayNumberOfTerminations
                    Integer32,
                mediaGatewayContextStartTime
                    DateAndTime
            }

mediaGatewayId OBJECT-TYPE
            SYNTAX         Integer32
            MAX-ACCESS     read-only
            STATUS         current
            DESCRIPTION
                "The Gateway Id."
                ::= { mediaGatewayContextEntry 1 }

mediaGatewayContextId OBJECT-TYPE
            SYNTAX         Integer32
            MAX-ACCESS     read-only
            STATUS         current
            DESCRIPTION
            "The Context Id."
            ::= { mediaGatewayContextEntry 2 }

mediaGatewayNumberOfTerminations OBJECT-TYPE
            SYNTAX         Integer32
            MAX-ACCESS     read-only
            STATUS         current
            DESCRIPTION
            "The number of terminations in a Context."
            ::= { mediaGatewayContextEntry 3 }

mediaGatewayContextStartTime OBJECT-TYPE
            SYNTAX         DateAndTime
            MAX-ACCESS     read-only
            STATUS         current
            DESCRIPTION
            "The date and time when Context was created."
            ::= { mediaGatewayContextEntry 4 }

--
-- Terminations
--
mediaGatewayTerminationsTable OBJECT-TYPE
            SYNTAX         SEQUENCE OF MediaGatewayTerminationsTableEntry
            MAX-ACCESS     not-accessible
            STATUS         current
            DESCRIPTION
                    "This table contains information about terminations in
                    a media gateway. It is a list of terminations. The
                    number of entries equals to the total number of
                    terminations for all contexts in a gateway."
            ::= { mediaGatewayConnections 2}

mediaGatewayTerminationsTableEntry OBJECT-TYPE
            SYNTAX         MediaGatewayTerminationsTableEntry
            MAX-ACCESS     not-accessible
            STATUS         current
            DESCRIPTION
                      "It contains objects that describe a termination."
            INDEX          { mediaGatewayId,
            mediaGatewayContextId
            mediaGatewayTerminationId }

::= { mediaGatewayTerminationsTable 1 }
MediaGatewayTerminationsTableEntry::=
            SEQUENCE {
                mediaGatewayTerminationId
                    Integer32,
                mediaGatewayTerminationType
                    INTEGER,
                mediaGatewayTerminationNumberOfStreams
                    Integer32,
                mediaGatewayTerminationMGCRequestedProperties
                    DisplayString,
                mediaGatewayTerminationActualProperties
                    DisplayString,
                mediaGatewayTerminationLastCommand
                    DisplayString,
                mediaGatewayTerminationStartTime
                DateAndTime

                }

mediaGatewayTerminationId OBJECT-TYPE
    SYNTAX         Integer32
    MAX-ACCESS     not-accessible
    STATUS         current
    DESCRIPTION
                    "An identification number that is assign to
                    the termination by a media gateway. "
            ::= { mediaGatewayTerminationsTableEntry 1 }

mediaGatewayTerminationType OBJECT-TYPE
    SYNTAX         INTEGER
    MAX-ACCESS     read-only
    STATUS         current
    DESCRIPTION
    "The termination type. "
    ::= { mediaGatewayTerminationsTableEntry 2 }

mediaGatewayTerminationNumberOfStreams OBJECT-TYPE
    SYNTAX         INTEGER
    MAX-ACCESS     read-only
    STATUS         current
    DESCRIPTION
    "The number of streams pertaining to the termination. "
    ::= { mediaGatewayTerminationsTableEntry 3 }

mediaGatewayTerminationMGCRequestedProperties OBJECT-TYPE
    SYNTAX         DisplayString
    MAX-ACCESS     read-only
    STATUS         current
    DESCRIPTION
    "The list of the properties requested by MGC in a
    form of descriptors. "
    ::= { mediaGatewayTerminationsTableEntry 4 }

mediaGatewayTerminationActualProperties OBJECT-TYPE
    SYNTAX         DisplayString
    MAX-ACCESS     read-only
    STATUS         current
    DESCRIPTION
    "The list of the actual properties for this termination. "
    ::= { mediaGatewayTerminationsTableEntry 5 }

mediaGatewayTerminationLastCommand OBJECT-TYPE
    SYNTAX         DisplayString
    MAX-ACCESS     read-only
    STATUS         current
    DESCRIPTION
    "The last command that was sent to this termination."
    ::= { mediaGatewayTerminationsTableEntry 6 }

mediaGatewayTerminationStartTime OBJECT-TYPE
    SYNTAX         DateAndTime
    MAX-ACCESS     read-only
    STATUS         current
    DESCRIPTION
    "The time of termination creation. "
    ::= { mediaGatewayTerminationsTableEntry 7 }

--
-- statistics
--

            -- Media Gateway Status & Statistics Group

            -- This group contains monitoring and statistical information
            -- for media gateway control interfaces.

mediaGatewayTable   OBJECT-TYPE
    SYNTAX              SEQUENCE OF MediaGatewayTableEntry
    ACCESS              not-accessible
    STATUS              mandatory
    DESCRIPTION         "A list of mediaGatewayTableEntry objects."
    ::= { mediaGatewayStatistics 1 }

mediaGatewayTableEntry   OBJECT-TYPE
    SYNTAX              MediaGatewayTableEntry
    ACCESS              not-accessible
    STATUS              mandatory
    DESCRIPTION         "Entry holding information about a group of
                   Media Gateway Controllers sharing the same
                   signaling link."
    INDEX               { mediaGatewayLinkName }
    ::= { mediaGatewayTable 1 }

MediaGatewayTableEntry ::=
    SEQUENCE {
        mediaGatewayLinkName                    OCTET STRING,
        mediaGatewayProtocol                    INTEGER,
        mediaGatewayAdminStatus            INTEGER,
        mediaGatewayOperStatus                  INTEGER,
        mediaGatewayLastStatusChange            TimeTicks,
        mediaGatewayNumInMessages               Counter32,
        mediaGatewayNumInOctets            Counter32,
        mediaGatewayNumOutMessages              Counter32,
        mediaGatewayNumOutOctets                Counter32,
        mediaGatewayNumErrors                   Counter32,
        mediaGatewayNumTimerRecovery            Counter32,
        mediaGatewayTransportNumLosses               Counter32,
        mediaGatewayTransportNumSwitchover           Counter32,
        mediaGatewayTransportTotalNumAlarms          Counter32,
        mediaGatewayTransportLastEvent               INTEGER,
        mediaGatewayTransportLastEventTime           TimeTicks,
        mediaGatewayResetStatistics             INTEGER,
        mediaGatewayLastStatisticsReset         TimeTicks
    }

-- Objects in mediaGatewayTableEntry:

mediaGatewayLinkName OBJECT-TYPE
    SYNTAX              OCTET STRING
    ACCESS              read-only
    STATUS              mandatory
    DESCRIPTION         "Name of this media gateway control group."
    ::= { mediaGatewayTableEntry 1 }

mediaGatewayProtocol OBJECT-TYPE
    SYNTAX               INTEGER {
                    notApplicable(1), --
                    other(2), -- Other (none from the list below)
                    dss1-ip(3), -- Q931+
                    ipdc(4) -- IPDC
                    megaco(5) -- MEGACO/H.248
                    }
    ACCESS         read-only
    STATUS         mandatory
    DESCRIPTION    "Type of the control protocol in use."
    ::= { mediaGatewayTableEntry 2 }

mediaGatewayAdminStatus OBJECT-TYPE
    SYNTAX          INTEGER {
                    up(1),
                    down(2)
                    }
    ACCESS         read-write
    STATUS         mandatory
    DESCRIPTION    "Administrative status for this media gateway
              control group."
    ::= { mediaGatewayTableEntry 3 }

mediaGatewayOperStatus        OBJECT-TYPE
    SYNTAX                   INTEGER {
                    up(1),
                    down(2),
                    unknown(3)
                    }
    ACCESS         read-only
    STATUS         mandatory
    DESCRIPTION    "Current operational status of the signaling link."
    ::= { mediaGatewayTableEntry 4 }

mediaGatewayLastStatusChange OBJECT-TYPE
    SYNTAX         TimeTicks
    ACCESS         read-only
    STATUS         mandatory
    DESCRIPTION    "The value of sysUpTime at the time the associated
              link entered its current operational status. If
              the current status was entered prior to the last
              re-initialization of the local network management
              subsystem, then this object contains a zero value."
    ::= { mediaGatewayTableEntry 5 }

mediaGatewayNumInMessages OBJECT-TYPE
    SYNTAX         Counter32
    ACCESS         read-only
    STATUS         mandatory
    DESCRIPTION    "Total number of messages received on the link."
    ::= { mediaGatewayTableEntry 6 }

mediaGatewayNumInOctets OBJECT-TYPE
    SYNTAX         Counter32
    ACCESS         read-only
    STATUS         mandatory
    DESCRIPTION    "Total number of octets received on the link."
    ::= { mediaGatewayTableEntry 7 }

mediaGatewayNumOutMessages OBJECT-TYPE
    SYNTAX         Counter32
    ACCESS         read-only
    STATUS         mandatory
    DESCRIPTION    "Total number of messages sent on the link."
    ::= { mediaGatewayTableEntry 8 }

mediaGatewayNumOutOctets OBJECT-TYPE
    SYNTAX         Counter32
    ACCESS         read-only
    STATUS         mandatory
    DESCRIPTION    "Total number of octets sent on the link."
    ::= { mediaGatewayTableEntry 9 }

mediaGatewayNumErrors OBJECT-TYPE
    SYNTAX         Counter32
    ACCESS         read-only
    STATUS         mandatory
    DESCRIPTION    "Total number of signaling-level errors
              encountered. Includes, but is not limited to,
              number of bad messages received, number of
              failures to sent a message and number of other
              errors."
    ::= { mediaGatewayTableEntry 10 }

mediaGatewayNumTimerRecovery OBJECT-TYPE
    SYNTAX         Counter32
    ACCESS         read-only
    STATUS         mandatory
    DESCRIPTION    "Number of timer recovery events since the
              statistics was last reset. This reflects
              all timers."
    ::= { mediaGatewayTableEntry 11 }

mediaGatewayTransportNumLosses OBJECT-TYPE
    SYNTAX         Counter32
    ACCESS         read-only
    STATUS         mandatory
    DESCRIPTION    "Number of times a transport link was lost (excluding
              switch-over cases)."
    ::= { mediaGatewayTableEntry 12 }

mediaGatewayTransportNumSwitchover OBJECT-TYPE
    SYNTAX         Counter32
    ACCESS         read-only
    STATUS         mandatory
    DESCRIPTION    "Number of times when the signaling was switched
              over to an alternative link."
    ::= { mediaGatewayTableEntry 13 }

mediaGatewayTransportTotalNumAlarms OBJECT-TYPE
    SYNTAX         Counter32
    ACCESS         read-only
    STATUS         mandatory
    DESCRIPTION    "Total number of all alarms issued for
              the transport layer."
    ::= { mediaGatewayTableEntry 14 }

mediaGatewayTransportLastEvent OBJECT-TYPE
    SYNTAX         INTEGER {
                    notApplicable(1), -- Invalid/unknown.
                    other(2), -- None from the list below.
                    linkUp(3), -- Transport link is up.
                    linkLoss(4), -- Transport link loss.
                    persistentError(5), -- No link - persistent error.
                    linkShutdown(6), -- Link is shut down.
                    switchOver(7) -- Fail-over.
                    }
    ACCESS         read-only
    STATUS         mandatory
    DESCRIPTION    "Last event reported by the transport layer."
    ::= { mediaGatewayTableEntry 15 }

mediaGatewayTransportLastEventTime OBJECT-TYPE
    SYNTAX         TimeTicks
    ACCESS         read-only
    STATUS         mandatory
    DESCRIPTION    "The value of sysUpTime at the time when the event
              specified by mediaGatewayTransportLastEvent occured.
              If the last event occured prior to the last
              re-initialization of the local network management
              subsystem, then this object contains a zero value."
    ::= { mediaGatewayTableEntry 16 }

mediaGatewayResetStatistics OBJECT-TYPE
    SYNTAX         INTEGER {
                    notApplicable(1), -- Invalid/unknown.
                    other(2), -- None from the list below.
                    reset(3) -- Reset all statistics now.
                    }
    ACCESS         read-write
    STATUS         mandatory
    DESCRIPTION    "This object can be used to reset all statistics
              collected for this media gateway link so far.
              Statistics will be reset when the object is SET
              to 'reset'. GET from this object always returns
              'notApplicable'."
    ::= { mediaGatewayTableEntry 17 }

mediaGatewayLastStatisticsReset OBJECT-TYPE
    SYNTAX         TimeTicks
    ACCESS         read-only
    STATUS         mandatory
    DESCRIPTION    "The value of sysUpTime at the time when the
              statistics was reset. If the reset occured
              prior to the last re-initialization of the local
              network management subsystem, this object contains
              a zero value."
    ::= { mediaGatewayTableEntry 18 }

-- End of mediaGatewayTableEntry.


mediaGatewayControllerTable OBJECT-TYPE
    SYNTAX         SEQUENCE OF mediaGatewayControllerEntry
    ACCESS         not-accessible
    STATUS         mandatory
    DESCRIPTION    "Addresses of Media Gateway Controllers."
    ::= { mediaGatewayGroup 3 }

mediaGatewayControllerEntry OBJECT-TYPE
    SYNTAX         MediaGatewayControllerEntry
    ACCESS         not-accessible
    STATUS         mandatory
    DESCRIPTION    "Entry holding information about an individual
              Media Gateway Controller."
    INDEX          { mediaGatewayControllerLinkName, mediaGatewayControllerIndex }
    ::= { mediaGatewayControllerTable 1 }

MediaGatewayControllerEntry ::=
    SEQUENCE {
        mediaGatewayControllerLinkName          OCTET STRING,
        mediaGatewayControllerIndex        INTEGER,
        mediaGatewayControllerIPAddress    IpAddress,
        mediaGatewayControllerPort         INTEGER,
        mediaGatewayControllerOperStatus   INTEGER
        }

-- Objects in mediaGatewayControllerEntry:

mediaGatewayControllerLinkName OBJECT-TYPE
    SYNTAX         OCTET STRING
    ACCESS         read-only
    STATUS         mandatory
    DESCRIPTION    "The same as mediaGatewayLinkName."
    ::= { mediaGatewayControllerEntry 1 }

mediaGatewayControllerIndex OBJECT-TYPE
    SYNTAX         INTEGER
    ACCESS         read-only
    STATUS         mandatory
    DESCRIPTION    "The index number for this Media Gateway Controller
              entry. Its value ranges from 1 to the maximum
              number of controllers per group and identifies
              which controller the entry is associated with."
    ::= { mediaGatewayControllerEntry 2 }

mediaGatewayControllerIPAddress OBJECT-TYPE
    SYNTAX         IpAddress
    ACCESS         read-only
    STATUS         mandatory
    DESCRIPTION    "The IP address of the Media Gateway Controller. The
              value 0.0.0.0 is returned if the entry is invalid."
    ::= { mediaGatewayControllerEntry 3 }

mediaGatewayControllerPort OBJECT-TYPE
    SYNTAX         INTEGER ( 0..'FFFF'h )
    ACCESS         read-only
    STATUS         mandatory
    DESCRIPTION    "TCP port of the Media Gateway Controller. The value
              0 is returned if the entry is invalid."
    ::= { mediaGatewayControllerEntry 4 }

mediaGatewayControllerOperStatus OBJECT-TYPE
    SYNTAX         INTEGER {
                    up(1), -- Up/active.
                    down(2), -- Down.
                    standby(3) -- Standby mode.
                    }
    ACCESS         read-only
    STATUS         mandatory
    DESCRIPTION    "Status of the transport link to this particular
              Media Gateway Controller."
    ::= { mediaGatewayControllerEntry 5 }

--
-- Traps
--

megacoLinkStatusTrap TRAP-TYPE
        ENTERPRISE XXX
        VARIABLES { mgLinkName, mgOperStatus }
        DESCRIPTION "This trap indicates that operational status
        of a media gateway control link has changed."
        ::= 42

-- End of mediaGatewayControllerEntry.

-- *****************************************************************************
--
-- OID and Group Definitions
--
-- *****************************************************************************


-- OID for the MIB Objects...
mediaGatewayMIBObjects    OBJECT IDENTIFIER::= { mediaGatewayMIB 1 }




--The Media Gateway MIB contains 4 (object) groups


medGwyConfiguration OBJECT IDENTIFIER::= { mediaGatewayMIBObjects 1 }
medGwyStatistics    OBJECT IDENTIFIER::= { mediaGatewayMIBObjects 2 }
medGwyConnections   OBJECT IDENTIFIER::= { mediaGatewayMIBObjects 3 }
medGwyProperties    OBJECT IDENTIFIER::= { mediaGatewayMIBObjects 4 }





-- *****************************************************************************
--
-- Textual conventions for the Media Gateway MIB
--
-- *****************************************************************************


MediaGatewayId ::= TEXTUAL-CONVENTION
    STATUS      current
    DESCRIPTION "Possible Media Gateway Id"
    SYNTAX      INTEGER (1..2147483647)







-- *****************************************************************************
--
-- medGwyLinkIdTable
--
--   Gateway LinkId Table...
--
--   Provides the manager with the nextId for use in creating a LinkId
--   There is one entry in this table for each MediaGateway.
--
-- Note:
--   If this table isn't implemented, the manager would be responsible for
--   providing the (unique) nextId (via retaining used id's, hashing, etc)
-- *****************************************************************************



medGwyLinkIdTable OBJECT-TYPE
    SYNTAX       SEQUENCE OF MedGwyLinkIdEntry
    MAX-ACCESS   not-accessible
    STATUS       current
    DESCRIPTION
                "This table contains a nextLinkId for each Gateway.
                 It provides the manager with the nextLinkId for use
                 in creating new Gateway Table Entries."
::= { medGwyConfiguration 1}


medGwyLinkIdEntry OBJECT-TYPE
    SYNTAX       MedGwyLinkIdEntry
    MAX-ACCESS   not-accessible
    STATUS       current
    DESCRIPTION "
                 This table contains the NextLinkId for this Gateway
                 One entry per mediaGatewayId.
                "
    INDEX        { medGwyGatewayId }
::= { medGwyLinkIdTable 1 }



MedGwyLinkIdEntry ::= SEQUENCE
{
    medGwyNextLinkId                    TestAndIncr         -- rw
}


medGwyNextLinkId OBJECT-TYPE
    SYNTAX        TestAndIncr
    MAX-ACCESS    read-write
    STATUS        current
    DESCRIPTION
       "The Next Value for a MediaGateway LinkId.  Assists the
        manager in selecting a value for medGwyGatewayLinkId.
        Using the TestAndIncr syntax, A Manager will 'lock' this
        variable, ensuring single access."
::= { medGwyLinkIdEntry 1 }






-- *****************************************************************************
--
-- medGwyGatewayConfigTable
--
--   The Media Gateway Config Table...
--
--   There is one entry in this table for each MediaGateway/SignallingLink.
--
-- *****************************************************************************


medGwyGatewayConfigTable       OBJECT-TYPE
    SYNTAX      SEQUENCE OF MedGwyGatewayConfigEntry
    MAX-ACCESS  not-accessible
    STATUS      current
    DESCRIPTION "A list of medGwyGatewayConfigEntry objects."
::= { medGwyConfiguration 2 }


medGwyGatewayConfigEntry  OBJECT-TYPE
    SYNTAX       MedGwyGatewayConfigEntry
    MAX-ACCESS   not-accessible
    STATUS       current
    DESCRIPTION "Entry holding configuration information about a group of
                 Media Gateway Controllers sharing the same signaling link."
    INDEX      { medGwyGatewayId, medGwyGatewayLinkId }
::= { medGwyGatewayConfigTable 1 }


MedGwyGatewayConfigEntry ::= SEQUENCE
{
    medGwyGatewayId                     MediaGatewayId,     -- na
    medGwyGatewayLinkId                 Integer32,          -- na
    medGwyGatewayLinkName               OCTET STRING,       -- rc
    medGwyGatewayIPAddress              IpAddress,          -- rc
    medGwyGatewayPort                   Integer32,          -- rc
    medGwyGatewayProtocol               INTEGER,            -- rc
    medGwyGatewayAdminStatus            INTEGER,            -- rc
    medGwyGatewayOperStatus             INTEGER,            -- ro
    medGwyGatewayLastStatusChange       TimeTicks,          -- ro
    medGwyGatewayResetStatistics        INTEGER,            -- rc
    medGwyGatewayRowStatus              RowStatus           -- rc
}



medGwyGatewayId OBJECT-TYPE
    SYNTAX       MediaGatewayId
    MAX-ACCESS   not-accessible
    STATUS       current
    DESCRIPTION "The Gateway Id."
::= { medGwyGatewayConfigEntry 1 }


medGwyGatewayLinkId OBJECT-TYPE
    SYNTAX       Integer32
    MAX-ACCESS   not-accessible
    STATUS       current
    DESCRIPTION "The Gateway Id."
::= { medGwyGatewayConfigEntry 2 }


--  SIZE of this may change??
medGwyGatewayLinkName OBJECT-TYPE
    SYNTAX      OCTET STRING  ( SIZE (0..32) )
    MAX-ACCESS  read-create
    STATUS      current
    DESCRIPTION "Name of this media gateway control group."
::= { medGwyGatewayConfigEntry 3 }


medGwyGatewayIPAddress OBJECT-TYPE
    SYNTAX      IpAddress
    MAX-ACCESS  read-create
    STATUS      current
    DESCRIPTION "The IP address that the Media Gateway Controller
                 will use to communicate with the Media Gateway.
                 The value 0.0.0.0 is returned if the entry is invalid."
::= { medGwyGatewayConfigEntry 4 }


medGwyGatewayPort OBJECT-TYPE
    SYNTAX      Integer32 (0..65535)
    MAX-ACCESS  read-create
    STATUS      current
    DESCRIPTION "TCP port that the Media Gateway Controller will use
                 to communiacte with the Media Gateway. The value
                 0 is returned if the entry is invalid."
::= { medGwyGatewayConfigEntry 5 }


medGwyGatewayProtocol OBJECT-TYPE
    SYNTAX     INTEGER
               {
                 notApplicable(1),  --
                 other        (2),  -- Other (none from the list below)
                 dss1-ip      (3),  -- Q931+
                 ipdc         (4),  -- IPDC
                 megaco       (5)   -- MEGACO/H.248
               }


    MAX-ACCESS  read-create
    STATUS      current
    DESCRIPTION "Type of the control protocol in use."
::= { medGwyGatewayConfigEntry 6 }


medGwyGatewayAdminStatus OBJECT-TYPE
    SYNTAX     INTEGER
               {
                 up   (1),
                 down (2)
               }
    MAX-ACCESS  read-create
    STATUS      current
    DESCRIPTION "Administrative status for this media gateway
                   control group."
::= { medGwyGatewayConfigEntry 7 }


medGwyGatewayOperStatus  OBJECT-TYPE
    SYNTAX     INTEGER
               {
                 up     (1),
                 down   (2),
                 unknown(3)
               }
    MAX-ACCESS  read-only
    STATUS      current
    DESCRIPTION "Current operational status of the signaling link."
::= { medGwyGatewayConfigEntry 8 }


medGwyGatewayLastStatusChange OBJECT-TYPE
    SYNTAX      TimeTicks
    MAX-ACCESS  read-only
    STATUS      current
    DESCRIPTION "The value of sysUpTime at the time the associated
                 link entered its current operational status. If
                 the current status was entered prior to the last
                 re-initialization of the local network management
                 subsystem, then this object contains a zero value."
::= { medGwyGatewayConfigEntry 9 }


medGwyGatewayResetStatistics OBJECT-TYPE
    SYNTAX     INTEGER
               {
                  notApplicable (1), -- Invalid/unknown.
                  other         (2), -- None from the list below.
                  reset         (3)  -- Reset all statistics now.
               }
    MAX-ACCESS  read-create
    STATUS      current
    DESCRIPTION "This object can be used to reset all statistics
                 collected for this media gateway link so far.
                 Statistics will be reset when the object is SET
                 to 'reset'.  Upon reset, the agent changes the value of
                 this object to 'notApplicable'."
::= { medGwyGatewayConfigEntry 10 }


medGwyGatewayRowStatus OBJECT-TYPE
    SYNTAX      RowStatus
    MAX-ACCESS  read-create
    STATUS      current
    DESCRIPTION "This is used to create new rows in this table, modify
                 existing rows, and to delete existing rows."
::= { medGwyGatewayConfigEntry 11 }




-- *****************************************************************************
--
-- medGwyGatewayControllerTable
--
--   The Media Gateway Controller Table...
--
--   'List' of Media Gateway Controllers (on a media gateway), and
--   Configuration Information on these Controllers.
--
--    An Entry in this Table is automatically created when a manager creates
--    an entry in the medGwyGatewayConfigTable
--
-- *****************************************************************************


medGwyGatewayControllerTable OBJECT-TYPE
    SYNTAX       SEQUENCE OF MedGwyGatewayControllerEntry
    MAX-ACCESS   not-accessible
    STATUS       current
    DESCRIPTION "Addresses of Media Gateway Controllers."
    ::= { medGwyConfiguration 3 }


medGwyGatewayControllerEntry OBJECT-TYPE
    SYNTAX      MedGwyGatewayControllerEntry
    MAX-ACCESS  not-accessible
    STATUS      current
    DESCRIPTION "Entry holding information about an individual
                 Media Gateway Controller."
    INDEX      { medGwyGatewayId, medGwyGatewayLinkId }
    ::= { medGwyGatewayControllerTable 1 }


MedGwyGatewayControllerEntry ::= SEQUENCE
{
    mediaGatewayControllerIPAddress      IpAddress,          -- rw
    mediaGatewayControllerPort           Integer32,          -- rw
    mediaGatewayControllerOperStatus     INTEGER             -- ro
}



mediaGatewayControllerIPAddress OBJECT-TYPE
    SYNTAX      IpAddress
    MAX-ACCESS  read-write
    STATUS      current
    DESCRIPTION "The IP address of the Media Gateway Controller. The
                 value 0.0.0.0 is returned if the entry is invalid."
::= { medGwyGatewayControllerEntry 1 }


mediaGatewayControllerPort OBJECT-TYPE
    SYNTAX      Integer32 (0..65535)
    MAX-ACCESS  read-write
    STATUS      current
    DESCRIPTION "TCP port of the Media Gateway Controller. The value
                 0 is returned if the entry is invalid."
::= { medGwyGatewayControllerEntry 2 }


mediaGatewayControllerOperStatus OBJECT-TYPE
    SYNTAX     INTEGER
               {
                  up      (1), -- Up/active.
                  down    (2), -- Down.
                  standby (3)  -- Standby mode.
               }
    MAX-ACCESS  read-only
    STATUS      current
    DESCRIPTION "Status of the Media Gateway Controller (and/or)
                 its transportLink."
::= { medGwyGatewayControllerEntry 3 }




-- *****************************************************************************
--
-- medGwyGatewayStatsTable
--
--   The Media Gateway Stats Table...
--
--   There is one entry in this table for each MediaGateway/SignallingLink.
--   The Agent creates this table, when a GatewayConfig Table Entry is created.
--
-- *****************************************************************************
medGwyGatewayStatsTable       OBJECT-TYPE
    SYNTAX      SEQUENCE OF MedGwyGatewayStatsEntry
    MAX-ACCESS  not-accessible
    STATUS      current
    DESCRIPTION "A list of mediaGatewayTableEntry objects."
::= { medGwyStatistics 1 }


medGwyGatewayStatsEntry  OBJECT-TYPE
    SYNTAX      MedGwyGatewayStatsEntry
    MAX-ACCESS  not-accessible
    STATUS      current
    DESCRIPTION "Entry holding stats about a group of
                 Media Gateway Controllers sharing the same
                 signaling link."
    INDEX      { medGwyGatewayId, medGwyGatewayLinkId }
::= { medGwyGatewayStatsTable 1 }


MedGwyGatewayStatsEntry ::= SEQUENCE
{
    medGwyGatewayNumInMessages           Counter32,          -- ro
    medGwyGatewayNumInOctets             Counter32,          -- ro
    medGwyGatewayNumOutMessages          Counter32,          -- ro
    medGwyGatewayNumOutOctets            Counter32,          -- ro
    medGwyGatewayNumErrors               Counter32,          -- ro
    medGwyGatewayNumTimerRecovery        Counter32,          -- ro
    medGwyGatewayTransportNumLosses      Counter32,          -- ro
    medGwyGatewayTransportNumSwitchover  Counter32,          -- ro
    medGwyGatewayTransportTotalNumAlarms Counter32,          -- ro
    medGwyGatewayTransportLastEvent      INTEGER,            -- ro
    medGwyGatewayTransportLastEventTime  TimeTicks,          -- ro
    medGwyGatewayLastStatisticsReset     TimeTicks           -- ro
}



medGwyGatewayNumInMessages OBJECT-TYPE
    SYNTAX      Counter32
    MAX-ACCESS  read-only
    STATUS      current
    DESCRIPTION "Total number of messages received on the link."
::= { medGwyGatewayStatsEntry 1 }


medGwyGatewayNumInOctets OBJECT-TYPE
    SYNTAX      Counter32
    MAX-ACCESS  read-only
    STATUS      current
    DESCRIPTION "Total number of octets received on the link."
::= { medGwyGatewayStatsEntry 2 }


medGwyGatewayNumOutMessages OBJECT-TYPE
    SYNTAX      Counter32
    MAX-ACCESS  read-only
    STATUS      current
    DESCRIPTION "Total number of messages sent on the link."
::= { medGwyGatewayStatsEntry 3 }


medGwyGatewayNumOutOctets OBJECT-TYPE
    SYNTAX      Counter32
    MAX-ACCESS  read-only
    STATUS      current
    DESCRIPTION "Total number of octets sent on the link."
::= { medGwyGatewayStatsEntry 4 }


medGwyGatewayNumErrors OBJECT-TYPE
    SYNTAX      Counter32
    MAX-ACCESS  read-only
    STATUS      current
    DESCRIPTION "Total number of signaling-level errors encountered.
                 Includes, but is not limited to, number of bad messages
                 received, number of failures to sent a message and number
                 of other errors."
::= { medGwyGatewayStatsEntry 5 }


medGwyGatewayNumTimerRecovery OBJECT-TYPE
    SYNTAX      Counter32
    MAX-ACCESS  read-only
    STATUS      current
    DESCRIPTION "Number of timer recovery events since the statistics was
                 last reset. This reflects all timers."
::= { medGwyGatewayStatsEntry 6 }


medGwyGatewayTransportNumLosses OBJECT-TYPE
    SYNTAX      Counter32
    MAX-ACCESS  read-only
    STATUS      current
    DESCRIPTION "Number of times a transport link was lost (excluding
                 switch-over cases)."
::= { medGwyGatewayStatsEntry 7 }


medGwyGatewayTransportNumSwitchover OBJECT-TYPE
    SYNTAX      Counter32
    MAX-ACCESS  read-only
    STATUS      current
    DESCRIPTION "Number of times when the signaling was switched
                 over to an alternative link."
::= { medGwyGatewayStatsEntry 8 }


medGwyGatewayTransportTotalNumAlarms OBJECT-TYPE
    SYNTAX      Counter32
    MAX-ACCESS  read-only
    STATUS      current
    DESCRIPTION "Total number of all alarms issued for the transport layer."
::= { medGwyGatewayStatsEntry 9 }


medGwyGatewayTransportLastEvent OBJECT-TYPE
    SYNTAX     INTEGER
               {
                  notApplicable   (1), -- Invalid/unknown.
                  other           (2), -- None from the list below.
                  linkUp          (3), -- Transport link is up.
                  linkLoss        (4), -- Transport link loss.
                  persistentError (5), -- No link - persistent error.
                  linkShutdown    (6), -- Link is shut down.
                  switchOver      (7)  -- Fail-over.
               }
    MAX-ACCESS   read-only
    STATUS       current
    DESCRIPTION  "Last event reported by the transport layer."
::= { medGwyGatewayStatsEntry 10 }


medGwyGatewayTransportLastEventTime OBJECT-TYPE
    SYNTAX      TimeTicks
    MAX-ACCESS  read-write
    STATUS      current
    DESCRIPTION "The value of sysUpTime at the time when the event
                 specified by mediaGatewayTransportLastEvent occured.
                 If the last event occured prior to the last
                 re-initialization of the local network management
                 subsystem, then this object contains a zero value."
::= { medGwyGatewayStatsEntry 11 }


medGwyGatewayLastStatisticsReset OBJECT-TYPE
    SYNTAX      TimeTicks
    MAX-ACCESS  read-only
    STATUS      current
    DESCRIPTION "The value of sysUpTime at the time when the statistics
                 was reset. If the reset occured prior to the last
                 re-initialization of the local network management
                 subsystem, this object contains a zero value."
::= { medGwyGatewayStatsEntry 12 }





-- *****************************************************************************
--
-- medGwyTermIdTable
--
--   TerminationId Table...
--
--   Provides the manager with the nextId for use in creating a Termination
--   There is one entry in this table for each MediaGateway.
--
-- Note:
--   If this table isn't implemented, the manager would be responsible for
--   providing the (unique) nextId (via retaining used id's, hashing, etc)
-- *****************************************************************************



medGwyTermIdTable OBJECT-TYPE
    SYNTAX       SEQUENCE OF MedGwyTermIdEntry
    MAX-ACCESS   not-accessible
    STATUS       current
    DESCRIPTION
                "This table contains a nextTerminationId for each Gateway.
                 It provides the manager with the nextTerminationId for use
                 in creating a new TerminationsTable Entry."
::= { medGwyConnections 1}


medGwyTermIdEntry OBJECT-TYPE
    SYNTAX       MedGwyTermIdEntry
    MAX-ACCESS   not-accessible
    STATUS       current
    DESCRIPTION
                "This table contains a nextTerminationId for each Gateway,
                 and is indexed by mediaGatewayId."
    INDEX        { medGwyGatewayId }
::= { medGwyTermIdTable 1 }



MedGwyTermIdEntry ::= SEQUENCE
{
    medGwyNextTerminationId             TestAndIncr         -- rw
}


medGwyNextTerminationId OBJECT-TYPE
    SYNTAX        TestAndIncr
    MAX-ACCESS    read-write
    STATUS        current
    DESCRIPTION
       "The Next Value for a MediaGateway TerminationId.  Assists the
        manager in selecting a value for medGwyTerminationId.
        Using the TestAndIncr syntax, A Manager will 'lock' this
        variable, ensuring single access."
::= { medGwyTermIdEntry 1 }





-- *****************************************************************************
--
-- medGwyTerminationsTable
--
--   The Terminations Table...
--
--   There is one entry in this table for each Termination in a MediaGateway.
--
-- *****************************************************************************


medGwyTerminationsTable OBJECT-TYPE
    SYNTAX       SEQUENCE OF MedGwyTerminationsEntry
    MAX-ACCESS   not-accessible
    STATUS       current
    DESCRIPTION
                "This table contains information about terminations in
                 a media gateway. It is a list of terminations. The
                 number of entries equals to the total number of
                 terminations for all contexts in a gateway."
::= { medGwyConnections 2}


medGwyTerminationsEntry OBJECT-TYPE
    SYNTAX       MedGwyTerminationsEntry
    MAX-ACCESS   not-accessible
    STATUS       current
    DESCRIPTION "
                 It contains objects that describe a termination.

                "
    INDEX        { medGwyGatewayId, medGwyTerminationId }
::= { medGwyTerminationsTable 1 }



MedGwyTerminationsEntry ::= SEQUENCE
{
    medGwyTerminationId                  Integer32,          -- na
    medGwyTerminationName                SnmpAdminString,    -- rc
    medGwyTerminationStatus              INTEGER,            -- rc
    medGwyTerminationTestStatus          INTEGER,            -- rc
    medGwyTerminationInterfaceIdentifier Integer32,          -- rc
    medGwyTerminationPropertyProfileId   Integer32,          -- rc
    medGwyTerminationRowStatus           RowStatus           -- rc
}


medGwyTerminationId OBJECT-TYPE
    SYNTAX      Integer32
    MAX-ACCESS  not-accessible
    STATUS      current
    DESCRIPTION "An identification number that is assign to
                 the termination by a media gateway. "
::= { medGwyTerminationsEntry 1 }


medGwyTerminationName OBJECT-TYPE
    SYNTAX      SnmpAdminString ( SIZE (0..64) )
    MAX-ACCESS  read-create
    STATUS      current
    DESCRIPTION "An Name that is assign to the termination. "
::= { medGwyTerminationsEntry 2 }


medGwyTerminationStatus OBJECT-TYPE
    SYNTAX      INTEGER
                {
                  in-Service    (1),
                  out-Of-Service(2)
                }
    MAX-ACCESS  read-create
    STATUS      current
    DESCRIPTION "current status of the line"
::= { medGwyTerminationsEntry 3 }


medGwyTerminationTestStatus OBJECT-TYPE
    SYNTAX      INTEGER
                {
                  in-Test     (1),
                  out-Of-Test (2)
                }
    MAX-ACCESS  read-create
    STATUS      current
    DESCRIPTION "current status of the line"
::= { medGwyTerminationsEntry 4 }


medGwyTerminationInterfaceIdentifier OBJECT-TYPE
    SYNTAX      InterfaceIndex
    MAX-ACCESS  read-create
    STATUS      current
    DESCRIPTION "A number that uniquely identifies the interface in
                 the physical gateway."
::= { medGwyTerminationsEntry 5 }


medGwyTerminationPropertyProfileId OBJECT-TYPE
    SYNTAX      Integer32
    MAX-ACCESS  read-create
    STATUS      current
    DESCRIPTION "PropertyId...an index into the PropertyProfile Table "
::= { medGwyTerminationsEntry 6 }


medGwyTerminationRowStatus OBJECT-TYPE
    SYNTAX      RowStatus
    MAX-ACCESS  read-create
    STATUS      current
    DESCRIPTION "This is used to create new rows in this table, modify
                 existing rows, and to delete existing rows."
::= { medGwyTerminationsEntry 7 }




-- *****************************************************************************
--
-- medGwyPropertyProfileTable
--
--   The Media Gateway Property Profile Table...
--
--   There are 'N' entries for each Gateway-PropertyProfile
--   Each entry is a supported property, thus this table gives a list of
--   supported properties for each specified Profile.
--
--   Each Property is defined as an Object Identifer in the various
--   Package Mibs.  That OID is used to identify the particular Package,
--   and if the Termination supports the property, this Package OID is
--   included in its list.
--
--   Terminations (in the TerminationsTable) will have a PropertyProfileId
--   which indicate which PropertyProfile this Termination supports.
--   A Manager builds a Profile of properties, then ties each termination
--   to a defined profile, via the PropertyProfileId
--
-- *****************************************************************************
medGwyPropertyProfileTable OBJECT-TYPE
    SYNTAX       SEQUENCE OF MedGwyPropertyProfileEntry
    MAX-ACCESS   not-accessible
    STATUS       current
    DESCRIPTION
                "This table contains a list of the properties supported
                 in a Profile.  A Manager builds a Profile of properties,
                 then ties each termination to a defined profile"
::= { medGwyConnections 3}


medGwyPropertyProfileEntry OBJECT-TYPE
    SYNTAX       MedGwyPropertyProfileEntry
    MAX-ACCESS   not-accessible
    STATUS       current
    DESCRIPTION "
                 Each row represents a default property of the Property Profile
                 N-entries per mediaGatewayId/PropertyId, 1 per property."
    INDEX        { medGwyGatewayId, medGwyPropertyProfileId,
                   medGwyPropertyProfileIndex }
::= { medGwyPropertyProfileTable 1 }



MedGwyPropertyProfileEntry ::= SEQUENCE
{
    medGwyPropertyProfileId             Integer32,          -- na
    medGwyPropertyProfileIndex          Integer32,          -- na
    medGwyPropertyProfileProperty       AutonomousType,     -- rc
    medGwyTermPropertyProfileStatus     RowStatus           -- rc
}



medGwyPropertyProfileId OBJECT-TYPE
    SYNTAX      Integer32
    MAX-ACCESS  not-accessible
    STATUS      current
    DESCRIPTION "PropertyProfile Identifier.  Identifies this Profile,
                 this is the value that each Termination will contain
                 point-to"
::= { medGwyPropertyProfileEntry 1 }


medGwyPropertyProfileIndex OBJECT-TYPE
    SYNTAX      Integer32
    MAX-ACCESS  not-accessible
    STATUS      current
    DESCRIPTION "PropertyProfile Index...merely a 'counter' thru the table,
                 ie, property-1, property-2, etc."
::= { medGwyPropertyProfileEntry 2 }


medGwyPropertyProfileProperty OBJECT-TYPE
    SYNTAX      AutonomousType
    MAX-ACCESS  read-create
    STATUS      current
    DESCRIPTION "The Property supported by this Profile.
                 This is an OID defined in a package to identify a particular
                 property (such as AnalogLines, Tones)."
::= { medGwyPropertyProfileEntry 3 }


medGwyTermPropertyProfileStatus OBJECT-TYPE
    SYNTAX      RowStatus
    MAX-ACCESS  read-create
    STATUS      current
    DESCRIPTION
               "used to create new rows in this table, modify
                existing rows, and to delete existing rows."
::= { medGwyPropertyProfileEntry 4 }





-- *****************************************************************************
--
-- Media-Gatway-MIB Notification Definitions
--
-- *****************************************************************************
mediaGatewayMIBNotifications OBJECT IDENTIFIER ::= { mediaGatewayMIB 2 }



medGwyNotifPrefix   OBJECT IDENTIFIER ::= { mediaGatewayMIBNotifications 0 }
medGwyNotifObjects  OBJECT IDENTIFIER ::= { mediaGatewayMIBNotifications 1 }


--
-- Objects necessary for these Notifications
--
medGwyReceivedElement OBJECT-TYPE
    SYNTAX      OCTET STRING  ( SIZE (0..64) )
    MAX-ACCESS  accessible-for-notify
    STATUS      current
    DESCRIPTION "The element name received in a megaco message."
::= { medGwyNotifObjects 1 }



medGwyLinkStatusChange NOTIFICATION-TYPE
    OBJECTS {
              medGwyGatewayLinkName,
              medGwyGatewayOperStatus
            }
    STATUS  current
    DESCRIPTION
        "This notification indicates that operational status
        of a media gateway control link has changed."
::= { medGwyNotifPrefix 1}


medGwyInvalidControllerAddress NOTIFICATION-TYPE
    OBJECTS {
              mediaGatewayControllerIPAddress
            }
    STATUS  current
    DESCRIPTION
        "This notification indicates that a message was received
         from a controller that did not match any none valid
         controller IPAddress"
::=  { medGwyNotifPrefix 2 }



medGwyInvalidTerminationId NOTIFICATION-TYPE
    OBJECTS {
              medGwyTerminationName
            }
    STATUS  current
    DESCRIPTION
        "This notification indicates that a message was received
         from a controller that contained a TerminationId
         that did not match any TerminationId in the
         TerminationsTable.
         TerminationId is found in the OID of the
         medGwyTerminationName Object."
::=  { medGwyNotifPrefix 3 }



medGwyInvalidPackageElement NOTIFICATION-TYPE
    OBJECTS {
              medGwyReceivedElement
            }
    STATUS  current
    DESCRIPTION
        "This notification indicates that a message was received
         from a controller that contained an event, signal,
         or descriptor that was not recognized for the
         package."
::=  { medGwyNotifPrefix 4 }



medGwyTerminationStatusChange NOTIFICATION-TYPE
    OBJECTS {
              medGwyTerminationStatus,
              medGwyTerminationTestStatus
            }
    STATUS  current
    DESCRIPTION
        "This notification is sent when a termination changes status."
::=  { medGwyNotifPrefix 5 }




-- *****************************************************************************
--
-- Conformance for the Media-Gateway-MIB
--
-- To be completed....
--
-- *****************************************************************************


mediaGatewayConformance OBJECT IDENTIFIER ::= { mediaGatewayMIB 3 }



medGwyCompliances  OBJECT IDENTIFIER ::= { mediaGatewayConformance 1 }
medGwyConfGroups   OBJECT IDENTIFIER ::= { mediaGatewayConformance 2 }



-- Compliance


medGwyCompliance MODULE-COMPLIANCE
    STATUS current
    DESCRIPTION
       "Compliance statement for entities which implement
        the Media Gateway MIB.
       "
    MODULE              -- this module
    MANDATORY-GROUPS
    {
        medGwyConfigGroup,
        medGwyStatsGroup,
        medGwyNotificationsGroup
    }



    GROUP medGwyGWControllerGroup
    DESCRIPTION
       "This group is mandatory for all Systems...."

    GROUP medGwyNextIdGroup
    DESCRIPTION
       "This group is NOT mandatory for Agents...in this event, the Manager
        is responsible for submitting valid Id's."

    --...


  ::= { medGwyCompliances 1 }



-- Units of Conformance


medGwyConfigGroup OBJECT-GROUP
    OBJECTS
    {
      medGwyGatewayLinkName,
      medGwyGatewayIPAddress
      -- etc...
    }
    STATUS current
    DESCRIPTION
       "Configuration Information for a Media Gateway"
::= { medGwyConfGroups 1 }


medGwyStatsGroup OBJECT-GROUP
    OBJECTS
    {
      --...
      medGwyGatewayNumErrors,
      medGwyGatewayTransportLastEvent
      --...
    }
    STATUS current
    DESCRIPTION
       "Stats Information for a Media Gateway"
::= { medGwyConfGroups 2 }


medGwyGWControllerGroup OBJECT-GROUP
    OBJECTS
    {
      mediaGatewayControllerIPAddress,
      mediaGatewayControllerPort
      --...
    }
    STATUS current
    DESCRIPTION
       "Stats Information for a Media Gateway"
::= { medGwyConfGroups 3 }


medGwyNextIdGroup OBJECT-GROUP
    OBJECTS
    {
      medGwyNextTerminationId,
      medGwyNextLinkId
      --...
    }
    STATUS current
    DESCRIPTION
       "Agent provides NextId's to the Manager to assist in selecting
        and creating new table entries."
::= { medGwyConfGroups 4 }


medGwyNotificationsGroup NOTIFICATION-GROUP
    NOTIFICATIONS
    {
      medGwyLinkStatusChange,
      medGwyInvalidControllerAddress,
      medGwyInvalidTerminationId,
      medGwyInvalidPackageElement,
      medGwyTerminationStatusChange
    }
    STATUS current
    DESCRIPTION
       "Notifications that an entity implementing the Media Gateway will
        send."
::= { medGwyConfGroups 5 }


-- etc!


END
