--****************************************************************************
-- Excel Switching Corporation Enterprise MIB Module
--
-- The Excel Enterprise MIB enables SNMP network management applications
-- to monitor and control the Excel EXS family of switches.
--
-- Copyright (c) 1998 by EXCEL Switching Corporation.  All rights reserved
-- No part of this document may be reproduced in any way, or by any
-- means, without the prior written permission of EXCEL Switching Corporation
--
-- This document is Confidential property of Excel Switching Corporation
-- EXCEL1-SWITCH-MIB DEFINITIONS
--***************************************************************************
                                                         
EXCEL1-SWITCH-MIB DEFINITIONS ::= BEGIN
IMPORTS
    IpAddress, enterprises, Counter
        FROM RFC1155-SMI
    OBJECT-TYPE
        FROM RFC-1212
    TRAP-TYPE
        FROM RFC-1215
    DisplayString
        FROM RFC1213-MIB
    MODULE-IDENTITY, ObjectName, Integer32, Counter32, snmpModules
        FROM SNMPv2-SMI
    TruthValue, DisplayString, TestAndIncr, TimeStamp, RowStatus
        FROM SNMPv2-TC;

lucent          OBJECT IDENTIFIER ::= {enterprises 1751 }
products        OBJECT IDENTIFIER ::= { lucent 1 }

excel  MODULE-IDENTITY    
        LAST-UPDATED "000118"
        ORGANIZATION "Excel Switching Corporation"    
        CONTACT-INFO 
                "Excel Switching Corporation
                225 Independence Dr
                Hyannis Ma. 02601

                (508)-862-3000"    
        DESCRIPTION
                "The MIB module for entities implementing the xxxx
                protocol."  

::= { products 67 }
--
--
-- Text Conventions used in this MIB
--
-- The following two definitions cause problems when loading onto netview
--


SlotsInNode                   ::= INTEGER ( 1..64 )

DSPFunctionTypes              ::= INTEGER {
                                    other(1),
                                    recDTMF(2),
                                    recDTMFHighPassFilter(3),
                                    recMFR1(4),
                                    recMFR2(5),
                                    recCPA(6),
                                    recE1Pulse(7),
                                    recEnergyDetection(8),
                                    genDTMF(9),
                                    genMFR1(10),
                                    genBongTone(11),
                                    genMFR2Forward(12),
                                    genMFR2Backward(13),
                                    genCPT4(14),
                                    confStandard(15),
                                    confMixed(16),
                                    confMonitor(17),
                                    vras(18)
}

CardOperState                 ::= INTEGER {
                                    inService(1),
                                    oosBySwitch(2),
                                    oosByHost(3),
                                    standbyByHost(4),
                                    generalHWFailure(5),
                                    needsSystemSW(6),
                                    other(7)
}

SS7VariantsTypes ::= INTEGER {
				ansi(1),
				itu-ts(2),
				none(3)
}

PayloadTypes ::= INTEGER {
                        g711aLaw (1),
                        g711uLaw (2),
                        g726-16  (3),
                        g726-24  (4),
                        g726-32  (5),
                        g726-40  (6),
                        g727-16  (7),
                        g727-16-24 (8),
                        g727-24  (9),
                        g727-32-16 (10),
                        g727-32-24 (11),
                        g727-32   (12),
                        g727-40-16 (13),
                        g727-40-24 (14),
                        g727-40-32 (15),
                        g723-5-3   (16),
                        g723-6-3   (17),
                        g729       (18),
                        g728       (19),
                        transparentPCM  (20),
                        netCoder-4-8    (21),
                        netCoder-5-6    (22),
                        netCoder-6-4    (23),
                        netCoder-7-2    (24),
                        netCoder-8-0    (25),
                        netCoder-8-8    (26),
                        netCoder-9-6    (27)
}

PacketDepth ::= INTEGER {
              noRedundancy (1),
              redundancyLevelOne (2),
              redundancyLevelTwo (3)
}


excel1	OBJECT IDENTIFIER	::= { excel 1 }
--
-- Second-Level Excel Branch Definitions
--
excelExperimental            OBJECT IDENTIFIER ::= { excel1 1 }
excelProducts                OBJECT IDENTIFIER ::= { excel1 2 }
--
-- Excel Product Definitions
--
excelSystem		     OBJECT IDENTIFIER ::= { excelProducts 1 }

excelNodeIdentifier OBJECT-TYPE
	SYNTAX DisplayString
	MAX-ACCESS read-write
	STATUS current
	DESCRIPTION
	    "An attribute assigned by the system administrator that 
	uniquely identifies this host system."
	REFERENCE
	    "Bellcore Generic Requirements GR-477-CORE, 
	Network Traffic Management, item R4-32"

	::= { excelSystem 1 }


excelNodeLocationIdentifier OBJECT-TYPE
	SYNTAX DisplayString
	MAX-ACCESS read-write
	STATUS current
	DESCRIPTION
	    "A unique identifier is a concatination of identifiers for the 
	 city, state, building and traffic unit identity of this host system."
	REFERENCE
	    "Bellcore Generic Requirements GR-477-CORE, 
	Network Traffic Management, item R4-32"
	::= { excelSystem 2 }

excelNodeCurrentTime OBJECT-TYPE
	SYNTAX DisplayString
	MAX-ACCESS read-only
	STATUS current
	DESCRIPTION
	    "The value for the current time on this host system."
	REFERENCE
	    "Bellcore Generic Requirements GR-477-CORE, 
	Network Traffic Management, item R4-32"
	::= { excelSystem 3 }

excelSwitch                  OBJECT IDENTIFIER ::= { excelProducts 2 }

excelCurrentNode OBJECT-TYPE
	SYNTAX INTEGER ( 0..255 )
	MAX-ACCESS read-write
	STATUS current
	DESCRIPTION
		"This agent can only view one node at a time.  Whatever
        this excelCurrentNode is set to is the view against which
        other objects are matched. This value represents a LOGICAL node ID."
	::= { excelSwitch 1 }

excelNodes OBJECT-TYPE
	SYNTAX INTEGER ( 0..32 )
	MAX-ACCESS read-only
	STATUS current
	DESCRIPTION
		"The number of nodes or rows in excelNodeTable."
	::= { excelSwitch 2 }

excelNodeTable OBJECT-TYPE
    SYNTAX SEQUENCE OF ExcelNodeEntry 
    MAX-ACCESS not-accessible
    STATUS current
    DESCRIPTION
        "This table contains a row for each node in the switch being
         managed by this agent."
    ::= { excelSwitch 3 }

excelNodeEntry OBJECT-TYPE
    SYNTAX ExcelNodeEntry 
    MAX-ACCESS not-accessible
    STATUS current
    DESCRIPTION "Definition for the ExcelNodeEntry List"

    INDEX { excelNodeIndex }
    
    ::= { excelNodeTable 1 }

ExcelNodeEntry ::= SEQUENCE {
    excelNodeIndex                INTEGER,
    excelNodeLogicalID            INTEGER,
    excelNodePhysicalID           INTEGER,
    excelNodeType                 INTEGER   
	}
    
excelNodeIndex OBJECT-TYPE
    SYNTAX INTEGER (0..32 )
    MAX-ACCESS not-accessible
    STATUS current
    DESCRIPTION
        "This object is a unique identifieer into the excelNodeTable."
    ::= { excelNodeEntry 1 }

excelNodeLogicalID OBJECT-TYPE
    SYNTAX INTEGER (0..255 )
    MAX-ACCESS read-only
    STATUS current
    DESCRIPTION
        "This object represents the logical ID that the host application 
        assigns to the node represented by this row."
    ::= { excelNodeEntry 2 }

excelNodePhysicalID OBJECT-TYPE
    SYNTAX INTEGER (0..8192 )
    MAX-ACCESS read-only
    STATUS current
    DESCRIPTION
        "This object represents the unique physical number used to identify
        the node. It is the serial number of the midplane."
    ::= { excelNodeEntry 3 }
    
  excelNodeType OBJECT-TYPE
      SYNTAX INTEGER {
          other(1),
          pcx(2),
          csn(3),
          lnx(4),
          exnetConnect(5)
          } 
      MAX-ACCESS read-only
      STATUS current
      DESCRIPTION 
          "This object indicates the node type of the node being managed."
      ::= { excelNodeEntry 4 }

--
--
-- Excel Node Component Definitions
--
excelNode                    OBJECT IDENTIFIER ::= { excelSwitch 4 }
excelNodeHardware            OBJECT IDENTIFIER ::= { excelNode 1 }
excelNodeSoftware            OBJECT IDENTIFIER ::= { excelNode 2 }

--
-- Excel Hardware Group Definitions
--
excelCommunicationEquipment  OBJECT IDENTIFIER ::= { excelNodeHardware 1 }
excelDeviceEquipment         OBJECT IDENTIFIER ::= { excelNodeHardware 2 }
excelResourceEquipment       OBJECT IDENTIFIER ::= { excelNodeHardware 3 }
  
--
-- Excel Software Group Definitions 
--
excelSystemSoftware          OBJECT IDENTIFIER ::= { excelNodeSoftware 1 }
excelCommunicationSoftware   OBJECT IDENTIFIER ::= { excelNodeSoftware 2 }

--
-- The Excel Communication Equipment Group (Communication Hardware)
--
-- This Group defines the components, attributes, statistics, state, and
-- actions necessary to manage Excel Communication Equipment Group Objects.
--

excelCommunicationCard OBJECT IDENTIFIER ::= { excelCommunicationEquipment 1 }

excelCommCardTable OBJECT-TYPE
    SYNTAX SEQUENCE OF ExcelCommCardEntry 
    MAX-ACCESS not-accessible
    STATUS current
    DESCRIPTION
        "This table contains a row for each communication card in this node.
        A communication card is considered to be a card that plays a role in 
        the call processing capabilities of the node."
    ::= { excelCommunicationCard 1 }

excelCommCardEntry OBJECT-TYPE
    SYNTAX ExcelCommCardEntry 
    MAX-ACCESS not-accessible
    STATUS current
DESCRIPTION ""

    INDEX { excelCommCardSlotIndex }
    ::= { excelCommCardTable 1 }

ExcelCommCardEntry ::= SEQUENCE {
    excelCommCardSlotIndex               SlotsInNode,
    excelCommCardOperState               INTEGER,
    excelCommCardResetReason             INTEGER,
    excelCommCardConfigStatus            INTEGER,
    excelCommCardConfidenceTest          INTEGER,
    excelCommCardAction                  INTEGER,
    excelCommCardActionTime              DisplayString
    }

excelCommCardSlotIndex OBJECT-TYPE
    SYNTAX SlotsInNode
    MAX-ACCESS not-accessible
    STATUS current
    DESCRIPTION
        "This object represents the slot number occupied by this card.  Note
        that this value is the index into the excelDeviceCardTable."
    ::= { excelCommCardEntry 1 }

excelCommCardOperState OBJECT-TYPE
    SYNTAX CardOperState
    MAX-ACCESS read-only
    STATUS current
    DESCRIPTION
        "This object represents the state of this card.  oosBySwitch(2) 
        indicates that the switch has taken the card out of service. 
        oosByHost(3) indicates that the host has taken the card out of
        service. standbyByHost(4) indicates that the host has put the card
        in a standby state. If this object is generalHWFailure(5), then the
        card is off-line and must be serviced. needsSystemSW(6) indicates
        that System Software needs to be downloaded to the switch."
    ::= { excelCommCardEntry 2 }

excelCommCardResetReason OBJECT-TYPE
    SYNTAX INTEGER { 
        other(1),
        unKnown(2),
        powerUp(3),
        resetButton(4)
        }
    MAX-ACCESS read-only
    STATUS current
    DESCRIPTION
        "This object represents the reason for this card's last reset."
    ::= { excelCommCardEntry 3}

excelCommCardConfigStatus OBJECT-TYPE
    SYNTAX INTEGER { 
        invalid(1),
        valid(2),
        unknown(3)
        }
    MAX-ACCESS read-only
    STATUS current
    DESCRIPTION
        "This object represents the state of the battery-backed configuration
        data.  If it is invalid(1), then the card must be reconfigured by the 
        host."
    ::= { excelCommCardEntry 4}

excelCommCardConfidenceTest OBJECT-TYPE
    SYNTAX INTEGER { 
        passed(1),
        otherFailure(2),
        ramFailure(3),
        romFailure(4)
        }
    MAX-ACCESS read-only
    STATUS current
    DESCRIPTION
        "Indicates status of Confidence test."
    ::= { excelCommCardEntry 5 }

--
-- These objects will provide the capability to take cards in and out
-- of service.  
--

excelCommCardAction OBJECT-TYPE
    SYNTAX INTEGER { 
                     locked (1),
                     unlocked (2),
                     shutdown (3)
           }
    MAX-ACCESS read-write
    STATUS current
    DESCRIPTION
        "This object contains the actions that can occur on a card.  These 
        include :
            locked - takes the card out of service, but leave the current
                     configuration intact.

            unlocked - puts a card out of service back into service

            shutdown - intermediate state when card is in the process of 
                       being locked."

    ::= { excelCommCardEntry 6  }

excelCommCardActionTime OBJECT-TYPE
    SYNTAX DisplayString
    MAX-ACCESS read-only
    STATUS current
    DESCRIPTION
        "Date and time of last action taken."

    ::= { excelCommCardEntry 7 }





--
-- Digital Signal Processing Group
--

excelDSP                OBJECT IDENTIFIER ::= { excelCommunicationEquipment 2 }
--
-- The Excel Device Equipment Group (Device Hardware)
--
-- This Group defines the components, attributes, statistics, state, and
-- actions necessary to manage the Excel Device Equipment Group Objects.
--
excelVoipDsp            OBJECT IDENTIFIER ::= { excelDSP 1 }

excelVoipSlotNumber OBJECT-TYPE
    SYNTAX INTEGER (1..64)
    MAX-ACCESS read-write
    STATUS current
    DESCRIPTION
        "This object represents the index of the card that information will be 
        presented on "
    ::= { excelVoipDsp 1 }

excelVoipDspTable OBJECT-TYPE
    SYNTAX SEQUENCE OF ExcelVoipDspEntry
    MAX-ACCESS not-accessible
    STATUS current
    DESCRIPTION
        ""

    ::= { excelVoipDsp 2 }

excelVoipDspEntry OBJECT-TYPE
    SYNTAX ExcelVoipDspEntry 
    MAX-ACCESS not-accessible
    STATUS current
    DESCRIPTION ""

    INDEX { excelVoipDspIndex }
    ::= { excelVoipDspTable 1 }

ExcelVoipDspEntry ::= SEQUENCE {
    excelVoipDspIndex INTEGER,
    excelVoipDspInstalled INTEGER,
    excelVoipDspNumChannelsSupported INTEGER,
    excelVoipDspOperState INTEGER,
    excelVoipDspArtworkRevision DisplayString,
    excelVoipDspFuncRevision INTEGER,
    excelVoipDspHWRevision DisplayString,
    excelVoipDspSWRevision DisplayString,
    excelVoipDspRamSize INTEGER,
    excelVoipDspSerialNum INTEGER,
    excelVoipDspRamBuildNumber INTEGER
    }

excelVoipDspIndex OBJECT-TYPE
    SYNTAX INTEGER ( 1..4 )
    MAX-ACCESS not-accessible
    STATUS current 
    DESCRIPTION 
        "Index into the Voice over IP DSP table"

    ::= { excelVoipDspEntry 1 }

excelVoipDspInstalled OBJECT-TYPE
    SYNTAX INTEGER {
              notInstalled (1),
              installed (2)
         }
    MAX-ACCESS read-only
    STATUS current 
    DESCRIPTION
        "This object indicates if the DSP module is installed or not."

    ::= { excelVoipDspEntry 2 }

excelVoipDspNumChannelsSupported OBJECT-TYPE
    SYNTAX INTEGER (1..2048)
    MAX-ACCESS read-only
    STATUS current 
    DESCRIPTION
        "This object indicates the number of channels available from the slot."

    ::= { excelVoipDspEntry 3 }

excelVoipDspOperState OBJECT-TYPE
    SYNTAX CardOperState
    MAX-ACCESS read-only
    STATUS current 
    DESCRIPTION
        "This object indicates operational state of the dsp."

    ::= { excelVoipDspEntry 4 }

excelVoipDspArtworkRevision OBJECT-TYPE
    SYNTAX DisplayString
    MAX-ACCESS read-only
    STATUS current 
    DESCRIPTION
        "This object indicates operational state of the dsp."

    ::= { excelVoipDspEntry 5 }


excelVoipDspFuncRevision OBJECT-TYPE
    SYNTAX INTEGER (1..2048) 
    MAX-ACCESS read-only
    STATUS current 
    DESCRIPTION
        "This object indicates function revision of this dsp."

    ::= { excelVoipDspEntry 6 }


excelVoipDspHWRevision OBJECT-TYPE
    SYNTAX DisplayString 
    MAX-ACCESS read-only
    STATUS current 
    DESCRIPTION
        "This object indicates function version of the hardware associated
        of this dsp."

    ::= { excelVoipDspEntry 7 }

excelVoipDspSWRevision OBJECT-TYPE
    SYNTAX DisplayString 
    MAX-ACCESS read-only
    STATUS current 
    DESCRIPTION
        "This object indicates function version of the software associated
        of this dsp."

    ::= { excelVoipDspEntry 8 }

excelVoipDspRamSize OBJECT-TYPE
    SYNTAX INTEGER (1..2048) 
    MAX-ACCESS read-only
    STATUS current 
    DESCRIPTION
        "This object indicates the current amount of RAM on this dsp."

    ::= { excelVoipDspEntry 9 }

excelVoipDspSerialNum OBJECT-TYPE
    SYNTAX INTEGER(0..2048) 
    MAX-ACCESS read-only
    STATUS current 
    DESCRIPTION
        "This object indicates the serial number of this dsp."

    ::= { excelVoipDspEntry 10 }

excelVoipDspRamBuildNumber OBJECT-TYPE
    SYNTAX INTEGER (0..2048) 
    MAX-ACCESS read-only
    STATUS current 
    DESCRIPTION
        "This object indicates the build number of this dsp."

    ::= { excelVoipDspEntry 11 }

excelDeviceCard              OBJECT IDENTIFIER ::= { excelDeviceEquipment 1 }

--
-- The Excel Device Equipment Group (Device Hardware)
--
-- This Group defines the components, attributes, statistics, state, and
-- actions necessary to manage the Excel Device Equipment Group Objects.
--
excelDeviceCardTable OBJECT-TYPE
    SYNTAX SEQUENCE OF ExcelDeviceCardEntry 
    MAX-ACCESS not-accessible
    STATUS current
    DESCRIPTION
         "The excelDeviceCardTable, which has a row for
         each of the 'slots' (the maximum being, excelConfigMaxSlot) in this 
         node. Note that this table will have an entry for each slot whether
         it is filled or not.  It is ordered by slot number.  And a slot does 
         not necessarily mean that the card is hot swappable, like the fan tray
         or midplane. The columns represent information that 
         (for the most part) is common between all types of cards."
    ::= { excelDeviceCard 1 }

excelDeviceCardEntry OBJECT-TYPE
    SYNTAX ExcelDeviceCardEntry 
    MAX-ACCESS not-accessible
    STATUS current
    DESCRIPTION ""

    INDEX { excelDeviceCardSlotIndex }
    ::= { excelDeviceCardTable 1 }

ExcelDeviceCardEntry ::= SEQUENCE {
    excelDeviceCardSlotIndex            SlotsInNode,
    excelDeviceCardType                 INTEGER,
    excelDeviceCardModelDescription     DisplayString,
    excelDeviceCardArtworkRevision      DisplayString,
    excelDeviceCardFuncRevision         INTEGER,
    excelDeviceCardHWRevision           DisplayString,
    excelDeviceCardSWRevision           DisplayString,
    excelDeviceCardRamSize              INTEGER,
    excelDeviceCardSerialNum            INTEGER,
    excelDeviceCardRAMBuildNum          INTEGER
    }

excelDeviceCardSlotIndex OBJECT-TYPE
    SYNTAX SlotsInNode
    MAX-ACCESS not-accessible
    STATUS current
    DESCRIPTION
        "This is the slot number of the slot that the card resides in as 
        well as the index into excelDeviceCardTable."
    ::= { excelDeviceCardEntry 1 }

excelDeviceCardType OBJECT-TYPE
     SYNTAX INTEGER {  
        other(1),							 
        empty(2),
        dead(3),
        powerSupply60(4),
        powerSupply90(5),   
        powerSupply150(6),
        exCPU2000(7),
        exCPU1000(8),       
        smartT14Span(9),
        smartT18Span(10),
        smartE14Span(11),
        smartE18Span(12),
        openNetE18Span(13),
        openNetE116Span(14),
        smartfourSpanJ1(15),
        mfDsp(16),
        openNetDSP(17),
        isdnPri24(18),
        isdnPri32(19),
        ss7TwoLink(20),
        ss7FourLink(21),
        ss7EightLink(22),
        ss7SixteenLink(23),
        dass2(24),
        exnetController(25),
        subrateController(26),
        rearFanTray(27),
        frontFanTray(28),
        midplane(29),
        exCpuIO(30),
        exNetIO(31),
        rbiIO(32),
        analogInterfaceIO(33),                
        openNetE1120OhmIO(34),
        smartE1120OhmIO(35),
        smartE175OhmIO(36),
        smartJ1120OhmIO(37),
        smartT1IO(38),
        standbyIO(39),
        isdnPRIRedunIO(40),
        ss7RedunIO(41),
        smartLineCardRedunIO(42),
        openNetE1120RedunIO(43),
        embeddedHostCard(44),
        exnetConnect(45),
        openNetT18Span(46),   
        openNetT116Span(47),
        openNetT1100RedunIO(48),
        openNetJ116Span(49),
        exNetOne(50),
        ss7PQ(51),
        vdacVoIP(52),
        vdacVoIPModule(53),
        exCpuHP (54),
        ss7HP (55),
        ds3LineCard (56),
        isdnPQ (57),
        exHost (58),
        exsMTXCtrlIO (59),
        exsMTXCtrl1000 (60)
        }
    MAX-ACCESS read-only    
    STATUS current
    DESCRIPTION
        "The type of card that is in this slot.  If the slot does not 
        contain a card, then the value is empty(2).  It the card is unable
        to communicate, then the value is dead(3).  If the agent is unfamiliar
        with the card, then the value is other(1). Otherwise, it is a value
        representing one of the appropriate Excel products that can reside in
        this slot."
    ::= { excelDeviceCardEntry 2 }

excelDeviceCardModelDescription OBJECT-TYPE
    SYNTAX DisplayString
    MAX-ACCESS read-only
    STATUS current
    DESCRIPTION
        "This object is an ASCII string that represents the model description
        of the card in this slot."
    ::= { excelDeviceCardEntry 3 }

excelDeviceCardArtworkRevision OBJECT-TYPE
    SYNTAX DisplayString  
    MAX-ACCESS read-only
    STATUS current
    DESCRIPTION
        "This field has an ASCII character in the range 'A' to 'Z' 
		(0x41-0x5B) which indicates the revision level of the
		card's Printed Circuit Artwork."
    ::= { excelDeviceCardEntry 4 }

excelDeviceCardFuncRevision OBJECT-TYPE
	SYNTAX INTEGER ( 0..2048 )
	MAX-ACCESS read-only
	STATUS current
	DESCRIPTION
		"This object indicates the card's functional revision level."
	::= { excelDeviceCardEntry 5 }

excelDeviceCardHWRevision OBJECT-TYPE
	SYNTAX DisplayString 
	MAX-ACCESS read-only
	STATUS current
	DESCRIPTION
	"This object is an ASCII string that represents the ROM Revision of 
        the card."
	::= { excelDeviceCardEntry 6 }

excelDeviceCardSWRevision OBJECT-TYPE
    SYNTAX DisplayString 
    MAX-ACCESS read-only
    STATUS current
    DESCRIPTION
        "This object is an ASCII string that represents the revision levels of
        the system software running on this card."
    ::= { excelDeviceCardEntry 7 }

excelDeviceCardRamSize OBJECT-TYPE
	SYNTAX INTEGER ( 0..8192 ) 
	MAX-ACCESS read-only
	STATUS current
	DESCRIPTION
	"This object indicates the amount of RAM that is on the card.  The RAM 
        is measured in 1K increments."
	::= { excelDeviceCardEntry 8 }

excelDeviceCardSerialNum OBJECT-TYPE
    SYNTAX INTEGER ( 0..32565 )
    MAX-ACCESS read-only
    STATUS current
    DESCRIPTION
        "This object contains the serial number of the card."
    ::= { excelDeviceCardEntry 9 }

excelDeviceCardRAMBuildNum OBJECT-TYPE
    SYNTAX INTEGER ( 0..32565 )
    MAX-ACCESS read-only
    STATUS current
    DESCRIPTION
        "This object contains the RAM Build number of the card."
    ::= { excelDeviceCardEntry 10 }

--
-- Excel Utilities Group contains objects having to do with the Fan Trays and
-- power supplies in the node
--
excelUtility                 OBJECT IDENTIFIER ::= { excelDeviceEquipment 2 }

--
-- Excel Resource Utilization Group contains objects having to do with  
-- region/partition size and usage, CPU Utilization and Message Control
-- Block (MCB) usage.

excelResourceUtilization     OBJECT IDENTIFIER ::= { excelResourceEquipment 1 }

excelResourceSlotId OBJECT-TYPE
    SYNTAX INTEGER (1..64)
    MAX-ACCESS read-write
    STATUS obsolete
    DESCRIPTION
	"This object represents the index of the card information will be 
        presented on"
    DEFVAL { 0 }
    ::= { excelResourceUtilization 1 }

excelResourceUsageTable OBJECT-TYPE
    SYNTAX SEQUENCE OF ExcelRegionEntry 
    MAX-ACCESS not-accessible
    STATUS current
    DESCRIPTION
        ""
    ::= {  excelResourceUtilization 2 }

excelResourceUsageEntry OBJECT-TYPE
    SYNTAX ExcelResourceUsageEntry 
    MAX-ACCESS not-accessible
    STATUS current
    DESCRIPTION ""

    INDEX {excelCurrentNode , excelResourceUsageIndex }
    ::= { excelResourceUsageTable 1 }

ExcelResourceUsageEntry ::= SEQUENCE {
    excelResourceUsageIndex    INTEGER,
    excelCpuTime       INTEGER,
    excelMcbUsage      INTEGER
}

excelResourceUsageIndex OBJECT-TYPE
    SYNTAX INTEGER (1..256)
    MAX-ACCESS not-accessible
    STATUS current
    DESCRIPTION
	""
    DEFVAL { 1 }
    ::= { excelResourceUsageEntry 1 }

excelCpuTime OBJECT-TYPE
    SYNTAX INTEGER (1..32565)
    MAX-ACCESS read-only
    STATUS current
    DESCRIPTION
	"This object represents the total amount of CPU time that has been 
        used by the selectd card."
    DEFVAL { 1 }
    ::= { excelResourceUsageEntry 2 }

excelMcbUsage OBJECT-TYPE
    SYNTAX INTEGER (0..100)
    MAX-ACCESS read-only
    STATUS current
    DESCRIPTION
	"This object represents the percentage MCB's currently in use"
    DEFVAL { 0 }
    ::= { excelResourceUsageEntry 3 }

excelRegionTable OBJECT-TYPE
    SYNTAX SEQUENCE OF ExcelRegionEntry 
    MAX-ACCESS not-accessible
    STATUS current
    DESCRIPTION
        ""
    ::= {  excelResourceUtilization 3 }

excelRegionEntry OBJECT-TYPE
    SYNTAX ExcelRegionEntry 
    MAX-ACCESS not-accessible
    STATUS current
    DESCRIPTION ""

    INDEX { excelCurrentNode, excelDeviceCardSlotIndex, excelRegionIndex }
    ::= { excelRegionTable 1 }

ExcelRegionEntry ::= SEQUENCE {
    excelRegionIndex    INTEGER,
    excelRegionId       INTEGER,
    excelRegionSize      INTEGER,
    excelRegionUsed      INTEGER
}
excelRegionIndex OBJECT-TYPE
    SYNTAX INTEGER (1..256)
    MAX-ACCESS not-accessible
    STATUS current
    DESCRIPTION
	""
    DEFVAL { 1 }
    ::= { excelRegionEntry 1 }

excelRegionId OBJECT-TYPE
    SYNTAX INTEGER (1..256)
    MAX-ACCESS read-only
    STATUS current
    DESCRIPTION
	""
    DEFVAL { 1 }
    ::= { excelRegionEntry 2 }

excelRegionSize OBJECT-TYPE
    SYNTAX INTEGER (1..32565)
    MAX-ACCESS read-only
    STATUS current
    DESCRIPTION
	""
    DEFVAL { 1 }
    ::= { excelRegionEntry 3 }

excelRegionUsed OBJECT-TYPE
    SYNTAX INTEGER (0..32565)
    MAX-ACCESS read-only
    STATUS current
    DESCRIPTION
	"The number of bytes in this region that are currently in use"
    DEFVAL { 0 }
    ::= { excelRegionEntry 4 }

excelPartitionTable OBJECT-TYPE
    SYNTAX SEQUENCE OF ExcelPartitionEntry 
    MAX-ACCESS not-accessible
    STATUS current
    DESCRIPTION
        ""
    ::= {  excelResourceUtilization 4 }

excelPartitionEntry OBJECT-TYPE
    SYNTAX ExcelPartitionEntry 
    MAX-ACCESS not-accessible
    STATUS current
    DESCRIPTION ""

    INDEX { excelCurrentNode, excelDeviceCardSlotIndex, excelPartitionIndex }
    ::= { excelPartitionTable 1 }

ExcelPartitionEntry ::= SEQUENCE {
    excelPartitionIndex    INTEGER,
    excelPartitionId       INTEGER,
    excelPartitionSize      INTEGER,
    excelPartitionUsed      INTEGER
}

excelPartitionIndex OBJECT-TYPE
    SYNTAX INTEGER (1..256)
    MAX-ACCESS not-accessible
    STATUS current
    DESCRIPTION
	""
    DEFVAL { 1 }
    ::= { excelPartitionEntry 1 }

excelPartitionId OBJECT-TYPE
    SYNTAX INTEGER (1..256)
    MAX-ACCESS read-only
    STATUS current
    DESCRIPTION
	""
    DEFVAL { 1 }
    ::= { excelPartitionEntry 2 }

excelPartitionSize OBJECT-TYPE
    SYNTAX INTEGER (1..32565)
    MAX-ACCESS read-only
    STATUS current
    DESCRIPTION
	""
    DEFVAL { 1 }
    ::= { excelPartitionEntry 3 }

excelPartitionUsed OBJECT-TYPE
    SYNTAX INTEGER (0..32565)
    MAX-ACCESS read-only
    STATUS current
    DESCRIPTION
	"The number of bytes in this partition that are currently in use"
    DEFVAL { 1 }
    ::= { excelPartitionEntry 4 }

excelCpuUsageTable OBJECT-TYPE
    SYNTAX SEQUENCE OF ExcelCpuUsageEntry 
    MAX-ACCESS not-accessible
    STATUS current
    DESCRIPTION
        ""
    ::= {  excelResourceUtilization 5 }

excelCpuUsageEntry OBJECT-TYPE
    SYNTAX ExcelCpuUsageEntry 
    MAX-ACCESS not-accessible
    STATUS current
    DESCRIPTION ""

    INDEX { excelCurrentNode, excelDeviceCardSlotIndex, excelCpuUsageIndex }
    ::= { excelCpuUsageTable 1 }

ExcelCpuUsageEntry ::= SEQUENCE {
    excelCpuUsageIndex    INTEGER,
    excelCpuUsageTaskId   INTEGER,
    excelCpuUsageUsed     INTEGER
}

excelCpuUsageIndex OBJECT-TYPE
    SYNTAX INTEGER (1..256)
    MAX-ACCESS not-accessible
    STATUS current
    DESCRIPTION
	""
    DEFVAL { 1 }
    ::= { excelCpuUsageEntry 1 }

excelCpuUsageTaskId OBJECT-TYPE
    SYNTAX INTEGER (1..256)
    MAX-ACCESS read-only
    STATUS current
    DESCRIPTION
	""
    DEFVAL { 1 }
    ::= { excelCpuUsageEntry 2 }

excelCpuUsageUsed OBJECT-TYPE
    SYNTAX INTEGER (1..100)
    MAX-ACCESS read-only
    STATUS current
    DESCRIPTION
	""
    DEFVAL { 1 }
    ::= { excelCpuUsageEntry 3 }
--
-- The Excel System Software Group (System Software)
--
-- This Group defines the components, attributes, statistics, state, and
-- actions necessary to manage the Excel System Software Group Objects.
--

excelSystemConfig            OBJECT IDENTIFIER ::= { excelSystemSoftware 1 }

--
-- Excel System Software Alarm and Fault Group
--
-- This group contains objects when alarms or faults occur in the system
-- A get on these objects, will return the values that occurred for the 
-- last trap.
--

excelSystemAlarm             OBJECT IDENTIFIER ::= { excelSystemSoftware 2}

excelSysLastAlarmTrap OBJECT-TYPE
	SYNTAX INTEGER (0..1024 )
	MAX-ACCESS read-only
	STATUS current
	DESCRIPTION
	"This object represents the last trap that has been sent by this 
        agent."
	::= { excelSystemAlarm 1 }

excelSysLastAlarmSeverity OBJECT-TYPE
    SYNTAX INTEGER {
        informative(1),
        minor(2),
        major(3)
        } 
    MAX-ACCESS read-only
    STATUS current
    DESCRIPTION
        "If an alarm occurred and a trap was sent, then this object 
        indicates the severity."
    ::= { excelSystemAlarm 2 }

excelSysLastAlarmNode OBJECT-TYPE
	SYNTAX INTEGER ( 0..255 )
	MAX-ACCESS read-only
	STATUS current
	DESCRIPTION
		"The Physical Node ID of the last node to encounter
        an alarm condition."
	::= { excelSystemAlarm 3 }

excelSysLastAlarmStatus OBJECT-TYPE
	SYNTAX INTEGER {
                other(1),
                cardOutOfService(2),
                cardInService(3),
                cardInServiceStandby(4),
                cardFail(5),
                cardAdded(6),
                cardRemoved(7),
                cardActive(8),
                cardReset(9),
                ringInitializing(10),
                ringConnected(11),
                ringInService(12),
                ringOutOfService(13),
                spanLossOfService(14),
                spanDegradedService(15),
                nodeDiscovered(16),
                nodeUp(17),
                nodeReady(18),
                nodeDown(19)
        }
	MAX-ACCESS read-only
	STATUS current
	DESCRIPTION
		"The last Alarm Status change value to go out in a trap."
	::= { excelSystemAlarm 4 }

excelSysLastAlarmDSPLastBlocked OBJECT-TYPE
    SYNTAX DSPFunctionTypes 
    MAX-ACCESS read-only
    STATUS current
    DESCRIPTION
        "The last DSP Function Type that was blocked."
    ::= { excelSystemAlarm 5 }

excelSysLastAlarmRefClockSrc OBJECT-TYPE
	SYNTAX INTEGER { 
                notApplicable(1),
                refClock1(2),
                refClock2(3)
        }
	MAX-ACCESS read-only
	STATUS current
	DESCRIPTION
		"If a Reference Clock Source Lost alarm occurred,
        this object stores which reference clock the alarm 
        is occurring on.  If this alarm has not occurred, then
        the value will be equal to notApplicable(1)."
	::= { excelSystemAlarm 6}


--
-- The Excel Communication Software Group (Communication Software)
--
-- This Group defines the components, attributes, statistics, state, and
-- actions necessary to manage the Excel Communication Software Group Objects.
--
--

--
-- The Matrix Group
--
--
excelMatrix                OBJECT IDENTIFIER ::= {excelCommunicationSoftware 1}

excelMtxTable OBJECT-TYPE
    SYNTAX SEQUENCE OF ExcelMtxEntry 
    MAX-ACCESS not-accessible
    STATUS current
    DESCRIPTION
        "This table contains an entry for each matrix card in
        the system.  Note that in an EXnet Connect system, there will be a row 
        in this table to represent the EXnet Connect Card."
    ::= { excelMatrix 1 }

excelMtxEntry OBJECT-TYPE
    SYNTAX ExcelMtxEntry 
    MAX-ACCESS not-accessible
    STATUS current
	DESCRIPTION ""

    INDEX { excelMtxSlotIndex }
    ::= { excelMtxTable 1 }

ExcelMtxEntry ::= SEQUENCE {
        excelMtxSlotIndex               SlotsInNode,
	excelMtxPosition	        INTEGER,
	excelMtxType		        INTEGER,
	excelMtxState		        INTEGER,
	excelMtxAdjacentMatrixStatus	INTEGER,
	excelMtxHostLink	        INTEGER,
	excelMtxRamLoadPresent	        INTEGER,
	excelMtxReadyForConfiguration   INTEGER,
        excelMtxIpAddress               IpAddress,
        excelMtxSecIpAddress            IpAddress,
        excelMtxBootMajorVersion        DisplayString,
        excelMtxBootMinorVersion        DisplayString,
        excelMtxSystemSoftwareMajor     DisplayString,
        excelMtxSystemSoftwareMinor     DisplayString,
        excelMtxSystemSoftwareBuild     DisplayString
    }            

excelMtxSlotIndex OBJECT-TYPE
    SYNTAX SlotsInNode
    MAX-ACCESS not-accessible
    STATUS current
    DESCRIPTION
        "The slot in which the matrix represented by this row resides."
    ::= { excelMtxEntry 1 }

excelMtxPosition OBJECT-TYPE
	SYNTAX INTEGER { 
                left(1),
                right(2),
	        other(3)
         }
	MAX-ACCESS read-only
	STATUS current
	DESCRIPTION
	"This object indicates the physical position of this matrix card. 
        Left(1), Right(2), or Other(3)"
	::= { excelMtxEntry 2 }

  excelMtxType OBJECT-TYPE
      SYNTAX INTEGER {
          other(1),
          pcx(2),
          csn(3),
          lnx(4),
          exnetConnect(5)
          } 
      MAX-ACCESS read-only
      STATUS current
      DESCRIPTION 
          "This object indicates the node type of this matrix card.
          other(1), pcx(2), csn(3), lnx(4), or exnetConnect(5)."
      ::= { excelMtxEntry 3 }

  excelMtxState OBJECT-TYPE
      SYNTAX INTEGER {
          booting(1),
          initializing(2),
          standby(3),
          switchOver(4),
          active(5),
          other(6),
          disabled (7)
          } 
      MAX-ACCESS read-only
      STATUS current
      DESCRIPTION 
          "This object indicates the current state of this matrix card.
          The possible return values are:
          booting(1), 
          initializing(2), 
          standby(3), 
          switchOver(4), 
          active(5),
          other(6),
          disabled(7)."
      ::= { excelMtxEntry 4 }

  excelMtxAdjacentMatrixStatus OBJECT-TYPE
      SYNTAX INTEGER {
          noAdjacentMatrixDetected(1),
          adjacentMatrixDetectedNoIMC(2),
          adjacentMatrixDetectedNoHost(3),
          adjacentMatrixDetectedHostComms(4),
          other(5)
          } 
      MAX-ACCESS read-only
      STATUS current
      DESCRIPTION 
          "This object indicates the status of the adjacent matrix card.
          notPresent(1), detected(2), noHost(3), ok(4), other(5)"
      ::= { excelMtxEntry 5 }


  excelMtxHostLink OBJECT-TYPE
      SYNTAX INTEGER {
          ok(1),
          error(2)
          } 
      MAX-ACCESS read-only
      STATUS current
      DESCRIPTION 
          "This object indicates the status of the matrix card host link."
      ::= { excelMtxEntry 6 }


  excelMtxRamLoadPresent OBJECT-TYPE
      SYNTAX INTEGER {
          yes(1),
          no(2)
          } 
      MAX-ACCESS read-only
      STATUS current
      DESCRIPTION 
          "This object indicates the status of the matrix card download."
      ::= { excelMtxEntry 7 }

  excelMtxReadyForConfiguration OBJECT-TYPE
      SYNTAX INTEGER {
          yes(1),
          no(2)
          } 
      MAX-ACCESS read-only
      STATUS current
      DESCRIPTION 
          "This object indicates the state of the matrix card."
      ::= { excelMtxEntry 8 }

excelMtxIpAddress OBJECT-TYPE
      SYNTAX IpAddress
      MAX-ACCESS read-only
      STATUS current
      DESCRIPTION 
          "This object is the IP Address associated with the currently 
          active matrix card."
      ::= { excelMtxEntry 9 }

excelMtxBootMajorVersion OBJECT-TYPE
    SYNTAX DisplayString
    MAX-ACCESS read-only
    STATUS current
    DESCRIPTION
        "Current value of the major version number of the boot software."

    ::= { excelMtxEntry 10 }

excelMtxBootMinorVersion  OBJECT-TYPE
    SYNTAX DisplayString
    MAX-ACCESS read-only
    STATUS current
    DESCRIPTION
        "If value is equal to zero (0), no system software is present"

    ::= { excelMtxEntry 11 }

excelMtxSystemSoftwareMajor OBJECT-TYPE    
    SYNTAX DisplayString
    MAX-ACCESS read-only
    STATUS current
    DESCRIPTION
        "If value is equal to zero (0), no system software is present"

    ::= { excelMtxEntry 12 }

excelMtxSystemSoftwareMinor OBJECT-TYPE    
    SYNTAX DisplayString    
    MAX-ACCESS read-only
    STATUS current
    DESCRIPTION
        "If value is equal to zero (0), no system software is present"

    ::= { excelMtxEntry 13 }

excelMtxSystemSoftwareBuild OBJECT-TYPE    
    SYNTAX DisplayString
    MAX-ACCESS read-only
    STATUS current
    DESCRIPTION
        "If value is equal to zero (0), no system software is present"

    ::= { excelMtxEntry 14 }

excelMtxSecIpAddress OBJECT-TYPE
      SYNTAX IpAddress
      MAX-ACCESS read-only
      STATUS current
      DESCRIPTION 
          "This object is the IP Address associated with the current  
          atand-by matrix card."
      ::= { excelMtxEntry 15 }

excelMatrixManagement  OBJECT IDENTIFIER ::= {excelMatrix 2}

excelMatrixSwitchOver OBJECT-TYPE
    SYNTAX INTEGER {
              initial (1),
              switchOver (2)
    }
    MAX-ACCESS read-write
    STATUS current
    DESCRIPTION
        "This object provides capabilty to cause a matrix switchover"
    DEFVAL { 1 } 

    ::= { excelMatrixManagement 1 }

excelMatrixSwitchOverTime OBJECT-TYPE
    SYNTAX DisplayString
    MAX-ACCESS read-only
    STATUS current
    DESCRIPTION
        "The date and time when the matrix switchover occurred"

    ::= { excelMatrixManagement 2 }
--
-- EXNET Connect Group
--
-- This group contains a table with rows representing each EXNET
-- Connect card that in a ExnetConnect Node (Exnet Connect Nodes are PC/AT 
-- based hardware that may share a chassis with equipment from other manufactures
--
excelExnetConnect OBJECT IDENTIFIER ::= { excelCommunicationSoftware 2 }
 
excelExnetConnectTable OBJECT-TYPE
	SYNTAX SEQUENCE OF ExcelExnetConnectEntry 
	MAX-ACCESS not-accessible
	STATUS current
	DESCRIPTION
	"This table contains a row for each EXNET Connect Card in the PC 
        Chassis."
	::= { excelExnetConnect 1 }

excelExnetConnectEntry OBJECT-TYPE
	SYNTAX ExcelExnetConnectEntry 
	MAX-ACCESS not-accessible
        STATUS current
    DESCRIPTION "Definition of the ExcelExnetConnectEntry sequence"

    INDEX { excelExnetConnectLogicalNodeIDIndex }
	::= { excelExnetConnectTable 1 }
    
ExcelExnetConnectEntry ::= SEQUENCE {
    excelExnetConnectLogicalNodeIDIndex     INTEGER,
    excelExnetConnectClockMaster            INTEGER,
    excelExnetConnectClockSpeed             INTEGER
    }

excelExnetConnectLogicalNodeIDIndex OBJECT-TYPE
	SYNTAX INTEGER ( 0..255 )
	MAX-ACCESS read-only
	STATUS current
	DESCRIPTION
	"This object is the logical Node ID that has been assigned to this 
        EXNET Connect"
	::= { excelExnetConnectEntry 1 }


excelExnetConnectClockMaster OBJECT-TYPE
	SYNTAX INTEGER { 
         no(1),
         yes(2)
         }
	MAX-ACCESS read-only
	STATUS current
	DESCRIPTION
		"This object indicates whether or not the EXNET Connect
        Card is the clock master on the bus.  If the value is
        yes(2), then the EXNET Connect card is the clock master."
	::= { excelExnetConnectEntry 2 }

excelExnetConnectClockSpeed OBJECT-TYPE
	SYNTAX INTEGER {
		fourMHz(1),
		twoMHz(2)
		}
	MAX-ACCESS read-only
	STATUS current
	DESCRIPTION
		"The clock speed of the resource bus on this EXNET
        Connect."
	::= { excelExnetConnectEntry 3 }
    
 
--
-- Span Group
--
-- This group contains the span table.  This table contains an entry  for 
-- every  logical span assigned in the system. The rows are ordered by
-- slot and then by span offset.
excelSpans                 OBJECT IDENTIFIER ::= {excelCommunicationSoftware 3}

excelGeneralSpan	   OBJECT IDENTIFIER ::= {excelSpans 1 }
--
-- This group contains general error information on T1 and E1 spans.  
-- Information is obtained by assigning a value to ExcelLogicalSpanId 
-- prior to making any requests
--
excelSpanTable OBJECT-TYPE
	SYNTAX SEQUENCE OF ExcelSpanEntry 
	MAX-ACCESS not-accessible
	STATUS current
	DESCRIPTION
	"This table contains a row for each active span defined on a line card
    contained in the chassis."
	::= { excelGeneralSpan 1 }

excelSpanEntry OBJECT-TYPE
	SYNTAX ExcelSpanEntry 
	MAX-ACCESS not-accessible
        STATUS current
    DESCRIPTION "Definition of the ExcelSpanEntry sequence"

    INDEX { excelCurrentNode, excelLogicalSpanId }
	::= { excelSpanTable 1 }
    
ExcelSpanEntry ::= SEQUENCE {
    excelSpanTableIndex INTEGER,
    excelLogicalSpanId INTEGER,
    excelSpanBipolarViolation Counter32,
    excelSpanFrameErrors Counter32,
    excelSpanSlipErrors Counter32,
    excelSpanLossofFrame Counter32
}

excelSpanTableIndex OBJECT-TYPE
	SYNTAX INTEGER (0..84 )
	MAX-ACCESS  not-accessible
	STATUS current
	DESCRIPTION 
	"The Logical Span ID being accessed"
	::= { excelSpanEntry 1 } 

excelLogicalSpanId OBJECT-TYPE
	SYNTAX INTEGER (0..84 )
	MAX-ACCESS read-only
	STATUS current
	DESCRIPTION 
	"The Logical Span ID being accessed"
	::= { excelSpanEntry 2 } 

excelSpanBipolarViolation OBJECT-TYPE
	SYNTAX Counter32
	MAX-ACCESS read-only
	STATUS current
	DESCRIPTION
		"The number of Bipolar Violations that have occurred on 
	this span since the span became active or since the last request"
	
	::= { excelSpanEntry 3 }

excelSpanFrameErrors OBJECT-TYPE
	SYNTAX Counter32
	MAX-ACCESS read-only
	STATUS current
	DESCRIPTION
		"If the queried span in a T1 span, then this field will 
	contain the number of Bit Frame Errors that have occurred on this span
 	since the span became active or since the last request.

	If the queried span in an E1 span, then this field will contain the 
	number of Frame Alignment Signal Errors that have occurred on this 
	span since the span became active or since the last request"

	::= { excelSpanEntry 4 }

excelSpanSlipErrors OBJECT-TYPE
	SYNTAX Counter32
	MAX-ACCESS read-only
	STATUS current
	DESCRIPTION
		"The number of slips that have occurred on this span since 
	the span became active or since the last request"

	::= { excelSpanEntry 5 }

excelSpanLossofFrame OBJECT-TYPE
	SYNTAX Counter32
	MAX-ACCESS read-only
	STATUS current
	DESCRIPTION
            "The number of loss of frame that have occurred on this 
            span since the since the last request"

	::= { excelSpanEntry 6 }

excelSpanManagement OBJECT IDENTIFIER ::= { excelSpans 2 }

excelCurrentSpanId OBJECT-TYPE
    SYNTAX INTEGER (0..84)
    MAX-ACCESS read-write
    STATUS current
    DESCRIPTION
        "The id of the span an in/out of service action will occur on."

    ::= { excelSpanManagement 1 }

excelSpanAction OBJECT-TYPE
    SYNTAX INTEGER { inService(1),
                     outOfService (2)
                     }
    MAX-ACCESS read-write
    STATUS current
    DESCRIPTION
        "The action to be taken againts the span id defined by 
        excelCurrentSpanId."

    ::= { excelSpanManagement 2 }

excelChannelAction OBJECT-TYPE
    SYNTAX INTEGER { inService (1),
                     outOfService (2)
                     }
    MAX-ACCESS read-write
    STATUS current
    DESCRIPTION
        "The action to be taken againts the channels associated with 
        the span as defined in excelCurrentSpanID"

    ::= { excelSpanManagement 3 }

-- Signaling System Number 7 Protocol
--
excelSS7   OBJECT IDENTIFIER ::= { excelCommunicationSoftware 4 }
-- SS7 Configuration
excelSS7Config               OBJECT IDENTIFIER ::= { excelSS7 1 }
-- SS7 Statistics
excelSS7Statistics           OBJECT IDENTIFIER ::= { excelSS7 2 }

-- Signaling System 7 Group
--
-- This group is broken up into two groups,  excelSS7Config and
-- excelSS7Statistics.
--

--
-- The SS7 Configuration Group contains 5 tables, excelSS7CardTable 
-- excelSS7ConfigStackTable, 
-- excelSS7ConfigRouteTable, excelSS7ConfigLinkTable and 
-- excelSS7ConfigCircuitIDCodeGroupTable
--
excelSS7CardTable OBJECT-TYPE
	SYNTAX SEQUENCE OF ExcelSS7CardEntry 
	MAX-ACCESS not-accessible
	STATUS current
	DESCRIPTION
	"This table contains a row for each SS7 Card in the current node."
	::= { excelSS7Config 1 }

excelSS7CardEntry OBJECT-TYPE
	SYNTAX ExcelSS7CardEntry 
	MAX-ACCESS not-accessible
	STATUS current
        DESCRIPTION 
          "Definition of the ExcelSS7CardEntry sequence"

    INDEX { excelSS7CardSlotNumberIndex }
    ::= { excelSS7CardTable 1 }

ExcelSS7CardEntry ::= SEQUENCE {
    excelSS7CardSlotNumberIndex		        INTEGER,
	excelSS7CardRedundancyConfiguredRole	INTEGER,
	excelSS7CardRedundancyCurrentRole   	INTEGER,
	excelSS7CardRedundancyMate		INTEGER,
	excelSS7CardRedundancyStatus		INTEGER,
	excelSS7CardStackID1    		INTEGER,
	excelSS7CardStackID2			INTEGER,
	excelSS7CardStackID3		        INTEGER,
	excelSS7CardStackID4		        INTEGER,
	excelSS7CardMaximumLinks		INTEGER 
    } 

excelSS7CardSlotNumberIndex OBJECT-TYPE
	SYNTAX INTEGER (0..64 )
	MAX-ACCESS not-accessible
	STATUS current
	DESCRIPTION
	" This entry represents slot number in which this card resides. "
	::= {excelSS7CardEntry 1 }

excelSS7CardRedundancyConfiguredRole OBJECT-TYPE
	SYNTAX INTEGER {
	primary(1),
	secondary(2),
	notConfigured(3),
	unknown(4)}
	MAX-ACCESS read-only
	STATUS current
	DESCRIPTION
	" This entry represents the configured role of this card in SS7 
        redundancy. The current role may be different"
	::= {excelSS7CardEntry 2 }

excelSS7CardRedundancyCurrentRole OBJECT-TYPE
	SYNTAX INTEGER {
		active(1),
		standby(2),
		notConfigured(3),
		unknown(4)}
	MAX-ACCESS read-only
	STATUS current
	DESCRIPTION
	" This entry represents the current role of this card in SS7 
        redundancy."

	::= {excelSS7CardEntry 3 }

excelSS7CardRedundancyMate OBJECT-TYPE
	SYNTAX INTEGER (0..255 )
	MAX-ACCESS read-only
	STATUS current
	DESCRIPTION
	" This entry represents the slot number of the SS7 card associated 
        with this card for the  purpose of SS7 redundancy. A value of 255 
        (0xff) indicates that there is no association."

	::= {excelSS7CardEntry 4 }

excelSS7CardRedundancyStatus OBJECT-TYPE
	SYNTAX INTEGER {
            synchronizing-PrimaryReceiveFromMatrix(1),
            synchronizing-PrimarySendToMatrix(2),
            bothCardsActive-PrimaryReceiveFromMatrix(3),
            bothCardsActive-PrimarySendToMatrix(4),
            primaryCardOutOfService(5),
            secondaryCardOutOfService(6),
            redundantIOCardRemoved(7),
            synchronizationTimeOut(8),
            redundancyDisabled(9),
            primaryCardResetDuringSynchronization(10),
            secondaryCardResetDuringSynchronization(11),
            primaryCardLinkFailureDuringSynchronization(12), 
            secondaryCardLinkFailureDuringSynchronization(13), 
            primaryCardLinkToMateFailureInStableState(14),
            secondaryCardLinkToMateFailureInStableState(15),
            dualInternalRedundancyFailure(16),
            unknown(17),
            notConfigured(18)
        }
	MAX-ACCESS read-only
	STATUS current
	DESCRIPTION
		" This entry represents the current role of this card in 
		SS7 redundancy."
	::= {excelSS7CardEntry 5 }

excelSS7CardStackID1 OBJECT-TYPE
	SYNTAX INTEGER (0..255 )
	MAX-ACCESS read-only
	STATUS current
	DESCRIPTION
	" This entry represents the ID of the first of four possible stack ids 
	resident on this card. A value of 255 (0xff) indicates not configured."
	::= {excelSS7CardEntry 6 }

excelSS7CardStackID2 OBJECT-TYPE
	SYNTAX INTEGER (0..255 )
	MAX-ACCESS read-only
	STATUS current
	DESCRIPTION
	" This entry represents the ID of the second of four possible stack 
        id resident on this card. A value of 255 (0xff) indicates not 
        configured."

	::= {excelSS7CardEntry 7 }

excelSS7CardStackID3 OBJECT-TYPE
	SYNTAX INTEGER (0..255 )
	MAX-ACCESS read-only
	STATUS current
	DESCRIPTION
	" This entry represents the ID of the third of four possible stack ids 
	resident on this card. A value of 255 (0xff) indicates not configured."

	::= {excelSS7CardEntry 8 }

excelSS7CardStackID4 OBJECT-TYPE
	SYNTAX INTEGER (0..255 )
	MAX-ACCESS read-only
	STATUS current
	DESCRIPTION
	" This entry represents the ID of the fourth of four possible stack 
        ids resident on this card. A value of 255 (0xff) indicates not 
        configured."

	::= {excelSS7CardEntry 9 }

excelSS7CardMaximumLinks OBJECT-TYPE
	SYNTAX INTEGER (0..255 )
	MAX-ACCESS read-only
	STATUS current
	DESCRIPTION
	" This entry represents the maximum number of links supported by this 
        card. "
	::= {excelSS7CardEntry 10 }

excelSS7ConfigLinkTable OBJECT-TYPE
	SYNTAX SEQUENCE OF ExcelSS7LinkEntry 
	MAX-ACCESS not-accessible
	STATUS current
	DESCRIPTION
	"This table contains a row for each link that is assigned in the node."
	::= { excelSS7Config 2 }

excelSS7LinkEntry OBJECT-TYPE
	SYNTAX ExcelSS7LinkEntry 
	MAX-ACCESS not-accessible
	STATUS current
        DESCRIPTION 
          "Definition of the ExcelSS7LinkEntry sequence"

    INDEX { excelSS7LinkStackIndex, excelSS7LinkLinkIndex, 
                excelSS7LinkLinkSetIndex }
    ::= { excelSS7ConfigLinkTable 1 }

ExcelSS7LinkEntry ::= SEQUENCE {
	excelSS7LinkStackIndex			INTEGER,
    excelSS7LinkLinkIndex			INTEGER,
	excelSS7LinkLinkSetIndex		INTEGER,
	excelSS7LinkStatus			INTEGER,
	excelSS7LinkSignalingLinkCode	        INTEGER,
	excelSS7LinkDataRate			INTEGER,
	excelSS7LinkLogicalSpanID		INTEGER,
	excelSS7Linkchannel			INTEGER
} 

excelSS7LinkStackIndex	OBJECT-TYPE
	SYNTAX INTEGER (0..255 )
	MAX-ACCESS not-accessible
	STATUS current
	DESCRIPTION
	" This entry represents the Stack with which this link is associated. 
		A value of 255 (0xff) indicates not configured."
	::= { excelSS7LinkEntry 1 }

excelSS7LinkLinkIndex OBJECT-TYPE
	SYNTAX INTEGER(0..255 )
	MAX-ACCESS not-accessible
	STATUS current
	DESCRIPTION
	" This entry represent the ID of this link. A value of 255 (0xff) 
        indicates not configured."

	::= {excelSS7LinkEntry 2 }

	
excelSS7LinkLinkSetIndex OBJECT-TYPE
	SYNTAX INTEGER(0..255 )
	MAX-ACCESS not-accessible
	STATUS current
	DESCRIPTION
	" This entry represents the Link Set with which this link is 
        associated.  A value of 255 (0xff) indicates not configured."

	::= { excelSS7LinkEntry 3 }

	
excelSS7LinkStatus OBJECT-TYPE
	SYNTAX INTEGER {
	available(1),
	failed(2),
	inhibitLocally(3),
	inhibitRemotely(4),
	remoteBlocked(5),
	reserved5(6),
	reserved6(7),
	reserved7(8),
	unknown(9) }
	MAX-ACCESS read-only
	STATUS current
	DESCRIPTION
		" This entry represents the status of this link."
	::= { excelSS7LinkEntry 4 }

	
excelSS7LinkSignalingLinkCode OBJECT-TYPE
	SYNTAX INTEGER (0..1024 )
	MAX-ACCESS read-only
	STATUS current
	DESCRIPTION
		" This entry represents the Signaling Link Code."
	::= { excelSS7LinkEntry 5 }

excelSS7LinkDataRate  OBJECT-TYPE
	SYNTAX INTEGER {
		dataRate64kbps(1),
		dataRate56kbps(2)
		}
	MAX-ACCESS read-only
	STATUS current
	DESCRIPTION
		" This entry represents the data rate for this link."
	::= { excelSS7LinkEntry 6 }

excelSS7LinkLogicalSpanID  OBJECT-TYPE
	SYNTAX INTEGER (0..255 )
	MAX-ACCESS read-only
	STATUS current
	DESCRIPTION
	" This entry represents the Logical Span on which this link resides."
	::= { excelSS7LinkEntry 7 }

excelSS7Linkchannel	 OBJECT-TYPE
	SYNTAX INTEGER (0..8192 )
	MAX-ACCESS read-only
	STATUS current
	DESCRIPTION
	" This entry represents the Channel Offset on which this link resides."
	::= { excelSS7LinkEntry 8 }


excelSS7StackTable OBJECT-TYPE
	SYNTAX SEQUENCE OF ExcelSS7StackEntry 
	MAX-ACCESS not-accessible
	STATUS current
	DESCRIPTION
	"This table contains a row for each SS7 Stack in the current node."
	::= { excelSS7Config 3 }

excelSS7StackEntry OBJECT-TYPE
	SYNTAX ExcelSS7StackEntry 
	MAX-ACCESS not-accessible
	STATUS current
        DESCRIPTION 
          "Definition of the ExcelSS7StackEntry sequence"

    INDEX { excelSS7StackIDIndex }
    ::= { excelSS7StackTable 1 }

ExcelSS7StackEntry ::= SEQUENCE {
        excelSS7StackIDIndex		INTEGER,
	excelSS7StackOPC		DisplayString,
	excelSS7StackMTPVariant		SS7VariantsTypes,
	excelSS7StackISUPVariant	SS7VariantsTypes,
	excelSS7StackL3PVariant		SS7VariantsTypes,
	excelSS7StackTUPVariant		SS7VariantsTypes,
	excelSS7StackL3PTUPVariant	SS7VariantsTypes	
    } 


excelSS7StackIDIndex  OBJECT-TYPE
	SYNTAX INTEGER (0..255 )
	MAX-ACCESS not-accessible
	STATUS current
	DESCRIPTION
		"This entry represents the stack id."
	::= { excelSS7StackEntry 1 }

excelSS7StackOPC  OBJECT-TYPE
	SYNTAX DisplayString
	MAX-ACCESS read-only
	STATUS current
	DESCRIPTION
	" This entry represents this Origination Point Code for this SS7 node."
	::= { excelSS7StackEntry 2 }

excelSS7StackMTPVariant  OBJECT-TYPE
	SYNTAX SS7VariantsTypes
	MAX-ACCESS read-only
	STATUS current
	DESCRIPTION
	" This entry represents the MTP variant supported."

	::= { excelSS7StackEntry 3 }

excelSS7StackISUPVariant  OBJECT-TYPE
	SYNTAX SS7VariantsTypes
	MAX-ACCESS read-only
	STATUS current
	DESCRIPTION
	" This entry represents the ISUP variant supported."

	::= { excelSS7StackEntry 4 }

excelSS7StackL3PVariant  OBJECT-TYPE
	SYNTAX SS7VariantsTypes
	MAX-ACCESS read-only
	STATUS current
	DESCRIPTION
	" This entry represents the L3P variant supported."

	::= { excelSS7StackEntry 5 }

excelSS7StackTUPVariant  OBJECT-TYPE
	SYNTAX SS7VariantsTypes
	MAX-ACCESS read-only
	STATUS current
	DESCRIPTION
		" This entry represents the TUP variant supported."
	::= { excelSS7StackEntry 6 }

excelSS7StackL3PTUPVariant  OBJECT-TYPE
	SYNTAX SS7VariantsTypes
	MAX-ACCESS read-only
	STATUS current
	DESCRIPTION
		" This entry represents the L3P	TUP variant supported."
	::= { excelSS7StackEntry 7 }


excelSS7LinkSetTable OBJECT-TYPE
	SYNTAX SEQUENCE OF ExcelSS7LinkSetEntry 
	MAX-ACCESS not-accessible
	STATUS current
	DESCRIPTION
	"This table contains a row for each SS7 LinkSet in the current node."
	::= { excelSS7Config 4 }

excelSS7LinkSetEntry OBJECT-TYPE
	SYNTAX ExcelSS7LinkSetEntry 
	MAX-ACCESS not-accessible
	STATUS current
        DESCRIPTION 
          "Definition of the ExcelSS7LinkSetEntry sequence"

    INDEX { excelSS7LinkSetIDIndex, excelSS7LinkSetStackIDIndex }
    ::= { excelSS7LinkSetTable 1 }

ExcelSS7LinkSetEntry ::= SEQUENCE {
    excelSS7LinkSetIDIndex		INTEGER,
    excelSS7LinkSetStackIDIndex	        INTEGER,
    excelSS7LinkSetStatus		INTEGER,
    excelSS7LinkSetAPC			DisplayString
}


excelSS7LinkSetIDIndex  OBJECT-TYPE
	SYNTAX INTEGER (0..255 )
	MAX-ACCESS not-accessible
	STATUS current
	DESCRIPTION
		"This entry represents the logical link set id."
	::= { excelSS7LinkSetEntry 1 }

excelSS7LinkSetStatus  OBJECT-TYPE
	SYNTAX INTEGER {
             available(1),
             unavailable(2),
             unknown(3)
         }
	MAX-ACCESS read-only
	STATUS current
	DESCRIPTION
		"This entry represents the link set status."
	::= { excelSS7LinkSetEntry 2 }

excelSS7LinkSetAPC  OBJECT-TYPE
	SYNTAX DisplayString
	MAX-ACCESS read-only
	STATUS current
	DESCRIPTION
		"This entry represents the APC for this link."
	::= { excelSS7LinkSetEntry 3 }

excelSS7LinkSetStackIDIndex  OBJECT-TYPE
	SYNTAX INTEGER (0..1024 )
	MAX-ACCESS read-only
	STATUS current
	DESCRIPTION
		"This entry represents the Logical Stack ID associated with 
                this link."
	::= { excelSS7LinkSetEntry 4 }

--
-- Excel PPL Group
-- 
-- This group contains objects pertaining Excel's Protocol Programming
-- Language.  
--
 
excelPPL OBJECT IDENTIFIER ::= { excelCommunicationSoftware 5 }

excelPPLComponentId OBJECT-TYPE
    SYNTAX INTEGER ( 0..99 )
    MAX-ACCESS read-only
    STATUS current
    DESCRIPTION
        "Component  id of the PPL event being processed"
    ::= { excelPPL 1 }

excelPPLComponentStatistics OBJECT IDENTIFIER ::= { excelPPL 2 }

--
-- Statistics table for PPL Component Layer 3 Plus CIC (L3PCIC)
--

excelL3PCICTable OBJECT-TYPE
	SYNTAX SEQUENCE OF ExcelL3PCICEntry 
	MAX-ACCESS not-accessible
	STATUS current
	DESCRIPTION
        "This table will contain information on the ppl L3P CIC events 
        receicved and the date and time of the last one received.  Only the 
        following event ID will be captured:
        
            8       Remote maintaince block indication
            15      Remote hardware group block indication
            18      Local maintaince block success
            22      UCIC received"

	::= { excelPPLComponentStatistics 1 }

excelL3PCICEntry OBJECT-TYPE
    SYNTAX ExcelL3PCICEntry 
    MAX-ACCESS not-accessible
    STATUS current
    DESCRIPTION 
          ""
    INDEX { excelL3PCICSpanID, excelL3PCICChannelID, excelL3PCICEventID }
    ::= { excelL3PCICTable 1 }

ExcelL3PCICEntry ::= SEQUENCE {
    excelL3PCICIndex        INTEGER,
    excelL3PCICSpanID       INTEGER,
    excelL3PCICChannelID    INTEGER,
    excelL3PCICEventID      INTEGER,
    excelL3PCICTime         DisplayString,
    excelL3PCICCount        INTEGER,
    excelL3PCICStatus       RowStatus
}

excelL3PCICIndex OBJECT-TYPE
	SYNTAX INTEGER (0..65535)
	MAX-ACCESS not-accessible
	STATUS current
	DESCRIPTION
	"Index into this table."
	::= { excelL3PCICEntry 1 }

excelL3PCICSpanID OBJECT-TYPE
	SYNTAX INTEGER ( 0..84 )
	MAX-ACCESS read-create
	STATUS current
	DESCRIPTION
	"The id of the span this event has occurred on."
	::= { excelL3PCICEntry 2 }

excelL3PCICChannelID OBJECT-TYPE
	SYNTAX INTEGER ( 0..16 )
	MAX-ACCESS read-create
	STATUS current
	DESCRIPTION
        "The id of the channel this event has occurred on."
	::= { excelL3PCICEntry 3 }

excelL3PCICEventID OBJECT-TYPE
	SYNTAX INTEGER ( 0..99 )
	MAX-ACCESS read-create
	STATUS current
	DESCRIPTION
        "Id of the event that has occurred."
	::= { excelL3PCICEntry 4 }

excelL3PCICTime OBJECT-TYPE
	SYNTAX DisplayString
	MAX-ACCESS read-create
	STATUS current
	DESCRIPTION
        "The time of the last occurance of this event."
	::= { excelL3PCICEntry 5 }

excelL3PCICCount OBJECT-TYPE
	SYNTAX INTEGER ( 0..32656 )
	MAX-ACCESS read-create
	STATUS current
	DESCRIPTION
        "The current number of times this event has occurred since system 
        startup"
	::= { excelL3PCICEntry 6 }

excelL3PCICStatus OBJECT-TYPE
	SYNTAX RowStatus
	MAX-ACCESS read-create
	STATUS current
	DESCRIPTION
        "The status of this program entry"
	::= { excelL3PCICEntry 7 }

--
-- Statistics table for PPL Component Layer 3 Plus Link (L3PLink)
--

excelL3PLinkTable OBJECT-TYPE
	SYNTAX SEQUENCE OF ExcelL3PCICEntry 
	MAX-ACCESS not-accessible
	STATUS current
	DESCRIPTION
        "This table will contain information on the ppl L3P link events 
        receicved and the date and time of the last one received.  Only the 
        following event ID will be captured:
        
            10 - Link in service
            11 - Link out-of-service, L1_DEAD
            12 - Link out of service, L5_OOS"

	::= { excelPPLComponentStatistics 2 }

excelL3PLinkEntry OBJECT-TYPE
	SYNTAX ExcelL3PLinkEntry 
	MAX-ACCESS not-accessible
	STATUS current
    DESCRIPTION 
          ""
    INDEX { excelL3PLinkSpanID, excelL3PLinkChannelID, excelL3PLinkEventID }
    ::= { excelL3PLinkTable 1 }

ExcelL3PLinkEntry ::= SEQUENCE {
    excelL3PLinkIndex        INTEGER,
    excelL3PLinkSpanID       INTEGER,
    excelL3PLinkChannelID    INTEGER,
    excelL3PLinkEventID      INTEGER,
    excelL3PLinkTime         DisplayString,
    excelL3PLinkCount        INTEGER,
    excelL3PLinkStatus       RowStatus
}

excelL3PLinkIndex OBJECT-TYPE
	SYNTAX INTEGER (0..65535)
	MAX-ACCESS not-accessible
	STATUS current
	DESCRIPTION
	"Index into this table."
	::= { excelL3PLinkEntry 1 }

excelL3PLinkSpanID OBJECT-TYPE
	SYNTAX INTEGER ( 0..84 )
	MAX-ACCESS read-create
	STATUS current
	DESCRIPTION
	"The id of the span this event has occurred on."
	::= { excelL3PLinkEntry 2 }

excelL3PLinkChannelID OBJECT-TYPE
	SYNTAX INTEGER ( 0..16 )
	MAX-ACCESS read-create
	STATUS current
	DESCRIPTION
        "The id of the channel this event has occurred on."
	::= { excelL3PLinkEntry 3 }

excelL3PLinkEventID OBJECT-TYPE
	SYNTAX INTEGER ( 0..99 )
	MAX-ACCESS read-create
	STATUS current
	DESCRIPTION
        "Id of the event that has occurred."
	::= { excelL3PLinkEntry 4 }

excelL3PLinkTime OBJECT-TYPE
	SYNTAX DisplayString
	MAX-ACCESS read-create
	STATUS current
	DESCRIPTION
        "The time of the last occurance of this event."
	::= { excelL3PLinkEntry 5 }

excelL3PLinkCount OBJECT-TYPE
	SYNTAX INTEGER ( 0..32656 )
	MAX-ACCESS read-create
	STATUS current
	DESCRIPTION
        "The current number of times this event has occurred since system 
        startup"
	::= { excelL3PLinkEntry 6 }

excelL3PLinkStatus OBJECT-TYPE
	SYNTAX RowStatus
	MAX-ACCESS read-create
	STATUS current
	DESCRIPTION
        "The status of this program entry"
	::= { excelL3PLinkEntry 7 }

--
-- Statistics table for PPL Component CPC
--

excelCPCTable OBJECT-TYPE
	SYNTAX SEQUENCE OF ExcelCPCEntry 
	MAX-ACCESS not-accessible
	STATUS current
	DESCRIPTION
        "This table will contain information on the ppl CPC events 
        receicved and the date and time of the last one received.  Only the 
        following event ID will be captured:
        
            20     Maximum number of UTP retries completed without a response"

	::= { excelPPLComponentStatistics 3 }

excelCPCEntry OBJECT-TYPE
	SYNTAX ExcelCPCEntry 
	MAX-ACCESS not-accessible
	STATUS current
    DESCRIPTION 
          ""
    INDEX { excelCPCSpanID, excelCPCChannelID, excelCPCEventID }
    ::= { excelCPCTable 1 }

ExcelCPCEntry ::= SEQUENCE {
    excelCPCIndex        INTEGER,
    excelCPCSpanID       INTEGER,
    excelCPCChannelID    INTEGER,
    excelCPCEventID      INTEGER,
    excelCPCTime         DisplayString,
    excelCPCCount        INTEGER,
    excelCPCStatus       RowStatus
}

excelCPCIndex OBJECT-TYPE
	SYNTAX INTEGER (0..65535)
	MAX-ACCESS not-accessible
	STATUS current
	DESCRIPTION
	"Index into this table."
	::= { excelCPCEntry 1 }

excelCPCSpanID OBJECT-TYPE
	SYNTAX INTEGER ( 0..84 )
	MAX-ACCESS read-create
	STATUS current
	DESCRIPTION
	"The id of the span this event has occurred on."
	::= { excelCPCEntry 2 }

excelCPCChannelID OBJECT-TYPE
	SYNTAX INTEGER ( 0..16 )
	MAX-ACCESS read-create
	STATUS current
	DESCRIPTION
        "The id of the channel this event has occurred on."
	::= { excelCPCEntry 3 }

excelCPCEventID OBJECT-TYPE
	SYNTAX INTEGER ( 0..99 )
	MAX-ACCESS read-create
	STATUS current
	DESCRIPTION
        "Id of the event that has occurred."
	::= { excelCPCEntry 4 }

excelCPCTime OBJECT-TYPE
	SYNTAX DisplayString
	MAX-ACCESS read-create
	STATUS current
	DESCRIPTION
        "The time of the last occurance of this event."
	::= { excelCPCEntry 5 }

excelCPCCount OBJECT-TYPE
	SYNTAX INTEGER ( 0..32656 )
	MAX-ACCESS read-create
	STATUS current
	DESCRIPTION
        "The current number of times this event has occurred since system 
        startup"
	::= { excelCPCEntry 6 }

excelCPCStatus OBJECT-TYPE
	SYNTAX RowStatus
	MAX-ACCESS read-create
	STATUS current
	DESCRIPTION
        "The status of this program entry"
	::= { excelCPCEntry 7 }

--
-- Statistics table for PPL Component SPRC
--

excelSPRCTable OBJECT-TYPE
	SYNTAX SEQUENCE OF ExcelSPRCEntry 
	MAX-ACCESS not-accessible
	STATUS current
	DESCRIPTION
        "This table will contain information on the ppl SPRC events 
        receicved and the date and time of the last one received.  Only the 
        following event ID will be captured:
        
            2       Undefined CIC in incoming message
            5       Remote user part available"

	::= { excelPPLComponentStatistics 4 }

excelSPRCEntry OBJECT-TYPE
	SYNTAX ExcelSPRCEntry 
	MAX-ACCESS not-accessible
	STATUS current
    DESCRIPTION 
          ""
    INDEX { excelSPRCSpanID, excelSPRCChannelID, excelSPRCEventID }
    ::= { excelSPRCTable 1 }

ExcelSPRCEntry ::= SEQUENCE {
    excelSPRCIndex        INTEGER,
    excelSPRCSpanID       INTEGER,
    excelSPRCChannelID    INTEGER,
    excelSPRCEventID      INTEGER,
    excelSPRCTime         DisplayString,
    excelSPRCCount        INTEGER,
    excelSPRCStatus       RowStatus
}

excelSPRCIndex OBJECT-TYPE
	SYNTAX INTEGER (0..65535)
	MAX-ACCESS not-accessible
	STATUS current
	DESCRIPTION
	"Index into this table."
	::= { excelSPRCEntry 1 }

excelSPRCSpanID OBJECT-TYPE
	SYNTAX INTEGER ( 0..84 )
	MAX-ACCESS read-create
	STATUS current
	DESCRIPTION
	"The id of the span this event has occurred on."
	::= { excelSPRCEntry 2 }

excelSPRCChannelID OBJECT-TYPE
	SYNTAX INTEGER ( 0..16 )
	MAX-ACCESS read-create
	STATUS current
	DESCRIPTION
        "The id of the channel this event has occurred on."
	::= { excelSPRCEntry 3 }

excelSPRCEventID OBJECT-TYPE
	SYNTAX INTEGER ( 0..99 )
	MAX-ACCESS read-create
	STATUS current
	DESCRIPTION
        "Id of the event that has occurred."
	::= { excelSPRCEntry 4 }

excelSPRCTime OBJECT-TYPE
	SYNTAX DisplayString
	MAX-ACCESS read-create
	STATUS current
	DESCRIPTION
        "The time of the last occurance of this event."
	::= { excelSPRCEntry 5 }

excelSPRCCount OBJECT-TYPE
	SYNTAX INTEGER ( 0..32656 )
	MAX-ACCESS read-create
	STATUS current
	DESCRIPTION
        "The current number of times this event has occurred since system 
        startup"
	::= { excelSPRCEntry 6 }

excelSPRCStatus OBJECT-TYPE
	SYNTAX RowStatus
	MAX-ACCESS read-create
	STATUS current
	DESCRIPTION
        "The status of this program entry"
	::= { excelSPRCEntry 7 }

--
-- Statistics table for PPL Component UCIC
--


excelUCICTable OBJECT-TYPE
	SYNTAX SEQUENCE OF ExcelUCICEntry 
	MAX-ACCESS not-accessible
	STATUS current
	DESCRIPTION
        "This table will contain information on the ppl UCIC events 
        receicved and the date and time of the last one received.  Only the 
        following event ID will be captured:
        
            1       Unequipped CIC reception"

	::= { excelPPLComponentStatistics 5 }

excelUCICEntry OBJECT-TYPE
	SYNTAX ExcelUCICEntry 
	MAX-ACCESS not-accessible
	STATUS current
    DESCRIPTION 
          ""
    INDEX { excelUCICSpanID, excelUCICChannelID, excelUCICEventID }
    ::= { excelUCICTable 1 }

ExcelUCICEntry ::= SEQUENCE {
    excelUCICIndex        INTEGER,
    excelUCICSpanID       INTEGER,
    excelUCICChannelID    INTEGER,
    excelUCICEventID      INTEGER,
    excelUCICTime         DisplayString,
    excelUCICCount        INTEGER,
    excelUCICStatus       RowStatus
}

excelUCICIndex OBJECT-TYPE
	SYNTAX INTEGER (0..65535)
	MAX-ACCESS not-accessible
	STATUS current
	DESCRIPTION
	"Index into this table."
	::= { excelUCICEntry 1 }

excelUCICSpanID OBJECT-TYPE
	SYNTAX INTEGER ( 0..84 )
	MAX-ACCESS read-create
	STATUS current
	DESCRIPTION
	"The id of the span this event has occurred on."
	::= { excelUCICEntry 2 }

excelUCICChannelID OBJECT-TYPE
	SYNTAX INTEGER ( 0..16 )
	MAX-ACCESS read-create
	STATUS current
	DESCRIPTION
        "The id of the channel this event has occurred on."
	::= { excelUCICEntry 3 }

excelUCICEventID OBJECT-TYPE
	SYNTAX INTEGER ( 0..99 )
	MAX-ACCESS read-create
	STATUS current
	DESCRIPTION
        "Id of the event that has occurred."
	::= { excelUCICEntry 4 }

excelUCICTime OBJECT-TYPE
	SYNTAX DisplayString
	MAX-ACCESS read-create
	STATUS current
	DESCRIPTION
        "The time of the last occurance of this event."
	::= { excelUCICEntry 5 }

excelUCICCount OBJECT-TYPE
	SYNTAX INTEGER ( 0..32656 )
	MAX-ACCESS read-create
	STATUS current
	DESCRIPTION
        "The current number of times this event has occurred since system 
        startup"
	::= { excelUCICEntry 6 }

excelUCICStatus OBJECT-TYPE
	SYNTAX RowStatus
	MAX-ACCESS read-create
	STATUS current
	DESCRIPTION
        "The status of this program entry"
	::= { excelUCICEntry 7 }

--
-- Statistics table for PPL Component MTP3 HMDT
--


excelHMDTTable OBJECT-TYPE
	SYNTAX SEQUENCE OF ExcelHMDTEntry 
	MAX-ACCESS not-accessible
	STATUS current
	DESCRIPTION
        "This table will contain information on the ppl HMDT events 
        receicved and the date and time of the last one received.  Only the 
        following event ID will be captured:
        
            0       Remote processor outage
            2       Local Inhibit
            6       UPN MSU Received"

	::= { excelPPLComponentStatistics 6 }

excelHMDTEntry OBJECT-TYPE
	SYNTAX ExcelHMDTEntry 
	MAX-ACCESS not-accessible
	STATUS current
    DESCRIPTION 
          ""
    INDEX { excelHMDTSpanID, excelHMDTChannelID, excelHMDTEventID }
    ::= { excelHMDTTable 1 }

ExcelHMDTEntry ::= SEQUENCE {
    excelHMDTIndex        INTEGER,
    excelHMDTSpanID       INTEGER,
    excelHMDTChannelID    INTEGER,
    excelHMDTEventID      INTEGER,
    excelHMDTTime         DisplayString,
    excelHMDTCount        INTEGER,
    excelHMDTStatus       RowStatus
}

excelHMDTIndex OBJECT-TYPE
	SYNTAX INTEGER (0..65535)
	MAX-ACCESS not-accessible
	STATUS current
	DESCRIPTION
	"Index into this table."
	::= { excelHMDTEntry 1 }

excelHMDTSpanID OBJECT-TYPE
	SYNTAX INTEGER ( 0..84 )
	MAX-ACCESS read-create
	STATUS current
	DESCRIPTION
	"The id of the span this event has occurred on."
	::= { excelHMDTEntry 2 }

excelHMDTChannelID OBJECT-TYPE
	SYNTAX INTEGER ( 0..16 )
	MAX-ACCESS read-create
	STATUS current
	DESCRIPTION
        "The id of the channel this event has occurred on."
	::= { excelHMDTEntry 3 }

excelHMDTEventID OBJECT-TYPE
	SYNTAX INTEGER ( 0..99 )
	MAX-ACCESS read-create
	STATUS current
	DESCRIPTION
        "Id of the event that has occurred."
	::= { excelHMDTEntry 4 }

excelHMDTTime OBJECT-TYPE
	SYNTAX DisplayString
	MAX-ACCESS read-create
	STATUS current
	DESCRIPTION
        "The time of the last occurance of this event."
	::= { excelHMDTEntry 5 }

excelHMDTCount OBJECT-TYPE
	SYNTAX INTEGER ( 0..32656 )
	MAX-ACCESS read-create
	STATUS current
	DESCRIPTION
        "The current number of times this event has occurred since system 
        startup"
	::= { excelHMDTEntry 6 }

excelHMDTStatus OBJECT-TYPE
	SYNTAX RowStatus
	MAX-ACCESS read-create
	STATUS current
	DESCRIPTION
        "The status of this program entry"
	::= { excelHMDTEntry 7 }

--
-- Statistics table for PPL Component MTP3 LSAC
--


excelLSACTable OBJECT-TYPE
	SYNTAX SEQUENCE OF ExcelLSACEntry 
	MAX-ACCESS not-accessible
	STATUS current
	DESCRIPTION
        "This table will contain information on the ppl LSAC events 
        receicved and the date and time of the last one received.  Only the 
        following event ID will be captured:
        
            2       Signaling Link Failure"

	::= { excelPPLComponentStatistics 7 }

excelLSACEntry OBJECT-TYPE
	SYNTAX ExcelLSACEntry 
	MAX-ACCESS not-accessible
	STATUS current
    DESCRIPTION 
          ""
    INDEX { excelLSACSpanID, excelLSACChannelID, excelLSACEventID }
    ::= { excelLSACTable 1 }

ExcelLSACEntry ::= SEQUENCE {
    excelLSACIndex        INTEGER,
    excelLSACSpanID       INTEGER,
    excelLSACChannelID    INTEGER,
    excelLSACEventID      INTEGER,
    excelLSACTime         DisplayString,
    excelLSACCount        INTEGER,
    excelLSACStatus       RowStatus
}

excelLSACIndex OBJECT-TYPE
	SYNTAX INTEGER (0..65535)
	MAX-ACCESS not-accessible
	STATUS current
	DESCRIPTION
	"Index into this table."
	::= { excelLSACEntry 1 }

excelLSACSpanID OBJECT-TYPE
	SYNTAX INTEGER ( 0..84 )
	MAX-ACCESS read-create
	STATUS current
	DESCRIPTION
	"The id of the span this event has occurred on."
	::= { excelLSACEntry 2 }

excelLSACChannelID OBJECT-TYPE
	SYNTAX INTEGER ( 0..16 )
	MAX-ACCESS read-create
	STATUS current
	DESCRIPTION
        "The id of the channel this event has occurred on."
	::= { excelLSACEntry 3 }

excelLSACEventID OBJECT-TYPE
	SYNTAX INTEGER ( 0..99 )
	MAX-ACCESS read-create
	STATUS current
	DESCRIPTION
        "Id of the event that has occurred."
	::= { excelLSACEntry 4 }

excelLSACTime OBJECT-TYPE
	SYNTAX DisplayString
	MAX-ACCESS read-create
	STATUS current
	DESCRIPTION
        "The time of the last occurance of this event."
	::= { excelLSACEntry 5 }

excelLSACCount OBJECT-TYPE
	SYNTAX INTEGER ( 0..32656 )
	MAX-ACCESS read-create
	STATUS current
	DESCRIPTION
        "The current number of times this event has occurred since system 
        startup"
	::= { excelLSACEntry 6 }

excelLSACStatus OBJECT-TYPE
	SYNTAX RowStatus
	MAX-ACCESS read-create
	STATUS current
	DESCRIPTION
        "The status of this program entry"
	::= { excelLSACEntry 7 }

--
-- Statistics table for PPL Component MTP3 TLAC
--


excelTLACTable OBJECT-TYPE
	SYNTAX SEQUENCE OF ExcelTLACEntry 
	MAX-ACCESS not-accessible
	STATUS current
	DESCRIPTION
        "This table will contain information on the ppl TLAC events 
        receicved and the date and time of the last one received.  Only the 
        following event ID will be captured:
        
            0       Remote processor outage
            2       Local Inhibit
            4       Remote Inhibit"

	::= { excelPPLComponentStatistics 8 }

excelTLACEntry OBJECT-TYPE
	SYNTAX ExcelTLACEntry 
	MAX-ACCESS not-accessible
	STATUS current
    DESCRIPTION 
          ""
    INDEX { excelTLACSpanID, excelTLACChannelID, excelTLACEventID }
    ::= { excelTLACTable 1 }

ExcelTLACEntry ::= SEQUENCE {
    excelTLACIndex        INTEGER,
    excelTLACSpanID       INTEGER,
    excelTLACChannelID    INTEGER,
    excelTLACEventID      INTEGER,
    excelTLACTime         DisplayString,
    excelTLACCount        INTEGER,
    excelTLACStatus       RowStatus
}

excelTLACIndex OBJECT-TYPE
	SYNTAX INTEGER (0..65535)
	MAX-ACCESS not-accessible
	STATUS current
	DESCRIPTION
	"Index into this table."
	::= { excelTLACEntry 1 }

excelTLACSpanID OBJECT-TYPE
	SYNTAX INTEGER ( 0..84 )
	MAX-ACCESS read-create
	STATUS current
	DESCRIPTION
	"The id of the span this event has occurred on."
	::= { excelTLACEntry 2 }

excelTLACChannelID OBJECT-TYPE
	SYNTAX INTEGER ( 0..16 )
	MAX-ACCESS read-create
	STATUS current
	DESCRIPTION
        "The id of the channel this event has occurred on."
	::= { excelTLACEntry 3 }

excelTLACEventID OBJECT-TYPE
	SYNTAX INTEGER ( 0..99 )
	MAX-ACCESS read-create
	STATUS current
	DESCRIPTION
        "Id of the event that has occurred."
	::= { excelTLACEntry 4 }

excelTLACTime OBJECT-TYPE
	SYNTAX DisplayString
	MAX-ACCESS read-create
	STATUS current
	DESCRIPTION
        "The time of the last occurance of this event."
	::= { excelTLACEntry 5 }

excelTLACCount OBJECT-TYPE
	SYNTAX INTEGER ( 0..32656 )
	MAX-ACCESS read-create
	STATUS current
	DESCRIPTION
        "The current number of times this event has occurred since system 
        startup"
	::= { excelTLACEntry 6 }

excelTLACStatus OBJECT-TYPE
	SYNTAX RowStatus
	MAX-ACCESS read-create
	STATUS current
	DESCRIPTION
        "The status of this program entry"
	::= { excelTLACEntry 7 }

--
-- Statistics table for PPL Component MTP3 TSFC
--


excelTSFCTable OBJECT-TYPE
	SYNTAX SEQUENCE OF ExcelTSFCEntry 
	MAX-ACCESS not-accessible
	STATUS current
	DESCRIPTION
        "This table will contain information on the ppl TSFC events 
        receicved and the date and time of the last one received.  Only the 
        following event ID will be captured:
        
            1       Destination Insaccessible"

	::= { excelPPLComponentStatistics 9 }

excelTSFCEntry OBJECT-TYPE
	SYNTAX ExcelTSFCEntry 
	MAX-ACCESS not-accessible
	STATUS current
    DESCRIPTION 
          ""
    INDEX { excelTSFCSpanID, excelTSFCChannelID, excelTSFCEventID }
    ::= { excelTSFCTable 1 }

ExcelTSFCEntry ::= SEQUENCE {
    excelTSFCIndex        INTEGER,
    excelTSFCSpanID       INTEGER,
    excelTSFCChannelID    INTEGER,
    excelTSFCEventID      INTEGER,
    excelTSFCTime         DisplayString,
    excelTSFCCount        INTEGER,
    excelTSFCStatus       RowStatus
}

excelTSFCIndex OBJECT-TYPE
	SYNTAX INTEGER (0..65535)
	MAX-ACCESS not-accessible
	STATUS current
	DESCRIPTION
	"Index into this table."
	::= { excelTSFCEntry 1 }

excelTSFCSpanID OBJECT-TYPE
	SYNTAX INTEGER ( 0..84 )
	MAX-ACCESS read-create
	STATUS current
	DESCRIPTION
	"The id of the span this event has occurred on."
	::= { excelTSFCEntry 2 }

excelTSFCChannelID OBJECT-TYPE
	SYNTAX INTEGER ( 0..16 )
	MAX-ACCESS read-create
	STATUS current
	DESCRIPTION
        "The id of the channel this event has occurred on."
	::= { excelTSFCEntry 3 }

excelTSFCEventID OBJECT-TYPE
	SYNTAX INTEGER ( 0..99 )
	MAX-ACCESS read-create
	STATUS current
	DESCRIPTION
        "Id of the event that has occurred."
	::= { excelTSFCEntry 4 }

excelTSFCTime OBJECT-TYPE
	SYNTAX DisplayString
	MAX-ACCESS read-create
	STATUS current
	DESCRIPTION
        "The time of the last occurance of this event."
	::= { excelTSFCEntry 5 }

excelTSFCCount OBJECT-TYPE
	SYNTAX INTEGER ( 0..32656 )
	MAX-ACCESS read-create
	STATUS current
	DESCRIPTION
        "The current number of times this event has occurred since system 
        startup"
	::= { excelTSFCEntry 6 }

excelTSFCStatus OBJECT-TYPE
	SYNTAX RowStatus
	MAX-ACCESS read-create
	STATUS current
	DESCRIPTION
        "The status of this program entry"
	::= { excelTSFCEntry 7 }

--
-- Statistics table for PPL Component CRO
--


excelCROTable OBJECT-TYPE
	SYNTAX SEQUENCE OF ExcelCROEntry 
	MAX-ACCESS not-accessible
	STATUS current
	DESCRIPTION
        "This table will contain information on the ppl CRO events 
        receicved and the date and time of the last one received.  Only the 
        following event ID will be captured:
        
            4       Continuity recheck attepmt failure"

	::= { excelPPLComponentStatistics 10 }

excelCROEntry OBJECT-TYPE
	SYNTAX ExcelCROEntry 
	MAX-ACCESS not-accessible
	STATUS current
    DESCRIPTION 
          ""
    INDEX { excelCROSpanID, excelCROChannelID, excelCROEventID }
    ::= { excelCROTable 1 }

ExcelCROEntry ::= SEQUENCE {
    excelCROIndex        INTEGER,
    excelCROSpanID       INTEGER,
    excelCROChannelID    INTEGER,
    excelCROEventID      INTEGER,
    excelCROTime         DisplayString,
    excelCROCount        INTEGER,
    excelCROStatus       RowStatus
}

excelCROIndex OBJECT-TYPE
	SYNTAX INTEGER (0..65535)
	MAX-ACCESS not-accessible
	STATUS current
	DESCRIPTION
	"Index into this table."
	::= { excelCROEntry 1 }

excelCROSpanID OBJECT-TYPE
	SYNTAX INTEGER ( 0..84 )
	MAX-ACCESS read-create
	STATUS current
	DESCRIPTION
	"The id of the span this event has occurred on."
	::= { excelCROEntry 2 }

excelCROChannelID OBJECT-TYPE
	SYNTAX INTEGER ( 0..16 )
	MAX-ACCESS read-create
	STATUS current
	DESCRIPTION
        "The id of the channel this event has occurred on."
	::= { excelCROEntry 3 }

excelCROEventID OBJECT-TYPE
	SYNTAX INTEGER ( 0..99 )
	MAX-ACCESS read-create
	STATUS current
	DESCRIPTION
        "Id of the event that has occurred."
	::= { excelCROEntry 4 }

excelCROTime OBJECT-TYPE
	SYNTAX DisplayString
	MAX-ACCESS read-create
	STATUS current
	DESCRIPTION
        "The time of the last occurance of this event."
	::= { excelCROEntry 5 }

excelCROCount OBJECT-TYPE
	SYNTAX INTEGER ( 0..32656 )
	MAX-ACCESS read-create
	STATUS current
	DESCRIPTION
        "The current number of times this event has occurred since system 
        startup"
	::= { excelCROEntry 6 }

excelCROStatus OBJECT-TYPE
	SYNTAX RowStatus
	MAX-ACCESS read-create
	STATUS current
	DESCRIPTION
        "The status of this program entry"
	::= { excelCROEntry 7 }


--
-- ISDN Protocol
--
-- The ISDN Group contains two groups, ISDN Configuration Group and ISDN 
-- Statistics Group
--
--
excelISDN  OBJECT IDENTIFIER ::= { excelCommunicationSoftware 6 }
-- ISDN Confiuration
excelISDNConfig              OBJECT IDENTIFIER ::= { excelISDN 1 }

--
-- The ISDN Configuration Group contains the ISDN D Channel Table
--
excelISDNConfigDChanTable OBJECT-TYPE
	SYNTAX SEQUENCE OF ExcelISDNConfigDChanEntry 
	MAX-ACCESS not-accessible
	STATUS current
	DESCRIPTION
	"This table contains a row for each D Channel that is assigned in the 
        node."
	::= { excelISDNConfig 1 }

excelISDNConfigDChanEntry OBJECT-TYPE
	SYNTAX ExcelISDNConfigDChanEntry 
	MAX-ACCESS not-accessible
	STATUS current
    DESCRIPTION 
          "Definition of the ExcelISDNConfigDChanEntry sequence"
    INDEX { excelISDNConfigDChanIndex, excelISDNConfigDChanSpanIndex }

    ::= { excelISDNConfigDChanTable 1 }

ExcelISDNConfigDChanEntry ::= SEQUENCE {
    excelISDNConfigDChanSpanIndex                INTEGER,
    excelISDNConfigDChanIndex                    INTEGER,
    excelISDNConfigDChanConnType                 INTEGER,
    excelISDNConfigDChanHDLCBitPol               INTEGER,
    excelISDNConfigDChanBChanSelect              INTEGER,
    excelISDNConfigDChanBChanEncTrans            INTEGER,
    excelISDNConfigDChanLocation                 INTEGER,
    excelISDNConfigDChanPhysicalMedium           INTEGER
    } 

excelISDNConfigDChanSpanIndex OBJECT-TYPE
	SYNTAX INTEGER (0..255 )
	MAX-ACCESS read-only
	STATUS current
	DESCRIPTION
	"The Logical Span ID of the span which contains the channel assigned 
		to the D Channel represented by this row. "
	::= { excelISDNConfigDChanEntry 1 }

excelISDNConfigDChanIndex OBJECT-TYPE
	SYNTAX INTEGER  (0..255 )
	MAX-ACCESS read-only
	STATUS current
	DESCRIPTION
	"The Channel ID of the channel assigned to the D Channel represented 
		by this row."
	::= { excelISDNConfigDChanEntry 2 }

excelISDNConfigDChanConnType OBJECT-TYPE
	SYNTAX INTEGER { 
        other(1),
        att4ESS(2),
        att5ESS(3),
        nortelDMS100(4),
        nortelDMS250(5),
        austel(6),
        jate(7),
        euroISDN(8),
        ukDpnss(9),
        ukDASS2(10),
        euro-ISDN(11),
        attISDNBri(12),
        att4ESS931PRI(13),
        att5ESS931PRI(14),
        nortelDMS100931PRI(15),
        nortelDMS250931PRI(16),
        euroIDSNNetwork(17)
		}               
	MAX-ACCESS read-only    
	STATUS current
	DESCRIPTION
	"The connection type of the D Channel represented by this row."
	::= { excelISDNConfigDChanEntry 3 }

excelISDNConfigDChanHDLCBitPol OBJECT-TYPE
	SYNTAX INTEGER { 
                normal(1),
                inverted(2)
	   }
	MAX-ACCESS read-only
	STATUS current
	DESCRIPTION
	"The HDLC Bit Polarity of the D Channel represented by this row."
	::= { excelISDNConfigDChanEntry 4 }

excelISDNConfigDChanBChanSelect OBJECT-TYPE
	SYNTAX INTEGER { 
        disabled(1),
        linearClockwise(2),
        linearCounterCwise(3),
        circularClockwise(4),
        circularCounterCwise(5)
	   }
	MAX-ACCESS read-only
	STATUS current
	DESCRIPTION
	"The B Channel Selection Mode associated with the D Channel that is
		represented by this row."
	::= { excelISDNConfigDChanEntry 5 }

excelISDNConfigDChanBChanEncTrans OBJECT-TYPE
	SYNTAX INTEGER { 
                channelNumber(1),
                slotMap(2)
	   }
	MAX-ACCESS read-only
	STATUS current
	DESCRIPTION
	"The B Channel Encoding for transmission associated with the D Channel
        that is reprsented by this row."
	::= { excelISDNConfigDChanEntry 6 }

excelISDNConfigDChanLocation OBJECT-TYPE
	SYNTAX INTEGER { 
        other(1),
        user(2),
        privateLocal(3),
        publicLocal(4),
        transit(5),
        publicRemote(6),
        privateRemote(7),
        international(8),
        beyondInternetworking(9)
	   }
	MAX-ACCESS read-only
	STATUS current
	DESCRIPTION
		"The location of the D Channel represented by this row."
	::= { excelISDNConfigDChanEntry 7 }

excelISDNConfigDChanPhysicalMedium OBJECT-TYPE
	SYNTAX INTEGER { 
                other(1),
                kbps64(2)
	   }
	MAX-ACCESS read-only
	STATUS current
	DESCRIPTION
		"The physical medium of the D channel.  Typically a 64kbps 
                T1/E1/J1 line."
	::= { excelISDNConfigDChanEntry 8 }
--
-- The ExcelMediaGateway Group
--

excelMediaGateway  OBJECT IDENTIFIER ::= { excelCommunicationSoftware 7 }

excelMGSystem  OBJECT IDENTIFIER ::= { excelMediaGateway 1 }

excelMGActiveProtocol OBJECT-TYPE
    SYNTAX INTEGER {
        other (1),
        ipdc (2),
        mgcp (3),
        ipst (4)
    }
    MAX-ACCESS read-only
    STATUS current
    DESCRIPTION
            "The current active protocol executing on the matrix."

    ::={ excelMGSystem 1 }

excelMGSystemName OBJECT-TYPE
    SYNTAX DisplayString 
    MAX-ACCESS read-only
    STATUS current
    DESCRIPTION
            "The name of the Media Gateway system.  The default name will the
            IP Address of the active matrix."

    ::={ excelMGSystem 2 }

excelMGNumSlots OBJECT-TYPE
    SYNTAX SlotsInNode
    MAX-ACCESS read-only
    STATUS current
    DESCRIPTION
            "The number of slots in th e chassis available for Media Gateway
            Hardware."

    ::={ excelMGSystem 3 }

excelMGVoip  OBJECT IDENTIFIER ::= { excelMediaGateway 2 }

excelVoipAddressTable OBJECT-TYPE
    SYNTAX SEQUENCE OF ExcelVoipAddressEntry
    MAX-ACCESS not-accessible
    STATUS current
    DESCRIPTION
        ""

    ::= { excelMGVoip 1 }

excelVoipAddressEntry OBJECT-TYPE
    SYNTAX ExcelVoipAddressEntry 
    MAX-ACCESS not-accessible
    STATUS current
    DESCRIPTION ""

    INDEX { excelVoipAddressIndex }
    ::= { excelVoipAddressTable 1 }

ExcelVoipAddressEntry ::= SEQUENCE {
    excelVoipAddressIndex INTEGER,
    excelVoipAddressEntityType INTEGER,
    excelVoipIpAddress IpAddress,
    excelVoipSubNetMask IpAddress,
    excelVoipIpGateway IpAddress,
    excelVoipResetIndicator INTEGER
    }

excelVoipAddressIndex OBJECT-TYPE
    SYNTAX INTEGER (0..16)
    MAX-ACCESS not-accessible
    STATUS current
    DESCRIPTION
        "This is the index into the excel VoIP address table ."
    ::= { excelVoipAddressEntry 1 }

excelVoipAddressEntityType OBJECT-TYPE
    SYNTAX INTEGER {
                        motherBoard (1),
                        dspModuleOne (2),
                        dspModuleTwo (3),
                        dspModuleThree (4),
                        dspModuleFour (5)
                        }
    MAX-ACCESS read-only
    STATUS current
    DESCRIPTION
        "This object describes the entity on the Vdac card being displayed."
    ::= { excelVoipAddressEntry 2 }

excelVoipIpAddress OBJECT-TYPE
    SYNTAX IpAddress
    MAX-ACCESS read-only
    STATUS current
    DESCRIPTION
        "This object displays the IP Address assigned to the current entity."
    ::= { excelVoipAddressEntry 3 }

excelVoipSubNetMask OBJECT-TYPE
    SYNTAX IpAddress
    MAX-ACCESS read-only
    STATUS current
    DESCRIPTION
        "This object displays the subnet mask assigned to the current entity."
    ::= { excelVoipAddressEntry 4 }

excelVoipIpGateway OBJECT-TYPE
    SYNTAX IpAddress
    MAX-ACCESS read-only
    STATUS current
    DESCRIPTION
        "This object displays the default IP Gateway Address assigned to the 
        current entity."
    ::= { excelVoipAddressEntry 5 }

excelVoipResetIndicator OBJECT-TYPE
    SYNTAX INTEGER {
              noResetNeeded(1),
              resetNeeded(2)
              }
    MAX-ACCESS read-only
    STATUS current
    DESCRIPTION
        "This object discribes if an object reset is needed."
    ::= { excelVoipAddressEntry 6 }

--
-- MIB Objects: Resource Attributes for a Media Gateway IP Address
--              Both the IP Address and the Slot Id (excelVoipSlotNumber) 
--              Need to be set in order to gather information.
--

excelMGResAttrIpAddress OBJECT-TYPE
    SYNTAX IpAddress
    MAX-ACCESS read-write
    STATUS current
    DESCRIPTION
        "This object displays the IP Address needed to get Resource Attribute
        information."
    ::= { excelMGVoip 2 }

excelMGResourceAttributeTable OBJECT-TYPE
    SYNTAX SEQUENCE OF ExcelMGResourceAttributeEntry
    MAX-ACCESS not-accessible
    STATUS current
    DESCRIPTION
        ""

    ::= { excelMGVoip 3 }

excelMGResourceAttributeEntry OBJECT-TYPE
    SYNTAX ExcelMGResourceAttributeEntry 
    MAX-ACCESS not-accessible
    STATUS current
    DESCRIPTION ""

    INDEX { excelMGResAttrIndex }
    ::= { excelMGResourceAttributeTable 1 }

ExcelMGResourceAttributeEntry ::= SEQUENCE {
     excelMGResAttrIndex INTEGER,
     excelMGPayloadType INTEGER,
     excelMGPayloadSize INTEGER,
     excelMGSilenceSupression INTEGER,
     excelMGEchoCancellation INTEGER,
     excelMGMinDelayValue INTEGER,
     excelMGMaxDelayValue INTEGER,   
     excelMGAdaptionRate INTEGER,
     excelMGFaxType INTEGER,
     excelMGModemEnableTransport INTEGER,
     excelMGBypassCoderType INTEGER,
     excelMGRtpPacketDepth PacketDepth,
     excelMGFaxPacketDepth PacketDepth,
     excelMGModemPacketDepth PacketDepth,
     excelMGTypeOfServicePrecedence INTEGER,
     excelMGTypeOServiceDelay INTEGER,
     excelMGTypeOfServiceThroughput INTEGER,
     excelMGTypeOfServiceReliability INTEGER,
     excelMGTypeOfServiceCost INTEGER,
     excelMGRtcpPortOffset INTEGER,
     excelMGT38PortOffset INTEGER
    }


excelMGResAttrIndex OBJECT-TYPE
    SYNTAX SlotsInNode
    MAX-ACCESS not-accessible
    STATUS current
    DESCRIPTION
        "Index into the excelMGResourceAttribute table."

    ::= { excelMGResourceAttributeEntry 1 }

excelMGPayloadType OBJECT-TYPE 
    SYNTAX PayloadTypes
    MAX-ACCESS read-only
    STATUS current
    DESCRIPTION
        ""

    ::= { excelMGResourceAttributeEntry 2 }


 excelMGPayloadSize OBJECT-TYPE
    SYNTAX INTEGER (1..1517)
    MAX-ACCESS read-only
    STATUS current
    DESCRIPTION
        "The basic packet rate of an RTP Packet that is sent out over Ethernet"

    ::= { excelMGResourceAttributeEntry 3 }                       

                        
excelMGSilenceSupression OBJECT-TYPE
    SYNTAX INTEGER{
                disabled (1),
                enabled (2)
                }
    MAX-ACCESS read-only
    STATUS current
    DESCRIPTION
        "This object indicates if silence supression has been enabled."

    ::= { excelMGResourceAttributeEntry 4}

excelMGEchoCancellation OBJECT-TYPE
    SYNTAX INTEGER {
                disabled (1),
                enabled (2)
                }
    MAX-ACCESS read-only
    STATUS current
    DESCRIPTION
        "This object determines if echo cancellation logic is enabled or not."

    ::= { excelMGResourceAttributeEntry 5 }


excelMGMinDelayValue OBJECT-TYPE
    SYNTAX INTEGER(0..150)
    MAX-ACCESS read-only
    STATUS current
    DESCRIPTION
        "Time in milliseconds of the minimum delay value."

    ::= { excelMGResourceAttributeEntry 6 }

excelMGMaxDelayValue OBJECT-TYPE
    SYNTAX INTEGER(0..150)
    MAX-ACCESS read-only
    STATUS current
    DESCRIPTION
        "Time in milliseconds of the maximum delay value."

    ::= { excelMGResourceAttributeEntry 7 }

excelMGAdaptionRate OBJECT-TYPE
    SYNTAX INTEGER(0..300)
    MAX-ACCESS read-only
    STATUS current
    DESCRIPTION
        "Time in milliseconds of the adaption rate"

    ::= { excelMGResourceAttributeEntry 8 }

excelMGFaxType OBJECT-TYPE
    SYNTAX INTEGER {
              disable(1),
              relay(2),
              bypass(3)
                        }
    MAX-ACCESS read-only
    STATUS current
    DESCRIPTION
        "The object returns the current Fax type."
    DEFVAL { 1 }

    ::= { excelMGResourceAttributeEntry 9 }

excelMGModemEnableTransport OBJECT-TYPE
    SYNTAX INTEGER {
              v22EnableBypassOnly (1),
              v22DisableBypassOnly (2),
              v23EnableBypassOnly (3),
              v23DisableBypassOnly (4),
              v32EnableBypass (5),
              v32DisableBypass (6),
              v32EnableRelay (7),
              v32DisableRelay (8),
              v34EnableBypass (9),
              v34DisableBypass (10),
              v34EnableRelayFallback (11),
              v34DisableRelay (12)
}
    MAX-ACCESS read-only
    STATUS current
    DESCRIPTION
        ""

    ::= { excelMGResourceAttributeEntry 10 }


excelMGBypassCoderType OBJECT-TYPE
    SYNTAX PayloadTypes
    MAX-ACCESS read-only
    STATUS current
    DESCRIPTION
        "The object returns the current bypass coder types."

    ::= { excelMGResourceAttributeEntry 11 }

excelMGRtpPacketDepth OBJECT-TYPE
    SYNTAX PacketDepth
    MAX-ACCESS read-only
    STATUS current
    DESCRIPTION
        "This object returns the redundancy packet depth for RTP."

    DEFVAL { 1 } 

    ::= { excelMGResourceAttributeEntry 12 }

excelMGFaxPacketDepth OBJECT-TYPE
   SYNTAX  PacketDepth
   MAX-ACCESS read-only
   STATUS current
   DESCRIPTION
       "This objects returns the current Fax redundancy packet depth."
   
   DEFVAL { 1 }

    ::= { excelMGResourceAttributeEntry 13 }

excelMGModemPacketDepth OBJECT-TYPE
    SYNTAX  PacketDepth
    MAX-ACCESS read-only
    STATUS  current
    DESCRIPTION
        "This object returns the current modem redundancy packet depth."

    DEFVAL { 1 }

    ::= { excelMGResourceAttributeEntry 14 }

excelMGTypeOfServicePrecedence OBJECT-TYPE
   SYNTAX INTEGER {
            routine (1),
            priority (2),
            immediate(3),
            flash(4),
            flashOverride(5),
            criticEcp(6),
            internetworkControl(7),
            networkControl(8)
            }
   MAX-ACCESS read-only
   STATUS  current
   DESCRIPTION
       ""

   DEFVAL { 1 } 

    ::= { excelMGResourceAttributeEntry 15 }

excelMGTypeOServiceDelay OBJECT-TYPE
   SYNTAX INTEGER {
            normalDelay(1),
            lowDelay(2)
            }
   MAX-ACCESS read-only
   STATUS  current
   DESCRIPTION
       ""

   DEFVAL { 1 } 

   ::= { excelMGResourceAttributeEntry 16 }

excelMGTypeOfServiceThroughput OBJECT-TYPE
   SYNTAX INTEGER {
            nomalThroughput(1),
            highThroughput(2)
   }
   MAX-ACCESS read-only
   STATUS  current
   DESCRIPTION
       ""

  DEFVAL { 1 } 

   ::= { excelMGResourceAttributeEntry 17 }

excelMGTypeOfServiceReliability  OBJECT-TYPE
   SYNTAX INTEGER {
            normalReliability(1),
            highReliability (2)
            }
   MAX-ACCESS read-only
   STATUS  current
   DESCRIPTION
       ""

  DEFVAL { 1 } 

   ::= { excelMGResourceAttributeEntry 18 }

excelMGTypeOfServiceCost  OBJECT-TYPE
   SYNTAX INTEGER {
            normalCost(1),
            lowCost(2)
            }
   MAX-ACCESS read-only
   STATUS  current
   DESCRIPTION
       ""

  DEFVAL { 1 } 

   ::= { excelMGResourceAttributeEntry 19 }

excelMGRtcpPortOffset OBJECT-TYPE
   SYNTAX INTEGER (2048..10000)
    MAX-ACCESS read-only
    STATUS  current
    DESCRIPTION
        "This object returns the current modem redundancy packet depth."

    ::= { excelMGResourceAttributeEntry 20 }

excelMGT38PortOffset OBJECT-TYPE
   SYNTAX INTEGER (2048..10000)
    MAX-ACCESS read-only
    STATUS  current
    DESCRIPTION
        "This object returns the current modem redundancy packet depth."

    ::= { excelMGResourceAttributeEntry 21 }

--
-- IPDC and MGCP configuration parameters
--
-- excelMGConfig contains objects that are supported by both the 
-- ipdc and mgcp protocols.
--
--  excelMGConfigIpdc contains objects that apply only to the IPDC protocol
--
--  excelMGConfigMgcp contains objects that apply only to the MGCP protocol
--


excelMGConfig        OBJECT IDENTIFIER ::= { excelMediaGateway 3 }

excelMGConfigPrimaryMGCAddress OBJECT-TYPE
    SYNTAX IpAddress
    MAX-ACCESS read-only
    STATUS current 
    DESCRIPTION
        "IP Address of the primary softswitch (call agent)"

    ::= { excelMGConfig 1 }

excelMGConfigPrimaryPort OBJECT-TYPE
    SYNTAX INTEGER (1025..32565)
    MAX-ACCESS read-only
    STATUS current
    DESCRIPTION
        "The port number used when connection to the primary softswitch call 
        agent"

    ::= { excelMGConfig 2 } 

excelMGConfigSecondaryMGCAddress OBJECT-TYPE
    SYNTAX IpAddress
    MAX-ACCESS read-only
    STATUS current 
    DESCRIPTION
        "IP Address of the secondary softswitch (call agent)"

    ::= { excelMGConfig 3 }

excelMGConfigSecondaryPort OBJECT-TYPE
    SYNTAX INTEGER (1025..32565)
    MAX-ACCESS read-only
    STATUS current
    DESCRIPTION
        "The port number used when connection to the secondary softswitch call 
        agent"

    ::= { excelMGConfig 4 }

excelMGConfigLocalPort OBJECT-TYPE
    SYNTAX INTEGER (1024..32565)
    MAX-ACCESS read-only
    STATUS current
    DESCRIPTION
        "Port number assigned to the local protocol task"

    ::= {excelMGConfig 5 }

excelMGConfigIpdc        OBJECT IDENTIFIER ::= { excelMediaGateway 4 }

excelMGConfigIpdcReconnectAttempts OBJECT-TYPE
    SYNTAX INTEGER (0..255)
    MAX-ACCESS read-only
    STATUS current
    DESCRIPTION
        "The number of time the local protocol task will attempt to connect
        to the currently active Call Agent"

    ::= {excelMGConfigIpdc 1 }

excelMGConfigMgcp        OBJECT IDENTIFIER ::= { excelMediaGateway 5 }

excelConfigMgcpPriTransmitInterval OBJECT-TYPE
    SYNTAX INTEGER (0..255)
    MAX-ACCESS read-only
    STATUS current
    DESCRIPTION
        "Count used when switching over to a secondary call agent from a 
        primary call agent"

    ::= { excelMGConfigMgcp 1 }

excelConfigMgcpSecTransmitInterval OBJECT-TYPE
    SYNTAX INTEGER (0..255)
    MAX-ACCESS read-only
    STATUS current
    DESCRIPTION
        "Count used when switching over to a primary call agent from a
        secondary call agent"

    ::= { excelMGConfigMgcp 2 }

excelConfigMgcpResponseInterval OBJECT-TYPE
    SYNTAX INTEGER (1000..10000)
    MAX-ACCESS read-only
    STATUS current
    DESCRIPTION
        "This object specifies the time the gateway holds onto a message 
        response sent to the CA. This is for solicited messages sent from the 
        CA. If the time expires, then the gateway removes the response from 
        the response queue. If the CA sends another solicited message to the 
        gateway and the response is in the response queue, then the gateway 
        sends the response which is contained in the response queue. This
        essentially means that for every solicited message sent from the CA,
        the gateway looks in its response queue to see if it has a response 
        for that message."

    ::= { excelMGConfigMgcp 3 }

excelConfigMgcpRetransmissionTime OBJECT-TYPE
    SYNTAX INTEGER (1000..10000)
    MAX-ACCESS read-only
    STATUS current
    DESCRIPTION
        "When the gateway sends an unsolicited message to the CA, and if a 
        response is not received, this parameter specifies the time before 
        the gateway resends the message."

    ::= { excelMGConfigMgcp 4 }
--
-- The excelRing Group
--
-- The objects in this group track the activities of a Exnet Ring.
--
-- Note, that if this node is standalone, i.e. not a member of a Ring,
-- then these objects will be invalid. Also, a node may be a member of several 
-- rings, each represented by a ring card.

excelRing            OBJECT IDENTIFIER ::= { excelSystemSoftware 3 }


excelRingTable OBJECT-TYPE
    SYNTAX SEQUENCE OF ExcelRingEntry 
    MAX-ACCESS not-accessible
    STATUS current
    DESCRIPTION
        "It is possible for a node to be a member of numerous rings.  
        Therefore, each row of this table describes the characteristics
        of each ring of which this node is a member."
    ::= { excelRing 2 }

excelRingEntry OBJECT-TYPE
    SYNTAX ExcelRingEntry 
    MAX-ACCESS not-accessible
    STATUS current
    DESCRIPTION 
        "Definition of the ExcelRingEntry sequence"

    INDEX { excelRingLogicalIDIndex }
    ::= { excelRingTable 1 }

ExcelRingEntry ::= SEQUENCE {
    excelRingLogicalIDIndex      INTEGER,
    excelRingStatus              INTEGER,
    excelRingOOSReason           INTEGER,
    excelRingTransmitMode        INTEGER,
    excelRingNodeRole	         INTEGER,
    excelRingCtrlSlot            SlotsInNode,
    excelRingPortAStatus         INTEGER,
    excelRingPortBStatus         INTEGER,
    excelRingSourcePacketID      INTEGER 
    }

excelRingLogicalIDIndex OBJECT-TYPE
    SYNTAX INTEGER ( 0..8 ) 
    MAX-ACCESS not-accessible
    STATUS current
    DESCRIPTION
        "The logical ID of the ring being described by this row."
    ::= { excelRingEntry 1 }

excelRingStatus OBJECT-TYPE
    SYNTAX INTEGER {
        other(1),
        inService(2),
        ringInitializing(3),
        connected(4),
        outOfService(5)
        }
    MAX-ACCESS read-only
    STATUS current
    DESCRIPTION
        "This object represents the status of the proprietary fiber network
        that connects the nodes of an EXS. If this object equals 
        outOfService(5), then excelRingOOSReason will contain
        the reason that this ring is considered out of service."
    ::= { excelRingEntry 2}

excelRingOOSReason OBJECT-TYPE
    SYNTAX INTEGER {
        other (1),
        cardReset(2),
        cardInFailedState(3),
        cardResetFailure(4),
        cardResetTimeout(5),
	cardTimeout(6),
        cardIsolatedFromRing(7),
        ringInternalOOS (8),
        ringNotReceivingLight(9),
        ringOOS(10)
        } 
    MAX-ACCESS read-only
    STATUS current
    DESCRIPTION
        "If the node has been declared out of service on this ring, and
        excelRingStatus equals outOfService(5), then this object will
        equal any value other than none(1)."
    ::= { excelRingEntry 3}


excelRingTransmitMode OBJECT-TYPE
    SYNTAX INTEGER {
        receiveOnly(1),
        transmitReceive(2),
		other(3)
        } 
    MAX-ACCESS read-only
    STATUS current
    DESCRIPTION
	"The transmit mode of this node as it relates to this ring"
    ::= { excelRingEntry 4}

excelRingNodeRole OBJECT-TYPE
    SYNTAX INTEGER {
        slave(1),
        master(2),
	other(3)
        } 
    MAX-ACCESS read-only
    STATUS current
    DESCRIPTION
	"The role that this node palys in this ring"
    ::= { excelRingEntry 5}

excelRingCtrlSlot OBJECT-TYPE
    SYNTAX SlotsInNode 
    MAX-ACCESS read-only
    STATUS current
    DESCRIPTION
        "The slot in which the EXNET I/O controller resides for this node."
    ::= { excelRingEntry 6 }

excelRingPortAStatus OBJECT-TYPE
    SYNTAX INTEGER { 
        other(1),
        normal(2),
        loopBack(3)
        }
    MAX-ACCESS read-only
    STATUS current
    DESCRIPTION
        "The status of port A on the EXNET I/O controller card for this
        node on this ring."
    ::= { excelRingEntry 7 }

excelRingPortBStatus OBJECT-TYPE
    SYNTAX INTEGER { 
        other(1),
        normal(2),
        loopBack(3)
        }
    MAX-ACCESS read-only
    STATUS current
    DESCRIPTION
        "The status of port B on the EXNET I/O controller card for this
        node on this ring."
    ::= { excelRingEntry 8 }


excelRingSourcePacketID OBJECT-TYPE
    SYNTAX INTEGER (0..29)
    MAX-ACCESS read-only
    STATUS current
    DESCRIPTION
        "The lowest packet ID assigned to this node for this ring."
    ::= { excelRingEntry 9 }

excelRingNodeStatus            OBJECT IDENTIFIER ::= { excelSystemSoftware 4 }

ringID OBJECT-TYPE
    SYNTAX  INTEGER (0..255)
    MAX-ACCESS  read-only
    STATUS  current
    DESCRIPTION
        "The id of this ring"
    DEFVAL { 255 }
    ::= { excelRingNodeStatus 1 }

ringStatusTable OBJECT-TYPE
    SYNTAX  SEQUENCE OF RingStatusTableEntry
    MAX-ACCESS  not-accessible
    STATUS  current
    DESCRIPTION
        "This table describes the phyysical and logical contents of the 
	selected ring."
    ::= { excelRingNodeStatus 2 }

ringStatusTableEntry OBJECT-TYPE
    SYNTAX  RingStatusTableEntry
    MAX-ACCESS  not-accessible
    STATUS  current
    DESCRIPTION
        ""
    INDEX   { ringStatusIndex }
    ::= {ringStatusTable 1 }

RingStatusTableEntry ::= SEQUENCE {
       ringStatusIndex INTEGER,
       ringStatusTransmitting INTEGER,
       ringStatusIpAddress IpAddress,
       ringStatusLogicalId INTEGER,
       ringStatusPhysicalId INTEGER,
       ringStatusLoadMajorRev INTEGER,
       ringStatusLoadMinorRev INTEGER,
       ringStatusLoadBuildNum INTEGER
}

ringStatusIndex OBJECT-TYPE
    SYNTAX  INTEGER (0..255)
    MAX-ACCESS  not-accessible
    STATUS  current
    DESCRIPTION
        "Index into the ring status entry table"
    ::= {ringStatusTableEntry 1 }

ringStatusTransmitting OBJECT-TYPE
    SYNTAX  INTEGER { 
                receiveOnly(1),
                receiveAndTransmit(2)
                }
    MAX-ACCESS  read-only
    STATUS  current
    DESCRIPTION
        "Is this node currently transmitting on a ring."
    DEFVAL { 2 }
    ::= { ringStatusTableEntry 2 }

ringStatusIpAddress OBJECT-TYPE
    SYNTAX  IpAddress
    MAX-ACCESS  read-only
    STATUS  current
    DESCRIPTION
        "The IP address of this object on the ring"
    ::= { ringStatusTableEntry 3 }

ringStatusLogicalId OBJECT-TYPE
    SYNTAX  INTEGER (0..32655)
    MAX-ACCESS  read-only
    STATUS  current
    DESCRIPTION
        "The logical ID of this node on the ring"
    DEFVAL { 255 }
    ::= { ringStatusTableEntry 4 }

ringStatusPhysicalId OBJECT-TYPE
    SYNTAX  INTEGER (0..32655)
    MAX-ACCESS  read-only
    STATUS  current
    DESCRIPTION
        "The physical Id on this node on the ring."
    DEFVAL { 255 }
    ::= { ringStatusTableEntry 5 }

ringStatusLoadMajorRev OBJECT-TYPE
    SYNTAX  INTEGER  (0..255)
    MAX-ACCESS  read-only
    STATUS  current
    DESCRIPTION
        "The major revision number of the current build"

    ::= { ringStatusTableEntry 6 }

ringStatusLoadMinorRev OBJECT-TYPE
    SYNTAX  INTEGER  (0..255)
    MAX-ACCESS  read-only
    STATUS  current
    DESCRIPTION
        "The minor revision number of the current build"

    ::= { ringStatusTableEntry 7 }

ringStatusLoadBuildNum OBJECT-TYPE
    SYNTAX  INTEGER  (0..255)
    MAX-ACCESS  read-only
    STATUS  current
    DESCRIPTION
        "The number of the current build"

    ::= { ringStatusTableEntry 8 }



--
-- The Excel OAM&P Group (OAM&P Software)
--
excelOAMP                      OBJECT IDENTIFIER ::= { excelProducts 3 }

excelEXSAgentVerbose OBJECT-TYPE
    SYNTAX  INTEGER {
                on(1),
                off(2)
                }
    MAX-ACCESS  read-write
    STATUS      current
    DESCRIPTION
        "This variable will allow debugging messages to be turned off and on 
        dynamically for the EXSAgent process"
    DEFVAL {2}
    
    ::= { excelOAMP 1 }

excelEXSEventManagerVerbose OBJECT-TYPE
    SYNTAX  INTEGER {
                on(1),
                off(2)
                }
    MAX-ACCESS  read-write
    STATUS      current
    DESCRIPTION
        "Ths object allows the end users to turn debugging information on 
        dynamically for process EXSEventManager."
    DEFVAL {2}
    
    ::= { excelOAMP 2 }
--
-- WinNT Extension Group
--
-- The WinNT 4.0 Extendible SNMP Agent does not support the SNMP group
-- of MIB-II.  The following group is an attempt to support some of the
-- objects in the MIB-II SNMP group.
--

excelExtension               OBJECT IDENTIFIER ::= { excelProducts 4 }


END
