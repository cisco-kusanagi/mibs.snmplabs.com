SWITCH-INFO-MIB
DEFINITIONS ::= BEGIN
IMPORTS
    MODULE-IDENTITY,
    OBJECT-TYPE			FROM SNMPv2-SMI
    DisplayString		FROM SNMPv2-TC
    switchVendor			FROM TELESYN-ATI-TC;
 
switchVendorMib MODULE-IDENTITY
    LAST-UPDATED "9611052200Z"
	ORGANIZATION ""
	CONTACT-INFO ""
	DESCRIPTION  
            "The MIB module identifies objects containing vendor information."
    REVISION "9705162200Z"
    DESCRIPTION
            "changed the max size of the vendorCopyright to 80 from 64."
    REVISION "9611052200Z"
    DESCRIPTION
            "Initial version."
   ::= { switchVendor 1 }
    
vendorInfo       	OBJECT IDENTIFIER ::= { switchVendorMib  1 }
vendorName	OBJECT-TYPE
	SYNTAX  DisplayString (SIZE (0..64))
	MAX-ACCESS    read-only
	STATUS    current
	DESCRIPTION
	    "The vendor company name"
	::= { vendorInfo 1 }
vendorProductName	OBJECT-TYPE
	SYNTAX  DisplayString (SIZE (0..64))
	MAX-ACCESS    read-only
	STATUS    current
	DESCRIPTION
	    "The product name assigned by the vendor Company"
	::= { vendorInfo 2 }
vendorModelName	OBJECT-TYPE
	SYNTAX  DisplayString (SIZE (0..64))
	MAX-ACCESS    read-only
	STATUS    current
	DESCRIPTION
	    "The model name or number assigned by the vendor Company"
	::= { vendorInfo 3 }
	
vendorModelId	OBJECT-TYPE
	SYNTAX  DisplayString (SIZE (0..64))
	MAX-ACCESS    read-only
	STATUS    current
	DESCRIPTION
	    "The model identifier assigend by the vendor Company"
	::= { vendorInfo 4 }
vendorCopyright	OBJECT-TYPE
	SYNTAX  DisplayString (SIZE (0..80))
	MAX-ACCESS    read-only
	STATUS    current
	DESCRIPTION
	    "The copyright string for the product."
	::= { vendorInfo 5 }
END
