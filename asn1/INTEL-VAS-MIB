INTEL-VAS-MIB DEFINITIONS ::= BEGIN

-- Copyright (C) 2000 Intel Corporation. All rights reserved.
--
-- VAS SNMP MIB, 2000-02-07
--
-- Proprietary MIB containing information VAS licensing System.
--
-- Change History:
-- 2000-02-07 Initial version
--
--
--

IMPORTS
    mib2ext			FROM INTEL-GEN-MIB
    OBJECT-TYPE                 FROM RFC-1212
    DisplayString		FROM RFC1213-MIB;


  vas               OBJECT IDENTIFIER ::= { mib2ext 53 }
  vasConfig         OBJECT IDENTIFIER ::= { vas 1 }

vasConfigTable OBJECT-TYPE
    SYNTAX SEQUENCE OF VasConfigEntry
    ACCESS not-accessible
    STATUS mandatory
    DESCRIPTION "VAS record"
    ::= { vasConfig 1 }

vasConfigEntry OBJECT-TYPE
    SYNTAX VasConfigEntry
    ACCESS not-accessible
    STATUS mandatory
    DESCRIPTION ""
    INDEX { vasConfigIndex }
    ::= { vasConfigTable 1 }

VasConfigEntry ::= SEQUENCE {
                        vasConfigIndex
                           INTEGER,
                        vasConfigStatus
                           INTEGER,
                        vasConfigLicenseKey
                           DisplayString,
                        vasConfigNameOfLicense
                           DisplayString,
                        vasConfigEraseLicense
                           INTEGER,
                        vasConfigDemoLicenseKey
                           INTEGER,
                        vasConfigNameOfUser
                           DisplayString,
                        vasConfigDateOfIssue
                           DisplayString
                        }

vasConfigIndex OBJECT-TYPE
    SYNTAX INTEGER
    ACCESS read-only
    STATUS mandatory
    DESCRIPTION "This is an index of the feature"
    ::= { vasConfigEntry 1 }

vasConfigStatus OBJECT-TYPE
    SYNTAX INTEGER
    ACCESS read-only
    STATUS mandatory
    DESCRIPTION "Holds status of feature. ZERO for OFF, NON-ZERO for On"
    ::= { vasConfigEntry 2 }

vasConfigLicenseKey OBJECT-TYPE
    SYNTAX DisplayString (SIZE (0..127))
    ACCESS read-write
    STATUS mandatory
    DESCRIPTION "This is the raw ascii license key, C-string"
    ::= { vasConfigEntry 3 }

vasConfigNameOfLicense OBJECT-TYPE
    SYNTAX DisplayString (SIZE (0..127))
    ACCESS read-only
    STATUS mandatory
    DESCRIPTION "Name of the actual license, ex OSPF, C-string"
    ::= { vasConfigEntry 4 }

vasConfigEraseLicense OBJECT-TYPE
    SYNTAX INTEGER
    ACCESS read-write
    STATUS mandatory
    DESCRIPTION "Write clears the license key. Read returns granularity of license"
    ::= { vasConfigEntry 5 }

vasConfigDemoLicenseKey OBJECT-TYPE
    SYNTAX INTEGER
    ACCESS read-only
    STATUS mandatory
    DESCRIPTION "Number of hours for this license key to operate, ZERO means no limit"
    ::= { vasConfigEntry 6 }

vasConfigNameOfUser OBJECT-TYPE
    SYNTAX DisplayString (SIZE (0..127))
    ACCESS read-write
    STATUS mandatory
    DESCRIPTION "Name of user, C-string"
    ::= { vasConfigEntry 7 }

vasConfigDateOfIssue OBJECT-TYPE
    SYNTAX DisplayString (SIZE (0..19))
    ACCESS read-only
    STATUS mandatory
    DESCRIPTION "Date of issue as:  YYYY-MM-DD, C-string"
    ::= { vasConfigEntry 8 }

END
