Wellfleet-MPLS-MLM-MIB DEFINITIONS ::= BEGIN

IMPORTS
  TimeTicks, Counter
    FROM RFC1155-SMI
  OBJECT-TYPE
    FROM RFC-1212
  wfMplsAtmGroup
    FROM Wellfleet-COMMON-MIB;



wfMplsAtm OBJECT IDENTIFIER ::= { wfMplsAtmGroup 1 }



wfMplsAtmIfConfTable OBJECT-TYPE
    SYNTAX SEQUENCE OF WfMplsAtmIfConfEntry
    ACCESS not-accessible
    STATUS mandatory
    DESCRIPTION
        "MPLS ATM interface configuration table -
         This tabulates the ATM interfaces within an mpls protocol group.
         All interfaces are indexed according to their line number.
         There is one ATM interface per MPLS LDP session, but there might
         be more LDP sessions per ATM interface."
    ::= { wfMplsAtm 1 }

wfMplsAtmIfConfEntry OBJECT-TYPE
    SYNTAX WfMplsAtmIfConfEntry
    ACCESS not-accessible
    STATUS mandatory
    DESCRIPTION
        "MPLS ATM interface configuration entries."
    INDEX { wfMplsAtmIfConfLineNumber }
    ::= { wfMplsAtmIfConfTable 1 }

WfMplsAtmIfConfEntry ::= SEQUENCE {
    wfMplsAtmIfCreate
            INTEGER,
    wfMplsAtmIfAdminStatus
            INTEGER,
    wfMplsAtmIfConfLineNumber
            INTEGER,
    wfMplsAtmIfDebugLogMask
            INTEGER
}

wfMplsAtmIfCreate OBJECT-TYPE
    SYNTAX  INTEGER {
        created(1),
        deleted(2)
    }
    ACCESS read-write
    STATUS mandatory
    DESCRIPTION
        "Create/Delete parameter. Default is created. Users modify
         this object in order to create/delete MPLS ATM interfaces"
    DEFVAL { created }
    ::= { wfMplsAtmIfConfEntry 1 }

wfMplsAtmIfAdminStatus OBJECT-TYPE
    SYNTAX INTEGER {
        enabled(1),
        disabled(2)
    }
    ACCESS read-write
    STATUS mandatory
    DESCRIPTION
        "Enable/Disable parameter. Default is enabled."
    DEFVAL  { enabled }
    ::= { wfMplsAtmIfConfEntry 2 }

wfMplsAtmIfConfLineNumber OBJECT-TYPE
    SYNTAX INTEGER
    ACCESS read-only
    STATUS mandatory
    DESCRIPTION
        "The line number of the driver line to which the interface belongs."
    ::= { wfMplsAtmIfConfEntry 3 }

wfMplsAtmIfDebugLogMask OBJECT-TYPE
    SYNTAX INTEGER {
	none(1),
	fsm(16),
        other(128),
        all(255)
    }
    ACCESS read-write
    STATUS mandatory
    DESCRIPTION
        "Log bits for debug messages. This values above can be used 
         separately, or OR'd together for a combination of debug levels."
    DEFVAL { none }
    ::= { wfMplsAtmIfConfEntry 4 }



wfMplsAtmIfStatusTable OBJECT-TYPE
    SYNTAX SEQUENCE OF WfMplsAtmIfStatusEntry
    ACCESS not-accessible
    STATUS mandatory
    DESCRIPTION
        "MPLS ATM interface status table -
         This tabulates the ATM interfaces within an mpls protocol group.
         All interfaces are indexed according to their line number.
         There is one ATM interface per MPLS LDP session, but there might
         be multiple LDP sessions per ATM interface."
    ::= { wfMplsAtm 2 }

wfMplsAtmIfStatusEntry OBJECT-TYPE
    SYNTAX WfMplsAtmIfStatusEntry
    ACCESS not-accessible
    STATUS mandatory
    DESCRIPTION
        "MPLS ATM interface status entries."
    INDEX { wfMplsAtmIfStatusLineNumber }
    ::= { wfMplsAtmIfStatusTable 1 }

WfMplsAtmIfStatusEntry ::= SEQUENCE {
    wfMplsAtmIfOperStatus
            INTEGER,
    wfMplsAtmIfStatusLineNumber
            INTEGER,
    wfMplsAtmIfCircuit
            INTEGER,
    wfMplsAtmIfTotalSess
            Counter,
    wfMplsAtmIfTotalVcs
            Counter,
    wfMplsAtmIfAllocVcs
            Counter  
}

wfMplsAtmIfOperStatus OBJECT-TYPE
    SYNTAX INTEGER {
        down(1),
        init(2),
	up(3),
	cleanup(4),
        notpresent(5)
    }
    ACCESS read-only
    STATUS mandatory
    DESCRIPTION
        "The current state of the MPLS ATM interface"
    DEFVAL { notpresent }
    ::= { wfMplsAtmIfStatusEntry 1 }

wfMplsAtmIfStatusLineNumber OBJECT-TYPE
    SYNTAX INTEGER
    ACCESS read-only
    STATUS mandatory
    DESCRIPTION
        "The line number of the driver line to which the interface belongs."
    ::= { wfMplsAtmIfStatusEntry 2 }

wfMplsAtmIfCircuit OBJECT-TYPE
    SYNTAX INTEGER (1..1023)
    ACCESS read-only
    STATUS mandatory
    DESCRIPTION
        "The circuit number of the circuit to which the interface belongs."
    ::= { wfMplsAtmIfStatusEntry 3 }

wfMplsAtmIfTotalSess OBJECT-TYPE
    SYNTAX Counter
    ACCESS read-only
    STATUS mandatory
    DESCRIPTION
        "The total number of LDPs up running."
    ::= { wfMplsAtmIfStatusEntry 4 }

wfMplsAtmIfTotalVcs OBJECT-TYPE
    SYNTAX Counter
    ACCESS read-only
    STATUS mandatory
    DESCRIPTION
        "The total number of VCs either in use, or available 
         on this interface."
    ::= { wfMplsAtmIfStatusEntry 5 }

wfMplsAtmIfAllocVcs OBJECT-TYPE
    SYNTAX Counter
    ACCESS read-only
    STATUS mandatory
    DESCRIPTION
        "The number of VCs which are currently allocated for different 
         LDP sessions on this interface. wfMplsAtmTotalVcs minus the value 
         of this object results in knowning how many VCs are still available
         to allocate to new LDP sessions on this interface."
    ::= { wfMplsAtmIfStatusEntry 6 }



wfMplsAtmSessConfTable OBJECT-TYPE
    SYNTAX  SEQUENCE OF WfMplsAtmSessConfEntry
    ACCESS  not-accessible
    STATUS  mandatory
    DESCRIPTION
        "This is the ATM related configuration table for every LDP session."
    ::= { wfMplsAtm 3 }

wfMplsAtmSessConfEntry OBJECT-TYPE
    SYNTAX  WfMplsAtmSessConfEntry
    ACCESS  not-accessible
    STATUS  mandatory
    DESCRIPTION
        "Entry definition."
    INDEX   { wfMplsAtmSessConfLineNumber,
              wfMplsAtmSessConfIndex }
    ::= { wfMplsAtmSessConfTable 1 }

WfMplsAtmSessConfEntry ::= SEQUENCE {
    wfMplsAtmSessDelete
        INTEGER,
    wfMplsAtmSessAdminStatus
        INTEGER,
    wfMplsAtmSessConfLineNumber
        INTEGER,
    wfMplsAtmSessConfIndex
        INTEGER,
    wfMplsAtmSessConfDefVclVpi
        INTEGER,
    wfMplsAtmSessConfDefVclVci
        INTEGER,
    wfMplsAtmSessConfVcRangeVpi
        INTEGER,
    wfMplsAtmSessConfVcRangeMinVci
        INTEGER,
    wfMplsAtmSessConfVcRangeMaxVci
        INTEGER,
    wfMplsAtmSessDefVclXmtPeakCellRate
        INTEGER,
    wfMplsAtmSessDefVclXmtSustainableCellRate
        INTEGER,
    wfMplsAtmSessDefVclXmtBurstSize
        INTEGER,
    wfMplsAtmSessDefVclXmtQosClass
        INTEGER,
    wfMplsAtmSessDefVclRcvPeakCellRate
        INTEGER,
    wfMplsAtmSessDefVclRcvSustainableCellRate
        INTEGER,
    wfMplsAtmSessDefVclRcvBurstSize
        INTEGER,
    wfMplsAtmSessDefVclRcvQosClass
        INTEGER,
    wfMplsAtmSessDefVclAalType
        INTEGER,
    wfMplsAtmSessDefVclAalCpcsTransmitSduSize
        INTEGER,
    wfMplsAtmSessDefVclAalCpcsReceiveSduSize
        INTEGER,
    wfMplsAtmSessDefVclAalEncapsType
        INTEGER,
    wfMplsAtmSessDefVclCongestionIndication
        INTEGER,
    wfMplsAtmSessDefVclCellLossPriority
        INTEGER,
    wfMplsAtmSessDefVclXmtTagging
        INTEGER,
    wfMplsAtmSessDefVclRcvTagging
        INTEGER
}

wfMplsAtmSessDelete OBJECT-TYPE
    SYNTAX  INTEGER {
                create(1),
                delete(2)
            }
    ACCESS  read-write
    STATUS  mandatory
    DESCRIPTION
        "Create/delete MIB instance parameter."
    DEFVAL  { create }
    ::= { wfMplsAtmSessConfEntry 1 }

wfMplsAtmSessAdminStatus OBJECT-TYPE
    SYNTAX  INTEGER {
                enable(1),
                disable(2)
            }
    ACCESS  read-write
    STATUS  mandatory
    DESCRIPTION
        "Specifies the desired administrative state of the VCL. The up
         and down states indicate that the traffic flow is enabled and 
         disabled respectively for the VCL."
    DEFVAL  { enable }
    ::= { wfMplsAtmSessConfEntry 2 }

wfMplsAtmSessConfLineNumber OBJECT-TYPE
    SYNTAX  INTEGER
    ACCESS  read-only
    STATUS  mandatory
    DESCRIPTION
        "Uniquely identifies the interface (port) that contains the
         appropriate management information. We use line number here."
    ::= { wfMplsAtmSessConfEntry 3 }

wfMplsAtmSessConfIndex OBJECT-TYPE
    SYNTAX  INTEGER (1..65535)
    ACCESS  read-only
    STATUS  mandatory
    DESCRIPTION
        "LDP session index number."
    ::= { wfMplsAtmSessConfEntry 4 }

wfMplsAtmSessConfDefVclVpi OBJECT-TYPE
    SYNTAX  INTEGER (0..255)
    ACCESS  read-write
    STATUS  mandatory
    DESCRIPTION
        "The VPI value of the default VC."
    DEFVAL { 0 }
    ::= { wfMplsAtmSessConfEntry 5 }

wfMplsAtmSessConfDefVclVci OBJECT-TYPE
    SYNTAX  INTEGER (32..65535)
    ACCESS  read-write
    STATUS  mandatory
    DESCRIPTION
        "The VCI value of the default VC. It should not in the configured 
	 VC range for any LDP session." 
    DEFVAL {32}
    ::= { wfMplsAtmSessConfEntry 6 }

wfMplsAtmSessConfVcRangeVpi OBJECT-TYPE
    SYNTAX  INTEGER (0..255)
    ACCESS  read-write
    STATUS  mandatory
    DESCRIPTION
        "The VPI value of the VCs in this LDP session."
    DEFVAL { 0 }
    ::= { wfMplsAtmSessConfEntry 7 }

wfMplsAtmSessConfVcRangeMinVci OBJECT-TYPE
    SYNTAX  INTEGER (32..65535)
    ACCESS  read-write
    STATUS  mandatory
    DESCRIPTION
        "The minimum VCI value of the configured LDP session."
    DEFVAL { 33 }
    ::= { wfMplsAtmSessConfEntry 8 }

wfMplsAtmSessConfVcRangeMaxVci OBJECT-TYPE
    SYNTAX  INTEGER (32..65535)
    ACCESS  read-write
    STATUS  mandatory
    DESCRIPTION
        "The maximum VCI value of the configured LDP session."
    DEFVAL { 65535 }
    ::= { wfMplsAtmSessConfEntry 9 }

wfMplsAtmSessDefVclXmtPeakCellRate OBJECT-TYPE
    SYNTAX  INTEGER 
    ACCESS  read-write
    STATUS  mandatory
    DESCRIPTION
        "Transmit (Forward) Peak Cell Rate in cells/second. This specifies
         the upper bound on the traffic that can be submitted on an ATM
         connection. 0 means best effort peak cell rate."
    DEFVAL  { 0 }
    ::= { wfMplsAtmSessConfEntry 10 }

wfMplsAtmSessDefVclXmtSustainableCellRate OBJECT-TYPE
    SYNTAX  INTEGER 
    ACCESS  read-write
    STATUS  mandatory
    DESCRIPTION
        "Transmit (Forward) Sustainable Cell Rate in cells/second. This
         specifies the upper bound on the conforming average rate of an 
         ATM connection, where 'average rate' is the number of cells 
         transmitted divided by the 'duration of the connection'. 0 means
         best effort sustainable cell rate."
    DEFVAL  { 0 }
    ::= { wfMplsAtmSessConfEntry 11 }

wfMplsAtmSessDefVclXmtBurstSize OBJECT-TYPE
    SYNTAX  INTEGER {
                default(40)
            }
    ACCESS  read-write
    STATUS  mandatory
    DESCRIPTION
        "Transmit (Forward) Burst Size in cells."
    DEFVAL  { default }
    ::= { wfMplsAtmSessConfEntry 12 }

wfMplsAtmSessDefVclXmtQosClass OBJECT-TYPE
    SYNTAX  INTEGER {
                class0(1),
                class1(2),
                class2(3),
                class3(4)
            }
    ACCESS  read-write
    STATUS  mandatory
    DESCRIPTION
        "Transmit (Forward) Quality of Service as specified in Appendix A,
         Section 4 of the ATM Forum UNI Specification, Version 3.0"
    DEFVAL  { class3 }
    ::= { wfMplsAtmSessConfEntry 13 }

wfMplsAtmSessDefVclRcvPeakCellRate OBJECT-TYPE
    SYNTAX  INTEGER 
    ACCESS  read-write
    STATUS  mandatory
    DESCRIPTION
        "Receive (Backward) Peak Cell Rate in cells/second. This specifies
         the upper bound on the traffic that can be submitted on an ATM
         connection. 0 means best effort peak cell rate."
    DEFVAL  { 0 }
    ::= { wfMplsAtmSessConfEntry 14 }

wfMplsAtmSessDefVclRcvSustainableCellRate OBJECT-TYPE
    SYNTAX  INTEGER 
    ACCESS  read-write
    STATUS  mandatory
    DESCRIPTION
        "Receive (Backward) Sustainable Cell Rate in cells/second. This 
         specifies the upper bound on the conforming average rate of an 
         ATM connection, where 'average rate' is the number of cells 
         transmitted divided by the 'duration of the connection'. 0 means
         best effort sustainable cell rate."
    DEFVAL  { 0 }
    ::= { wfMplsAtmSessConfEntry 15 }

wfMplsAtmSessDefVclRcvBurstSize OBJECT-TYPE
    SYNTAX  INTEGER {
                default(40)
            }
    ACCESS  read-write
    STATUS  mandatory
    DESCRIPTION
        "Receive (Backward) Burst Size in cells."
    DEFVAL  { default }
    ::= { wfMplsAtmSessConfEntry 16 }

wfMplsAtmSessDefVclRcvQosClass OBJECT-TYPE
    SYNTAX  INTEGER {
                class0(1),
                class1(2),
                class2(3),
                class3(4)
            }
    ACCESS  read-write
    STATUS  mandatory
    DESCRIPTION
        "Receive (Backward) Quality of Service as specified in Appendix A,
         Section 4 of the ATM Forum UNI Specification, Version 3.0"
    DEFVAL  { class3 }
    ::= { wfMplsAtmSessConfEntry 17 }

wfMplsAtmSessDefVclAalType OBJECT-TYPE
    SYNTAX  INTEGER {
                type1(1),
                type34(2),
                type5(3),
                other(4),
                unknown(5)
            }
    ACCESS  read-write
    STATUS  mandatory
    DESCRIPTION
        "The type of AAL used on the VCL."
    DEFVAL  { type5 }
    ::= { wfMplsAtmSessConfEntry 18 }

wfMplsAtmSessDefVclAalCpcsTransmitSduSize OBJECT-TYPE
    SYNTAX  INTEGER(1..65535)
    ACCESS  read-write
    STATUS  mandatory
    DESCRIPTION
        "The maximum AAL CPCS SDU size in octets that is supported on the
         transmit direction of this VCC."
    DEFVAL  { 4608 }
    ::= { wfMplsAtmSessConfEntry 19 }

wfMplsAtmSessDefVclAalCpcsReceiveSduSize OBJECT-TYPE
    SYNTAX  INTEGER(1..65535)
    ACCESS  read-write
    STATUS  mandatory
    DESCRIPTION
        "The maximum AAL CPCS SDU size in octets that is supported on the
         receive direction of this VCC."
    DEFVAL  { 4608 }
    ::= { wfMplsAtmSessConfEntry 20 }

wfMplsAtmSessDefVclAalEncapsType OBJECT-TYPE
    SYNTAX  INTEGER {
                unknown(1),
                llcencaps(2),
                null(3),
                other(4)
            }
    ACCESS  read-write 
    STATUS  mandatory
    DESCRIPTION
        "The type of data encapsulation used over both AAL3/4 and
         AAL5 SSCS layer. Currently, the only values supported are :
         ATM_VCLENCAPS_LLCENCAPS - RFC1483
         ATM_VCLENCAPS_ROUTEDPROTO - NONE"
    DEFVAL  { llcencaps }
    ::= { wfMplsAtmSessConfEntry 21 }

wfMplsAtmSessDefVclCongestionIndication OBJECT-TYPE
    SYNTAX  INTEGER {
                off(1),
                on(2)
            }
    ACCESS  read-write
    STATUS  mandatory
    DESCRIPTION    
        "The desired state of the Congestion Indication (CI) bit in the
         payload field of each ATM cell for this VCL."
    DEFVAL  { off }
    ::= { wfMplsAtmSessConfEntry 22 }

wfMplsAtmSessDefVclCellLossPriority OBJECT-TYPE
    SYNTAX  INTEGER {
                off(1),
                on(2)
            }
    ACCESS  read-write
    STATUS  mandatory
    DESCRIPTION
        "The desired state of the Cell Loss Priority (CLP) bit in the ATM
         header of each cell for this VCL."
    DEFVAL  { off }
    ::= { wfMplsAtmSessConfEntry 23 }

wfMplsAtmSessDefVclXmtTagging OBJECT-TYPE
    SYNTAX  INTEGER {
                on(1),
                off(2)
            }
    ACCESS  read-write
    STATUS  mandatory
    DESCRIPTION
        "Tagging forward VC messages if peak/sustainable rates exceeded"
    DEFVAL  { off }
    ::= { wfMplsAtmSessConfEntry 24 }

wfMplsAtmSessDefVclRcvTagging OBJECT-TYPE
    SYNTAX  INTEGER {
                on(1),
                off(2)
                }
    ACCESS  read-write
    STATUS  mandatory
    DESCRIPTION
        "Tagging backward VC messages if peak/sustainable rates exceeded"
    DEFVAL  { off }
    ::= { wfMplsAtmSessConfEntry 25 }



wfMplsAtmSessStatusTable OBJECT-TYPE
    SYNTAX  SEQUENCE OF WfMplsAtmSessStatusEntry
    ACCESS  not-accessible
    STATUS  mandatory
    DESCRIPTION
        "This is the ATM related status table for every LDP session."
    ::= { wfMplsAtm 4 }

wfMplsAtmSessStatusEntry OBJECT-TYPE
    SYNTAX  WfMplsAtmSessStatusEntry
    ACCESS  not-accessible
    STATUS  mandatory
    DESCRIPTION
        "Entry definition."
    INDEX   { wfMplsAtmSessStatusLineNumber,
              wfMplsAtmSessStatusIndex }
    ::= { wfMplsAtmSessStatusTable 1 }

WfMplsAtmSessStatusEntry ::= SEQUENCE {
    wfMplsAtmSessOperStatus
        INTEGER,
    wfMplsAtmSessStatusLineNumber
        INTEGER,
    wfMplsAtmSessStatusIndex
        INTEGER,
    wfMplsAtmSessActualVcRangeVpi
        INTEGER,
    wfMplsAtmSessActualVcRangeMinVci
        INTEGER,
    wfMplsAtmSessActualVcRangeMaxVci
        INTEGER,
    wfMplsAtmSessNegotiatedVcRangeVpi
        INTEGER,
    wfMplsAtmSessNegotiatedVcRangeMinVci
        INTEGER,
    wfMplsAtmSessNegotiatedVcRangeMaxVci
        INTEGER,
    wfMplsAtmSessInboundInuseVcs
        Counter,
    wfMplsAtmSessOutboundInuseVcs
        Counter
}

wfMplsAtmSessOperStatus OBJECT-TYPE
    SYNTAX  INTEGER {
                down(1),
	        init(2),
                up(3),
	        cleanup(4),
	        notpresent(5)
            }
    ACCESS  read-only
    STATUS  mandatory
    DESCRIPTION
        "The ATM related LDP session state."
    DEFVAL  { notpresent }
    ::= { wfMplsAtmSessStatusEntry 1 }

wfMplsAtmSessStatusLineNumber OBJECT-TYPE
    SYNTAX  INTEGER
    ACCESS  read-only
    STATUS  mandatory
    DESCRIPTION
        "Uniquely identifies the interface (port) that contains the
         appropriate management information. We use line number here."
    ::= { wfMplsAtmSessStatusEntry 2 }

wfMplsAtmSessStatusIndex OBJECT-TYPE
    SYNTAX  INTEGER (1..65535)
    ACCESS  read-only
    STATUS  mandatory
    DESCRIPTION
        "LDP session index number."
    ::= { wfMplsAtmSessStatusEntry 3 }

wfMplsAtmSessActualVcRangeVpi OBJECT-TYPE
    SYNTAX  INTEGER (0..255)
    ACCESS  read-only
    STATUS  mandatory
    DESCRIPTION
        "The VPI value of the actually allowable VC range for 
         this session. The maximum VPI value cannot exceed the value allowable 
         by the wfAtmInterfaceMaxActiveVpiBits."
    ::= { wfMplsAtmSessStatusEntry 4 }

wfMplsAtmSessActualVcRangeMinVci OBJECT-TYPE
    SYNTAX  INTEGER (32..65535)
    ACCESS  read-only
    STATUS  mandatory
    DESCRIPTION
        "The minimum VCI value of the actually allowable VC range for LDP session.
         The maximum VCI value cannot exceed the value allowable by the 
         wfAtmInterfaceMaxActiveVciBits."
    ::= { wfMplsAtmSessStatusEntry 5 }

wfMplsAtmSessActualVcRangeMaxVci OBJECT-TYPE
    SYNTAX  INTEGER (32..65535)
    ACCESS  read-only
    STATUS  mandatory
    DESCRIPTION
        "The maximum VCI value of the actually allowable VC range for LDP session.
         The maximum VCI value cannot exceed the value allowable by the 
         wfAtmInterfaceMaxActiveVciBits."
    ::= { wfMplsAtmSessStatusEntry 6 }

wfMplsAtmSessNegotiatedVcRangeVpi OBJECT-TYPE
    SYNTAX  INTEGER (-1..255)
    ACCESS  read-only
    STATUS  mandatory
    DESCRIPTION
        "The VPI value of the VCs negotiated with LDP peer for this LDP session. 
         The maximum VPI value cannot exceed the value allowable by the 
         wfAtmInterfaceMaxActiveVpiBits. -1 means it is not possible."
    ::= { wfMplsAtmSessStatusEntry 7 }

wfMplsAtmSessNegotiatedVcRangeMinVci OBJECT-TYPE
    SYNTAX  INTEGER (32..65535)
    ACCESS  read-only
    STATUS  mandatory
    DESCRIPTION
        "The minimum VCI value of VCs negotiated with LDP peer for this LDP 
         session. The maximum VCI value cannot exceed the value allowable by the 
         wfAtmInterfaceMaxActiveVciBits."
    ::= { wfMplsAtmSessStatusEntry 8 }

wfMplsAtmSessNegotiatedVcRangeMaxVci OBJECT-TYPE
    SYNTAX  INTEGER (32..65535)
    ACCESS  read-only
    STATUS  mandatory
    DESCRIPTION
        "The maximum VCI value of VCs negotiated with LDP peer for this LDP 
         session. The maximum VCI value cannot exceed the value allowable by the 
         wfAtmInterfaceMaxActiveVciBits."
    ::= { wfMplsAtmSessStatusEntry 9 }   

wfMplsAtmSessInboundInuseVcs OBJECT-TYPE
    SYNTAX  Counter 
    ACCESS  read-only
    STATUS  mandatory
    DESCRIPTION
        "number of VCs opened for inbound LSP."
    ::= { wfMplsAtmSessStatusEntry 10 }   

wfMplsAtmSessOutboundInuseVcs OBJECT-TYPE
    SYNTAX  Counter 
    ACCESS  read-only
    STATUS  mandatory
    DESCRIPTION
        "number of VCs opened for outbound LSP."
    ::= { wfMplsAtmSessStatusEntry 11 }   



wfMplsAtmVclTable OBJECT-TYPE
    SYNTAX  SEQUENCE OF WfMplsAtmVclEntry
    ACCESS  not-accessible
    STATUS  mandatory
    DESCRIPTION
        "Read-only per VC infomation."
    ::= { wfMplsAtm 5 }

wfMplsAtmVclEntry OBJECT-TYPE
    SYNTAX  WfMplsAtmVclEntry
    ACCESS  not-accessible
    STATUS  mandatory
    DESCRIPTION
        "Entry definition."
    INDEX   { wfMplsAtmVclLineNumber,
              wfMplsAtmVclVpi,
              wfMplsAtmVclVci }
    ::= { wfMplsAtmVclTable 1 }

WfMplsAtmVclEntry ::= SEQUENCE {
    wfMplsAtmVclLineNumber
	INTEGER,
    wfMplsAtmVclVpi
        INTEGER,
    wfMplsAtmVclVci
        INTEGER,
    wfMplsAtmVclLdpIndex
        INTEGER,
    wfMplsAtmVclDirection
        INTEGER,
    wfMplsAtmVclState
	INTEGER,
    wfMplsAtmVclType
        INTEGER,
    wfMplsAtmVclLastChange
        TimeTicks,
    wfMplsAtmVclXmtPeakCellRate
        INTEGER,
    wfMplsAtmVclXmtSustainableCellRate
        INTEGER,
    wfMplsAtmVclXmtBurstSize
        INTEGER,
    wfMplsAtmVclXmtQosClass
        INTEGER,
    wfMplsAtmVclRcvPeakCellRate
        INTEGER,
    wfMplsAtmVclRcvSustainableCellRate
        INTEGER,
    wfMplsAtmVclRcvBurstSize
        INTEGER,
    wfMplsAtmVclRcvQosClass
        INTEGER,
    wfMplsAtmVclAalType
        INTEGER,
    wfMplsAtmVclAalCpcsTransmitSduSize
        INTEGER,
    wfMplsAtmVclAalCpcsReceiveSduSize
        INTEGER,
    wfMplsAtmVclAalEncapsType
        INTEGER,
    wfMplsAtmVclCongestionIndication
        INTEGER,
    wfMplsAtmVclCellLossPriority
        INTEGER,
    wfMplsAtmVclXmtTagging
        INTEGER,
    wfMplsAtmVclRcvTagging
        INTEGER
}

wfMplsAtmVclLineNumber OBJECT-TYPE
    SYNTAX  INTEGER
    ACCESS  read-only
    STATUS  mandatory
    DESCRIPTION
        "Uniquely identifies the interface (port) that contains the
         appropriate management information. We use line number here."
    ::= { wfMplsAtmVclEntry 1 }

wfMplsAtmVclVpi OBJECT-TYPE
    SYNTAX  INTEGER
    ACCESS  read-only
    STATUS  mandatory
    DESCRIPTION
        "The VPI value of the VCL. The maximum VPI value cannot exceed the
         value allowable by the wfMplsAtmInterfaceMaxActiveVpiBits."
    ::= { wfMplsAtmVclEntry 2 }

wfMplsAtmVclVci OBJECT-TYPE
    SYNTAX  INTEGER
    ACCESS  read-only
    STATUS  mandatory
    DESCRIPTION
        "The VCI value of the VCL. The maximum VCI value cannot exceed the
         value allowable by the wfMplsAtmInterfaceMaxActiveVciBits."
    ::= { wfMplsAtmVclEntry 3 }

wfMplsAtmVclLdpIndex OBJECT-TYPE
    SYNTAX  INTEGER
    ACCESS  read-only
    STATUS  mandatory
    DESCRIPTION
        "Uniquely identifies the LDP session number in this interface."
    ::= { wfMplsAtmVclEntry 4 }

wfMplsAtmVclDirection OBJECT-TYPE
    SYNTAX  INTEGER {
                inbound(1),
	        outbound(2),
                duplex(3)
            }
    ACCESS  read-only
    STATUS  mandatory
    DESCRIPTION
        "The direction of LSP"   
    ::= { wfMplsAtmVclEntry 5 }

wfMplsAtmVclState OBJECT-TYPE
    SYNTAX  INTEGER {
	    down(1),
            init(2),
            up(3),
	    cleanup(4),
	    notpresent(5)
    }
    ACCESS  read-only
    STATUS  mandatory
    DESCRIPTION
        "The VC state."
    ::= { wfMplsAtmVclEntry 6 }

wfMplsAtmVclType OBJECT-TYPE
    SYNTAX  INTEGER {
	    default(1),
            lsp(2),
            unknown(3)
            }
    ACCESS  read-only
    STATUS  mandatory
    DESCRIPTION
        "default VC or normal LSP VC."
    ::= { wfMplsAtmVclEntry 7 }

wfMplsAtmVclLastChange OBJECT-TYPE
    SYNTAX  TimeTicks
    ACCESS  read-only
    STATUS  mandatory
    DESCRIPTION
        "The value of MIBII's sysUpTime at the time this VCL entered its
         current operational state."
    ::= { wfMplsAtmVclEntry 8 }

wfMplsAtmVclXmtPeakCellRate OBJECT-TYPE
    SYNTAX  INTEGER {
                default(4716)
            }
    ACCESS  read-only
    STATUS  mandatory
    DESCRIPTION
        "Transmit (Forward) Peak Cell Rate in cells/second. This specifies
         the upper bound on the traffic that can be submitted on an ATM
         connection."
    ::= { wfMplsAtmVclEntry 9 }

wfMplsAtmVclXmtSustainableCellRate OBJECT-TYPE
    SYNTAX  INTEGER {
                default(4716)
            }
    ACCESS  read-only
    STATUS  mandatory
    DESCRIPTION
        "Transmit (Forward) Sustainable Cell Rate in cells/second. This 
         specifies the upper bound on the conforming average rate of an 
         ATM connection, where 'average rate' is the number of cells 
         transmitted divided by the 'duration of the connection'."
    ::= { wfMplsAtmVclEntry 10 }

wfMplsAtmVclXmtBurstSize OBJECT-TYPE
    SYNTAX  INTEGER {
                default(40)
            }
    ACCESS  read-only
    STATUS  mandatory
    DESCRIPTION
        "Transmit (Forward) Burst Size in cells."
    ::= { wfMplsAtmVclEntry 11 }

wfMplsAtmVclXmtQosClass OBJECT-TYPE
    SYNTAX  INTEGER {
                class0(1),
                class1(2),
                class2(3),
                class3(4)
            }
    ACCESS  read-only
    STATUS  mandatory
    DESCRIPTION
        "Transmit (Forward) Quality of Service as specified in Appendix A,
         Section 4 of the ATM Forum UNI Specification, Version 3.0"
    ::= { wfMplsAtmVclEntry 12 }

wfMplsAtmVclRcvPeakCellRate OBJECT-TYPE
    SYNTAX  INTEGER {
                default(4716)
            }
    ACCESS  read-only
    STATUS  mandatory
    DESCRIPTION
        "Receive (Backward) Peak Cell Rate in cells/second. This specifies
         the upper bound on the traffic that can be submitted on an ATM
         connection."
    ::= { wfMplsAtmVclEntry 13 }

wfMplsAtmVclRcvSustainableCellRate OBJECT-TYPE
    SYNTAX  INTEGER {
                default(4716)
            }
    ACCESS  read-only
    STATUS  mandatory
    DESCRIPTION
        "Receive (Backward) Sustainable Cell Rate in cells/second. This
         specifies the upper bound on the conforming average rate of an 
         ATM connection, where 'average rate' is the number of cells 
         transmitted divided by the 'duration of the connection'."
    ::= { wfMplsAtmVclEntry 14 }

wfMplsAtmVclRcvBurstSize OBJECT-TYPE
    SYNTAX  INTEGER {
                default(40)
            }
    ACCESS  read-only
    STATUS  mandatory
    DESCRIPTION
        "Receive (Backward) Burst Size in cells."
    ::= { wfMplsAtmVclEntry 15 }

wfMplsAtmVclRcvQosClass OBJECT-TYPE
    SYNTAX  INTEGER {
                class0(1),
                class1(2),
                class2(3),
                class3(4)
            }
    ACCESS  read-only
    STATUS  mandatory
    DESCRIPTION
        "Receive (Backward) Quality of Service as specified in Appendix A,
         Section 4 of the ATM Forum UNI Specification, Version 3.0"
    ::= { wfMplsAtmVclEntry 16 }

wfMplsAtmVclAalType OBJECT-TYPE
    SYNTAX  INTEGER {
                type1(1),
                type34(2),
                type5(3),
                other(4),
                unknown(5)
            }
    ACCESS  read-only
    STATUS  mandatory
    DESCRIPTION
        "The type of AAL used on the VCL."
    ::= { wfMplsAtmVclEntry 17 }

wfMplsAtmVclAalCpcsTransmitSduSize OBJECT-TYPE
    SYNTAX  INTEGER(1..65535)
    ACCESS  read-only
    STATUS  mandatory
    DESCRIPTION
        "The maximum AAL CPCS SDU size in octets that is supported on the
         transmit direction of this VCC."
    ::= { wfMplsAtmVclEntry 18 }

wfMplsAtmVclAalCpcsReceiveSduSize OBJECT-TYPE
    SYNTAX  INTEGER(1..65535)
    ACCESS  read-only
    STATUS  mandatory
    DESCRIPTION
        "The maximum AAL CPCS SDU size in octets that is supported on the
         receive direction of this VCC."
    ::= { wfMplsAtmVclEntry 19 }

wfMplsAtmVclAalEncapsType OBJECT-TYPE
    SYNTAX  INTEGER {
                unknown(1),
                llcencaps(2),
                null(3),
                other(4)
                }
    ACCESS  read-only
    STATUS  mandatory
    DESCRIPTION
        "The type of data encapsulation used over both AAL3/4 and
         AAL5 SSCS layer. Currently, the only values supported are :
         ATM_VCLENCAPS_LLCENCAPS - RFC1483
         ATM_VCLENCAPS_ROUTEDPROTO - NONE"
    ::= { wfMplsAtmVclEntry 20 }

wfMplsAtmVclCongestionIndication OBJECT-TYPE
    SYNTAX  INTEGER {
                off(1),
                on(2)
            }
    ACCESS  read-only
    STATUS  mandatory
    DESCRIPTION
        "The desired state of the Congestion Indication (CI) bit in the
         payload field of each ATM cell for this VCL."
    ::= { wfMplsAtmVclEntry 21 }

wfMplsAtmVclCellLossPriority OBJECT-TYPE
    SYNTAX  INTEGER {
                off(1),
                on(2)
            }
    ACCESS  read-only
    STATUS  mandatory
    DESCRIPTION
        "The desired state of the Cell Loss Priority (CLP) bit in the ATM
         header of each cell for this VCL."
    ::= { wfMplsAtmVclEntry 22 }

wfMplsAtmVclXmtTagging OBJECT-TYPE
    SYNTAX  INTEGER {
                on(1),
                off(2)
            }
    ACCESS  read-only
    STATUS  mandatory
    DESCRIPTION
        "Tagging forward VC messages if peak/sustainable rates exceeded"
    ::= { wfMplsAtmVclEntry 23 }

wfMplsAtmVclRcvTagging OBJECT-TYPE
    SYNTAX  INTEGER {
                on(1),
                off(2)
            }
    ACCESS  read-only
    STATUS  mandatory
    DESCRIPTION
        "Tagging backward VC messages if peak/sustainable rates exceeded"
    ::= { wfMplsAtmVclEntry 24 }



END -- Wellfleet-MPLS-MLM-MIB
