-- SCCS version: "@(#)att_ds3.mib	4.1.2.2"

--
--		Copyright 1992 AT&T
--		All Rights Reserved
--
--	NOTICE
--	------
--	The information in this document is subject to change
--	without notice. AT&T assumes no responsibility for
--	any errors that may appear in this document.
--
--	Notwithstanding any other lease or license agreement
--	that may pertain to, or accompany the delivery of,
--	this computer software, the rights of the Government
--	regarding its use, reproduction and disclosure are as
--	set forth in Government contract no. GS00K89AGS6495.
--

--
-- Title: AT&T DS3 MIB for Customer Network Management
--


        ATT-CNM-DS3-MIB DEFINITIONS ::= BEGIN

        IMPORTS
                enterprises, Gauge
                        FROM RFC1155-SMI
                DisplayString
                        FROM RFC1213-MIB
                OBJECT-TYPE
                        FROM RFC-1212;

	--
	-- Object Identifiers
	--

        att-2		OBJECT IDENTIFIER ::= { enterprises 74 }
        att-products	OBJECT IDENTIFIER ::= { att-2 1 }
        att-mgmt	OBJECT IDENTIFIER ::= { att-2 2 }
        att-cnmAgent	OBJECT IDENTIFIER ::= { att-products 9 }
        att-cnm		OBJECT IDENTIFIER ::= { att-mgmt 15 }
        att-cnm-ds3	OBJECT IDENTIFIER ::= { att-cnm 4 }


	--
	-- the DS3 group of objects (att-cnm-ds3) include:
	--	
	--	the DS3 Configuration table
	--	the DS3 Status table
	--	the DS3 Error Counts table
	--


	-- the DS3 Configuration table

	--
	-- This table provides configuration information
	-- on DS3 interfaces supported by this system.
	--

	attCNMds3ConfigTable OBJECT-TYPE
		SYNTAX	SEQUENCE OF AttCNMds3ConfigEntry
		ACCESS  not-accessible
		STATUS  mandatory
		DESCRIPTION
			"A list of entries containing configuration
			information for all DS3 interfaces managed by
			this system."
		::= { att-cnm-ds3 1 }

	attCNMds3ConfigEntry OBJECT-TYPE
		SYNTAX  AttCNMds3ConfigEntry
		ACCESS  not-accessible
		STATUS  mandatory
		DESCRIPTION
			"An entry containing configuration information
			for a particular DS3 interface."
		INDEX	{ attCNMds3ConfigIndex }
		::= { attCNMds3ConfigTable 1 }

	AttCNMds3ConfigEntry ::=
		SEQUENCE {
		    attCNMds3ConfigIndex
			INTEGER,
		    attCNMds3LineType
			INTEGER,
		    attCNMds3ZeroCoding
			INTEGER,
		    attCNMds3ErrorsMaxIntervals
			INTEGER,
		    attCNMds3ErrorsIntervalLen
			INTEGER
		}

	attCNMds3ConfigIndex OBJECT-TYPE
		SYNTAX  INTEGER
		ACCESS  read-only
		STATUS  mandatory
		DESCRIPTION
			"A unique value for each DS3 interface. The interface
			identified by a particular value of this index is
			the same interface as identified by the same value
			of an attCNMifConfigIndex object instance."
		::= { attCNMds3ConfigEntry 1 }

	attCNMds3LineType OBJECT-TYPE
		SYNTAX	INTEGER {
			    other(1),
			    ds3M23(2),
			    ds3SYNTRAN(3),
			    ds3CbitParity(4),
			    ds3ClearChannel(5)
			}
		ACCESS	read-only
		STATUS	mandatory
		DESCRIPTION
			"This variable indicates the variety of DS3 C-bit
			application supported by this interface.

			For SMDS, this variable will have the value
			ds3ClearChannel, denoting that this interface supports
			the clear-channel with C-bit usage unspecified as
			specified by ANSI."
		::= { attCNMds3ConfigEntry 2 }

	attCNMds3ZeroCoding OBJECT-TYPE
		SYNTAX	INTEGER {
			    ds3other(1),
			    ds3B3ZS(2)
			}
		ACCESS	read-only
		STATUS	mandatory
		DESCRIPTION
			"This variable describes the variety of zero
			code suppression/substitution used on the DS3
			interface its characteristics."
		::= { attCNMds3ConfigEntry 3 }

        attCNMds3ErrorsMaxIntervals OBJECT-TYPE
                SYNTAX  INTEGER
                ACCESS  read-only
                STATUS  mandatory
                DESCRIPTION
                        "This variable identifies the maximum number
			of measurement intervals supported for the
			error counts maintained by this DS3 interface
			in the attCNMds3ErrorsTable."
                ::= { attCNMds3ConfigEntry 4 }

        attCNMds3ErrorsIntervalLen OBJECT-TYPE
                SYNTAX  INTEGER
                ACCESS  read-only
                STATUS  mandatory
                DESCRIPTION
                        "This variable identifies the number of seconds
			that make up one complete measurement interval for
			the error counts maintained by this DS3 interface
                        in the attCNMds3ErrorsTable."
                ::= { attCNMds3ConfigEntry 5 }


	-- the DS3 Status table

	--
	-- This table provides status information
	-- on DS3 interfaces supported by this system.
	--

	attCNMds3StatusTable OBJECT-TYPE
		SYNTAX	SEQUENCE OF AttCNMds3StatusEntry
		ACCESS  not-accessible
		STATUS  mandatory
		DESCRIPTION
			"A list of entries containing status information
			for all DS3 interfaces managed by this system."
		::= { att-cnm-ds3 2 }

	attCNMds3StatusEntry OBJECT-TYPE
		SYNTAX  AttCNMds3StatusEntry
		ACCESS  not-accessible
		STATUS  mandatory
		DESCRIPTION
			"An entry containing status information for a
			particular DS3 interface."
		INDEX	{ attCNMds3StatusIndex }
		::= { attCNMds3StatusTable 1 }

	AttCNMds3StatusEntry ::=
		SEQUENCE {
		    attCNMds3StatusIndex
			INTEGER,
		    attCNMds3LineStatus
			INTEGER
		}

	attCNMds3StatusIndex OBJECT-TYPE
		SYNTAX  INTEGER
		ACCESS  read-only
		STATUS  mandatory
		DESCRIPTION
			"A unique value for each DS3 interface. The interface
			identified by a particular value of this index is
			the same interface as identified by the same value
			of an attCNMifConfigIndex object instance."
		::= { attCNMds3StatusEntry 1 }
	
	attCNMds3LineStatus OBJECT-TYPE
		SYNTAX	INTEGER
		ACCESS	read-only
		STATUS	mandatory
		DESCRIPTION
                        "This variable indicates the most Line Status
                        of this interface. This object is a bit map
                        represented as a sum, therefore, it can represent
                        multiple failures (alarms) simultaneously. The
                        various bit positions are:

                        	1	No Alarm Present
                        	2	Yellow Alarm
                        	4	Near End Alarm-Indication-Signal
                        	8	Near End Loss-Of-Frame  
                        	16	Near End Loss-Of-Signal

			For example, for an interface that has LOF and
			LOS outstanding, this object will have a value
			of 24."
		::= { attCNMds3StatusEntry 2 }


	-- the DS3 Error Counts table

	--
	-- This table provides counts on the various protocol
	-- errors encountered by a DS3 interface during the
	-- specified measurement interval.
	--

	attCNMds3ErrorsTable OBJECT-TYPE
		SYNTAX	SEQUENCE OF AttCNMds3ErrorsEntry
		ACCESS  not-accessible
		STATUS  mandatory
		DESCRIPTION
			"A list of entries containing protocol error counts,
			maintained during the specified measurement interval,
			for all DS3 interfaces managed by this system."
		::= { att-cnm-ds3 3 }

	attCNMds3ErrorsEntry OBJECT-TYPE
		SYNTAX  AttCNMds3ErrorsEntry
		ACCESS  not-accessible
		STATUS  mandatory
		DESCRIPTION
			"An entry containing protocol error counts,
			maintained during the specified measurement interval,
			for a particular DS3 interface."
		INDEX	{ attCNMds3ErrorsIndex,
				attCNMds3ErrorsInterval }
		::= { attCNMds3ErrorsTable 1 }

	AttCNMds3ErrorsEntry ::=
		SEQUENCE {
		    attCNMds3ErrorsIndex
			INTEGER,
		    attCNMds3ErrorsInterval
			INTEGER,
		    attCNMds3ErrorsTimeStamp
			INTEGER,
		    attCNMds3ErrorsLocalTime
			DisplayString,
		    attCNMds3LCVs
			Gauge,
		    attCNMds3LESs
			Gauge,
		    attCNMds3LSESs
			Gauge,
		    attCNMds3CVs
			Gauge,
		    attCNMds3ESs
			Gauge,
		    attCNMds3SESs
			Gauge,
		    attCNMds3SEFSs
			Gauge,
		    attCNMds3UASs
			Gauge
		}

	attCNMds3ErrorsIndex OBJECT-TYPE
		SYNTAX	INTEGER
		ACCESS	read-only
		STATUS	mandatory
		DESCRIPTION
			"A unique value for each DS3 interface. The interface
			identified by a particular value of this index is
			the same interface as identified by the same value
			of an attCNMifConfigIndex object instance."
		::= { attCNMds3ErrorsEntry 1 }

	attCNMds3ErrorsInterval OBJECT-TYPE
		SYNTAX  INTEGER
		ACCESS  read-only
		STATUS  mandatory
		DESCRIPTION
			"This variable identifies the measurement interval
			number for which measurement is provided. It is a
			number between 1 and XX, where 1 identifies the most
			recently completed measurement interval and XX is
			the least recently completed measurement interval.

                        The value of XX is specified by the
			attCNMds3ErrorsMaxIntervals object given in the
			attCNMds3ConfigTable.

                        The maximum length of each measurement interval is
                        specified by the attCNMds3ErrorsIntervalLen object
			given in the attCNMds3ConfigTable."
		::= { attCNMds3ErrorsEntry 2 }

	attCNMds3ErrorsTimeStamp OBJECT-TYPE
		SYNTAX  INTEGER
		ACCESS  read-only
		STATUS  mandatory
		DESCRIPTION
			"The time stamp corresponding to the end of the
			specified measurement interval, as measured in
			seconds from 00:00:00 UTC (Coordinated Universal
			Time) January 1, 1970. Any fraction is rounded up."
		::= { attCNMds3ErrorsEntry 3 }

	attCNMds3ErrorsLocalTime OBJECT-TYPE
		SYNTAX  DisplayString(SIZE(0..255))
		ACCESS  read-only
		STATUS  mandatory
		DESCRIPTION
			"The time stamp corresponding to the end of the
			specified measurement interval.  Any fraction is
			rounded up. It is given as a printable ASCII string
			showing the local time at the end of the interval."
		::= { attCNMds3ErrorsEntry 4 }

	attCNMds3LCVs OBJECT-TYPE
		SYNTAX	Gauge
		ACCESS	read-only
		STATUS	mandatory
		DESCRIPTION
			"The counter associated with the number of Line
			Code Violations encountered by a DS3 interface
			during the specified measurement interval.

			For a B3ZS-coded signal, a Line Code Violation is
			the occurrence of a received bipolar violation that
			is not part of a zero-substitution code. For a B3ZS
			signal, an LCV may also include other error patterns
			such as: three consecutive zeros and incorrect parity.

			The Bipolar Violation Rate is generally viewed as
			approximating the Bit Error Rate."
		::= { attCNMds3ErrorsEntry 5 }

	attCNMds3LESs OBJECT-TYPE
		SYNTAX	Gauge
		ACCESS	read-only
		STATUS	mandatory
		DESCRIPTION
			"The counter associated with the number of Line
			Errored Seconds encountered by a DS3 interface
			during the specified measurement interval.

			A Line Errored Second is any second with at least
			one Line Code Violation."
		::= { attCNMds3ErrorsEntry 6 }

	attCNMds3LSESs OBJECT-TYPE
		SYNTAX	Gauge
		ACCESS	read-only
		STATUS	mandatory
		DESCRIPTION
			"The counter associated with the number of Line
			Severely Errored Seconds encountered by a DS3
			interface during the specified measurement interval.

			A Line Severely Errored Second is any second with
			45 or more Line Code Violations monitored at the
			DS3 rate."
		::= { attCNMds3ErrorsEntry 7 }

	attCNMds3CVs OBJECT-TYPE
		SYNTAX	Gauge
		ACCESS	read-only
		STATUS	mandatory
		DESCRIPTION
			"The counter associated with the number of Code
			Violations encountered by a DS3 interface during
			the specified measurement interval.

			For SMDS, a DS3 Code Violation is an occurrence of 
			a P-bit error. Excessive Coding Violations signifies
			a faulty transmission line."

		::= { attCNMds3ErrorsEntry 8 }

	attCNMds3ESs OBJECT-TYPE
		SYNTAX	Gauge
		ACCESS	read-only
		STATUS	mandatory
		DESCRIPTION
			"The counter associated with the number of Errored
			Seconds encountered by a DS3 interface during the
			specified measurement interval.

			For SMDS DS3 signals, this is the number of seconds
			during which at least one error occurred which is a
			P-bit error or a Severely Errored Framing event."
		::= { attCNMds3ErrorsEntry 9 }

	attCNMds3SESs OBJECT-TYPE
		SYNTAX	Gauge
		ACCESS	read-only
		STATUS	mandatory
		DESCRIPTION
			"The counter associated with the number of Severely
			Errored Seconds encountered by a DS3 interface
			during the specified measurement interval.

			For SMDS DS3 signals, this is the number of seconds
			during which 44 or more P-bit errors occurred or at
			least one Severely Errored Framing event occurred.

			All Severely Errored Seconds are also counted as
			Errored Seconds."
		::= { attCNMds3ErrorsEntry 10 }

	attCNMds3SEFSs OBJECT-TYPE
		SYNTAX	Gauge
		ACCESS	read-only
		STATUS	mandatory
		DESCRIPTION
			"The counter associated with the number of Severely
			Errored Framing Seconds encountered by a DS3
			interface during the specified measurement interval.

			A Severely Errored Framing Second is any second
			during which one or more Severely Errored Framing
			(SEF) events occurred. A Severely Errored Framing
			event is declared when 3 or more errors in 16 or fewer
			consecutive F-bits occur within a DS3 M-frame."
		::= { attCNMds3ErrorsEntry 11 }

	attCNMds3UASs OBJECT-TYPE
		SYNTAX	Gauge
		ACCESS	read-only
		STATUS	mandatory
		DESCRIPTION
			"The counter associated with the number of
			Unavailable Seconds encountered by a DS3
			interface during the specified measurement interval.

			An Unavailable Second is any second during which
			the DS3 interface was unavailable to offer service."
		::= { attCNMds3ErrorsEntry 12 }


	END
