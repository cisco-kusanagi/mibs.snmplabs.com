--			Ascend mibds3net MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBDS3NET-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibdS3NetworkProfile  OBJECT IDENTIFIER ::= { configuration 4}

	-- The mibdS3NetworkProfile table
	--
	-- This table contains parameters for the mibdS3NetworkProfile profile
	--

    mibdS3NetworkProfileTable	OBJECT-TYPE
	SYNTAX		SEQUENCE OF MibdS3NetworkProfileEntry
	ACCESS		not-accessible
	STATUS		mandatory
	DESCRIPTION	"A list of mibdS3NetworkProfile profile entries."
	::= { mibdS3NetworkProfile 1 }

    mibdS3NetworkProfileEntry	OBJECT-TYPE
	SYNTAX		MibdS3NetworkProfileEntry
	ACCESS		not-accessible
	STATUS		mandatory
	DESCRIPTION	"A mibdS3NetworkProfile entry containing objects that
			 maps to the parameters of mibdS3NetworkProfile profile."
	INDEX		{ dS3NetworkProfile-Shelf-o, dS3NetworkProfile-Slot-o, dS3NetworkProfile-Item-o }
	::= { mibdS3NetworkProfileTable 1 }

    MibdS3NetworkProfileEntry ::=
	SEQUENCE {
	    dS3NetworkProfile-Shelf-o
		INTEGER,
	    dS3NetworkProfile-Slot-o
		INTEGER,
	    dS3NetworkProfile-Item-o
		INTEGER,
	    dS3NetworkProfile-Name
		DisplayString,
	    dS3NetworkProfile-PhysicalAddress-Shelf
		INTEGER,
	    dS3NetworkProfile-PhysicalAddress-Slot
		INTEGER,
	    dS3NetworkProfile-PhysicalAddress-ItemNumber
		INTEGER,
	    dS3NetworkProfile-Enabled
		INTEGER,
	    dS3NetworkProfile-FrameType
		INTEGER,
	    dS3NetworkProfile-LineLength
		INTEGER,
	    dS3NetworkProfile-Loopback
		INTEGER,
	    dS3NetworkProfile-StatusChangeTrapEnable
		INTEGER,
	    dS3NetworkProfile-Action-o
		INTEGER
	}

    dS3NetworkProfile-Shelf-o	OBJECT-TYPE
	SYNTAX	INTEGER
	ACCESS	read-only
	STATUS	mandatory
	DESCRIPTION	""
	::= { mibdS3NetworkProfileEntry 1 }

    dS3NetworkProfile-Slot-o	OBJECT-TYPE
	SYNTAX	INTEGER
	ACCESS	read-only
	STATUS	mandatory
	DESCRIPTION	""
	::= { mibdS3NetworkProfileEntry 2 }

    dS3NetworkProfile-Item-o	OBJECT-TYPE
	SYNTAX	INTEGER
	ACCESS	read-only
	STATUS	mandatory
	DESCRIPTION	""
	::= { mibdS3NetworkProfileEntry 3 }

    dS3NetworkProfile-Name	OBJECT-TYPE
	SYNTAX	DisplayString
	ACCESS	read-write
	STATUS	mandatory
	DESCRIPTION	"Name of DS3 line."
	::= { mibdS3NetworkProfileEntry 4 }

    dS3NetworkProfile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibdS3NetworkProfileEntry 5 }

    dS3NetworkProfile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibdS3NetworkProfileEntry 6 }

    dS3NetworkProfile-PhysicalAddress-ItemNumber	OBJECT-TYPE
	SYNTAX	INTEGER
	ACCESS	read-write
	STATUS	mandatory
	DESCRIPTION	"A number that specifies an addressable entity within the context of shelf and slot."
	::= { mibdS3NetworkProfileEntry 7 }

    dS3NetworkProfile-Enabled	OBJECT-TYPE
	SYNTAX	INTEGER {
		    no (1),
		    yes (2)
		}
	ACCESS	read-write
	STATUS	mandatory
	DESCRIPTION	"TRUE if the line is enabled, otherwise FALSE."
	::= { mibdS3NetworkProfileEntry 8 }

    dS3NetworkProfile-FrameType	OBJECT-TYPE
	SYNTAX	INTEGER {
		    m13 (1),
		    cBitParity (2)
		}
	ACCESS	read-write
	STATUS	mandatory
	DESCRIPTION	"Determines the DS3 frame format, also known as the DS3 application."
	::= { mibdS3NetworkProfileEntry 9 }

    dS3NetworkProfile-LineLength	OBJECT-TYPE
	SYNTAX	INTEGER {
		    n-0225 (1),
		    n-226450 (2)
		}
	ACCESS	read-write
	STATUS	mandatory
	DESCRIPTION	"The length in feet of the Rx and Tx lines to a DSX-3 cross connect. Double these values for direct connection."
	::= { mibdS3NetworkProfileEntry 10 }

    dS3NetworkProfile-Loopback	OBJECT-TYPE
	SYNTAX	INTEGER {
		    noLoopback (1),
		    lineLoopback (2),
		    localLoopback (3)
		}
	ACCESS	read-write
	STATUS	mandatory
	DESCRIPTION	"Loopback mode."
	::= { mibdS3NetworkProfileEntry 12 }

    dS3NetworkProfile-StatusChangeTrapEnable	OBJECT-TYPE
	SYNTAX	INTEGER {
		    no (1),
		    yes (2)
		}
	ACCESS	read-write
	STATUS	mandatory
	DESCRIPTION	"When set to No, do not send dsx3LineStatusChangeTrapEnable trap. If Yes, send traps. The default is No."
	::= { mibdS3NetworkProfileEntry 13 }

    dS3NetworkProfile-Action-o	OBJECT-TYPE
	SYNTAX	INTEGER {
		    noAction (1),
		    createProfile (2),
		    deleteProfile (3)
		}
	ACCESS	read-write
	STATUS	mandatory
	DESCRIPTION	""
	::= { mibdS3NetworkProfileEntry 11 }

END
