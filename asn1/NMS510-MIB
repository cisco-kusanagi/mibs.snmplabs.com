-- Copyright 1994 General DataComm Inc., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.

-- Revision History
-- Version   Date	Name		Description
-- 1.00A     20-Jul-95  C. Amorossi	Initial Revision

NMS510-MIB DEFINITIONS ::= BEGIN

IMPORTS
	OBJECT-TYPE			FROM RFC-1212
	DisplayString			FROM RFC1213-MIB
	SCinstance			FROM GDCMACRO-MIB
        gdc                             FROM GDCCMN-MIB
	dsu				FROM DDS-MIB;

nms510 		OBJECT IDENTIFIER ::= { dsu 6 }

-- This MIB module uses the extended OBJECT-TYPE macro as
-- defined in RFC 1212.

-- The implementation of all groups is mandatory for all products in
-- the NMS510 family.

-- All objects in this mib are directed toward one interface which
-- is the unit. There is one entry per table for each managed nms510.

-- Note:  All rows in all tables defined within this MIB module are
-- virtual.  They can neither be created or deleted by management
-- operations.

-- The Version Group. This group identifies the version information
-- for the MIB.
--
nms510MIBversion OBJECT-TYPE
    SYNTAX DisplayString (SIZE (5))
    ACCESS read-only
    STATUS mandatory
    DESCRIPTION
    	"Identifies the version of the MIB. The format of the version
    	is x.yzT, where 'x' identifies the major revision number, 'y'
    	identifies the minor revision number, 'z' identifies the
    	typographical revision, and T identifies the test revision.
    	Acceptable values for the individual revision components are
    	as follows:

    		x: 1 - 9
    		y: 0 - 9
    		z: 0 - 9
    		T: A - Z

    	Upon formal release, no designation for the test revision will
    	be present."
    ::= { nms510 1 }

-- The NMS510 Group.  This group contains objects that support the
-- specific management requirements of the NMS510 that are not
-- addressed through other standard MIB modules.  The group contains one
-- table:  NMS510 Unit Configuration table.  There is one entry in
-- this table for each managed NMS510.

nms510UnitCfgTable OBJECT-TYPE
    SYNTAX SEQUENCE OF Nms510UnitCfgEntry
    ACCESS not-accessible
    STATUS mandatory
    DESCRIPTION
    	"The NMS510 Unit Configuration table.  This table augments the 
	GDC SC5520 Unit Configuration table, providing unit level configuration 
	for each NMS510 device installed. For each entry in the GDC SC 
	Unit Configuration table that represents an NMS510, there is a 
	corresponding entry here whereby the value of the gdcSCunitCfgIndex 
	object is equivalent to the value of the nms510unitCfgIndex object."
    ::= { nms510 2 }

nms510UnitCfgEntry OBJECT-TYPE
    SYNTAX Nms510UnitCfgEntry
    ACCESS not-accessible
    STATUS mandatory
    DESCRIPTION
    	"The NMS510 Unit Configuration table entry. The information in this 
	entry augments the information in the corresponding entry in the 
	GDC SC Unit Configuration table and provides unit level configuration 
	for the installed NMS510."
    INDEX { nms510UnitCfgIndex }
    ::= { nms510UnitCfgTable 1 }

Nms510UnitCfgEntry ::= 
    SEQUENCE {
        nms510UnitCfgIndex SCinstance,
	nms510DteCtsDelay INTEGER,
	nms510DteCtsDelayExt INTEGER,
	nms510FirmwareLevel DisplayString,
	nms510AlarmCfgCountWindow INTEGER,
	nms510SoftReset INTEGER,
        nms510FrontPanelInhibit INTEGER,
        nms510FrontPanelEnable INTEGER,
        nms510HdlcInvert INTEGER,
	nms510PiggyBackDetect INTEGER,
	nms510ExtPortCtrlOut1 INTEGER,
	nms510ExtPortCtrlOut2 INTEGER
    }

nms510UnitCfgIndex OBJECT-TYPE
    SYNTAX SCinstance
    ACCESS read-only
    STATUS mandatory
    DESCRIPTION
    	"The index value which uniquely identifies the NMS510 to which 
	this entry is applicable.  This has the form of a SCinstance 
	which defines the slot, line, and drop of the NMS510 with no 
	sub-identifier value."
    ::= { nms510UnitCfgEntry 1 }

nms510DteCtsDelay OBJECT-TYPE
    SYNTAX INTEGER {
    	ctsOn(1),
    	cts0mSec(2),
    	ctsFixed3Char(3)
    }
    ACCESS read-write
    STATUS mandatory
    DESCRIPTION
    	"RTS/CTS Delay options

		ctsOn(1) 	Forces both RTS and CTS On regardless of the
				state of the attached business equipment (the
				transmitter is On regardless of the status of
				the RTS interface lead). MIB object
				nms510DteCtsDelayExt is ignored.

		cts0mSec(2)	Provides zero bits of delay between active
				RTS and CTS being set to active. MIB object
				nms510DteCtsDelayExt must be set to ext0mSec(1).

		ctsFix3Char(3)	Provides three character bits of delay between
 				active RTS and CTS being set to active. MIB
 				object nms510DteCtsDelayExt must be set to
 				ext0mSec(1)."
    ::= { nms510UnitCfgEntry 2 }

nms510DteCtsDelayExt OBJECT-TYPE
    SYNTAX INTEGER {
    	ext0mSec(1),
    	ext30mSec(2),
    	ext60mSec(3),
    	ext90mSec(4)
    }
    ACCESS read-write
    STATUS mandatory
    DESCRIPTION
    	"RTS/CTS Delay options extension

		ext0mSec(1)	Used to enable options cts0mSec(2) or
				ctsFix3Char(3) from MIB object
				nms510DteCtsDelay.

		ext30mSec(2)	Provides 30 msec of delay between active
				RTS and CTS being set to active. MIB object
				nms510DteCtsDelay must be set for either
				cts0mSec(2) or ctsFix3Char(3).

		ext60mSec(3)	Provides 60 msec of delay between active
				RTS and CTS being set to active. MIB object
				nms510DteCtsDelay must be set for either
				cts0mSec(2) or ctsFix3Char(3).


		ext90mSec(4)	Provides 90 msec of delay between active
				RTS and CTS being set to active. MIB object
				nms510DteCtsDelay must be set for either
				cts0mSec(2) or ctsFix3Char(3)."
   ::= { nms510UnitCfgEntry 3 }

nms510FirmwareLevel OBJECT-TYPE
    SYNTAX DisplayString (SIZE(2))
    ACCESS read-only
    STATUS mandatory
    DESCRIPTION
	 "The version number of the firmware, to allow products to know which 
	 revision is installed.  The released version number is sequenced from 
	 --, A-, ... AA, ... ZZ.  Test versions are numerical from 01 to 99."
    ::= { nms510UnitCfgEntry 4 }

nms510AlarmCfgCountWindow OBJECT-TYPE
    SYNTAX  INTEGER (1..15)
    ACCESS read-write
    STATUS mandatory
    DESCRIPTION
    	"The DDS Alarm Threshold Alarm Interval. It specifies the amount of 
	time in minutes, 1 to 15 minutes, in which the threshold setting is 
	to be exceeded for the alarm to occur.  There is one Alarm Interval
	for all alarms that require thresholds: nms510FrameLossAlm. "
    ::= { nms510UnitCfgEntry 5 }

nms510SoftReset OBJECT-TYPE
    SYNTAX INTEGER {
    	normal(1),      -- read only
    	reset(2)	-- write only
    }
    ACCESS read-write
    STATUS mandatory
    DESCRIPTION
    	"This object will cause software reset in dataset."
    ::= { nms510UnitCfgEntry 6 }

nms510FrontPanelInhibit OBJECT-TYPE
    SYNTAX INTEGER {
	fpInhibited(1),		-- Read only
	fpEnabled(2),		-- Read only
    	execute(3)		-- Write only
    }
    ACCESS read-write
    STATUS mandatory
    DESCRIPTION
	"Inhibits front panel test switch.  If a test
	switch is activated while inhibited it will simply be ignored.
	If enabled via the nms510FrontPanelEnable object the test 
	switch will function as normal."
    ::= { nms510UnitCfgEntry 7 }


nms510FrontPanelEnable OBJECT-TYPE
    SYNTAX INTEGER {
	fpInhibited(1),		-- Read only
	fpEnabled(2),		-- Read only
    	execute(3)		-- Write only
    }
    ACCESS read-write
    STATUS mandatory
    DESCRIPTION
	"Enables front panel test switch.  If a test
	switch is activated while inhibited, via the 
	nms510FrontPanelInhibit object, it will simply be ignored.
	If enabled the test switch will function as normal."
    ::= { nms510UnitCfgEntry 8 }

nms510HdlcInvert OBJECT-TYPE
    SYNTAX INTEGER {
	normal(1),
	invert(2)
    }
    ACCESS read-write
    STATUS mandatory
    DESCRIPTION
	"Primary data invert option.  Will enhance the quality of
	data when network does not provide B8Z5.  Primarily used
	with DDS II 56k"
    ::= { nms510UnitCfgEntry 9 }

nms510PiggyBackDetect OBJECT-TYPE
    SYNTAX INTEGER  {
	not-installed(1),
	installed(2)
    }
    ACCESS read-only
    STATUS mandatory
    DESCRIPTION
	"If set to 2 then either a Data Rate Adadaptor or 530 card is
	installed."
    ::= { nms510UnitCfgEntry 10 }

nms510ExtPortCtrlOut1 OBJECT-TYPE
   SYNTAX INTEGER {
	on(1),
	off(2)
   }
   ACCESS read-write
   STATUS mandatory
   DESCRIPTION
	"This option sets the external output state (on/off) of the
	current network element and displays the external output."
   ::= { nms510UnitCfgEntry 11 }

nms510ExtPortCtrlOut2 OBJECT-TYPE
   SYNTAX INTEGER {
	on(1),
	off(2)
   }
   ACCESS read-write
   STATUS mandatory
   DESCRIPTION
	"This option sets the external output state (on/off) of the
	current network element and displays the external output."
   ::= { nms510UnitCfgEntry 12 }

--**************************************************************************
--                      Alarm Configuration
--**************************************************************************
nms510AlarmData  	OBJECT IDENTIFIER ::= { nms510 4 }

nms510NoResponseAlm 		OBJECT IDENTIFIER ::= { nms510AlarmData 1 }
nms510DiagRxErrAlm 		OBJECT IDENTIFIER ::= { nms510AlarmData 2 }
nms510PowerUpAlm 		OBJECT IDENTIFIER ::= { nms510AlarmData 3 }
nms510EEChkSumErrAlm 		OBJECT IDENTIFIER ::= { nms510AlarmData 4 }
nms510StcLoopbackAlm       	OBJECT IDENTIFIER ::= { nms510AlarmData 5 } 
nms510NoSignalAlm	        OBJECT IDENTIFIER ::= { nms510AlarmData 6 } 
nms510FpTestAlm	        	OBJECT IDENTIFIER ::= { nms510AlarmData 7 } 
nms510StreamingAlm      	OBJECT IDENTIFIER ::= { nms510AlarmData 8 } 
nms510DSRLossAlm		OBJECT IDENTIFIER ::= { nms510AlarmData 9 } 
nms510DTRLossAlm 		OBJECT IDENTIFIER ::= { nms510AlarmData 10 }
nms510DTPLossAlm        	OBJECT IDENTIFIER ::= { nms510AlarmData 11 }
nms510DCDLossAlm        	OBJECT IDENTIFIER ::= { nms510AlarmData 12 } 
nms510RXDLossAlm        	OBJECT IDENTIFIER ::= { nms510AlarmData 13 } 
nms510TXDLossAlm        	OBJECT IDENTIFIER ::= { nms510AlarmData 14 } 
nms510DBURequestForScanAlm      OBJECT IDENTIFIER ::= { nms510AlarmData 15 } 
nms510DBUOnalm                  OBJECT IDENTIFIER ::= { nms510AlarmData 16 } 
nms510DBUFailedAlm              OBJECT IDENTIFIER ::= { nms510AlarmData 17 }  
nms510ExtInputChangeAlm		OBJECT IDENTIFIER ::= { nms510AlarmData 18 }
nms510ExtInputLowAlm		OBJECT IDENTIFIER ::= { nms510AlarmData 19 }
nms510FrameLossAlm      	OBJECT IDENTIFIER ::= { nms510AlarmData 20 } 

-- The following alarms are 'NOT MASKABLE' nms510NoResponseAlm {1},
-- nms510DiagRxErrAlm {2} and nms510PowerUpAlm {3}. All other alarms 'ARE MASKABLE'. 

-- Alarm entry nms510FrameLossAlm{20} requires 
-- threshold settings. See nms510AlarmCfgTable for alarm threshold settings.
-- Alarm		Table Entry			Port Use
-- --------------	---------------------------	------------ 
-- No Responce		nms510NoResponseAlm		DTE and Line
-- Diag Rx Error	nms510DiagRxErrAlm		DTE and Line
-- Power Up Alarm 	nms510PowerUpAlm		DTE and Line
-- Network Loop		nms510StcLoopbackAlm 		Line
-- No Signal		nms510NoSignalAlm		Line
-- Front Panel Test	nms510FpTestAlm			DTE and Line
-- Streaming		nms510StreamingAlm		DTE
-- DSR Loss		nms510DSRLossAlm		DTE
-- DTR Loss		nms510DTRLossAlm		DTE
-- DTP Loss		nms510DTPLossAlm		DTE
-- DCD Loss		nms510DCDLossAlm		DTE
-- RXD Loss		nms510RXDLossAlm		DTE
-- TXD Loss		nms510TXDLossAlm		DTE
-- DBU request for scan nms510DBURequestforScanAlm      Line
-- DBU on 		nms510DBUOnalm                  Line
-- DBU Failed		nms510DBUFailedAlm              Line
-- Ext Input changed	nms510ExtInputChangeAlm
-- Ext Input is active	nms510ExtInputLowAlm
-- Frame Loss		nms510FrameLossAlm		Line
--*****************************************************************************
--                    NEW ALARMS CONFIGURATION TABLE
--*****************************************************************************
nms510AlarmCfgTable OBJECT-TYPE
        SYNTAX  SEQUENCE OF Nms510AlarmCfgEntry
        ACCESS  not-accessible
        STATUS  mandatory   
        DESCRIPTION 
                "The GDC NMS510 Alarm Configuration Table."
        ::= { nms510 8 }

nms510AlarmCfgEntry OBJECT-TYPE
        SYNTAX  Nms510AlarmCfgEntry
        ACCESS  not-accessible
        STATUS  mandatory
        DESCRIPTION
		"An entry in the GDC NMS510 alarm Configuration table."
        INDEX   { nms510AlarmCfgIndex, nms510AlarmCfgIdentifier }   
        ::= { nms510AlarmCfgTable 1 }

Nms510AlarmCfgEntry ::=
        SEQUENCE {
		nms510AlarmCfgIndex 		  SCinstance,
                nms510AlarmCfgIdentifier 	  OBJECT IDENTIFIER,
		nms510AlarmCfgThreshold  INTEGER
	}
nms510AlarmCfgIndex OBJECT-TYPE
        SYNTAX  SCinstance
        ACCESS  read-only
	STATUS  mandatory
        DESCRIPTION
               "This object is the index of the NMS510 Alarm 
		Threshold Configuration table."
        ::= { nms510AlarmCfgEntry 1 }

nms510AlarmCfgIdentifier OBJECT-TYPE
    SYNTAX OBJECT IDENTIFIER
    ACCESS read-only
    STATUS mandatory
    DESCRIPTION
        "The unique alarm identifier assigned to this alarm type. The
         format of this identifier is an OBJECT IDENTIFIER that has
         the following format: {iso(1) org(3) dod(6) internet(1)
         private(4) enterprises(1) gdc(498) xxx(x) alarm(z) yyy(y)
         where xxx(x) is the administratively assigned family object
        identifier (z) is the object identifier for alarms in the family
        defined MIB and yyy(y) is the administratively assigned alarm
        type identifier for this alarm."
    ::= { nms510AlarmCfgEntry 2 }

nms510AlarmCfgThreshold OBJECT-TYPE
    SYNTAX  INTEGER (0..99)
    ACCESS read-write
    STATUS mandatory
    DESCRIPTION
    	"This function sets/reads the alarm threashold settings criteria.
	This threshold is used along with the alarm window to determine
	the number of instances in a given time frame for a Frame Loss alarm 
	to occur before the alarm is considered active.  Frame Loss alarm
	only reported in DDS-2 line type. 

Alarm           	Table Entry		Threshold Range   Defaults
------------------	--------------------	--------------	  --------
Frame Loss      	nms510FrameLossAlm      1 to 99 Count	  10"
    ::= { nms510AlarmCfgEntry 3 }


--
-- Diagonostics
--
--
nms510DiagCfgTable OBJECT-TYPE
    SYNTAX SEQUENCE OF Nms510DiagCfgEntry
    ACCESS not-accessible
    STATUS mandatory
    DESCRIPTION
    	"The NMS510 Unit Diagonostic table. "
    ::= { nms510 6 }

nms510DiagCfgEntry OBJECT-TYPE
    SYNTAX Nms510DiagCfgEntry
    ACCESS not-accessible
    STATUS mandatory
    DESCRIPTION
    	"The NMS510 Unit Diagonostic table entry. "
    INDEX { nms510DiagCfgIndex }
    ::= { nms510DiagCfgTable 1 }

Nms510DiagCfgEntry ::= 
    SEQUENCE {
	nms510DiagCfgIndex SCinstance,
	nms510DiagSendCode INTEGER,
	nms510DiagTestExceptions INTEGER,
	nms510DiagBitErrors INTEGER,
	nms510DiagBlockErrors INTEGER,
	nms510DiagTestReset INTEGER
    }

nms510DiagCfgIndex OBJECT-TYPE
    SYNTAX SCinstance
    ACCESS read-only
    STATUS mandatory
    DESCRIPTION
    	"The index value which uniquely identifies the NMS510 to which 
	this entry is applicable.  This has the form of a SCinstance 
	which defines the slot, line, and drop of the NMS510 with no 
	sub-identifier value."
    ::= { nms510DiagCfgEntry 1 }


nms510DiagSendCode OBJECT-TYPE
    SYNTAX INTEGER {
    	sendOtherPattern(1),
    	send511Pattern(2),
    	send2047Pattern(3),
    	send15BitPattern(4)
    }
    ACCESS read-write
    STATUS mandatory
    DESCRIPTION
	"Configures the selftest pattern to be run during any
	diagonostic test involving selftest. If option SendOtherPattern is
        selected, then pattern will default to 15 bit if unit is set
	for 56k-DDS/sc-multi point else pattern will default to 511 bit
	for all other conditions"
    ::= { nms510DiagCfgEntry 2 }


nms510DiagTestExceptions OBJECT-TYPE
    SYNTAX INTEGER {
	noExceptions(1),
	blocksOutOfRange(2),
	bitsOutOfRange(3),
	blocksAndBitsOutOfRange(4)
    }
    ACCESS read-only
    STATUS mandatory
    DESCRIPTION
    	"Indicates exceptions that have occurred that may affect
    	interpretation of the test results.

    	The value of this object is a sum.  This sum initially take
    	the value zero.  Then, for each exception, the value
    	associated with the exception is added to the sum.

    	The exception values are:

    		value	exception
		    0	No errors
   		    1   bit over range
    		    2   block over range
		    4 	bit and block over range"
    ::= { nms510DiagCfgEntry 3 }

nms510DiagBitErrors OBJECT-TYPE
    SYNTAX INTEGER (0..65535)
    ACCESS read-only
    STATUS mandatory
    DESCRIPTION
    	"The bit errors of the last diagnostic test that involved a
	Selftest pattern.  Reading bit errors while a diagnostic
	test in running will cause the unit to drop out of test
	and invalidate the bit errors.  Bit errors should be read
	only after the test is completed.  The valid range for bit
	errors is 0 to 1,023, 65535 will be returned if for any reason
	the test was terminated early."
    ::= { nms510DiagCfgEntry 4 }

nms510DiagBlockErrors OBJECT-TYPE
    SYNTAX INTEGER (0..65535)
    ACCESS read-only
    STATUS mandatory
    DESCRIPTION
    	"The block errors of the last diagnostic test that involved a
	Selftest pattern.  Reading block errors while a diagnostic
	test in running will cause the unit to drop out of test
	and invalidate the block errors.  Block errors should be read
	only after the test is completed.  The valid range for block
	errors is 0 to 1,023, 65535 will be returned if for any reason
	the test was terminated early."
    ::= { nms510DiagCfgEntry 5 }


nms510DiagTestReset OBJECT-TYPE
    SYNTAX INTEGER {
    	normal(1),      -- read only
	diagnostic(2),  -- read only
    	resetTest(3)	-- write only
    }
    ACCESS read-write
    STATUS mandatory
    DESCRIPTION
    	"This object will halt the execution of any and all
	diagnostic test that may be running with the exception 
	of the Network Delay Test.  This should only be used
	to terminate the test because reading this object will
	terminate the test."
    ::= { nms510DiagCfgEntry 6 }

--
--
--

nms510DiagExcTable OBJECT-TYPE
    SYNTAX SEQUENCE OF Nms510DiagExcEntry
    ACCESS not-accessible
    STATUS mandatory
    DESCRIPTION
    	"The NMS510 Unit Diagonostic table. "
    ::= { nms510 7 }

nms510DiagExcEntry OBJECT-TYPE
    SYNTAX Nms510DiagExcEntry
    ACCESS not-accessible
    STATUS mandatory
    DESCRIPTION
    	"The NMS510 Unit Diagonostic table entry. "
    INDEX { nms510DiagExcIndex }
    ::= { nms510DiagExcTable 1 }

Nms510DiagExcEntry ::= 
    SEQUENCE {
	nms510DiagExcIndex SCinstance,
	nms510DiagIntLineloop INTEGER,
	nms510DiagIntDataloop INTEGER,
	nms510DiagEndToEndSelftest INTEGER,
	nms510DiagNetworkDelay INTEGER,
	nms510DiagTestStatus INTEGER,
 	nms510DiagExtDataloop INTEGER
}

nms510DiagExcIndex OBJECT-TYPE
    SYNTAX SCinstance
    ACCESS read-only
    STATUS mandatory
    DESCRIPTION
    	"The index value which uniquely identifies the NMS510 to which 
	this entry is applicable.  This has the form of a SCinstance 
	which defines the slot, line, and drop of the NMS510 with no 
	sub-identifier value."
    ::= { nms510DiagExcEntry 1 }

nms510DiagIntLineloop OBJECT-TYPE
  	SYNTAX INTEGER {
	lineloopOff(1),		-- Read only
        lineloopOn(2),		-- Read only
	blocks1(3),		-- Write only
	blocks10(4),		-- Write only
	blocks100(5),		-- Write only
	blocks500(6),		-- Write only
	blocks1000(7),		-- Write only
	blocks5000(8),		-- Write only
	blocks10000(9),		-- Write only
	blocks50000(10) 	-- Write only
    }
    ACCESS read-write
    STATUS mandatory
    DESCRIPTION
	"Lineloop (or Analoop) can be either a Bilaterial or Unilaterial
	loopback depending on option ddsDteTermaloop.  To initiate a
	Lineloop with Selftest SET this object and specifiy a 
	blocksize. The blocksize indicates the number of blocks the 
	Selftest pattern generator will run.  There are 1000 bits/block.
	Emuns 3 through 10 are write only.  The only valid 
	responses to a READ are lineloopOn(2) or lineloopOff(1). This test 
	will terminate after the specified number of blocks have been run.
 	Reading test results via the nms510DiagBitErrors or nms510DiagBlockErrors 
	objects while the test is running will cause 
	the test to terminate prematurely and render the results invalid.
	Test results should be only read after the test is completed.  
	The current Test Status can be obtained by reading this object or the
	nms510DiagTestStatus object on the unit under test.  This test can 
	also be terminated by seting the nms510DiagTestReset object. "
    ::= { nms510DiagExcEntry 2 }


nms510DiagIntDataloop OBJECT-TYPE
	SYNTAX INTEGER {
	dataloopOff(1),		-- Read only
        dataloopOn(2),		-- Read only
	blocks1(3),		-- Write only
	blocks10(4),		-- Write only
	blocks100(5),		-- Write only
	blocks500(6),		-- Write only
	blocks1000(7),		-- Write only
	blocks5000(8),		-- Write only
	blocks10000(9),		-- Write only
	blocks50000(10)		-- Write only
    }
    ACCESS read-write
    STATUS mandatory
    DESCRIPTION
	"To initiate a Dataloop with Selftest SET this object and specifiy a 
	blocksize. The nms510 (the remote) unit will go into Dataloop and 
	the master (the sc5520) unit will go into Selftest.  The blocksize
	indicates the number of blocks the Selftest pattern generator will run.
	There are 1000 bits/block.  Emuns 3 through 10 are write only.
	The only valid responses to a READ are dataloopOn(2) or dataloopOff(1).
	This test will terminate after the specified number of blocks have been run.
 	Reading test results via the nms510DiagBitErrors or nms510DiagBlockErrors 
	objects while the test is running will cause the test to terminate 
	prematurely and render the results invalid.  Test results should be read 
	only after the test is completed and are available from the master (sc5520) 
	unit.  The current Test Status can be obtained by reading the 
	sc5520DiagTestStatus object on the master unit, reading test status on the 
	remote unit may interfere with the diagonostic test pattern and cause errors.
	This test can also be terminated by seting the nms510DiagTestReset object. "
    ::= { nms510DiagExcEntry 3 }


nms510DiagEndToEndSelftest OBJECT-TYPE
	SYNTAX INTEGER {
	endToEndOff(1),		-- Read only
        endToEndOn(2),		-- Read only
	blocks1(3),		-- Write only
	blocks10(4),		-- Write only
	blocks100(5),		-- Write only
	blocks500(6),		-- Write only
	blocks1000(7),		-- Write only
	blocks5000(8),		-- Write only
	blocks10000(9),		-- Write only
	blocks50000(10)		-- Write only
    }
    ACCESS read-write
    STATUS mandatory
    DESCRIPTION
	"To initiate an End to End Selftest(Error Rate Test) SET this object 
	and specifiy a blocksize.  Both the remote (nms510)
	amd master (sc5520) units will go into Selftest. The blocksize
	indicates the number of blocks the Selftest pattern generator will run.
	There are 1000 bits/block.  Emuns 3 through 10 are write only.
	The only valid responses to a READ are selftestOn(2) or selftestOff(1).
	This test will terminate after the specified number of blocks have been run.
 	Reading test results via the nms510DiagBitErrors or nms510DiagBlockErrors 
	objects while the test is running will cause 
	the test to terminate prematurely and render the results invalid.
	Test results should be read only after the test is completed and are 
	available from both the remote (nms510) and master (sc5520) units.  The 
	current Test Status can be obtained by reading the sc5520DiagTestStatus 
	object on the master unit, reading test status on the remote unit may 
	interfere with the diagonostic test patternand cause errors.  This test can 
	also be terminated by seting the nms510DiagTestReset object. "
   ::= { nms510DiagExcEntry 4 }


nms510DiagNetworkDelay OBJECT-TYPE
	SYNTAX INTEGER {
	delayTestOff(1),	-- Read only
        delayTestOn(2),		-- Read only
	runDelayTest(3) 	-- Write only
    }
    ACCESS read-write
    STATUS mandatory
    DESCRIPTION
	"To initiate a Network Delay test SET this object and specifiy 
	runDelayTest.  Both the remote (nms510) and master (sc5520) units 
	will go into a test to measure network delay. Emun 3 
	is write only.  The only valid responses to a READ are delayTestOn(2) 
	or delayTestOff(1).  This test will terminate after 10 seconds.  
 	Test results should be read only after the test is 
	completed and are available from the master (sc5520) unit.  The 
	current Test Status can be obtained by reading the sc5520DiagTestStatus 
	object on the master unit, reading test status on the remote unit may 
	interfere with the test and cause errors. This test can not be 
	terminated early once it is started."
   ::= { nms510DiagExcEntry 5 }

nms510DiagTestStatus OBJECT-TYPE
    	SYNTAX INTEGER {
	noTest(1),			
	internalLineloop(2),        	-- Analoop & SelfTest
	externalDataloop(3),		-- Dataloop
  	internalDataloop(4),		-- Dataloop & SelfTest
	serviceTestCenterLoop(5),	-- Network initiated loopback
	endToend(6)			-- EndtoEnd Selftest
	}
    ACCESS read-only
    STATUS mandatory
    DESCRIPTION
	"This object gives the current diagonostic test status. noTest 
	indicates that no diagonostic test is currently active. Reading
	this object while in a diagonostic test involing two units may 
	interfere with a selftest pattern and invalidate the test results.
	Reading the sc5520DiagTestStatus (master unit) object during 
	dagonostic tests involing two unit will not disrupt the test 
	results. "
   ::= { nms510DiagExcEntry 6 }

nms510DiagExtDataloop OBJECT-TYPE
	SYNTAX INTEGER {
	dataloopOff(1),		-- Read only
        dataloopOn(2),		-- Read only
	external(3)		-- Write only
    }
    ACCESS read-write
    STATUS mandatory
    DESCRIPTION
	"To initiate a Dataloop test with no Selftest SET this object
	and specifiy external, this will allow the data from the DTE attached 
	to the far end unit (sc5520) to looped back to itself. Emun external(3) 
	is write only.  The only valid response to a READ is dataloopOn(2) or 
	dataloopOff(1). To halt this test you must SET the nms510DiagTestReset 
	object. Reading test results via the nms510DiagBitErrors or 
	nms510DiagBlockErrors objects while the test is running will also cause 
	the test to terminate. There are no test results associated with this test.  
	Reading test status on the remote unit via nms510DiagTestStatus may 
	interfere with the diagonostic test pattern generated from the terminal 
	equiptment. "
    ::= { nms510DiagExcEntry 7 }


END
