-- MIB generated by miftomib version 1.0a

APCUPS-MIB DEFINITIONS ::= BEGIN

IMPORTS
    OBJECT-TYPE
    FROM RFC-1212
    Counter, Gauge, enterprises
    FROM RFC1155-SMI
    DisplayString
    FROM RFC1213-MIB;

DmiCounter			::= Counter
DmiGauge			::= Gauge
DmiInteger			::= INTEGER
DmiDisplaystring	::= DisplayString
DmiDateX			::= OCTET STRING (SIZE (28))
DmiComponentIndex	::= INTEGER

apc                   	OBJECT IDENTIFIER ::= {enterprises 318}
products             	OBJECT IDENTIFIER ::= {apc 1}
software         	OBJECT IDENTIFIER ::= {products 2}
powerChuteDMIAgent     	OBJECT IDENTIFIER ::= {software 2}
dmtfGroups          	OBJECT IDENTIFIER ::= {powerChuteDMIAgent 1}

SComponentid ::= SEQUENCE {
	a1Manufacturer                          	DmiDisplaystring,
	a1Product                               	DmiDisplaystring,
	a1Version                               	DmiDisplaystring,
	a1SerialNumber                          	DmiDisplaystring,
	a1Installation                          	DmiDateX,
	a1Verify                                	DmiInteger
}

tComponentid OBJECT-TYPE
	SYNTAX		SEQUENCE OF SComponentid
	ACCESS		not-accessible
	STATUS		mandatory
	DESCRIPTION	"This group defines the attributes common to all components.
This groupis required."
	::= {dmtfGroups 1}

eComponentid OBJECT-TYPE
	SYNTAX		SComponentid
	ACCESS		not-accessible
	STATUS		mandatory
	DESCRIPTION	""
	INDEX		{DmiComponentIndex}
	::= {tComponentid 1}

a1Manufacturer OBJECT-TYPE
	SYNTAX		DmiDisplaystring
	ACCESS		read-only
	STATUS		mandatory
	DESCRIPTION	"Manufacturer of this system."
	::= {eComponentid 1}

a1Product OBJECT-TYPE
	SYNTAX		DmiDisplaystring
	ACCESS		read-only
	STATUS		mandatory
	DESCRIPTION	"Product name for this system."
	::= {eComponentid 2}

a1Version OBJECT-TYPE
	SYNTAX		DmiDisplaystring
	ACCESS		read-only
	STATUS		mandatory
	DESCRIPTION	"Version number of this system."
	::= {eComponentid 3}

a1SerialNumber OBJECT-TYPE
	SYNTAX		DmiDisplaystring
	ACCESS		read-only
	STATUS		mandatory
	DESCRIPTION	"Serial number for this system."
	::= {eComponentid 4}

a1Installation OBJECT-TYPE
	SYNTAX		DmiDateX
	ACCESS		read-only
	STATUS		mandatory
	DESCRIPTION	"The time and date when this component was installed."
	::= {eComponentid 5}

a1Verify OBJECT-TYPE
	SYNTAX		INTEGER {
		vAnErrorOccuredCheckStatusCode          	(0),
		vThisComponentDoesNotExist              	(1),
		vVerificationIsNotSupported             	(2),
		vReserved                               	(3),
		vThisComponentExistsButTheFunctionalityI	(4),
		vThisComponentExistsButTheFunctionality1	(5),
		vThisComponentExistsAndIsNotFunctioningC	(6),
		vThisComponentExistsAndIsFunctioningCorr	(7)
	}
	ACCESS		read-only
	STATUS		mandatory
	DESCRIPTION	"A code that provides a level of verification that the component
is stillinstalled and working."
	::= {eComponentid 6}

SUpsBattery ::= SEQUENCE {
	a2BatteryStatus                         	DmiInteger,
	a2SecondsOnBattery                      	DmiCounter,
	a2EstimatedMinutesRemaining             	DmiInteger,
	a2EstimatedChargeRemaining              	DmiGauge,
	a2BatteryVoltage                        	DmiGauge,
	a2BatteryCurrent                        	DmiGauge,
	a2TemperatureProbeIndex                 	DmiInteger,
	a2FruGroupIndex                         	DmiInteger,
	a2OperationalGroupIndex                 	DmiInteger
}

tUpsBattery OBJECT-TYPE
	SYNTAX		SEQUENCE OF SUpsBattery
	ACCESS		not-accessible
	STATUS		mandatory
	DESCRIPTION	"The UPS Battery group contains information regarding the
UPSsystem's battery status."
	::= {dmtfGroups 2}

eUpsBattery OBJECT-TYPE
	SYNTAX		SUpsBattery
	ACCESS		not-accessible
	STATUS		mandatory
	DESCRIPTION	""
	INDEX		{DmiComponentIndex}
	::= {tUpsBattery 1}

a2BatteryStatus OBJECT-TYPE
	SYNTAX		INTEGER {
		vUnknown                                	(1),
		vBatteryNormal                          	(2),
		vBatteryLow                             	(3),
		vBatteryDepleted                        	(4)
	}
	ACCESS		read-only
	STATUS		mandatory
	DESCRIPTION	"The indication of the capacity remaining in the UPS system's
batteries. Avalue of 'battery normal' indicates that the remaining estimated
minutes of run-time isgreater than the UPS's configured 'low battery time'
(typically two minutes). A valueof 'battery low'  indicates that the remaining
estimated minutes of battery run-time isless than or equal to the UPS's configur
d 'low battery time'. A value of 'batterydepleted' indicates that the UPS
will be unable to sustain the present load when and ifthe uti"
	::= {eUpsBattery 1}

a2SecondsOnBattery OBJECT-TYPE
	SYNTAX		DmiCounter
	ACCESS		read-only
	STATUS		mandatory
	DESCRIPTION	"If the UPS is on battery power, the elapsed time in seconds
since theUPS last switched to battery power, or the time since the UPS component
software waslast restarted, whichever is less. Zero shall be returned if
the UPS is not on batterypower."
	::= {eUpsBattery 2}

a2EstimatedMinutesRemaining OBJECT-TYPE
	SYNTAX		DmiInteger
	ACCESS		read-only
	STATUS		mandatory
	DESCRIPTION	"An estimate in minutes of the time to battery charge depletion
under thepresent load conditions if the utility power is off and remains
off, or if it were to be lostand remain off."
	::= {eUpsBattery 3}

a2EstimatedChargeRemaining OBJECT-TYPE
	SYNTAX		DmiGauge
	ACCESS		read-only
	STATUS		mandatory
	DESCRIPTION	"An estimate of the time to battery charge depletion under
the present load conditions if theutility power is off and remains off, or
if it were to be lost and remain off. The valuerepresents a percent of full
charge."
	::= {eUpsBattery 4}

a2BatteryVoltage OBJECT-TYPE
	SYNTAX		DmiGauge
	ACCESS		read-only
	STATUS		mandatory
	DESCRIPTION	"The magnitude of the present battery voltage in 0.1 volts
DC."
	::= {eUpsBattery 5}

a2BatteryCurrent OBJECT-TYPE
	SYNTAX		DmiGauge
	ACCESS		read-only
	STATUS		mandatory
	DESCRIPTION	"The present battery current in 0.1 Amps DC."
	::= {eUpsBattery 6}

a2TemperatureProbeIndex OBJECT-TYPE
	SYNTAX		DmiInteger
	ACCESS		read-only
	STATUS		mandatory
	DESCRIPTION	"Index into the Temperature Probe table. This probe indicates
the ambienttemperature at or near the UPS battery casing."
	::= {eUpsBattery 7}

a2FruGroupIndex OBJECT-TYPE
	SYNTAX		DmiInteger
	ACCESS		read-only
	STATUS		mandatory
	DESCRIPTION	"If this is a Field Replaceable Unit or it is part of another
FRU, this providesan index into the FRU table; 'value = -1' indicates that
the group is not a FRU."
	::= {eUpsBattery 8}

a2OperationalGroupIndex OBJECT-TYPE
	SYNTAX		DmiInteger
	ACCESS		read-only
	STATUS		mandatory
	DESCRIPTION	"The index into the Operational State table for this device."
	::= {eUpsBattery 9}

STemperatureProbe ::= SEQUENCE {
	a3TemperatureProbeTableIndex            	DmiInteger,
	a3TemperatureProbeLocation              	DmiInteger,
	a3TemperatureProbeDescription           	DmiDisplaystring,
	a3TemperatureStatus                     	DmiInteger,
	a3TemperatureProbeTemperatureReading    	DmiInteger,
	a3MonitoredTemperatureNominalReading    	DmiInteger,
	a3MonitoredTemperatureNormalMaximum     	DmiInteger,
	a3MonitoredTemperatureNormalMinimum     	DmiInteger,
	a3TemperatureProbeMaximum               	DmiInteger,
	a3TemperatureProbeMinimum               	DmiInteger,
	a3TemperatureReadingLowerThreshold-Non-c	DmiInteger,
	a3TemperatureReadingUpperThreshold-Non-c	DmiInteger,
	a3TemperatureReadingLowerThreshold-Criti	DmiInteger,
	a3TemperatureReadingUpperThreshold-Criti	DmiInteger,
	a3TemperatureReadingLowerThreshold-Non-r	DmiInteger,
	a3TemperatureReadingUpperThreshold-Non-r	DmiInteger,
	a3TemperatureProbeResolution            	DmiInteger,
	a3TemperatureProbeTolerance             	DmiInteger,
	a3TemperatureProbeAccuracy              	DmiInteger,
	a3FruGroupIndex1                        	DmiInteger,
	a3OperationalGroupIndex1                	DmiInteger
}

tTemperatureProbe OBJECT-TYPE
	SYNTAX		SEQUENCE OF STemperatureProbe
	ACCESS		not-accessible
	STATUS		mandatory
	DESCRIPTION	"This group defines the attributes for the temperature probes
in thissystem."
	::= {dmtfGroups 3}

eTemperatureProbe OBJECT-TYPE
	SYNTAX		STemperatureProbe
	ACCESS		not-accessible
	STATUS		mandatory
	DESCRIPTION	""
	INDEX		{DmiComponentIndex}
	::= {tTemperatureProbe 1}

a3TemperatureProbeTableIndex OBJECT-TYPE
	SYNTAX		DmiInteger
	ACCESS		read-only
	STATUS		mandatory
	DESCRIPTION	"Index into this temperature probe table."
	::= {eTemperatureProbe 1}

a3TemperatureProbeLocation OBJECT-TYPE
	SYNTAX		INTEGER {
		vOther                                  	(1),
		vUnknown                                	(2),
		vProcessor                              	(3),
		vDisk                                   	(4),
		vPeripheralBay                          	(5),
		vSmbMaster                              	(6),
		vMotherboard                            	(7),
		vMemoryModule                           	(8),
		vProcessorModule                        	(9),
		vPowerUnit                              	(10),
		vAdd-inCard                             	(11)
	}
	ACCESS		read-only
	STATUS		mandatory
	DESCRIPTION	"Identifies the physical location of the temperature probe."
	::= {eTemperatureProbe 2}

a3TemperatureProbeDescription OBJECT-TYPE
	SYNTAX		DmiDisplaystring
	ACCESS		read-only
	STATUS		mandatory
	DESCRIPTION	"Additional descriptive information about the temperature
probe orprobe's location."
	::= {eTemperatureProbe 3}

a3TemperatureStatus OBJECT-TYPE
	SYNTAX		INTEGER {
		vOther                                  	(1),
		vUnknown                                	(2),
		vOk                                     	(3),
		vNon-critical                           	(4),
		vCritical                               	(5),
		vNon-recoverable                        	(6)
	}
	ACCESS		read-only
	STATUS		mandatory
	DESCRIPTION	"Defines the status of the temperature monitored by this temperat
reprobe."
	::= {eTemperatureProbe 4}

a3TemperatureProbeTemperatureReading OBJECT-TYPE
	SYNTAX		DmiInteger
	ACCESS		read-only
	STATUS		mandatory
	DESCRIPTION	"The present temperature reading of this temperature probe
in 1/10th degrees C. 0x8000000 denotes 'unknown' or 'unsupported'."
	::= {eTemperatureProbe 5}

a3MonitoredTemperatureNominalReading OBJECT-TYPE
	SYNTAX		DmiInteger
	ACCESS		read-only
	STATUS		mandatory
	DESCRIPTION	"The nominal temperature reading of the temperature monitored
by this probe in 1/10th degrees C. 0x80000000 denotes 'unknown' or 'unsupported'
"
	::= {eTemperatureProbe 6}

a3MonitoredTemperatureNormalMaximum OBJECT-TYPE
	SYNTAX		DmiInteger
	ACCESS		read-only
	STATUS		mandatory
	DESCRIPTION	"The normal maximum temperature reading of the temperature
monitored by this probe in 1/10th degrees C. 0x80000000 denotes 'unknown'
or 'unsupported'."
	::= {eTemperatureProbe 7}

a3MonitoredTemperatureNormalMinimum OBJECT-TYPE
	SYNTAX		DmiInteger
	ACCESS		read-only
	STATUS		mandatory
	DESCRIPTION	"The normal minimum temperature reading of the temperature
monitored by this probe in 1/10th degrees C. 0x80000000 denotes 'unknown'
or 'unsupported'."
	::= {eTemperatureProbe 8}

a3TemperatureProbeMaximum OBJECT-TYPE
	SYNTAX		DmiInteger
	ACCESS		read-only
	STATUS		mandatory
	DESCRIPTION	"The maximum temperature reading specified to be readable
by this probe in 1/10th degrees C. 0x80000000 denotes 'unknown' or 'unsupported'
"
	::= {eTemperatureProbe 9}

a3TemperatureProbeMinimum OBJECT-TYPE
	SYNTAX		DmiInteger
	ACCESS		read-only
	STATUS		mandatory
	DESCRIPTION	"The minimum temperature reading specified to be readable
by this probe in 1/10th degrees C. 0x80000000 denotes 'unknown' or 'unsupported'
"
	::= {eTemperatureProbe 10}

a3TemperatureReadingLowerThreshold-Non-c OBJECT-TYPE
	SYNTAX		DmiInteger
	ACCESS		read-write
	STATUS		mandatory
	DESCRIPTION	"The lower non-critical threshold for the temperature reading
set by the user, in 1/10th degrees C. 0x80000000 denotes 'unknown' or 'unsupport
d'."
	::= {eTemperatureProbe 11}

a3TemperatureReadingUpperThreshold-Non-c OBJECT-TYPE
	SYNTAX		DmiInteger
	ACCESS		read-write
	STATUS		mandatory
	DESCRIPTION	"The upper non-critical threshold for the temperature probe,
in 1/10th degrees C. 0x80000000 denotes 'unknown' or 'unsupported'."
	::= {eTemperatureProbe 12}

a3TemperatureReadingLowerThreshold-Criti OBJECT-TYPE
	SYNTAX		DmiInteger
	ACCESS		read-write
	STATUS		mandatory
	DESCRIPTION	"The lower critical threshold for the temperature probe, in
1/10 degrees C. 0x80000000 denotes 'unknown' or 'unsupported'."
	::= {eTemperatureProbe 13}

a3TemperatureReadingUpperThreshold-Criti OBJECT-TYPE
	SYNTAX		DmiInteger
	ACCESS		read-write
	STATUS		mandatory
	DESCRIPTION	"The upper critical threshold for the temperature probe, in
/10th degrees C. 0x80000000 denotes 'unknown' or 'unsupported'."
	::= {eTemperatureProbe 14}

a3TemperatureReadingLowerThreshold-Non-r OBJECT-TYPE
	SYNTAX		DmiInteger
	ACCESS		read-write
	STATUS		mandatory
	DESCRIPTION	"The lower non-recoverable threshold for the temperature probe,
in 1/10th degrees C. 0x80000000 denotes 'unknown' or 'unsupported'."
	::= {eTemperatureProbe 15}

a3TemperatureReadingUpperThreshold-Non-r OBJECT-TYPE
	SYNTAX		DmiInteger
	ACCESS		read-write
	STATUS		mandatory
	DESCRIPTION	"The upper non-recoverable threshold for the temperature probe,
in 1/10th degrees C. 0x80000000 denotes 'unknown' or 'unsupported'."
	::= {eTemperatureProbe 16}

a3TemperatureProbeResolution OBJECT-TYPE
	SYNTAX		DmiInteger
	ACCESS		read-write
	STATUS		mandatory
	DESCRIPTION	"The resolution for the reading from this temperature probe,
in tenths of 1/10th degrees C. '0x80000000 denotes 'unknown' or 'unsupported'."
	::= {eTemperatureProbe 17}

a3TemperatureProbeTolerance OBJECT-TYPE
	SYNTAX		DmiInteger
	ACCESS		read-write
	STATUS		mandatory
	DESCRIPTION	"The tolerance for the reading from this temperature probe,
in plus/minus 1/10 degrees C. 0x80000000 denotes 'unknown' or 'unsupported'."
	::= {eTemperatureProbe 18}

a3TemperatureProbeAccuracy OBJECT-TYPE
	SYNTAX		DmiInteger
	ACCESS		read-write
	STATUS		mandatory
	DESCRIPTION	"The accuracy for the reading from this temperature probe,
in plus/minus hundredths of a percent. 0x80000000 denotes 'unknown' or 'unsuppor
ed'."
	::= {eTemperatureProbe 19}

a3FruGroupIndex OBJECT-TYPE
	SYNTAX		DmiInteger
	ACCESS		read-only
	STATUS		mandatory
	DESCRIPTION	"Index into the FRU table. A value of -1 indicates that this
device is not an FRU."
	::= {eTemperatureProbe 20}

a3OperationalGroupIndex OBJECT-TYPE
	SYNTAX		DmiInteger
	ACCESS		read-only
	STATUS		mandatory
	DESCRIPTION	"Index into the Operational State table"
	::= {eTemperatureProbe 21}

SOperationalStateTable ::= SEQUENCE {
	a4OperationalStateInstanceIndex         	DmiInteger,
	a4DeviceGroupIndex                      	DmiInteger,
	a4OperationalStatus                     	DmiInteger,
	a4UsageState                            	DmiInteger,
	a4AvailabilityStatus                    	DmiInteger,
	a4AdministrativeState                   	DmiInteger,
	a4FatalErrorCount                       	DmiCounter,
	a4MajorErrorCount                       	DmiCounter,
	a4WarningErrorCount                     	DmiCounter,
	a4CurrentErrorStatus                    	DmiInteger
}

tOperationalStateTable OBJECT-TYPE
	SYNTAX		SEQUENCE OF SOperationalStateTable
	ACCESS		not-accessible
	STATUS		mandatory
	DESCRIPTION	"This group provides the operational state, usage, and availabili
y status,and administrative state indicators for specific Device Group instances
"
	::= {dmtfGroups 4}

eOperationalStateTable OBJECT-TYPE
	SYNTAX		SOperationalStateTable
	ACCESS		not-accessible
	STATUS		mandatory
	DESCRIPTION	""
	INDEX		{DmiComponentIndex, a4OperationalStateInstanceIndex}
	::= {tOperationalStateTable 1}

a4OperationalStateInstanceIndex OBJECT-TYPE
	SYNTAX		DmiInteger
	ACCESS		read-only
	STATUS		mandatory
	DESCRIPTION	"The Index into the Operational State table."
	::= {eOperationalStateTable 1}

a4DeviceGroupIndex OBJECT-TYPE
	SYNTAX		DmiInteger
	ACCESS		read-only
	STATUS		mandatory
	DESCRIPTION	"The group ID of the group referencing this instance."
	::= {eOperationalStateTable 2}

a4OperationalStatus OBJECT-TYPE
	SYNTAX		INTEGER {
		vOther                                  	(1),
		vUnknown                                	(2),
		vEnabled                                	(3),
		vDisabled                               	(4),
		vNotApplicable                          	(5)
	}
	ACCESS		read-only
	STATUS		mandatory
	DESCRIPTION	"The operational status of the Device Group instance."
	::= {eOperationalStateTable 3}

a4UsageState OBJECT-TYPE
	SYNTAX		INTEGER {
		vOther                                  	(1),
		vUnknown                                	(2),
		vIdle                                   	(3),
		vActive                                 	(4),
		vBusy                                   	(5),
		vNotApplicable                          	(6)
	}
	ACCESS		read-only
	STATUS		mandatory
	DESCRIPTION	"The usage state of the Device Group instance."
	::= {eOperationalStateTable 4}

a4AvailabilityStatus OBJECT-TYPE
	SYNTAX		INTEGER {
		vOther                                  	(1),
		vUnknown                                	(2),
		vRunning                                	(3),
		vWarning                                	(4),
		vInTest                                 	(5),
		vNotApplicable                          	(6),
		vPowerOff                               	(7),
		vOffLine                                	(8),
		vOffDuty                                	(9),
		vDegraded                               	(10),
		vNotInstalled                           	(11),
		vInstallError                           	(12),
		vPowerSave                              	(13)
	}
	ACCESS		read-only
	STATUS		mandatory
	DESCRIPTION	"The availability status of the Device Group instance."
	::= {eOperationalStateTable 5}

a4AdministrativeState OBJECT-TYPE
	SYNTAX		INTEGER {
		vOther                                  	(1),
		vUnknown                                	(2),
		vLocked                                 	(3),
		vUnlocked                               	(4),
		vNotApplicable                          	(5),
		vShuttingDown                           	(6)
	}
	ACCESS		read-only
	STATUS		mandatory
	DESCRIPTION	"The administrative state of the Device Group instance."
	::= {eOperationalStateTable 6}

a4FatalErrorCount OBJECT-TYPE
	SYNTAX		DmiCounter
	ACCESS		read-only
	STATUS		mandatory
	DESCRIPTION	"The accumulated Fatal or Non-recoverable error count for
this DeviceGroup instance."
	::= {eOperationalStateTable 7}

a4MajorErrorCount OBJECT-TYPE
	SYNTAX		DmiCounter
	ACCESS		read-only
	STATUS		mandatory
	DESCRIPTION	"The accumulated Major or Critical error count for this Device
Groupinstance."
	::= {eOperationalStateTable 8}

a4WarningErrorCount OBJECT-TYPE
	SYNTAX		DmiCounter
	ACCESS		read-only
	STATUS		mandatory
	DESCRIPTION	"The accumulated Warning or Non-Critical error count for this
DeviceGroup instance."
	::= {eOperationalStateTable 9}

a4CurrentErrorStatus OBJECT-TYPE
	SYNTAX		INTEGER {
		vOther                                  	(1),
		vUnknown                                	(2),
		vOk                                     	(3),
		vNon-critical                           	(4),
		vCritical                               	(5),
		vNon-recoverable                        	(6)
	}
	ACCESS		read-only
	STATUS		mandatory
	DESCRIPTION	"This attribute presents the current error status for this
Device Groupinstance. The most critical error status in effect should be
presented. I.e. if a part of theDevice Group instance is 'Critical', while
other status is 'Non-critical' then the status'Critical' should be reported."
	::= {eOperationalStateTable 10}

SDiagnostics ::= SEQUENCE {
	a5DiagnosticFunctionTableIndex          	DmiInteger,
	a5DiagnosticFunctionName                	DmiDisplaystring,
	a5DiagnosticFunctionDescription         	DmiDisplaystring,
	a5ExclusiveAccessRequired               	DmiInteger,
	a5PrerequisiteConditions                	DmiInteger,
	a5PrerequisiteDiagnosticFunction        	DmiInteger
}

tDiagnostics OBJECT-TYPE
	SYNTAX		SEQUENCE OF SDiagnostics
	ACCESS		not-accessible
	STATUS		mandatory
	DESCRIPTION	"This group defines the diagnostic functions that are provided
by thiscomponent for analyzing potential failures within the component. A
diagnosticfunction could be an actual test run against the component, the
results of a self-test ofthe component, an analysis of failure information
captured during a failure of thecomponent, or an analysis of the current
state of the component. "
	::= {dmtfGroups 5}

eDiagnostics OBJECT-TYPE
	SYNTAX		SDiagnostics
	ACCESS		not-accessible
	STATUS		mandatory
	DESCRIPTION	""
	INDEX		{DmiComponentIndex, a5DiagnosticFunctionTableIndex}
	::= {tDiagnostics 1}

a5DiagnosticFunctionTableIndex OBJECT-TYPE
	SYNTAX		DmiInteger
	ACCESS		read-only
	STATUS		mandatory
	DESCRIPTION	"A unique identifier for this specific diagnostic function.
"
	::= {eDiagnostics 1}

a5DiagnosticFunctionName OBJECT-TYPE
	SYNTAX		DmiDisplaystring
	ACCESS		read-only
	STATUS		mandatory
	DESCRIPTION	"A specific descriptive name of the diagnostic function, includin
 versioninformation, if relevant. "
	::= {eDiagnostics 2}

a5DiagnosticFunctionDescription OBJECT-TYPE
	SYNTAX		DmiDisplaystring
	ACCESS		read-only
	STATUS		mandatory
	DESCRIPTION	"A description of what this diagnostic function does. "
	::= {eDiagnostics 3}

a5ExclusiveAccessRequired OBJECT-TYPE
	SYNTAX		INTEGER {
		vFalse                                  	(0),
		vTrue                                   	(1)
	}
	ACCESS		read-only
	STATUS		mandatory
	DESCRIPTION	"Indicates whether this diagnostic function requires exclusive
access tothe device or component, implying that the user or management applicati
n must takesome action within the operating system to ensure that the device
or component cannotbe used by any other function. "
	::= {eDiagnostics 4}

a5PrerequisiteConditions OBJECT-TYPE
	SYNTAX		INTEGER {
		vOther                                  	(1),
		vUnknown                                	(2),
		vNoPrerequisites                        	(3),
		vWrapPlugInstalled                      	(4),
		vNoMediaInstalled                       	(5),
		vScratchMediaInstalled                  	(6),
		vTestMediaInstalled                     	(7),
		vSystemReferenceDisketteInstalled       	(8)
	}
	ACCESS		read-only
	STATUS		mandatory
	DESCRIPTION	"Indicates what conditions must be met before this diagnostic
functioncan be run. "
	::= {eDiagnostics 5}

a5PrerequisiteDiagnosticFunction OBJECT-TYPE
	SYNTAX		DmiInteger
	ACCESS		read-only
	STATUS		mandatory
	DESCRIPTION	"If non-0, this specifies the ID of another diagnostic function
that must berun immediately prior to this one. "
	::= {eDiagnostics 6}

SDiagnosticRequestGroup ::= SEQUENCE {
	a6DiagnosticFunctionReserveKey          	DmiInteger,
	a6DiagnosticFunctionRequest             	DmiInteger,
	a6DiagnosticFunctionResult              	DmiInteger
}

tDiagnosticRequestGroup OBJECT-TYPE
	SYNTAX		SEQUENCE OF SDiagnosticRequestGroup
	ACCESS		not-accessible
	STATUS		mandatory
	DESCRIPTION	"This group defines the attributes which a management application
usesto request an actual diagnostic analysis. "
	::= {dmtfGroups 6}

eDiagnosticRequestGroup OBJECT-TYPE
	SYNTAX		SDiagnosticRequestGroup
	ACCESS		not-accessible
	STATUS		mandatory
	DESCRIPTION	""
	INDEX		{DmiComponentIndex}
	::= {tDiagnosticRequestGroup 1}

a6DiagnosticFunctionReserveKey OBJECT-TYPE
	SYNTAX		DmiInteger
	ACCESS		read-write
	STATUS		mandatory
	DESCRIPTION	"Indicates whether the interface to this component's diagnostic
functionsis reserved. A zero value returned on a get indicates that a reserve
is already in effect. A non-zero value indicates that no reserve was in effect,
and the returned value may beused as a reserve key. "
	::= {eDiagnosticRequestGroup 1}

a6DiagnosticFunctionRequest OBJECT-TYPE
	SYNTAX		DmiInteger
	ACCESS		read-write
	STATUS		mandatory
	DESCRIPTION	"The ID of the specific diagnostic function which is being
requested. Ifthe interface is reserved, a set request to this attribute should
also set the DiagnosticFunction Reserve Key with the reserve key value. "
	::= {eDiagnosticRequestGroup 2}

a6DiagnosticFunctionResult OBJECT-TYPE
	SYNTAX		DmiInteger
	ACCESS		read-only
	STATUS		mandatory
	DESCRIPTION	"The integer-based result code of the last diagnostic function
run. "
	::= {eDiagnosticRequestGroup 3}

SDiagnosticResults ::= SEQUENCE {
	a7DiagnosticFunctionId                  	DmiInteger,
	a7DiagnosticFunctionResult              	DmiInteger,
	a7DiagnosticFunctionResultDescription   	DmiDisplaystring,
	a7FaultIsolatedToThisComponent          	DmiInteger
}

tDiagnosticResults OBJECT-TYPE
	SYNTAX		SEQUENCE OF SDiagnosticResults
	ACCESS		not-accessible
	STATUS		mandatory
	DESCRIPTION	"This group defines the attributes for interpreting diagnostic
functionresult codes. "
	::= {dmtfGroups 7}

eDiagnosticResults OBJECT-TYPE
	SYNTAX		SDiagnosticResults
	ACCESS		not-accessible
	STATUS		mandatory
	DESCRIPTION	""
	INDEX		{DmiComponentIndex, a7DiagnosticFunctionId, a7DiagnosticFunctionResult}
	::= {tDiagnosticResults 1}

a7DiagnosticFunctionId OBJECT-TYPE
	SYNTAX		DmiInteger
	ACCESS		read-only
	STATUS		mandatory
	DESCRIPTION	"The unique ID for a specific diagnostic function. "
	::= {eDiagnosticResults 1}

a7DiagnosticFunctionResult OBJECT-TYPE
	SYNTAX		DmiInteger
	ACCESS		read-only
	STATUS		mandatory
	DESCRIPTION	"An integer-based result code of the diagnostic function.
"
	::= {eDiagnosticResults 2}

a7DiagnosticFunctionResultDescription OBJECT-TYPE
	SYNTAX		DmiDisplaystring
	ACCESS		read-only
	STATUS		mandatory
	DESCRIPTION	"A description of what this result code for this diagnostic
functionmeans, including suggested corrective actions, where possible. "
	::= {eDiagnosticResults 3}

a7FaultIsolatedToThisComponent OBJECT-TYPE
	SYNTAX		INTEGER {
		vFalse                                  	(0),
		vTrue                                   	(1)
	}
	ACCESS		read-only
	STATUS		mandatory
	DESCRIPTION	"An indicator of whether the fault is strictly isolated within
the bounds ofthis component. A False value indicates that the fault might
be caused by a failingparent component; for example, a disk test may fail
because of a faulty disk controller. "
	::= {eDiagnosticResults 4}

SErrorControlGroup ::= SEQUENCE {
	a8Selfid                                	DmiInteger,
	a8NumberOfFatalErrors                   	DmiCounter,
	a8NumberOfMajorErrors                   	DmiCounter,
	a8NumberOfWarnings                      	DmiCounter,
	a8ErrorStatus                           	DmiInteger,
	a8ErrorStatusType                       	DmiInteger,
	a8AlarmGeneration                       	DmiInteger
}

tErrorControlGroup OBJECT-TYPE
	SYNTAX		SEQUENCE OF SErrorControlGroup
	ACCESS		not-accessible
	STATUS		mandatory
	DESCRIPTION	"Indication control and status for the parent group."
	::= {dmtfGroups 8}

eErrorControlGroup OBJECT-TYPE
	SYNTAX		SErrorControlGroup
	ACCESS		not-accessible
	STATUS		mandatory
	DESCRIPTION	""
	INDEX		{DmiComponentIndex}
	::= {tErrorControlGroup 1}

a8Selfid OBJECT-TYPE
	SYNTAX		DmiInteger
	ACCESS		read-only
	STATUS		mandatory
	DESCRIPTION	"Instance id. A unique number that identifies this row."
	::= {eErrorControlGroup 1}

a8NumberOfFatalErrors OBJECT-TYPE
	SYNTAX		DmiCounter
	ACCESS		read-only
	STATUS		mandatory
	DESCRIPTION	"Count of all fatal errors since system startup."
	::= {eErrorControlGroup 2}

a8NumberOfMajorErrors OBJECT-TYPE
	SYNTAX		DmiCounter
	ACCESS		read-only
	STATUS		mandatory
	DESCRIPTION	"Count of all major errors since system startup."
	::= {eErrorControlGroup 3}

a8NumberOfWarnings OBJECT-TYPE
	SYNTAX		DmiCounter
	ACCESS		read-only
	STATUS		mandatory
	DESCRIPTION	"Count of all warning errors since system startup."
	::= {eErrorControlGroup 4}

a8ErrorStatus OBJECT-TYPE
	SYNTAX		INTEGER {
		vOk                                     	(0),
		vWarning	                               	(1),
		vMajor                                  	(2),
		vFatal                                  	(3)
	}
	ACCESS		read-only
	STATUS		mandatory
	DESCRIPTION	"current error status"
	::= {eErrorControlGroup 5}

a8ErrorStatusType OBJECT-TYPE
	SYNTAX		INTEGER {
		vPost                                   	(0),
		vRuntime                                	(1),
		vDiagnosticTest                         	(2)
	}
	ACCESS		read-only
	STATUS		mandatory
	DESCRIPTION	"Indicates the type of detection that set the current error
status."
	::= {eErrorControlGroup 6}

a8AlarmGeneration OBJECT-TYPE
	SYNTAX		INTEGER {
		vOff                                    	(0),
		vOn                                     	(1)
	}
	ACCESS		read-write
	STATUS		mandatory
	DESCRIPTION	"Controls indication generation for errors."
	::= {eErrorControlGroup 7}

SMiftomib ::= SEQUENCE {
	a99MibName                              	DmiDisplaystring,
	a99MibOid                               	DmiDisplaystring,
	a99DisableTrap                          	DmiInteger
}

tMiftomib OBJECT-TYPE
	SYNTAX		SEQUENCE OF SMiftomib
	ACCESS		not-accessible
	STATUS		mandatory
	DESCRIPTION	"This group defines attributes required for DMI to
SNMP translati
n."
	::= {dmtfGroups 99}

eMiftomib OBJECT-TYPE
	SYNTAX		SMiftomib
	ACCESS		not-accessible
	STATUS		mandatory
	DESCRIPTION	""
	INDEX		{DmiComponentIndex}
	::= {tMiftomib 1}

a99MibName OBJECT-TYPE
	SYNTAX		DmiDisplaystring
	ACCESS		read-only
	STATUS		mandatory
	DESCRIPTION	"The MIB name that defines this MIF"
	::= {eMiftomib 1}

a99MibOid OBJECT-TYPE
	SYNTAX		DmiDisplaystring
	ACCESS		read-only
	STATUS		mandatory
	DESCRIPTION	"The MIB Object Identifier that corresponds to this MIF"
	::= {eMiftomib 2}

a99DisableTrap OBJECT-TYPE
	SYNTAX		DmiInteger
	ACCESS		read-write
	STATUS		mandatory
	DESCRIPTION	"This attribute can be changed to disable sending oftraps
from this component"
	::= {eMiftomib 3}


-- Here is the TRAP definition for the MIB
-- Append this to the MIB produced by MIFTOMIB
-- DO NOT CHANGE ANYTHING in this definition, SNMP-DMI translator only
--         handles this specific format of the TRAP
-- changing this format WILL cause trnaslator to fail

tTrapGroup OBJECT-TYPE
    SYNTAX        SEQUENCE OF STrapGroup
    ACCESS        not-accessible
    STATUS        mandatory
    DESCRIPTION    "This group defines attributes needed for Trap
            definition. This group does not exist in MIF file"
    ::= {dmtfGroups 9999}

STrapGroup ::= SEQUENCE {
    a9999ErrorTime              DisplayString,
    a9999ErrorStatus            DmiInteger,
    a9999ErrorGroupId           DmiInteger,
    a9999ErrorInstanceId        DmiInteger,
    a9999ComponentId            DmiInteger,
    a9999GroupId                DmiInteger,
    a9999InstanceId             DmiInteger,
    a9999VendorCode1            DmiInteger,
    a9999VendorCode2            DmiInteger,
    a9999VendorText             OCTET STRING,
    a9999ParentGroupId          DmiInteger,
    a9999ParentInstanceId       DmiInteger
}

eTrapGroup OBJECT-TYPE
    SYNTAX        STrapGroup
    ACCESS        not-accessible
    STATUS        mandatory
    DESCRIPTION    ""
    INDEX        {DmiComponentIndex}
    ::= {tTrapGroup 1}

a9999ErrorTime OBJECT-TYPE
    SYNTAX        DisplayString
    ACCESS        read-only
    STATUS        mandatory
    DESCRIPTION    "The Date & Time when the error occured"
    ::= {eTrapGroup 1}

a9999ErrorStatus OBJECT-TYPE
    SYNTAX        DmiInteger
    ACCESS        read-only
    STATUS        mandatory
    DESCRIPTION    "Error Status Code"
    ::= {eTrapGroup 2}

a9999ErrorGroupId OBJECT-TYPE
    SYNTAX        DmiInteger
    ACCESS        read-only
    STATUS        mandatory
    DESCRIPTION    "Group ID of the errorControl Group"
    ::= {eTrapGroup 3}

a9999ErrorInstanceId OBJECT-TYPE
    SYNTAX        DmiInteger
    ACCESS        read-only
    STATUS        mandatory
    DESCRIPTION    "Instance ID of the errorControl Group"
    ::= {eTrapGroup 4}

a9999ComponentId OBJECT-TYPE
    SYNTAX        DmiInteger
    ACCESS        read-only
    STATUS        mandatory
    DESCRIPTION    "Component ID of the component that caused this error"
    ::= {eTrapGroup 5}

a9999GroupId OBJECT-TYPE
    SYNTAX        DmiInteger
    ACCESS        read-only
    STATUS        mandatory
    DESCRIPTION    "Group ID of the Group that caused this error"
    ::= {eTrapGroup 6}

a9999InstanceId OBJECT-TYPE
    SYNTAX        DmiInteger
    ACCESS        read-only
    STATUS        mandatory
    DESCRIPTION    "Instance ID of the Group that caused this error"
    ::= {eTrapGroup 7}

a9999VendorCode1 OBJECT-TYPE
    SYNTAX        DmiInteger
    ACCESS        read-only
    STATUS        mandatory
    DESCRIPTION    "Vendor specific code 1"
    ::= {eTrapGroup 8}

a9999VendorCode2 OBJECT-TYPE
    SYNTAX        DmiInteger
    ACCESS        read-only
    STATUS        mandatory
    DESCRIPTION    "Vendor specific code 2"
    ::= {eTrapGroup 9}

a9999VendorText OBJECT-TYPE
    SYNTAX        OCTET STRING
    ACCESS        read-only
    STATUS        mandatory
    DESCRIPTION    "Vendor specific octet string info"
    ::= {eTrapGroup 10}

a9999ParentGroupId OBJECT-TYPE
    SYNTAX        DmiInteger
    ACCESS        read-only
    STATUS        mandatory
    DESCRIPTION    "Group ID of parent of Group that caused this error"
    ::= {eTrapGroup 11}

a9999ParentInstanceId OBJECT-TYPE
    SYNTAX        DmiInteger
    ACCESS        read-only
    STATUS        mandatory
    DESCRIPTION    "Instance ID of parent of Group that caused this error"
    ::= {eTrapGroup 12}

pwrchuteEventError TRAP-TYPE
    ENTERPRISE eTrapGroup
    VARIABLES  { a9999ErrorTime,
                 a9999ErrorStatus,
                 a9999ErrorGroupId,
                 a9999ErrorInstanceId,
                 a9999ComponentId,
                 a9999GroupId,
                 a9999InstanceId,
                 a9999VendorCode1,
                 a9999VendorCode2,
                 a9999VendorText,
                 a9999ParentGroupId,
                 a9999ParentInstanceId}

    DESCRIPTION "DMI Service Layer generated event for APC UPS"

    --NMS trap annotation

    --#TYPE       "DMI APC UPS Error Event"
    --#SUMMARY    "Event Data: (%s,%d,%d,%d) (%d,%d,%d,%d,%d) (%d,%d)"
    --#ARGUMENTS  {0, 1, 2, 3, 4, 5, 6, 7, 8, 10, 11}
    --#SEVERITY   CRITICAL
    --#TIMEINDEX  12
    --#STATE      DEGRADED
    ::= 1
END
