-- ===================================================================
-- Copyright (C) 2010 by HUAWEI TECHNOLOGIES. All rights reserved.
-- Description: 
-- Reference:
-- Version: V1.01
-- ===================================================================


 HUAWEI-USA-MIB DEFINITIONS ::= BEGIN
 
        IMPORTS                                            
            OBJECT-GROUP, MODULE-COMPLIANCE, NOTIFICATION-GROUP            
                FROM SNMPv2-CONF            
            DisplayString, RowStatus,MacAddress                      
                FROM SNMPv2-TC
            TimeTicks, Integer32, Unsigned32, IpAddress, Counter32, OBJECT-TYPE, 
            MODULE-IDENTITY, NOTIFICATION-TYPE            
                FROM SNMPv2-SMI  
            EnabledStatus
                FROM P-BRIDGE-MIB   
            hwBRASMib            
                FROM HUAWEI-MIB;
    
    
        hwUSA MODULE-IDENTITY 
            LAST-UPDATED "201008111600Z"        
            ORGANIZATION 
                  "Huawei Technologies Co.,Ltd."
            CONTACT-INFO 
                  "Huawei Industrial Base
  Bantian, Longgang
   Shenzhen 518129
   People's Republic of China
   Website: http://www.huawei.com
   Email: support@huawei.com
 "
            DESCRIPTION 
                "Please provide the descritpion."
            REVISION    "201008111600Z"   
            DESCRIPTION "V1.00, initial version."

            REVISION    "201009111600Z"   
            DESCRIPTION "V1.01, initial version."

    
            ::= { hwBRASMib 20 }



        
        hwUSAObjects  OBJECT IDENTIFIER ::= { hwUSA  1 }
                                        
        hwUSAConfigTable OBJECT-TYPE
            SYNTAX SEQUENCE OF HwUSAConfigEntry
            MAX-ACCESS not-accessible
            STATUS current
            DESCRIPTION
                "The table describes USA configuration."
            ::= { hwUSAObjects  1 }
        
        hwUSAConfigEntry OBJECT-TYPE
            SYNTAX HwUSAConfigEntry
            MAX-ACCESS not-accessible
            STATUS current
            DESCRIPTION
                "Description."
            INDEX { hwUSAPortIndex }
            ::= { hwUSAConfigTable 1 }
           
        
        HwUSAConfigEntry ::=
            SEQUENCE { 
                hwUSAPortIndex
                    Integer32,
                hwUSAInterfaceName
                    DisplayString,
                hwAuthenAccessPoint
                    EnabledStatus
                      }
         
        hwUSAPortIndex OBJECT-TYPE
            SYNTAX Integer32(1..32767)
            MAX-ACCESS read-only
            STATUS current
            DESCRIPTION
                "USC Portindex."
            ::= { hwUSAConfigEntry 1 } 
            
        hwUSAInterfaceName OBJECT-TYPE
            SYNTAX DisplayString (SIZE (1..64))
            MAX-ACCESS read-write
            STATUS current
            DESCRIPTION
                "The URL of portal."
            ::= { hwUSAConfigEntry 2 } 
            
        hwAuthenAccessPoint OBJECT-TYPE
            SYNTAX EnabledStatus
            MAX-ACCESS read-write
            STATUS current
            DESCRIPTION
                "authentication access-point. disable:2 , enable:1 "      
            DEFVAL { disable }
            ::= { hwUSAConfigEntry 3 }
         
            
        
         hwAssociateUserTable OBJECT-TYPE
            SYNTAX SEQUENCE OF HwAssociateUserEntry
            MAX-ACCESS not-accessible
            STATUS current
            DESCRIPTION
                "The table describes USA configuration."
            ::= { hwUSAObjects  2 }
        
        hwAssociateUserEntry OBJECT-TYPE
            SYNTAX HwAssociateUserEntry
            MAX-ACCESS not-accessible
            STATUS current
            DESCRIPTION
                "Associate table of users"
            INDEX { hwAssociateUserIndex }
            ::= { hwAssociateUserTable 1 }
        
        HwAssociateUserEntry ::=
            SEQUENCE {
                    hwAssociateUserIndex
                    Integer32,
            		hwAssociateUserMac
                    MacAddress,
                    hwAssociateUserIp
                    IpAddress,
                    hwAssociateUserStates
                    INTEGER,
                    hwAssociateType
                    INTEGER
                    }
        hwAssociateUserIndex OBJECT-TYPE
            SYNTAX Integer32(0..32767)
            MAX-ACCESS read-only
            STATUS current
            DESCRIPTION
                "hwAssociateUserIndex"
            ::= { hwAssociateUserEntry 1 }
            
        hwAssociateUserMac OBJECT-TYPE
            SYNTAX MacAddress
            MAX-ACCESS read-only
            STATUS current
            DESCRIPTION
                "AssociateUser mac."
            ::= { hwAssociateUserEntry 2 } 

        hwAssociateUserIp OBJECT-TYPE
            SYNTAX IpAddress
            MAX-ACCESS read-only
            STATUS current
            DESCRIPTION
                "AssociateUser ip."
            ::= { hwAssociateUserEntry 3 } 

        hwAssociateUserStates OBJECT-TYPE
            SYNTAX INTEGER
            {   
              idle(0),
              associated(1),
              up(2)
            }
            MAX-ACCESS read-only
            STATUS current
            DESCRIPTION
                "AssociateUser status : 0 - IDLE, 1 - ASSOCIATED, 2 - UP"
            ::= { hwAssociateUserEntry 4 } 
        
        hwAssociateType OBJECT-TYPE
            SYNTAX INTEGER
            {   
              arp(0),
              dot1x(1),
              dhcp(2),
              http(3)
            }
            MAX-ACCESS read-only
            STATUS current
            DESCRIPTION
                "AssociateUser type : 0 -arp,1 - dot1x, 2 - dhcp, 3 - http"
            ::= { hwAssociateUserEntry 5 }
            
                                
        hwUserDetectInterval  OBJECT-TYPE
            SYNTAX     Integer32(1..65535)
            MAX-ACCESS read-write
            STATUS current
            DESCRIPTION
                "The Global user detect interval.default : 15"           
            ::= { hwUSAObjects  3 }
        
        hwUserDetectRetry   OBJECT-TYPE
            SYNTAX     Integer32(1..255)
            MAX-ACCESS read-write
            STATUS current
            DESCRIPTION
                "The Global detect retry times.default : 3"          
            ::= { hwUSAObjects  4 }      
        
        hwUserSyncInterval     OBJECT-TYPE
            SYNTAX     Integer32(60..3600)
            MAX-ACCESS read-write
            STATUS current
            DESCRIPTION
                "The Global user sync interval.default : 60"          
            ::= { hwUSAObjects  5 }   
        
        hwGlobalLinkDownOffline  OBJECT-TYPE
            SYNTAX     Integer32(0..65535)
            MAX-ACCESS read-write
            STATUS current
            DESCRIPTION
                "The Global port link-down offline.default : 0"           
            ::= { hwUSAObjects  6 }  
        
        hwGlobalControlDownOffline   OBJECT-TYPE
            SYNTAX     Integer32(0..65535)
            MAX-ACCESS read-write
            STATUS current
            DESCRIPTION
                "The Global port control-down offline.default : 0"          
            ::= { hwUSAObjects  7 }
        
        hwAuthenSpeedLimitMaxNum  OBJECT-TYPE
            SYNTAX     Integer32(1..65535)
            MAX-ACCESS read-write
            STATUS current
            DESCRIPTION
                "The Global authentication speed limit max-num.default : 60"           
            ::= { hwUSAObjects  8 }
        
        hwAuthenSpeedLimitInterval   OBJECT-TYPE
            SYNTAX     Integer32(1..65535)
            MAX-ACCESS read-write
            STATUS current
            DESCRIPTION
                "The Global authentication limit interval.default : 30"          
            ::= { hwUSAObjects  9 }
                  
        END
