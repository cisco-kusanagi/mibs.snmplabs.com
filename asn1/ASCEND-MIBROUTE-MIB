--			Ascend mibroute MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBROUTE-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibrouteProfile  OBJECT IDENTIFIER ::= { configuration 105}

	-- The mibrouteProfile table
	--
	-- This table contains parameters for the mibrouteProfile profile
	--

    mibrouteProfileTable	OBJECT-TYPE
	SYNTAX		SEQUENCE OF MibrouteProfileEntry
	ACCESS		not-accessible
	STATUS		mandatory
	DESCRIPTION	"A list of mibrouteProfile profile entries."
	::= { mibrouteProfile 1 }

    mibrouteProfileEntry	OBJECT-TYPE
	SYNTAX		MibrouteProfileEntry
	ACCESS		not-accessible
	STATUS		mandatory
	DESCRIPTION	"A mibrouteProfile entry containing objects that
			 maps to the parameters of mibrouteProfile profile."
	INDEX		{ routeProfile-Name }
	::= { mibrouteProfileTable 1 }

    MibrouteProfileEntry ::=
	SEQUENCE {
	    routeProfile-Name
		DisplayString,
	    routeProfile-DestAddress
		IpAddress,
	    routeProfile-Netmask
		IpAddress,
	    routeProfile-GatewayAddress
		IpAddress,
	    routeProfile-Metric
		INTEGER,
	    routeProfile-Cost
		INTEGER,
	    routeProfile-Preference
		INTEGER,
	    routeProfile-ThirdParty
		INTEGER,
	    routeProfile-AseType
		INTEGER,
	    routeProfile-AseTag
		DisplayString,
	    routeProfile-PrivateRoute
		INTEGER,
	    routeProfile-ActiveRoute
		INTEGER,
	    routeProfile-Ase7Adv
		INTEGER,
	    routeProfile-Vrouter
		DisplayString,
	    routeProfile-InterVrouter
		DisplayString,
	    routeProfile-Action-o
		INTEGER
	}

    routeProfile-Name	OBJECT-TYPE
	SYNTAX	DisplayString
	ACCESS	read-only
	STATUS	mandatory
	DESCRIPTION	"The name of this route."
	::= { mibrouteProfileEntry 1 }

    routeProfile-DestAddress	OBJECT-TYPE
	SYNTAX	IpAddress
	ACCESS	read-write
	STATUS	mandatory
	DESCRIPTION	"The IP address of the destination network or subnet. An address of 0.0.0.0 indicates a default route."
	::= { mibrouteProfileEntry 2 }

    routeProfile-Netmask	OBJECT-TYPE
	SYNTAX	IpAddress
	ACCESS	read-write
	STATUS	mandatory
	DESCRIPTION	"The netmask to be used for the destination."
	::= { mibrouteProfileEntry 16 }

    routeProfile-GatewayAddress	OBJECT-TYPE
	SYNTAX	IpAddress
	ACCESS	read-write
	STATUS	mandatory
	DESCRIPTION	"The address of the gateway/router for this static route."
	::= { mibrouteProfileEntry 3 }

    routeProfile-Metric	OBJECT-TYPE
	SYNTAX	INTEGER
	ACCESS	read-write
	STATUS	mandatory
	DESCRIPTION	"The number of hops to the named host."
	::= { mibrouteProfileEntry 4 }

    routeProfile-Cost	OBJECT-TYPE
	SYNTAX	INTEGER
	ACCESS	read-write
	STATUS	mandatory
	DESCRIPTION	"The OSPF cost of this link."
	::= { mibrouteProfileEntry 5 }

    routeProfile-Preference	OBJECT-TYPE
	SYNTAX	INTEGER
	ACCESS	read-write
	STATUS	mandatory
	DESCRIPTION	"The preference of this route."
	::= { mibrouteProfileEntry 6 }

    routeProfile-ThirdParty	OBJECT-TYPE
	SYNTAX	INTEGER {
		    no (1),
		    yes (2)
		}
	ACCESS	read-write
	STATUS	mandatory
	DESCRIPTION	"Advertise the gateway as an OSPF 3rd party advertisement."
	::= { mibrouteProfileEntry 7 }

    routeProfile-AseType	OBJECT-TYPE
	SYNTAX	INTEGER {
		    type1 (1),
		    type2 (2)
		}
	ACCESS	read-write
	STATUS	mandatory
	DESCRIPTION	"The OSPF ASE type of this LSA."
	::= { mibrouteProfileEntry 8 }

    routeProfile-AseTag	OBJECT-TYPE
	SYNTAX	DisplayString
	ACCESS	read-write
	STATUS	mandatory
	DESCRIPTION	"The OSPF ASE tag of this link."
	::= { mibrouteProfileEntry 9 }

    routeProfile-PrivateRoute	OBJECT-TYPE
	SYNTAX	INTEGER {
		    no (1),
		    yes (2)
		}
	ACCESS	read-write
	STATUS	mandatory
	DESCRIPTION	"TRUE if this is a private route that should not be advertised via routing protocols."
	::= { mibrouteProfileEntry 10 }

    routeProfile-ActiveRoute	OBJECT-TYPE
	SYNTAX	INTEGER {
		    no (1),
		    yes (2)
		}
	ACCESS	read-write
	STATUS	mandatory
	DESCRIPTION	"TRUE if this is route is active. Inactive routes are ignored and do not affect the routing tables."
	::= { mibrouteProfileEntry 11 }

    routeProfile-Ase7Adv	OBJECT-TYPE
	SYNTAX	INTEGER {
		    n-A (1),
		    advertise (2),
		    doNotAdvertise (3)
		}
	ACCESS	read-write
	STATUS	mandatory
	DESCRIPTION	"Indicates OSPF ASE7, and whether to advertise or not."
	::= { mibrouteProfileEntry 12 }

    routeProfile-Vrouter	OBJECT-TYPE
	SYNTAX	DisplayString
	ACCESS	read-write
	STATUS	mandatory
	DESCRIPTION	"Specifies the VRouter in which this IP Route belongs."
	::= { mibrouteProfileEntry 13 }

    routeProfile-InterVrouter	OBJECT-TYPE
	SYNTAX	DisplayString
	ACCESS	read-write
	STATUS	mandatory
	DESCRIPTION	"Specifies the VRouter."
	::= { mibrouteProfileEntry 14 }

    routeProfile-Action-o	OBJECT-TYPE
	SYNTAX	INTEGER {
		    noAction (1),
		    createProfile (2),
		    deleteProfile (3)
		}
	ACCESS	read-write
	STATUS	mandatory
	DESCRIPTION	""
	::= { mibrouteProfileEntry 15 }

END
