-- TNI-MIB, TRANSITION NETWORKS, INC.
--          (Formerly TEI-MIB, TRANSITION ENGINEERING, INC.)
--                                                
-- MIB Release 2.10 08/08/08 - xFBRM/xBFFG new mib variables for suppressing violations added
--						   - rate limiting values expanded for jumbo frame support boards
-- MIB Release 2.09 12/20/07- xFBRM/xBFFG 3-port redudancy board mib variables added
-- MIB Release 2.08 2/16/07	- xFBRM/xBFFG mib corrections.
--						        - Add xBFFG to comments
-- MIB Release 2.07 2/13/07 - xFBRM/xBFFG mib corrextions.
--								- Extra commas eliminated
--								- index variables sfbrm100SysPortIndex, sfbrm100PortStatsIndex
--								  name corrected.
-- MIB Release 2.06 12/08/06 - xFBRM/xBFFG new mib variables added
--                           - Descriptions expanded for some SFBRM mib variables.   
-- MIB Release 2.05 09/12/06 - SFBRM new mib variables added
-- MIB Release 2.04 06/19/06 - SFBRM mib module added
-- MIB Release 2.03 09/18/98 - Move all MCC16 related definitions to MCC16-MIB
-- MIB Release 2.02 08/18/98 - add mc20pErrorId
-- MIB Release 2.01 07/10/98
-- 
-- Copyright (c) 1996-1998 Transition Networks, Inc.  All Rights Reserved.
-- 
-- Reproduction of this document is authorized on condition that
-- this copyright notice is included.  This Transition
-- Networks, Inc. SNMP Management Information Base
-- Specification (TNI-MIB) embodies T.N.I.'s confidential and
-- proprietary intellectual property.  T.N.I. retains all title and
-- ownership in the TNI-MIB Specification, including any revisions.
-- 
-- It is T.N.I.'s intent to encourage the widespread use of this
-- specification in connection with the management of Transition
-- Networks, Inc.'s products.  T.N.I. grants vendor, end-users,
-- and other interested parties a non-exclusive license to use this
-- specification in connection with the management of Transition
-- Networks, Inc.'s products.
-- 
-- This TNI-MIB Specification is supplied "AS IS," and T.N.I. makes
-- no warranty, either express or implied, as to the use,
-- operation, condition, or performance of the TNI-MIB Specification.
-- 
-- If you have any questions about this MIB, please call Transition
-- Networks, Inc.'s Technical Support at 1-800-260-1312.
-- 
-- 
-- T.N.I. retains the right to change this TNI-MIB without notification.

TNI-MIB DEFINITIONS ::= BEGIN

--
-- SECTION 1: Top Level Definitions
--

--
-- Imports
--
IMPORTS
	Counter, enterprises, Gauge,
	TimeTicks, IpAddress		FROM RFC1155-SMI
	DisplayString, PhysAddress	FROM RFC1213-MIB
	OBJECT-TYPE				FROM RFC-1212
	TRAP-TYPE				FROM RFC-1215;

MacAddress ::= OCTET STRING (SIZE (6))
		-- a 6 octet address in the "canonical" order defined by IEEE 
		-- 802.1a, i.e., as if it were transmitted least significant bit 
		-- first, even though 802.5 (in contrast to other 802.x protocols) 
		-- requires MAC addresses to be transmitted most significant bit 
		-- first.  16-bit addresses, if needed, are represented by setting
		-- their upper 4 octets to all 0's, i.e., AAFF would be
		-- represented as 00000000AAFF.
		
-- The types of connectors that can be built into a Point System converter.
-- No type of converter uses all of these connector types.
-- Some converters return 16 bit connector style values that contain additional
-- information on the connector in the upper byte. In these cases, the lower 
-- byte is one of the values below. 
CpsConnector ::= INTEGER { rj-45(10),     -- RJ-45, unshielded twisted pair
                           stmm(11),      -- ST fiber, multimode
                           stsm(12),      -- ST fiber, singlemode
                           scmm(13),      -- SC fiber, multimode
                           scsm(14),      -- SC fiber, singlemode
                           scsmlh(15),    -- SC fiber, singlemode, long haul
                           scsmelh(16),   -- SC fiber, singlemode, extra long haul
                           scsmlhlw(17),  -- SC fiber, long haul, long wavelength
                           mtrjmm(18),    -- MT-RJ multimode fiber
                           lc(19),        -- LC fiber, singlemode
                           bnc(20),       -- BNC coax
                           stsmlh(21),    -- ST Singlemode Long Haul
                           stsmelh(22),   -- ST Singlemode Extra Long Haul
                           scmm1300(23),  -- SC Multimode 1300nm
                           stmm1300(24),  -- ST Multimode 1300nm
                           mtrjsm(25),    -- MTRJ singlemode fiber
                           serial26(26),  -- Universal 26-pin Serial Interface Connector
                           stmmlh(27),    -- ST Multimode Long Haul
                           scsmsh(28),    -- SC Singlemode Short Haul
                           scsimplex(29), -- SC Simplex
                           bncdual(30),   -- Dual BNC coax connectors
                           db9rsxxx(31),  -- DB9 for RS232 and RS485
                           termblock(32), -- Terminal Block for RS485
                           rj11(33),      -- RJ-11, unshielded twisted pair
                           sc40km(34),    -- SC fiber, 1550nm 40km 
                           sc125km(35),    -- SC fiber, 1 x 9, 125km Gigiabit
                           din6(38) 	  -- DIN 6-Pin for RS232
                           }
		
--
-- Categories
--
transition       OBJECT IDENTIFIER ::=   { enterprises 868 }
productId        OBJECT IDENTIFIER ::=   { transition  1 }
rptrProdsId      OBJECT IDENTIFIER ::=   { productId 1 }
rptrStackMId     OBJECT IDENTIFIER ::=   { rptrProdsId 1 }
rptrSPSId        OBJECT IDENTIFIER ::=   { rptrProdsId 2 }
ringProdsId      OBJECT IDENTIFIER ::=   { productId 2 }
ringStackTRId    OBJECT IDENTIFIER ::=   { ringProdsId 1 }
brdgProdsId      OBJECT IDENTIFIER ::=   { productId 3 }
brdgSwitchMId    OBJECT IDENTIFIER ::=   { brdgProdsId 1 }     
brdgFBRMId		 OBJECT IDENTIFIER ::=	 { brdgProdsId 2 }
  -- productId 4 reserved

products         OBJECT IDENTIFIER ::=   { transition 2 }

--
-- sysObjectID product object identifiers for T.N. products
--
rptrSMVer1Id	OBJECT IDENTIFIER ::=	{ rptrStackMId 1 }
rptrSMVer2Id	OBJECT IDENTIFIER ::=	{ rptrStackMId 2 }
rptrSM08TId  	OBJECT IDENTIFIER ::=	{ rptrStackMId 3 }
rptrSM08TSId	OBJECT IDENTIFIER ::=	{ rptrStackMId 4 }
rptrSM06FId 	OBJECT IDENTIFIER ::=	{ rptrStackMId 5 }
rptrSM06FSId	OBJECT IDENTIFIER ::=	{ rptrStackMId 6 }
rptrSM8T0Id     OBJECT IDENTIFIER ::=	{ rptrStackMId 7 }
rptrSM8TS0Id    OBJECT IDENTIFIER ::=	{ rptrStackMId 8 }
rptrSM6F0Id     OBJECT IDENTIFIER ::=	{ rptrStackMId 9 }
rptrSM6FS0Id	OBJECT IDENTIFIER ::=	{ rptrStackMId 10 }
rptrSM8T6FId	OBJECT IDENTIFIER ::=	{ rptrStackMId 11 }
rptrSM8TS6FId	OBJECT IDENTIFIER ::=	{ rptrStackMId 12 }
rptrSM8T6FSId	OBJECT IDENTIFIER ::=	{ rptrStackMId 13 }
rptrSM8TS6FSId	OBJECT IDENTIFIER ::=	{ rptrStackMId 14 }
rptrSM6F8TId	OBJECT IDENTIFIER ::=	{ rptrStackMId 15 }
rptrSM6FS8TId	OBJECT IDENTIFIER ::=	{ rptrStackMId 16 }
rptrSM6F8TSId	OBJECT IDENTIFIER ::=	{ rptrStackMId 17 }
rptrSM6FS8TSId	OBJECT IDENTIFIER ::=	{ rptrStackMId 18 }
rptrSM8T8TId	OBJECT IDENTIFIER ::=	{ rptrStackMId 19 }
rptrSM8TS8TId	OBJECT IDENTIFIER ::=	{ rptrStackMId 20 }
rptrSM8T8TSId	OBJECT IDENTIFIER ::=	{ rptrStackMId 21 }
rptrSM8TS8TSId	OBJECT IDENTIFIER ::=	{ rptrStackMId 22 }
rptrSM6F6FId	OBJECT IDENTIFIER ::=	{ rptrStackMId 23 }
rptrSM6FS6FId	OBJECT IDENTIFIER ::=	{ rptrStackMId 24 }
rptrSM6F6FSId	OBJECT IDENTIFIER ::=	{ rptrStackMId 25 }
rptrSM6FS6FSId	OBJECT IDENTIFIER ::=	{ rptrStackMId 26 }
rptrSM24TId	OBJECT IDENTIFIER ::=	{ rptrStackMId 27 }
rptrSM16TId	OBJECT IDENTIFIER ::=	{ rptrStackMId 28 }
rptrSM14FId	OBJECT IDENTIFIER ::=	{ rptrStackMId 29 }
rptrSM12FId	OBJECT IDENTIFIER ::=	{ rptrStackMId 30 }
rptrSM6FId	OBJECT IDENTIFIER ::=	{ rptrStackMId 31 }
rptrSM0Id	OBJECT IDENTIFIER ::=	{ rptrStackMId 32 }

rptrSPSVer1Id	OBJECT IDENTIFIER ::=	{ rptrSPSId 1 }
rptrESPS24Id	OBJECT IDENTIFIER ::=	{ rptrSPSId 2 }
rptrESPS24SId	OBJECT IDENTIFIER ::=	{ rptrSPSId 3 }

ringTRVer1Id	OBJECT IDENTIFIER ::=	{ ringStackTRId 1 }
ringTRVer2Id	OBJECT IDENTIFIER ::=	{ ringStackTRId 2 }
ringTR0Id	OBJECT IDENTIFIER ::=	{ ringStackTRId 3 }
ringTR16TId	OBJECT IDENTIFIER ::=	{ ringStackTRId 4 }

brdgSWVer1Id	OBJECT IDENTIFIER ::=	{ brdgSwitchMId 1 }

repeater	OBJECT IDENTIFIER ::=	{ products 1 }
tnStackM	OBJECT IDENTIFIER ::=	{ repeater 1 }
tnSMCommon	OBJECT IDENTIFIER ::=	{ tnStackM 1 }
tnSMVer1	OBJECT IDENTIFIER ::=	{ tnStackM 2 }
tnSMVer2	OBJECT IDENTIFIER ::=	{ tnStackM 3 }

sps	OBJECT IDENTIFIER ::=	{ repeater 2 }
spsCommon	OBJECT IDENTIFIER ::=	{ sps 1 }
spsVer1         OBJECT IDENTIFIER ::=   { sps  2 }

ring	OBJECT IDENTIFIER ::=	{ products 2 }
tnStackTR	OBJECT IDENTIFIER ::=	{ ring 1 }
tnTRCommon	OBJECT IDENTIFIER ::=	{ tnStackTR 1 }
tnTRVer1	OBJECT IDENTIFIER ::=	{ tnStackTR 2 }
tnTRVer2	OBJECT IDENTIFIER ::=	{ tnStackTR 3 }

bridge  OBJECT IDENTIFIER ::=   { products 3 }

-- Stand-alone 10/100 Remote managed switch
sfbrm10x100  OBJECT IDENTIFIER ::=   { bridge 1 }

sfbrmSystem   OBJECT IDENTIFIER ::=   { sfbrm10x100 1 }
sfbrmSwitch   OBJECT IDENTIFIER ::=   { sfbrm10x100 2 }
sfbrmPort     OBJECT IDENTIFIER ::=   { sfbrm10x100 3 }
sfbrmAddrDB   OBJECT IDENTIFIER ::=   { sfbrm10x100 4 }

-- {products 4} is reserved

--
-- SECTION 2.1: Repeater, StackMaster Common
--
tnSMComHwReset OBJECT-TYPE
	SYNTAX  INTEGER {
		noReset(1),
		reset(2)
	}
	ACCESS  read-write
	STATUS  mandatory
	DESCRIPTION
		"Perform a hardware reset."
	::= { tnSMCommon 1 }

tnSMComMgmtHwRev OBJECT-TYPE
	SYNTAX  DisplayString (SIZE (0..255))
	ACCESS  read-only
	STATUS  mandatory
	DESCRIPTION
		"The management h/w board revision."
	::= { tnSMCommon 2 }

tnSMComDiagSwRev OBJECT-TYPE
	SYNTAX  DisplayString (SIZE (0..255))
	ACCESS  read-only
	STATUS  mandatory
	DESCRIPTION
		"The diagnostic s/w code revision."
	::= { tnSMCommon 3 }

tnSMComMgmtSwRev OBJECT-TYPE
	SYNTAX  DisplayString (SIZE (0..255))
	ACCESS  read-only
	STATUS  mandatory
	DESCRIPTION
		"The downloadable management s/w code revision."
	::= { tnSMCommon 4 }

tnSMComIpAddr OBJECT-TYPE
	SYNTAX  IpAddress
	ACCESS  read-write
	STATUS  mandatory
	DESCRIPTION
		"The IP address to which this entry's addressing
		 information pertains."
	::= { tnSMCommon 5 }

tnSMComNetMask OBJECT-TYPE
	SYNTAX  IpAddress
	ACCESS  read-write
	STATUS  mandatory
	DESCRIPTION
		"The subnet mask associated with the IP address of
		 this entry.  The value of the mask is an IP
		 address with all the network bits set to 1 and all
		 the hosts bits set to 0."
	::= { tnSMCommon 6 }

--
-- SECTION 2.2: Repeater, StackMaster Pro Common (SPS)
--
spsReset    OBJECT-TYPE
	SYNTAX INTEGER {
		noReset(1),
		reset(2)
	}
	ACCESS read-write
	STATUS mandatory
	DESCRIPTION
		"Setting this object to reset(2) causes a  reset of the hardware.
		Setting this object to noReset(1) has no effect. The agent will 
		always return the value noReset(1) when this object is read."
	::= { spsCommon 1 }

spsConfig OBJECT-TYPE
	SYNTAX DisplayString(SIZE(0..255))
	ACCESS read-only
	STATUS mandatory
	DESCRIPTION
		"The hardware configuration information. The type and size of 
		ROM, RAM, and DRAM."
	REFERENCE
		"Port Switching Management Engine HDS. Document Number: 
		xxxx Revision 2.2." 
	::= { spsCommon 2 }

spsBootpEnable OBJECT-TYPE
	SYNTAX INTEGER {
		enabled(1),
		disabled(2)
	}
	ACCESS read-only
	STATUS mandatory
	DESCRIPTION
		"If this object is set to enabled(1) the unit will use the Bootstrap 
		Protocol (BOOTP) on power-up or reset to obtain  its IP
		configuration parameters. If this object is set to disabled(2) the unit 
		will not use BOOTP. It will use values stored in non-volatile 
		storage."
	REFERENCE
		"RFC-951 Bootstrap Protocol (BOOTP)." 
	::= { spsCommon 3 }

spsBootpServer OBJECT-TYPE
	SYNTAX IpAddress
	ACCESS read-only
	STATUS mandatory
	DESCRIPTION
		"This object specifies the IP address of the BOOTP server the client wishes to 
		respond;  forcing the boot to occur from a specific host.  If the IP address of the 
		BOOTP server is unknown this object should be set to be the 'broadcast address'
		255.255.255.255.

		The value of this object  is not updated by the system when it determines the 
		IP address of the BOOTP server."
	REFERENCE
		"RFC-951 Bootstrap Protocol (BOOTP)." 
	::= { spsCommon 4 }

spsBootpFilename OBJECT-TYPE
	SYNTAX DisplayString(SIZE(0..127))
	ACCESS read-only
	STATUS mandatory
	DESCRIPTION
 		"The 'generic' filename to be booted."
	REFERENCE
		"RFC-951 Bootstrap Protocol (BOOTP)."
	::= { spsCommon 5 }

spsDefaultGateway OBJECT-TYPE
	SYNTAX IpAddress
	ACCESS read-write
	STATUS mandatory
	DESCRIPTION
		"This object specifies the IP address of the default gateway.

		This object is the same as ipRouteDest for the default route. It
		is placed here as a single object for convenience."
	::= { spsCommon 6 }

spsMgmtSegment OBJECT-TYPE
	SYNTAX INTEGER
	ACCESS read-write
	STATUS mandatory
	DESCRIPTION
		"Indicates the segment the management interface is on.  The value is between 1 and 
		spsMaxSegment.

		The agent should not allow the NMU to be placed on a segment which has no ports 
		assigned to it, as this would prevent communication with the NMU."
	::= { spsCommon 7 }

spsIpAddrTable OBJECT-TYPE
	SYNTAX SEQUENCE OF SpsIpAddrEntry
	ACCESS not-accessible
	STATUS mandatory
	DESCRIPTION
		"The table of addressing information relevant to this entity's IP 
		addresses."
	::= { spsCommon 8 }
 
spsIpAddrEntry OBJECT-TYPE
	SYNTAX SpsIpAddrEntry
	ACCESS not-accessible
	STATUS mandatory
	DESCRIPTION
		"The addressing information relevant to this entity's IP addresses."
	INDEX { spsIpIfIndex }
	::= { spsIpAddrTable 1 }

SpsIpAddrEntry ::=
	SEQUENCE {
		spsIpIfIndex INTEGER,
		spsIpAddr IpAddress,
		spsIpNetMask IpAddress
	}

spsIpIfIndex OBJECT-TYPE
	SYNTAX INTEGER
	ACCESS read-only
	STATUS mandatory
	DESCRIPTION
		"The index value which uniquely identifies the  interface to which this entry is 
		applicable. The interface identified by a particular value of this index is the same as 
		identified by the same value of ifIndex (and also ipAdEntIfIndex)."
	::= { spsIpAddrEntry 1 }

spsIpAddr OBJECT-TYPE
	SYNTAX IpAddress
	ACCESS read-write
	STATUS mandatory
	DESCRIPTION 
		"The IP address to which this entry's addressing information pertains.  The IP 
		address value for this entry is the same value as specified by ipAdEntAddr. This 
		entry differs from ipAdEntAddr, in that it has read-write access, which allows the 
		IP address to be specified using SNMP.

		The unit must be reset for the new IP address to take effect."
	 ::= { spsIpAddrEntry 2 }

spsIpNetMask OBJECT-TYPE
	SYNTAX IpAddress
	ACCESS read-write
	STATUS mandatory
	DESCRIPTION
		"The subnet mask associated with the IP address of this entry. The value of the 
		mask is an IP address with all the network bits set to 1 and all the hosts bits set to 0. 
		The subnet mask value for this entry is the same value as specified by 
		ipAdEntNetMask. This entry differs from ipAdEntNetMask in that is has read-
		write access, which allows the subnet mask to be specified using SNMP.

		The unit must be reset for the new subnet mask to take effect." 
	::= { spsIpAddrEntry 3 }

spsTrapTable OBJECT-TYPE
	SYNTAX SEQUENCE OF SpsTrapEntry
	ACCESS not-accessible
	STATUS mandatory
	DESCRIPTION
		"A list of trap destinations and community names. When 
		generating a trap, each destination in this list is sent the trap using 
		the associated community name."
	::= { spsCommon 9 }
 
spsTrapEntry OBJECT-TYPE
	SYNTAX SpsTrapEntry
	ACCESS not-accessible
	STATUS mandatory
	DESCRIPTION
		"An entry in the spsTrapTable."
	INDEX { spsTrapIndex }
	::= { spsTrapTable 1 }

SpsTrapEntry ::=
	SEQUENCE {
		spsTrapIndex INTEGER,
		spsTrapDestination IpAddress,
		spsTrapCommunity DisplayString
	}

spsTrapIndex OBJECT-TYPE
	SYNTAX INTEGER
	ACCESS read-only
	STATUS mandatory
	DESCRIPTION
		"The index value which uniquely identifies the SNMP trap 
		destination and community name pairing to which this entry is 
		applicable."
	::= { spsTrapEntry 1 }

spsTrapDestination OBJECT-TYPE
	SYNTAX IpAddress
	ACCESS read-write
	STATUS mandatory
	DESCRIPTION
		"This object specifies the destination address of the Trap-PDU."
	REFERENCE
		"A Simple Network Management Protocol (SNMP), RFC1157"
	::= { spsTrapEntry 2 }

spsTrapCommunity OBJECT-TYPE
	SYNTAX DisplayString(SIZE(0..31))
	ACCESS read-write
	STATUS mandatory
	DESCRIPTION
		"The community name used when generating traps."
	::= { spsTrapEntry 3 }

--
-- SECTION 2.2.1: Repeater, StackMaster Pro Ver 1
--
spsMaxSegment OBJECT-TYPE
	SYNTAX INTEGER
	ACCESS read-only
	STATUS mandatory
	DESCRIPTION
		"The maximum number of segments supported."
	::= { spsVer1 1 }

spsPasswdReset OBJECT-TYPE
	SYNTAX INTEGER {
		noReset(1),
		reset(2)
	}
	ACCESS read-write
	STATUS mandatory
	DESCRIPTION
		"If this object is set to reset(2) resets the joystick password to a 
		known value.

		Setting this value to noReset(1) has no effect. The agent will always 
		return the value noReset(1) when this object is read."
	::= { spsVer1 2 }

spsExternalPowerSupply OBJECT-TYPE
	SYNTAX INTEGER {
		present(1),
		notPresent(2)
	}
	ACCESS read-only
	STATUS mandatory
	DESCRIPTION
		"This object indicates the status of the internal power supply.

		A value of present(1) indicates the power supply is present and able 
		to provide power. A value of notPresent(2) indicates the power 
		supply is unable to provide power or is not present."
	::= { spsVer1 3 }

spsDisplayString OBJECT-TYPE
	SYNTAX DisplayString(SIZE(8))
	ACCESS read-write
	STATUS mandatory
	DESCRIPTION
		"Setting this object changes the contents of the display."
	::= { spsVer1 4 }

spsRptrGroupTable OBJECT-TYPE
	SYNTAX SEQUENCE OF SpsRptrGroupEntry
	ACCESS not-accessible
	STATUS mandatory
	DESCRIPTION
		"Table of descriptive and status information about the repeater 
		groups (Units)."
	::= { spsVer1 5 }

spsRptrGroupEntry OBJECT-TYPE
	SYNTAX SpsRptrGroupEntry
	ACCESS not-accessible
	STATUS mandatory
	DESCRIPTION
		"An entry in the table, containing information about a single 
		repeater group."
	INDEX { spsRptrGroupIndex }
	::= { spsRptrGroupTable 1 }

SpsRptrGroupEntry ::=
	SEQUENCE {
		spsRptrGroupIndex INTEGER,
		spsRptrGroupUnitId OCTET STRING,
		spsRptrGroupInternalPowerSupply INTEGER
	}

spsRptrGroupIndex OBJECT-TYPE
	SYNTAX INTEGER
	ACCESS read-only
	STATUS mandatory
	DESCRIPTION
		"This object identifies the group containing the port for which this 
		entry contains information. The group identified by a particular 
		value of this index is the same group as identified by the same value 
		of rptrPortGroupIndex."
	::= { spsRptrGroupEntry 1 }

spsRptrGroupUnitId OBJECT-TYPE
	SYNTAX OCTET STRING(SIZE(6))
	ACCESS read-only
	STATUS mandatory
	DESCRIPTION
		"A unique string which identifies this unit."
	::= { spsRptrGroupEntry 2 }

spsRptrGroupInternalPowerSupply OBJECT-TYPE
	SYNTAX INTEGER {
		present(1),
		notPresent(2)
	}
	ACCESS read-only
	STATUS mandatory
	DESCRIPTION
		"This object indicates the status of the internal power supply.

		A value of present(1) indicates the power supply is present and able 
		to provide power. A value of notPresent(2) indicates the power 
		supply is unable to provide power or is not present."
	::= { spsRptrGroupEntry 3 }

spsRptrPortTable OBJECT-TYPE
	SYNTAX SEQUENCE OF SpsRptrPortEntry
	ACCESS not-accessible
	STATUS mandatory
	DESCRIPTION
		"Table of descriptive and status information about the ports."
	::= { spsVer1 6 }

spsRptrPortEntry OBJECT-TYPE
	SYNTAX SpsRptrPortEntry
	ACCESS not-accessible
	STATUS mandatory
	DESCRIPTION
		"An entry in the table, containing information about a single port."
	INDEX { spsRptrPortGroupIndex, spsRptrPortIndex }
	::= { spsRptrPortTable 1 }

SpsRptrPortEntry ::=
	SEQUENCE {
		spsRptrPortGroupIndex INTEGER,
		spsRptrPortIndex INTEGER,
		spsRptrPortSegment INTEGER,
		spsRptrPortSrcAddr MacAddress,
		spsRptrPortEavesdropping INTEGER,
		spsRptrPortIntrusion INTEGER,
		spsRptrPortCollisionLimit INTEGER,
		spsRptrPortEnableIntruderDetectTrap INTEGER,
		spsRptrPortDisableIntruder INTEGER
	}

spsRptrPortGroupIndex OBJECT-TYPE
	SYNTAX INTEGER
	ACCESS read-only
	STATUS mandatory
	DESCRIPTION
		"This object identifies the group containing the port for which this 
		entry contains information. The group identified by a particular 
		value of this index is the same group as identified by the same value 
		of rptrPortGroupIndex."
	::= { spsRptrPortEntry 1 }

spsRptrPortIndex OBJECT-TYPE
	SYNTAX INTEGER
	ACCESS read-only
	STATUS mandatory
	DESCRIPTION
		"This object identifies the port within the group for which this 
		entry contains information. The port identified by a particular 
		value of this index is the same port as identified by the same value 
		of rptrPortIndex.  This value can never be greater than 
		rptrGroupPortCapacity for the associated group."
	::= { spsRptrPortEntry 2 }

spsRptrPortSegment OBJECT-TYPE
	SYNTAX INTEGER
	ACCESS read-write
	STATUS mandatory
	DESCRIPTION
		"The segment number to which this port belongs. This value is 
		never greater than spsMaxSegment."
	::= { spsRptrPortEntry 3 }

spsRptrPortSrcAddr OBJECT-TYPE
	SYNTAX MacAddress
	ACCESS read-write
	STATUS mandatory
	DESCRIPTION
		"When spsRptrPortEavesdropping  or spsRptrPortIntrusion  are 
		enabled this object contains the authorized source address, 
		otherwise this object contains the source address field from the last 
		correctly received frame."
	REFERENCE
		"ATT1RX04 (FORESPAR) Four(4) Managed Ethernet Repeaters 
		Data Sheet."
	::= { spsRptrPortEntry 4 }

spsRptrPortEavesdropping OBJECT-TYPE
	SYNTAX INTEGER {
		enabled(1),
		disabled(2)
	}
	ACCESS read-write
	STATUS mandatory
	DESCRIPTION
		"Eavesdropping protection safeguards the network from 
		promiscuous mode stations receiving intelligible data from the 
		network. 

		Setting this object to enabled(1)  enables eavesdropping protection. 
		Eavesdropping protection causes the currently transmitted frame 
		to be jammed if the destination address 	field does not match 
		spsRptrPortSrcAddr . Setting this object to disabled(2) disables 
		eavesdropping protection and the frame is not jammed. 

		All broadcast and multicast packets are repeated to all ports on the 
		same segment."
	REFERENCE
		"ATT1RX04 (FORESPAR) Four(4) Managed Ethernet Repeaters 
		Data Sheet."
	::= { spsRptrPortEntry 5 }

spsRptrPortIntrusion OBJECT-TYPE
	SYNTAX INTEGER {
		enabled(1),
		disabled(2)
	}
	ACCESS read-write
	STATUS mandatory
	DESCRIPTION
		"Automatic intrusion protection prevents unauthorized users from 
		gaining access to the network. Conceptually, the source address
		field of the received packet is compared to the authorized source 
		address. If the addresses differ, the user is classified as an intruder
		and the data going to the backplane is jammed."
	REFERENCE
		"ATT1RX04 (FORESPAR) Four(4) Managed Ethernet Repeaters 
		Data Sheet."
	::= { spsRptrPortEntry 6 }

spsRptrPortCollisionLimit OBJECT-TYPE
	SYNTAX INTEGER {
		collision-limit-31(31),
		collision-limit-63(63),
		collision-limit-127(127),
		collision-limit-155(255)
	}
	ACCESS read-write
	STATUS mandatory
	DESCRIPTION
		"Selects the consecutive collision count that will cause port 
		partitioning. Valid values are 31, 63, 127, and 255."
	REFERENCE
		"ATT1RX04 (FORESPAR) Four(4) Managed Ethernet Repeaters 
		Data Sheet."
	::= { spsRptrPortEntry 7 }

spsRptrPortEnableIntruderDetectTrap OBJECT-TYPE
	SYNTAX INTEGER {
		enabled(1),
		disabled(2)
	}
	ACCESS read-write
	STATUS mandatory
	DESCRIPTION
		"Indicates whether the SNMP agent process is permitted to 
		generate intruderDetection traps."
	::= { spsRptrPortEntry 8 }

spsRptrPortDisableIntruder OBJECT-TYPE
	SYNTAX INTEGER {
		enabled(1),
		disabled(2)
	}
	ACCESS write-only
	STATUS mandatory
	DESCRIPTION
		"Indicates whether the port is disabled when an intruder is 
		detected. Disabling a port in this manner is the same as setting the 
		rptrPortAdminStatus object for this port to disabled(2). The 
		security mechanism will not automatically enable a port."
	::= { spsRptrPortEntry 9 }

spsSerialPortTable OBJECT-TYPE
	SYNTAX SEQUENCE OF SpsSerialPortEntry
	ACCESS not-accessible
	STATUS mandatory
	DESCRIPTION
		"The table of RS-232 serial ports. Table only contains information
		 not found in RFC-1316 and RFC-1317 Definitions of Managed
		Objects for RS-232-like Hardware Devices."
	::= { spsVer1 7 }

spsSerialPortEntry OBJECT-TYPE
	SYNTAX SpsSerialPortEntry
	ACCESS not-accessible
	STATUS mandatory
	DESCRIPTION
		"Table entry for a specific RS-232 serial port."
	INDEX { spsSerialPortIndex }
	::= { spsSerialPortTable 1 }

SpsSerialPortEntry ::=
	SEQUENCE {
		spsSerialPortIndex INTEGER,
		spsSerialPortModemControl INTEGER
	}

spsSerialPortIndex OBJECT-TYPE
	SYNTAX INTEGER
	ACCESS read-only
	STATUS mandatory
	DESCRIPTION
		"A unique value for each port."
	::= { spsSerialPortEntry 1 }

spsSerialPortModemControl OBJECT-TYPE
	SYNTAX INTEGER {
		enabled(1),
		disabled(2)
	}
	ACCESS read-only
	STATUS mandatory
	DESCRIPTION
		"Setting this object to enabled(1) enables the monitoring and
		control of modem control lines by the serial port. Setting this
		object to disabled(2) disables the 	monitoring and control of
		modem control lines by the serial port."
	REFERENCE
		"PC16552D Dual Universal Asynchronous Receiver/Transmitter 
		with FIFOs"
	::= { spsSerialPortEntry 2 }

--- spsMonitorSegmentTable is similar to rptrMonitorPortTable.
--- It monitors statistics based on segment instead of group

spsMonitorSegmentTable OBJECT-TYPE
	SYNTAX    SEQUENCE OF SpsMonitorSegmentEntry
	ACCESS    not-accessible
	STATUS    mandatory
	DESCRIPTION
		"Table of performance and error statistics for the
		segments."
	::= { spsVer1 8 }

spsMonitorSegmentEntry OBJECT-TYPE
	SYNTAX    SpsMonitorSegmentEntry
	ACCESS    not-accessible
	STATUS    mandatory
	DESCRIPTION
		"An entry in the table, containing total
		performance and error statistics for a single
		segment.  Regular retrieval of the information in
		this table provides a means of tracking the
		performance and health of the networked devices
		attached to this segment's ports.

		The counters in this table are redundant in the
		sense that they are the summations of information
		already available through other objects.  However,
		these sums provide a considerable optimization of
		network management traffic over the otherwise
		necessary retrieval of the individual counters
		included in each sum."
	INDEX    { spsMonitorSegmentIndex }
	::= { spsMonitorSegmentTable 1 }

SpsMonitorSegmentEntry ::=
	SEQUENCE {
		spsMonitorSegmentIndex INTEGER,
		spsMonitorSegmentTotalFrames Counter,
		spsMonitorSegmentTotalOctets Counter,
		spsMonitorSegmentTotalErrors Counter
	}

spsMonitorSegmentIndex OBJECT-TYPE
	SYNTAX    INTEGER (1..1024)
	ACCESS    read-only
	STATUS    mandatory
	DESCRIPTION
		"This object identifies the group within the
		repeater for which this entry contains
		information."
	::= { spsMonitorSegmentEntry 1 }

spsMonitorSegmentTotalFrames OBJECT-TYPE
	SYNTAX    Counter
	ACCESS    read-only
	STATUS    mandatory
	DESCRIPTION
		"The total number of frames of valid frame length
		that have been received on the ports in this group
		and for which the FCSError and CollisionEvent
		signals were not asserted.  This counter is the
		summation of the values of the
		rptrMonitorPortReadableFrames counters for all of
		the ports in the segment.

		This statistic provides one of the parameters
		necessary for obtaining the packet error rate."
	::= { spsMonitorSegmentEntry 2 }

spsMonitorSegmentTotalOctets OBJECT-TYPE
	SYNTAX    Counter
	ACCESS    read-only
	STATUS    mandatory
	DESCRIPTION
		"The total number of octets contained in the valid
		frames that have been received on the ports in
		this segment.  This counter is the summation of the
		values of the rptrMonitorPortReadableOctets
		counters for all of the ports in the segment.

		This statistic provides an indicator of the total
		data transferred."
	::= { spsMonitorSegmentEntry 3 }

spsMonitorSegmentTotalErrors OBJECT-TYPE
	SYNTAX    Counter
	ACCESS    read-only
	STATUS    mandatory
	DESCRIPTION
		"The total number of errors which have occurred on
		all of the ports in this segment.  This counter is
		the summation of the values of the
		rptrMonitorPortTotalErrors counters for all of the
		ports in the segment."
::= { spsMonitorSegmentEntry 4 }

--
-- SECTION 3: Ring, StackMaster TR Common
--
tnTRComHwReset OBJECT-TYPE
	SYNTAX  INTEGER {
				noReset(1),
				reset(2)
			}
	ACCESS  read-write
	STATUS  mandatory
	DESCRIPTION
		"Perform a hardware reset."
	::= { tnTRCommon 1 }

tnTRComMgmtHwRev OBJECT-TYPE
	SYNTAX  DisplayString (SIZE (0..255))
	ACCESS  read-only
	STATUS  mandatory
	DESCRIPTION
		"The management h/w board revision."
	::= { tnTRCommon 2 }

tnTRComDiagSwRev OBJECT-TYPE
	SYNTAX  DisplayString (SIZE (0..255))
	ACCESS  read-only
	STATUS  mandatory
	DESCRIPTION
		"The diagnostic s/w code revision."
	::= { tnTRCommon 3 }

tnTRComMgmtSwRev OBJECT-TYPE
	SYNTAX  DisplayString (SIZE (0..255))
	ACCESS  read-only
	STATUS  mandatory
	DESCRIPTION
		"The downloadable management s/w code revision."
	::= { tnTRCommon 4 }
tnTRComIpAddr OBJECT-TYPE
	SYNTAX  IpAddress
	ACCESS  read-write
	STATUS  mandatory
	DESCRIPTION
		"The IP address to which this entry's addressing
		 information pertains."
	::= { tnTRCommon 5 }
tnTRComNetMask OBJECT-TYPE
	SYNTAX  IpAddress
	ACCESS  read-write
	STATUS  mandatory
	DESCRIPTION
		"The subnet mask associated with the IP address of
		 this entry.  The value of the mask is an IP
		 address with all the network bits set to 1 and all
		 the hosts bits set to 0."
	::= { tnTRCommon 6 }
tnTRComIfaceCapacity OBJECT-TYPE
	SYNTAX  INTEGER
	ACCESS  read-only
	STATUS  mandatory
	DESCRIPTION
		"The total number of interfaces found in the stack."
	::= { tnTRCommon 7 }
		  
--
-- SECTION 3.1: Ring, StackMaster TR Version 1
--
tnTRV1Commands  OBJECT-TYPE
	SYNTAX  INTEGER {
				no-op(1),
				open(2),
				reset(3),
				close(4)
			}
	ACCESS  read-write
	STATUS  mandatory
	DESCRIPTION
		"When this object is set to the value of open(2), the station should 
		 go into the open state.  The progress and success of the open is 
		 given by the values of the objects dot5RingState and
		 dot5RingOpenStatus.  When this object is set to the value of
		 reset(3), then the station should do a reset.  On a reset, all MIB 
		 counters should retain their values, if possible.  Other side 
		 affects are dependent on the hardware chip set.  When this object is 
		 set to the value of close(4), the station should go into the stopped 
		 state by removing itself from the ring.  Setting this object to a 
		 value of no-op(1) has no effect.  When read, this object always has 
		 a value of no-op(1)."
	::= { tnTRVer1 1 }
tnTRV1RingStatus OBJECT-TYPE
	SYNTAX  INTEGER
	ACCESS  read-only
	STATUS  mandatory
	DESCRIPTION
		"The current interface status which can be used to diagnose
		 fluctuating problems that can occur on token rings, after a station 
		 has successfully been added to the ring.  Before an open is 
		 completed, this object has the value for the 'no status' condition.  
		 The dot5RingState and dot5RingOpenStatus objects provide for
		 debugging problems when the station can not even enter the ring.
		 The object's value is a sum of values, one for each currently 
		 applicable condition.  The following values are defined for various 
		 conditions:
				 0 = No Problems detected
				32 = Ring Recovery
				64 = Single Station
			   256 = Remove Received
			   512 = reserved
			  1024 = Auto-Removal Error
			  2048 = Lobe Wire Fault
			  4096 = Transmit Beacon
			  8192 = Soft Error
			 16384 = Hard Error
			 32768 = Signal Loss
			131072 = no status, open not completed."
	::= { tnTRVer1 2 }
tnTRV1RingState  OBJECT-TYPE
	SYNTAX  INTEGER {
				opened(1),
				closed(2),
				opening(3),
				closing(4),
				openFailure(5),
				ringFailure(6)
			}
	ACCESS  read-only
	STATUS  mandatory
	DESCRIPTION
		"The current interface state with respect
		 to entering or leaving the ring."
	::= { tnTRVer1 3 }
tnTRV1RingOpenStatus  OBJECT-TYPE
	SYNTAX  INTEGER {
				noOpen(1),     -- no open attempted
				badParam(2),
				lobeFailed(3),
				signalLoss(4),
				insertionTimeout(5),
				ringFailed(6),
				beaconing(7),
				duplicateMAC(8),
				requestFailed(9),
				removeReceived(10),
				open(11)      -- last open successful
			}
	ACCESS  read-only
	STATUS  mandatory
	DESCRIPTION
		"This object indicates the success, or the reason for failure, of the 
		 station's most recent attempt to enter the ring."
	::= { tnTRVer1 4 }
tnTRV1RingSpeed  OBJECT-TYPE
	SYNTAX  INTEGER {
				unknown(1),
				oneMegabit(2),
				fourMegabit(3),
				sixteenMegabit(4)
			}
	ACCESS  read-write
	STATUS  mandatory
	DESCRIPTION
		"The ring's bandwidth."
	::= { tnTRVer1 5 }
tnTRV1UpStream  OBJECT-TYPE
	SYNTAX  MacAddress
	ACCESS  read-only
	STATUS  mandatory
	DESCRIPTION
		"The MAC-address of the up stream neighbor station in the ring."
	::= { tnTRVer1 6 }
tnTRV1ActMonParticipate OBJECT-TYPE
	SYNTAX  INTEGER {
				true(1),
				false(2)
			}
	ACCESS  read-write
	STATUS  mandatory
	DESCRIPTION
		"If this object has a value of true(1) then this interface will 
		 participate in the active monitor selection process.  If the value 
		 is false(2) then it will not.  Setting this object might not have an
		 effect until the next time the interface is opened."
	::= { tnTRVer1 7 }
tnTRV1Functional OBJECT-TYPE
	SYNTAX  MacAddress
	ACCESS  read-write
	STATUS  mandatory
	DESCRIPTION
		"The bit mask of all Token Ring functional addresses for which this 
		interface will accept frames."
	::= { tnTRVer1 8 }
tnTRV1StatsLineErrors OBJECT-TYPE
	SYNTAX  Counter
	ACCESS  read-only
	STATUS  mandatory
	DESCRIPTION
		"This counter is incremented when a frame or token is copied or 
		 repeated by a station, the E bit is zero in the frame or token and 
		 one of the following conditions exists: 1) there is a non-data bit 
		 (J or K bit) between the SD and the ED of the frame or token, or 2) 
		 there is an FCS error in the frame."
	::= { tnTRVer1 9 }
tnTRV1StatsBurstErrors OBJECT-TYPE
	SYNTAX  Counter
	ACCESS  read-only
	STATUS  mandatory
	DESCRIPTION
		"This counter is incremented when a station detects the absence of
		 transitions for five half-bit timers (burst-five error)."
	::= { tnTRVer1 10 }
tnTRV1StatsACErrors OBJECT-TYPE
	SYNTAX  Counter
	ACCESS  read-only
	STATUS  mandatory
	DESCRIPTION
		"This counter is incremented when a station receives an AMP or SMP 
		 frame in which A is equal to C is equal to 0, and then receives
		 another SMP frame with A is equal to C is equal to 0 without first 
		 receiving an AMP frame. It denotes a station that cannot set the AC 
		 bits properly."
	::= { tnTRVer1 11 }
tnTRV1StatsAbortTransErrors OBJECT-TYPE
	SYNTAX  Counter
	ACCESS  read-only
	STATUS  mandatory
	DESCRIPTION
		"This counter is incremented when a station transmits an abort 
		 delimiter while transmitting."
	::= { tnTRVer1 12 }
tnTRV1StatsInternalErrors OBJECT-TYPE
	SYNTAX  Counter
	ACCESS  read-only
	STATUS  mandatory
	DESCRIPTION
		"This counter is incremented when a station recognizes an internal 
		 error."
	::= { tnTRVer1 13 }
tnTRV1StatsLostFrameErrors OBJECT-TYPE
	SYNTAX  Counter
	ACCESS  read-only
	STATUS  mandatory
	DESCRIPTION
		"This counter is incremented when a station is transmitting and its 
		 TRR timer expires.  This condition denotes a condition where a
		 transmitting station in strip mode does not receive the trailer of 
		 the frame before the TRR timer goes off."
	::= { tnTRVer1 14 }
tnTRV1StatsReceiveCongestions OBJECT-TYPE
	SYNTAX  Counter
	ACCESS  read-only
	STATUS  mandatory
	DESCRIPTION
		"This counter is incremented when a station recognizes a frame 
		 addressed to its specific address, but has no available buffer space 
		 indicating that the station is congested."
	::= { tnTRVer1 15 }
tnTRV1StatsFrameCopiedErrors OBJECT-TYPE
	SYNTAX  Counter
	ACCESS  read-only
	STATUS  mandatory
	DESCRIPTION
		"This counter is incremented when a station recognizes a frame 
		 addressed to its specific address and detects that the FS field A 
		 bits are set to 1 indicating a possible line hit or duplicate 
		 address."
	::= { tnTRVer1 16 }
tnTRV1StatsTokenErrors OBJECT-TYPE
	SYNTAX  Counter
	ACCESS  read-only
	STATUS  mandatory
	DESCRIPTION
		"This counter is incremented when a station acting as the active 
		 monitor recognizes an error condition that needs a token 
		 transmitted."
	::= { tnTRVer1 17 }
tnTRV1StatsSoftErrors OBJECT-TYPE
	SYNTAX  Counter
	ACCESS  read-only
	STATUS  mandatory
	DESCRIPTION
		"The number of Soft Errors the interface has detected. It directly 
		 corresponds to the number of Report Error MAC frames that this 
		 interface has transmitted.  Soft Errors are those which are 
		 recoverable by the MAC layer protocols."
	::= { tnTRVer1 18 }
tnTRV1StatsHardErrors OBJECT-TYPE
	SYNTAX  Counter
	ACCESS  read-only
	STATUS  mandatory
	DESCRIPTION
		"The number of times this interface has detected an immediately 
		 recoverable fatal error.  It denotes the number of times this 
		 interface is either transmitting or receiving beacon MAC frames."
	::= { tnTRVer1 19 }
tnTRV1StatsSignalLoss OBJECT-TYPE
	SYNTAX  Counter
	ACCESS  read-only
	STATUS  mandatory
	DESCRIPTION
		"The number of times this interface has detected the loss of signal 
		 condition from the ring."
	::= { tnTRVer1 20 }
tnTRV1StatsTransmitBeacons OBJECT-TYPE
	SYNTAX  Counter
	ACCESS  read-only
	STATUS  mandatory
	DESCRIPTION
		"The number of times this interface has transmitted a beacon frame."
	::= { tnTRVer1 21 }
tnTRV1StatsRecoverys OBJECT-TYPE
	SYNTAX  Counter
	ACCESS  read-only
	STATUS  mandatory
	DESCRIPTION
		"The number of Claim Token MAC frames received or transmitted after 
		 the interface has received a Ring Purge MAC frame.  This counter 
		 signifies the number of times the ring has been purged and is being 
		 recovered back into a normal operating state."
	::= { tnTRVer1 22 }
tnTRV1StatsLobeWires OBJECT-TYPE
	SYNTAX  Counter
	ACCESS  read-only
	STATUS  mandatory
	DESCRIPTION
		"The number of times the interface has detected an open or short 
		 circuit in the lobe data path.  The adapter will be closed and 
		 dot5RingState will signify this condition."
	::= { tnTRVer1 23 }
tnTRV1StatsRemoves OBJECT-TYPE
	SYNTAX  Counter
	ACCESS  read-only
	STATUS  mandatory
	DESCRIPTION
		"The number of times the interface has received a Remove Ring Station 
		 MAC frame request.  When this frame is received the interface will 
		 enter the close state and dot5RingState will signify this condition."
	::= { tnTRVer1 24 }
tnTRV1StatsSingles OBJECT-TYPE
	SYNTAX  Counter
	ACCESS  read-only
	STATUS  mandatory
	DESCRIPTION
		"The number of times the interface has sensed that it is the only 
		 station on the ring.  This will happen if the interface is the first 
		 one up on a ring, or if there is a hardware problem."
	::= { tnTRVer1 25 }
tnTRV1StatsFreqErrors OBJECT-TYPE
	SYNTAX  Counter
	ACCESS  read-only
	STATUS  optional
	DESCRIPTION
		"The number of times the interface has detected that the frequency of 
		 the incoming signal differs from the expected frequency by more than 
		 that specified by the IEEE 802.5 standard, see chapter 7 in [10]."
	::= { tnTRVer1 26 }
tnTRV1TimerReturnRepeat  OBJECT-TYPE
	SYNTAX  INTEGER
	ACCESS  read-only
	STATUS  mandatory
	DESCRIPTION
		"The time-out value used to ensure the interface will return to 
		 Repeat State, in units of 100 micro-seconds.  The value should be 
		 greater than the maximum ring latency.  Implementers are encouraged 
		 to provide read-write access to this object if that is 
		 possible/useful in their system, but giving due consideration to the 
		 dangers of write-able timers."
	::= { tnTRVer1 27 }
tnTRV1TimerHolding  OBJECT-TYPE
	SYNTAX  INTEGER
	ACCESS  read-only
	STATUS  mandatory
	DESCRIPTION
		"Maximum period of time a station is permitted to transmit frames 
		 after capturing a token, in units of 100 micro-seconds.  
		 Implementers are encouraged to provide read-write access to this 
		 object if that is possible/useful in their system, but giving due 
		 consideration to the dangers of write-able timers."
	::= { tnTRVer1 28 }
tnTRV1TimerQueuePDU  OBJECT-TYPE
	SYNTAX  INTEGER
	ACCESS  read-only
	STATUS  mandatory
	DESCRIPTION
		"The time-out value for enqueuing of an SMP PDU after reception of an 
		 AMP or SMP frame in which the A and C bits were equal to 0, in units 
		 of 100 micro-seconds.  Implementors are encouraged to provide 
		 read-write access to this object if that is possible/useful in their 
		 system, but giving due consideration to the dangers of write-able 
		 timers."
	::= { tnTRVer1 29 }
tnTRV1TimerValidTransmit OBJECT-TYPE
	SYNTAX  INTEGER
	ACCESS  read-only
	STATUS  mandatory
	DESCRIPTION
		"The time-out value used by the active monitor to detect the absence 
		 of valid transmissions, in units of 100 micro-seconds.  Implementers 
		 are encouraged to provide read-write access to this object if that 
		 is possible/useful in their system, but giving due consideration to 
		 the dangers of write-able timers."
	::= { tnTRVer1 30 }
tnTRV1TimerNoToken  OBJECT-TYPE
	SYNTAX  INTEGER
	ACCESS  read-only
	STATUS  mandatory
	DESCRIPTION
		"The time-out value used to recover from various-related error 
		 situations [9].  If N is the maximum number of stations on the ring, 
		 the value of this timer is normally: dot5TimerReturnRepeat + N * 
		 dot5TimerHolding.  Implementors are encouraged to provide read-write 
		 access to this object if that is possible/useful in their system, 
		 but giving due consideration to the dangers of write-able timers."
	::= { tnTRVer1 31 }
tnTRV1TimerActiveMon  OBJECT-TYPE
	SYNTAX  INTEGER
	ACCESS  read-only
	STATUS  mandatory
	DESCRIPTION
		"The time-out value used by the active monitor to stimulate the 
		 enqueuing of an AMP PDU for transmission, in units of 100 
		 micro-seconds.  Implementors are encouraged to provide read-write 
		 access to this object if that is possible/useful in their system, 
		 but giving due consideration to the dangers of write-able timers."
	::= { tnTRVer1 32 }
tnTRV1TimerStandbyMon  OBJECT-TYPE
	SYNTAX  INTEGER
	ACCESS  read-only
	STATUS  mandatory
	DESCRIPTION
		"The time-out value used by the stand-by monitors to ensure that 
		 there is an active monitor on the ring and to detect a continuous 
		 stream of tokens, in units of 100 micro-seconds.  Implementers are 
		 encouraged to provide read-write access to this object if that is
		 possible/useful in their system, but giving due consideration to the 
		 dangers of write-able timers."
	::= { tnTRVer1 33 }
tnTRV1TimerErrorReport  OBJECT-TYPE
	SYNTAX  INTEGER
	ACCESS  read-only
	STATUS  mandatory
	DESCRIPTION
		"The time-out value which determines how often a station shall send a 
		 Report Error MAC frame to report its error counters, in units of 100 
		 micro-seconds.  Implementors are encouraged to provide read-write 
		 access to this object if that is possible/useful in their system, 
		 but giving due consideration to the dangers of write-able timers."
	::= { tnTRVer1 34 }
tnTRV1TimerBeaconTransmit  OBJECT-TYPE
	SYNTAX  INTEGER
	ACCESS  read-only
	STATUS  mandatory
	DESCRIPTION
		"The time-out value which determines how long a station shall remain 
		 in the state of transmitting Beacon frames before entering the 
		 Bypass state, in units of 100 micro-seconds.  Implementers are 
		 encouraged to provide read-write access to this object if that is
		 possible/useful in their system, but giving due consideration to the 
		 dangers of write-able timers."
	::= { tnTRVer1 35 }

tnTRV1TimerBeaconReceive  OBJECT-TYPE
	SYNTAX  INTEGER
	ACCESS  read-only
	STATUS  mandatory
	DESCRIPTION
		"The time-out value which determines how long a station shall receive 
		 Beacon frames from its downstream neighbor before entering the 
		 Bypass state, in units of 100 micro-seconds. Implementers are 
		 encouraged to provide read-write access to this object if that is
		 possible/useful in their system, but giving due consideration to the 
		 dangers of write-able timers."
	::= { tnTRVer1 36 }


-- Traps for use by Transition Networks agents

-- Traps are defined using the conventions in RFC 1215.

tnIntruderDetect TRAP-TYPE
	ENTERPRISE transition
	VARIABLES {spsRptrPortGroupIndex, spsRptrPortIndex}
	DESCRIPTION
		"The tnIntruderDetect trap conveys information related to the 
		automatic intrusion detection of the SPS2000. This trap is sent 
		when an intruder is detected."
	REFERENCE
		"ATT1RX04 (FORESPAR) Four(4) Managed Ethernet Repeaters 
		Data Sheet. "

	::= 1

-- IP based MIB for xFBRM and xBFFG Converters

-- sfbrmLocSystem Group
sfbrm100SystemTable  OBJECT-TYPE
    SYNTAX SEQUENCE OF Sfbrm100SystemEntry
    ACCESS not-accessible
    STATUS mandatory
    DESCRIPTION "System Information and Configuration table for the xFBRM/xBFFG 802.3ah Managed device."
	::= { sfbrmSystem 1 }

sfbrm100SystemEntry OBJECT-TYPE
    SYNTAX Sfbrm100SystemEntry
    ACCESS not-accessible
    STATUS mandatory
    DESCRIPTION "Status and configuration entries for a xFBRM/xBFFG device."
    INDEX { sfbrm100SysLocPortIndex, sfbrm100SysSecIndex }
    ::= { sfbrm100SystemTable 1 }

Sfbrm100SystemEntry ::=
	SEQUENCE {
		 sfbrm100SysLocPortIndex		 INTEGER,
		 sfbrm100SysSecIndex		 	 INTEGER,		 
		 sfbrm100SysGrpString			 DisplayString,
		 sfbrm100SysMRevision			 INTEGER,
		 sfbrm100SysCfgMatch			 INTEGER,
		 sfbrm100SysBootLoaderRevision	 OCTET STRING, 
		 sfbrm100SysFirmwareRevision	 OCTET STRING,
		 sfbrm100SysSerialNumber		 INTEGER,
		 sfbrm100SysBIAddress			 INTEGER,
		 sfbrm100SysSlotIndex			 INTEGER,
		 sfbrm100SysNumPorts			 INTEGER,
		 sfbrm100SysMACAddress			 PhysAddress,
		 sfbrm100SystemReset			 INTEGER,
		 sfbrm100SysIPaddress			 IpAddress,
		 sfbrm100SysSubnetMask			 IpAddress,
		 sfbrm100SysDefGateway			 IpAddress,
		 sfbrm100SysSNMPTrapMgr			 IpAddress,
		 sfbrm100SysRadiusAuth			 INTEGER,
		 sfbrm100SysRadiusServerAddr	 IpAddress,
		 sfbrm100SysRadiusSecret		 OCTET STRING,
		 sfbrm100SysRadiusRetry			 INTEGER,
		 sfbrm100SysRadiusTimeout		 INTEGER,
		 sfbrm100SysDHCPEnable			 INTEGER,
		 sfbrm100SysSerialAccess		 INTEGER,
		 sfbrm100SysTLPT				 INTEGER,
		 sfbrm100SysTFTPServerAddr		 IpAddress,
		 sfbrm100SysTFTPfilename		 OCTET STRING,
		 sfbrm100SysTFTPCmd				 INTEGER,       
		 sfbrm100SysTFTPServerIgnore	 INTEGER,
		 sfbrm100SysMgmtVlanId			 INTEGER,
		 sfbrm100SysSNMPAccess			 INTEGER,
		 sfbrm100SysIPAccess			 INTEGER,
		 sfbrm100SysLastGaspPdu			 INTEGER,
		 sfbrm100SysLastGaspPort		 INTEGER,
		 sfbrm100SysLocalLPT			 INTEGER,
		 sfbrm100SysLPTPort				 INTEGER,
		 sfbrm100SysAutoUpgrade			 INTEGER,
		 sfbrm100SysFormFactorSlot		 INTEGER,
		 sfbrm100SysFormFactorPort		 INTEGER,
		 sfbrm100SysOAMPort				 INTEGER
		}

sfbrm100SysLocPortIndex OBJECT-TYPE
	SYNTAX INTEGER
	ACCESS read-only
	STATUS mandatory
	DESCRIPTION "The local port index of the port to which the peer is connected.
				 The local device has an index of 0."
	        ::= { sfbrm100SystemEntry 1 }

sfbrm100SysSecIndex OBJECT-TYPE
	SYNTAX INTEGER
	ACCESS read-only
	STATUS mandatory
	DESCRIPTION "Secondary index for the table. It is always 1."
	        ::= { sfbrm100SystemEntry 2 }
	       
sfbrm100SysGrpString OBJECT-TYPE
	SYNTAX DisplayString
	ACCESS read-write
	STATUS mandatory
	DESCRIPTION "Group membership string. See 
 				 http://www.transition.com/pshelp/configmgmt1.html"
        ::= { sfbrm100SystemEntry 3 }
        
sfbrm100SysMRevision OBJECT-TYPE
	SYNTAX INTEGER
	ACCESS read-only
	STATUS mandatory
    DESCRIPTION "The marketing revision of this device. See 
 				 http://www.transition.com/pshelp/mrevision.html"
    ::= { sfbrm100SystemEntry 4 }
        
sfbrm100SysCfgMatch OBJECT-TYPE
    SYNTAX INTEGER { yes(1), no(2), notApplicable(3) }
    ACCESS read-write
    STATUS mandatory
    DESCRIPTION "See http://www.transition.com/pshelp/configmgmt1.html"
    ::= { sfbrm100SystemEntry 5 }             

sfbrm100SysBootLoaderRevision OBJECT-TYPE
    SYNTAX OCTET STRING
    ACCESS read-only
    STATUS mandatory
    DESCRIPTION "The bootloader revision level for this device."
    ::= { sfbrm100SystemEntry 6 }
        
sfbrm100SysFirmwareRevision OBJECT-TYPE
    SYNTAX OCTET STRING
    ACCESS read-only
    STATUS mandatory
    DESCRIPTION "The firmware revision level for this device."
    ::= { sfbrm100SystemEntry 7 }

sfbrm100SysSerialNumber OBJECT-TYPE
    SYNTAX INTEGER
    ACCESS read-only
    STATUS mandatory
    DESCRIPTION "The serial number of this device."
    ::= { sfbrm100SystemEntry 8 }

sfbrm100SysBIAddress  OBJECT-TYPE
    SYNTAX INTEGER
    ACCESS read-only
    STATUS mandatory
    DESCRIPTION "The serial number (BIA) of the cabinet in which the 
 				device is installed. If it is a stand-alone this is zero."
    ::= { sfbrm100SystemEntry 9 }
    
sfbrm100SysSlotIndex  OBJECT-TYPE
    SYNTAX INTEGER
    ACCESS read-only
    STATUS mandatory
    DESCRIPTION "The Slot number if installed in a chassis. Zero if stand-alone."
    ::= { sfbrm100SystemEntry 10 }
    
sfbrm100SysNumPorts OBJECT-TYPE
    SYNTAX INTEGER
    ACCESS read-only
    STATUS mandatory
    DESCRIPTION "The Number of ports on this device."
    ::= { sfbrm100SystemEntry 11 }

sfbrm100SysMACAddress OBJECT-TYPE
	SYNTAX PhysAddress 
	ACCESS read-only
	STATUS mandatory
	DESCRIPTION "The MAC address used in MGMT frames and IP Packets."
	::= { sfbrm100SystemEntry 12 }

sfbrm100SystemReset OBJECT-TYPE
	SYNTAX INTEGER { reset(1), doNothing(2) }
	ACCESS read-write
	STATUS mandatory
	DESCRIPTION "Set this to reset(1) to cause the system to reboot."
	::= { sfbrm100SystemEntry 13 }

sfbrm100SysIPaddress OBJECT-TYPE
	SYNTAX IpAddress 
	ACCESS read-write
	STATUS mandatory
	DESCRIPTION "The IPV4 address of the device."
	::= { sfbrm100SystemEntry 14 }

sfbrm100SysSubnetMask OBJECT-TYPE
	SYNTAX IpAddress 
	ACCESS read-write
	STATUS mandatory
	DESCRIPTION "The subnet mask associated with the IP address of the
                 device.  The value of the mask is an IP address with 
                 all the network bits set to 1 and all the hosts bits set to 0."
	::= { sfbrm100SystemEntry 15 }
		
sfbrm100SysDefGateway OBJECT-TYPE
	SYNTAX IpAddress 
	ACCESS read-write
	STATUS mandatory
	DESCRIPTION "The default gateway for the device"
	::= { sfbrm100SystemEntry 16 }		

sfbrm100SysSNMPTrapMgr OBJECT-TYPE
    SYNTAX IpAddress
    ACCESS read-write
    STATUS mandatory
	DESCRIPTION "The IPV4 address of the SNMP trap manager."
	::= { sfbrm100SystemEntry 17 }

-- RADIUS setting
sfbrm100SysRadiusAuth OBJECT-TYPE
	SYNTAX INTEGER { enable(1), disable(2) }
	ACCESS read-write
	STATUS mandatory
	DESCRIPTION "RADIUS authentication can be enabled or disabled using 
	             this variable. RADIUS Authentication is used for
	             management access only."
	::= { sfbrm100SystemEntry 18 }

sfbrm100SysRadiusServerAddr OBJECT-TYPE
	SYNTAX IpAddress 
	ACCESS read-write
	STATUS mandatory
	DESCRIPTION "The IPV4 address of the Radius Server."
	::= { sfbrm100SystemEntry 19 }
        
sfbrm100SysRadiusSecret OBJECT-TYPE
	SYNTAX OCTET STRING 
	ACCESS read-write
	STATUS mandatory
	DESCRIPTION "The shared secret between the device and RADIUS server. A read returns 'xxx'
				 for security."
	::= { sfbrm100SystemEntry 20 }

sfbrm100SysRadiusRetry OBJECT-TYPE
	SYNTAX INTEGER
	ACCESS read-write
	STATUS mandatory
	DESCRIPTION "The number of times the device would try to contact the 
	             RADIUS server, when there is any communication problem."
	::= { sfbrm100SystemEntry 21 }

sfbrm100SysRadiusTimeout OBJECT-TYPE
	SYNTAX INTEGER
	ACCESS read-write
	STATUS mandatory
	DESCRIPTION "The number of seconds the device would wait for the server
	             response before it times out."
	::= { sfbrm100SystemEntry 22 }

sfbrm100SysDHCPEnable OBJECT-TYPE
	SYNTAX INTEGER { enabled(1), disabled(2) }
	ACCESS read-write
	STATUS mandatory
	DESCRIPTION "Enable/Disable DHCP. A reset of the system is needed."
	::= { sfbrm100SystemEntry 23 }

sfbrm100SysSerialAccess OBJECT-TYPE
	SYNTAX INTEGER {enabled(1), disabled(2) }
	ACCESS read-write
	STATUS mandatory
	DESCRIPTION "Enable/Disable access to USB Port."
	::= { sfbrm100SystemEntry 24 }

sfbrm100SysTLPT OBJECT-TYPE
	SYNTAX INTEGER { enabled(1), disabled(2) }
	ACCESS read-write
	STATUS mandatory
	DESCRIPTION "Enable/disable Transparent Link Pass through.
				If the Peer's remote link goes down, the link down 
				is passed on to the other end while the OAM channel 
				is still active."
	::= { sfbrm100SystemEntry 25 }
	       
-- tftp
sfbrm100SysTFTPServerAddr OBJECT-TYPE
	SYNTAX IpAddress 
	ACCESS read-write
	STATUS mandatory
	DESCRIPTION "The IPV4 address of the TFTP Server."
	::= { sfbrm100SystemEntry 26 }

sfbrm100SysTFTPfilename OBJECT-TYPE
	SYNTAX OCTET STRING
	ACCESS read-write
	STATUS mandatory
	DESCRIPTION "The Firmware file to be downloaded from the TFTP Server
				 for upgrading."
	::= { sfbrm100SystemEntry 27 }
	
sfbrm100SysTFTPCmd OBJECT-TYPE
	SYNTAX INTEGER { perform(1), donothing(2), notApplicable(3) }
	ACCESS read-write
	STATUS mandatory
	DESCRIPTION "To initiate a TFTP upgrading, set the value to
				perform(1), the systems resets and the bootloader
				is invoked to perform the upgrade."
	::= { sfbrm100SystemEntry 28 }
	
sfbrm100SysTFTPServerIgnore OBJECT-TYPE
	SYNTAX INTEGER { enabled(1), disabled(2), notApplicable(3) }
	ACCESS read-write
	STATUS mandatory
	DESCRIPTION "In some configuration, when the device uses DHCP
				to get its IP address, it also receives the tftpserver
				address for upgrading. When this variable is enabled
				the tftpserver address got from DHCP is ignored.
				This is valid only when DHCP is enabled, else
				notApplicable(3) is returned. It is disabled by default."
	::= { sfbrm100SystemEntry 29 }

sfbrm100SysMgmtVlanId OBJECT-TYPE
	SYNTAX INTEGER 
	ACCESS read-only
	STATUS mandatory
	DESCRIPTION "VLAN Id for the management frames. This is valid only when
				vlan is enabled. This creates a secure channel for all
				management traffic."
	::= { sfbrm100SystemEntry 30 }
	
sfbrm100SysSNMPAccess OBJECT-TYPE
	SYNTAX INTEGER { enabled(1), disabled(2) }
	ACCESS read-write
	STATUS mandatory
	DESCRIPTION "The SNMP access to the device."
	::= { sfbrm100SystemEntry 31 }
	
sfbrm100SysIPAccess OBJECT-TYPE
	SYNTAX INTEGER { enabled(1), disabled(2) }
	ACCESS read-write
	STATUS mandatory
	DESCRIPTION "IP management access to the device."
	::= { sfbrm100SystemEntry 32 }

sfbrm100SysLastGaspPdu  OBJECT-TYPE
	SYNTAX INTEGER { snmpTrap(1), oamDyingGaspPdu(2) }
	ACCESS read-write
	STATUS mandatory
	DESCRIPTION "This mib variable is used to choose the type of PDU
				 to be generated on the last gasp event."
	::= { sfbrm100SystemEntry 33 }

sfbrm100SysLastGaspPort  OBJECT-TYPE
	SYNTAX INTEGER 
	ACCESS read-write
	STATUS mandatory
	DESCRIPTION "When there are multiple OAM enabled ports, this variable 
				 decides which port to send the Dying gasp OAM PDU. The 
				 default is Port 2. This variable is valid only
				 when sfbrm100SysLastGaspPdu is set to oamDyingGaspPdu(2)."
	::= { sfbrm100SystemEntry 34 }

sfbrm100SysLocalLPT   OBJECT-TYPE
	SYNTAX INTEGER { enabled(1), disabled(2) }
	ACCESS read-write
	STATUS mandatory
	DESCRIPTION "When the monitored port (sfbrm100SysLPTPort)link goes down, the 
				other port is brought down when this is enabled. This is also named 
				as Selective Link Pass Through."
	::= { sfbrm100SystemEntry 35 }

sfbrm100SysLPTPort   OBJECT-TYPE
	SYNTAX INTEGER 
	ACCESS read-write
	STATUS mandatory
	DESCRIPTION "This determines the port, on which the Transparent Link pass through
				 and the Selective/local Link pass through will be active. Any link change
				 on this port activates the TLPT and LocalLPT. 
				 This is should be the port with active OAM session."
	::= { sfbrm100SystemEntry 36 }    
	
sfbrm100SysAutoUpgrade OBJECT-TYPE
	SYNTAX INTEGER { enabled(1), disabled(2) }
	ACCESS read-write
	STATUS mandatory
	DESCRIPTION "When enabled, auto upgrade of this device can be done by its peer.
				By default this is 'enabled(1)'. When disabled, the peer should do a Force
				upgrade in order to override this variable.
				Auto upgrade feature affects when this device is in 'passive' mode
				during the OAM session and is running a different firmware than its peer."
	::= { sfbrm100SystemEntry 37 }    
	
sfbrm100SysFormFactorSlot OBJECT-TYPE
	SYNTAX INTEGER 
	ACCESS read-only
	STATUS mandatory
	DESCRIPTION "This read-only variable gives the number of slots in a chassis
				 this unit occupies if its a chassis card."
	::= { sfbrm100SystemEntry 38 }  
	
sfbrm100SysFormFactorPort OBJECT-TYPE
	SYNTAX INTEGER 
	ACCESS read-only
	STATUS mandatory
	DESCRIPTION "This read-only variables gives type of ports present on this board.
				 The values and description for each board :
				 	1 -  xFBRM 10/100BaseT to 100BaseFx
				 	2 -  xFBRM 100BaseFx to 1000BaseX
				 	3 -  xBFFG 1000BaseX to 1000BaseX
				    4 -  xBFFG 10/100/1000BaseT to 1000BaseX
				    5 -  xFBRM 10/100BaseT to 2x100BaseFx
				    6 -  xBFFG 10/100/1000BaseT to 2x1000BaseX
				 "
	::= { sfbrm100SystemEntry 39 }  
			
sfbrm100SysOAMPort OBJECT-TYPE
	SYNTAX INTEGER 
	ACCESS read-write
	STATUS mandatory
	DESCRIPTION "When only one OAM session is allowed, this determines the port
				that will be used for sending and receiving OAM messages. 
				This also restricts the	number of manageable remotes to be 1. 
				All other ports have OAM admin state will be disabled, this will affect
				the current OAM sessions."
	::= { sfbrm100SystemEntry 40 }  
	
sfbrm100SwTable OBJECT-TYPE
    SYNTAX SEQUENCE OF Sfbrm100SwEntry
    ACCESS not-accessible
    STATUS mandatory
    DESCRIPTION "Switch Status and configuration table"
	::= { sfbrmSwitch 1 }

sfbrm100SwEntry OBJECT-TYPE
    SYNTAX Sfbrm100SwEntry
    ACCESS not-accessible
    STATUS mandatory
    DESCRIPTION "Status and configuration entries for switch setting."
    INDEX { sfbrm100SwPortIndex, sfbrm100SwSecIndex }
    ::= { sfbrm100SwTable 1 }

Sfbrm100SwEntry ::=         
	    SEQUENCE {                  
	    	sfbrm100SwPortIndex    		  	INTEGER,
	    	sfbrm100SwSecIndex      		INTEGER,
	    	sfbrm100SwATUAgeTimeout   		INTEGER,
	    	sfbrm100SwIngressMonPort 		INTEGER,
	    	sfbrm100SwEgressMonPort  		INTEGER,
	    	sfbrm100SwFactoryDefaults	 	INTEGER,
	    	sfbrm100SwResetCounters   		INTEGER,
	    	sfbrm100SwHistMode		 		INTEGER,
	    	sfbrm100SwIEEEPriRemap0	 	 	INTEGER,
	    	sfbrm100SwIEEEPriRemap1	  		INTEGER,
	    	sfbrm100SwIEEEPriRemap2	 		INTEGER,
	    	sfbrm100SwIEEEPriRemap3	 		INTEGER,
	    	sfbrm100SwIEEEPriRemap4	 		INTEGER,
	    	sfbrm100SwIEEEPriRemap5	 		INTEGER,
	    	sfbrm100SwIEEEPriRemap6	 		INTEGER,
	    	sfbrm100SwIEEEPriRemap7	 		INTEGER,
	    	sfbrm100SwFlushFdb		  		INTEGER,
	    	sfbrm100SwFlushVlandb	  		INTEGER,
	    	sfbrm100SwUseDoubleTagData 		INTEGER,
	    	sfbrm100SwFiberRedundancy		INTEGER,
	    	sfbrm100SwFiberRedundRevert		INTEGER,
	    	sfbrm100SwFbrRedundActivePort 	INTEGER,
	    	sfbrm100SwSupressVlanViolations INTEGER,
	    	sfbrm100SwSupressMACViolations	INTEGER
		}           
		
sfbrm100SwPortIndex OBJECT-TYPE
	SYNTAX INTEGER
	ACCESS read-only
	STATUS mandatory
	DESCRIPTION "The Local Port Index of the local port to which the peer is connected.
				 The local device has the port index of 0."
	::= { sfbrm100SwEntry 1 }

sfbrm100SwSecIndex OBJECT-TYPE
	SYNTAX INTEGER
	ACCESS read-only
	STATUS mandatory
	DESCRIPTION "Secondary index for the table. It is always 1."
	::= { sfbrm100SwEntry 2 }

sfbrm100SwATUAgeTimeout OBJECT-TYPE
	SYNTAX INTEGER
	ACCESS read-write
	STATUS mandatory     
	DESCRIPTION "The ATU ageing time in seconds. This indicates the time that each
				ATU entry remains valid in the database before being purged. The minimum
				aging time is 15 seconds and maximum is 64 minutes. A ageing time time of zero
				disables ageing. i.e All addresses remain in the database, they are never purged.
				The aging time should be in 15 sec increments."
	::= { sfbrm100SwEntry 3 }

sfbrm100SwIngressMonPort OBJECT-TYPE
	SYNTAX INTEGER
	ACCESS read-write
	STATUS mandatory
	DESCRIPTION "The Ingress monitor port. Frames that are targeted towards
				an Ingress monitor port go out this port. Not-applicable for a 
				2-Port device."
	::= { sfbrm100SwEntry 4 }

sfbrm100SwEgressMonPort OBJECT-TYPE
	SYNTAX INTEGER
	ACCESS read-write
	STATUS mandatory
	DESCRIPTION "The egress monitor port. Frames that are targeted towards
				 an Egress monitor port go out this port. Not-applicable for a 
				2-Port device."
	::= { sfbrm100SwEntry 5 }        

sfbrm100SwFactoryDefaults OBJECT-TYPE
	SYNTAX INTEGER   { reset(1), notApplicable(2) }
	ACCESS read-write
	STATUS mandatory
	DESCRIPTION "Reset the switch to factory default settings. 
				A read always returns a notApplicable(2) value."
	::= { sfbrm100SwEntry 6 }        

sfbrm100SwResetCounters OBJECT-TYPE
	SYNTAX INTEGER  { reset(1), notApplicable(2) }
	ACCESS read-write
	STATUS mandatory
	DESCRIPTION "Resets all port counters. A read always returns a notApplicable(2) value."
	::= { sfbrm100SwEntry 7 }        
	
sfbrm100SwHistMode OBJECT-TYPE
	SYNTAX INTEGER  { cntRx(1), cntTx(2), cntRxTx(3) }
	ACCESS read-write
	STATUS mandatory
	DESCRIPTION "The port histogram counters can be set to :
					cntRx   (1) -  count Rx frames only.
					cntTx   (2)  - count Tx frames only
					cntRxTx (3)  - count Rx and Tx frames.
				This affects the histogram counters." 
					
	::= { sfbrm100SwEntry 8 }        

sfbrm100SwIEEEPriRemap0		OBJECT-TYPE
	SYNTAX INTEGER
	ACCESS read-write
	STATUS mandatory
	DESCRIPTION "All Frames with priority 0 are remapped to this set value inside the switch."
	::= { sfbrm100SwEntry 9 }
	
sfbrm100SwIEEEPriRemap1		OBJECT-TYPE
	SYNTAX INTEGER
	ACCESS read-write
	STATUS mandatory
	DESCRIPTION "All Frames with priority 1 are remapped to this set value inside the switch."
	::= { sfbrm100SwEntry 10 }
	
sfbrm100SwIEEEPriRemap2		OBJECT-TYPE
	SYNTAX INTEGER
	ACCESS read-write
	STATUS mandatory
	DESCRIPTION "All Frames with priority 2 are remapped to this set value inside the switch."
	::= { sfbrm100SwEntry 11 }
	
sfbrm100SwIEEEPriRemap3		OBJECT-TYPE
	SYNTAX INTEGER
	ACCESS read-write
	STATUS mandatory
	DESCRIPTION "All Frames with priority 3 are remapped to this set value inside the switch."
	::= { sfbrm100SwEntry 12 }
	
sfbrm100SwIEEEPriRemap4		OBJECT-TYPE
	SYNTAX INTEGER
	ACCESS read-write
	STATUS mandatory
	DESCRIPTION "All Frames with priority 4 are remapped to this set value inside the switch."
	::= { sfbrm100SwEntry 13 }
	
sfbrm100SwIEEEPriRemap5		OBJECT-TYPE
	SYNTAX INTEGER
	ACCESS read-write
	STATUS mandatory
	DESCRIPTION "All Frames with priority 5 are remapped to this set value inside the switch."
	::= { sfbrm100SwEntry 14 }
	
sfbrm100SwIEEEPriRemap6		OBJECT-TYPE
	SYNTAX INTEGER
	ACCESS read-write
	STATUS mandatory
	DESCRIPTION "All Frames with priority 6 are remapped to this set value inside the switch."
	::= { sfbrm100SwEntry 15 }
	
sfbrm100SwIEEEPriRemap7		OBJECT-TYPE
	SYNTAX INTEGER
	ACCESS read-write
	STATUS mandatory
	DESCRIPTION "All Frames with priority 7 are remapped to this set value inside the switch."
	::= { sfbrm100SwEntry 16 }

sfbrm100SwFlushFdb		OBJECT-TYPE
	SYNTAX INTEGER { flushAll(1), flushNonStatic(2), doNothing(3) }
	ACCESS read-write
	STATUS mandatory
	DESCRIPTION "Flushes all static entries in the forwarding database.
	             When set to flushAll(1), all the entries in the database are purged. 
	             when set to flushNonStatic(2), all non-static entries in the database
	             are flushed.
	             A read always returns doNothing(3)."
	::= { sfbrm100SwEntry 17 }

sfbrm100SwFlushVlandb   OBJECT-TYPE
	SYNTAX INTEGER { flushAll(1), doNothing(2) }
	ACCESS read-write
	STATUS mandatory
	DESCRIPTION "Flushes all VLAN entries in the database. When set to flushAll(1), 
				all VLAN entries in the database are purged, and VLAN is disabled automatically.
	            A read always returns doNothing(2)."
	::= { sfbrm100SwEntry 18 }

sfbrm100SwUseDoubleTagData   OBJECT-TYPE
	SYNTAX INTEGER { use(1), ignore(2) }
	ACCESS read-write
	STATUS mandatory
	DESCRIPTION "When Double tagging is enabled on any of the ports, this
				mib variable decides if the tag that is removed from Ingress
				frames should be used or ignored when making switching decision
				on the frame."
	::= { sfbrm100SwEntry 19 }
	
sfbrm100SwFiberRedundancy 	OBJECT-TYPE
	SYNTAX INTEGER { enabled(1), disabled(2), notApplicable(3) }
	ACCESS read-write
	STATUS mandatory
	DESCRIPTION "This feature is applicable in the xFBRM/xBFFG series 
				which have 2 fiber ports. 
				When set to enabled, the primary and backup fiber 
                ports are assumed to be connected to the same 
                destination. Only one of these paths will be active
                at any given time, and the configuration
                settings kept in sync between the ports. 
                When set to disabled, the primary and backup ports 
                are assumed to be connected to different 
                destinations, and lose their special functions."    
	::= { sfbrm100SwEntry 20 }	
	
sfbrm100SwFiberRedundRevert	OBJECT-TYPE
	SYNTAX INTEGER { revert(1), noRevert(2), notApplicable(3) }
	ACCESS read-write
	STATUS mandatory
	DESCRIPTION "This mib variable is applicable only if 
				'sfbrm100SwFiberRedundancy' is enabled. When there
				is a failure in the primary and secondary fiber
				takes over, this determines what happens when primary
				comes back again. Does the link switch back to primary 
				or the secondary takes over as the primary link."    
	::= { sfbrm100SwEntry 21 }	

sfbrm100SwFbrRedundActivePort OBJECT-TYPE
	SYNTAX INTEGER 
	ACCESS read-write
	STATUS mandatory
	DESCRIPTION "This mib variable is applicable only if 
				'sfbrm100SwFiberRedundancy' is enabled.
				This indicates the current active port that 
				is operational as the primary link."
	::= { sfbrm100SwEntry 22 }	

sfbrm100SwSupressVlanViolations  OBJECT-TYPE
	SYNTAX INTEGER { enabled(1), disabled(2)}
	ACCESS read-write
	STATUS mandatory
	DESCRIPTION "This supresses all VLAN database violations and 
				the traps caused by these events."    
	::= { sfbrm100SwEntry 23 }

sfbrm100SwSupressMACViolations  OBJECT-TYPE
	SYNTAX INTEGER { enabled(1), disabled(2)}
	ACCESS read-write
	STATUS mandatory
	DESCRIPTION "This supresses all MAC database violations and 
				the traps caused by these events."    
	::= { sfbrm100SwEntry 24 }
	
-- IP Priority mapping Table
sfbrm100SwIPPrioTable OBJECT-TYPE
    SYNTAX SEQUENCE OF Sfbrm100SwIPPrioEntry
    ACCESS not-accessible
    STATUS mandatory
    DESCRIPTION "IP Traffic class table."
	::= { sfbrmSwitch 2 }

sfbrm100SwIPPrioEntry OBJECT-TYPE
    SYNTAX Sfbrm100SwIPPrioEntry
    ACCESS not-accessible
    STATUS mandatory
    DESCRIPTION "Each entry represents the remapped value for each traffic class."
    INDEX { sfbrm100SwIPPrioPortIndex, sfbrm100SwIPPrioIndex }
    ::= { sfbrm100SwIPPrioTable 1 }

Sfbrm100SwIPPrioEntry ::=         
	    SEQUENCE {       
	    	sfbrm100SwIPPrioPortIndex  	INTEGER,
	    	sfbrm100SwIPPrioIndex 		INTEGER,   
	    	sfbrm100SwIPPrioTC 			INTEGER,
	    	sfbrm100SwIPPrioRemap    	INTEGER
		} 

sfbrm100SwIPPrioPortIndex OBJECT-TYPE
	SYNTAX INTEGER
	ACCESS read-only
	STATUS mandatory
	DESCRIPTION "The Local port to which the device is connected.
	             The local device has the port index as zero."
	::= { sfbrm100SwIPPrioEntry 1 }

sfbrm100SwIPPrioIndex OBJECT-TYPE
	SYNTAX INTEGER
	ACCESS read-only
	STATUS mandatory
	DESCRIPTION "The IP traffic class remap table index."
	::= { sfbrm100SwIPPrioEntry 2 }
		
sfbrm100SwIPPrioTC OBJECT-TYPE
	SYNTAX INTEGER
	ACCESS read-only
	STATUS mandatory
	DESCRIPTION "The IP traffic class value."
	::= { sfbrm100SwIPPrioEntry 3 }

sfbrm100SwIPPrioRemap OBJECT-TYPE
	SYNTAX INTEGER  { pri0(1), pri1(2), pri2(3), pri3(4) }
	ACCESS read-write
	STATUS mandatory
	DESCRIPTION "The IP traffic class defined by sfbrm100SwIPPrioTC, is given the
				priority value set in this variable."
	::= { sfbrm100SwIPPrioEntry 4 }

-- sfbrmPort   
sfbrm100PortTable OBJECT-TYPE
    SYNTAX SEQUENCE OF Sfbrm100PortEntry
    ACCESS not-accessible
    STATUS mandatory
    DESCRIPTION "Port attributes status and configuration."
	::= { sfbrmPort 1 }

sfbrm100PortEntry OBJECT-TYPE
    SYNTAX Sfbrm100PortEntry
    ACCESS not-accessible
    STATUS mandatory
    DESCRIPTION "Status and configuration entries for a each port on the device."
    INDEX { sfbrm100PortLocIndex, sfbrm100PortRmtIndex }
    ::= { sfbrm100PortTable 1 }

Sfbrm100PortEntry ::=         
	    SEQUENCE {
	    	sfbrm100PortLocIndex    	        INTEGER,
			sfbrm100PortRmtIndex   	            INTEGER,	    	
			sfbrm100PortGrpString          	    DisplayString,
			sfbrm100PortConnType             	CpsConnector,
			sfbrm100PortOAMState             	INTEGER,     
			sfbrm100PortOAMModeCtrl            	INTEGER,     			
			sfbrm100PortRmtLoopback				INTEGER,
			sfbrm100PortIgnoreLoopback			INTEGER,
			sfbrm100PortAdvPause		   	    INTEGER,
			sfbrm100PortAdv1000FDX			    INTEGER,
			sfbrm100PortAdv1000HDX			    INTEGER,
			sfbrm100PortAdv100FDX			    INTEGER,
			sfbrm100PortAdv100HDX			    INTEGER,
			sfbrm100PortAdv10FDX		        INTEGER,
			sfbrm100PortAdv10HDX		        INTEGER,
			sfbrm100PortAutoneg       	        INTEGER,
			sfbrm100PortFDuplex		    	    INTEGER,
			sfbrm100PortFSpeed  		        INTEGER,
			sfbrm100PortLpPauseAbility			INTEGER,
			sfbrm100PortLpAutonegAbility		INTEGER,
			sfbrm100PortLinkState				INTEGER,
			sfbrm100PortAutonegState			INTEGER,
			sfbrm100PortDuplex					INTEGER,
			sfbrm100PortSpeed					INTEGER,
			sfbrm100PortFEFI 			  	    INTEGER,
			sfbrm100PortAutocross		    	INTEGER,
			sfbrm100PortLock				    INTEGER,
			sfbrm100PortIgnoreWrongData	  		INTEGER,
			sfbrm100PortIGMPSnoop		    	INTEGER,
			sfbrm100PortDoubleTagging	    	INTEGER,
			sfbrm100PortUseIPTC			    	INTEGER,
			sfbrm100PortUseTagTC			    INTEGER,
			sfbrm100PortUseBothTC		    	INTEGER,
			sfbrm100PortVLANTunnel		    	INTEGER,
			sfbrm100PortFwdUnknown			    INTEGER,			
			sfbrm100PortDefForward			    INTEGER,
			sfbrm100PortAdminState		    	INTEGER,
			sfbrm100PortVTUPriOverride		    INTEGER,
			sfbrm100PortSAPriOverride		    INTEGER,
			sfbrm100PortDAPriOverride	    	INTEGER,
			sfbrm100PortVLANStatus		 	    INTEGER,
			sfbrm100PortDiscardTagged	   		INTEGER,
			sfbrm100PortDiscardUntagged		    INTEGER,
			sfbrm100PortEgressMonitor	    	INTEGER,
			sfbrm100PortIngressMonitor	 	  	INTEGER,
			sfbrm100PortPri3IngressRateCtrl	  	INTEGER,
			sfbrm100PortPri2IngressRateCtrl  	INTEGER,
			sfbrm100PortPri1IngressRateCtrl  	INTEGER,
			sfbrm100PortPri0IngressRate	    	INTEGER,
			sfbrm100PortIngressLimitMode 		INTEGER,
			sfbrm100PortEgressRate		    	INTEGER,
			sfbrm100PortDefaultPriority      	INTEGER,
			sfbrm100PortForceDefVLANId       	INTEGER,
			sfbrm100PortDefaultVLANId			INTEGER,
			sfbrm100PortBasedVLANTbl			INTEGER,
			sfbrm100PortIEEEPriRemap0			INTEGER,
			sfbrm100PortIEEEPriRemap1			INTEGER,
			sfbrm100PortIEEEPriRemap2			INTEGER,
			sfbrm100PortIEEEPriRemap3			INTEGER,
			sfbrm100PortIEEEPriRemap4			INTEGER,
			sfbrm100PortIEEEPriRemap5			INTEGER,
			sfbrm100PortIEEEPriRemap6			INTEGER,
			sfbrm100PortIEEEPriRemap7			INTEGER,
			sfbrm100PortVCTest 				    INTEGER,
			sfbrm100PortVCTxMDI0Status			INTEGER,
			sfbrm100PortTxMDI0Dist				INTEGER,
			sfbrm100PortVCRxMDI1Status			INTEGER,
			sfbrm100PortRxMDI1Dist				INTEGER,
			sfbrm100PortVCMDI2Status			INTEGER,
			sfbrm100PortMDI2Dist				INTEGER,
			sfbrm100PortVCMDI3Status			INTEGER,
			sfbrm100PortMDI3Dist				INTEGER,
			sfbrm100PortResetCounters			INTEGER,
			sfbrm100PortIPTrafficAccess			INTEGER,
			sfbrm100PortResetOAMCounters		INTEGER,
			sfbrm100PortForceAutoUpgrade		INTEGER,
			sfbrm100PortModeType				INTEGER,
			sfbrm100PortOAMMode					INTEGER,
			sfbrm100PortPhyNumber				INTEGER,
			sfbrm100PortIngressRateLimit2    	INTEGER,						
			sfbrm100PortEgressRateLimit2    	INTEGER									
		}                       

sfbrm100PortLocIndex  OBJECT-TYPE
	SYNTAX INTEGER
	ACCESS read-only
	STATUS mandatory
	DESCRIPTION "Uniquely indentifies each port on the device."
	::= { sfbrm100PortEntry 1 }

sfbrm100PortRmtIndex  OBJECT-TYPE
	SYNTAX INTEGER
	ACCESS read-only
	STATUS mandatory
	DESCRIPTION "Uniquely indentifies each port on the peer device."
	::= { sfbrm100PortEntry 2 }
	
sfbrm100PortGrpString  OBJECT-TYPE
	SYNTAX DisplayString
    ACCESS read-write
	STATUS mandatory
	DESCRIPTION "Description string for each port."
	::= { sfbrm100PortEntry 3 }
	
sfbrm100PortConnType  OBJECT-TYPE
	SYNTAX CpsConnector 
	ACCESS read-only
	STATUS mandatory
	DESCRIPTION "The actual physical connector on the port."
	::= { sfbrm100PortEntry 4 }
	
sfbrm100PortOAMState  OBJECT-TYPE
	SYNTAX INTEGER { enabled(1), disabled(2) }
	ACCESS read-write
	STATUS mandatory
	DESCRIPTION "This object is used to provision the default administrative
 				 enable/disable of OAM on this interface."
	::= { sfbrm100PortEntry 5 }

sfbrm100PortOAMModeCtrl  OBJECT-TYPE
	SYNTAX INTEGER { auto(1), manual(2) }
	ACCESS read-write
	STATUS mandatory
	DESCRIPTION "This object can be used to provision the OAM mode for this interface. 
				 In auto(1) mode , the interface is set to active/passive depending on
				 if the board is in a chassis or stand-alone. The manual(2) mode lets
				 the user choose the OAM mode (active/passive)."
	::= { sfbrm100PortEntry 6 }

sfbrm100PortRmtLoopback  OBJECT-TYPE
	SYNTAX INTEGER { oamLoopback(1), alternateLoopback(2), disable(3), notSupported(4) }
	ACCESS read-write
	STATUS mandatory
	DESCRIPTION "Initiates remote loopback, if supported by remote peer."
	::= { sfbrm100PortEntry 7 }
	
sfbrm100PortIgnoreLoopback  OBJECT-TYPE
	SYNTAX INTEGER { ignore(1), process(2) }
	ACCESS read-write
	STATUS mandatory
	DESCRIPTION "If enabled, the device ignores any loopback requests."
	::= { sfbrm100PortEntry 8 }
	
sfbrm100PortAdvPause	OBJECT-TYPE
	SYNTAX INTEGER { noPause(1), symPause(2), asymPauseLp(3), asymPauseCon(4), notApplicable(5) }
	ACCESS read-write
	STATUS mandatory
	DESCRIPTION "Specifies the Pause frame advertisement capability."
	::= { sfbrm100PortEntry 9 }

sfbrm100PortAdv1000FDX	OBJECT-TYPE
	SYNTAX INTEGER  { enabled(1), disabled(2), notApplicable(3) }
	ACCESS read-write
	STATUS mandatory
	DESCRIPTION "This configuration setting controls whether or not this 
			 	port advertises willingness to connect at 1000Mbps, full 
			 	duplex.  This is ignored when autonegotiation is disabled,
				read-only value notApplicable(3)is returned. This is valid 
 				only for Gigabit Ports and not valid for fiber ports." 
	::= { sfbrm100PortEntry 10 }
	
sfbrm100PortAdv1000HDX	OBJECT-TYPE
	SYNTAX INTEGER  { enabled(1), disabled(2), notApplicable(3) }
	ACCESS read-write
	STATUS mandatory
	DESCRIPTION "This configuration setting controls whether or not this 
			 	port advertises willingness to connect at 1000Mbps, half 
			 	duplex.  This is ignored when autonegotiation is disabled,
				read-only value notApplicable(3)is returned. This is valid 
 				only for Gigabit Ports and not valid for fiber ports." 
	::= { sfbrm100PortEntry 11 }
	
sfbrm100PortAdv100FDX  OBJECT-TYPE
	SYNTAX INTEGER  { enabled(1), disabled(2), notApplicable(3) }
	ACCESS read-write
	STATUS mandatory
	DESCRIPTION "This configuration setting controls whether or not this 
			 	port advertises willingness to connect at 100Mbps, full 
			 	duplex.  This is ignored when autonegotiation is disabled,
				read-only value notApplicable(3)is returned. This is not valid 
				on Fiber ports." 
	::= { sfbrm100PortEntry 12 }
	
sfbrm100PortAdv100HDX  OBJECT-TYPE
	SYNTAX INTEGER   { enabled(1), disabled(2), notApplicable(3) }
	ACCESS read-write
	STATUS mandatory
	DESCRIPTION "This configuration setting controls whether or not this 
			 	port advertises willingness to connect at 100Mbps, half 
			 	duplex.  This is ignored when autonegotiation is disabled,
				read-only value notApplicable(3)is returned. This is not valid 
				on Fiber ports." 
	::= { sfbrm100PortEntry 13 }
	
sfbrm100PortAdv10FDX	 OBJECT-TYPE
	SYNTAX INTEGER  { enabled(1), disabled(2), notApplicable(3) }
	ACCESS read-write
	STATUS mandatory
	DESCRIPTION "This configuration setting controls whether or not this 
			 	port advertises willingness to connect at 10Mbps, full 
			 	duplex.  This is ignored when autonegotiation is disabled,
				read-only value notApplicable(3)is returned. This is not valid 
				on Fiber ports." 
	::= { sfbrm100PortEntry 14 }
	
sfbrm100PortAdv10HDX	 OBJECT-TYPE
	SYNTAX INTEGER   { enabled(1), disabled(2), notApplicable(3) }
    ACCESS read-write
	STATUS mandatory
	DESCRIPTION "This configuration setting controls whether or not this 
			 	port advertises willingness to connect at 100Mbps, half 
			 	duplex.  This is ignored when autonegotiation is disabled,
				read-only value notApplicable(3)is returned. This is not valid 
				on Fiber ports." 
	::= { sfbrm100PortEntry 15 }

sfbrm100PortAutoneg  OBJECT-TYPE
	SYNTAX INTEGER  { enabled(1), disabled(2), negotiating(3), resolved(4)}
	ACCESS read-write
	STATUS mandatory
	DESCRIPTION "Enable/Disable autonegotiation on this port."
	::= { sfbrm100PortEntry 16 }

sfbrm100PortFDuplex	OBJECT-TYPE
	SYNTAX INTEGER  { fullDuplex(1), halfDuplex(2), notApplicable(3)}
	ACCESS read-write
	STATUS mandatory
	DESCRIPTION "This is a configuration setting that controls the duplex mode; 
				fullDuplex is full duplex and halfDuplex is half duplex.
				This is valid only when autonegotiation is disabled."
	::= { sfbrm100PortEntry 17 }

sfbrm100PortFSpeed  OBJECT-TYPE
	SYNTAX INTEGER { mbps10(1), mbps100(2), mbps1000(3), notApplicable(4) }
	ACCESS read-write
	STATUS mandatory
	DESCRIPTION "This is a configuration setting that controls the speed; 
				 This is valid only when autonegotiation is disabled."
	::= { sfbrm100PortEntry 18 }
	
sfbrm100PortLpPauseAbility	OBJECT-TYPE
	SYNTAX INTEGER  { noPause(1), symPause(2), asymPauseLp(3), asymPauseCon(4), notApplicable(5) }
	ACCESS read-only
	STATUS mandatory
	DESCRIPTION "Link Partner's pause capability."
	::= { sfbrm100PortEntry 19 }
	
sfbrm100PortLpAutonegAbility	OBJECT-TYPE
	SYNTAX INTEGER  
		{  
		   spdAutoDupAuto(1), 
		   spd1000DupAuto(2), 
		   spd100DupAuto(3),
		   spd10DupAuto(4),
		   spdAutoDupFull(5),
		   spdAutoDupHalf(6),
		   spd1000DupFull(7),
		   spd1000DupHalf(8),
		   spd100DupFull(9),
		   spd100DupHalf(10),
		   spd10DupFull(11),
		   spd10DupHalf(12),
		   notcapable(13)
		}
	ACCESS read-write
	STATUS mandatory
	DESCRIPTION "The autonegotiation advertisement mode can be set using the 
				 options of this variable.
				 	spdAutoDupAuto(1)  -  Advertise all speed and duplex supported.
					spd1000DupAuto(2)  -  Advertise 1000Mbps with duplex as full and half
				    spd100DupAuto(3)   -  Advertise 100Mbps with duplex as full and half
				    spd10DupAuto(4)    -  Advertise 10Mbps with duplex as full and half
				    spdAutoDupFull(5)  -  Advertise all speeds (10, 100, 1000 Mbps) with Full duplex
				    spdAutoDupHalf(6)  -  Advertise all speeds (10, 100, 1000 Mbps) with Half duplex
				    spd1000DupFull(7)  -  Advertise 1000Mbps full duplex
				    spd1000DupHalf(8)  -  Advertise 1000Mbps half duplex
				    spd100DupFull(9)   -  Advertise 100Mbps full duplex
				    spd100DupHalf(10)  -  Advertise 100Mbps half duplex
				    spd10DupFull(11)   -  Advertise 10Mbps full duplex
				    spd10DupHalf(12)   -  Advertise 10Mbps half duplex
				   		 	
				Read-only value notApplicable returned when 
 				autonegotiation is disabled."
	::= { sfbrm100PortEntry 20 }
	
sfbrm100PortLinkState	OBJECT-TYPE
	SYNTAX INTEGER { up(1), down(2), notApplicable(3) }
	ACCESS read-only
	STATUS mandatory
	DESCRIPTION "Link status on this port."
	::= { sfbrm100PortEntry 21 }
	
sfbrm100PortAutonegState	OBJECT-TYPE
	SYNTAX INTEGER  { resolved(1), notResolved(2) }
	ACCESS read-only
	STATUS mandatory
	DESCRIPTION "The autonegotiation state or if autonegotiation is disabled it returns resolved(1)."
	::= { sfbrm100PortEntry 22 }
	
sfbrm100PortDuplex	OBJECT-TYPE
	SYNTAX INTEGER  { fullDuplex(1), halfDuplex(2), notApplicable(3)} 
	ACCESS read-only
	STATUS mandatory
	DESCRIPTION "The port's duplex value when autonegotiation is resolved."
	::= { sfbrm100PortEntry 23 }
	
sfbrm100PortSpeed	OBJECT-TYPE
	SYNTAX INTEGER { mbps10(1), mbps100(2), mbps1000(3), notApplicable(4) }
	ACCESS read-only
	STATUS mandatory
	DESCRIPTION "The port's duplex value when autonegotiation is resolved"
	::= { sfbrm100PortEntry 24 }
	
sfbrm100PortFEFI	OBJECT-TYPE
	SYNTAX INTEGER  { enabled(1), disabled(2), notApplicable(3) }
	ACCESS read-write
	STATUS mandatory
	DESCRIPTION "Enabled/Disable Far-end Fault detection. Read-only value
	             notApplicable is returned for unsupported Ethernet PHY's."
	::= { sfbrm100PortEntry 25 }
	
sfbrm100PortAutocross	OBJECT-TYPE
	SYNTAX INTEGER { mdi(1), mdiX(2), autoCross(3), notApplicable(4) }
	ACCESS read-write
	STATUS mandatory
	DESCRIPTION "This is applicable for supporting  PHY's. 
				If set to mdi(1)  the transmit happens on pair 1 & 2 and receive on 3 & 4.
				If set to mdiX(2) the transmit happens on 3 & 4 and receive on 1 & 2.
				If set to autoCross(3) - automatic crossover is enabled."
	::= { sfbrm100PortEntry 26 }
	
sfbrm100PortLock	OBJECT-TYPE
	SYNTAX INTEGER  { enabled(1), disabled(2) }
	ACCESS read-write
	STATUS mandatory
	DESCRIPTION "When enabled, it disables the automatic learning of source addresses 
	             on this port and drops frames where the SA does not exist in the ATU, and 
	             originates a ATU Miss Violation Trap."
	::= { sfbrm100PortEntry 27 }
	
sfbrm100PortIgnoreWrongData	 OBJECT-TYPE
	SYNTAX INTEGER  { enabled(1), disabled(2) }
	ACCESS read-write
	STATUS mandatory
	DESCRIPTION "Ignores interrupts caused by reception of frames whose source address
				 is not assigned to this port. When disabled(2), generates a SNMP trap
				 every time a frame is received with SA not belonging to this Port."
	::= { sfbrm100PortEntry 28 }
	
sfbrm100PortIGMPSnoop	OBJECT-TYPE
	SYNTAX INTEGER  { enabled(1), disabled(2) }
	ACCESS read-write
	STATUS mandatory
	DESCRIPTION "When enabled all IGMP frames are directed to the CPU overriding the 
				 Destination address."
	::= { sfbrm100PortEntry 29 }
	
sfbrm100PortDoubleTagging	OBJECT-TYPE
	SYNTAX INTEGER   { enabled(1), disabled(2) }
	ACCESS read-write
	STATUS mandatory
	DESCRIPTION "When set to enabled, the frames which have 802.3ac tag with IEEE standard
	             ether-type of 0x8100 are examined for tags. 
	             On Ingress frames : All untagged frames remain
	             untagged, all single tagged will become untagged and all double tagged
	             frames will be single tagged on ingress.
	             On Egress frames : All frames exit with a extra tag.
	             All untagged frames get a single tag.
	             All single tagged frames gets double tagged."
	::= { sfbrm100PortEntry 30 }
	
sfbrm100PortUseIPTC	OBJECT-TYPE
	SYNTAX INTEGER  { enabled(1), disabled(2) }
	ACCESS read-write
	STATUS mandatory
	DESCRIPTION "When enabled, IP priority fields are used for Traffic class of priority data."
	::= { sfbrm100PortEntry 31 }
	
sfbrm100PortUseTagTC	OBJECT-TYPE
	SYNTAX INTEGER  { enabled(1), disabled(2) }
	ACCESS read-write
	STATUS mandatory
	DESCRIPTION "When enabled, the IEEE 802.1p fields are used for traffic class 
				 of priority data if the frame is IEEE 802.1ac tagged."
	::= { sfbrm100PortEntry 32 }
		
sfbrm100PortUseBothTC	OBJECT-TYPE
	SYNTAX INTEGER { useIP(1), useTag(2) }
	ACCESS read-write 
	STATUS mandatory
	DESCRIPTION "When a frame has both IP priority fields and IEEE 802.1ac tags and both 
				 sfbrm100PortUseIPTC and sfbrm100PortUseTagTC are enabled then 
				 this mib variable is used to decide which traffic class to use."
	::= { sfbrm100PortEntry 33 }
	
sfbrm100PortVLANTunnel	OBJECT-TYPE
	SYNTAX INTEGER { enabled(1), disabled(2) }
	ACCESS read-write
	STATUS mandatory
	DESCRIPTION "For all unicast and multicast frames with destination address defined as 
				'static' in the address database port-based VLAN masking, 802.1Q VLAN membership
				masking and trunk masking are enforced. When this mib variable is enabled, these
				rules are bypassed for all frames ingressing this port,	whose destination address
				is 'static' in the database."
	::= { sfbrm100PortEntry 34 }
	
sfbrm100PortFwdUnknown	OBJECT-TYPE
	SYNTAX INTEGER    { enabled(1), disabled(2) }
	ACCESS read-write
	STATUS mandatory
	DESCRIPTION "When enabled, all unicast frames with unknown destination address are allowed
				 to egress this port( assuming VLAN settings allow this frame to egress)."
	::= { sfbrm100PortEntry 35 }
	
sfbrm100PortDefForward	OBJECT-TYPE
	SYNTAX INTEGER   { enabled(1), disabled(2) }
	ACCESS read-write
	STATUS mandatory
	DESCRIPTION "When enabled, all multicast frames with unknown destination address are allowed
				 to egress this port( assuming VLAN settings allow this frame to egress)."
	::= { sfbrm100PortEntry 36 }
	
sfbrm100PortAdminState	OBJECT-TYPE
	SYNTAX INTEGER { enabled(1), disabled(2) } 
	ACCESS read-write
	STATUS mandatory
	DESCRIPTION "Set port state administratively up or down."
	::= { sfbrm100PortEntry 37 }
	
sfbrm100PortVTUPriOverride	OBJECT-TYPE
	SYNTAX INTEGER  { enabled(1), disabled(2) }
	ACCESS read-write
	STATUS mandatory
	DESCRIPTION "When disabled, normal switch operation is done.
				 When enabled, VTU Priority override occurs. i.e
				 The determined VID priority takes precedence over all
				 other priorities of that frame as per the VLAN database."
	::= { sfbrm100PortEntry 38 }
	
sfbrm100PortSAPriOverride	OBJECT-TYPE
	SYNTAX INTEGER { enabled(1), disabled(2) }
	ACCESS read-write
	STATUS mandatory
	DESCRIPTION "When enabled, Source address decides the priority as per the 
				 address database entry rules."
		::= { sfbrm100PortEntry 39 }
	
sfbrm100PortDAPriOverride	OBJECT-TYPE
	SYNTAX INTEGER { enabled(1), disabled(2) }
	ACCESS read-write
	STATUS mandatory
	DESCRIPTION "When enabled, Destination address decides the priority as per the 
				 address database entry rules."
	::= { sfbrm100PortEntry 40 }
	
sfbrm100PortVLANStatus	OBJECT-TYPE
	SYNTAX INTEGER  { vlanDisabled(1), fallback(2), check(3), secure(4) }
	ACCESS read-write
	STATUS mandatory
	DESCRIPTION "802.1Q VLAN setting :
					vlanDisabled - 802.1Q is disabled.
					fallback 	 - The frame is not discarded if the VID is not in the VLAN Db.
					check 		 - The VID must be in the VLAN Db, the ingress port may or may not be a member.
					               If the VID is not in the VLAN Db, it is discarded.
					secure  	 - The VID must be in the VLAN Db and the ingresss port should be a member
						  		   of the VLAN, else it is discarded.
				In all the three cases when 802.1Q is enabled, the frame is allowed to egress only if the egress
				port is a member of the VLAN. In 'fallback' mode, if VID is not in the VLAN db, the frame is allowed 
				to egress based on Port Based VLAN. "
	::= { sfbrm100PortEntry 41 }
	
sfbrm100PortDiscardTagged	OBJECT-TYPE
	SYNTAX INTEGER  { enabled(1), disabled(2) }
	ACCESS read-write
	STATUS mandatory
	DESCRIPTION "All ingress tagged frames are discarded if enabled."
	::= { sfbrm100PortEntry 42 }
	
sfbrm100PortDiscardUntagged	 OBJECT-TYPE
	SYNTAX INTEGER { enabled(1), disabled(2) }
	ACCESS read-write
	STATUS mandatory
	DESCRIPTION "All untagged ingress frames are discarded if enabled."
	::= { sfbrm100PortEntry 43 }
	
sfbrm100PortEgressMonitor	OBJECT-TYPE
	SYNTAX INTEGER  { enabled(1), disabled(2) }
	ACCESS read-write
	STATUS mandatory
	DESCRIPTION "Any frame that egress this port is also sent to the egress
				 monitor destination port. Not applicable for 2-port device."
	::= { sfbrm100PortEntry 44 }
	
sfbrm100PortIngressMonitor	 OBJECT-TYPE
	SYNTAX INTEGER  { enabled(1), disabled(2) }
	ACCESS read-write
	STATUS mandatory
	DESCRIPTION "Any frame that ingress this port is also sent to the ingress
				 monitor destination port. Not applicable for 2-port device"
	::= { sfbrm100PortEntry 45 }
	
sfbrm100PortPri3IngressRateCtrl  OBJECT-TYPE
	SYNTAX INTEGER  { sameAsPri2(1), twiceAsPri2(2) }
	ACCESS read-write
	STATUS mandatory
	DESCRIPTION "Ingress rate limit for Priority 3 frames, but not faster than port speed."
	::= { sfbrm100PortEntry 46 }
	
sfbrm100PortPri2IngressRateCtrl  OBJECT-TYPE
	SYNTAX INTEGER  { sameAsPri1(1), twiceAsPri1(2) }
	ACCESS read-write
	STATUS mandatory
	DESCRIPTION "Ingress rate limit for Priority 2 frames, but not faster than port speed."
	::= { sfbrm100PortEntry 47 }
	
sfbrm100PortPri1IngressRateCtrl  OBJECT-TYPE
	SYNTAX INTEGER { sameAsPri0(1), twiceAsPri0(2) }
	ACCESS read-write
	STATUS mandatory
	DESCRIPTION "Ingress rate limit for Priority 1 frames, but not faster than port speed."
	::= { sfbrm100PortEntry 48 }
	
sfbrm100PortPri0IngressRate	    OBJECT-TYPE
	SYNTAX INTEGER {
					 	noLimit(1),
					 	rate64K(2), 
						rate96K(3), 
						rate128K(4), 
						rate160K(5),
						rate192K(6),
						rate224K(7),
						rate256K(8), 
						rate320K(9),
						rate384K(10),
						rate512K(11),
						rate768K(12),
						rate1M(13),
						rate1-2M(14),
						rate1-5M(15),
						rate2M(16),
						rate3M(17),
						rate4M(18),
						rate5M(19),
						rate8M(20),
						rate10M(21),
						rate20M(22),
						rate30M(23),
						rate40M(24),
						rate60M(25),
						rate80M(26),
						rate128M(27),
						rate256M(28)
					} 
	ACCESS read-write
	STATUS mandatory
	DESCRIPTION "Ingress rate for Priority 0 frames in bits per second,
				 but not faster than port speed. Priority 0 frames are discarded after
				 the ingress rate selected is reached or exceeded. The rates of 128M and 256M are
				 valid for Gigabit ports only."
	::= { sfbrm100PortEntry 49 }
	
sfbrm100PortIngressLimitMode OBJECT-TYPE
	SYNTAX INTEGER { all(1), bCastMCastFloodedUCast(2), bCastMCastOnly(3), bCastOnly(4) }
	ACCESS read-write
	STATUS mandatory
	DESCRIPTION "Ingress Limit mode. 
					all(1) 					  - Limits and counts all frames
					bCastMCastFloodedUCast(2) - Limits and counts all broadcast, multicast
												and flooded unicast frames.
					bCastMCastOnly(3)         - Limits and counts all broadcast and multicast 
												frames only.
					bCastOnly(4) 		      - Limits and counts only broadcast frames.
					
					If a frame is not limited by the above setting, its size is not counted
					against the limit of the other frames."
	::= { sfbrm100PortEntry 50 }
	
sfbrm100PortEgressRate    OBJECT-TYPE
	SYNTAX INTEGER {
					 	noLimit(1),
					 	rate64K(2), 
						rate96K(3), 
						rate128K(4), 
						rate160K(5),
						rate192K(6),
						rate224K(7),
						rate256K(8), 
						rate320K(9),
						rate384K(10),
						rate512K(11),
						rate768K(12),
						rate1M(13),
						rate1-2M(14),
						rate1-5M(15),
						rate2M(16),
						rate3M(17),
						rate4M(18),
						rate5M(19),
						rate8M(20),
						rate10M(21),
						rate20M(22),
						rate30M(23),
						rate40M(24),
						rate60M(25),
						rate80M(26),
						rate128M(27),
						rate256M(28)
					} 
	ACCESS read-write
	STATUS mandatory
	DESCRIPTION "Egress priority rate in bits per seconds. This affects
				the port's effective transmission rate."
	::= { sfbrm100PortEntry 51 }
	
sfbrm100PortDefaultPriority      OBJECT-TYPE
	SYNTAX INTEGER
	ACCESS read-write
	STATUS mandatory
	DESCRIPTION "The default priority of the frame if its not IEEE tagged or not 
				 IP frames or no other priority overides are active for this frame."
	::= { sfbrm100PortEntry 52 }
	
sfbrm100PortForceDefVLANId       OBJECT-TYPE
	SYNTAX INTEGER { enabled(1), disabled(2) }
	ACCESS read-write
	STATUS mandatory
	DESCRIPTION "Force to use the sfbrm100PortDefaultVLANId when 802.1Q is enabled
				 on this port. The frames actual VLAN id is replaced with the
				 default VLAN Id. Has no effect when 802.1Q is disabled."
	::= { sfbrm100PortEntry 53 }
	
sfbrm100PortDefaultVLANId		OBJECT-TYPE
	SYNTAX INTEGER
	ACCESS read-write
	STATUS mandatory
	DESCRIPTION "The default VLAN Id of the port. All untagged frames that are to
	             exit tagged will use the VID of the ingress port on exit.
	             This VID is also used on all frames when 'sfbrm100PortForceDefVLANId'
	             is set."
	::= { sfbrm100PortEntry 54 }

sfbrm100PortBasedVLANTbl			OBJECT-TYPE
	SYNTAX INTEGER
	ACCESS read-write
	STATUS mandatory
	DESCRIPTION "Each bit represents ports on the switch.
				These bits restrict where this port can send frames to, setting the
				bits to zero will disable this port's ability to egress frames out of the 
				indicated port.
					Ex: Port 0 is represented by bit 0 in the bitmap.
				By default all ports can send to all ports."
	::= { sfbrm100PortEntry 55 }
	
sfbrm100PortIEEEPriRemap0		OBJECT-TYPE
	SYNTAX INTEGER
	ACCESS read-write
	STATUS mandatory
	DESCRIPTION "All Frames with priority 0 are remapped to this set value inside the switch."
	::= { sfbrm100PortEntry 56 }
	
sfbrm100PortIEEEPriRemap1		OBJECT-TYPE
	SYNTAX INTEGER
	ACCESS read-write
	STATUS mandatory
	DESCRIPTION "All Frames with priority 1 are remapped to this set value inside the switch."
	::= { sfbrm100PortEntry 57 }
	
sfbrm100PortIEEEPriRemap2		OBJECT-TYPE
	SYNTAX INTEGER
	ACCESS read-write
	STATUS mandatory
	DESCRIPTION "All Frames with priority 2 are remapped to this set value inside the switch."
	::= { sfbrm100PortEntry 58 }
	
sfbrm100PortIEEEPriRemap3		OBJECT-TYPE
	SYNTAX INTEGER
	ACCESS read-write
	STATUS mandatory
	DESCRIPTION "All Frames with priority 3 are remapped to this set value inside the switch."
	::= { sfbrm100PortEntry 59 }
	
sfbrm100PortIEEEPriRemap4		OBJECT-TYPE
	SYNTAX INTEGER
	ACCESS read-write
	STATUS mandatory
	DESCRIPTION "All Frames with priority 4 are remapped to this set value inside the switch."
	::= { sfbrm100PortEntry 60 }
	
sfbrm100PortIEEEPriRemap5		OBJECT-TYPE
	SYNTAX INTEGER
	ACCESS read-write
	STATUS mandatory
	DESCRIPTION "All Frames with priority 5 are remapped to this set value inside the switch."
	::= { sfbrm100PortEntry 61 }
	
sfbrm100PortIEEEPriRemap6		OBJECT-TYPE
	SYNTAX INTEGER
	ACCESS read-write
	STATUS mandatory
	DESCRIPTION "All Frames with priority 6 are remapped to this set value inside the switch."
	::= { sfbrm100PortEntry 62 }
	
sfbrm100PortIEEEPriRemap7		OBJECT-TYPE
	SYNTAX INTEGER
	ACCESS read-write
	STATUS mandatory
	DESCRIPTION "All Frames with priority 7 are remapped to this set value inside the switch."
	::= { sfbrm100PortEntry 63 }
	
sfbrm100PortVCTest 			    OBJECT-TYPE
	SYNTAX INTEGER  { perform(1), doNothing(2) }
	ACCESS read-write
	STATUS mandatory
	DESCRIPTION "The virtual cable test can be done using this variable set to perform(1), 
				 otherwise the Read-only value notApplicable(2) will be returned."
	::= { sfbrm100PortEntry 64 }
	
sfbrm100PortVCTxMDI0Status		OBJECT-TYPE
	SYNTAX INTEGER  { normal(1), impedanceMismatch(2), shortInCable(3), openInCable(4), failed(5), notApplicable(6) }
	ACCESS read-only
	STATUS mandatory
	DESCRIPTION "The test status of the Tx pair or MDI[0](Gigabit port) depending on port type.
					normal(1)  		- Test was successful, cable is normal (no short or open in cable)
					impedanceMismatch(2)- Test was successful, cable has impedance mismatch.
					shortInCable(3) - Test was successful, short in cable (impedance < 33 Ohm)
					openInCable(4)  - Test was successful, open in cable (impedance > 333 Ohm)
					failed(5)       - Test failed."
	::= { sfbrm100PortEntry 65 }
	
sfbrm100PortTxMDI0Dist			OBJECT-TYPE
	SYNTAX INTEGER  { lessThan50m(1), between50m80m(2), between80m110m(3), between110m140m(4), morethan140m(5),  notApplicable(6) }
	ACCESS read-only
	STATUS mandatory
	DESCRIPTION "The cable distance of the Tx pair or MDI[0](Gigabit port) from the tested port.
				In case of sfbrm100PortVCRxMDIXStatus having a value of 2 - 4, this gives the
				distance from the port where the impedance occured. In case of normal(1) cable status,
				one of the listed value is returned."
	::= { sfbrm100PortEntry 66 }
	
sfbrm100PortVCRxMDI1Status		OBJECT-TYPE
	SYNTAX INTEGER  { normal(1), impedanceMismatch(2), shortInCable(3), openInCable(4), failed(5), notApplicable(6) }
	ACCESS read-only
	STATUS mandatory
	DESCRIPTION "The test status of the Rx or MDI[1](Gigabit port) depending on port type.
					normal(1)  		- Test was successful, cable is normal (no short or open in cable)
					impedanceMismatch(2)- Test was successful, cable has impedance mismatch.
					shortInCable(3) - Test was successful, short in cable (impedance < 33 Ohm)
					openInCable(4)  - Test was successful, open in cable (impedance > 333 Ohm)
					failed(5)       - Test failed."
	::= { sfbrm100PortEntry 67 }
	
sfbrm100PortRxMDI1Dist			OBJECT-TYPE
	SYNTAX INTEGER { lessThan50m(1), between50m80m(2), between80m110m(3), between110m140m(4), morethan140m(5),  notApplicable(6) }
	ACCESS read-only
	STATUS mandatory
	DESCRIPTION "The cable distance of the Rx pair or MDI[1](Gigabit port) from the tested port.
				In case of sfbrm100PortVCRxMDIXStatus having a value of 2 - 4, this gives the
				distance from the port where the impedance occured.In case of normal(1) cable status,
				one of the listed value is returned."
	::= { sfbrm100PortEntry 68 }
	
sfbrm100PortVCMDI2Status			OBJECT-TYPE
	SYNTAX INTEGER  { normal(1), impedanceMismatch(2), shortInCable(3), openInCable(4), failed(5), notApplicable(6) }
	ACCESS read-only
	STATUS mandatory
	DESCRIPTION "The test status of the MDI[2](Gigabit port), 0 otherwise.
					normal(1)  		- Test was successful, cable is normal (no short or open in cable)
					impedanceMismatch(2)- Test was successful, cable has impedance mismatch.
					shortInCable(3) - Test was successful, short in cable (impedance < 33 Ohm)
					openInCable(4)  - Test was successful, open in cable (impedance > 333 Ohm)
					failed(5)       - Test failed."
	::= { sfbrm100PortEntry 69 }
	
sfbrm100PortMDI2Dist				OBJECT-TYPE
	SYNTAX INTEGER { lessThan50m(1), between50m80m(2), between80m110m(3), between110m140m(4), morethan140m(5),  notApplicable(6) }
	ACCESS read-only
	STATUS mandatory
	DESCRIPTION "The cable distance of the MDI[2](if Gigabit port else notApplicable(6)) from the test port.
				In case of sfbrm100PortVCRxMDIXStatus having a value of 2 - 4, this gives the
				distance from the port where the impedance occured.In case of normal(1) cable status,
				one of the listed value is returned."
	::= { sfbrm100PortEntry 70 }
	
sfbrm100PortVCMDI3Status			OBJECT-TYPE
	SYNTAX INTEGER { normal(1), impedanceMismatch(2), shortInCable(3), openInCable(4), failed(5), notApplicable(6) }
	ACCESS read-only
	STATUS mandatory
	DESCRIPTION "The test status of the MDI[3](Gigabit port), 0 otherwise.
					normal(1)  		- Test was successful, cable is normal (no short or open in cable)
					impedanceMismatch(2)- Test was successful, cable has impedance mismatch.
					shortInCable(3) - Test was successful, short in cable (impedance < 33 Ohm)
					openInCable(4)  - Test was successful, open in cable (impedance > 333 Ohm)
					failed(5)       - Test failed."
	::= { sfbrm100PortEntry 71 }
	
sfbrm100PortMDI3Dist				OBJECT-TYPE
	SYNTAX INTEGER	{ lessThan50m(1), between50m80m(2), between80m110m(3), between110m140m(4), morethan140m(5),  notApplicable(6) }
	ACCESS read-only
	STATUS mandatory
	DESCRIPTION "The cable distance of the MDI[3](if Gigabit port else notApplicable(6)) from the tested port.
				In case of sfbrm100PortVCRxMDIXStatus having a value of 2 - 4, this gives the
				distance from the port where the impedance occured.In case of normal(1) cable status,
				one of the listed value is returned."
	::= { sfbrm100PortEntry 72 }

sfbrm100PortResetCounters		OBJECT-TYPE
	SYNTAX INTEGER	{ reset(1), donothing(2) }
	ACCESS read-write
	STATUS mandatory
	DESCRIPTION "Resets all the port counters for this port. A read returns read-only value donothing(2)."
	::= { sfbrm100PortEntry 73 }

sfbrm100PortIPTrafficAccess		OBJECT-TYPE
	SYNTAX INTEGER	{ enabled(1), disabled(2) }
	ACCESS read-write
	STATUS mandatory
	DESCRIPTION "Allow/block IP management traffic on this port."
	::= { sfbrm100PortEntry 74 }
	
sfbrm100PortResetOAMCounters	OBJECT-TYPE
	SYNTAX INTEGER	{ enabled(1), disabled(2) }
	ACCESS read-write
	STATUS mandatory
	DESCRIPTION "Resets all OAM counters for this port."
	::= { sfbrm100PortEntry 75 }
			
sfbrm100PortForceAutoUpgrade	OBJECT-TYPE
	SYNTAX INTEGER	{ enabled(1), disabled(2) }
	ACCESS read-write
	STATUS mandatory
	DESCRIPTION "Force Automatic firmware upgrade on this peer, when the peer
				 has its auto upgrade turned off."
	::= { sfbrm100PortEntry 76 }
	                       
sfbrm100PortModeType	OBJECT-TYPE
	SYNTAX INTEGER	{ mode10or100or1000BaseT(1), mode1000BaseX(2), mode10or100BaseT(3),  mode100BaseFX(4)}
	ACCESS read-write
	STATUS mandatory
	DESCRIPTION "The Interface mode. The capabilities of the interface."
	::= { sfbrm100PortEntry 77 }
	                       
sfbrm100PortOAMMode	OBJECT-TYPE
	SYNTAX INTEGER	{ passive(1), active(2) }
	ACCESS read-write
	STATUS mandatory
	DESCRIPTION "The OAM mode for this port."
	::= { sfbrm100PortEntry 78 }
	
sfbrm100PortPhyNumber OBJECT-TYPE
	SYNTAX INTEGER	
	ACCESS read-only
	STATUS mandatory
	DESCRIPTION "This gives the physical port number on the hardware switch.
				This is useful in computing the port based VLAN setting for this
				port. The bit position in the port based VLAN corresponds to this
				physical port number."
	::= { sfbrm100PortEntry 79 }

sfbrm100PortIngressRateLimit2 OBJECT-TYPE
	SYNTAX INTEGER {
					 	noLimit(1),
					 	rate64K(2), 
						rate128K(3), 
						rate192K(4),
						rate256K(5), 
						rate320K(6),
						rate384K(7),
						rate512K(8),
						rate768K(9),
						rate1M(10),
						rate2M(11),
						rate3M(12),
						rate4M(13),
						rate6M(14),
						rate8M(15),
						rate10M(16),
						rate20M(17),
						rate30M(18),
						rate40M(19),
						rate50M(20),
						rate60M(21),
						rate70M(22),
						rate80M(23),
						rate100M(24),
						rate200M(25),
						rate300M(26),
						rate400M(27),
						rate500M(28),
						rate600M(29),
						rate700M(30),
						rate800M(31),
						rate900M(32)
					} 
	ACCESS read-write
	STATUS mandatory
	DESCRIPTION "Ingress bandwidth limiting in bits per second,
				 but not faster than port speed. Frames are discarded if
				 the ingress rate selected is reached or exceeded. Devices which support
				 this mib variable do not use 'sfbrm100PortPri0IngressRate' for rate limiting."
	::= { sfbrm100PortEntry 80 }

sfbrm100PortEgressRateLimit2 OBJECT-TYPE
	SYNTAX INTEGER {
					 	noLimit(1),
					 	rate64K(2), 
						rate128K(3), 
						rate192K(4),
						rate256K(5), 
						rate320K(6),
						rate384K(7),
						rate512K(8),
						rate768K(9),
						rate1M(10),
						rate2M(11),
						rate3M(12),
						rate4M(13),
						rate6M(14),
						rate8M(15),
						rate10M(16),
						rate20M(17),
						rate30M(18),
						rate40M(19),
						rate50M(20),
						rate60M(21),
						rate70M(22),
						rate80M(23),
						rate100M(24),
						rate200M(25),
						rate300M(26),
						rate400M(27),
						rate500M(28),
						rate600M(29),
						rate700M(30),
						rate800M(31),
						rate900M(32)
					} 
	ACCESS read-write
	STATUS mandatory
	DESCRIPTION "Egress bandwidth limiting in bits per second,
				 but not faster than port speed. Frames are discarded if over the limit.
				 Devices which support this mib variable do not use 'sfbrm100PortEgressRate' 
				 for rate limiting"
	::= { sfbrm100PortEntry 81 }
 	
--Port statistics
sfbrm100PortStatsTable  OBJECT-TYPE
    SYNTAX SEQUENCE OF Sfbrm100PortStatsEntry
    ACCESS not-accessible
    STATUS mandatory
    DESCRIPTION "Port Statistics table."
	::= { sfbrmPort 2 }

sfbrm100PortStatsEntry OBJECT-TYPE
    SYNTAX Sfbrm100PortStatsEntry
    ACCESS not-accessible
    STATUS mandatory
    DESCRIPTION "Statistics for a single port."
    INDEX { sfbrm100PortLocStatsIndex, sfbrm100PortRmtStatsIndex }
    ::= { sfbrm100PortStatsTable 1 }

Sfbrm100PortStatsEntry ::=         
	    SEQUENCE {
	   		sfbrm100PortLocStatsIndex		INTEGER,
	   		sfbrm100PortRmtStatsIndex		INTEGER,
	   		sfbrm100PortInGoodOctetsLo		INTEGER,
	   		sfbrm100PortInGoodOctetsHi		INTEGER,
	   		sfbrm100PortInBadOctets			INTEGER,
	   		sfbrm100PortInUnicasts			INTEGER,
	   		sfbrm100PortInBroadcasts		INTEGER,
	   		sfbrm100PortInMulticasts		INTEGER,
	   		sfbrm100PortInPause				INTEGER,
	   		sfbrm100PortInUndersize			INTEGER,
	   		sfbrm100PortInFragments			INTEGER,
	   		sfbrm100PortInOversize			INTEGER,
	   		sfbrm100PortInJabber			INTEGER,
	   		sfbrm100PortInRxErr				INTEGER,
	   		sfbrm100PortInFCSErr			INTEGER,
	   		sfbrm100PortIn64Octets			INTEGER,
	   		sfbrm100PortIn65to127Octets		INTEGER,
	   		sfbrm100PortIn128to255Octets	INTEGER,
	   		sfbrm100PortIn256to511Octets	INTEGER,
	   		sfbrm100PortIn512to1023Octets	INTEGER,
	   		sfbrm100PortIn1024toMaxOctets	INTEGER,
	   		sfbrm100PortOutOctetsLo			INTEGER,
	   		sfbrm100PortOutOctetsHi			INTEGER,
	   		sfbrm100PortOutUnicasts			INTEGER,
	   		sfbrm100PortOutBroadcasts		INTEGER,
	   		sfbrm100PortOutMulticasts		INTEGER,
	   		sfbrm100PortOutPause			INTEGER,
	   		sfbrm100PortOutDeferred			INTEGER,
	   		sfbrm100PortOutCollisions		INTEGER,
	   		sfbrm100PortOutSingle			INTEGER,
	   		sfbrm100PortOutMultiple			INTEGER,
	   		sfbrm100PortOutExcessive		INTEGER,
	   		sfbrm100PortOutLate				INTEGER,
	   		sfbrm100PortOutFCSErr			INTEGER,
	   		sfbrm100PortInDiscard			INTEGER,
	   		sfbrm100PortInFiltered			INTEGER,
        	sfbrm100PortOutFiltered			INTEGER
        }

sfbrm100PortLocStatsIndex	OBJECT-TYPE
    SYNTAX INTEGER
	ACCESS read-only
	STATUS mandatory
	DESCRIPTION "The port index of the local port as defined by sfbrm100PortLocIndex."
	::= { sfbrm100PortStatsEntry 1 }

sfbrm100PortRmtStatsIndex	OBJECT-TYPE
    SYNTAX INTEGER
	ACCESS read-only
	STATUS mandatory
	DESCRIPTION "The remote port index of the remote peer as defined by sfbrm100PortRmtIndex."
	::= { sfbrm100PortStatsEntry 2 }
	
sfbrm100PortInGoodOctetsLo	OBJECT-TYPE
    SYNTAX INTEGER
	ACCESS read-only
	STATUS mandatory
	DESCRIPTION "The lower 32-bits of the received good octets counter."
	::= { sfbrm100PortStatsEntry 3 }
	
sfbrm100PortInGoodOctetsHi	OBJECT-TYPE
    SYNTAX INTEGER
	ACCESS read-only
	STATUS mandatory
	DESCRIPTION "The upper 32-bits of the received good octets counter."
	::= { sfbrm100PortStatsEntry 4 }

sfbrm100PortInBadOctets	OBJECT-TYPE
    SYNTAX INTEGER
	ACCESS read-only
	STATUS mandatory
	DESCRIPTION "The sum of all octets in bad Ethernet frames."
	::= { sfbrm100PortStatsEntry 5 }

sfbrm100PortInUnicasts	OBJECT-TYPE
    SYNTAX INTEGER
	ACCESS read-only
	STATUS mandatory
	DESCRIPTION "The number of good unicast frames."
	::= { sfbrm100PortStatsEntry 6 }

sfbrm100PortInBroadcasts	OBJECT-TYPE
    SYNTAX INTEGER
	ACCESS read-only
	STATUS mandatory
	DESCRIPTION "The number of good broadcast frames."
	::= { sfbrm100PortStatsEntry 7 }

sfbrm100PortInMulticasts	OBJECT-TYPE
    SYNTAX INTEGER
	ACCESS read-only
	STATUS mandatory
	DESCRIPTION "The number of good multicast frames."
	::= { sfbrm100PortStatsEntry 8 }

sfbrm100PortInPause	OBJECT-TYPE
    SYNTAX INTEGER
	ACCESS read-only
	STATUS mandatory
	DESCRIPTION "The number of good Pause flow control frames."
	::= { sfbrm100PortStatsEntry 9 }

sfbrm100PortInUndersize	OBJECT-TYPE
    SYNTAX INTEGER
	ACCESS read-only
	STATUS mandatory
	DESCRIPTION "The number of frames received with a length of less than 64 octets
				 with a valid FCS."
	::= { sfbrm100PortStatsEntry 10 }

sfbrm100PortInFragments	OBJECT-TYPE
    SYNTAX INTEGER
	ACCESS read-only
	STATUS mandatory
	DESCRIPTION "The number of frames received with a length of less than 64 octets
				 with an invalid FCS."
	::= { sfbrm100PortStatsEntry 11 }

sfbrm100PortInOversize	OBJECT-TYPE
    SYNTAX INTEGER
	ACCESS read-only
	STATUS mandatory
	DESCRIPTION "The number of frames received with a length of more than maximum size
				 octets	with a valid FCS."
	::= { sfbrm100PortStatsEntry 12 }

sfbrm100PortInJabber	OBJECT-TYPE
    SYNTAX INTEGER
	ACCESS read-only
	STATUS mandatory
	DESCRIPTION "The number of frames received with a length of more than maximum size
				 octets	with an invalid FCS."
	::= { sfbrm100PortStatsEntry 13 }

sfbrm100PortInRxErr	OBJECT-TYPE
    SYNTAX INTEGER
	ACCESS read-only
	STATUS mandatory
	DESCRIPTION "The number of frames received with a RxErr signal from the Physical layer"
	::= { sfbrm100PortStatsEntry 14 }

sfbrm100PortInFCSErr	OBJECT-TYPE
    SYNTAX INTEGER
	ACCESS read-only
	STATUS mandatory
	DESCRIPTION "The number of frames received with a CRC error not counted in 
				sfbrm100PortInFragments,  sfbrm100PortInJabber or sfbrm100PortInRxErr."
	::= { sfbrm100PortStatsEntry 15 }

sfbrm100PortIn64Octets	OBJECT-TYPE
    SYNTAX INTEGER
	ACCESS read-only
	STATUS mandatory
	DESCRIPTION "The total number of frames received with a length of 64 octets,
				including errored frames. This is a histogram counter, dependent on the 
				histogram mode 'sfbrm100SwHistMode'	chosen."
	::= { sfbrm100PortStatsEntry 16 }

sfbrm100PortIn65to127Octets	OBJECT-TYPE
    SYNTAX INTEGER
	ACCESS read-only
	STATUS mandatory
	DESCRIPTION "The total number of frames received with a length between 65 and 127 octets,
				including errored frames. This is a histogram counter, dependent on the 
				histogram mode 'sfbrm100SwHistMode'	chosen."
	::= { sfbrm100PortStatsEntry 17 }

sfbrm100PortIn128to255Octets	OBJECT-TYPE
    SYNTAX INTEGER
	ACCESS read-only
	STATUS mandatory
	DESCRIPTION "The total number of frames received with a length between 128 and 255 octets,
				 including errored frames. This is a histogram counter, dependent on the 
				histogram mode 'sfbrm100SwHistMode'	chosen."
	::= { sfbrm100PortStatsEntry 18 }

sfbrm100PortIn256to511Octets	OBJECT-TYPE
    SYNTAX INTEGER
	ACCESS read-only
	STATUS mandatory
	DESCRIPTION "The total number of frames received with a length between 256 and 511 octets,
				 including errored frames. This is a histogram counter, dependent on the 
				histogram mode 'sfbrm100SwHistMode'	chosen."
	::= { sfbrm100PortStatsEntry 19 }

sfbrm100PortIn512to1023Octets	OBJECT-TYPE
    SYNTAX INTEGER
	ACCESS read-only
	STATUS mandatory
	DESCRIPTION "The total number of frames received with a length between 512 and 1023 octets,
				 including errored frames. This is a histogram counter, dependent on the 
				histogram mode 'sfbrm100SwHistMode'	chosen."
	::= { sfbrm100PortStatsEntry 20 }

sfbrm100PortIn1024toMaxOctets	OBJECT-TYPE
    SYNTAX INTEGER
	ACCESS read-only
	STATUS mandatory
	DESCRIPTION "The total number of frames received with a length between 1024 and max size octets,
				 including errored frames. This is a histogram counter, dependent on the 
				histogram mode 'sfbrm100SwHistMode'	chosen."
	::= { sfbrm100PortStatsEntry 21 }
	
sfbrm100PortOutOctetsLo	OBJECT-TYPE
    SYNTAX INTEGER
	ACCESS read-only
	STATUS mandatory
	DESCRIPTION "The lower 32-bit of the sum of all frames sent from this port."
	::= { sfbrm100PortStatsEntry 22 }

sfbrm100PortOutOctetsHi	OBJECT-TYPE
    SYNTAX INTEGER
	ACCESS read-only
	STATUS mandatory
	DESCRIPTION "The upper 32-bit of the sum of all frames sent from this port."
	::= { sfbrm100PortStatsEntry 23 }

sfbrm100PortOutUnicasts	OBJECT-TYPE
    SYNTAX INTEGER
	ACCESS read-only
	STATUS mandatory
	DESCRIPTION "The number of unicast frames transmitted."
	::= { sfbrm100PortStatsEntry 24 }

sfbrm100PortOutBroadcasts	OBJECT-TYPE
    SYNTAX INTEGER
	ACCESS read-only
	STATUS mandatory
	DESCRIPTION "The number of broadcast frames transmitted."
	::= { sfbrm100PortStatsEntry 25 }

sfbrm100PortOutMulticasts	OBJECT-TYPE
    SYNTAX INTEGER
	ACCESS read-only
	STATUS mandatory
	DESCRIPTION "The number of multicast frames transmitted."
	::= { sfbrm100PortStatsEntry 26 }

sfbrm100PortOutPause		OBJECT-TYPE
    SYNTAX INTEGER
	ACCESS read-only
	STATUS mandatory
	DESCRIPTION "The number of Pause frames transmitted."
	::= { sfbrm100PortStatsEntry 27 }

sfbrm100PortOutDeferred	OBJECT-TYPE
    SYNTAX INTEGER
	ACCESS read-only
	STATUS mandatory
	DESCRIPTION "The number of frames transmitted with a delay."
	::= { sfbrm100PortStatsEntry 28 }

sfbrm100PortOutCollisions	OBJECT-TYPE
    SYNTAX INTEGER
	ACCESS read-only
	STATUS mandatory
	DESCRIPTION "The number of collisions during transmission not including single,
					multiple, excessive or late collisions."
	::= { sfbrm100PortStatsEntry 29 }

sfbrm100PortOutSingle	OBJECT-TYPE
    SYNTAX INTEGER
	ACCESS read-only
	STATUS mandatory
	DESCRIPTION "The number of frames transmitted with exactly one collision."
	::= { sfbrm100PortStatsEntry 30 }

sfbrm100PortOutMultiple	OBJECT-TYPE
    SYNTAX INTEGER
	ACCESS read-only
	STATUS mandatory
	DESCRIPTION "The number of frames transmitted with more than one collision."
	::= { sfbrm100PortStatsEntry 31 }

sfbrm100PortOutExcessive	OBJECT-TYPE
    SYNTAX INTEGER
	ACCESS read-only
	STATUS mandatory
	DESCRIPTION "The number of frames dropped due to excessive collision."
	::= { sfbrm100PortStatsEntry 32 }

sfbrm100PortOutLate	OBJECT-TYPE
    SYNTAX INTEGER
	ACCESS read-only
	STATUS mandatory
	DESCRIPTION "The number of times a collision is detected later than 512 bits-times 
				into transmission of a frame."
	::= { sfbrm100PortStatsEntry 33 }

sfbrm100PortOutFCSErr	OBJECT-TYPE
    SYNTAX INTEGER
	ACCESS read-only
	STATUS mandatory
	DESCRIPTION "The number of frames transmitted with invalid FCS."
	::= { sfbrm100PortStatsEntry 34 }

sfbrm100PortInDiscard	OBJECT-TYPE
    SYNTAX INTEGER
	ACCESS read-only
	STATUS mandatory
	DESCRIPTION "The number of good frames that were discarded due to lack of resources."	
	::= { sfbrm100PortStatsEntry 35 }

sfbrm100PortInFiltered	OBJECT-TYPE
    SYNTAX INTEGER
	ACCESS read-only
	STATUS mandatory
	DESCRIPTION "The number of good frames filtered due to ingress switch policy."
	::= { sfbrm100PortStatsEntry 36 }

sfbrm100PortOutFiltered	OBJECT-TYPE
    SYNTAX INTEGER
	ACCESS read-only
	STATUS mandatory
	DESCRIPTION "The number of good frames filtered due to egress switch policy."
	::= { sfbrm100PortStatsEntry 37 }    
	
        
--	DMI Table for Ports that have DMI
sfbrm100DMITable  OBJECT-TYPE
    SYNTAX SEQUENCE OF Sfbrm100DMIEntry
    ACCESS not-accessible
    STATUS mandatory
    DESCRIPTION "DMI ports on the device."
	::= { sfbrmPort 3 }

sfbrm100DMIEntry OBJECT-TYPE
    SYNTAX Sfbrm100DMIEntry
    ACCESS not-accessible
    STATUS mandatory
    DESCRIPTION "Status of the DMI ports."
    INDEX { sfbrm100DMILocPortIndex, sfbrm100DMIRmtPortIndex }
    ::= { sfbrm100DMITable 1 }

Sfbrm100DMIEntry ::=         
	    SEQUENCE {
			sfbrm100DMILocPortIndex         INTEGER,
			sfbrm100DMIRmtPortIndex         INTEGER,
			sfbrm100DMIRxPwrLvlPreset       INTEGER,
			sfbrm100DMIConnType	            CpsConnector,
			sfbrm100DMIBitRate		        INTEGER,
			sfbrm100DMILenFor9x125umKM      INTEGER,
			sfbrm100DMILenFor9x125um100M    INTEGER,
			sfbrm100DMILenFor50x125um10M    INTEGER,
			sfbrm100DMILenFor625x125um10M   INTEGER,
			sfbrm100DMILenForCopper         INTEGER,
			sfbrm100DMIId				    INTEGER,
			sfbrm100DMILaserWavelength      INTEGER,
			sfbrm100DMITemperature      	INTEGER,
			sfbrm100DMITempAlarm			INTEGER,			
			sfbrm100DMITxBiasCurrent		INTEGER,
			sfbrm100DMITxBiasAlarm			INTEGER,			
			sfbrm100DMITxPowerLevel		    INTEGER,
			sfbrm100DMITxPowerAlarm			INTEGER,			
			sfbrm100DMIRxPowerLevel		    INTEGER,
			sfbrm100DMIRxPowerAlarm			INTEGER
			}
       
sfbrm100DMILocPortIndex OBJECT-TYPE
    SYNTAX INTEGER
	ACCESS read-only
	STATUS mandatory
	DESCRIPTION "The port index of the DMI port as defined by sfbrm100PortLocIndex."
	::= { sfbrm100DMIEntry 1 }

sfbrm100DMIRmtPortIndex OBJECT-TYPE
    SYNTAX INTEGER
	ACCESS read-only
	STATUS mandatory
	DESCRIPTION "The port index of the DMI port as defined by sfbrm100PortRmtIndex."
	::= { sfbrm100DMIEntry 2 }
    
sfbrm100DMIRxPwrLvlPreset OBJECT-TYPE
    SYNTAX INTEGER
	ACCESS read-write
	STATUS mandatory
	DESCRIPTION "A preset level for Rx Power on the Fiber port, if the DMI read value 
				 falls below the preset value, an intrusion is detected, and a trap
				 is generated."
	::= { sfbrm100DMIEntry 3 }

sfbrm100DMIConnType	OBJECT-TYPE
    SYNTAX CpsConnector
	ACCESS read-only
	STATUS mandatory
	DESCRIPTION "The DMI connector type indicates the external optical or electrical
				cable connector provided as the interface. From SFF 8472 Rev 9.5
					  Value 	Description of connector
						00h 	Unknown or unspecified
						01h 	SC
						02h 	Fibre Channel Style 1 copper connector
						03h 	Fibre Channel Style 2 copper connector
						04h 	BNC/TNC
						05h 	Fibre Channel coaxial headers
						06h 	FiberJack
						07h 	LC
						08h 	MT-RJ
						09h 	MU
						0Ah 	SG
						0Bh 	Optical pigtail
						0C-1Fh 	Reserved
						20h 	HSSDC II
						21h 	Copper Pigtail
						22h-7Fh Reserved
						80-FFh 	Vendor specific	"
	::= { sfbrm100DMIEntry 4 }

sfbrm100DMIBitRate	OBJECT-TYPE
    SYNTAX INTEGER
	ACCESS read-only
	STATUS mandatory
	DESCRIPTION "Bitrate in units of 100Mbps."
	::= { sfbrm100DMIEntry 5 }

sfbrm100DMILenFor9x125umKM OBJECT-TYPE
    SYNTAX INTEGER
	ACCESS read-only
	STATUS mandatory
	DESCRIPTION "Specifies the link length that is supported by the transceiver
				while operating in single mode fiber. The value is in units of KM."
	::= { sfbrm100DMIEntry 6 }

sfbrm100DMILenFor9x125um100M  OBJECT-TYPE
    SYNTAX INTEGER
	ACCESS read-only
	STATUS mandatory
	DESCRIPTION "Specifies the link length that is supported by the transceiver
				while operating in single mode fiber. The value is in units of 100m."
	::= { sfbrm100DMIEntry 7 }

sfbrm100DMILenFor50x125um10M  OBJECT-TYPE
    SYNTAX INTEGER
	ACCESS read-only
	STATUS mandatory
	DESCRIPTION "Specifies the link length that is supported by the transceiver
				while operating in 50 micron multi mode fiber. The value is in units of 10m."
	::= { sfbrm100DMIEntry 8 }

sfbrm100DMILenFor625x125um10M  OBJECT-TYPE
    SYNTAX INTEGER
	ACCESS read-only
	STATUS mandatory
	DESCRIPTION "Specifies the link length that is supported by the transceiver
				while operating in 62.5 micron multi mode fiber. The value is in units of 10m."
	::= { sfbrm100DMIEntry 9 }

sfbrm100DMILenForCopper   OBJECT-TYPE
    SYNTAX INTEGER
	ACCESS read-only
	STATUS mandatory
	DESCRIPTION "Specifies the link length that is supported by the transceiver
				while operating in copper cable. The value is in units of meters."
	::= { sfbrm100DMIEntry 10 }

sfbrm100DMIId	OBJECT-TYPE
    SYNTAX INTEGER
	ACCESS read-only
	STATUS mandatory
	DESCRIPTION "Specifies the physical device. The table below
				from SFF-8472 Rev 9.5 Standard gives description
				for the values.
					00h Unknown or unspecified
					01h GBIC
					02h Module/connector soldered to motherboard
					03h SFP
					04-7Fh Reserved
					80-FFh Vendor specific."
	::= { sfbrm100DMIEntry 11 }

sfbrm100DMILaserWavelength  OBJECT-TYPE
    SYNTAX INTEGER
	ACCESS read-only
	STATUS mandatory
	DESCRIPTION "The Nominal transmitter output wavelength at room temperature.
				The units in nm"
	::= { sfbrm100DMIEntry 12 }

sfbrm100DMITemperature  OBJECT-TYPE
    SYNTAX INTEGER
	ACCESS read-only
	STATUS mandatory
	DESCRIPTION "Temperature of fiber transceiver in tenths of 
 				degrees C."
	::= { sfbrm100DMIEntry 13 }

sfbrm100DMITempAlarm OBJECT-TYPE
    SYNTAX INTEGER { normal(1), notSupported(2), lowWarn(3), highWarn(4), lowAlarm(6), highAlarm(7) }
	ACCESS read-only
	STATUS mandatory
	DESCRIPTION "."
	::= { sfbrm100DMIEntry 14 }			

sfbrm100DMITxBiasCurrent		OBJECT-TYPE
    SYNTAX INTEGER
	ACCESS read-only
	STATUS mandatory
	DESCRIPTION "Transmit bias current on local fiber interface, in 
 				microamperes."
	::= { sfbrm100DMIEntry 15 }

sfbrm100DMITxBiasAlarm OBJECT-TYPE
    SYNTAX INTEGER { normal(1), notSupported(2), lowWarn(3), highWarn(4), lowAlarm(6), highAlarm(7) }
	ACCESS read-only
	STATUS mandatory
	DESCRIPTION "."
	::= { sfbrm100DMIEntry 16 }			

sfbrm100DMITxPowerLevel	OBJECT-TYPE
    SYNTAX INTEGER
	ACCESS read-only
	STATUS mandatory
	DESCRIPTION "DMI: Diagnostic Monitoring Interface for fiber 
			 	transceivers. Transmit power on local fiber 
			 	measured in microwatts."
	::= { sfbrm100DMIEntry 17 }

sfbrm100DMITxPowerAlarm	OBJECT-TYPE
    SYNTAX INTEGER { normal(1), notSupported(2), lowWarn(3), highWarn(4), lowAlarm(6), highAlarm(7) }
	ACCESS read-only
	STATUS mandatory
	DESCRIPTION "."
	::= { sfbrm100DMIEntry 18 }			
				    
sfbrm100DMIRxPowerLevel	OBJECT-TYPE
    SYNTAX INTEGER
	ACCESS read-only
	STATUS mandatory
	DESCRIPTION "DMI: Diagnostic Monitoring Interface for fiber 
			 	transceivers. Receive power on local fiber 
			 	measured in microwatts."
	::= { sfbrm100DMIEntry 19 }
                    
sfbrm100DMIRxPowerAlarm	OBJECT-TYPE
    SYNTAX INTEGER { normal(1), notSupported(2), lowWarn(3), highWarn(4), lowAlarm(6), highAlarm(7) }
	ACCESS read-only
	STATUS mandatory
	DESCRIPTION "."
	::= { sfbrm100DMIEntry 20 }

sfbrm100PortL2CPTable OBJECT-TYPE
    SYNTAX SEQUENCE OF Sfbrm100PortL2CPEntry
    ACCESS not-accessible
    STATUS mandatory
    DESCRIPTION "Port L2CP processing."
	::= { sfbrmPort 4 }

sfbrm100PortL2CPEntry OBJECT-TYPE
    SYNTAX Sfbrm100PortL2CPEntry
    ACCESS not-accessible
    STATUS mandatory
    DESCRIPTION "Status and configuration entries for a each port on the device."
    INDEX { sfbrm100PortLocIndex, sfbrm100PortRmtIndex }
    ::= { sfbrm100PortL2CPTable 1 }

Sfbrm100PortL2CPEntry ::=         
	    SEQUENCE {
	    	sfbrm100PortL2CPLocIndex   	        INTEGER,
			sfbrm100PortL2CPRmtIndex            INTEGER,
			sfbrm100STPProtocolsFwd				INTEGER,
			sfbrm100SlowProtocolsFwd			INTEGER,
			sfbrm100PortAuthProtocolFwd			INTEGER,
			sfbrm100ELMIProtocolFwd				INTEGER,
			sfbrm100LLDPProtocolFwd				INTEGER, 
			sfbrm100BridgeMgmtProtocolsFwd		INTEGER,
			sfbrm100GARPBlockProtocolsFwd		INTEGER,			
			sfbrm100BridgeBlkOtherMulticastsFwd	INTEGER
			}   
			
sfbrm100PortL2CPLocIndex  OBJECT-TYPE
	SYNTAX INTEGER
	ACCESS read-only
	STATUS mandatory
	DESCRIPTION "Uniquely indentifies each port on the device."
	::= { sfbrm100PortL2CPEntry 1 }

sfbrm100PortL2CPRmtIndex  OBJECT-TYPE
	SYNTAX INTEGER
	ACCESS read-only
	STATUS mandatory
	DESCRIPTION "Uniquely indentifies each port on the peer device."
	::= { sfbrm100PortL2CPEntry 2 }
	
sfbrm100STPProtocolsFwd  OBJECT-TYPE
	SYNTAX INTEGER  { tunnel(1), discard(2) }
    ACCESS read-write
	STATUS mandatory
	DESCRIPTION "Any STP/RSTP/MSTP protocol frames with destination address
				 of 01-80-C2-00-00-00 is discarded at this port or tunnelled."
	::= { sfbrm100PortL2CPEntry 3 }

sfbrm100SlowProtocolsFwd  OBJECT-TYPE
	SYNTAX INTEGER  { tunnel(1), discard(2) }
    ACCESS read-write
	STATUS mandatory
	DESCRIPTION "Any LACP/LAMP protocol frames with destination address
				 of 01-80-C2-00-00-02 is discarded at this port or tunnelled.
				 Since this device pairs link OAM frames, these frames will not
				 forwarded or discarded."
	::= { sfbrm100PortL2CPEntry 4 }

sfbrm100PortAuthProtocolFwd  OBJECT-TYPE
	SYNTAX INTEGER  { tunnel(1), discard(2) }
    ACCESS read-write
	STATUS mandatory
	DESCRIPTION "Port authentication protocol frames with destination address
				 of 01-80-C2-00-00-03 is discarded at this port or tunnelled."
	::= { sfbrm100PortL2CPEntry 5 }

sfbrm100ELMIProtocolFwd  OBJECT-TYPE
	SYNTAX INTEGER  { tunnel(1), discard(2) }
    ACCESS read-write
	STATUS mandatory
	DESCRIPTION "E-LMI protocol frames with destination address
				 of 01-80-C2-00-00-07 is discarded at this port or tunnelled."
	::= { sfbrm100PortL2CPEntry 6 }
			
sfbrm100LLDPProtocolFwd OBJECT-TYPE
	SYNTAX INTEGER  { tunnel(1), discard(2) }
    ACCESS read-write
	STATUS mandatory
	DESCRIPTION "LLDP protocol frames with destination address
				 of 01-80-C2-00-00-0E is discarded at this port or tunnelled."
	::= { sfbrm100PortL2CPEntry 7 }

sfbrm100BridgeMgmtProtocolsFwd OBJECT-TYPE
	SYNTAX INTEGER  { tunnel(1), discard(2) }
    ACCESS read-write
	STATUS mandatory
	DESCRIPTION "Bridge Management protocol frames with destination address
				 of 01-80-C2-00-00-10 is discarded at this port or tunnelled."
	::= { sfbrm100PortL2CPEntry 8 }

sfbrm100GARPBlockProtocolsFwd OBJECT-TYPE
	SYNTAX INTEGER  { tunnel(1), discard(2) }
    ACCESS read-write
	STATUS mandatory
	DESCRIPTION "GARP/MRP with destination address of 01-80-C2-00-00-20 to 01-80-C2-00-00-2F
				 is discarded at this port or tunnelled."
	::= { sfbrm100PortL2CPEntry 9 }

sfbrm100BridgeBlkOtherMulticastsFwd OBJECT-TYPE
	SYNTAX INTEGER  { tunnel(1), discard(2) }
    ACCESS read-write
	STATUS mandatory
	DESCRIPTION "This mib variable tunnels or discards all the IEEE multicast
				frames in the bridge block of addresses [01-80-C2-00-00-20 to 01-80-C2-00-00-0F].
				The mib variables applies to all addresses in this block that are not covered by 
				the other mib variables in this table.
				i.e this is not applicable for STP, slow protocols, etc.,"
	::= { sfbrm100PortL2CPEntry 10 }
			
-- ATU Table	
sfbrm100FwdDBTable OBJECT-TYPE
    SYNTAX SEQUENCE OF Sfbrm100FwdDBEntry
    ACCESS not-accessible
    STATUS mandatory
    DESCRIPTION "Learned address database for this device."
	::= { sfbrmAddrDB 1 }

sfbrm100FwdDBEntry OBJECT-TYPE
    SYNTAX Sfbrm100FwdDBEntry
    ACCESS not-accessible
    STATUS mandatory
    DESCRIPTION "Status and configuration entries for a single port on this device."
    INDEX { sfbrm100FwdLocPortIndex, sfbrm100FwdDBNum, sfbrm100FwdMacAddress }
    ::= { sfbrm100FwdDBTable 1 }

Sfbrm100FwdDBEntry ::=         
    SEQUENCE {                             
    	sfbrm100FwdLocPortIndex		INTEGER,    
    	sfbrm100FwdDBNum			INTEGER,
    	sfbrm100FwdMacAddress		PhysAddress,
		sfbrm100FwdConnPort			INTEGER,
    	sfbrm100FwdPriority			INTEGER,
		sfbrm100FwdEntryType		INTEGER,
    	sfbrm100FwdEntryStatus		INTEGER
	}

sfbrm100FwdLocPortIndex OBJECT-TYPE
    SYNTAX INTEGER
	ACCESS read-only
	STATUS mandatory
	DESCRIPTION "The entry can belong to the local switch or one of the
	             remote peers. The local switch has the index as zero.
	             The remote peers have the port index of the local port
	             to which they are connected."
	::= { sfbrm100FwdDBEntry 1 }

sfbrm100FwdDBNum 	OBJECT-TYPE
    SYNTAX INTEGER (0..255)
    ACCESS read-only
	STATUS mandatory
	DESCRIPTION "The Address Database Number the entry belongs to. 
                 DBNum of 0 is the default database."
	::= { sfbrm100FwdDBEntry 2 }

sfbrm100FwdMacAddress 	OBJECT-TYPE
    SYNTAX PhysAddress
	ACCESS read-only
	STATUS mandatory
	DESCRIPTION "The unicast or multicast address."
	::= { sfbrm100FwdDBEntry 3 }

sfbrm100FwdConnPort OBJECT-TYPE
    SYNTAX INTEGER
	ACCESS read-write
	STATUS mandatory
	DESCRIPTION "The index of the logical Port from sfbrm100PortTable to which the MAC address
	             is connected."
	::= { sfbrm100FwdDBEntry 4 }

sfbrm100FwdPriority OBJECT-TYPE
    SYNTAX INTEGER
	ACCESS read-write
	STATUS mandatory
	DESCRIPTION "The priority of this entry."
	::= { sfbrm100FwdDBEntry 5 }

sfbrm100FwdEntryType OBJECT-TYPE
    SYNTAX INTEGER  { static(1), staticNRL(2), staticPA(3), dynamic(4) }
	ACCESS read-write
	STATUS mandatory
	DESCRIPTION "The Entry state of this unicast or multicast entry. 
				The types represent :
					static(1)    - A Valid entry that doesnot age.
					staticNRL(2) - A static entry that has no ingress rate limiting.
					staticPA(3)  - A static entry that has priority override enabled.
					dynamic(4)   - A valid entry with no special attributes which
					               ages and finally removed from the database.
					
				A unicast entry can be static(1) or staticPA(3) but not 
				staticNRL(2). For MAC address which are learned, the read-only value
				of dynamic(4) is returned."
	::= { sfbrm100FwdDBEntry 6 }

sfbrm100FwdEntryStatus OBJECT-TYPE
    SYNTAX INTEGER  { write(1), delete(2), valid(3) }
	ACCESS read-write
	STATUS mandatory
	DESCRIPTION "The status of the row and operations on the entry.
				 write(1) is used to create a entry with default values.
			     Immediately after completing the add operation, the agent
			     sets this object to valid(1) if the operation was successful.
				 It is also used to change the existing entry's properties like priority,
				 type and port associations.
					 
				 delete(2) is used to delete any entries created by the managment station.
				       
			     An entry in the read-only value of valid(3) state is fully configured and
			     consistent."
         
    ::= { sfbrm100FwdDBEntry 7 }

--VLAN Table
sfbrm100VlanTable OBJECT-TYPE
    SYNTAX SEQUENCE OF Sfbrm100VlanEntry
    ACCESS not-accessible
    STATUS mandatory
    DESCRIPTION "VLAN database for this device."
	::= { sfbrmAddrDB 2 }

sfbrm100VlanEntry OBJECT-TYPE
    SYNTAX Sfbrm100VlanEntry
    ACCESS not-accessible
    STATUS mandatory
    DESCRIPTION "Status and configuration entries for a single port on this device."
    INDEX { sfbrm100VlanLocPortIndex, sfbrm100VlanDBNum, sfbrm100VlanVID }
    ::= { sfbrm100VlanTable 1 }

Sfbrm100VlanEntry ::=         
    SEQUENCE {              
    	sfbrm100VlanLocPortIndex	INTEGER,
		sfbrm100VlanDBNum			INTEGER,    	
    	sfbrm100VlanVID				INTEGER,
    	sfbrm100VlanVIDPriOverride	INTEGER,
		sfbrm100VlanVIDPriority		INTEGER,
		sfbrm100VlanMemTagPort1		INTEGER,
		sfbrm100VlanMemTagPort2		INTEGER,
		sfbrm100VlanMemTagPort3		INTEGER,
		sfbrm100VlanMemTagPort4		INTEGER,
		sfbrm100VlanMemTagPort5		INTEGER,
		sfbrm100VlanMemTagPort6		INTEGER,
		sfbrm100VlanMemTagPort7		INTEGER,
		sfbrm100VlanMemTagPort8		INTEGER,
		sfbrm100VlanMemTagPort9		INTEGER,
		sfbrm100VlanMemTagPort10	INTEGER,		
		sfbrm100VlanEntryStatus		INTEGER
	}
		
sfbrm100VlanLocPortIndex OBJECT-TYPE
    SYNTAX INTEGER
	ACCESS read-only
	STATUS mandatory
	DESCRIPTION "The entry can belong to the local switch or one of the
	             remote peers. The local switch has the index as zero.
	             The remote peers have the port index of the local port
	             to which they are connected."
	::= { sfbrm100VlanEntry 1 }

sfbrm100VlanDBNum 	OBJECT-TYPE
    SYNTAX INTEGER (0..255)
    ACCESS read-only
	STATUS mandatory
	DESCRIPTION "The Address Database Number the entry belongs to. 
                 DBNum of 0 is the default database."
	::= { sfbrm100VlanEntry 2 }

sfbrm100VlanVID 	OBJECT-TYPE
    SYNTAX INTEGER 
    ACCESS read-only
	STATUS mandatory
	DESCRIPTION "The VLAN ID of the entry."
	::= { sfbrm100VlanEntry 3 }

sfbrm100VlanVIDPriOverride 	OBJECT-TYPE
    SYNTAX INTEGER { enable(1), disable(2) }
    ACCESS read-write
	STATUS mandatory
	DESCRIPTION "Override Priority on frames assosicated with this VID."
	::= { sfbrm100VlanEntry 4 }

sfbrm100VlanVIDPriority 	OBJECT-TYPE
    SYNTAX INTEGER 
    ACCESS read-write
	STATUS mandatory
	DESCRIPTION "Priority for frames assosicated with this VID."
	::= { sfbrm100VlanEntry 5 }

sfbrm100VlanMemTagPort1 	OBJECT-TYPE
    SYNTAX INTEGER { memEgressNoMod(1), memEgressNoTag(2), memEgressTag(3), notMember(4), notApplicable(5) }
    ACCESS read-write
	STATUS mandatory
	DESCRIPTION "Membership and Egress Tagging on Logical Port 1.
				    memEgressNoMode(1)- Port 1 is a member of this VLAN and frames
				                         that egress are unmodified.
				    memEgressNoTag(2) - Port 1 is a member of this VLAN and frames
				                         that egress are untagged.
				    memEgressTag(3)   - Port 1 is a member of this VLAN and frames
				                         that egress are tagged.
				    notMember(4)      - Port 1 is not a member of this VLAN and frames
				                         that ingress with this VID are discarded.
				    notApplicable(5) is returned if there is no valid port."				                         
				                         
	::= { sfbrm100VlanEntry 6 }

sfbrm100VlanMemTagPort2 	OBJECT-TYPE
    SYNTAX INTEGER { memEgressNoMod(1), memEgressNoTag(2), memEgressTag(3), notMember(4), notApplicable(5) }
    ACCESS read-write
	STATUS mandatory
	DESCRIPTION "Membership and Egress Tagging on Logical Port 2.
				    memEgressNoMode(1)- Port 2 is a member of this VLAN and frames
				                         that egress are unmodified.
				    memEgressNoTag(2) - Port 2 is a member of this VLAN and frames
				                         that egress are untagged.
				    memEgressTag(3)   - Port 2 is a member of this VLAN and frames
				                         that egress are tagged.
				    notMember(4)      - Port 2 is not a member of this VLAN and frames
				                         that ingress with this VID are discarded.
				    notApplicable(5) is returned if there is no valid port."      
				                   
	::= { sfbrm100VlanEntry 7 }

sfbrm100VlanMemTagPort3 	OBJECT-TYPE
    SYNTAX INTEGER { memEgressNoMod(1), memEgressNoTag(2), memEgressTag(3), notMember(4), notApplicable(5) }
    ACCESS read-write
	STATUS mandatory
	DESCRIPTION "Membership and Egress Tagging on Logical Port 3.
				    memEgressNoMode(1)- Port 3 is a member of this VLAN and frames
				                         that egress are unmodified.
				    memEgressNoTag(2) - Port 3 is a member of this VLAN and frames
				                         that egress are untagged.
				    memEgressTag(3)   - Port 3 is a member of this VLAN and frames
				                         that egress are tagged.
				    notMember(4)      - Port 3 is not a member of this VLAN and frames
				                         that ingress with this VID are discarded.
				    notApplicable(5) is returned if there is no valid port."      
				                   
	::= { sfbrm100VlanEntry 8 }

sfbrm100VlanMemTagPort4 	OBJECT-TYPE
    SYNTAX INTEGER { memEgressNoMod(1), memEgressNoTag(2), memEgressTag(3), notMember(4), notApplicable(5) }
    ACCESS read-write
	STATUS mandatory
	DESCRIPTION "Membership and Egress Tagging on Logical Port 4.
				    memEgressNoMode(1)- Port 4 is a member of this VLAN and frames
				                         that egress are unmodified.
				    memEgressNoTag(2) - Port 4 is a member of this VLAN and frames
				                         that egress are untagged.
				    memEgressTag(3)   - Port 4 is a member of this VLAN and frames
				                         that egress are tagged.
				    notMember(4)      - Port 4 is not a member of this VLAN and frames
				                         that ingress with this VID are discarded.
				    notApplicable(5) is returned if there is no valid port."      
				                   
	::= { sfbrm100VlanEntry 9 }

sfbrm100VlanMemTagPort5 	OBJECT-TYPE
    SYNTAX INTEGER { memEgressNoMod(1), memEgressNoTag(2), memEgressTag(3), notMember(4), notApplicable(5) }
    ACCESS read-write
	STATUS mandatory
	DESCRIPTION "Membership and Egress Tagging on Logical Port 5.
				    memEgressNoMode(1)- Port 5 is a member of this VLAN and frames
				                         that egress are unmodified.
				    memEgressNoTag(2) - Port 5 is a member of this VLAN and frames
				                         that egress are untagged.
				    memEgressTag(3)   - Port 5 is a member of this VLAN and frames
				                         that egress are tagged.
				    notMember(4)      - Port 5 is not a member of this VLAN and frames
				                         that ingress with this VID are discarded.
				    notApplicable(5) is returned if there is no valid port."      
				                   
	::= { sfbrm100VlanEntry 10 }              

sfbrm100VlanMemTagPort6 	OBJECT-TYPE
    SYNTAX INTEGER { memEgressNoMod(1), memEgressNoTag(2), memEgressTag(3), notMember(4), notApplicable(5) }
    ACCESS read-write
	STATUS mandatory
	DESCRIPTION "Membership and Egress Tagging on Logical Port 6.
				    memEgressNoMode(1)- Port 6 is a member of this VLAN and frames
				                         that egress are unmodified.
				    memEgressNoTag(2) - Port 6 is a member of this VLAN and frames
				                         that egress are untagged.
				    memEgressTag(3)   - Port 6 is a member of this VLAN and frames
				                         that egress are tagged.
				    notMember(4)      - Port 6 is not a member of this VLAN and frames
				                         that ingress with this VID are discarded.
				    notApplicable(5) is returned if there is no valid port."      
				                   
	::= { sfbrm100VlanEntry 11 }
	
sfbrm100VlanMemTagPort7 	OBJECT-TYPE
    SYNTAX INTEGER { memEgressNoMod(1), memEgressNoTag(2), memEgressTag(3), notMember(4), notApplicable(5) }
    ACCESS read-write
	STATUS mandatory
	DESCRIPTION "Membership and Egress Tagging on Logical Port 7.
				    memEgressNoMode(1)- Port 7 is a member of this VLAN and frames
				                         that egress are unmodified.
				    memEgressNoTag(2) - Port 7 is a member of this VLAN and frames
				                         that egress are untagged.
				    memEgressTag(3)   - Port 7 is a member of this VLAN and frames
				                         that egress are tagged.
				    notMember(4)      - Port 7 is not a member of this VLAN and frames
				                         that ingress with this VID are discarded.
				    notApplicable(5) is returned if there is no valid port."      
				                   
	::= { sfbrm100VlanEntry 12 }

sfbrm100VlanMemTagPort8 	OBJECT-TYPE
    SYNTAX INTEGER { memEgressNoMod(1), memEgressNoTag(2), memEgressTag(3), notMember(4), notApplicable(5) }
    ACCESS read-write
	STATUS mandatory
	DESCRIPTION "Membership and Egress Tagging on Logical Port 8.
				    memEgressNoMode(1)- Port 8 is a member of this VLAN and frames
				                         that egress are unmodified.
				    memEgressNoTag(2) - Port 8 is a member of this VLAN and frames
				                         that egress are untagged.
				    memEgressTag(3)   - Port 8 is a member of this VLAN and frames
				                         that egress are tagged.
				    notMember(4)      - Port 8 is not a member of this VLAN and frames
				                         that ingress with this VID are discarded.
				    notApplicable(5) is returned if there is no valid port."      
				                   
	::= { sfbrm100VlanEntry 13 }
	
sfbrm100VlanMemTagPort9 	OBJECT-TYPE
    SYNTAX INTEGER { memEgressNoMod(1), memEgressNoTag(2), memEgressTag(3), notMember(4), notApplicable(5) }
    ACCESS read-write
	STATUS mandatory
	DESCRIPTION "Membership and Egress Tagging on Logical Port 9.
				    memEgressNoMode(1)- Port 9 is a member of this VLAN and frames
				                         that egress are unmodified.
				    memEgressNoTag(2) - Port 9 is a member of this VLAN and frames
				                         that egress are untagged.
				    memEgressTag(3)   - Port 9 is a member of this VLAN and frames
				                         that egress are tagged.
				    notMember(4)      - Port 9 is not a member of this VLAN and frames
				                         that ingress with this VID are discarded.
				    notApplicable(5) is returned if there is no valid port."      
				                   
	::= { sfbrm100VlanEntry 14 }

sfbrm100VlanMemTagPort10 	OBJECT-TYPE
    SYNTAX INTEGER { memEgressNoMod(1), memEgressNoTag(2), memEgressTag(3), notMember(4), notApplicable(5) }
    ACCESS read-write
	STATUS mandatory
	DESCRIPTION "Membership and Egress Tagging on Logical Port 10.
				    memEgressNoMode(1)- Port 10 is a member of this VLAN and frames
				                         that egress are unmodified.
				    memEgressNoTag(2) - Port 10 is a member of this VLAN and frames
				                         that egress are untagged.
				    memEgressTag(3)   - Port 10 is a member of this VLAN and frames
				                         that egress are tagged.
				    notMember(4)      - Port 10 is not a member of this VLAN and frames
				                         that ingress with this VID are discarded.
				    notApplicable(5) is returned if there is no valid port."      
				                   
	::= { sfbrm100VlanEntry 15 }

sfbrm100VlanEntryStatus 	OBJECT-TYPE
    SYNTAX INTEGER  { write(1), delete(2), valid(3) }
	ACCESS read-write
	STATUS mandatory
	DESCRIPTION "The status of the row and operations on the entry.
				 write(1) is used to create a entry with default values.
			     Immediately after completing the add operation, the agent
			     sets this object to valid(1) if the operation was successful.
				 It is also used to change the existing entry's properties like priority,
				 type and port associations.
					 
				 delete(2) is used to delete any entries created by the managment station.
				       
			     An entry in the read-only value of valid(3) state is fully configured and
			     consistent."
		         
	::= { sfbrm100VlanEntry 16 }
	

-- Traps from IP-Based FBRM10x100y board		
sfbrm100ATUDbFull TRAP-TYPE
        ENTERPRISE brdgFBRMId
        DESCRIPTION
			"The Address Translation Database is full, no more entries can be added."
		::= 119

sfbrm100VTUMemberViolation TRAP-TYPE
        ENTERPRISE brdgFBRMId
        DESCRIPTION
			"A Frame with VLAN ID found in the VLAN Table has been received, but the Ingress
			port is not a member of the VLAN."
		::= 120

sfbrm100VTUMissViolation TRAP-TYPE
        ENTERPRISE brdgFBRMId
        DESCRIPTION
			"A Frame with a VLAN ID not in VLAN Table is received."
		::= 121

sfbrm100ATUMemberViolation TRAP-TYPE
        ENTERPRISE brdgFBRMId
        DESCRIPTION
			"A Source address look-up in the Address Database finds a entry but
			 the ingress port is not on the list of source port."
		::= 122

sfbrm100ATUMissViolation TRAP-TYPE
        ENTERPRISE brdgFBRMId
        DESCRIPTION
			"A source address look-up in the Address Database resulted in a
			miss."
		::= 123

sfbrm100OAMRemoteDetected TRAP-TYPE
        ENTERPRISE brdgFBRMId
        DESCRIPTION
			"A OAM peer is detected and active OAM communication is established with the Peer."
		::= 124

sfbrm100EEPROMOnFiber TRAP-TYPE
        ENTERPRISE brdgFBRMId
        DESCRIPTION
			"EEPROM for monitoring, is detected on this port."
		::= 125

sfbrm100DMIOnFiber TRAP-TYPE
        ENTERPRISE brdgFBRMId
        DESCRIPTION
			"DMI is detected on this port."
		::= 126

sfbrm100LinkChanged TRAP-TYPE
        ENTERPRISE brdgFBRMId
        DESCRIPTION
			"A Link Status change occurred."
		::= 127

sfbrm100DMILowRxIntrusion TRAP-TYPE
        ENTERPRISE brdgFBRMId
        DESCRIPTION
			"Intrusion detected on Rx Power."
		::= 128

sfbrm100DMILowRxPower TRAP-TYPE
        ENTERPRISE brdgFBRMId
        DESCRIPTION
			"Rx Power Alarm."
		::= 129

sfbrm100DMILowTxPower TRAP-TYPE
        ENTERPRISE brdgFBRMId
        DESCRIPTION
			"Tx Power Alarm."
		::= 130

sfbrm100DMILowTxBias TRAP-TYPE
        ENTERPRISE brdgFBRMId
        DESCRIPTION
			"Transmit bias alarm."
		::= 131

sfbrm100DMILowTemperature TRAP-TYPE
        ENTERPRISE brdgFBRMId
        DESCRIPTION
			"Temperature alarm."
		::= 132		                                  

sfbrm100LastGasp TRAP-TYPE
		ENTERPRISE brdgFBRMId
		DESCRIPTION
			"The Last gasp from the local device."
		::= 133
		
sfbrm100OAMPeerLinkDown TRAP-TYPE
		ENTERPRISE brdgFBRMId
		DESCRIPTION
			"The remote port is down on the peer."
		::= 134

sfbrm100OAMPeerLinkUp TRAP-TYPE
		ENTERPRISE brdgFBRMId
		DESCRIPTION
			"The remote port is up on the peer."
		::= 135

sfbrm100OAMPeerDyingGasp TRAP-TYPE
		ENTERPRISE brdgFBRMId
		DESCRIPTION
			"The remote peer OAM dying gasp trap."
		::= 136

sfbrm100OAMThresholdEvent TRAP-TYPE
		ENTERPRISE brdgFBRMId
		DESCRIPTION
			"Local/remote peer's OAM Threshold crossing traps."
		::= 137

sfbrm100PeerVersionMismatch TRAP-TYPE
		ENTERPRISE brdgFBRMId
		DESCRIPTION
			"The remote peer is running a different firmware than local.
			The remote peer needs upgrading."
		::= 138
		
END
