-- $Id: it-ppp-mib.mib,v 1.2 2001/06/26 13:45:27 sse Exp $
        ITOUCH-PPP-MIB DEFINITIONS ::= BEGIN

               IMPORTS
                       Counter, IpAddress
                               FROM RFC1155-SMI
                       ifIndex
                               FROM RFC1213-MIB
                       OBJECT-TYPE
                               FROM RFC-1212
                       iTouch
                               FROM ITOUCH-MIB;

       xPpp            OBJECT IDENTIFIER ::= { iTouch 22 }

       -- The individual Groups within the PPP MIB

       xPppBasic       OBJECT IDENTIFIER ::= { xPpp 1 }
       xPppLcp         OBJECT IDENTIFIER ::= { xPpp 2 }
       xPppIpcp        OBJECT IDENTIFIER ::= { xPpp 3 }
       xPppAuth        OBJECT IDENTIFIER ::= { xPpp 4 }
       xPppIpxcp       OBJECT IDENTIFIER ::= { xPpp 5 }

 


            -- This is a MIB module for all iTouch Communications systems that
            -- implement PPP.

            -- Copyright 2000 iTouch Communications, Inc. All Rights Reserved.
            -- Reproduction of this document is authorized on
            -- condition that this copyright notice is included.
            -- This MIB document embodies iTouch Communications, Inc.'s 
            -- proprietary intellectual property.  iTouch Communications, Inc.
            -- retains all title and ownership in this MIB, including any
            -- revisions.
            --
            -- It is iTouch Communications, Inc.'s intent to encourage the
            -- widespread use of this MIB in connection with the management of
            -- iTouch Communications, Inc. products. iTouch Communications,
            -- Inc. grants vendors,end-users, and other interested parties a
            -- non-exclusive license to use this MIB in connection with the
            -- management of iTouch Communications, Inc. products.
            --
            -- This MIB document is supplied "AS IS," and iTouch 
            -- Communications, Inc. makes no warranty, either express or
            -- implied, as to the use operation, condition, or performance of
            -- the MIB.


       -- the PPP basic group

       -- Implementation of this group is mandatory for all iTouch
       -- systems that implement PPP

       xPppConfigTable OBJECT-TYPE
           SYNTAX SEQUENCE OF XPppConfigEntry
           ACCESS not-accessible
           STATUS mandatory
           DESCRIPTION
               "A table containing PPP specific variables for this 
               PPP implementation."
           ::= { xPppBasic 1 }

       xPppConfigEntry OBJECT-TYPE
           SYNTAX XPppConfigEntry
           ACCESS not-accessible
           STATUS mandatory
           DESCRIPTION
               "Management information about a particular PPP."
           INDEX { ifIndex }
           ::= { xPppConfigTable 1 }

       XPppConfigEntry ::=
           SEQUENCE {
               xPppConfigOpen
                   INTEGER,
               xPppConfigActive
                   INTEGER,
               xPppConfigDefaults
                   INTEGER,
               xPppConfigRestartTimer
                   INTEGER,
               xPppConfigConfLimit
                   INTEGER,
               xPppConfigFailLimit
                   INTEGER,
               xPppConfigPacketLogging
                   INTEGER,
               xPppConfigKATimer
                   INTEGER,
               xPppConfigKATimeout
                   INTEGER
           }

       xPppConfigOpen OBJECT-TYPE
           SYNTAX INTEGER { disabled(1), enabled(2)}
           ACCESS read-write
           STATUS mandatory
           DESCRIPTION
               "Determines if PPP is configured on this port."
           ::= { xPppConfigEntry 1 }

       xPppConfigActive OBJECT-TYPE
           SYNTAX INTEGER { active(1), passive(2)}
           ACCESS read-write
           STATUS mandatory
           DESCRIPTION
               "Determines if LCP will actively open or wait 
               passively."
           ::= { xPppConfigEntry 2 }

       xPppConfigDefaults OBJECT-TYPE
           SYNTAX INTEGER { ready(1), execute(2)}
           ACCESS read-write
           STATUS mandatory
           DESCRIPTION
               "Revert to factory default PPP parameters.  In 
               response to a get-request or get-next-request, the 
               agent always returns 'ready' for this value.  
               Setting the value to 'ready' has no effect.  Setting 
               it to 'execute' sets PPP parameters to factory 
               defaults."
           ::= { xPppConfigEntry 3 }

       xPppConfigRestartTimer OBJECT-TYPE
           SYNTAX INTEGER (1..10)
           ACCESS read-write
           STATUS mandatory
           DESCRIPTION
               "The number of seconds waited before retransmitting 
               during option negotiation."
           ::= { xPppConfigEntry 4 }

       xPppConfigConfLimit OBJECT-TYPE
           SYNTAX INTEGER (2..10)
           ACCESS read-write
           STATUS mandatory
           DESCRIPTION
               "Maximum number of times a configuration request 
               will be sent to the peer without receiving a 
               response."
           ::= { xPppConfigEntry 5 }

       xPppConfigFailLimit OBJECT-TYPE
           SYNTAX INTEGER (2..10)
           ACCESS read-write
           STATUS mandatory
           DESCRIPTION
               "Maximum number of times a peer's proposed option 
               will be NAKed before REJECTing the option."
           ::= { xPppConfigEntry 6 }

       xPppConfigPacketLogging OBJECT-TYPE
           SYNTAX INTEGER { none(1), raw(2), interpreted(3) }
           ACCESS read-write
           STATUS mandatory
           DESCRIPTION
               "Determines the level of packet logging to accounting on this port."
           ::= { xPppConfigEntry 7 }

       xPppConfigKATimer OBJECT-TYPE
           SYNTAX INTEGER ( 0..255 )
           ACCESS read-write
           STATUS mandatory
           DESCRIPTION
               "Determines the number of seconds between transmission of LCP Echo
		Keepalive packets."
           ::= { xPppConfigEntry 8 }

       xPppConfigKATimeout OBJECT-TYPE
           SYNTAX INTEGER
           ACCESS read-write
           STATUS mandatory
           DESCRIPTION
               "Determines the number of seconds to wait to hear LCP Echo Replies
		to our Echo Request Keepalive packets before giving up and shutting
		down the link."
           ::= { xPppConfigEntry 9 }

--     xPppConfigEntries 10 to 19 reserved for Internetworking products.

       xPppStatusTable OBJECT-TYPE
           SYNTAX SEQUENCE OF XPppStatusEntry
           ACCESS not-accessible
           STATUS mandatory
           DESCRIPTION
               "A table containing basic PPP status info."
           ::= { xPppBasic 2 }

       xPppStatusEntry OBJECT-TYPE
           SYNTAX XPppStatusEntry
           ACCESS not-accessible
           STATUS mandatory
           DESCRIPTION
               "Status information about a particular PPP."
           INDEX { ifIndex }
           ::= { xPppStatusTable 1 }

       XPppStatusEntry ::=
           SEQUENCE {
               xPppStatusState
                   INTEGER,
               xPppLinkOpen
                   INTEGER,
               xPppHdlcRxTotalPkts
                   Counter,
               xPppHdlcTxTotalPkts
                   Counter,
               xPppHdlcRxFrameErrs
                   Counter,
               xPppHdlcRxNoBuffer
                   Counter,
               xPppHdlcTxNoBuffer
                   Counter,
               xPppHdlcRxBadFcs
                   Counter,
               xPppHdlcVJDiscards
                   Counter
           }

       xPppStatusState OBJECT-TYPE
           SYNTAX INTEGER { disabled(1), enabled(2) }
           ACCESS read-only
           STATUS mandatory
           DESCRIPTION
               "Displays whether PPP is enabled or disabled on this 
               port."
           ::= { xPppStatusEntry 1 }

       xPppLinkOpen OBJECT-TYPE
           SYNTAX INTEGER { notOpen(1), open(2)}
           ACCESS read-only
           STATUS mandatory
           DESCRIPTION
               "Displays open status of the link."
           ::= { xPppStatusEntry 2 }

       xPppHdlcRxTotalPkts OBJECT-TYPE
           SYNTAX Counter
           ACCESS read-only
           STATUS mandatory
           DESCRIPTION
               "Total of all packets received on PPP link."
           ::= { xPppStatusEntry 3 }

       xPppHdlcTxTotalPkts OBJECT-TYPE
           SYNTAX Counter
           ACCESS read-only
           STATUS mandatory
           DESCRIPTION
               "Total of all packets transmitted on PPP link."
           ::= { xPppStatusEntry 4 }

       xPppHdlcRxFrameErrs OBJECT-TYPE
           SYNTAX Counter
           ACCESS read-only
           STATUS mandatory
           DESCRIPTION
               "Number of framing errors received on PPP link."
           ::= { xPppStatusEntry 5 }

       xPppHdlcRxNoBuffer OBJECT-TYPE
           SYNTAX Counter
           ACCESS read-only
           STATUS mandatory
           DESCRIPTION
               "Number of times a buffer was not available to  
               receive packet into."
           ::= { xPppStatusEntry 6 }

       xPppHdlcTxNoBuffer OBJECT-TYPE
           SYNTAX Counter
           ACCESS read-only
           STATUS mandatory
           DESCRIPTION
               "Number of times a buffer was not available to 
               transmit a packet from."
           ::= { xPppStatusEntry 7 }

       xPppHdlcRxBadFcs OBJECT-TYPE
           SYNTAX Counter
           ACCESS read-only
           STATUS mandatory
           DESCRIPTION
               "Number of packets received with a bad checksum."
           ::= { xPppStatusEntry 8 }

       xPppHdlcVJDiscards OBJECT-TYPE
           SYNTAX Counter
           ACCESS read-only
           STATUS mandatory
           DESCRIPTION
               "Number of packets received that failed VJ 
               decompression."
           ::= { xPppStatusEntry 9 }

       xPppLcpConfigTable OBJECT-TYPE
           SYNTAX SEQUENCE OF XPppLcpConfigEntry
           ACCESS not-accessible
           STATUS mandatory
           DESCRIPTION
               "A table containing PPP LCP specific variables for 
               this PPP implementation."
           ::= { xPppLcp 1 }

       xPppLcpConfigEntry OBJECT-TYPE
           SYNTAX XPppLcpConfigEntry
           ACCESS not-accessible
            STATUS mandatory
           DESCRIPTION
               "Management information about a particular PPP LCP 
               session."
           INDEX { ifIndex }
           ::= { xPppLcpConfigTable 1 }

       XPppLcpConfigEntry ::=
           SEQUENCE {
               xPppLcpConfigAuth
                   INTEGER,
               xPppLcpConfigChapAuth
                   INTEGER
           }

       xPppLcpConfigAuth OBJECT-TYPE
           SYNTAX INTEGER { none(1), pap(2)}
           ACCESS read-write
           STATUS mandatory
           DESCRIPTION
               "Authentication protocol used for authenticating 
               peers."
           ::= { xPppLcpConfigEntry 1 }

       xPppLcpConfigChapAuth OBJECT-TYPE
           SYNTAX INTEGER { none(1), chap(2)}
           ACCESS read-write
           STATUS mandatory
           DESCRIPTION
               "Authentication CHAP protocol used for authenticating 
               peers."
           ::= { xPppLcpConfigEntry 2 }

       xPppLcpStatusTable OBJECT-TYPE
           SYNTAX SEQUENCE OF XPppLcpStatusEntry
           ACCESS not-accessible
           STATUS mandatory
           DESCRIPTION
               "A table containing PPP LCP status info."
           ::= { xPppLcp 2 }

       xPppLcpStatusEntry OBJECT-TYPE
           SYNTAX XPppLcpStatusEntry
           ACCESS not-accessible
           STATUS mandatory
           DESCRIPTION
               "Status information about a particular PPP LCP 
               session."
           INDEX { ifIndex }
           ::= { xPppLcpStatusTable 1 }

       XPppLcpStatusEntry ::=
           SEQUENCE {
               xPppLcpStatusState
                   INTEGER,
               xPppLcpStatusRxAuth
                   INTEGER,
               xPppLcpStatusTxAuth
                   INTEGER,
               xPppLcpStatusRxConReq
                   Counter,
               xPppLcpStatusTxConReq
                   Counter,
               xPppLcpStatusRxConNak
                   Counter,
               xPppLcpStatusTxConNak
                   Counter,
               xPppLcpStatusRxConAck
                   Counter,
               xPppLcpStatusTxConAck
                   Counter,
               xPppLcpStatusRxConRej
                   Counter,
               xPppLcpStatusTxConRej
                   Counter,
               xPppLcpStatusRxTrmReq
                   Counter,
               xPppLcpStatusTxTrmReq
                   Counter,
               xPppLcpStatusRxTrmAck
                   Counter,
               xPppLcpStatusTxTrmAck
                   Counter,
               xPppLcpStatusRxEcoReq
                   Counter,
               xPppLcpStatusTxEcoReq
                   Counter,
               xPppLcpStatusRxEcoRep
                   Counter,
               xPppLcpStatusTxEcoRep
                   Counter,
               xPppLcpStatusRxCodRej
                   Counter,
               xPppLcpStatusTxCodRej
                   Counter,
               xPppLcpStatusRxProRej
                   Counter,
               xPppLcpStatusTxProRej
                   Counter,
               xPppLcpStatusState2
                   INTEGER
           }

       xPppLcpStatusState OBJECT-TYPE
           SYNTAX INTEGER { closed(1), listen(2), requestSent(3),
                            ackReceived(4), ackSent(5), open(6),
                            closing(7) }
           ACCESS read-only
           STATUS deprecated
           DESCRIPTION
               "The current state of LCP."
           ::= { xPppLcpStatusEntry 1 }

       xPppLcpStatusRxAuth OBJECT-TYPE
           SYNTAX INTEGER { none(1), pap(2)}
           ACCESS read-only
           STATUS mandatory
           DESCRIPTION
               "The authentication protocol currently in use from 
               the peer to us."
           ::= { xPppLcpStatusEntry 2 }

       xPppLcpStatusTxAuth OBJECT-TYPE
           SYNTAX INTEGER { none(1), pap(2)}
           ACCESS read-only
           STATUS mandatory
           DESCRIPTION
               "The authentication protocol currently in use from 
               us to the peer."
           ::= { xPppLcpStatusEntry 3 }

       xPppLcpStatusRxConReq OBJECT-TYPE
           SYNTAX Counter 
           ACCESS read-only
           STATUS mandatory
           DESCRIPTION
               "The count of LCP Configure Requests received from 
               the peer."
           ::= { xPppLcpStatusEntry 4 }

       xPppLcpStatusTxConReq OBJECT-TYPE
           SYNTAX Counter 
           ACCESS read-only
           STATUS mandatory
           DESCRIPTION
               "The count of LCP Configure Requests transmitted to 
               the peer."
           ::= { xPppLcpStatusEntry 5 }

       xPppLcpStatusRxConNak OBJECT-TYPE
           SYNTAX Counter 
           ACCESS read-only
           STATUS mandatory
           DESCRIPTION
               "The count of LCP Configure Naks received from the 
               peer."
           ::= { xPppLcpStatusEntry 6 }

       xPppLcpStatusTxConNak OBJECT-TYPE
           SYNTAX Counter 
           ACCESS read-only
           STATUS mandatory
           DESCRIPTION
               "The count of LCP Configure Naks transmitted to the 
               peer."
           ::= { xPppLcpStatusEntry 7 }

       xPppLcpStatusRxConAck OBJECT-TYPE
           SYNTAX Counter 
           ACCESS read-only
           STATUS mandatory
           DESCRIPTION
               "The count of LCP Configure Acks received from the 
               peer."
           ::= { xPppLcpStatusEntry 8 }

       xPppLcpStatusTxConAck OBJECT-TYPE
           SYNTAX Counter 
           ACCESS read-only
           STATUS mandatory
           DESCRIPTION
               "The count of LCP Configure Acks transmitted to the 
               peer."
           ::= { xPppLcpStatusEntry 9 }

       xPppLcpStatusRxConRej OBJECT-TYPE
           SYNTAX Counter 
           ACCESS read-only
           STATUS mandatory
           DESCRIPTION
               "The count of LCP Configure Rejects received from 
               the peer."
           ::= { xPppLcpStatusEntry 10 }

       xPppLcpStatusTxConRej OBJECT-TYPE
           SYNTAX Counter 
           ACCESS read-only
           STATUS mandatory
           DESCRIPTION
               "The count of LCP Configure Rejects transmitted to 
               the peer."
           ::= { xPppLcpStatusEntry 11 }

       xPppLcpStatusRxTrmReq OBJECT-TYPE
           SYNTAX Counter 
           ACCESS read-only
           STATUS mandatory
           DESCRIPTION
               "The count of LCP Terminate Requests received from 
               the peer."
           ::= { xPppLcpStatusEntry 12 }

       xPppLcpStatusTxTrmReq OBJECT-TYPE
           SYNTAX Counter 
           ACCESS read-only
           STATUS mandatory
           DESCRIPTION
               "The count of LCP Terminate Requests transmitted to 
               the peer."
           ::= { xPppLcpStatusEntry 13 }

       xPppLcpStatusRxTrmAck OBJECT-TYPE
           SYNTAX Counter 
           ACCESS read-only
           STATUS mandatory
           DESCRIPTION
               "The count of LCP Terminate Acks received from the 
               peer."
           ::= { xPppLcpStatusEntry 14 }

       xPppLcpStatusTxTrmAck OBJECT-TYPE
           SYNTAX Counter 
           ACCESS read-only
           STATUS mandatory
           DESCRIPTION
               "The count of LCP Terminate Acks transmitted to the 
               peer."
           ::= { xPppLcpStatusEntry 15 }

       xPppLcpStatusRxEcoReq OBJECT-TYPE
           SYNTAX Counter 
           ACCESS read-only
           STATUS mandatory
           DESCRIPTION
               "The count of LCP Echo Requests received from the 
               peer."
           ::= { xPppLcpStatusEntry 16 }

       xPppLcpStatusTxEcoReq OBJECT-TYPE
           SYNTAX Counter 
           ACCESS read-only
           STATUS mandatory
           DESCRIPTION
               "The count of LCP Echo Requests transmitted to the 
               peer."
           ::= { xPppLcpStatusEntry 17 }

       xPppLcpStatusRxEcoRep OBJECT-TYPE
           SYNTAX Counter 
           ACCESS read-only
           STATUS mandatory
           DESCRIPTION
               "The count of LCP Echo Reply received from the 
               peer."
           ::= { xPppLcpStatusEntry 18 }

       xPppLcpStatusTxEcoRep OBJECT-TYPE
           SYNTAX Counter 
           ACCESS read-only
           STATUS mandatory
           DESCRIPTION
               "The count of LCP Echo Reply transmitted to the 
               peer."
           ::= { xPppLcpStatusEntry 19 }

       xPppLcpStatusRxCodRej OBJECT-TYPE
           SYNTAX Counter 
           ACCESS read-only
           STATUS mandatory
           DESCRIPTION
               "The count of LCP Code Rejects received from the 
               peer."
           ::= { xPppLcpStatusEntry 20 }

       xPppLcpStatusTxCodRej OBJECT-TYPE
           SYNTAX Counter 
           ACCESS read-only
           STATUS mandatory
           DESCRIPTION
               "The count of LCP Code Rejects transmitted to the 
               peer."
           ::= { xPppLcpStatusEntry 21 }

       xPppLcpStatusRxProRej OBJECT-TYPE
           SYNTAX Counter 
           ACCESS read-only
           STATUS mandatory
           DESCRIPTION
               "The count of LCP Protocol Rejects received from the 
               peer."
           ::= { xPppLcpStatusEntry 22 }

       xPppLcpStatusTxProRej OBJECT-TYPE
           SYNTAX Counter 
           ACCESS read-only
           STATUS mandatory
           DESCRIPTION
               "The count of LCP Protocol Rejects transmitted to 
               the peer."
           ::= { xPppLcpStatusEntry 23 }

       xPppLcpStatusState2 OBJECT-TYPE
            SYNTAX INTEGER { initial(1), starting(2), closed(3), stopped(4),
                             closing(5), stopping(6), reqSent(7), ackRcvd(8),
                             ackSent(9), opened(10) }
           ACCESS read-only
           STATUS mandatory
           DESCRIPTION
               "The current state of LCP."
           ::= { xPppLcpStatusEntry 24 }

       xPppIpcpConfigTable OBJECT-TYPE
           SYNTAX SEQUENCE OF XPppIpcpConfigEntry
           ACCESS not-accessible
           STATUS mandatory
           DESCRIPTION
               "A table containing PPP IPCPspecific variables for 
               this PPP implementation."
           ::= { xPppIpcp 1 }

       xPppIpcpConfigEntry OBJECT-TYPE
           SYNTAX XPppIpcpConfigEntry
           ACCESS not-accessible
           STATUS mandatory
           DESCRIPTION
               "Management information about a particular PPP IPCP 
               session."
           INDEX { ifIndex }
           ::= { xPppIpcpConfigTable 1 }

       XPppIpcpConfigEntry ::=
           SEQUENCE {
               xPppIpcpConfigLocalAddress
                   IpAddress,
               xPppIpcpConfigRemoteAddress
                   IpAddress,
               xPppIpcpConfigVJCompSlots
                   INTEGER,
               xPppIpcpConfigRangeStart
                   IpAddress,
               xPppIpcpConfigRangeEnd
                   IpAddress,
               xPppIpcpConfigState
                   INTEGER,
               xPppIpcpConfigLocalRangeStart
                   IpAddress,
               xPppIpcpConfigLocalRangeEnd
                   IpAddress,
               xPppIpcpConfigPppIpMask
                   IpAddress


           }

       xPppIpcpConfigLocalAddress OBJECT-TYPE
           SYNTAX IpAddress
           ACCESS read-write
           STATUS mandatory
           DESCRIPTION
               "IP Address of the local PPP interface."
           ::= { xPppIpcpConfigEntry 1 }

       xPppIpcpConfigRemoteAddress OBJECT-TYPE
           SYNTAX IpAddress
           ACCESS read-write
           STATUS mandatory
           DESCRIPTION
               "IP Address of the peer PPP interface."
           ::= { xPppIpcpConfigEntry 2 }

       xPppIpcpConfigVJCompSlots OBJECT-TYPE
           SYNTAX INTEGER (3..15)
           ACCESS read-write
           STATUS mandatory
           DESCRIPTION
               "Number of slots to be used by VJ compression."
           ::= { xPppIpcpConfigEntry 3 }

       xPppIpcpConfigRangeStart OBJECT-TYPE
           SYNTAX IpAddress
           ACCESS read-write
           STATUS mandatory
           DESCRIPTION
               "Start of acceptable address range in which the negotiated 
		remote IP address must fall."
           ::= { xPppIpcpConfigEntry 4 }

       xPppIpcpConfigRangeEnd OBJECT-TYPE
           SYNTAX IpAddress
           ACCESS read-write
           STATUS mandatory
           DESCRIPTION
               "End of acceptable address range in which the negotiated 
		remote IP address must fall."
           ::= { xPppIpcpConfigEntry 5 }
 
       xPppIpcpConfigState OBJECT-TYPE
           SYNTAX INTEGER { disabled(1), enabled(2) }
           ACCESS read-write
           STATUS mandatory
           DESCRIPTION
               "Controls whether IPCP is allowed to run on this port."
           ::= { xPppIpcpConfigEntry 6 }

       xPppIpcpConfigLocalRangeStart OBJECT-TYPE
           SYNTAX IpAddress
           ACCESS read-write
           STATUS mandatory
           DESCRIPTION
               "Start of acceptable address range in which the negotiated 
		local IP address must fall."
           ::= { xPppIpcpConfigEntry 7 }

       xPppIpcpConfigLocalRangeEnd OBJECT-TYPE
           SYNTAX IpAddress
           ACCESS read-write
           STATUS mandatory
           DESCRIPTION
               "End of acceptable address range in which the negotiated 
		local IP address must fall."
           ::= { xPppIpcpConfigEntry 8 }

       xPppIpcpConfigPppIpMask OBJECT-TYPE
           SYNTAX IpAddress
           ACCESS read-write
           STATUS mandatory
           DESCRIPTION
               "The subnet mask to use for a PPP operation on the port. 
                Corresponds directly to the value labeled 'IP Mask:' in the 
                PPP PORT IP CHARACTERISTICS display."
           DEFVAL { 'ffffffff'h }    -- 255.255.255.255
           ::= { xPppIpcpConfigEntry 9 }




       xPppIpcpAsyncConfigTable OBJECT-TYPE
           SYNTAX SEQUENCE OF XPppIpcpAsyncConfigEntry
           ACCESS not-accessible
           STATUS mandatory
           DESCRIPTION
               "A table containing PPP specific variables for this 
               PPP implementation."
           ::= { xPppIpcp 2 }

       xPppIpcpAsyncConfigEntry OBJECT-TYPE
           SYNTAX XPppIpcpAsyncConfigEntry
           ACCESS not-accessible
           STATUS mandatory
           DESCRIPTION
               "Management information about a particular PPP 
               Asynchronous LCP."
           INDEX { ifIndex }
           ::= { xPppIpcpAsyncConfigTable 1 }

       XPppIpcpAsyncConfigEntry ::=
           SEQUENCE {
               xPppIpcpAsyncConfigBrdcast
                   INTEGER
            }

       xPppIpcpAsyncConfigBrdcast OBJECT-TYPE
           SYNTAX INTEGER { disabled(1), enabled(2)}
           ACCESS read-write
           STATUS mandatory
           DESCRIPTION
               "Determines whether to forward an IP Broadcast or 
               not."
           ::= { xPppIpcpAsyncConfigEntry 1 }





       xPppIpcpStatusTable OBJECT-TYPE
           SYNTAX SEQUENCE OF XPppIpcpStatusEntry
           ACCESS not-accessible
           STATUS mandatory
           DESCRIPTION
               "A table containing basic PPP IPCP status info."
           ::= { xPppIpcp 3 }

       xPppIpcpStatusEntry OBJECT-TYPE
           SYNTAX XPppIpcpStatusEntry
           ACCESS not-accessible
           STATUS mandatory
           DESCRIPTION
               "Status information about a particular PPP IPCP 
               session."
           INDEX { ifIndex }
           ::= { xPppIpcpStatusTable 1 }

       XPppIpcpStatusEntry ::=
           SEQUENCE {
               xPppIpcpStatusState
                   INTEGER,
               xPppIpcpStatusLocalAddress
                   IpAddress,
               xPppIpcpStatusRemoteAddress
                   IpAddress,
               xPppIpcpRxConReq
                   Counter,
               xPppIpcpTxConReq
                   Counter,
               xPppIpcpRxConNak 
                   Counter,
               xPppIpcpTxConNak
                   Counter,
               xPppIpcpRxConAck
                   Counter,
               xPppIpcpTxConAck
                   Counter,
               xPppIpcpRxConRej
                   Counter,
               xPppIpcpTxConRej
                   Counter,
               xPppIpcpRxTrmReq
                   Counter,
               xPppIpcpTxTrmReq
                   Counter,
               xPppIpcpRxTrmAck
                   Counter,
               xPppIpcpTxTrmAck
                   Counter,
               xPppIpcpRxPkts
                   Counter,
               xPppIpcpTxPkts
                   Counter,
               xPppIpcpStatusState2
                   INTEGER
           }

       xPppIpcpStatusState OBJECT-TYPE
           SYNTAX INTEGER { closed(1), listen(2), requestSent(3),
                            ackReceived(4), ackSent(5), open(6),
                            closing(7) }
           ACCESS read-only
           STATUS deprecated
           DESCRIPTION
               "The current state of IPCP."
           ::= { xPppIpcpStatusEntry 1 }

       xPppIpcpStatusLocalAddress OBJECT-TYPE
           SYNTAX IpAddress
           ACCESS read-only
           STATUS mandatory
           DESCRIPTION
               "The IP Address currently being used by the local 
               IPCP."
           ::= { xPppIpcpStatusEntry 2 }

       xPppIpcpStatusRemoteAddress OBJECT-TYPE
           SYNTAX IpAddress
           ACCESS read-only
           STATUS mandatory
           DESCRIPTION
               "The IP Address currently being used by the Remote 
               IPCP."
           ::= { xPppIpcpStatusEntry 3 }

       xPppIpcpRxPkts OBJECT-TYPE
           SYNTAX Counter
           ACCESS read-only
           STATUS mandatory
           DESCRIPTION
               "Total number of IP packets received."
           ::= { xPppIpcpStatusEntry 4 }

       xPppIpcpTxPkts OBJECT-TYPE
           SYNTAX Counter
           ACCESS read-only
           STATUS mandatory
           DESCRIPTION
               "Total number of IP packets transmitted."
           ::= { xPppIpcpStatusEntry 5 }

       xPppIpcpRxConReq OBJECT-TYPE
           SYNTAX Counter
           ACCESS read-only
           STATUS mandatory
           DESCRIPTION
               "The count of IPCP Configure Requests received from 
               the peer."
           ::= { xPppIpcpStatusEntry 6 }

       xPppIpcpTxConReq OBJECT-TYPE
           SYNTAX Counter
           ACCESS read-only
           STATUS mandatory
           DESCRIPTION
               "The count of IPCP Configure Requests transmitted to 
               the peer."
           ::= { xPppIpcpStatusEntry 7 }

       xPppIpcpRxConNak OBJECT-TYPE
           SYNTAX Counter
           ACCESS read-only
           STATUS mandatory
           DESCRIPTION
               "The count of IPCP Configure Naks received from the 
               peer."
           ::= { xPppIpcpStatusEntry 8 }

       xPppIpcpTxConNak OBJECT-TYPE
           SYNTAX Counter
           ACCESS read-only
           STATUS mandatory
           DESCRIPTION
               "The count of IPCP Configure Naks transmitted to the 
               peer."
           ::= { xPppIpcpStatusEntry 9 }

       xPppIpcpRxConAck OBJECT-TYPE
           SYNTAX Counter
           ACCESS read-only
           STATUS mandatory
           DESCRIPTION
               "The count of IPCP Configure Acks received from the 
               peer."
           ::= { xPppIpcpStatusEntry 10 }

       xPppIpcpTxConAck OBJECT-TYPE
           SYNTAX Counter
           ACCESS read-only
           STATUS mandatory
           DESCRIPTION
               "The count of IPCP Configure Acks transmitted to the 
               peer."
           ::= { xPppIpcpStatusEntry 11 }

       xPppIpcpRxConRej OBJECT-TYPE
           SYNTAX Counter
           ACCESS read-only
           STATUS mandatory
           DESCRIPTION
               "The count of IPCP Configure Rejects received from 
               the peer."
           ::= { xPppIpcpStatusEntry 12 }

       xPppIpcpTxConRej OBJECT-TYPE
           SYNTAX Counter
           ACCESS read-only
           STATUS mandatory
           DESCRIPTION
               "The count of IPCP Configure Rejects transmitted to 
               the peer."
           ::= { xPppIpcpStatusEntry 13 }

       xPppIpcpRxTrmReq OBJECT-TYPE
           SYNTAX Counter
           ACCESS read-only
           STATUS mandatory
           DESCRIPTION
               "The count of IPCP Terminate Requests received from 
               the peer."
           ::= { xPppIpcpStatusEntry 14 }

       xPppIpcpTxTrmReq OBJECT-TYPE
           SYNTAX Counter
           ACCESS read-only
           STATUS mandatory
           DESCRIPTION
               "The count of IPCP Terminate Requests transmitted to 
               the peer."
           ::= { xPppIpcpStatusEntry 15 }

       xPppIpcpRxTrmAck OBJECT-TYPE
           SYNTAX Counter
           ACCESS read-only
           STATUS mandatory
           DESCRIPTION
               "The count of IPCP Terminate Acks received from the 
               peer."
           ::= { xPppIpcpStatusEntry 16 }

       xPppIpcpTxTrmAck OBJECT-TYPE
           SYNTAX Counter
           ACCESS read-only
           STATUS mandatory
           DESCRIPTION
               "The count of IPCP Terminate Acks transmitted to the 
               peer."
           ::= { xPppIpcpStatusEntry 17 }

       xPppIpcpStatusState2 OBJECT-TYPE
           SYNTAX INTEGER { initial(1), starting(2), closed(3), stopped(4),
                            closing(5), stopping(6), reqSent(7), ackRcvd(8),
                            ackSent(9), opened(10) }
           ACCESS read-only
           STATUS mandatory
           DESCRIPTION
               "The current state of IPCP."
           ::= { xPppIpcpStatusEntry 18 }

       -- The PPP Authentication group is mandatory for systems that
       -- implement PAP or CHAP

       xPppPapPassword OBJECT-TYPE
           SYNTAX OCTET STRING (SIZE (0..16))
           ACCESS read-write
           STATUS mandatory
           DESCRIPTION
               "The password to use for PAP authentication."
           ::= { xPppAuth 1 }


       xPppAuthConfigTable OBJECT-TYPE
           SYNTAX SEQUENCE OF XPppAuthConfigEntry
           ACCESS not-accessible
           STATUS mandatory
           DESCRIPTION
               "A table containing PPP specific variables for this 
               PPP implementation."
           ::= { xPppAuth 2 }

       xPppAuthConfigEntry OBJECT-TYPE
           SYNTAX XPppAuthConfigEntry
           ACCESS not-accessible
           STATUS mandatory
           DESCRIPTION
               "Management information about a particular PPP."
           INDEX { ifIndex }
           ::= { xPppAuthConfigTable 1 }

       XPppAuthConfigEntry ::=
           SEQUENCE {
               xPppAuthChapChallengeTimer
                   INTEGER,
               xPppAuthPapConfigState
                   INTEGER,
               xPppAuthChapConfigState
                   INTEGER
           }

--     xPppAuthTransfer(1),  xPppAuthPapState(2),  xPppAuthChapState(3)
--     reserved for Internetworking products.

       xPppAuthChapChallengeTimer OBJECT-TYPE
           SYNTAX INTEGER (0..120)
           ACCESS read-write
           STATUS mandatory
           DESCRIPTION
               "Length of time in minutes between CHAP reauthentication challenges.
                A value of zero disables the timer."
           DEFVAL { 0 } 
           ::= { xPppAuthConfigEntry 4 }

       xPppAuthPapConfigState OBJECT-TYPE
           SYNTAX INTEGER { disabled(1), enabled(2), kerberos(3), radius(4) }
           ACCESS read-write
           STATUS mandatory
           DESCRIPTION
               "Controls the type of Pap authentication required for this port,
		and whether it is combined with another authentication
		mechanism such as Radius."
           DEFVAL { disabled } 
           ::= { xPppAuthConfigEntry 5 }

       xPppAuthChapConfigState OBJECT-TYPE
           SYNTAX INTEGER { disabled(1), enabled(2), radius(4) }
           ACCESS read-write
           STATUS mandatory
           DESCRIPTION
               "Controls the type of Chap authentication required for this port,
		and whether it is combined with another authentication
		mechanism such as Radius."
           DEFVAL { disabled } 
           ::= { xPppAuthConfigEntry 6 }
			
       xPppAuthStatusTable OBJECT-TYPE
           SYNTAX SEQUENCE OF XPppAuthStatusEntry
           ACCESS not-accessible
           STATUS mandatory
           DESCRIPTION
               "A table containing PPP specific variables for this 
               PPP implementation."
           ::= { xPppAuth 3 }

       xPppAuthStatusEntry OBJECT-TYPE
           SYNTAX XPppAuthStatusEntry
           ACCESS not-accessible
           STATUS mandatory
           DESCRIPTION
               "Management information about a particular PPP."
           INDEX { ifIndex }
           ::= { xPppAuthStatusTable 1 }

       XPppAuthStatusEntry ::=
           SEQUENCE {
               xPppPapStatusState
                   INTEGER,
               xPppChapStatusState
                   INTEGER
           }

       -- xPppAuthStatusState(1), xPppChapInStatus(2) and xPppChapOutStatus(3)
       -- are reserved for Internetworking products.

       xPppPapStatusState OBJECT-TYPE
           SYNTAX INTEGER { initial(1), closed(2), stopped(3), closing(4),
                            reqSent(5), ackRecv(6), ackSent(7), opened(8),
                            kerberosReqSent(9), kerberosStopped(10), 
                            kerberosAckRecv(11), kerberosAckSent(12),
                            papKerberosOpened(13) }
           ACCESS read-only
           STATUS mandatory
           DESCRIPTION
               "The current state of PAP."
           ::= { xPppAuthStatusEntry 4 }

       xPppChapStatusState OBJECT-TYPE
           SYNTAX INTEGER { idle(1), challengeWait(2), challengeSent(3),
                            responseSent(4), challengeSentResponseSent(5),
                            challengeSentAckRecv(6), open(7) }
           ACCESS read-only
           STATUS mandatory
           DESCRIPTION
               "The current state of CHAP."
           ::= { xPppAuthStatusEntry 5 }


       xPppChapPassword OBJECT-TYPE
           SYNTAX OCTET STRING (SIZE (0..16))
           ACCESS read-write
           STATUS mandatory
           DESCRIPTION
               "The password to use for CHAP authentication."
           ::= { xPppAuth 4 }


       -- The PPP IPXCP group for the ipx protocol

       xPppIpxcpConfigTable OBJECT-TYPE
           SYNTAX SEQUENCE OF XPppIpxcpConfigEntry
           ACCESS not-accessible
           STATUS mandatory
           DESCRIPTION
               "A table containing PPP specific variables for this 
               PPP implementation."
           ::= { xPppIpxcp 1 }

       xPppIpxcpConfigEntry OBJECT-TYPE
           SYNTAX XPppIpxcpConfigEntry
           ACCESS not-accessible
           STATUS mandatory
           DESCRIPTION
               "Management information about a particular PPP."
           INDEX { ifIndex }
           ::= { xPppIpxcpConfigTable 1 }

       XPppIpxcpConfigEntry ::=
           SEQUENCE {
               xPppIpxcpCipxCompression
                   INTEGER,
               xPppIpxcpConfigRemoteNode
                   OCTET STRING
           }

       xPppIpxcpCipxCompression OBJECT-TYPE
           SYNTAX INTEGER { disabled(1), enabled(2) }
           ACCESS read-write
           STATUS mandatory
           DESCRIPTION
               "Controls whether CIPX compression will be negotiated on the
               interface."
           DEFVAL { disabled }
           ::= { xPppIpxcpConfigEntry 1 }

       xPppIpxcpConfigRemoteNode OBJECT-TYPE
           SYNTAX OCTET STRING ( SIZE(6) )
           ACCESS read-write
           STATUS mandatory
           DESCRIPTION
               "The IPX Node address which can be offered to the peer if
		it does not know a Node number but requires one."
           ::= { xPppIpxcpConfigEntry 2 }

       xPppIpxcpStatusTable OBJECT-TYPE
           SYNTAX SEQUENCE OF XPppIpxcpStatusEntry
           ACCESS not-accessible
           STATUS mandatory
           DESCRIPTION
               "A table containing PPP specific variables for this 
               PPP implementation."
           ::= { xPppIpxcp 2 }

       xPppIpxcpStatusEntry OBJECT-TYPE
           SYNTAX XPppIpxcpStatusEntry
           ACCESS not-accessible
           STATUS mandatory
           DESCRIPTION
               "Management information about a particular PPP."
           INDEX { ifIndex }
           ::= { xPppIpxcpStatusTable 1 }

       XPppIpxcpStatusEntry ::=
           SEQUENCE {
               xPppIpxcpStatusState
                   INTEGER,
               xPppIpxcpCipxInCompression
                   INTEGER,
               xPppIpxcpCipxOutCompression
                   INTEGER,
               xPppIpxcpCipxInSlots
                   INTEGER,
               xPppIpxcpCipxOutSlots
                   INTEGER,
               xPppIpxcpStatusRemoteNode
                   OCTET STRING
           }

       xPppIpxcpStatusState OBJECT-TYPE
           SYNTAX INTEGER { initial(1), starting(2), closed(3), stopped(4),
                            closing(5), stopping(6), reqSent(7), ackRcvd(8),
                            ackSent(9), opened(10) }
           ACCESS read-only
           STATUS mandatory
           DESCRIPTION
               "The current state of IPXCP."
           ::= { xPppIpxcpStatusEntry 1 }

       xPppIpxcpCipxInCompression OBJECT-TYPE
           SYNTAX INTEGER { open(1), closed(2) }
           ACCESS read-only
           STATUS mandatory
           DESCRIPTION
               "The current state of CIPX compression inbound."
           ::= { xPppIpxcpStatusEntry 2 }

       xPppIpxcpCipxOutCompression OBJECT-TYPE
           SYNTAX INTEGER { open(1), closed(2) }
           ACCESS read-only
           STATUS mandatory
           DESCRIPTION
               "The current state of CIPX compression outbound."
           ::= { xPppIpxcpStatusEntry 3 }

       xPppIpxcpCipxInSlots OBJECT-TYPE
           SYNTAX INTEGER
           ACCESS read-only
           STATUS mandatory
           DESCRIPTION
               "The current number of CIPX compression inbound slots."
           ::= { xPppIpxcpStatusEntry 4 }

       xPppIpxcpCipxOutSlots OBJECT-TYPE
           SYNTAX INTEGER
           ACCESS read-only
           STATUS mandatory
           DESCRIPTION
               "The current number of CIPX compression outbound slots."
           ::= { xPppIpxcpStatusEntry 5 }


       xPppIpxcpStatusRemoteNode OBJECT-TYPE
           SYNTAX OCTET STRING ( SIZE(6) )
           ACCESS read-only
           STATUS mandatory
           DESCRIPTION
               "The IPX Node address currently being used by the Remote 
               IPX peer."
           ::= { xPppIpxcpStatusEntry 6 }

       xPppIpxcpCountersTable OBJECT-TYPE
           SYNTAX SEQUENCE OF XPppIpxcpCountersEntry
           ACCESS not-accessible
           STATUS mandatory
           DESCRIPTION
               "A table containing basic PPP IPXCP status info."
           ::= { xPppIpxcp 3 }

       xPppIpxcpCountersEntry OBJECT-TYPE
           SYNTAX XPppIpxcpCountersEntry
           ACCESS not-accessible
           STATUS mandatory
           DESCRIPTION
               "Counter information about a particular PPP IPXCP 
               session."
           INDEX { ifIndex }
           ::= { xPppIpxcpCountersTable 1 }

       XPppIpxcpCountersEntry ::=
           SEQUENCE {
               xPppIpxcpRxConReq
                   Counter,
               xPppIpxcpTxConReq
                   Counter,
               xPppIpxcpRxConNak 
                   Counter,
               xPppIpxcpTxConNak
                   Counter,
               xPppIpxcpRxConAck
                   Counter,
               xPppIpxcpTxConAck
                   Counter,
               xPppIpxcpRxConRej
                   Counter,
               xPppIpxcpTxConRej
                   Counter,
               xPppIpxcpRxTrmReq
                   Counter,
               xPppIpxcpTxTrmReq
                   Counter,
               xPppIpxcpRxTrmAck
                   Counter,
               xPppIpxcpTxTrmAck
                   Counter
           }

       xPppIpxcpRxConReq OBJECT-TYPE
           SYNTAX Counter
           ACCESS read-only
           STATUS mandatory
           DESCRIPTION
               "The count of IPXCP Configure Requests received from 
               the peer."
           ::= { xPppIpxcpCountersEntry 1 }

       xPppIpxcpTxConReq OBJECT-TYPE
           SYNTAX Counter
           ACCESS read-only
           STATUS mandatory
           DESCRIPTION
               "The count of IPXCP Configure Requests transmitted to 
               the peer."
           ::= { xPppIpxcpCountersEntry 2 }

       xPppIpxcpRxConNak OBJECT-TYPE
           SYNTAX Counter
           ACCESS read-only
           STATUS mandatory
           DESCRIPTION
               "The count of IPXCP Configure Naks received from the 
               peer."
           ::= { xPppIpxcpCountersEntry 3 }

       xPppIpxcpTxConNak OBJECT-TYPE
           SYNTAX Counter
           ACCESS read-only
           STATUS mandatory
           DESCRIPTION
               "The count of IPXCP Configure Naks transmitted to the 
               peer."
           ::= { xPppIpxcpCountersEntry 4 }

       xPppIpxcpRxConAck OBJECT-TYPE
           SYNTAX Counter
           ACCESS read-only
           STATUS mandatory
           DESCRIPTION
               "The count of IPXCP Configure Acks received from the 
               peer."
           ::= { xPppIpxcpCountersEntry 5 }

       xPppIpxcpTxConAck OBJECT-TYPE
           SYNTAX Counter
           ACCESS read-only
           STATUS mandatory
           DESCRIPTION
               "The count of IPXCP Configure Acks transmitted to the 
               peer."
           ::= { xPppIpxcpCountersEntry 6 }

       xPppIpxcpRxConRej OBJECT-TYPE
           SYNTAX Counter
           ACCESS read-only
           STATUS mandatory
           DESCRIPTION
               "The count of IPXCP Configure Rejects received from 
               the peer."
           ::= { xPppIpxcpCountersEntry 7 }

       xPppIpxcpTxConRej OBJECT-TYPE
           SYNTAX Counter
           ACCESS read-only
           STATUS mandatory
           DESCRIPTION
               "The count of IPXCP Configure Rejects transmitted to 
               the peer."
           ::= { xPppIpxcpCountersEntry 8 }

       xPppIpxcpRxTrmReq OBJECT-TYPE
           SYNTAX Counter
           ACCESS read-only
           STATUS mandatory
           DESCRIPTION
               "The count of IPXCP Terminate Requests received from 
               the peer."
           ::= { xPppIpxcpCountersEntry 9 }

       xPppIpxcpTxTrmReq OBJECT-TYPE
           SYNTAX Counter
           ACCESS read-only
           STATUS mandatory
           DESCRIPTION
               "The count of IPXCP Terminate Requests transmitted to 
               the peer."
           ::= { xPppIpxcpCountersEntry 10 }

       xPppIpxcpRxTrmAck OBJECT-TYPE
           SYNTAX Counter
           ACCESS read-only
           STATUS mandatory
           DESCRIPTION
               "The count of IPXCP Terminate Acks received from the 
               peer."
           ::= { xPppIpxcpCountersEntry 11 }

       xPppIpxcpTxTrmAck OBJECT-TYPE
           SYNTAX Counter
           ACCESS read-only
           STATUS mandatory
           DESCRIPTION
               "The count of IPXCP Terminate Acks transmitted to the 
               peer."
           ::= { xPppIpxcpCountersEntry 12 }


END
