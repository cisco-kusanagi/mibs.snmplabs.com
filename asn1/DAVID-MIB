DAVID-MIB DEFINITIONS ::= BEGIN

-- Title:       DAVID Systems MIB version 1.1 in concise format
-- Date:        12 February 1992
-- By:          Kathryn de Graaf <degraaf@davidsys.com>

IMPORTS
        enterprises, OBJECT-TYPE, NetworkAddress, IpAddress,
        Counter, Gauge, TimeTicks, DisplayString
        FROM RFC1155-SMI;

david                   OBJECT IDENTIFIER ::=   { enterprises 66 }

products                OBJECT IDENTIFIER ::=   { david 1 }

davidExpressNet         OBJECT IDENTIFIER ::=   { products 3 }

exNetChassis            OBJECT IDENTIFIER ::=   { davidExpressNet 1 }
exNetEthernet           OBJECT IDENTIFIER ::=   { davidExpressNet 2 }

exNetConcentrator       OBJECT IDENTIFIER ::=   { exNetEthernet 1 }
exNetModule             OBJECT IDENTIFIER ::=   { exNetEthernet 2 }
exNetPort               OBJECT IDENTIFIER ::=   { exNetEthernet 3 }
exNetMgmt               OBJECT IDENTIFIER ::=   { exNetEthernet 4 }


--
-- the DAVID ExpressNet Chassis Group
--

exNetChassisType OBJECT-TYPE
        SYNTAX  INTEGER {
                other(1),               -- none of the following
                m6102(2),               -- 5-Slot Concentrator, Model 6102
                m6103(3),               -- 12-Slot Concentrator, Model 6103
                m6310tel(4),            -- 10BASE-T Hub, Model 6310 (Telco)
                m6310rj(5),             -- 10BASE-T Hub, Model 6310 (RJ45)
                m6318st(6),             -- FOIRL Hub, Model 6318 (ST)
                m6318sma(7),            -- FOIRL Hub, Model 6318 (SMA)
                reserved(8)
                }
        ACCESS  read-only
        STATUS  mandatory
        DESCRIPTION
                "The chassis type (option)."
        ::= { exNetChassis 1 }

exNetChassisBkplType OBJECT-TYPE
        SYNTAX  INTEGER {
                other(1),               -- none of the following
                expressNet(2),          -- DAVID ExpressNet
                reserved(3)             -- reserved for future 
                }
        ACCESS  read-only
        STATUS  mandatory
        DESCRIPTION
                "The chassis backplane type (option)."
        ::= { exNetChassis 2 }

exNetChassisBkplRev OBJECT-TYPE
        SYNTAX  INTEGER
        ACCESS  read-only
        STATUS  mandatory
        DESCRIPTION
                "The chassis backplane revision."
        ::= { exNetChassis 3 }

exNetChassisPsType OBJECT-TYPE
        SYNTAX  INTEGER {
                other(1),               -- none of the following
                standardXfmr(2)         -- currently only one type
                }
        ACCESS  read-only
        STATUS  mandatory
        DESCRIPTION
                "The chassis power supply type.
        
                 This refers to the chassis transformer.  Each module
                 (including the Supervisor Module) has its own switching power
                    supply."
        ::= { exNetChassis 4 }

exNetChassisPsStatus OBJECT-TYPE
        SYNTAX  INTEGER {
                ok(1),                  -- supply ok
                failed(2)               -- power supply failure
                }
        ACCESS  read-only
        STATUS  mandatory
        DESCRIPTION
                "The chassis power supply status.

                 This refers t othe chassis transformer.  Each module
                 (including the Supervisor Module) has its own switching power
                 supply.  The status of the individual modules' power supplies
                 is a module attribute."
        ::= { exNetChassis 5 }

exNetSlotConfigTable OBJECT-TYPE
        SYNTAX  SEQUENCE OF ExNetSlotConfigEntry
        ACCESS  not-accessible
        STATUS  mandatory
        DESCRIPTION
                "The chassis slot configuration table."
        ::= { exNetChassis 7 }

exNetSlotConfigEntry OBJECT-TYPE
        SYNTAX  ExNetSlotConfigEntry
        ACCESS  not-accessible
        STATUS  mandatory
        DESCRIPTION
                "Descriptions of the modules (or boards) in each slot."
        INDEX   { exNetSlotIndex }
        ::= { exNetSlotConfigTable 1 }

ExNetSlotConfigEntry ::= SEQUENCE {
        exNetSlotIndex 
                INTEGER,
        exNetBoardId
                INTEGER,
        exNetBoardType
                INTEGER,
        exNetBoardDescr
                DisplayString,
        exNetBoardNumOfPorts
                INTEGER
}

exNetSlotIndex OBJECT-TYPE
        SYNTAX  INTEGER
        ACCESS  read-only
        STATUS  mandatory
        DESCRIPTION
                "The DAVID ExpressNet chassis slot number.  Valid entries are
                 1 to exNetChassisCapacity.

                 On the physical Concentrator boxes, the Supervisor Modules
                 are not numbered and the plug-in modules are numbered from
                 1 to n-1, where n is the number of slots in the Concentrator.
                 For the purposes of the DAVID ExpressNet SNMP MIB, the
                 Supervisor Module is numbered one past the highest-numbered
                 plug-in module.  For example, in a 12-Slot Concentrator, the
                 plug-in modules are numbered 1-11 and the Supervisor Module
                 is numbered 12."
        ::= { exNetSlotConfigEntry 1 }

exNetBoardId OBJECT-TYPE
        SYNTAX  INTEGER
        ACCESS  read-only
        STATUS  mandatory
        DESCRIPTION
                "The unique hardware ID for the module."
        ::= { exNetSlotConfigEntry 2 }

exNetBoardType OBJECT-TYPE
        SYNTAX  INTEGER {
                empty(1),       -- nothing installed
                other(2),       -- none of the following
                m6203(3),       -- Supervisor Module, Model 6203
                m6201(4),       -- Twisted-Pair Module, Model 6201
                m6311(5),       -- 10BASE-T Module, Model 6311 (Telco)
                m6312(6),       -- 10BASE-T Module, Model 6312 (RJ-45)
                m6313st(7),     -- FOIRL Module, Model 6313 (ST)
                m6313sma(8),    -- FOIRL Module, Model 6313 (SMA)
                m6006(9),       -- Hub SNMP Mgmt Module, Model 6006
                reserved(10)
                }
        ACCESS  read-only
        STATUS  mandatory
        DESCRIPTION
                "The type of the module."
        ::= { exNetSlotConfigEntry 3 }

exNetBoardDescr OBJECT-TYPE
        SYNTAX  DisplayString (SIZE(0..128))
        ACCESS  read-only
        STATUS  mandatory
        DESCRIPTION
                "Textual description of the module type."
        ::= { exNetSlotConfigEntry 4 }

exNetBoardNumOfPorts OBJECT-TYPE
        SYNTAX  INTEGER
        ACCESS  read-only
        STATUS  mandatory
        DESCRIPTION
                "The number of ports supported by the plug-in module.
                 For a 10BASE-T Module the value is 12; for an
                 FOIRL Module, 6; for a Supervisor Module, 1."
        ::= { exNetSlotConfigEntry 40 }

exNetChassisCapacity OBJECT-TYPE
        SYNTAX  INTEGER
        ACCESS  read-only
        STATUS  mandatory
        DESCRIPTION
                "The number of slots in the chassis for plug-in modules.
                 This number will be either five or twelve for a
                 Concentrator and two for a Hub."
        ::= { exNetChassis 8 }

--
-- the DAVID ExpressNet Concentrator Group
--

exNetConcRetimingStatus OBJECT-TYPE
        SYNTAX  INTEGER {
                off(1),         -- retiming off
                on(2)           -- retiming on
                }
        ACCESS  read-only
        STATUS  mandatory
        DESCRIPTION
                "Indicates whether this repeater has retiming turned on.

                 All DAVID ExpressNet repeaters implement retiming, so
                 the value on(2) is always returned for this variable."
        ::= { exNetConcentrator 1 }

exNetConcFrmsRxOk OBJECT-TYPE
        SYNTAX  Counter
        ACCESS  read-only
        STATUS  mandatory
        DESCRIPTION
                "A count of frames that are successfully received by the
                 Concentrator.  This counter does not include frames received
                 with frame-too-long, runt, FCS, or alignment errors.

                 This counter includes broadcast and multicast frames that are
                 received."
        ::= { exNetConcentrator 2 }

exNetConcOctetsRxOk OBJECT-TYPE
        SYNTAX  Counter
        ACCESS  read-only
        STATUS  mandatory
        DESCRIPTION
                "A count of data and padding octets in frames that are 
                 successfully received by the concentrator. This counter 
                 does not include frames received with frame-too-long, 
                 runt, FCS, or alignment errors.

                 This counter includes octets in broadcast and multicast
                 frames that are received."
        ::= { exNetConcentrator 3 }

exNetConcMcastFrmsRxOk OBJECT-TYPE
        SYNTAX  Counter
        ACCESS  read-only
        STATUS  mandatory
        DESCRIPTION
                "A count of frames that are successfully received by the 
                 concentrator and are directed to an active non-broadcast
                 group address. This counter does not include frames received
                 with frame-too-long, runt, FCS, or alignment errors.

                 Only frames that are for a multicast address that this 
                 interface is receiving are counted. Broadcast packets are not 
                 included."
        ::= { exNetConcentrator 4 }

exNetConcBcastFrmsRxOk OBJECT-TYPE
        SYNTAX  Counter
        ACCESS  read-only
        STATUS  mandatory
        DESCRIPTION
                "A count of frames that are successfully received by the 
                 concentrator and are directed to the broadcast group address. 
                 This counter does not include frames received with frame-too-
                 long, runt, FCS, or alignment errors.

                 Multicast packets are not included."
        ::= { exNetConcentrator 5 }

exNetConcColls OBJECT-TYPE
        SYNTAX  Counter
        ACCESS  read-only
        STATUS  mandatory
        DESCRIPTION
                "Total collisions involving an incoming packet on any port
                 (link or Network Interface port) in the Concentrator.  This
                 counter increments once for each collision involving an
                 incoming packet on any port, no matter how many ports are
                 involved."
        ::= { exNetConcentrator 6 }

--
-- MAC Receive Error Statistics
--
-- A hierarchical order has been established for the objects listed 
-- below, such that when more than one error status can be associated 
-- with one frame, only one status is counted. This hierarchy, in 
-- descending order, is as follows:
-- 
--    1. frame too long
--    2. runt frames
--    3. fragments
--    4. alignment error
--    5. frame check error
--

exNetConcTooLongErrors OBJECT-TYPE
        SYNTAX  Counter
        ACCESS  read-only
        STATUS  mandatory
        DESCRIPTION
                "A count of frames that are received by the Concentrator and
                 exceed the maximum permitted frame size."
        ::= { exNetConcentrator 7 }

exNetConcRuntErrors OBJECT-TYPE
        SYNTAX  Counter
        ACCESS  read-only
        STATUS  mandatory
        DESCRIPTION
                "Number of frames received by the Concentrator that have a 
                 correct preamble (including double 1), but are shorter than
                 the minimum legal frame size of 64 bytes (512 bits).  Runts
                 are commonly collision fragments, and as such do not
                 necessarily indicate a problem in the network.

                 Runts are also known as 'short frames.'"
        ::= { exNetConcentrator 8 }

exNetConcFragErrors OBJECT-TYPE
        SYNTAX  Counter
        ACCESS  read-only
        STATUS  mandatory
        DESCRIPTION
                "Fragments of packets, shorter than the minimum legal
                 transmission size of 96 bits, that are received on the
                 Concentrator.  Fragments indicate an external noise hit
                 (a problem on the network).

                 Fragments are also known as 'pygmies.'"
        ::= { exNetConcentrator 9 }

exNetConcAlignErrors OBJECT-TYPE
        SYNTAX  Counter
        ACCESS  read-only
        STATUS  mandatory
        DESCRIPTION
                "Number of frames received on the Concentrator that are
                 byte-misaligned, such that the number of bits is not
                 a multiple of 8.

                 (These frames do not pass the frame check sequence check, 
                 but are not counted as FCS errors.)"
        ::= { exNetConcentrator 10 }

exNetConcFcsErrors OBJECT-TYPE
        SYNTAX  Counter
        ACCESS  read-only
        STATUS  mandatory
        DESCRIPTION
                "A count of frames received by the Concentrator that are an
                 integral number of octets in length and do not pass the frame
                 check sequence (FCS) check.

                 FCS errors are sometimes called CRC errors."
        ::= { exNetConcentrator 11 }

exNetConcLateCollErrors OBJECT-TYPE
        SYNTAX  Counter
        ACCESS  read-only
        STATUS  mandatory
        DESCRIPTION
                "A total Concentrator count of the late collisions.  The 
                 late collision counter for a port is incremented whenever
                 a collision is detected on the port later than 512 bit times
                 into the transmitted packet.  
        
                 Late collisions are not included in the collision count."
        ::= { exNetConcentrator 12 }

exNetConcName OBJECT-TYPE
        SYNTAX  DisplayString (SIZE(0..20))
        ACCESS  read-write
        STATUS  mandatory
        DESCRIPTION
                "A descriptive string that can be used by a network
                 administrator to name the Concentrator."
        ::= { exNetConcentrator 40 }

exNetConcJabbers OBJECT-TYPE
        SYNTAX  Counter
        ACCESS  read-only
        STATUS  mandatory
        DESCRIPTION
                "A count of the number of times that the jabber function had 
                 to be invoked because a frame received from one of this
                 Concentrator's ports exceeded 5 msec in duration."
        ::= { exNetConcentrator 41 }

exNetConcSfdErrors OBJECT-TYPE
        SYNTAX  Counter
        ACCESS  read-only
        STATUS  mandatory
        DESCRIPTION
                "Amount of activity from this Concentrator's ports where a
                 double-zero is seen before the start-frame delimiter
                 (double-1).  (This could indicate a polarity problem.)"
        ::= { exNetConcentrator 42 }

exNetConcAutoPartitions OBJECT-TYPE
        SYNTAX  Counter
        ACCESS  read-only
        STATUS  mandatory
        DESCRIPTION
                "Indicates how often ports on this Concentrator have been
                 automatically partitioned by the Concentrator repeater
                 function."
        ::= { exNetConcentrator 43 }

exNetConcOosBitRate OBJECT-TYPE
        SYNTAX  Counter
        ACCESS  read-only
        STATUS  mandatory
        DESCRIPTION
                "Number of times that frames have been received on the 
                 Concentrator with the transmission frequency (data rate)
                 badly out of spec.  This counter is incremented when the
                 frequency of a received frame is so far out of spec that
                 the packet has been corrupted within the relay.

                 The spec allows deviations of +/- 100 parts per million (ppm).
                 The DAVID ExpressNet Intelligent Concentrators can handle 
                 greater deviations than this, depending on frame length."
        ::= { exNetConcentrator 44 }

exNetConcLinkErrors OBJECT-TYPE
        SYNTAX  Counter
        ACCESS  read-only
        STATUS  mandatory
        DESCRIPTION
                "This composite counter includes jabbers, auto-partitions, and
                 start-frame delimiter errors."
        ::= { exNetConcentrator 45 }

exNetConcFrameErrors OBJECT-TYPE
        SYNTAX  Counter
        ACCESS  read-only
        STATUS  mandatory
        DESCRIPTION
                "This composite counter includes frame check sequence errors,
                 fragments, short frames, long frames, and alignment errors."
        ::= { exNetConcentrator 46 }

exNetConcNetUtilization OBJECT-TYPE
        SYNTAX  OCTET STRING (SIZE (1..10))
        ACCESS  read-only
        STATUS  mandatory
        DESCRIPTION
                "A series of ten bytes, each indicating the percentage of
                 bandwidth utilization for a 100-millisecond interval.
                 Together they give the bandwidth utilization for the previous
                 second."
        ::= { exNetConcentrator 47 }

exNetConcResetTimeStamp OBJECT-TYPE
        SYNTAX  Gauge
        ACCESS  read-only
        STATUS  mandatory
        DESCRIPTION
                "The value of sysUpTime at the point that the Concentrator
                 repeater state machine was last reset."
        ::= { exNetConcentrator 48 }

exNetConcReset OBJECT-TYPE
        SYNTAX  INTEGER {
                noReset(1),             -- not resetting
                reset(2),               -- resetting, maintaining config
                resetToDefault(3)       -- resetting to factory config
                }
        ACCESS  read-write
        STATUS  mandatory
        DESCRIPTION
                "The reset state of the Concentrator's repeater state machine.
                 Writing a 2 will reset the Concentrator's control logic, 
                 without changing the current configuration.  Writing a 3 
                 will reset the Concentrator to the initial factory default
                 configuration."
        ::= { exNetConcentrator 49 }


--
-- the DAVID ExpressNet Module Group
--

exNetModuleTable OBJECT-TYPE
        SYNTAX  SEQUENCE OF ExNetModuleEntry
        ACCESS  not-accessible
        STATUS  mandatory
        DESCRIPTION
                "A list of module entries.  The number of entries is given by 
                 the number of modules that are obtained by the Concentrator 
                 Slot Configuration Table."
        ::= { exNetModule 1 }

exNetModuleEntry OBJECT-TYPE
        SYNTAX  ExNetModuleEntry
        ACCESS  not-accessible
        STATUS  mandatory
        DESCRIPTION
                "A module entry containing objects at the module level for a
                 particular module."
        INDEX   { exNetModuleIndex }
        ::= { exNetModuleTable 1 }

ExNetModuleEntry ::= SEQUENCE {
        exNetModuleIndex
                INTEGER,
        exNetModuleType
                INTEGER,
        exNetModuleHwVer
                INTEGER,
        exNetModuleStatus
                INTEGER,
        exNetModuleReset
                INTEGER,
        exNetModulePartStatus
                INTEGER,
        exNetModuleNmCntlStatus
                INTEGER,
        exNetModulePsStatus
                INTEGER,
        exNetModuleFrmsRxOk
                Counter,
        exNetModuleOctetsRxOk
                Counter,
        exNetModuleColls
                Counter,
        exNetModuleTooLongErrors
                Counter,
        exNetModuleRuntErrors
                Counter,
        exNetModuleAlignErrors
                Counter,
        exNetModuleFcsErrors
                Counter,
        exNetModuleLateCollErrors
                Counter,
        exNetModuleName
                DisplayString,
        exNetModuleJabbers
                Counter,
        exNetModuleSfdErrors
                Counter,
        exNetModuleAutoPartitions
                Counter,
        exNetModuleOosBitRate
                Counter,
        exNetModuleLinkErrors
                Counter,
        exNetModuleFrameErrors
                Counter,
        exNetModuleFragErrors
                Counter,
        exNetModulePortConfig
                INTEGER,
        exNetModuleLinkStatConfig
                INTEGER,
        exNetModuleResetTimeStamp
                INTEGER,
        exNetModuleLinkStatus
                INTEGER,
        exNetModuleFwVer
                INTEGER,
        exNetModuleFwFeaturePkg
                INTEGER,
        exNetModuleSelfTestResult
                INTEGER
}

exNetModuleIndex OBJECT-TYPE
        SYNTAX  INTEGER
        ACCESS  read-only
        STATUS  mandatory
        DESCRIPTION
                "A unique value for each module.  Its value ranges between 1
                 and exNetChassisCapacity.  The value for each module must
                 remain constant at least from one reinitialization of the
                 entity's network management system to the next
                 reinitialization.

                 This value is tied to the hardware chassis slot number."
        ::= { exNetModuleEntry 1 }

exNetModuleType OBJECT-TYPE
        SYNTAX  INTEGER {
                empty(1),       -- nothing installed
                other(2),       -- none of the following
                m6203(3),       -- Supervisor Module, Model 6203
                m6201(4),       -- Twisted-Pair Module, Model 6201
                m6311(5),       -- 10BASE-T Module, Model 6311 (Telco)
                m6312(6),       -- 10BASE-T Module, Model 6312 (RJ-45)
                m6313st(7),     -- FOIRL Module, Model 6313 (ST)
                m6313sma(8),    -- FOIRL Module, Model 6313 (SMA)
                m6006(9),       -- Hub SNMP Mgmt Module, Model 6006
                reserved(10)
                }
        ACCESS  read-only
        STATUS  mandatory
        DESCRIPTION
                "The type of the module."
        ::= { exNetModuleEntry 2 }

exNetModuleHwVer OBJECT-TYPE
        SYNTAX  INTEGER
        ACCESS  read-only
        STATUS  mandatory
        DESCRIPTION
                "The hardware configuration of the module or hub.

                For model 6311, 6312, and 6313 board types, the
                type of Network Interface provided with the board is
                indicated by the following values (0-3 apply to ExpressNet
                Hubs; 7 is returned for Concentrator modules):
                    0 = AUI
                    1 = 10BASE2
                    2 = 10BASE-T
                    3 = FOIRL
                    7 = no interface"
        ::= { exNetModuleEntry 3 }

exNetModuleStatus OBJECT-TYPE
        SYNTAX  INTEGER {
                ok(1),          -- good status
                noComms(2),     -- lost communications with module
                selfTestFail(3) -- module self-test failed
                }
        ACCESS  read-only
        STATUS  mandatory
        DESCRIPTION
                "The operational status of the module.  If the status is 
                 selfTestFail(3), the exNetModuleSelfTestResult will give
                 more detailed information about the module's condition."
        ::= { exNetModuleEntry 4 }

exNetModuleReset OBJECT-TYPE
        SYNTAX  INTEGER {
                noReset(1),             -- not resetting
                reset(2),               -- resetting, maintaining config
                resetToDefault(3)       -- resetting to factory config
                }
        ACCESS  read-write
        STATUS  mandatory
        DESCRIPTION
                "The reset state of the module.  Writing a 2 will reset the 
                 module's control logic, without changing the current 
                 configuration.  Writing a 3 will reset the module to the
                 initial factory default configuration."
        ::= { exNetModuleEntry 5 }

exNetModulePartStatus OBJECT-TYPE
        SYNTAX  INTEGER {
                enabled(1),     -- module enabled
                partition(2)    -- module partitioned
                }
        ACCESS  read-write
        STATUS  mandatory
        DESCRIPTION
                "Tells whether the module is partitioned or enabled.  Writing
                 a 2 will partition the module and 1 will enable the module."
        ::= { exNetModuleEntry 6 }

exNetModuleNmCntlStatus OBJECT-TYPE
        SYNTAX  INTEGER {
                notNmControl(1),        -- module not under mgmt control
                nmControl(2)            -- module under net mgmt control
                }
        ACCESS  read-only
        STATUS  mandatory
        DESCRIPTION
                "Tells whether the module is under network management control.

                 DAVID ExpressNet Concentrators always return nmControl(2),
                 since all modules are always under network management
                 control."
        ::= { exNetModuleEntry 7 }

exNetModulePsStatus OBJECT-TYPE
        SYNTAX  INTEGER {
                ok(1),          -- good status
                fail(2)         -- bad status
                }
        ACCESS  read-only
        STATUS  mandatory
        DESCRIPTION
                "The status of the module's power supply."
        ::= { exNetModuleEntry 8 }

exNetModuleFrmsRxOk OBJECT-TYPE
        SYNTAX  Counter
        ACCESS  read-only
        STATUS  mandatory
        DESCRIPTION
                "A count of frames that are successfully received by the
                 module.  This counter does not include frames received with
                 frame-too-long, runt, FCS, or alignment errors.

                 This counter includes broadcast and multicast frames that are 
                 received."
        ::= { exNetModuleEntry 9 }

exNetModuleOctetsRxOk OBJECT-TYPE
        SYNTAX  Counter
        ACCESS  read-only
        STATUS  mandatory
        DESCRIPTION
                "A count of data and padding octets in frames that are 
                 successfully received by the module. This counter does not 
                 include frames received with frame-too-long, runt, FCS, or 
                 alignment errors.

                 This counter includes octets in broadcast and multicast
                 frames that are received."
        ::= { exNetModuleEntry 10 }

exNetModuleColls OBJECT-TYPE
        SYNTAX  Counter
        ACCESS  read-only
        STATUS  mandatory
        DESCRIPTION
                "Total collisions involving an incoming packet on any link or
                 the backplane connector in the module.  This counter
                 increments once for each collision involving an incoming
                 packet on any port, no matter how many ports are involved."
        ::= { exNetModuleEntry 13 }

exNetModuleTooLongErrors OBJECT-TYPE
        SYNTAX  Counter
        ACCESS  read-only
        STATUS  mandatory
        DESCRIPTION
                "A count of frames that are received by the module and 
                 exceed the maximum permitted frame size."
        ::= { exNetModuleEntry 14 }

exNetModuleRuntErrors OBJECT-TYPE
        SYNTAX  Counter
        ACCESS  read-only
        STATUS  mandatory
        DESCRIPTION
                "Number of frames received by the module that have a correct
                 preamble (including double 1), but are shorter than the
                 minimum legal frame size of 64 bytes (512 bits).  Runts are
                 commonly collision fragments, and as such do not necessarily
                 indicate a problem in the network.

                 Runts are also called 'short frames.'"
        ::= { exNetModuleEntry 15 }

exNetModuleAlignErrors OBJECT-TYPE
        SYNTAX  Counter
        ACCESS  read-only
        STATUS  mandatory
        DESCRIPTION
                "Number of frames received by the module that are
                 byte-misaligned, such that the number of bits is not
                 a multiple of 8.

                 (These frames do not pass the frame check sequence check, 
                 but are not counted as FCS errors.)"
        ::= { exNetModuleEntry 16 }

exNetModuleFcsErrors OBJECT-TYPE
        SYNTAX  Counter
        ACCESS  read-only
        STATUS  mandatory
        DESCRIPTION
                "A count of frames received by the module that are an integral
                 number of octets in length and do not pass the frame check
                 sequence (FCS) check.

                 FCS errors are sometimes called CRC errors."
        ::= { exNetModuleEntry 17 }

exNetModuleLateCollErrors OBJECT-TYPE
        SYNTAX  Counter
        ACCESS  read-only
        STATUS  mandatory
        DESCRIPTION
                "A module count of the late collisions on all of the module's
                 ports.  The late collision counter for a port is incremented
                 whenever a collision is detected on the port later than 512 
                 bit times into the transmitted packet.  
        
                 Late collisions are not included in the collision count."
        ::= { exNetModuleEntry 18 }

exNetModuleName OBJECT-TYPE
        SYNTAX  DisplayString (SIZE(0..20))
        ACCESS  read-write
        STATUS  mandatory
        DESCRIPTION
                "A descriptive string that can be used by a network
                 administrator to name the module."
        ::= { exNetModuleEntry 40 }

exNetModuleJabbers OBJECT-TYPE
        SYNTAX  Counter
        ACCESS  read-only
        STATUS  mandatory
        DESCRIPTION
                "A count of the number of times that the jabber function had 
                 to be invoked because a frame received from one of this
                 module's ports exceeded 5 msec in duration."
        ::= { exNetModuleEntry 41 }

exNetModuleSfdErrors OBJECT-TYPE
        SYNTAX  Counter
        ACCESS  read-only
        STATUS  mandatory
        DESCRIPTION
                "Amount of activity from this module's ports where a 
                 double-zero is seen before the start-frame delimiter
                 (double-1).  (This could indicate a polarity problem.)"
        ::= { exNetModuleEntry 42 }

exNetModuleAutoPartitions OBJECT-TYPE
        SYNTAX  Counter
        ACCESS  read-only
        STATUS  mandatory
        DESCRIPTION
                "Indicates how often ports on this module have been
                 automatically partitioned by the module repeater
                 function."
        ::= { exNetModuleEntry 43 }

exNetModuleOosBitRate OBJECT-TYPE
        SYNTAX  Counter
        ACCESS  read-only
        STATUS  mandatory
        DESCRIPTION
                "Number of times that frames have been received from ports on
                 this module with the transmission frequency (data rate) badly
                 out of spec.  This counter is incremented when the frequency
                 of a received frame is so far out of spec that the packet has
                 been corrupted within the relay.

                 The spec allows deviations of +/- 100 parts per million (ppm).
                 The DAVID ExpressNet Concentrators can handle greater
                 deviations than this, depending on frame length."
        ::= { exNetModuleEntry 44 }

exNetModuleLinkErrors OBJECT-TYPE
        SYNTAX  Counter
        ACCESS  read-only
        STATUS  mandatory
        DESCRIPTION
                "This composite counter includes jabbers, auto-partitions, and
                 start-frame delimiter errors."
        ::= { exNetModuleEntry 45 }

exNetModuleFrameErrors OBJECT-TYPE
        SYNTAX  Counter
        ACCESS  read-only
        STATUS  mandatory
        DESCRIPTION
                "This composite counter includes frame check sequence errors,
                 fragments, short frames, long frames, and alignment errors."
        ::= { exNetModuleEntry 46 }

exNetModuleFragErrors OBJECT-TYPE
        SYNTAX  Counter
        ACCESS  read-only
        STATUS  mandatory
        DESCRIPTION
                "Fragments of packets, shorter than the minimum legal
                 transmission size of 96 bits, that are received on the
                 module.  Fragments indicate an external noise hit (a
                 problem on the network).

                 Fragments are also known as 'pygmies.'"
        ::= { exNetModuleEntry 47 }

exNetModulePortConfig OBJECT-TYPE
        SYNTAX  INTEGER
        ACCESS  read-write
        STATUS  mandatory
        DESCRIPTION
                "Compresses the configuration of all of this module's ports
                 into a two-byte integer value.

                 Sums f(x) as x goes from 1 to number of ports, where f(x) = 0
                 for disabled port and f(x) = exp(2,x-1) for enabled port."
        ::= { exNetModuleEntry 48 }

exNetModuleLinkStatConfig OBJECT-TYPE
        SYNTAX  INTEGER
        ACCESS  read-write
        STATUS  mandatory
        DESCRIPTION
                "Compresses the link status configuration of all of this
                 module's ports into a two-byte integer value.
                 Sums f(x) as x goes from 1 to number of ports, where 
                 f(x) = 0 for port with link status disabled and 
                 f(x) = exp(2,x-1) for port with link status enabled."
        ::= { exNetModuleEntry 49 }

exNetModuleResetTimeStamp OBJECT-TYPE
        SYNTAX  Gauge
        ACCESS  read-only
        STATUS  mandatory
        DESCRIPTION
                "The value of sysUpTime at the point that the module
                 repeater state machine was last reset."
        ::= { exNetModuleEntry 50 }

exNetModuleLinkStatus OBJECT-TYPE
        SYNTAX  INTEGER
        ACCESS  read-only
        STATUS  mandatory
        DESCRIPTION
                "Compresses the link status of all of this module's ports
                 into a two-byte integer value.  Sums f(x) as x goes from
                 1 to number of ports, where f(x) = 0 for port with link 
                 status test passed (link active) and f(x) = exp(2,x-1) for
                 port with link status test failed (link inactive).
        
                 For ports with link status test disabled, zero is returned. 

                 For example, if link status is active on all ports, the
                 value returned is zero.  If link status for ports 3 and 7
                 is inactive and the rest of the ports have active link 
                 status, the value returned is (2^(3-1) + 2^(7-1)) =
                 (4 + 64) = 68."
        ::= { exNetModuleEntry 51 }

exNetModuleFwVer OBJECT-TYPE
        SYNTAX  INTEGER
        ACCESS  read-only
        STATUS  mandatory
        DESCRIPTION
                "The firmware revision of the GAP processor on the module."
        ::= { exNetModuleEntry 52 }

exNetModuleFwFeaturePkg OBJECT-TYPE
        SYNTAX  INTEGER
        ACCESS  read-only
        STATUS  mandatory
        DESCRIPTION
                "The feature package associated with the GAP processor
                 on the module."
        ::= { exNetModuleEntry 53 }

exNetModuleSelfTestResult OBJECT-TYPE
        SYNTAX  INTEGER
        ACCESS  read-only
        STATUS  mandatory
        DESCRIPTION
                "The self-test result value returned by the GAP processor 
                 on the module.  Zero indicates that the module passed all
                 tests.  Bits set in the result indicate error conditions,
                 as follows:

                 Bit number      Error encountered
                 0               ROM failure
                 1               CPU failure
                 2               RAM failure
                 3               repeater module failure
                 4               reserved
                 5               internal power (-5v) failure
                 6               NI power fuse (+12v) failure"
        ::= { exNetModuleEntry 54 }


--
-- the DAVID ExpressNet Port Group
--
--
-- The Network Interface (NI) port on a Supervisor Module is numbered port 1.
-- On a 12-Slot Concentrator, the NI port would be slot 12 port 1, and
-- exNetPortFCSErrors.12.1 would identify the FCS error counts for the
-- NI port.  On a Hub, the NI port would be slot 2 port 1, and
-- exNetPortFCSErrors.2.1 would identify the FCS error counts for the NI port.
--

exNetPortTable OBJECT-TYPE
        SYNTAX  SEQUENCE OF ExNetPortEntry
        ACCESS  not-accessible
        STATUS  mandatory
        DESCRIPTION
                "A list of port entries. The number of entries is given by 
                 knowing the number of occupied slots in the 
                 exNetSlotConfigTable and the number of ports that are
                 on an exNetModuleType."
        ::= { exNetPort 1 }

exNetPortEntry OBJECT-TYPE
        SYNTAX  ExNetPortEntry
        ACCESS  not-accessible
        STATUS  mandatory
        DESCRIPTION
                "A port entry containing objects at the port level for a 
                 particular port."
        INDEX   { exNetPortModuleIndex,
                  exNetPortIndex }
        ::= { exNetPortTable 1 }

ExNetPortEntry ::= SEQUENCE {
        exNetPortModuleIndex
                INTEGER,
        exNetPortIndex
                INTEGER,
        exNetPortLinkStatus
                INTEGER,
        exNetPortPartStatus
                INTEGER,
        exNetPortJabberStatus
                INTEGER,
        exNetPortFrmsRxOk
                Counter,
        exNetPortOctetsRxOk
                Counter,
        exNetPortColls
                Counter,
        exNetPortTooLongErrors
                Counter,
        exNetPortRuntErrors
                Counter,
        exNetPortAlignErrors
                Counter,
        exNetPortFcsErrors
                Counter,
        exNetPortLateCollErrors
                Counter,
        exNetPortName
                DisplayString,
        exNetPortJabbers
                Counter,
        exNetPortSfdErrors
                Counter,
        exNetPortAutoPartitions
                Counter,
        exNetPortOosBitRate
                Counter,
        exNetPortLinkErrors
                Counter,
        exNetPortFrameErrors
                Counter,
        exNetPortFragErrors
                Counter,
        exNetPortType
                INTEGER,
        exNetPortMauType
                INTEGER,
        exNetPortConfig
                INTEGER,
        exNetPortLinkStatConfig
                INTEGER,
        exNetPortPolarity
                INTEGER,
        exNetPortTransmitTest
                INTEGER
}

exNetPortModuleIndex OBJECT-TYPE
        SYNTAX  INTEGER
        ACCESS  read-only
        STATUS  mandatory
        DESCRIPTION
                "A unique value for each module. Its value ranges between 1 
                 and exNetChassisCapacity."
        ::= { exNetPortEntry 1 }

exNetPortIndex OBJECT-TYPE
        SYNTAX  INTEGER
        ACCESS  read-only
        STATUS  mandatory
        DESCRIPTION
                "A unique value for each port. Its value ranges between 1 
                 and the value of exNetBoardNumOfPorts for this module."
        ::= { exNetPortEntry 2 }

exNetPortLinkStatus OBJECT-TYPE
        SYNTAX  INTEGER {
                off(1),         -- link is not connected
                on(2),          -- link is connected
                other(3)        -- returned for AUI
                }
        ACCESS  read-only
        STATUS  mandatory
        DESCRIPTION
                "For 10BASE-T ports:  this is the link integrity test defined
                 by the 10BASE-T standard.  If link status test is enabled,
                 this flag indicates whether the link is active or inactive.
                 There are several reasons for an inactive link:
                    .    PC or workstation connected to the MAU has
                         been turned off
                    .    disrupted link (e.g., wiring problem)
                    .    TP-MAU on the end of the link is missing, dead, 
                         or powered off
                    .    transmit and receive polarities are swapped

                 For FOIRL ports:  the link status is constantly tested; thus,
                 this variable is always meaningful.  A value of off(1)
                 indicates a low-light condition (poor signal quality).  The
                 value on(2) indicates that signal quality on the link is ok.

                 For AUI ports:  the value other(3) is always returned since
                 link status test does not apply."
        ::= { exNetPortEntry 3 }

exNetPortPartStatus OBJECT-TYPE
        SYNTAX  INTEGER {
                enabled(1),             -- port enabled
                partition(2),           -- port partitioned
                autoPartition(3)        -- port auto-partitioned
                }
        ACCESS  read-write
        STATUS  mandatory
        DESCRIPTION
                "Indicates whether the port is currently partitioned by the
                 Concentrator's auto-partition protection.  (The Concentrator
                 automatically partitions a port if it is signalling 
                 continuous collision, or 32 consecutive collisions.)

                 Writing a 1 will forcibly unpartition the port.  Writing a 2
                 or a 3 is illegal.  To enable or disable the port, use the 
                 exNetPortConfig variable."
        ::= { exNetPortEntry 4 }

exNetPortJabberStatus OBJECT-TYPE
        SYNTAX  INTEGER {
                ok(1),
                jabbering(2)    -- Port receiving jabber
                }
        ACCESS  read-only
        STATUS  mandatory
        DESCRIPTION
                "Tells whether the DTE connected to the port is jabbering
                 (receiving a frame longer than 5 msec in duration)."
        ::= { exNetPortEntry 5 }

exNetPortFrmsRxOk OBJECT-TYPE
        SYNTAX  Counter
        ACCESS  read-only
        STATUS  mandatory
        DESCRIPTION
                "A count of frames that are successfully received by the port. 
                 This counter does not include frames received with frame-too-
                 long, runt, FCS, or alignment errors.

                 This counter includes broadcast and multicast frames that are 
                 received."
        ::= { exNetPortEntry 6 }

exNetPortOctetsRxOk OBJECT-TYPE
        SYNTAX  Counter
        ACCESS  read-only
        STATUS  mandatory
        DESCRIPTION
                "A count of data and padding octets in frames that are 
                 successfully received by the port. This counter does not 
                 include frames received with frame-too-long, runt, FCS, or 
                 alignment errors.

                 This counter includes octets in broadcast and multicast
                 frames that are received."
        ::= { exNetPortEntry 7 }

exNetPortColls OBJECT-TYPE
        SYNTAX  Counter
        ACCESS  read-only
        STATUS  mandatory
        DESCRIPTION
                "Number of times this port was involved in a collision with
                 another port in the same Hub."
        ::= { exNetPortEntry 10 }

exNetPortTooLongErrors OBJECT-TYPE
        SYNTAX  Counter
        ACCESS  read-only
        STATUS  mandatory
        DESCRIPTION
                "A count of frames that are received by the port and exceed 
                 the maximum permitted frame size."
        ::= { exNetPortEntry 11 }

exNetPortRuntErrors OBJECT-TYPE
        SYNTAX  Counter
        ACCESS  read-only
        STATUS  mandatory
        DESCRIPTION
                "Number of frames received by the port that have a correct
                 preamble (including double 1), but are shorter than the
                 minimum legal frame size of 64 bytes (512 bits).  Runts are
                 commonly collision fragments, and as such do not necessarily
                 indicate a problem in the network.

                 Runts are also called 'short frames.'"
        ::= { exNetPortEntry 12 }

exNetPortAlignErrors OBJECT-TYPE
        SYNTAX  Counter
        ACCESS  read-only
        STATUS  mandatory
        DESCRIPTION
                "Number of frames received by the port that are
                 byte-misaligned, such that the number of bits is not
                 a multiple of 8.

                 (These frames do not pass the frame check sequence check, 
                 but are not counted as FCS errors.)"
        ::= { exNetPortEntry 13 }

exNetPortFcsErrors OBJECT-TYPE
        SYNTAX  Counter
        ACCESS  read-only
        STATUS  mandatory
        DESCRIPTION
                "A count of frames received by the port that are an integral
                 number of octets in length and do not pass the frame check
                 sequence (FCS) check.  This counter is incremented when the
                 frameCheckError status is detected.

                 FCS errors are sometimes called CRC errors."
        ::= { exNetPortEntry 14 }

exNetPortLateCollErrors OBJECT-TYPE
        SYNTAX  Counter
        ACCESS  read-only
        STATUS  mandatory
        DESCRIPTION
                "Number of times that a collision has been detected on this
                 port later than 512 bit times into the transmitted packet.

                 Late collisions are not included in the collision count."
        ::= { exNetPortEntry 15 }

exNetPortName OBJECT-TYPE
        SYNTAX  DisplayString (SIZE(0..20))
        ACCESS  read-write
        STATUS  mandatory
        DESCRIPTION
                "A descriptive string that can be used by a network
                 administrator to name the port."
        ::= { exNetPortEntry 40 }

exNetPortJabbers OBJECT-TYPE
        SYNTAX  Counter
        ACCESS  read-only
        STATUS  mandatory
        DESCRIPTION
                "A count of the number of times that the jabber function
                 had to be invoked because a frame received from this port
                 exceeded 5 msec in duration."
        ::= { exNetPortEntry 41 }

exNetPortSfdErrors OBJECT-TYPE
        SYNTAX  Counter
        ACCESS  read-only
        STATUS  mandatory
        DESCRIPTION
                "Amount of activity from this port where a double-zero
                 is seen before the start-frame delimiter (double-1).
                 (This could indicate a polarity problem.)"
        ::= { exNetPortEntry 42 }

exNetPortAutoPartitions OBJECT-TYPE
        SYNTAX  Counter
        ACCESS  read-only
        STATUS  mandatory
        DESCRIPTION
                "Indicates how often this port has been automatically
                 partitioned by the module repeater function."
        ::= { exNetPortEntry 43 }

exNetPortOosBitRate OBJECT-TYPE
        SYNTAX  Counter
        ACCESS  read-only
        STATUS  mandatory
        DESCRIPTION
                "Number of times that frames have been received from this link
                 with the transmission frequency (data rate) badly out of spec.
                 This counter is incremented when the frequency of a received
                 frame is so far out of spec that the packet has been corrupted
                 within the relay.

                 The spec allows deviations of +/- 100 parts per million (ppm).
                 The DAVID ExpressNet Concentrators can handle greater
                 deviations than this, depending on frame length."
        ::= { exNetPortEntry 44 }

exNetPortLinkErrors OBJECT-TYPE
        SYNTAX  Counter
        ACCESS  read-only
        STATUS  mandatory
        DESCRIPTION
                "This composite counter includes jabbers, auto-partitions,
                 late collisions, start-frame delimiter errors, and
                 out-of-spec bit rate errors."
        ::= { exNetPortEntry 45 }

exNetPortFrameErrors OBJECT-TYPE
        SYNTAX  Counter
        ACCESS  read-only
        STATUS  mandatory
        DESCRIPTION
                "This composite counter includes frame check sequence errors,
                 fragments, short frames, long frames, and alignment errors."
        ::= { exNetPortEntry 46 }

exNetPortFragErrors OBJECT-TYPE
        SYNTAX  Counter
        ACCESS  read-only
        STATUS  mandatory
        DESCRIPTION
                "Fragments of packets, shorter than the minimum legal
                 transmission size of 96 bits, that are received on this
                 port.  Fragments indicate an external noise hit (a problem
                 on the network)."
        ::= { exNetPortEntry 47 }

exNetPortType OBJECT-TYPE
        SYNTAX  INTEGER {
                other(1),         -- none of the following
                repeater(2),      -- any 802.3 section 9 rptr port
                tenBasefAsync(3), -- FOIRL-compat. port on 10BASE-FA star
                tenBasefSync(4)   -- synchronous port on 10BASE-FA star
                }
        ACCESS  read-only
        STATUS  mandatory
        DESCRIPTION
                "The type of the port."
        ::= { exNetPortEntry 48 }

exNetPortMauType OBJECT-TYPE
        SYNTAX  INTEGER {
                other(1),         -- none of the following
                tenBase5(2),      -- thick-wire (AUI)
                tenBaseT(3),      -- 10BASE-T
                fOIRL(4),         -- FOIRL
                tenBase2(5),      -- thin-wire (BNC)
                tenBaseFA(6)      -- 10BASE-F Active
                }
        ACCESS  read-only
        STATUS  mandatory
        DESCRIPTION
                "The type of the MAU attached to the port."
        ::= { exNetPortEntry 49 }

exNetPortConfig OBJECT-TYPE
        SYNTAX  INTEGER {
                other(1),         -- none of the following
                enabled(2),       -- port enabled
                disabled(3),      -- port disabled
                txDisabled(4),    -- transmit disabled (receive enabled)
                rxDisabled(5)     -- receive disabled (transmit enabled)
                }
        ACCESS  read-write
        STATUS  mandatory
        DESCRIPTION
                "The administrative state of the port.

                 If both transmit and receive are enabled, the port state
                 is enabled.  If both transmit and receive are disabled,
                 the port state is disabled."
        ::= { exNetPortEntry 50 }

exNetPortLinkStatConfig OBJECT-TYPE
        SYNTAX  INTEGER {
                other(1),         -- none of the following
                enabled(2),       -- link status enabled
                disabled(3),      -- link status disabled
                txDisabled(4),    -- transmit disabled (receive enabled)
                rxDisabled(5)     -- receive disabled (transmit enabled)
                }
        ACCESS  read-write
        STATUS  mandatory
        DESCRIPTION
                "The administrative status of the link status test for this 
                 link.

                 If both transmit and receive are enabled, the link status
                 test is enabled.  If both transmit and receive are disabled,
                 the link status test is disabled.

                 This variable applies only to ports with MauType = 10BASE-T.
                 The value other(1) is returned for other MAU types."
        ::= { exNetPortEntry 51 }

exNetPortPolarity OBJECT-TYPE
        SYNTAX  INTEGER {
                other(1),         -- none of the following
                positive(2),      -- positive polarity
                negative(3),      -- negative polarity
                txNegative(4),    -- transmit negative, receive positive
                rxNegative(5)     -- receive negative, transmit positive
                }
        ACCESS  read-write
        STATUS  mandatory
        DESCRIPTION
                "The polarity of the port.  Applies only to ports with MAU type
                 10BASE-T.  The value other(1) is returned for other MAU
                 types."
        ::= { exNetPortEntry 52 }

exNetPortTransmitTest OBJECT-TYPE
        SYNTAX  INTEGER {
                other(1),         -- none of the following
                disabled(2),      -- transmit test disabled
                enabled(3)        -- transmit test enabled
                }
        ACCESS  read-write
        STATUS  mandatory
        DESCRIPTION
                "Whether or not transmit test is enabled on the link.
                 Transmit test applies only to links of type 10BASE-T.
                 The value other(1) is returned for other MAU types.

                 THIS TEST CAN BE DISRUPTIVE TO THE NETWORK."
        ::= { exNetPortEntry 53 }

--
-- the DAVID ExpressNet Management Group
--

exNetMgmtType OBJECT-TYPE
        SYNTAX  INTEGER {
                other(1),       -- none of the following
                tbd(2)
                }
        ACCESS  read-only
        STATUS  mandatory
        DESCRIPTION
                "The DAVID ExpressNet Ethernet network management type."
        ::= { exNetMgmt 1 }

exNetMgmtHwVer OBJECT-TYPE
        SYNTAX  INTEGER
        ACCESS  read-only
        STATUS  mandatory
        DESCRIPTION
                "The network management ICM hardware version number: 
                 1=Rev. A, 2=Rev. B, etc."
        ::= { exNetMgmt 2 }

exNetMgmtFwVer OBJECT-TYPE
        SYNTAX  INTEGER
        ACCESS  read-only
        STATUS  mandatory
        DESCRIPTION
                "The network management ICP firmware version."
        ::= { exNetMgmt 3 }

exNetMgmtSwMajorVer OBJECT-TYPE
        SYNTAX  INTEGER
        ACCESS  read-only
        STATUS  mandatory
        DESCRIPTION
                "The network management major software version number, 
                 where the version number is of the form major.minor, 
                 e.g. 3.0.
        
                 Refers to the ECP (External Communications Processor)."
        ::= { exNetMgmt 4 }

exNetMgmtSwMinorVer OBJECT-TYPE
        SYNTAX  INTEGER
        ACCESS  read-only
        STATUS  mandatory
        DESCRIPTION
                "The network management minor software version number, 
                 where the version number is of the form major.minor, 
                 e.g. 3.0.

                 Refers to the ECP."
        ::= { exNetMgmt 5 }

exNetMgmtStatus OBJECT-TYPE
        SYNTAX  INTEGER {
                offline(1),     -- management is off-line
                online(2)       -- management is on-line
                }
        ACCESS  read-only
        STATUS  mandatory
        DESCRIPTION
                "Indicates that the network management is on line and
                 operating.

                 For the DAVID ExpressNet Concentrators, management status is
                 always online(2)."
        ::= { exNetMgmt 6 }

exNetMgmtMode OBJECT-TYPE
        SYNTAX  INTEGER {
                primary(1),     -- in primary mode
                secondary(2)    -- in secondary mode
                }
        ACCESS  read-write
        STATUS  mandatory
        DESCRIPTION
                "Indicates whether the network management is operating in
                 primary or secondary mode.

                 Presently, all DAVID ExpressNet Concentrators return
                 primary(1)."
        ::= { exNetMgmt 7 }

exNetMgmtReset OBJECT-TYPE
        SYNTAX  INTEGER {
                notReset(1),    -- not resetting
                reset(2)        -- reset
                }
        ACCESS  read-write
        STATUS  mandatory
        DESCRIPTION
                "Network management reset status.  Writing a 2 to this object
                 will reset the network management (stop refreshing the
                 watchdog timer) and restart."
        ::= { exNetMgmt 8 }

exNetMgmtRestart OBJECT-TYPE
        SYNTAX  INTEGER {
                notRestart(1),  -- not restarting
                restart(2)      -- restart
                }
        ACCESS  read-write
        STATUS  mandatory
        DESCRIPTION
                "Network management restart status.  Writing a 2 to this object
                 will restart the network management.  This initializes all
                 the counters, rereads the EEPROM data structure, and starts 
                 executing from the beginning of the code."
        ::= { exNetMgmt 9 }

exNetMgmtIpAddr OBJECT-TYPE
        SYNTAX  IpAddress
        ACCESS  read-write
        STATUS  mandatory
        DESCRIPTION
                "The network management's administrative IP address.  This
                 parameter will take effect ONLY after a restart
                 (exNetMgmtRestart) or reset (exNetMgmtReset) is issued.
                 At that time it becomes the operational IP address.

                 The value of the CURRENT operational IP address can be
                 obtained from the ipAdEntAddr entry in the ipAddrTable."
        ::= { exNetMgmt 10 }

exNetMgmtNetMask OBJECT-TYPE
        SYNTAX  IpAddress
        ACCESS  read-write
        STATUS  mandatory
        DESCRIPTION
                "The network management's administrative subnet mask.  This
                 parameter will take effect ONLY after a restart
                 (exNetMgmtRestart) or reset (exNetMgmtReset) is issued.
                 At that time it becomes the operational subnet mask.

                 The value of the CURRENT operational subnet mask can be
                 obtained from the ipAdEntNetMask entry in the ipAddrTable."
         ::= { exNetMgmt 11 }

exNetMgmtDefaultGateway OBJECT-TYPE
        SYNTAX  IpAddress
        ACCESS  read-write
        STATUS  mandatory
        DESCRIPTION
                "The network management's administrative default gateway 
                 IP address.  This parameter will take effect ONLY after a
                 restart (exNetMgmtRestart) or reset (exNetMgmtReset) is
                 issued.  At that time it becomes the operational default
                 gateway IP address.

                 The value of the CURRENT operational default gateway's IP 
                 address can be obtained from the ipRoutingTable."
        ::= { exNetMgmt 12 }

exNetMgmtBaudRate OBJECT-TYPE
        SYNTAX  Gauge
        ACCESS  read-only
        STATUS  mandatory
        DESCRIPTION
                "Returns the baud rate in bits per second of the RS-232 port.

                 Note:  The Concentrators autobaud to match the device attached
                 to the RS-232 port."
        ::= { exNetMgmt 17 }

exNetMgmtLocation OBJECT-TYPE
        SYNTAX  DisplayString
        ACCESS  read-write
        STATUS  mandatory
        DESCRIPTION
                "This is an informational string that could be used to show
                 the physical location (i.e., area) of the network management
                 or Concentrator.

                 This parameter is saved in non-volatile memory and will
                 survive a reset.

                 Note:  This variable is aliased to the sysLocation variable
                 in the MIB-II system group.  Changing one will change the
                 other.  It is suggested that the system group variable be used
                 whenever possible."
        ::= { exNetMgmt 19 }

exNetMgmtTrapReceiverTable OBJECT-TYPE
        SYNTAX  SEQUENCE OF ExNetMgmtTrapReceiverEntry
        ACCESS  not-accessible
        STATUS  mandatory
        DESCRIPTION
                "This entity's Trap Receiver Table (10 entries)."
        ::= { exNetMgmt 20 }

exNetMgmtTrapReceiverEntry OBJECT-TYPE
        SYNTAX  ExNetMgmtTrapReceiverEntry
        ACCESS  not-accessible
        STATUS  mandatory
        DESCRIPTION
                "A destination address and community string to a particular 
                 trap receiver."
        INDEX   { exNetMgmtTrapReceiverAddr }
        ::= { exNetMgmtTrapReceiverTable 1 }

ExNetMgmtTrapReceiverEntry ::= SEQUENCE {
        exNetMgmtTrapType
                INTEGER,
        exNetMgmtTrapReceiverAddr
                IpAddress,
        exNetMgmtTrapReceiverComm
                OCTET STRING
        }

exNetMgmtTrapType OBJECT-TYPE
        SYNTAX  INTEGER {
                other (1),      -- none of the following
                invalid (2)     -- an invalidated address
                }
        ACCESS  read-write
        STATUS  mandatory
        DESCRIPTION
                "Setting this object to the value invalid(2) invalidates the 
                 corresponding entry in the exNetTrapReceiverTable. 
                 That is, it effectively disassociates the address identified 
                 with the entry by removing the entry from the table."
        DEFVAL  { 1 }   -- defaults to other(1), which means valid address
        ::= { exNetMgmtTrapReceiverEntry 1 }

exNetMgmtTrapReceiverAddr OBJECT-TYPE
        SYNTAX  IpAddress
        ACCESS  read-write
        STATUS  mandatory
        DESCRIPTION
                "IP address for trap receiver."
        -- no default value for this column!
        ::= { exNetMgmtTrapReceiverEntry 2 }

exNetMgmtTrapReceiverComm OBJECT-TYPE
        SYNTAX  OCTET STRING (SIZE(20))
        ACCESS  read-write
        STATUS  mandatory
        DESCRIPTION
                "Community string used for traps."
        DEFVAL { "" }  -- if not specified, this column defaults to null string
        ::= { exNetMgmtTrapReceiverEntry 3 }

exNetMgmtAuthTrap OBJECT-TYPE
        SYNTAX  INTEGER {
                disable(1),     -- disable authentication traps
                enable(2)       -- enable authentication traps
                }
        ACCESS  read-write
        STATUS  mandatory
        DESCRIPTION
                "Enable or disable the use of authentication error trap 
                 generation."
        ::= { exNetMgmt 21 }

END
