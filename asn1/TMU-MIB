TMU-MIB DEFINITIONS ::= BEGIN
--
--tmu-mib-h(){}
--
--                Mib for the TMU snmp agent
--                ==========================
--
--$Revision: /main/TORNADO/1 $
--
--
--$Log: fibr-FR9230,v $
--Revision /main/TORNADO/1  1995/09/06  20:55 UTC  conrad
--	Merging /main/T10/1
--
--Revision /main/T10/1  1995/08/29  17:46 UTC  lrb
--	Add 3Com, Fibronics, Melco, TrippLite Mibs
--
--
--   Rev 1.25   22 Oct 1993 10:22:02   "A.SEGAL"
--1. Taken the following elements out of the MIB:
--   fibTmuFunctStpRiOpenRun
--   fibTmuFunctStpRoOpenRun
--   fibTmuFunctStpRiOpenPerm
--   fibTmuFunctStpRoOpenPerm
--
--   Rev 1.24   22 Oct 1993  9:44:28   "A.SEGAL"
--1. Replace elements
--   fibTmuFunctFiberRiOpenRun,
--   fibTmuFunctFiberRiOpenPerm,
--   by
--   fibTmuFunctForceStpRiRun,
--   fibTmuFunctForceStpRiPerm
--2. Replace elements
--   fibTmuFunctFiberRoOpenRun,
--   fibTmuFunctFiberRoOpenPerm
--   by
--   fibTmuFunctForceStpRoRun,
--   fibTmuFunctForceStpRoPerm
--
--   Rev 1.23   17 Sep 1993 10:50:08   "A.SEGAL"
--1. Add elements to the
--   Tmu Function Group - permanent variables
--   and to the
--   Tmu Function Group - run time variables
--
--   Rev 1.22   05 Sep 1993 12:22:28   "A.SEGAL"
--1. Correct a few underscores in
--   and 'fibTmuDontResetFatal'
--
    IMPORTS
      mgmt, NetworkAddress, IpAddress, Counter, Gauge,
      TimeTicks, internet
        FROM RFC1155-SMI
		  MacAddress, DisplayString FROM SNMPv2-TC
      OBJECT-TYPE
        FROM RFC-1212 ;

-- *********************************************
--    PRIVATE  TMU  MIB
-- *********************************************
    --IMPORTS  OBJECT-TYPE, internet FROM RFC1155-SMI;

--    MacAddress ::= OCTET STRING (SIZE (6))

  mgmt        OBJECT IDENTIFIER ::= { iso org(3) dod(6) internet(1) mgmt(2) }
    private     OBJECT IDENTIFIER ::= { internet 4 }
    enterprises OBJECT IDENTIFIER ::= { private  1 }

      fibronics   OBJECT IDENTIFIER ::= { enterprises 22 }
        tmu            OBJECT IDENTIFIER ::= { fibronics 60 }
          tmuSystem     OBJECT IDENTIFIER ::= { tmu 1 }
          tmuIntrfc     OBJECT IDENTIFIER ::= { tmu 2 }
          tmuMatch      OBJECT IDENTIFIER ::= { tmu 3 }
          tmuStations   OBJECT IDENTIFIER ::= { tmu 4 }
          tmuPorts      OBJECT IDENTIFIER ::= { tmu 5 }
          tmuProduction OBJECT IDENTIFIER ::= { tmu 6 }
          tmuSecurity   OBJECT IDENTIFIER ::= { tmu 7 }
-- =============================================
--
--Tmu Function Group
--
--  A list of all parameters related to cau
--  functionality features built into the Tmu.
--
-- =============================================
          tmuFunction   OBJECT IDENTIFIER ::= { tmu 8 }
-- =============================================
--
-- Runtime variables of cau functionality
--   Entry of information concerning runtime
--   parameters of 'functionality' module.
-- =============================================
            fibTmuFunctRtpGrpVrsRun OBJECT IDENTIFIER ::= { tmuFunction 1 }
-- =============================================
--
-- Non volatile ram variables of cau functionality
--   Entry of information concerning permanent
--   memory parameters of 'functionality' module.
--   Factory use only! Setting without thorough
--   understanding of each parameter may cause
--   unexpected system behaviour.
-- =============================================
            fibTmuFunctRtpGrpVrsPerm OBJECT IDENTIFIER ::= { tmuFunction 2 }

-- =============================================
--
--Tmu System Group
--
--A list of information items, such as counters,
--and control items which have to do with the
--complete system rather than with each
--interface.
--
-- =============================================

fibTmuNumEventErrs  OBJECT-TYPE
    SYNTAX    Counter
    ACCESS    read-only
    STATUS    mandatory
    DESCRIPTION
              "Cyclic counter.  Indicates how many times
              the event-handler procedure has been called with
              the 'ERR' severity level or higher."
    ::= { tmuSystem 1 }

fibTmuArpAgeTime  OBJECT-TYPE
    SYNTAX    TimeTicks
    ACCESS    read-only
    STATUS    mandatory
    DESCRIPTION
              "The value of the system timer [in SYS-TICKs]
              at the last time ARP aging was carried out."
    ::= { tmuSystem 2 }

fibTmuNumRarpUpdate OBJECT-TYPE
    SYNTAX    Counter
    ACCESS    read-only
    STATUS    mandatory
    DESCRIPTION
              "Cyclic counter. Indicates how many times
              the system's IP address was updated because of
              a RARP message."
    ::= { tmuSystem 3 }

fibTmuMainSwVersion  OBJECT-TYPE
    SYNTAX    INTEGER
    ACCESS    read-only
    STATUS    mandatory
    DESCRIPTION
              "United version for all software packages
              in this system."
    ::= { tmuSystem 4 }

fibTmuEepromVersion  OBJECT-TYPE
    SYNTAX    INTEGER
    ACCESS    read-only
    STATUS    mandatory
    DESCRIPTION
              "Version of the eeprom package"
    ::= { tmuSystem 5 }


fibTmuEepromDeffective  OBJECT-TYPE
    SYNTAX    INTEGER
    ACCESS    read-only
    STATUS    mandatory
    DESCRIPTION
              "System information. Set when eeprom is found to
              be physically deffective and can not be read
              nor written to."
    ::= { tmuSystem 6 }

fibTmuLastSysIfIndex  OBJECT-TYPE
    SYNTAX    INTEGER
    ACCESS    read-only
    STATUS    mandatory
    DESCRIPTION
              "Number of inteface via which the last
              ip message was received. Currently
              interfaces 1->3 are token ring interfaces
              and interface 4 is the serial/slip interface."
    ::= { tmuSystem 7 }

fibTmuTrDrvVersion  OBJECT-TYPE
    SYNTAX    INTEGER
    ACCESS    read-only
    STATUS    mandatory
    DESCRIPTION
              "The software version of the token ring
              driver as received from the driver at
              initialization."
    ::= { tmuSystem 8 }

fibTmuSccDrvVersion  OBJECT-TYPE
    SYNTAX    INTEGER
    ACCESS    read-only
    STATUS    mandatory
    DESCRIPTION
              "The software version of the serial line
              driver as received from the driver at
              initialization."
    ::= { tmuSystem 9 }

fibTmuSnmpUsrVersion  OBJECT-TYPE
    SYNTAX    INTEGER
    ACCESS    read-only
    STATUS    mandatory
    DESCRIPTION
              "The software version of the sw package
              employing udp/ip/snmp and the preliminary
              reduction of messages from any of the interfaces.
              Loaded at initialization."
    ::= { tmuSystem 10 }


fibTmuDisplayDebugMode  OBJECT-TYPE
    SYNTAX    INTEGER {
                  regular-mode(1),
                  special-debug-mode(2)
              }
    ACCESS    read-write
    STATUS    mandatory
    DESCRIPTION
              "Flag indicating whether system is in
              a special debug mode. In that mode, extra
              code is executed to output indications
              on system state."
    ::= { tmuSystem 11 }

fibTmuEeFaultsFormat  OBJECT-TYPE
    SYNTAX    INTEGER {
                  full-mode(1),
                  concise-mode(2)
              }
    ACCESS    read-write
    STATUS    mandatory
    DESCRIPTION
              "Flag indicating whether faults stored
              in eeprom will each take a small eeprom
              space or a large eeprom space. If the
              'small' option is chosen, only so many
              first bytes of the fault text are stored
              but the number of stored faults is larger.
              This value is stored in eeprom and becomes
              effective only after the next reset."
    ::= { tmuSystem 12 }

fibTmuRunFaultsFormat  OBJECT-TYPE
    SYNTAX    INTEGER {
                  full-mode(1),
                  concise-mode(2)
              }
    ACCESS    read-only
    STATUS    mandatory
    DESCRIPTION
              "This is the run time value of flag
               described in eeFaultsFormat above."
    ::= { tmuSystem 13 }

fibTmuFunctionalityVersion  OBJECT-TYPE
    SYNTAX    INTEGER
    ACCESS    read-only
    STATUS    mandatory
    DESCRIPTION
              "The software version of the sw package
              which realizes the recovery process when
              the token ring fails (e.g. beaconing).
              Loaded at initialization."
    ::= { tmuSystem 14 }

fibTmuUtilitiesVersion  OBJECT-TYPE
    SYNTAX    INTEGER
    ACCESS    read-only
    STATUS    mandatory
    DESCRIPTION
              "The software version of the sw package
              containing operating system and hw
              utilities. Loaded at initialization."
    ::= { tmuSystem 15 }

fibTmuWrapIn  OBJECT-TYPE
    SYNTAX    INTEGER {
                  no-wrap(1),
                  wrap-set-by-manager(2),
                  wrap-set-by-Tmu(3),
                  wrap-set-by-both(4)
              }

    ACCESS    read-write
    STATUS    mandatory
    DESCRIPTION
              "Get: Read the state of the specified relay
               (wrap on 'ring in' port on trunk). Wrap
               may be set either by the manager or by
               the Tmu due to some errors on the trunk.
               Set: Only two values are allowed.
               'no-wrap' indicates 'open the relay and attach
               the trunk'
               'wrap-set-by-manager' indicates 'detach
               the trunk' "
    ::= { tmuSystem 16 }

fibTmuWrapOut  OBJECT-TYPE
    SYNTAX    INTEGER {
                  no-wrap(1),
                  wrap-set-by-manager(2),
                  wrap-set-by-Tmu(3),
                  wrap-set-by-both(4)
              }

    ACCESS    read-write
    STATUS    mandatory
    DESCRIPTION
              "Get: Read the state of the specified relay
               (wrap on 'ring Out' port on trunk). Wrap
               may be set either by the manager or by
               the Tmu due to some errors on the trunk.
               Set: Only two values are allowed.
               'no-wrap' indicates 'open the relay and attach
               the trunk'
               'wrap-set-by-manager' indicates 'detach
               the trunk' "
    ::= { tmuSystem 17 }

fibTmuLoadEeDefaults  OBJECT-TYPE
    SYNTAX    INTEGER {
                  dont-load-default(1),
                  load-defaults(2)
              }

    ACCESS    read-write
    STATUS    mandatory
    DESCRIPTION
              "When this object is set, the Tmu system is
               instructed to load non volatile memory by
               default values at the next reset.
               Get: Read the value the system will use on
               the next reset.
               Set: If 'load-defults' is written then at
               the next system reset, non volatile ram will
               be loaded by default values and the object
               will automatically be loaded by
               'dont-load-defaults'. Note that, among other
               things, Tmu will lose, in this case, its IP
               address."
    ::= { tmuSystem 18 }

fibTmuDontResetFatal  OBJECT-TYPE
    SYNTAX    INTEGER {
                  reset-fatal(1),
                  dont-reset-fatal(2)
              }

    ACCESS    read-write
    STATUS    mandatory
    DESCRIPTION
              "When this object is set, the Tmu system is
               instructed to reset the system when a fatal
               error has been detected. For debug purposes.
               In regular cases, this variable is set to
               'reset-fatal'."
    ::= { tmuSystem 19 }

fibTmuRIConnection  OBJECT-TYPE
	SYNTAX    INTEGER{
				none(0),
				copper(1),
				fiber(2)
			  }
	ACCESS  read-only
	STATUS  mandatory
	DESCRIPTION
		"GET: Read what kind of trank is connected to Ring In port.
	     At board type 9232/nn has no value."
	::= {tmuSystem 20}

fibTmuROConnection  OBJECT-TYPE
	SYNTAX    INTEGER{
				none(0),
				copper(1),
				fiber(2)
			  }
	ACCESS  read-only
	STATUS  mandatory
	DESCRIPTION
		"GET: Read what kind of trank is connected to Ring Out port.
	     At board type 9232/nn has no value."
	::= {tmuSystem 21}

fibTmuRealTimeClock  OBJECT-TYPE
	SYNTAX  DisplayString (SIZE (23))
	ACCESS  read-write
	STATUS  mandatory
	DESCRIPTION
		"Get: Read real time with format hh:mm:ss DDD dd/MMM/yy.
		 Set: Recive Display string of format hh:mm:ss DDD
		 dd/MMM/yy."
	::= { tmuSystem 22 }


-- =============================================
--
--Tmu Interface Group
--
--A list of information items, such as counters,
--and control items which have to do with each
--each interface installed on the system.
--
-- =============================================

fibTmuIntrfcTable OBJECT-TYPE
    SYNTAX    SEQUENCE OF FibTmuIntrfcEntry
    ACCESS    not-accessible
    STATUS    mandatory
    DESCRIPTION
              "Table containing information and control
              items concerning a specific IP handling
              interface."
    ::= { tmuIntrfc 1 }

fibTmuIntrfcEntry OBJECT-TYPE
    SYNTAX    FibTmuIntrfcEntry
    ACCESS    not-accessible
    STATUS    mandatory
    DESCRIPTION
              "Entry of information and control
              items concerning a specific IP handling
              interface."
    INDEX     { fibTmuIntrfcIndex }
    ::= { fibTmuIntrfcTable 1 }


FibTmuIntrfcEntry
    ::= SEQUENCE {
              fibTmuIntrfcIndex
                    INTEGER,
              fibTmuNumRarpRcvd
                    Counter,
              fibTmuNumRxRjctMem
                    Counter,
              fibTmuNumRxAccepted
                    Counter,
              fibTmuNumRxBdcst
                    Counter,
              fibTmuNumRxSpecific
                    Counter,
              fibTmuNumRifIncluded
                    Counter,
              fibTmuNumNoRif
                    Counter,
              fibTmuNumNonSnap
                    Counter,
              fibTmuNumUnknownType
                    Counter,
              fibTmuNumRifLong
                    Counter,
              fibTmuNumRrpRjctIp
                    Counter,
              fibTmuNumArpRcvd
                    Counter,
              fibTmuNumIpRcvd
                    Counter,
              fibTmuNumIfDown
                    Counter,
              fibTmuNumOwnBrdcst
                    Counter,
              fibTmuAc00Cntr
                    Counter,
              fibTmuAc01Cntr
                    Counter,
              fibTmuAc10Cntr
                    Counter,
              fibTmuAc11Cntr
                    Counter,
              fibTmuParityEc
                    Counter,
              fibTmuFrameEc
                    Counter,
              fibTmuRxNoiseEc
                    Counter,
              fibTmuBreakEc
                    Counter,
              fibTmuNumConfigNotValid
                    Counter,
              fibTmuNumAddrNotFound
                    Counter,
              fibTmuNumProcessDisabled
                    Counter,

              fibTmuNumBeaconsRcvd
                    Counter,
              fibTmuLastBeaconTime
                    TimeTicks,
              fibTmuLastBeaconType
                    INTEGER,
              fibTmuLastBeaconAddr
                    MacAddress,
              fibTmuLastBeaconNaun
                    MacAddress,
              fibTmuNumRxGroup
                    Counter,
              fibTmuNumRxFunctional
                    Counter
        }

fibTmuIntrfcIndex  OBJECT-TYPE
    SYNTAX    INTEGER
    ACCESS    read-only
    STATUS    mandatory
    DESCRIPTION
              "The value of this object identifies
              the IP interface for which this entry
              contains management information. The
              value of this object for a particular
              interface has the same value as the
              ifIndex object defined for the same
              interface."
    ::= { fibTmuIntrfcEntry 1 }

fibTmuNumRarpRcvd  OBJECT-TYPE
    SYNTAX    Counter
    ACCESS    read-only
    STATUS    mandatory
    DESCRIPTION
              "Cyclic counter. Contains the number of rarp
              response messages received via this interface.
              Meaningful for Token Ring interfaces only."
    ::= { fibTmuIntrfcEntry 2 }

fibTmuNumRxRjctMem  OBJECT-TYPE
    SYNTAX    Counter
    ACCESS    read-only
    STATUS    mandatory
    DESCRIPTION
              "Cyclic counter. Contains the number of
              non-mac messages which were received by the
              tr chip but rejected by the higher sw levels
              because there was no memory."
    ::= { fibTmuIntrfcEntry 3 }

fibTmuNumRxAccepted  OBJECT-TYPE
    SYNTAX    Counter
    ACCESS    read-only
    STATUS    mandatory
    DESCRIPTION
              "Cyclic counter. Contains the number of
              non-mac frames received by higher level sw."
    ::= { fibTmuIntrfcEntry 4 }

fibTmuNumRxBdcst  OBJECT-TYPE
    SYNTAX    Counter
    ACCESS    read-only
    STATUS    mandatory
    DESCRIPTION
              "Cyclic counter. Contains the number of
              non-mac broadcast frames received by higher
              level SW.
              Meaningful for Token Ring interfaces only."
    ::= { fibTmuIntrfcEntry 5 }

fibTmuNumRxSpecific  OBJECT-TYPE
    SYNTAX    Counter
    ACCESS    read-only
    STATUS    mandatory
    DESCRIPTION
              "Cyclic counter. Contains the number of
              non-mac specific [non-broadcast, non-functional,
              non-group] frames received by higher level SW.
              Meaningful for Token Ring interfaces only."
    ::= { fibTmuIntrfcEntry 6 }

fibTmuNumRifIncluded  OBJECT-TYPE
    SYNTAX    Counter
    ACCESS    read-only
    STATUS    mandatory
    DESCRIPTION
              "Cyclic counter. Contains the number of
              non-mac frames with routing info field
              received by higher level SW.
              Meaningful for Token Ring interfaces only."
    ::= { fibTmuIntrfcEntry 7 }

fibTmuNumNoRif  OBJECT-TYPE
    SYNTAX    Counter
    ACCESS    read-only
    STATUS    mandatory
    DESCRIPTION
              "Cyclic counter. Contains the number of
              non-mac frames without routing info field
              received by higher level SW.
              Meaningful for Token Ring interfaces only."
    ::= { fibTmuIntrfcEntry 8 }

fibTmuNumNonSnap  OBJECT-TYPE
    SYNTAX    Counter
    ACCESS    read-only
    STATUS    mandatory
    DESCRIPTION
              "Cyclic counter. Contains the number of
              non-mac frames which were not snap messages
              and which were handed over to higher level SW
              by the mac level SW. These messages are rejected.
              Meaningful for Token Ring interfaces only."
    ::= { fibTmuIntrfcEntry 9 }

fibTmuNumUnknownType  OBJECT-TYPE
    SYNTAX    Counter
    ACCESS    read-only
    STATUS    mandatory
    DESCRIPTION
              "Cyclic counter. Contains the number of
              non-mac frames which had an unknown 'TYPE' field
              in the snap header and which were handed over
              to higher level SW by the mac level SW. These
              messages are rejected.
              Meaningful for Token Ring interfaces only."
    ::= { fibTmuIntrfcEntry 10 }

fibTmuNumRifLong  OBJECT-TYPE
    SYNTAX    Counter
    ACCESS    read-only
    STATUS    mandatory
    DESCRIPTION
              "Cyclic counter. Contains the number of
              non-mac frames which had a routing information
              field [rif] which was longer than the UDPIP
              package can take [for learning].
              Meaningful for Token Ring interfaces only."
    ::= { fibTmuIntrfcEntry 11 }

fibTmuNumRrpRjctIp   OBJECT-TYPE
    SYNTAX    Counter
    ACCESS    read-only
    STATUS    mandatory
    DESCRIPTION
              "Cyclic counter. Contains the number of
              rarp messages which were rejected because
              the message contents was illegal [e.g. illegal
              ip address].
              Meaningful for Token Ring interfaces only."
    ::= { fibTmuIntrfcEntry 12 }

fibTmuNumArpRcvd  OBJECT-TYPE
    SYNTAX    Counter
    ACCESS    read-only
    STATUS    mandatory
    DESCRIPTION
              "Cyclic counter. Contains the number of arp
              response messages received via this interface.
              Meaningful for Token Ring interfaces only."
    ::= { fibTmuIntrfcEntry 13 }

fibTmuNumIpRcvd  OBJECT-TYPE
    SYNTAX    Counter
    ACCESS    read-only
    STATUS    mandatory
    DESCRIPTION
              "Cyclic counter. Contains the number of ip
               response messages received via this interface."
    ::= { fibTmuIntrfcEntry 14 }

fibTmuNumIfDown  OBJECT-TYPE
    SYNTAX    Counter
    ACCESS    read-only
    STATUS    mandatory
    DESCRIPTION
              "Cyclic counter. Number of times a message
               was directed to an interface which was 'down'."
    ::= { fibTmuIntrfcEntry 15 }

fibTmuNumOwnBrdcst  OBJECT-TYPE
    SYNTAX    Counter
    ACCESS    read-only
    STATUS    mandatory
    DESCRIPTION
              "Cyclic counter. Contains the number of
              broadcast frames which were received in one of
              the system's macs and which were very same
              messages sent by one of the system's macs.
              The mac hw receives broadcast messages even if
              they were sent by the mac's own 48 bits address.
              These messages are rejected.
              Meaningful for Token Ring interfaces only."
    ::= { fibTmuIntrfcEntry 16 }

fibTmuAc00Cntr  OBJECT-TYPE
    SYNTAX    Counter
    ACCESS    read-only
    STATUS    mandatory
    DESCRIPTION
              "Cyclic counter. Contains the number of
              frames which were received with the 'A' and 'C'
              bits both '0'.
              Meaningful for Token Ring interfaces only."
    ::= { fibTmuIntrfcEntry 17 }

fibTmuAc01Cntr  OBJECT-TYPE
    SYNTAX    Counter
    ACCESS    read-only
    STATUS    mandatory
    DESCRIPTION
              "Cyclic counter. contains the number of
              frames which were received with the 'A' and 'C'
              bits equal to '0' and '1'.
              Meaningful for Token Ring interfaces only."
    ::= { fibTmuIntrfcEntry 18 }

fibTmuAc10Cntr  OBJECT-TYPE
    SYNTAX    Counter
    ACCESS    read-only
    STATUS    mandatory
    DESCRIPTION
              "Cyclic counter. Contains the number of
              frames which were received with the 'A' and 'C'
              bits equal to '1' and '0'.
              Meaningful for Token Ring interfaces only."
    ::= { fibTmuIntrfcEntry 19 }

fibTmuAc11Cntr  OBJECT-TYPE
    SYNTAX    Counter
    ACCESS    read-only
    STATUS    mandatory
    DESCRIPTION
              "Cyclic counter. Contains the number of
              frames which were received with the 'A' and 'C'
              bits equal to '1' and '1'."
    ::= { fibTmuIntrfcEntry 20 }

fibTmuParityEc  OBJECT-TYPE
    SYNTAX    Counter
    ACCESS    read-only
    STATUS    mandatory
    DESCRIPTION
              "Cyclic counter. Contains the number of
              times scc reported parity error [per character].
              Meaningful for serial intefaces only."
    ::= { fibTmuIntrfcEntry 21 }

fibTmuFrameEc  OBJECT-TYPE
    SYNTAX    Counter
    ACCESS    read-only
    STATUS    mandatory
    DESCRIPTION
              "Cyclic counter. Contains the number of
              times scc reported framing error [per character].
              Meaningful for serial intefaces only."
    ::= { fibTmuIntrfcEntry 22 }

fibTmuRxNoiseEc  OBJECT-TYPE
    SYNTAX    Counter
    ACCESS    read-only
    STATUS    mandatory
    DESCRIPTION
              "Cyclic counter. Contains the number of
              times scc reported noise error [per character].
              Meaningful for serial intefaces only."
    ::= { fibTmuIntrfcEntry 23 }

fibTmuBreakEc  OBJECT-TYPE
    SYNTAX    Counter
    ACCESS    read-only
    STATUS    mandatory
    DESCRIPTION
              "Cyclic counter. Contains the number of
              times scc reported break character was received.
              Meaningful for serial intefaces only."
    ::= { fibTmuIntrfcEntry 24 }

fibTmuNumConfigNotValid  OBJECT-TYPE
    SYNTAX    Counter
    ACCESS    read-only
    STATUS    mandatory
    DESCRIPTION
              "Cyclic counter. Contains the number of
              times get-naun or get-config of tr driver
              reported 'MAC-ERR-CONFIG-NOT-VALID'.
              Meaningful for Token Ring interfaces only."
    ::= { fibTmuIntrfcEntry 25 }

fibTmuNumAddrNotFound  OBJECT-TYPE
    SYNTAX    Counter
    ACCESS    read-only
    STATUS    mandatory
    DESCRIPTION
              "Cyclic counter. Contains the number of
              times get-naun or get-config of tr driver reported
              'MAC-ERR-ADDR-NOT-FOUND'.
              Meaningful for Token Ring interfaces only."
    ::= { fibTmuIntrfcEntry 26 }

fibTmuNumProcessDisabled  OBJECT-TYPE
    SYNTAX    Counter
    ACCESS    read-only
    STATUS    mandatory
    DESCRIPTION
              "Cyclic counter. Contains the number of
              times get-naun or get-config of tr driver reported
              'MAC-ERR-PROCESS-DISABLED'.
              Meaningful for Token Ring interfaces only."
    ::= { fibTmuIntrfcEntry 27 }

fibTmuNumBeaconsRcvd  OBJECT-TYPE
    SYNTAX    Counter
    ACCESS    read-only
    STATUS    mandatory
    DESCRIPTION
              " Cyclic counter. Contains the number of
              times tr driver reported receiving a beacon
              on this interface.
              Meaningful for Token Ring interfaces only."
    ::= { fibTmuIntrfcEntry 28 }

fibTmuLastBeaconTime  OBJECT-TYPE
    SYNTAX    TimeTicks
    ACCESS    read-only
    STATUS    mandatory
    DESCRIPTION
              "Time [in sys timer units] when
              last beacon was reported on this intrerface.
              Meaningful for Token Ring interfaces only."
    ::= { fibTmuIntrfcEntry 29 }

fibTmuLastBeaconType  OBJECT-TYPE
    SYNTAX    INTEGER
    ACCESS    read-only
    STATUS    mandatory
    DESCRIPTION
              "Type of the last beacon reported on
              this intrerface.
              Meaningful for Token Ring interfaces only."
    ::= { fibTmuIntrfcEntry 30 }

fibTmuLastBeaconAddr  OBJECT-TYPE
    SYNTAX    MacAddress
    ACCESS    read-only
    STATUS    mandatory
    DESCRIPTION
              "Mac address of the last station which reported
              'beacon' on this interface.
              Meaningful for Token Ring interfaces only."
    ::= { fibTmuIntrfcEntry 31 }

fibTmuLastBeaconNaun  OBJECT-TYPE
    SYNTAX    MacAddress
    ACCESS    read-only
    STATUS    mandatory
    DESCRIPTION
              "Mac address of the next upsream neighbour of
              the last station which reported 'beacon' on
              this interface.
              Meaningful for Token Ring interfaces only."
    ::= { fibTmuIntrfcEntry 32 }

fibTmuNumRxGroup  OBJECT-TYPE
    SYNTAX    Counter
    ACCESS    read-only
    STATUS    mandatory
    DESCRIPTION
              "Cyclic counter. Contains the number of
              non-mac group frames received by higher level SW.
              Meaningful for Token Ring interfaces only."
    ::= { fibTmuIntrfcEntry 33 }

fibTmuNumRxFunctional  OBJECT-TYPE
    SYNTAX    Counter
    ACCESS    read-only
    STATUS    mandatory
    DESCRIPTION
              "Cyclic counter. Contains the number of
              non-mac functional frames received by higher
              level SW.
              Meaningful for Token Ring interfaces only."
    ::= { fibTmuIntrfcEntry 34 }

-- =============================================
--
--Tmu Match Group
--
--A list of information items, such as number od entries,
--related to the table, below, of matched 'port vs. mac
--address' pairs
--
-- =============================================

fibTmuMatchUpdateTime  OBJECT-TYPE
    SYNTAX    TimeTicks
    ACCESS    read-only
    STATUS    mandatory
    DESCRIPTION
              "Time [in sys timer units] from startup
              at which the table below has been updated.
              See remark in fibTmuMatchListValid below."
    ::= { tmuMatch 1 }

fibTmuMatchNumEntries  OBJECT-TYPE
    SYNTAX    INTEGER
    ACCESS    read-only
    STATUS    mandatory
    DESCRIPTION
              "Number of meaningful entries in the
               match array. The index of the last meaningful
               entry is num-entries. See remark in
               fibTmuMatchListValid below."
    ::= { tmuMatch 2 }

fibTmuMatchNumTmuEntries  OBJECT-TYPE
    SYNTAX    INTEGER
    ACCESS    read-only
    STATUS    mandatory
    DESCRIPTION
              "Number of meaningful entries in the
               match array which belong to stations attached
               to the tmu via tau ports. This does not include
               the two (or one) chipsets themselves. Example:
               if second chip index is 3 and first chip index
               is 1 then the number of cau entries is 1. See
               remark in fibTmuMatchListValid below."
    ::= { tmuMatch 3 }

fibTmuMatchFirstChipIndex  OBJECT-TYPE
    SYNTAX    INTEGER
    ACCESS    read-only
    STATUS    mandatory
    DESCRIPTION
              "The index in the match table at which the
               the first chipset is located (order of stations
               on match table is downstream, i.e. in the
               direction messages are transported). See remark
               in fibTmuMatchListValid below."
    ::= { tmuMatch 4 }


fibTmuMatchSecondChipIndex  OBJECT-TYPE
    SYNTAX    INTEGER
    ACCESS    read-only
    STATUS    mandatory
    DESCRIPTION
              "The index in the match table at which the
               the second chipset is located (order of stations
               on match table is downstream, i.e. in the
               direction messages are transported). See remark
               in fibTmuMatchListValid below."
    ::= { tmuMatch 5 }

fibTmuMatchActMonIndex  OBJECT-TYPE
    SYNTAX    INTEGER
    ACCESS    read-only
    STATUS    mandatory
    DESCRIPTION
              "The index in the match table at which
               the active monitor is located (order of
               stations on match table is downstream, i.e.
               in the direction messages are transported).
               See remark in fibTmuMatchListValid below."
    ::= { tmuMatch 6 }

fibTmuMatchConfigChipIndex  OBJECT-TYPE
    SYNTAX    INTEGER
    ACCESS    read-only
    STATUS    mandatory
    DESCRIPTION
              "The index in the match table from which the
               information for the configuration was
               collected (order of stations on match table
               is downstream, i.e. in the direction
               messages are transported). See remark in
               fibTmuMatchListValid below."
    ::= { tmuMatch 7 }

fibTmuMatchListValid  OBJECT-TYPE
    SYNTAX    INTEGER {
                  valid(2),
                  not-valid(-1)
              }
    ACCESS    read-only
    STATUS    mandatory
    DESCRIPTION
              "Flag indicating whether the information
               in the tmuMatch group is valid or not.
               If information is not valid, ALL objects
               will return with a 'no such object' response."
    ::= { tmuMatch 8 }


fibTmuMatchUpToDate  OBJECT-TYPE
    SYNTAX    INTEGER {
                  up-to-date(2),
                  not-up-to-date(1)
              }
    ACCESS    read-only
    STATUS    mandatory
    DESCRIPTION
              "Flag. If set '1' then the information
               in All objects of tmuMatch group is not
               up to date any more: Some changes have
               occurred and a new, up to date matching
               configuration can not be supplied.
               In that case, the information in tmuMatch group
               remains true for the update time as specified
               above but not for the current time.
               See remark in fibTmuMatchListValid above."
    ::= { tmuMatch 9 }

fibTmuMatchNoMatchReason  OBJECT-TYPE
    SYNTAX    INTEGER {
                empty-reason(1),
                malloc-fail(2),
                segment-unstable(3),
                no-chip-on-list(4),
                inconsistency(5),
                soft-01(6),
                soft-02(7),
                first-not-found(8),
                second-not-found(9),
                found-twice(10),
                soft-03(11),
                ports-gt-stations(12),
                stations-gt-ports(13),
                no-tr-list(14)
              }
    ACCESS    read-only
    STATUS    mandatory
    DESCRIPTION
              "Indication meaningful only if fibTmuMatchUpToDate
               above is not up-to-date.
               empty-reason -
                 Either there is a list or the reason for
                 the fact that there is no list is yet
                 unknown.
               malloc-fail -
                 System could not provide memory for this
                 list.
               segment-unstable -
                 Indications from the token ring chip sets
                 were that the ring has not reached a stable
                 state yet.
               no-chip-on-list -
                 Chip set handling software could not indicate
                 which of the Tmu chips is on the portion
                 of token ring which is on the Tau ports.
               inconsistency -
                 Inconsistent responses from low level token
                 ring handler indicate ring is not yet stable.
               soft-01 -
                 Software error. system could not retrieve a
                 mac address related to a specified tr interface.
               soft-02 -
                 Software error. system could not retrieve a
                 mac address related to a specified tr interface.
               first-not-found -
                 First chip set of Tmu could not be found on the
                 list of addresses supplied by the token ring
                 driver. Ring is not stable yet.
               second-not-found -
                 Second chip set of Tmu could not be found on the
                 list of addresses supplied by the token ring
                 driver. Ring is not stable yet.
               found-twice -
                 One chip set of Tmu was found twice on the
                 list of addresses supplied by the token ring
                 driver. Ring is not stable yet.
               soft-03 -
                 Software indicated a match could be found but
                 could not supply the actula list. Internal
                 sw error.
               ports-gt-stations -
                 Number of ports was fould to be higher than the
                 number of stations. This is only reason for not
                 construction the 'match' table.
               stations-gt-ports -
                 Number of stations was fould to be higher than the
                 number of ports. This is only reason for not
                 construction the 'match' table.
               no-tr-list -
                 No configuration is currently available from the
                 token ring driver. Ring is unstable or some sw
                 error.
               See remark in fibTmuMatchListValid above."
    ::= { tmuMatch 10 }


-- =============================================
--
--Tmu Match Group
--
--A list of matched port-mac address pairs.
--
-- =============================================

fibTmuMatchTable OBJECT-TYPE
    SYNTAX    SEQUENCE OF FibTmuMatchEntry
    ACCESS    not-accessible
    STATUS    mandatory
    DESCRIPTION
              "Table containing information on the location
              of stations (identified by their physical
              address in terms of Tmu/Tau ports)."
    ::= { tmuMatch 20 }

fibTmuMatchEntry OBJECT-TYPE
    SYNTAX    FibTmuMatchEntry
    ACCESS    not-accessible
    STATUS    mandatory
    DESCRIPTION
              "Entry of information concerning a single
              station and its port (on Tmu/Tau)."
    INDEX     { fibTmuMatchIndex }
    ::= { fibTmuMatchTable 1 }


FibTmuMatchEntry
    ::= SEQUENCE {
              fibTmuMatchIndex
                    INTEGER,
              fibTmuMatchTauId
                    INTEGER,
              fibTmuMatchPortId
                    INTEGER,
              fibTmuMatchPhysAddr
                    MacAddress,
              fibTmuMatchStationInfo
                    INTEGER
        }

fibTmuMatchIndex  OBJECT-TYPE
    SYNTAX    INTEGER
    ACCESS    read-only
    STATUS    mandatory
    DESCRIPTION
              "The value of this object identifies
              the the number of the entry in the
              table. See remark in fibTmuMatchListValid
              above"
    ::= { fibTmuMatchEntry 1 }

fibTmuMatchTauId   OBJECT-TYPE
    SYNTAX    INTEGER
    ACCESS    read-only
    STATUS    mandatory
    DESCRIPTION
              "Number of the tau port on which station is
               attached. Tau ports are connectors on the
               tmu. The may have either a tau connected or
               a single station. See fibTmuMatchPortId below.
               If this object is not valid for the specified
               instance (station is not on the Tmu but on
               the trunk), return value is 0xFFFFFFFF (-1).
               See remark in fibTmuMatchListValid above"
    ::= { fibTmuMatchEntry 2 }

fibTmuMatchPortId  OBJECT-TYPE
    SYNTAX    INTEGER
    ACCESS    read-only
    STATUS    mandatory
    DESCRIPTION
              "If greater than 1 then 'fibTmuMatchTauId' is the
               number of the port on the tmu and 'fibTmuMatchPortId'
               is the number of the port on the related Tau (starting
               with port #1 for fibTmuMatchPortId = 2). If less than
               or equal to 1 then it is a  One-Station-Port
               Indicating that one station is directly attached to
               the port specified by 'fibTmuMatchTauId'.
               The information contained in values smaller than 2 may
               also be deduced from 'fibTmuMatchStationInfow' below.
               If this object is not valid for the specified
               instance (station is not on the Tmu but on
               the trunk), return value is 0xFFFFFFFF (-1).
               See remark in fibTmuMatchListValid above"
    ::= { fibTmuMatchEntry 3 }

fibTmuMatchPhysAddr  OBJECT-TYPE
    SYNTAX    MacAddress
    ACCESS    read-only
    STATUS    mandatory
    DESCRIPTION
              "The token ring physical address of the
               station which is attached to the specified
               port. See remark in fibTmuMatchListValid
               above"
    ::= { fibTmuMatchEntry 4 }


fibTmuMatchStationInfo OBJECT-TYPE
    SYNTAX    INTEGER
    ACCESS    read-only
    STATUS    mandatory
    DESCRIPTION
              "Information on the attached station:
               If BIT0 is set (value = 0x01) then this is definitely
                 a 'sniffer' port (i.e. a station which is sending
                 'trace tool present' messages is located on this port).
               If BIT1 is set (value = 0x02) then its location
                 is doubtful (System has been unable to resolve
                 the location of this station).
               If BIT2 is set (value = 0x04) then station is not
                 attached to one of the tmu's ports but rather to
                 the trunk.
               If bit3 is set (value = 0x08) then station is one of
                 the tmu's chips.
               If BIT4 is set (value = 0x10) then this is a station
                 attached to the tmu (and not on the trunk).
               See remark in fibTmuMatchListValid above"
    ::= { fibTmuMatchEntry 5 }

-- =============================================
--
--Tmu Stations Group
--
-- a list of all stations on the token ring with
-- information on each station and information
-- related to the whole list.
--
-- =============================================

fibTmuStationsUpdateTime  OBJECT-TYPE
    SYNTAX    TimeTicks
    ACCESS    read-only
    STATUS    mandatory
    DESCRIPTION
              "Time [in sys timer units] from startup
              at which the table below has been updated.
              See remark in fibTmuStationsListValid below."
    ::= { tmuStations 1 }

fibTmuStationsNumEntries  OBJECT-TYPE
    SYNTAX    INTEGER
    ACCESS    read-only
    STATUS    mandatory
    DESCRIPTION
              "Number of meaningful entries in the Stations
               array. The index of the last meaningful entry
               is num-entries. See remark in fibTmuStationsListValid
               below."
    ::= { tmuStations 2 }

fibTmuStationsNumTmuEntries  OBJECT-TYPE
    SYNTAX    INTEGER
    ACCESS    read-only
    STATUS    mandatory
    DESCRIPTION
              "Number of meaningful entries in the
               Stations array which belong to stations attached
               to the tmu via tau ports. This does not include
               the two (or one) chipsets themselves. Example:
               if second chip index is 3 and first chip index
               is 1 then the number of Tmu entries is 1. See
               remark in fibTmuStationsListValid below."
    ::= { tmuStations 3 }

fibTmuStationsFirstChipIndex  OBJECT-TYPE
    SYNTAX    INTEGER
    ACCESS    read-only
    STATUS    mandatory
    DESCRIPTION
              "The index in the Stations table at which the
               the first chipset is located (order of stations
               on Stations table is downstream, i.e. in the
               direction messages are transported). See remark
               in fibTmuStationsListValid below."
    ::= { tmuStations 4 }


fibTmuStationsSecondChipIndex  OBJECT-TYPE
    SYNTAX    INTEGER
    ACCESS    read-only
    STATUS    mandatory
    DESCRIPTION
              "The index in the Stations table at which the
               the second chipset is located (order of stations
               on Stations table is downstream, i.e. in the
               direction messages are transported). See remark
               in fibTmuStationsListValid below."
    ::= { tmuStations 5 }

fibTmuStationsActMonIndex  OBJECT-TYPE
    SYNTAX    INTEGER
    ACCESS    read-only
    STATUS    mandatory
    DESCRIPTION
              "The index in the Stations table at which
               the active monitor is located (order of
               stations on Stations table is downstream, i.e.
               in the direction messages are transported).
               See remark in fibTmuStationsListValid below."
    ::= { tmuStations 6 }

fibTmuStationsConfigChipIndex  OBJECT-TYPE
    SYNTAX    INTEGER
    ACCESS    read-only
    STATUS    mandatory
    DESCRIPTION
              "The index in the Stations table from which the
               information for the configuration was
               collected (order of stations on Stations table
               is downstream, i.e. in the direction
               messages are transported). See remark in
               fibTmuStationsListValid below."
    ::= { tmuStations 7 }

fibTmuStationsStationsListValid  OBJECT-TYPE
    SYNTAX    INTEGER {
                  valid(2),
                  not-valid(-1)
              }
    ACCESS    read-only
    STATUS    mandatory
    DESCRIPTION
              "Flag indicating whether the information
               in the tmuStations group is valid or not.
               If information is not valid, ALL objects
               will return with a 'no such object' response."
    ::= { tmuStations 8 }


fibTmuStationsUpToDate  OBJECT-TYPE
    SYNTAX    INTEGER {
                  up-to-date(2),
                  not-up-to-date(1)
              }
    ACCESS    read-only
    STATUS    mandatory
    DESCRIPTION
              "Flag. If set '1' then the information
               in All objects of tmuStations group is not
               up to date any more: Some changes have
               occurred and a new, up to date Stationsing
               configuration can not be supplied.
               In that case, the information in tmuStations group
               remains true for the update time as specified
               above but not for the current time.
               See remark in fibTmuStationsListValid above."
    ::= { tmuStations 9 }

fibTmuMatchNoStationsListReason  OBJECT-TYPE
    SYNTAX    INTEGER {
                empty-reason(1),
                malloc-fail(2),
                segment-unstable(3),
                no-chip-on-list(4),
                inconsistency(5),
                soft-01(6),
                soft-02(7),
                first-not-found(8),
                second-not-found(9),
                found-twice(10),
                no-tr-list(14)
              }
    ACCESS    read-only
    STATUS    mandatory
    DESCRIPTION
              "Indication meaningful only if fibTmuStationsUpToDate
               above is not up-to-date.
               empty-reason -
                 Either there is a list or the reason for
                 the fact that there is no list is yet
                 unknown.
               malloc-fail -
                 System could not provide memory for this
                 list.
               segment-unstable -
                 Indications from the token ring chip sets
                 were that the ring has not reached a stable
                 state yet.
               no-chip-on-list -
                 Chip set handling software could not indicate
                 which of the Tmu chips is on the portion
                 of token ring which is on the Tau ports.
               inconsistency -
                 Inconsistent responses from low level token
                 ring handler indicate ring is not yet stable.
               soft-01 -
                 Software error. system could not retrieve a
                 mac address related to a specified tr interface.
               soft-02 -
                 Software error. system could not retrieve a
                 mac address related to a specified tr interface.
               first-not-found -
                 First chip set of Tmu could not be found on the
                 list of addresses supplied by the token ring
                 driver. Ring is not stable yet.
               second-not-found -
                 Second chip set of Tmu could not be found on the
                 list of addresses supplied by the token ring
                 driver. Ring is not stable yet.
               found-twice -
                 One chip set of Tmu was found twice on the
                 list of addresses supplied by the token ring
                 driver. Ring is not stable yet.
               no-tr-list -
                 No configuration is currently available from the
                 token ring driver. Ring is unstable or some sw
                 error.
               See remark in fibTmuStationsListValid above."
    ::= { tmuStations 10 }


-- =============================================
--
--Tmu Stations Group
--
--A list of all Stations on the ring.
--
-- =============================================

fibTmuStationsTable OBJECT-TYPE
    SYNTAX    SEQUENCE OF FibTmuStationsEntry
    ACCESS    not-accessible
    STATUS    mandatory
    DESCRIPTION
              "Table containing information on the location
              of stations (identified by their physical
              address)."
    ::= { tmuStations 20 }

fibTmuStationsEntry OBJECT-TYPE
    SYNTAX    FibTmuStationsEntry
    ACCESS    not-accessible
    STATUS    mandatory
    DESCRIPTION
              "Entry of information concerning a single
              station."
    INDEX     { fibTmuStationsIndex }
    ::= { fibTmuStationsTable 1 }


FibTmuStationsEntry
    ::= SEQUENCE {
              fibTmuStationsIndex
                    INTEGER,
              fibTmuStationsPhysAddr
                    MacAddress,
              fibTmuStationsStationInfo
                    INTEGER
        }


fibTmuStationsIndex  OBJECT-TYPE
    SYNTAX    INTEGER
    ACCESS    read-only
    STATUS    mandatory
    DESCRIPTION
              "The value of this object identifies
              the the number of the entry in the
              table. See remark in fibTmuStationsListValid
              above"
    ::= { fibTmuStationsEntry 1 }

fibTmuStationsPhysAddr  OBJECT-TYPE
    SYNTAX    MacAddress
    ACCESS    read-only
    STATUS    mandatory
    DESCRIPTION
              "The token ring physical address of the
               station which is at the specified
               index. See remark in fibTmuStationsListValid
               above"
    ::= { fibTmuStationsEntry 2 }

fibTmuStationsStationInfo OBJECT-TYPE
    SYNTAX    INTEGER
    ACCESS    read-only
    STATUS    mandatory
    DESCRIPTION
              "Information on the attached station:
               If BIT0 is set (value = 0x01) then this is definitely
                 a 'sniffer' port (i.e. a station which is sending
                 'trace tool present' messages is located on this port).
               If BIT1 is set (value = 0x02) then its location
                 is doubtful (System has been unable to resolve
                 the location of this station).
               If BIT2 is set (value = 0x04) then station is not
                 attached to one of the tmu's ports but rather to
                 the trunk.
               If bit3 is set (value = 0x08) then station is one of
                 the tmu's chips.
               If BIT4 is set (value = 0x10) then this is a station
                 attached to the tmu (and not on the trunk).
               See remark in fibTmuStationsListValid above"
    ::= { fibTmuStationsEntry 3 }

-- =============================================
--
--Tmu Ports Group
--
-- a list of all Ports on the Tmu/Tau pair with
-- information on each port and information
-- related to the whole list.
--
-- =============================================

fibTmuPortsNumRelayOpen  OBJECT-TYPE
    SYNTAX    INTEGER
    ACCESS    read-only
    STATUS    mandatory
    DESCRIPTION
              "Number of ports attached to single stations
               either directly on the tmu or on a tau which
               have their relay open. A relay remains open as
               long as there is an attached station and it
               not a source of some problem."
    ::= { tmuPorts 1 }

fibTmuPortsNumPhantomPresent  OBJECT-TYPE
    SYNTAX    INTEGER
    ACCESS    read-only
    STATUS    mandatory
    DESCRIPTION
              "Number of ports attached to single stations
               (either directly on the tmu or on a tau) which
               have their phantom up."
    ::= { tmuPorts 2 }

fibTmuPortsNumPortsPerTmu  OBJECT-TYPE
    SYNTAX    INTEGER
    ACCESS    read-only
    STATUS    mandatory
    DESCRIPTION
              "Number of ports on one tmu (both ports
               which support a tau and ports which may
               support only single stations)."
    ::= { tmuPorts 3 }

fibTmuPortsNumTausPerTmu  OBJECT-TYPE
    SYNTAX    INTEGER
    ACCESS    read-only
    STATUS    mandatory
    DESCRIPTION
              "The maximal number of Tau's which can
               be connected to one Tmu"
    ::= { tmuPorts 4 }


fibTmuPortsNumPortsPerTau  OBJECT-TYPE
    SYNTAX    INTEGER
    ACCESS    read-only
    STATUS    mandatory
    DESCRIPTION
              "The maximal number of ports on one Tau"
    ::= { tmuPorts 5 }

fibTmuPortsMaxNumTauErrs  OBJECT-TYPE
    SYNTAX    INTEGER
    ACCESS    read-only
    STATUS    mandatory
    DESCRIPTION
              "Number of errors (which cause temporary
               relay closing) allowed after phantom goes up
               on a single Tau port and before its relay is
               closed (port detached). Relay is reopened
               (port attached) after phantom goes down and
               up again."
    ::= { tmuPorts 6 }

fibTmuPortsMaxFirstTimeout  OBJECT-TYPE
    SYNTAX    INTEGER
    ACCESS    read-only
    STATUS    mandatory
    DESCRIPTION
              "Number of timeouts allowed before it is
               decided that communication with Tau is really
               faulty. System moves from state of connection
               into no-connection and attempts will be made to
               determine the type of connection (Tau or single)."
    ::= { tmuPorts 7 }

-- =============================================
--
--Tmu Ports Group
--
--A list of all Ports on the Tmu with information
--on each port and on whatever is connected to
--it.
--
-- =============================================

fibTmuPortsTauTable OBJECT-TYPE
    SYNTAX    SEQUENCE OF FibTmuPortsTauEntry
    ACCESS    not-accessible
    STATUS    mandatory
    DESCRIPTION
              "Table containing information on ports
              which are directly on Tmu and on Tau's
              which may be connected to them."
    ::= { tmuPorts 29 }

fibTmuPortsTauEntry OBJECT-TYPE
    SYNTAX    FibTmuPortsTauEntry
    ACCESS    not-accessible
    STATUS    mandatory
    DESCRIPTION
              "Entry of information concerning a single
              port on Tmu and the attached station/Tau."
    INDEX     { fibTmuPortsTmuPort }
    ::= { fibTmuPortsTauTable 1 }


FibTmuPortsTauEntry
    ::= SEQUENCE {
              fibTmuPortsTmuPort
                    INTEGER,
              fibTmuPortsPortType
                    INTEGER,
              fibTmuPortsEndConnection
                    INTEGER,
              fibTmuPortsPortStatus
                    INTEGER,
              fibTmuPortsManagerCloseRun
                    INTEGER,
              fibTmuPortsManagerClosePerm
                    INTEGER,
              fibTmuPortsNumConsequentErrs
                    INTEGER,
              fibTmuPortsNumTimeout
                    INTEGER,
              fibTmuPortsTauPortState
                    INTEGER,
              fibTmuPortsNumPorts
                    INTEGER,
              fibTmuPortsNumAttached
                    INTEGER,
              fibTmuPortsNumPhantomUp
                    INTEGER,
              fibTmuPortsTauRevision
                    INTEGER,
              fibTmuPortsModuleId
                    INTEGER,
              fibTmuPortsNumModules
                    INTEGER,
              fibTmuPortsTauMode
                    INTEGER,
              fibTmuPortsLedState
                    INTEGER,
              fibTmuPortsRequestType
                    INTEGER,
              fibTmuPortsLastTxTime
                    TimeTicks,
              fibTmuPortsLastPollTime
                    TimeTicks,
              fibTmuPortsUpdateTime
                    TimeTicks,
              fibTmuPortsAllowedAddr
                    MacAddress,
              fibTmuPortsAllowedAddrLoaded
                    INTEGER
              }


fibTmuPortsTmuPort  OBJECT-TYPE
    SYNTAX    INTEGER
    ACCESS    read-only
    STATUS    mandatory
    DESCRIPTION
              "Number of port (on TMU) described in this
               array entry. Port numbers increase in
               the direction of the token."
    ::= { fibTmuPortsTauEntry 1 }

fibTmuPortsPortType  OBJECT-TYPE
    SYNTAX    INTEGER {
                  station-or-Tau(1),
                  station-only(2)
              }
    ACCESS    read-only
    STATUS    mandatory
    DESCRIPTION
              "Flag indicating whether this port supports
               both a Tau and a single station or just a
               single station."
    ::= { fibTmuPortsTauEntry 2 }

fibTmuPortsEndConnection  OBJECT-TYPE
    SYNTAX    INTEGER {
                  undefined(1),
                  tau-connected(2),
                  single-connected(3),
                  passive-connected(4)
              }
    ACCESS    read-only
    STATUS    mandatory
    DESCRIPTION
              "Flag indicating whether this port is
               connected to a Tau or to a single station
               (or is in a state where it is not clear
               exactly what is connected to the specified
               port)."
    ::= { fibTmuPortsTauEntry 3 }


fibTmuPortsPortStatus  OBJECT-TYPE
    SYNTAX    INTEGER
    ACCESS    read-only
    STATUS    mandatory
    DESCRIPTION
              "Bit map indicating status of the port:
               Bit3 (0x08) -
                 If set indicates that the relay of this
                 port is open (and, therefore, the station/Tau
                 connected to this port is on the token ring).
               Bit4 (0x10) -
                 If set indicates that phantom signal was detected
                 at this port (and, therefore, a station/Tau
                 is connected to this port).
               Bit5 (0x20) -
                 If set indicates that the relay of this
                 port is closed because a command was received
                 to do so from an snmp manager.
               Bit6 (0x40) -
                 If set then port has been temporarily closed
                 by Tmu because it was decided that either
                 the Tau or the communication line is faulty.
                 System may still revert to attaching the port
                 if faulty state is overcome.
                 This state may also be entered because Tmu
                 received indication that the ring was not
                 stable. As long as this is the only reason
                 for the port to be closed, system will
                 continually try to revert to attaching the port.
               Bit7 (0x80) -
                 If set then port has been closed because
                 it was found to create too many errors.
                 Port will remain closed until phantom goes
                 down and up again.
               Bit9 (0x200)  -
                 Port is detached because of security
                 violation and will remain so until phantom
                 goes down and up again or until manager
                 releases the lock."
    ::= { fibTmuPortsTauEntry 4 }

fibTmuPortsManagerCloseRun OBJECT-TYPE
    SYNTAX    INTEGER {
                  open(1),
                  close(2)
              }
    ACCESS    read-write
    STATUS    mandatory
    DESCRIPTION
              "When setting this object to the value of close (2)
               the indicated port on Tmu will be closed, the
               related led will start blinking at a slow rate and
               port will not be opened before it is set to the value
               of open (1). Setting to the value of open (1)
               does not guarantee the opening of the indicated
               Tmu port but will only allow the Tmu system to
               let this port into the ring if it obeys the rules
               of token ring. Reading this object returns the value
               last set by the manager (or the default value). This
               command holds only until the next system reset. To
               make sure it remains valid after reset, use
               'fibTmuPortsManagerClosePerm'"
    ::= { fibTmuPortsTauEntry 5 }

fibTmuPortsManagerClosePerm OBJECT-TYPE
    SYNTAX    INTEGER {
                  open(1),
                  close(2)
              }
    ACCESS    read-write
    STATUS    mandatory
    DESCRIPTION
              "When setting this object to the value of close (2)
               the indicated port on Tmu will be closed after
               the next system reset. see 'fibTmuPortsManagerCloseRun'.
               Setting to the value of open (1) will only allow the
               Tmu system to let this port into the ring (after
               the next reset) if it obeys the rules of token ring.
               Reading this object returns the value last set by
               the manager (or the default value)."
    ::= { fibTmuPortsTauEntry 6 }

fibTmuPortsNumConsequentErrs  OBJECT-TYPE
    SYNTAX    INTEGER
    ACCESS    read-only
    STATUS    mandatory
    DESCRIPTION
              "Counter. Number of times an error has
               been detected on this Tau port (one after
               the other, without a 'no error' state in
               between) since phantom last came up.
               When the number of errors reaches
               fibTmuPortsMaxNumTauErrs, relay
               is closed and is not opened until phantom
               goes down and up again."
    ::= { fibTmuPortsTauEntry 10 }

fibTmuPortsNumTimeout  OBJECT-TYPE
    SYNTAX    Counter
    ACCESS    read-only
    STATUS    mandatory
    DESCRIPTION
              "Number of times communication with Tau
               has been attempted immediately after
               pahntom has gone up. Attempt go on for
               MaxFirstTimeout times.
               After that, it is decided that a regular station
               is connected and this will remain the state
               until phantom goes down and up again."
    ::= { fibTmuPortsTauEntry 11 }


fibTmuPortsTauPortState  OBJECT-TYPE
    SYNTAX    INTEGER {
                  no-connection(1),
                  waiting-to-open(2),
                  active-connection(3),
                  getting-config(4),
                  initializing(5),
                  pre-active(6)
              }
    ACCESS    read-only
    STATUS    mandatory
    DESCRIPTION
              "This is a status byte. it indicates the
               state of the port as far as software is
               concerned. A port which may only carry a
               single station can possibly be in one of
               two states:
               no-connection     (1)
               waiting-to-open   (2)
               active-connection (3)
               A port which may carry either a Tau or a single
               station can possibly be in one of the following
               states:
               no-connection     (1)
               getting-config    (4)
               initializing      (5)
               pre-active        (6)
               active-connection (3)"
    ::= { fibTmuPortsTauEntry 12 }

fibTmuPortsNumPorts  OBJECT-TYPE
    SYNTAX    INTEGER
    ACCESS    read-only
    STATUS    mandatory
    DESCRIPTION
              "The number of ports on the Tau connected
               to this port. Set to '1' when a station
               is directly connected to this port. Only
               meaningful when 'fibTmuPortsTauPortState'
               is 'active-connection'"
    ::= { fibTmuPortsTauEntry 13 }

fibTmuPortsNumAttached  OBJECT-TYPE
    SYNTAX    INTEGER
    ACCESS    read-only
    STATUS    mandatory
    DESCRIPTION
              "This is the number of ports on the connected
               Tau (if there is any) that have their relay
               open (station is attached to the ring). Only
               meaningful when 'fibTmuPortsTauPortState'
               is 'active-connection'"
    ::= { fibTmuPortsTauEntry 14 }


fibTmuPortsNumPhantomUp  OBJECT-TYPE
    SYNTAX    INTEGER
    ACCESS    read-only
    STATUS    mandatory
    DESCRIPTION
              "This is the number of ports on the connected
               Tau (if there is any) that have their phantom
               in 'up' state. Only meaningful when
               'fibTmuPortsTauPortState' is 'active-connection'"
    ::= { fibTmuPortsTauEntry 15 }

fibTmuPortsTauRevision  OBJECT-TYPE
    SYNTAX    INTEGER
    ACCESS    read-only
    STATUS    mandatory
    DESCRIPTION
              "This is the Tau revision as reported by
               the Tau itself (if there is one). Only
               meaningful when 'fibTmuPortsTauPortState'
               is 'active-connection'."
    ::= { fibTmuPortsTauEntry 16 }

fibTmuPortsModuleId  OBJECT-TYPE
    SYNTAX    OCTET STRING (SIZE (4))
    ACCESS    read-only
    STATUS    mandatory
    DESCRIPTION
              "This is a hw id attached to each of its
               modules by the Tau. each octet is related
               to one module (up to 4 modules). Number
               of meaningful octets is determined by
               fibTmuPortsNumModules below. Only
               meaningful when 'fibTmuPortsTauPortState'
               is 'active-connection'"
    ::= { fibTmuPortsTauEntry 17 }

fibTmuPortsNumModules  OBJECT-TYPE
    SYNTAX    INTEGER
    ACCESS    read-only
    STATUS    mandatory
    DESCRIPTION
              "This is the number of modules on the
               attached Tau as reported by the Tau
               itself. Only meaningful when
               'fibTmuPortsTauPortState' is
               'active-connection'."
    ::= { fibTmuPortsTauEntry 18 }


fibTmuPortsTauMode  OBJECT-TYPE
    SYNTAX    INTEGER
    ACCESS    read-only
    STATUS    mandatory
    DESCRIPTION
              "This is a bit map of information on the
               status of the Tau and the way it is set.
               Details of the various bits:
                 Bit0  (= 0x01)
                   If '1' then Tau is set to a rate of
                   16 mega bits per second on token ring.
                   Otherwise, it is set to a rate of 4 mega
                   bits per second.
               Only meaningful when 'fibTmuPortsTauPortState'
               is 'active-connection'."
    ::= { fibTmuPortsTauEntry 19 }

fibTmuPortsLedState  OBJECT-TYPE
    SYNTAX    INTEGER {
                  slow-rate(1),
                  fast-rate(2),
                  fixed-on(3),
                  fixed-off(4)
              }
    ACCESS    read-only
    STATUS    mandatory
    DESCRIPTION
              "State of the indication led related to
               this port. Values can be:
                 slow-rate   (1)
                 fast-rate   (2)
                 fixed-on    (3)
                 fixed-off   (4)"
    ::= { fibTmuPortsTauEntry 20 }


fibTmuPortsRequestType  OBJECT-TYPE
    SYNTAX    INTEGER {
                  no-Tau-msg(1),
                  get-configuration-msg(17),
                  get-phantom-msg(33),
                  get-relay-msg(49),
                  attach-detach-msg(65),
                  set-beacon-msg(81),
                  set-active-msg(97),
                  get-all-msg(113),
                  get-changes-msg(129),
                  reset-Tau-msg(145),
                  self-test-Tau-msg(161)
              }
    ACCESS    read-only
    STATUS    mandatory
    DESCRIPTION
              "This is the type of the message sent to
               the attached Tau for which a response is
               required. If request-type is 'no-Tau-msg' then
               no message was sent and, therefore, no request
               is expected.
                 no-Tau-msg                (=0x01)
                 get-configuration-msg     (=0x11)
                 get-phantom-msg           (=0x21)
                 get-relay-msg             (=0x31)
                 attach-detach-msg         (=0x41)
                 set-beacon-msg            (=0x51)
                 set-active-msg            (=0x61)
                 get-all-msg               (=0x71)
                 get-changes-msg           (=0x81)
                 reset-Tau-msg             (=0x91)
                 self-test-Tau-msg         (=0xA1)"
    ::= { fibTmuPortsTauEntry 21 }

fibTmuPortsLastTxTime  OBJECT-TYPE
    SYNTAX    TimeTicks
    ACCESS    read-only
    STATUS    mandatory
    DESCRIPTION
              "This is the system timer value
               at the last tx-to-Tau on this Tau port
               (provided a Tau is attached to it)."
    ::= { fibTmuPortsTauEntry 22 }

fibTmuPortsLastPollTime  OBJECT-TYPE
    SYNTAX    TimeTicks
    ACCESS    read-only
    STATUS    mandatory
    DESCRIPTION
              "This is the system timer value
               at the last poll response on this Tau port
               (provided a Tau is attached to it). If
               no polling has so far been carried out,
               a value of 0 is returned."
    ::= { fibTmuPortsTauEntry 23 }


fibTmuPortsUpdateTime  OBJECT-TYPE
    SYNTAX    TimeTicks
    ACCESS    read-only
    STATUS    mandatory
    DESCRIPTION
              "This is the system timer value when
               phantom was last probed on this Tau port."
    ::= { fibTmuPortsTauEntry 24 }

fibTmuPortsAllowedAddr  OBJECT-TYPE
    SYNTAX    MacAddress
    ACCESS    read-write
    STATUS    mandatory
    DESCRIPTION
              "This is the one physical address allowed
               to be on this Tmu port (provided a single
               station is attached to it and not a Tau).
               The value loaded in fibTmuPortsAllowedAddrLoaded
               below determines the state of this object.
               Writing to this object stores the address
               in non-volatile memory. It also makes
               security on this port active provided
               fibTmuSecurityModeRun has bit0 set. Loading
               will not be carried out if fibTmuNumStationLeft
               is 0 (no more space in non-volatile memory). In
               that case, an error will be returned
               (genErr = 5)."
    ::= { fibTmuPortsTauEntry 25 }


fibTmuPortsAllowedAddrLoaded  OBJECT-TYPE
    SYNTAX    INTEGER {
              addr-not-loaded(1),
              loaded-not-active(2),
              loaded-and-active(3)
              }
    ACCESS    read-write
    STATUS    mandatory
    DESCRIPTION
              "This is the status of fibTmuPortsAllowedAddr.
               When reading, the possible values are as follows:
               addr-not-loaded indicates the value in
                 fibTmuPortsAllowedAddr is meaningless. No
                 security address has been loaded for this port.
               loaded-not-active indicates the value in
                 fibTmuPortsAllowedAddr is stored in non
                 volatile memory but security action for this
                 port is not active. This happens when address
                 is loaded while security action for the
                 Tmu system is disabled (fibTmuSecurityModeRun
                 has bit0 reset).
               loaded-and-active indicates the value in
                 fibTmuPortsAllowedAddr is loaded in non
                 volatile memory and security is active on
                 this port. This means that if a station is
                 directly connected to this port then it must
                 have the specified physical address or this
                 port will automatically close.
               As for writing, this object can be written
               only if its value is either 'loaded-not-active'
               or 'loaded-and-active' and the only value
               allowed is addr-not-loaded. In that case,
               'fibTmuPortsAllowedAddr' is erased from the
               non-volatile memory and 'fibTmuNumStationLeft'
               is incremented. If port has been closed
               because of security (fibTmuPortsPortStatus had
               bit9 set) then it will open (provided it has not
               been closed because of some other reason)."
    ::= { fibTmuPortsTauEntry 26 }
-- =============================================
--
--Tmu-Tau Ports Group
--
--A list of all ports on attached Tau's and
--of ports on Tmu which carry one station.
--Including information on each port.
--
-- =============================================

fibTmuPortsAllTable OBJECT-TYPE
    SYNTAX    SEQUENCE OF FibTmuPortsAllEntry
    ACCESS    not-accessible
    STATUS    mandatory
    DESCRIPTION
              "Table containing information on ports
              which are directly connected to stations
              and on Tau ports which may be connected
              to stations."
    ::= { tmuPorts 30 }

fibTmuPortsAllEntry OBJECT-TYPE
    SYNTAX    FibTmuPortsAllEntry
    ACCESS    not-accessible
    STATUS    mandatory
    DESCRIPTION
              "Entry of information concerning a single
              port on Tmu or on Tau."
    INDEX     { fibTmuPortsTmuPortIndex,
                fibTmuPortsTauPortIndex }
    ::= { fibTmuPortsAllTable 1 }


FibTmuPortsAllEntry
    ::= SEQUENCE {
              fibTmuPortsTmuPortIndex
                    INTEGER,
              fibTmuPortsTauPortIndex
                    INTEGER,
              fibTmuPortsPortState
                    INTEGER,
              fibTmuPortsGenCloseRun
                    INTEGER,
              fibTmuPortsGenClosePerm
                    INTEGER,
              fibTmuPortsPhysAddr
                    MacAddress,
              fibTmuPortsStationInfo
                    INTEGER,
              fibTmuPortsTauAllowedAddr
                    MacAddress,
              fibTmuPortsTauAllowedAddrLoaded
                    INTEGER
              }


fibTmuPortsTmuPortIndex  OBJECT-TYPE
    SYNTAX    INTEGER
    ACCESS    read-only
    STATUS    mandatory
    DESCRIPTION
              "Number of port on Tmu. Port numbers
               increase in the direction of the token.
               range of valid values:
               1->fibTmuPortsNumTausPerTmu"
    ::= { fibTmuPortsAllEntry 1 }

fibTmuPortsTauPortIndex  OBJECT-TYPE
    SYNTAX    INTEGER
    ACCESS    read-only
    STATUS    mandatory
    DESCRIPTION
              "Number of port on Tau. Port numbers
               increase in the direction of the token.
               range of valid values:
               1->fibTmuPortsNumTausPerTau"
    ::= { fibTmuPortsAllEntry 2 }


fibTmuPortsPortState  OBJECT-TYPE
    SYNTAX    INTEGER
    ACCESS    read-only
    STATUS    mandatory
    DESCRIPTION
              "Bit map describing the indicated port:
                 Bit1 (0x02)  -
                   No such port. Index is out of bounds.
                   Either a Tau is connected and the specified
                   port number is larger than the number
                   of ports on the Tau currently connected
                   or a single station is directly attached and
                   the specified port number is larger than
                   1.
                 Bit2 (0x04)  -
                   It has not yet been determined what is
                   connected to the specified Tmu port. It
                   may later be found to be either a single
                   station of a Tau.
                 Bit3 (0x08)  -
                   Port is attached. This means that the token
                   ring goes through the station related to
                   this port.
                 Bit4 (0x10)  -
                   Phantom signal is 'on' for this port.
                 Bit5 (0x20)  -
                   Port is detached because of a request
                   from manager.
                 Bit6 (0x40)  -
                   Port is temporarily detached because
                   of a temporary error or because it is
                   in a transition state.
                 Bit7 (0x80)  -
                   Port is detached because of an error and
                   will remain so until phantom goes down and
                   up again.
                 Bit8 (0x100) -
                   Port is a Tmu port attached to a single
                   station.
                 Bit9 (0x200)  -
                   Port is detached because of security
                   violation and will remain so until phantom
                   goes down and up again or until manager
                   releases the lock."
    ::= { fibTmuPortsAllEntry 3 }


fibTmuPortsGenCloseRun OBJECT-TYPE
    SYNTAX    INTEGER {
                  open(1),
                  close(2)
              }
    ACCESS    read-write
    STATUS    mandatory
    DESCRIPTION
              "When setting this object to the value of close (2)
               the indicated port on Tau will be closed, the
               related led will start blinking at a slow rate and
               port will not be opened before it is set to the value
               of open (1). Setting to the value of open (1)
               does not guarantee the opening of the indicated
               Tau port but will only allow the Tmu system to
               let this port into the ring if it obeys the rules
               of token ring. Reading this object returns the value
               last set by the manager (or the default value). This
               command holds only until the next system reset. To
               make sure it remains valid after reset, use
               'fibTmuPortsGenClosePerm'.
               This command only affects ports on Tau. If there is
               no Tau attached when command is issued, then it is
               stored in memory and goes into effect when a Tau
               is attached. This command will have no effect of
               a station directly attached to the Tmu. To detach
               a directly attached station, use
               'fibTmuPortsManagerCloseRun' (See above)."
    ::= { fibTmuPortsAllEntry 4 }
    
fibTmuPortsGenClosePerm OBJECT-TYPE
    SYNTAX    INTEGER {
                  open(1),
                  close(2)
              }
    ACCESS    read-write
    STATUS    mandatory
    DESCRIPTION
              "When setting this object to the value of close (2)
               the indicated port on Tau is instructed to be
               closed after the next reset. Setting to the value
               of open (1) does not guarantee the opening of the
               indicated Tau port after the next reset but will
               only allow the Tmu system to let this port into
               the ring if it obeys the rules of token ring.
               Reading this object returns the value last set
               by the manager (or the default value).
               This command only affects ports on Tau. If there is
               no Tau attached at startup (after reset), then it is
               stored in memory and goes into effect when a Tau
               is attached. This command will have no effect of
               a station directly attached to the Tmu. To permanently
               detach a directly attached station, use
               'fibTmuPortsManagerClosePerm' (See above)."
    ::= { fibTmuPortsAllEntry 5 }


fibTmuPortsPhysAddr  OBJECT-TYPE
    SYNTAX    MacAddress
    ACCESS    read-only
    STATUS    mandatory
    DESCRIPTION
              "The token ring physical address of the
               station which is attached to the specified
               port. If station is not identified (e.g.
               fibTmuMatchListValid, see above, is
               not 'TRUE') then a string of 0xFF characters
               is returned."
    ::= { fibTmuPortsAllEntry 6 }

fibTmuPortsStationInfo OBJECT-TYPE
    SYNTAX    INTEGER
    ACCESS    read-only
    STATUS    mandatory
    DESCRIPTION
              "Information on the attached station:
               If BIT0 is set (value = 0x01) then this is definitely
                 a 'sniffer' port (i.e. a station which is sending
                 'trace tool present' messages is located on this port).
               If BIT1 is set (value = 0x02) then its location
                 is doubtful (System has been unable to resolve
                 the location of this station).
               If BIT2 is set (value = 0x04) then station is not
                 attached to one of the tmu's ports but rather to
                 the trunk.
               If bit3 is set (value = 0x08) then station is one of
                 the tmu's chips.
               If BIT4 is set (value = 0x10) then this is a station
                 attached to the tmu (and not on the trunk).
               If station is not identified (e.g.
               fibTmuMatchListValid, see above, is not 'TRUE')
               then -1 (0xFFFFFFFF) is returned."
    ::= { fibTmuPortsAllEntry 7 }

fibTmuPortsTauAllowedAddr  OBJECT-TYPE
    SYNTAX    MacAddress
    ACCESS    read-write
    STATUS    mandatory
    DESCRIPTION
              "This is the one physical address allowed
               to be on this port on Tau.
               The value loaded in fibTmuPortsTauAllowedAddrLoaded
               below determines the state of this object.
               Writing to this object stores the address
               in non-volatile memory. It also makes
               security on this port active provided
               fibTmuSecurityModeRun has bit0 set. Loading
               will not be carried out if fibTmuNumStationLeft
               is 0 (no more space in non-volatile memory). In
               that case, an error will be returned
               (genErr = 5).
               This command only affects ports on Tau. If there is
               no Tau attached when command is issued, then it is
               stored in memory and goes into effect when a Tau
               is attached. This command will have no effect of
               a station directly attached to the Tmu. To affect
               such ports, use 'fibTmuPortsAllowedAddr'"
    ::= { fibTmuPortsAllEntry 8 }


fibTmuPortsTauAllowedAddrLoaded  OBJECT-TYPE
    SYNTAX    INTEGER {
              addr-not-loaded(1),
              loaded-not-active(2),
              loaded-and-active(3)
              }
    ACCESS    read-write
    STATUS    mandatory
    DESCRIPTION
              "This is the status of fibTmuPortsTauAllowedAddr.
               When reading, the possible values are as follows:
               addr-not-loaded indicates the value in
                 fibTmuPortsTauAllowedAddr is meaningless. No
                 security address has been loaded for this port.
               loaded-not-active indicates the value in
                 fibTmuPortsTauAllowedAddr is stored in non
                 volatile memory but security action for this
                 port is not active. This happens when address
                 is loaded while security action for the
                 Tmu system is disabled (fibTmuSecurityModeRun
                 has bit0 reset).
               loaded-and-active indicates the value in
                 fibTmuPortsTauAllowedAddr is loaded in non
                 volatile memory and security is active on
                 this port. This means that if a station is
                 directly connected to this port then it must
                 have the specified physical address or this
                 port will automatically close.
               As for writing, this object can be written
               only if its value is either 'loaded-not-active'
               or 'loaded-and-active' and the only value
               allowed is addr-not-loaded. In that case,
               'fibTmuPortsTauAllowedAddr' is erased from the
               non-volatile memory and 'fibTmuNumStationLeft'
               is incremented. If port has been closed
               because of security (fibTmuPortsPortState had
               bit9 set) then it will open (provided it has not
               been closed because of some other reason).
               This command only affects ports on Tau. If there is
               no Tau attached when command is issued, then it is
               stored in memory and goes into effect when a Tau
               is attached. This command will have no effect of
               a station directly attached to the Tmu. To affect
               such ports, use 'fibTmuPortsAllowedAddrLoaded'"
    ::= { fibTmuPortsAllEntry 9 }
-- =============================================
--
--Tmu Production Group
--
-- A list of all parameters related to hardware
-- configuration including the 48 bit addresses.
--
-- =============================================

fibTmuProductionAddr48No1  OBJECT-TYPE
    SYNTAX    MacAddress
    ACCESS    read-write
    STATUS    mandatory
    DESCRIPTION
              "48 bit address of the chip set which is
               located at the primary in port."
    ::= { tmuProduction 1 }

fibTmuProductionAddr48No2  OBJECT-TYPE
    SYNTAX    MacAddress
    ACCESS    read-write
    STATUS    mandatory
    DESCRIPTION
              "48 bit address of the chip set which is
               located at the primary out port."
    ::= { tmuProduction 2 }

fibTmuProductionAddr48No3  OBJECT-TYPE
    SYNTAX    MacAddress
    ACCESS    read-write
    STATUS    mandatory
    DESCRIPTION
              "48 bit address of the chip set which is
               located at the secondary ring port."
    ::= { tmuProduction 3 }

fibTmuProductionRomType  OBJECT-TYPE
    SYNTAX    INTEGER {
                  unknown(1),
                  rom-27c020(2),
                  rom-27c040(3)
              }
    ACCESS    read-write
    STATUS    mandatory
    DESCRIPTION
              "Type of EPROM used in the Tmu system."
    ::= { tmuProduction 4 }

fibTmuProductionRamType  OBJECT-TYPE
    SYNTAX    INTEGER {
                  unknown(1),
                  ram-128k8(2)
              }
    ACCESS    read-write
    STATUS    mandatory
    DESCRIPTION
              "Type of RAM used in the Tmu system."
    ::= { tmuProduction 5 }

fibTmuProductionFlashType  OBJECT-TYPE
    SYNTAX    INTEGER {
                  unknown(1),
                  flash-28f010(2),
                  flash-28f020(3),
                  flash-29f010(4),
                  flash-29f040(5)
              }
    ACCESS    read-write
    STATUS    mandatory
    DESCRIPTION
              "Type of FLASH used in the Tmu system."
    ::= { tmuProduction 6 }

fibTmuProductionEepromType  OBJECT-TYPE
    SYNTAX    INTEGER {
                  unknown(1),
                  with-page-mode(2),
                  without-page-mode(3)
              }
    ACCESS    read-write
    STATUS    mandatory
    DESCRIPTION
              "Type of EEPROM used in the Tmu system."
    ::= { tmuProduction 7 }

fibTmuProductionSerialNum  OBJECT-TYPE
    SYNTAX    OCTET STRING (SIZE (3))
    ACCESS    read-write
    STATUS    mandatory
    DESCRIPTION
              "Serial number of Tmu HW system."
    ::= { tmuProduction 8 }

fibTmuProductionRamSize  OBJECT-TYPE
    SYNTAX    INTEGER (3..64)
    ACCESS    read-write
    STATUS    mandatory
    DESCRIPTION
              "Size of RAM used in the Tmu system
               in units of 32K bytes. A value of '3' indicates
               size is not known."
    ::= { tmuProduction 9 }

fibTmuProductionFlash0Size  OBJECT-TYPE
    SYNTAX    INTEGER (3..64)
    ACCESS    read-write
    STATUS    mandatory
    DESCRIPTION
              "Size of FLASH memory bank #0 used in
               the Tmu system in units of 32K bytes.
               A value of '3' indicates size is not known."
    ::= { tmuProduction 10 }

fibTmuProductionFlash1Size  OBJECT-TYPE
    SYNTAX    INTEGER (2..64)
    ACCESS    read-write
    STATUS    mandatory
    DESCRIPTION
              "Size of FLASH memory bank #1 used in
               the Tmu system in units of 32K bytes.
               A value of '3' indicates size is not known.
               A value of '2' indicates chip is not
               installed."
    ::= { tmuProduction 11 }

fibTmuProductionEepromSize  OBJECT-TYPE
    SYNTAX    INTEGER (3..64)
    ACCESS    read-write
    STATUS    mandatory
    DESCRIPTION
              "Size of EEPROM memory used in
               the Tmu system in units of 0.5K bytes.
               A value of '3' indicates size is not known."
    ::= { tmuProduction 12 }

fibTmuProductionHwInfo  OBJECT-TYPE
    SYNTAX    OCTET STRING (SIZE (4))
    ACCESS    read-write
    STATUS    mandatory
    DESCRIPTION
              "General encoded information concerning
               Tmu system's hardware."
    ::= { tmuProduction 13 }

fibTmuProductionBoardType OBJECT-TYPE
	SYNTAX  INTEGER {
				unknown(1),
				board-9230(2),
				board-9230-16(3),
				board-9230-32(4),
				board-9230-16F(5),
				board-9230-32F(6),
				board-9232-16(7),
				board-9232-32(8)
				}
	ACCESS  read-only
	STATUS  mandatory
	DESCRIPTION
			"Type of TMU Board."
	::= { tmuProduction 14}

-- =============================================
--
--Tmu Security Group
--
-- A list of all parameters related to security
-- features built into the Tmu.
--
-- =============================================

fibTmuSecurityModeRun OBJECT-TYPE
    SYNTAX    INTEGER
    ACCESS    read-only
    STATUS    mandatory
    DESCRIPTION
              "The currently effective security
               mode. This is a bit map. This object
               is only loaded once after reset.
               To change it, fibTmuSecurityModeRun
               must be loaded and then system must be
               reset.
               BIT(0) - Station security. If set then
                 some ports are marked as being allowed
                 to have only specific stations (station
                 per port). The list of port is
                 specified below.
               REST - T.B.D."
    ::= { tmuSecurity 1 }

fibTmuSecurityModePerm  OBJECT-TYPE
    SYNTAX    INTEGER
    ACCESS    read-write
    STATUS    mandatory
    DESCRIPTION
              "The value currently in non volatile
               memory of the security mode. This is
               a bit map. See detals in fibTmuSecurityModeRun
               above. This object is only loaded into
               fibTmuSecurityModeRun once after reset.
               Changing it effects the system only after
               reset."
    ::= { tmuSecurity 2 }

fibTmuNumStationSecurity  OBJECT-TYPE
    SYNTAX    INTEGER
    ACCESS    read-only
    STATUS    mandatory
    DESCRIPTION
              "Maximal number of ports for which the
               security mode 'station security' (see
               fibTmuSecurityModeRun above) can be
               specified."
    ::= { tmuSecurity 3 }

fibTmuNumStationLeft  OBJECT-TYPE
    SYNTAX    INTEGER
    ACCESS    read-only
    STATUS    mandatory
    DESCRIPTION
              "Number of ports for which the
               security mode 'station security' (see
               fibTmuSecurityModeRun above) can still
               be specified. This is the difference
               between 'fibTmuNumStationSecurity' and
               the number of port for which the allowed
               station has already been specified."
    ::= { tmuSecurity 4 }

-- =============================================
--
--Tmu Function Group
--
-- A list of all parameters related to cau functionality
-- features built into the Tmu.
--
-- =============================================

-- =============================================
--
--Tmu Function Group - run time variables
--
-- =============================================
fibTmuFunctBeacon2AutotestRun  OBJECT-TYPE
    SYNTAX    INTEGER (160..200)
    ACCESS    read-only
    STATUS    mandatory
    DESCRIPTION
              "The time period for starting the
               'autoremove' test after start of
               beaconing. In units of milliseconds.
               Minimal value: 160. maximal value 200.
               Factory default: 160.
               To change this object, load
               'fibTmuFunctBeacon2AutotestPerm'
               into non-volatile ram.
               The value written into non volatile memory
               is loaded into the current value only
               after reset."
    ::= { fibTmuFunctRtpGrpVrsRun 1 }

fibTmuFunctBeacon2OkRun  OBJECT-TYPE
    SYNTAX    INTEGER (40..200)
    ACCESS    read-only
    STATUS    mandatory
    DESCRIPTION
              "The upper bound for time period starting
               at the removal of a problem till ring status
               indicates no beaconing. In units of milliseconds.
               Minimal value: 40. maximal value 200.
               Factory default: 50.
               To change this object, load
               'fibTmuFunctBeacon2OkPerm'
               into non-volatile ram.
               The value written into non volatile memory
               is loaded into the current value only
               after reset."
    ::= { fibTmuFunctRtpGrpVrsRun 2 }

fibTmuFunctOk2BeaconRun  OBJECT-TYPE
    SYNTAX    INTEGER (1100..2500)
    ACCESS    read-only
    STATUS    mandatory
    DESCRIPTION
              "The upper bound for time period starting
               at the insertion of a problem till ring status
               indicates beaconing. In units of milliseconds.
               Minimal value: 1100. maximal value 2500.
               Factory default: 2000.
               To change this object, load
               'fibTmuFunctOk2BeaconPerm'
               into non-volatile ram.
               The value written into non volatile memory
               is loaded into the current value only
               after reset."
    ::= { fibTmuFunctRtpGrpVrsRun 3 }


fibTmuFunctWrapCwtRun  OBJECT-TYPE
    SYNTAX    INTEGER (0..200)
    ACCESS    read-only
    STATUS    mandatory
    DESCRIPTION
              "Time delay to apply, after changing warp
               relay state. In units of milliseconds.
               Intended to let TMS get the real ring status.
               Minimal value: 0. maximal value 200.
               Factory default: 100.
               To change this object, load
               'fibTmuFunctWrapCwtPerm'
               into non-volatile ram.
               The value written into non volatile memory
               is loaded into the current value only
               after reset."
    ::= { fibTmuFunctRtpGrpVrsRun 4 }

fibTmuFunctWrapWnrRun  OBJECT-TYPE
    SYNTAX    INTEGER {
                  wnr-dont-release-cpu(1),
                  wnr-release-cpu(2)
              }
    ACCESS    read-only
    STATUS    mandatory
    DESCRIPTION
              "Flag indicating whether to release CPU
               while waiting after warp change.
               Values: 1 - FALSE, 2 - TRUE.
               Factory default: TRUE.
               To change this object, load
               'fibTmuFunctWrapWnrPerm'
               into non-volatile ram.
               The value written into non volatile memory
               is loaded into the current value only
               after reset."
    ::= { fibTmuFunctRtpGrpVrsRun 5 }

fibTmuFunctRingIstRun  OBJECT-TYPE
    SYNTAX    INTEGER (0..200)
    ACCESS    read-only
    STATUS    mandatory
    DESCRIPTION
              "Time to poll for consistent Tmu ring
               status before continuing recovery.
               In units of milliseconds.
               Minimal value: 0. maximal value 200.
               Factory default: 0
               To change this object, load
               'fibTmuFunctRingIstPerm'
               into non-volatile ram.
               The value written into non volatile memory
               is loaded into the current value only
               after reset."
    ::= { fibTmuFunctRtpGrpVrsRun 6 }


fibTmuFunctRingIstnrRun  OBJECT-TYPE
    SYNTAX    INTEGER {
                  istnr-dont-release-cpu(1),
                  istnr-release-cpu(2)
              }
    ACCESS    read-only
    STATUS    mandatory
    DESCRIPTION
              "Flag indicating whether to release CPU
               while waiting for consistent Tmu ring
               status.
               Values: 1 - FALSE, 2 - TRUE.
               Factory default: TRUE.
               To change this object, load
               'fibTmuFunctRingIstnrPerm'
               into non-volatile ram.
               The value written into non volatile memory
               is loaded into the current value only
               after reset."
    ::= { fibTmuFunctRtpGrpVrsRun 7 }

fibTmuFunctCheckAogTauRun  OBJECT-TYPE
    SYNTAX    INTEGER {
                  dont-check-ring(1),
                  check-ring(2)
              }
    ACCESS    read-only
    STATUS    mandatory
    DESCRIPTION
              "Flag is used during BRUTAL recovery (single
               problem). If TRUE (checck-ring) then check whether
               the ring is BEACONING after opening the good TAU's
               (This check takes fibTmuFunctOk2BeaconRun milli sec.
               and not needed in most cases).
               Values: 1 - FALSE, 2 - TRUE.
               Factory default: FALSE.
               To change this object, load
               'fibTmuFunctCheckAogTauPerm'
               into non-volatile ram.
               The value written into non volatile memory
               is loaded into the current value only
               after reset."
    ::= { fibTmuFunctRtpGrpVrsRun 8 }


fibTmuFunctMaxNoiRun  OBJECT-TYPE
    SYNTAX    INTEGER (0..300)
    ACCESS    read-only
    STATUS    mandatory
    DESCRIPTION
              "When several station wants to insert into
               the ring, this parameter sets the limit on
               the maximal number of stations which are
               allowed to insert (other stations are delayed
               until the next round).
               If 0 then enable all stations are allowed to
               insert.
               Minimal value: 0. maximal value 300.
               Factory default: 1
               To change this object, load
               'fibTmuFunctRingIstPerm'
               into non-volatile ram.
               The value written into non volatile memory
               is loaded into the current value only
               after reset."
    ::= { fibTmuFunctRtpGrpVrsRun 9 }

fibTmuFunctLinkPtifRun  OBJECT-TYPE
    SYNTAX    INTEGER {
                  dont-link-to-last(1),
                  link-to-last(2)
              }
    ACCESS    read-only
    STATUS    mandatory
    DESCRIPTION
              "When problem in TMU segment is discovered
               then if this flag is TRUE, first of all
               try to find problem between last inserted
               stations.
               Values: 1 - FALSE, 2 - TRUE.
               Factory default: TRUE.
               To change this object, load
               'fibTmuFunctLinkPtifPerm'
               into non-volatile ram.
               The value written into non volatile memory
               is loaded into the current value only
               after reset."
    ::= { fibTmuFunctRtpGrpVrsRun 10 }

fibTmuFunctInsPatRun  OBJECT-TYPE
    SYNTAX    INTEGER (1500..4000)
    ACCESS    read-only
    STATUS    mandatory
    DESCRIPTION
              "Parameter for controlling the aging of the
               'inseretion-pool' (Should be long enough to
               make sure that the station is not malfunctioning).
               Units: milli seconds.
               Minimal value: 1500. maximal value 4000.
               Factory default: 3000
               To change this object, load
               'fibTmuFunctInsPatPerm'
               into non-volatile ram.
               The value written into non volatile memory
               is loaded into the current value only
               after reset."
    ::= { fibTmuFunctRtpGrpVrsRun 11 }


fibTmuFunctUseMismatchRun  OBJECT-TYPE
    SYNTAX    INTEGER {
                  dont-use-mismatch(1),
                  use-mismatch(2)
              }
    ACCESS    read-only
    STATUS    mandatory
    DESCRIPTION
              "Indication on whether to apply recovery
               when the number of stations is larger than
               the number of open ports.
               Values: 1 - FALSE, 2 - TRUE.
               Factory default: TRUE.
               To change this object, load
               'fibTmuFunctUseMismatchPerm'
               into non-volatile ram.
               The value written into non volatile memory
               is loaded into the current value only
               after reset."
    ::= { fibTmuFunctRtpGrpVrsRun 12 }

fibTmuFunctChkRingInsRun  OBJECT-TYPE
    SYNTAX    INTEGER {
                  dont-check-ring(1),
                  check-ring(2)
              }
    ACCESS    read-only
    STATUS    mandatory
    DESCRIPTION
              "Indication on whether to check ring status
               (for possible problems caused by the currently
               inserted stations) or not. Setting 'TRUE' results
               in quicker discovery of stations with invalid
               frequency but inflicts higher overhead on
               legitimate frequency stations.
               Values: 1 - FALSE, 2 - TRUE.
               Factory default: FALSE.
               To change this object, load
               'fibTmuFunctChkRingInsPerm'
               into non-volatile ram.
               The value written into non volatile memory
               is loaded into the current value only
               after reset."
    ::= { fibTmuFunctRtpGrpVrsRun 13 }


fibTmuFunctChkRingPerRun  OBJECT-TYPE
    SYNTAX    INTEGER (1500..4000)
    ACCESS    read-only
    STATUS    mandatory
    DESCRIPTION
              "Parameter indicating the elapsed time after
               letting a station into the ring after which
               a station is considered to be o.k. See
               'fibTmuFunctChkRingInsRun'
               Units: milli seconds.
               Minimal value: 1500. maximal value 4000.
               Factory default: 3000
               To change this object, load
               'fibTmuFunctChkRingPerPerm'
               into non-volatile ram.
               The value written into non volatile memory
               is loaded into the current value only
               after reset."
    ::= { fibTmuFunctRtpGrpVrsRun 14 }

fibTmuFunctClaimTimeOutRun  OBJECT-TYPE
    SYNTAX    INTEGER (150..500)
    ACCESS    read-only
    STATUS    mandatory
    DESCRIPTION
              "Parameter indicating the elapsed time between
               the detection of a problem and the beginning
               of sending 'claim'.
               Units: milli seconds.
               Minimal value: 150. maximal value 500.
               Factory default: 250
               To change this object, load
               'fibTmuFunctClaimTimeOutPerm'
               into non-volatile ram.
               The value written into non volatile memory
               is loaded into the current value only
               after reset."
    ::= { fibTmuFunctRtpGrpVrsRun 15 }

fibTmuFunctAnotherCheckRun  OBJECT-TYPE
    SYNTAX    INTEGER {
                  no-another-check(1),
                  another-check(2)
              }
    ACCESS    read-only
    STATUS    mandatory
    DESCRIPTION
              "Indication on whether to perform another
               check before disabling a port as a cross check.
               Values: 1 - FALSE, 2 - TRUE.
               Factory default: FALSE.
               To change this object, load
               'fibTmuFunctAnotherCheckPerm'
               into non-volatile ram.
               The value written into non volatile memory
               is loaded into the current value only
               after reset."
    ::= { fibTmuFunctRtpGrpVrsRun 16 }


fibTmuFunctTmsOnOutRun  OBJECT-TYPE
    SYNTAX    INTEGER (1..2)
    ACCESS    read-only
    STATUS    mandatory
    DESCRIPTION
              "Parameter indicating the tms to leave out
               of the ring when carrying out 'warp out':
               It could be TMS no. 2 (TMS OUT) or the TMS
               which is on the secondary ring.
               values: (TMS OUT) 1, (TMS SECONDARY) 2
               Factory default: (TMS OUT) 1
               To change this object, load
               'fibTmuFunctTmsOnOutPerm'
               into non-volatile ram.
               The value written into non volatile memory
               is loaded into the current value only
               after reset."
    ::= { fibTmuFunctRtpGrpVrsRun 17 }

fibTmuFunctUseJitterRun  OBJECT-TYPE
    SYNTAX    INTEGER {
                  no-jitter-buster(1),
                  use-jitter-buster(2)
              }
    ACCESS    read-only
    STATUS    mandatory
    DESCRIPTION
              "Indication on whether to use the jitter buster
               hardware module or not.
               Values: 1 - FALSE, 2 - TRUE.
               Factory default: TRUE.
               To change this object, load
               'fibTmuFunctUseJitterPerm'
               into non-volatile ram.
               The value written into non volatile memory
               is loaded into the current value only
               after reset."
    ::= { fibTmuFunctRtpGrpVrsRun 18 }


fibTmuFunctForceStpRiRun  OBJECT-TYPE
    SYNTAX    INTEGER {
                  do-not-force-ri-stp(1),
                  force-ri-stp(2)
              }
    ACCESS    read-only
    STATUS    mandatory
    DESCRIPTION
              "This object is used to control the type of the
               trunk (OPTIC or STP). Algorithm:
               if (optic-module-exists && do-not-force-ri-stp)
               {
                 ri-trunk-type = OPTIC ;
               }
               else
               {
                 /*
                  * This is the case of: NO-OPTIC-MODULE or
                  * FORCING-THE-TRUNK-TO-STP
                  */
                 ri-trunk-type = STP ;
               }
               Factory default: FALSE (1).
               To change this object, load
               'fibTmuFunctForceStpRiPerm'
               into non-volatile ram.
               The value written into non volatile memory
               is loaded into the current value only
               after reset."
    ::= { fibTmuFunctRtpGrpVrsRun 21 }


fibTmuFunctForceStpRoRun  OBJECT-TYPE
    SYNTAX    INTEGER {
                  do-not-force-ro-stp(1),
                  force-ro-stp(2)
              }
    ACCESS    read-only
    STATUS    mandatory
    DESCRIPTION
              "This object is used to control the type of the
               trunk (OPTIC or STP). Algorithm:
               if (optic-module-exists && do-not-force-ro-stp)
               {
                 ro-trunk-type = OPTIC ;
               }
               else
               {
                 /*
                  * This is the case of: NO-OPTIC-MODULE or
                  * FORCING-THE-TRUNK-TO-STP
                  */
                 ro-trunk-type = STP ;
               }
               Factory default: FALSE (1).
               To change this object, load
               'fibTmuFunctForceStpRoPerm'
               into non-volatile ram.
               The value written into non volatile memory
               is loaded into the current value only
               after reset."
    ::= { fibTmuFunctRtpGrpVrsRun 22 }

fibTmuFunctMaxSavRecRun  OBJECT-TYPE
    SYNTAX    INTEGER (5..20)
    ACCESS    read-only
    STATUS    mandatory
    DESCRIPTION
              "Parameter indicating how many elements
               to save in the fifo buffer of containing
               the history of recovery.
               Minimal value: 5. maximal value 20.
               Factory default: 20
               To change this object, load
               'fibTmuFunctMaxSavRecPerm'
               into non-volatile ram.
               The value written into non volatile memory
               is loaded into the current value only
               after reset."
    ::= { fibTmuFunctRtpGrpVrsRun 23 }

fibTmuFunctReadPerRun  OBJECT-TYPE
    SYNTAX    INTEGER (0..5000)
    ACCESS    read-only
    STATUS    mandatory
    DESCRIPTION
              "Parameter indicating the elapsed time between
               two readings of the error counter of a TMS.
               Too large a period may result in counter
               overflow. A value of '0' indicates 'read
               every TR driver poll'
               Units: milli seconds.
               Minimal value: 0. maximal value 5000.
               Factory default: 5000.
               To change this object, load
               'fibTmuFunctReadPerPerm'
               into non-volatile ram.
               The value written into non volatile memory
               is loaded into the current value only
               after reset."
    ::= { fibTmuFunctRtpGrpVrsRun 24 }


fibTmuFunctDmaThreshRun  OBJECT-TYPE
    SYNTAX    INTEGER (0..30)
    ACCESS    read-only
    STATUS    mandatory
    DESCRIPTION
              "Parameter indicating the number of times DMA
               will attempt retry in case of bus error
               before giving up.
               Minimal value: 0. maximal value 30.
               Factory default: 30.
               To change this object, load
               'fibTmuFunctDmaThreshPerm'
               into non-volatile ram.
               The value written into non volatile memory
               is loaded into the current value only
               after reset."
    ::= { fibTmuFunctRtpGrpVrsRun 25 }

fibTmuFunctRemWrapTypeRun  OBJECT-TYPE
    SYNTAX    INTEGER (1..2)
    ACCESS    read-only
    STATUS    mandatory
    DESCRIPTION
              "Parameter indicating the criterion for
               removing 'wrap': 
               It could be removed when the ring is not
               beaconing and it could be removed when the
               ring is not claiming.
               values: (NOT BEACONING) 1, (NOT CLAIMING) 2
               Factory default: (NOT BEACONING) 1
               To change this object, load
               'fibTmuFunctRemWrapTypePerm'
               into non-volatile ram.
               The value written into non volatile memory
               is loaded into the current value only
               after reset."
    ::= { fibTmuFunctRtpGrpVrsRun 26 }


fibTmuFunctRemWrapLenRun  OBJECT-TYPE
    SYNTAX    INTEGER (0..2000)
    ACCESS    read-only
    STATUS    mandatory
    DESCRIPTION
              "Parameter indicating the elapsed time between
               the time it is decided that wrap can be removed
               and the actual removal. See
               'fibTmuFunctRemWrapTypeRun'.
               Units: milli seconds.
               Minimal value: 0. maximal value 2000.
               Factory default: 0.
               To change this object, load
               'fibTmuFunctRemWrapLenPerm'
               into non-volatile ram.
               The value written into non volatile memory
               is loaded into the current value only
               after reset."
    ::= { fibTmuFunctRtpGrpVrsRun 27 }

-- =============================================
--
--Tmu Function Group - permanent variables
--
-- =============================================
fibTmuFunctBeacon2AutotestPerm  OBJECT-TYPE
    SYNTAX    INTEGER (160..200)
    ACCESS    read-write
    STATUS    mandatory
    DESCRIPTION
              "The time period for starting the
               'autoremove' test after start of
               beaconing. In units of milliseconds.
               Minimal value: 160. maximal value 200.
               Factory default: 160.
               Setting this variable loads it into
               non volatile memory.
               The value written into non volatile memory
               is loaded into the current value only
               after reset."
    ::= { fibTmuFunctRtpGrpVrsPerm 1 }

fibTmuFunctBeacon2OkPerm  OBJECT-TYPE
    SYNTAX    INTEGER (40..200)
    ACCESS    read-write
    STATUS    mandatory
    DESCRIPTION
              "The upper bound for time period starting
               at the removal of a problem till ring status
               indicates no beaconing. In units of milliseconds.
               Minimal value: 40. maximal value 200.
               Factory default: 50.
               Setting this variable loads it into
               non volatile memory.
               The value written into non volatile memory
               is loaded into the current value only
               after reset."
    ::= { fibTmuFunctRtpGrpVrsPerm 2 }

fibTmuFunctOk2BeaconPerm  OBJECT-TYPE
    SYNTAX    INTEGER (1100..2500)
    ACCESS    read-write
    STATUS    mandatory
    DESCRIPTION
              "The upper bound for time period starting
               at the insertion of a problem till ring status
               indicates beaconing. In units of milliseconds.
               Minimal value: 1100. maximal value 2500.
               Factory default: 2000.
               Setting this variable loads it into
               non volatile memory.
               The value written into non volatile memory
               is loaded into the current value only
               after reset."
    ::= { fibTmuFunctRtpGrpVrsPerm 3 }


fibTmuFunctWrapCwtPerm  OBJECT-TYPE
    SYNTAX    INTEGER (0..200)
    ACCESS    read-write
    STATUS    mandatory
    DESCRIPTION
              "Time delay to apply, after changing warp
               relay state. In units of milliseconds.
               Intended to let TMS get the real ring status.
               Minimal value: 0. maximal value 200.
               Factory default: 100.
               Setting this variable loads it into
               non volatile memory.
               The value written into non volatile memory
               is loaded into the current value only
               after reset."
    ::= { fibTmuFunctRtpGrpVrsPerm 4 }

fibTmuFunctWrapWnrPerm  OBJECT-TYPE
    SYNTAX    INTEGER {
                  dont-release-cpu(1),
                  release-cpu(2)
              }
    ACCESS    read-write
    STATUS    mandatory
    DESCRIPTION
              "Flag indicating whether to release CPU
               while waiting after warp change.
               Values: 1 - FALSE, 2 - TRUE.
               Factory default: TRUE.
               Setting this variable loads it into
               non volatile memory.
               The value written into non volatile memory
               is loaded into the current value only
               after reset."
    ::= { fibTmuFunctRtpGrpVrsPerm 5 }

fibTmuFunctRingIstPerm  OBJECT-TYPE
    SYNTAX    INTEGER (0..200)
    ACCESS    read-write
    STATUS    mandatory
    DESCRIPTION
              "Time to poll for consistent Tmu ring
               status before continuing recovery.
               In units of milliseconds.
               Minimal value: 0. maximal value 200.
               Factory default: 0
               Setting this variable loads it into
               non volatile memory.
               The value written into non volatile memory
               is loaded into the current value only
               after reset."
    ::= { fibTmuFunctRtpGrpVrsPerm 6 }


fibTmuFunctRingIstnrPerm  OBJECT-TYPE
    SYNTAX    INTEGER {
                  istnr-dont-release-cpu(1),
                  istnr-release-cpu(2)
              }
    ACCESS    read-write
    STATUS    mandatory
    DESCRIPTION
              "Flag indicating whether to release CPU
               while waiting for consistent Tmu ring
               status.
               Values: 1 - FALSE, 2 - TRUE.
               Factory default: TRUE.
               Setting this variable loads it into
               non volatile memory.
               The value written into non volatile memory
               is loaded into the current value only
               after reset."
    ::= { fibTmuFunctRtpGrpVrsPerm 7 }

fibTmuFunctCheckAogTauPerm  OBJECT-TYPE
    SYNTAX    INTEGER {
                  dont-check-ring(1),
                  check-ring(2)
              }
    ACCESS    read-write
    STATUS    mandatory
    DESCRIPTION
              "Flag is used during BRUTAL recovery (single
               problem). If TRUE (checck-ring) then check whether
               the ring is BEACONING after opening the good TAU's
               (This check takes fibTmuFunctOk2BeaconRun milli sec.
               and not needed in most cases).
               Values: 1 - FALSE, 2 - TRUE.
               Factory default: FALSE.
               Setting this variable loads it into
               non volatile memory.
               The value written into non volatile memory
               is loaded into the current value only
               after reset."
    ::= { fibTmuFunctRtpGrpVrsPerm 8 }


fibTmuFunctMaxNoiPerm  OBJECT-TYPE
    SYNTAX    INTEGER (0..300)
    ACCESS    read-write
    STATUS    mandatory
    DESCRIPTION
              "When several station wants to insert into
               the ring, this parameter sets the limit on
               the maximal number of stations which are
               allowed to insert (other stations are delayed
               until the next round).
               If 0 then enable all stations are allowed to
               insert.
               Minimal value: 0. maximal value 300.
               Factory default: 1
               Setting this variable loads it into
               non volatile memory.
               The value written into non volatile memory
               is loaded into the current value only
               after reset."
    ::= { fibTmuFunctRtpGrpVrsPerm 9 }

fibTmuFunctLinkPtifPerm  OBJECT-TYPE
    SYNTAX    INTEGER {
                  dont-link-to-last(1),
                  link-to-last(2)
              }
    ACCESS    read-write
    STATUS    mandatory
    DESCRIPTION
              "When problem in TMU segment is discovered
               then if this flag is TRUE, first of all
               try to find problem between last inserted
               stations.
               Values: 1 - FALSE, 2 - TRUE.
               Factory default: TRUE.
               Setting this variable loads it into
               non volatile memory.
               The value written into non volatile memory
               is loaded into the current value only
               after reset."
    ::= { fibTmuFunctRtpGrpVrsPerm 10 }

fibTmuFunctInsPatPerm  OBJECT-TYPE
    SYNTAX    INTEGER (1500..4000)
    ACCESS    read-write
    STATUS    mandatory
    DESCRIPTION
              "Parameter for controlling the aging of the
               'inseretion-pool' (Should be long enough to
               make sure that the station is not malfunctioning).
               Units: milli seconds.
               Minimal value: 1500. maximal value 4000.
               Factory default: 3000
               Setting this variable loads it into
               non volatile memory.
               The value written into non volatile memory
               is loaded into the current value only
               after reset."
    ::= { fibTmuFunctRtpGrpVrsPerm 11 }


fibTmuFunctUseMismatchPerm  OBJECT-TYPE
    SYNTAX    INTEGER {
                  dont-use-mismatch(1),
                  use-mismatch(2)
              }
    ACCESS    read-write
    STATUS    mandatory
    DESCRIPTION
              "Indication on whether to apply recovery
               when the number of stations is larger than
               the number of open ports.
               Values: 1 - FALSE, 2 - TRUE.
               Factory default: TRUE.
               Setting this variable loads it into
               non volatile memory.
               The value written into non volatile memory
               is loaded into the current value only
               after reset."
    ::= { fibTmuFunctRtpGrpVrsPerm 12 }

fibTmuFunctChkRingInsPerm  OBJECT-TYPE
    SYNTAX    INTEGER {
                  dont-check-ring(1),
                  check-ring(2)
              }
    ACCESS    read-write
    STATUS    mandatory
    DESCRIPTION
              "Indication on whether to check ring status
               (for possible problems caused by the currently
               inserted stations) or not. Setting 'TRUE' results
               in quicker discovery of stations with invalid
               frequency but inflicts higher overhead on
               legitimate frequency stations.
               Values: 1 - FALSE, 2 - TRUE.
               Factory default: FALSE.
               Setting this variable loads it into
               non volatile memory.
               The value written into non volatile memory
               is loaded into the current value only
               after reset."
    ::= { fibTmuFunctRtpGrpVrsPerm 13 }


fibTmuFunctChkRingPerPerm  OBJECT-TYPE
    SYNTAX    INTEGER (1500..4000)
    ACCESS    read-write
    STATUS    mandatory
    DESCRIPTION
              "Parameter indicating the elapsed time after
               letting a station into the ring after which
               a station is considered to be o.k. See
               'fibTmuFunctChkRingInsPerm'
               Units: milli seconds.
               Minimal value: 1500. maximal value 4000.
               Factory default: 3000
               Setting this variable loads it into
               non volatile memory.
               The value written into non volatile memory
               is loaded into the current value only
               after reset."
    ::= { fibTmuFunctRtpGrpVrsPerm 14 }

fibTmuFunctClaimTimeOutPerm  OBJECT-TYPE
    SYNTAX    INTEGER (150..500)
    ACCESS    read-write
    STATUS    mandatory
    DESCRIPTION
              "Parameter indicating the elapsed time between
               the detection of a problem and the beginning
               of sending 'claim'.
               Units: milli seconds.
               Minimal value: 150. maximal value 500.
               Factory default: 250
               Setting this variable loads it into
               non volatile memory.
               The value written into non volatile memory
               is loaded into the current value only
               after reset."
    ::= { fibTmuFunctRtpGrpVrsPerm 15 }

fibTmuFunctAnotherCheckPerm  OBJECT-TYPE
    SYNTAX    INTEGER {
                  no-another-check(1),
                  another-check(2)
              }
    ACCESS    read-write
    STATUS    mandatory
    DESCRIPTION
              "Indication on whether to perform another
               check before disabling a port as a cross check.
               Values: 1 - FALSE, 2 - TRUE.
               Factory default: FALSE.
               Setting this variable loads it into
               non volatile memory.
               The value written into non volatile memory
               is loaded into the current value only
               after reset."
    ::= { fibTmuFunctRtpGrpVrsPerm 16 }


fibTmuFunctTmsOnOutPerm  OBJECT-TYPE
    SYNTAX    INTEGER (1..2)
    ACCESS    read-write
    STATUS    mandatory
    DESCRIPTION
              "Parameter indicating the tms to leave out
               of the ring when carrying out 'warp out':
               It could be TMS no. 2 (TMS OUT) or the TMS
               which is on the secondary ring.
               values: (TMS OUT) 1, (TMS SECONDARY) 2
               Factory default: (TMS OUT) 1
               Setting this variable loads it into
               non volatile memory.
               The value written into non volatile memory
               is loaded into the current value only
               after reset."
    ::= { fibTmuFunctRtpGrpVrsPerm 17 }

fibTmuFunctUseJitterPerm  OBJECT-TYPE
    SYNTAX    INTEGER {
                  no-jitter-buster(1),
                  use-jitter-buster(2)
              }
    ACCESS    read-write
    STATUS    mandatory
    DESCRIPTION
              "Indication on whether to use the jitter buster
               hardware module or not.
               Values: 1 - FALSE, 2 - TRUE.
               Factory default: TRUE.
               Setting this variable loads it into
               non volatile memory.
               The value written into non volatile memory
               is loaded into the current value only
               after reset."
    ::= { fibTmuFunctRtpGrpVrsPerm 18 }


fibTmuFunctForceStpRiPerm  OBJECT-TYPE
    SYNTAX    INTEGER {
                  do-not-force-ri-stp(1),
                  force-ri-stp(2)
              }
    ACCESS    read-write
    STATUS    mandatory
    DESCRIPTION
              "This object is used to control the type of the
               trunk (OPTIC or STP). Algorithm:
               if (optic-module-exists && do-not-force-ri-stp)
               {
                 ri-trunk-type = OPTIC ;
               }
               else
               {
                 /*
                  * This is the case of: NO-OPTIC-MODULE or
                  * FORCING-THE-TRUNK-TO-STP
                  */
                 ri-trunk-type = STP ;
               }
               Factory default: FALSE (1).
               Setting this variable loads it into
               non volatile memory.
               The value written into non volatile memory
               is loaded into the current value only
               after reset."
    ::= { fibTmuFunctRtpGrpVrsPerm 21 }


fibTmuFunctForceStpRoPerm  OBJECT-TYPE
    SYNTAX    INTEGER {
                  do-not-force-ro-stp(1),
                  force-ro-stp(2)
              }
    ACCESS    read-write
    STATUS    mandatory
    DESCRIPTION
              "This object is used to control the type of the
               trunk (OPTIC or STP). Algorithm:
               if (optic-module-exists && do-not-force-ro-stp)
               {
                 ro-trunk-type = OPTIC ;
               }
               else
               {
                 /*
                  * This is the case of: NO-OPTIC-MODULE or
                  * FORCING-THE-TRUNK-TO-STP
                  */
                 ro-trunk-type = STP ;
               }
               Factory default: FALSE (1).
               Setting this variable loads it into
               non volatile memory.
               The value written into non volatile memory
               is loaded into the current value only
               after reset."
    ::= { fibTmuFunctRtpGrpVrsPerm 22 }

fibTmuFunctMaxSavRecPerm  OBJECT-TYPE
    SYNTAX    INTEGER (5..20)
    ACCESS    read-write
    STATUS    mandatory
    DESCRIPTION
              "Parameter indicating how many elements
               to save in the fifo buffer of containing
               the history of recovery.
               Minimal value: 5. maximal value 20.
               Factory default: 20
               Setting this variable loads it into
               non volatile memory.
               The value written into non volatile memory
               is loaded into the current value only
               after reset."
    ::= { fibTmuFunctRtpGrpVrsPerm 23 }

fibTmuFunctReadPerPerm  OBJECT-TYPE
    SYNTAX    INTEGER (0..5000)
    ACCESS    read-write
    STATUS    mandatory
    DESCRIPTION
              "Parameter indicating the elapsed time between
               two readings of the error counter of a TMS.
               Too large a period may result in counter
               overflow. A value of '0' indicates 'read
               every TR driver poll'
               Units: milli seconds.
               Minimal value: 0. maximal value 5000.
               Factory default: 5000.
               Setting this variable loads it into
               non volatile memory.
               The value written into non volatile memory
               is loaded into the current value only
               after reset."
    ::= { fibTmuFunctRtpGrpVrsPerm 24 }


fibTmuFunctDmaThreshPerm  OBJECT-TYPE
    SYNTAX    INTEGER (0..30)
    ACCESS    read-write
    STATUS    mandatory
    DESCRIPTION
              "Parameter indicating the number of times DMA
               will attempt retry in case of bus error
               before giving up.
               Minimal value: 0. maximal value 30.
               Factory default: 30.
               Setting this variable loads it into
               non volatile memory.
               The value written into non volatile memory
               is loaded into the current value only
               after reset."
    ::= { fibTmuFunctRtpGrpVrsPerm 25 }

fibTmuFunctRemWrapTypePerm  OBJECT-TYPE
    SYNTAX    INTEGER (1..2)
    ACCESS    read-write
    STATUS    mandatory
    DESCRIPTION
              "Parameter indicating the criterion for
               removing 'wrap': 
               It could be removed when the ring is not
               beaconing and it could be removed when the
               ring is not claiming.
               values: (NOT BEACONING) 1, (NOT CLAIMING) 2
               Factory default: (NOT BEACONING) 1
               Setting this variable loads it into
               non volatile memory.
               The value written into non volatile memory
               is loaded into the current value only
               after reset."
    ::= { fibTmuFunctRtpGrpVrsPerm 26 }


fibTmuFunctRemWrapLenPerm  OBJECT-TYPE
    SYNTAX    INTEGER (0..2000)
    ACCESS    read-write
    STATUS    mandatory
    DESCRIPTION
              "Parameter indicating the elapsed time between
               the time it is decided that wrap can be removed
               and the actual removal. See
               'fibTmuFunctRemWrapTypePerm'.
               Units: milli seconds.
               Minimal value: 0. maximal value 2000.
               Factory default: 0.
               Setting this variable loads it into
               non volatile memory.
               The value written into non volatile memory
               is loaded into the current value only
               after reset."

    ::= { fibTmuFunctRtpGrpVrsPerm 27 }

-- =============================================
--
--Tmu Traps
--
-- A list of all specific traps sent by the Tmu
-- system.
--
-- =============================================
--
--fibTmuGenericTrap  TRAP-TYPE
--    ENTERPRISE    tmu
--    VARIABLES { fmDiagTrapInfo }
--    DESCRIPTION
--              "Trap sent if some error condition was
--               encountered for which no trap was assigned.
--               Accompanied by text describing the last
--               generic trap sent by Tmu"
--    ::= 1
--
--fibTmuDownloadTrap  TRAP-TYPE
--    ENTERPRISE    tmu
--    VARIABLES { fmSystemLastSourceIpAddr, fmSystemLastDestinationIpAddr }
--    DESCRIPTION
--              "Trap sent when Tmu system is about to enter
--               a download phase. accompanied by source and
--               destination ip addresses from the last ip          
--               message received by Tmu."
--    ::= 2
--
--fibTmuGeneralTrap  TRAP-TYPE
--    ENTERPRISE    tmu
--    VARIABLES { fmDiagTrapInfo }
--    DESCRIPTION
--              "Trap sent when Tmu system has detected a change
--               in network configuration such as in the list of
--               stations on the token ring or in the list of
--               ports sensing phantom current. Accompanied by
--               text describing the change"
--    ::= 3
--
END
