WS-MGMT-MIB DEFINITIONS ::= BEGIN
 
		IMPORTS
			OBJECT-GROUP, MODULE-COMPLIANCE			
				FROM SNMPv2-CONF			
			IpAddress, Integer32, Unsigned32, OBJECT-TYPE, MODULE-IDENTITY			
				FROM SNMPv2-SMI			
			PhysAddress, DisplayString, TruthValue, RowStatus, DateAndTime			
				FROM SNMPv2-TC			
			wsMgmt			
				FROM WS-SMI			
			DoActionNow			
				FROM WS-TYPE-MIB;

		-- 1.3.6.1.4.1.388.14.4.1
		wsMgmtMib MODULE-IDENTITY 
			LAST-UPDATED "200701261515Z"		-- January 26, 2007 at 15:15 GMT
			ORGANIZATION 
				"Symbol Technologies"
			CONTACT-INFO 
				"Symbol Technologies, Inc.
				Customer Service
				Postal:
				One Symbol Plaza
				Holtsville, NY 11742-1300
				USA
				Tel: +1. 631.738.6213
				E-mail: support@symbol.com
				Web: http://www.symbol.com/support"
			DESCRIPTION 
				"Description."
			REVISION "200701261515Z"		-- January 26, 2007 at 15:15 GMT
			DESCRIPTION 
				"01a32"
			REVISION "200611031430Z"		-- November 03, 2006 at 14:30 GMT
			DESCRIPTION 
				"01a31"
			REVISION "200610061451Z"		-- October 06, 2006 at 14:51 GMT
			DESCRIPTION 
				"01a30"
			REVISION "200609071609Z"		-- September 07, 2006 at 16:09 GMT
			DESCRIPTION 
				"01a29"
			REVISION "200609051659Z"		-- September 05, 2006 at 16:59 GMT
			DESCRIPTION 
				"01a28"
			REVISION "200608191710Z"		-- August 19, 2006 at 17:10 GMT
			DESCRIPTION 
				"01a27"
			REVISION "200606231730Z"		-- June 23, 2006 at 17:30 GMT
			DESCRIPTION 
				"01a26"
			REVISION "200606061035Z"		-- June 06, 2006 at 10:35 GMT
			DESCRIPTION 
				"01a25"
			REVISION "200601061051Z"		-- January 06, 2006 at 10:51 GMT
			DESCRIPTION 
				"01a24"
			REVISION "200512291844Z"		-- December 29, 2005 at 18:44 GMT
			DESCRIPTION 
				"01a23"
			REVISION "200512121347Z"		-- December 12, 2005 at 13:47 GMT
			DESCRIPTION 
				"01a22"
			REVISION "200512050006Z"		-- December 05, 2005 at 00:06 GMT
			DESCRIPTION 
				"01a21"
			REVISION "200511141657Z"		-- November 14, 2005 at 16:57 GMT
			DESCRIPTION 
				"01a20"
			REVISION "200510211630Z"		-- October 21, 2005 at 16:30 GMT
			DESCRIPTION 
				"01a19"
			REVISION "200510201400Z"		-- October 20, 2005 at 14:00 GMT
			DESCRIPTION 
				"01a18"
			REVISION "200509271327Z"		-- September 27, 2005 at 13:27 GMT
			DESCRIPTION 
				"01a16"
			REVISION "200509231621Z"		-- September 23, 2005 at 16:21 GMT
			DESCRIPTION 
				"01a15"
			REVISION "200509221754Z"		-- September 22, 2005 at 17:54 GMT
			DESCRIPTION 
				"01a14"
			REVISION "200509221625Z"		-- September 22, 2005 at 16:25 GMT
			DESCRIPTION 
				"01a13"
			REVISION "200509221450Z"		-- September 22, 2005 at 14:50 GMT
			DESCRIPTION 
				"01a12"
			REVISION "200509211059Z"		-- September 21, 2005 at 10:59 GMT
			DESCRIPTION 
				"01a11"
			REVISION "200509201725Z"		-- September 20, 2005 at 17:25 GMT
			DESCRIPTION 
				"01a10"
			REVISION "200509201144Z"		-- September 20, 2005 at 11:44 GMT
			DESCRIPTION 
				"01a09"
			REVISION "200509191901Z"		-- September 19, 2005 at 19:01 GMT
			DESCRIPTION 
				"01a08"
			REVISION "200509142211Z"		-- September 14, 2005 at 22:11 GMT
			DESCRIPTION 
				"01a07"
			REVISION "200508251141Z"		-- August 25, 2005 at 11:41 GMT
			DESCRIPTION 
				"01a06"
			REVISION "200508181102Z"		-- August 18, 2005 at 11:02 GMT
			DESCRIPTION 
				"01a05"
			REVISION "200508161720Z"		-- August 16, 2005 at 17:20 GMT
			DESCRIPTION 
				"01a04"
			REVISION "200508121414Z"		-- August 12, 2005 at 14:14 GMT
			DESCRIPTION 
				"01a03"
			REVISION "200508121356Z"		-- August 12, 2005 at 13:56 GMT
			DESCRIPTION 
				"01a02"
			REVISION "200507071612Z"		-- July 07, 2005 at 16:12 GMT
			DESCRIPTION 
				"01a01"
			::= { wsMgmt 1 }

		AbbrRowStatus ::= INTEGER
			{
			createAndGo(4),
			destroy(6)
			}

		DoActionShowProgress ::= INTEGER
			{
			doActionRightNow(1),
			idleState(2)
			}

		Password ::= OCTET STRING (SIZE (0..255))

		StaticRowEnable ::= INTEGER
			{
			enable(1),
			disable(2)
			}

		-- 1.3.6.1.4.1.388.14.4.1.1
		wsMgmtReset OBJECT IDENTIFIER ::= { wsMgmtMib 1 }

		-- 1.3.6.1.4.1.388.14.4.1.1.1
		wsMgmtSystemReset OBJECT-TYPE
			SYNTAX INTEGER
				{
				idle(0),
				reset(1),
				shutDown(2)
				}
			MAX-ACCESS read-write
			STATUS current
			DESCRIPTION
				"Description."
			::= { wsMgmtReset 1 }

		-- 1.3.6.1.4.1.388.14.4.1.1.2
		wsMgmtSystemFactoryDefaultCfg OBJECT-TYPE
			SYNTAX DoActionNow
			MAX-ACCESS read-write
			STATUS current
			DESCRIPTION
				"Description."
			::= { wsMgmtReset 2 }

		-- 1.3.6.1.4.1.388.14.4.1.2
		wsMgmtSnmp OBJECT IDENTIFIER ::= { wsMgmtMib 2 }

		-- 1.3.6.1.4.1.388.14.4.1.2.1
		wsMgmtSnmpV2Switch OBJECT-TYPE
			SYNTAX TruthValue
			MAX-ACCESS read-write
			STATUS current
			DESCRIPTION
				"Description."
			::= { wsMgmtSnmp 1 }

		-- 1.3.6.1.4.1.388.14.4.1.2.2
		wsMgmtSnmpV3Switch OBJECT-TYPE
			SYNTAX TruthValue
			MAX-ACCESS read-write
			STATUS current
			DESCRIPTION
				"Description."
			::= { wsMgmtSnmp 2 }

		-- 1.3.6.1.4.1.388.14.4.1.3
		wsMgmtHttp OBJECT IDENTIFIER ::= { wsMgmtMib 3 }

		-- 1.3.6.1.4.1.388.14.4.1.3.1
		wsMgmtHttpEnable OBJECT-TYPE
			SYNTAX TruthValue
			MAX-ACCESS read-write
			STATUS current
			DESCRIPTION
				"Description."
			::= { wsMgmtHttp 1 }

		-- 1.3.6.1.4.1.388.14.4.1.3.2
		wsMgmtHttpsEnable OBJECT-TYPE
			SYNTAX TruthValue
			MAX-ACCESS read-write
			STATUS current
			DESCRIPTION
				"Description."
			::= { wsMgmtHttp 2 }

		-- 1.3.6.1.4.1.388.14.4.1.3.3
		wsMgmtHttpTrustpoint OBJECT-TYPE
			SYNTAX DisplayString
			MAX-ACCESS read-write
			STATUS current
			DESCRIPTION
				"Name of certificate used to secure the https session.
				If defined, the length must be between 2 and 64 characters.
				If null, no certificate is defined."
			::= { wsMgmtHttp 3 }

		-- 1.3.6.1.4.1.388.14.4.1.4
		wsMgmtAlarms OBJECT IDENTIFIER ::= { wsMgmtMib 4 }

		-- 1.3.6.1.4.1.388.14.4.1.4.1
		wsMgmtAlarmTable OBJECT-TYPE
			SYNTAX SEQUENCE OF WsMgmtAlarmEntry
			MAX-ACCESS not-accessible
			STATUS current
			DESCRIPTION
				"Description."
			::= { wsMgmtAlarms 1 }

		-- 1.3.6.1.4.1.388.14.4.1.4.1.1
		wsMgmtAlarmEntry OBJECT-TYPE
			SYNTAX WsMgmtAlarmEntry
			MAX-ACCESS not-accessible
			STATUS current
			DESCRIPTION
				"Description."
			INDEX { wsMgmtAlarmIndex }
			::= { wsMgmtAlarmTable 1 }

		WsMgmtAlarmEntry ::=
			SEQUENCE { 
				wsMgmtAlarmIndex
					Unsigned32,
				wsMgmtAlarmSeverity
					INTEGER,
				wsMgmtAlarmTypeID
					Unsigned32,
				wsMgmtAlarmTypeName
					DisplayString,
				wsMgmtAlarmTimestamp
					DateAndTime,
				wsMgmtAlarmMessage
					DisplayString,
				wsMgmtModuleName
					DisplayString,
				wsMgmtAlarmStatus
					INTEGER,
				wsMgmtAlarmRowStatus
					INTEGER
			 }

		-- 1.3.6.1.4.1.388.14.4.1.4.1.1.1
		wsMgmtAlarmIndex OBJECT-TYPE
			SYNTAX Unsigned32 (1..4294967295)
			MAX-ACCESS read-only
			STATUS current
			DESCRIPTION
				"Simple index."
			::= { wsMgmtAlarmEntry 1 }

		-- 1.3.6.1.4.1.388.14.4.1.4.1.1.2
		wsMgmtAlarmSeverity OBJECT-TYPE
			SYNTAX INTEGER
				{
				critical(0),
				major(1),
				warning(2),
				informational(3),
				normal(4)
				}
			MAX-ACCESS read-only
			STATUS current
			DESCRIPTION
				"Alarm severity."
			::= { wsMgmtAlarmEntry 2 }

		-- 1.3.6.1.4.1.388.14.4.1.4.1.1.3
		wsMgmtAlarmTypeID OBJECT-TYPE
			SYNTAX Unsigned32
			MAX-ACCESS read-only
			STATUS current
			DESCRIPTION
				"Alarm Type ID."
			::= { wsMgmtAlarmEntry 3 }

		-- 1.3.6.1.4.1.388.14.4.1.4.1.1.4
		wsMgmtAlarmTypeName OBJECT-TYPE
			SYNTAX DisplayString
			MAX-ACCESS read-only
			STATUS current
			DESCRIPTION
				"Alarm name."
			::= { wsMgmtAlarmEntry 4 }

		-- 1.3.6.1.4.1.388.14.4.1.4.1.1.5
		wsMgmtAlarmTimestamp OBJECT-TYPE
			SYNTAX DateAndTime
			MAX-ACCESS read-only
			STATUS current
			DESCRIPTION
				"Alarm timestamp."
			::= { wsMgmtAlarmEntry 5 }

		-- 1.3.6.1.4.1.388.14.4.1.4.1.1.6
		wsMgmtAlarmMessage OBJECT-TYPE
			SYNTAX DisplayString
			MAX-ACCESS read-only
			STATUS current
			DESCRIPTION
				"Detailed description of the alarm ."
			::= { wsMgmtAlarmEntry 6 }

		-- 1.3.6.1.4.1.388.14.4.1.4.1.1.7
		wsMgmtModuleName OBJECT-TYPE
			SYNTAX DisplayString
			MAX-ACCESS read-only
			STATUS current
			DESCRIPTION
				"Name of the module which raised this alarm."
			::= { wsMgmtAlarmEntry 7 }

		-- 1.3.6.1.4.1.388.14.4.1.4.1.1.8
		wsMgmtAlarmStatus OBJECT-TYPE
			SYNTAX INTEGER
				{
				acknowledged(1),
				unacknowledged(2)
				}
			MAX-ACCESS read-write
			STATUS current
			DESCRIPTION
				"Status of this Alarm."
			::= { wsMgmtAlarmEntry 8 }

		-- 1.3.6.1.4.1.388.14.4.1.4.1.1.9
		wsMgmtAlarmRowStatus OBJECT-TYPE
			SYNTAX INTEGER
				{
				active(1),
				clear(6)
				}
			MAX-ACCESS read-write
			STATUS current
			DESCRIPTION
				"Setting this column permanently deletes the row from Alarm Log."
			::= { wsMgmtAlarmEntry 9 }

		-- 1.3.6.1.4.1.388.14.4.1.4.2
		wsMgmtClearAllAlarms OBJECT-TYPE
			SYNTAX DoActionNow
			MAX-ACCESS read-write
			STATUS current
			DESCRIPTION
				"Deletes all the rows from Alarm Table."
			::= { wsMgmtAlarms 2 }

		-- 1.3.6.1.4.1.388.14.4.1.4.3
		wsMgmtAcknowledgeAllAlarms OBJECT-TYPE
			SYNTAX DoActionNow
			MAX-ACCESS read-write
			STATUS current
			DESCRIPTION
				"Acknowledges all the alarms."
			::= { wsMgmtAlarms 3 }

		-- 1.3.6.1.4.1.388.14.4.1.4.4
		wsMgmtNewAlarmsCount OBJECT-TYPE
			SYNTAX Unsigned32
			MAX-ACCESS read-only
			STATUS current
			DESCRIPTION
				"Number of new/unacknowledged currently 
				active alarms."
			::= { wsMgmtAlarms 4 }

		-- 1.3.6.1.4.1.388.14.4.1.4.5
		wsMgmtTotalAlarmsCount OBJECT-TYPE
			SYNTAX Unsigned32
			MAX-ACCESS read-only
			STATUS current
			DESCRIPTION
				"Total number of currently active alarms."
			::= { wsMgmtAlarms 5 }

		-- 1.3.6.1.4.1.388.14.4.1.4.6
		wsMgmtTotalAlarmsCountSinceBoot OBJECT-TYPE
			SYNTAX Unsigned32
			MAX-ACCESS read-only
			STATUS current
			DESCRIPTION
				"Total number of alarms that have been 
				generated since system boot. This number
				could be different from wsMgmtTotalAlarmsCount,
				in cases where alarms get deleted from alarm
				log either manually or during alarm-log
				rollover."
			::= { wsMgmtAlarms 6 }

		-- 1.3.6.1.4.1.388.14.4.1.4.7
		wsMgmtAlarmsIndexLow OBJECT-TYPE
			SYNTAX Unsigned32
			MAX-ACCESS read-only
			STATUS current
			DESCRIPTION
				"The index of the oldest currently active 
				alarm in the alarm log."
			::= { wsMgmtAlarms 7 }

		-- 1.3.6.1.4.1.388.14.4.1.4.8
		wsMgmtAlarmsIndexHigh OBJECT-TYPE
			SYNTAX Unsigned32
			MAX-ACCESS read-only
			STATUS current
			DESCRIPTION
				"The index of the newest currently active 
				alarm in the alarm log."
			::= { wsMgmtAlarms 8 }

		-- 1.3.6.1.4.1.388.14.4.1.4.9
		wsMgmCriticalAlarmsCount OBJECT-TYPE
			SYNTAX Unsigned32
			MAX-ACCESS read-only
			STATUS current
			DESCRIPTION
				"Total number of currently active alarms 
				of critical severity."
			::= { wsMgmtAlarms 9 }

		-- 1.3.6.1.4.1.388.14.4.1.4.10
		wsMgmMajorAlarmsCount OBJECT-TYPE
			SYNTAX Unsigned32
			MAX-ACCESS read-only
			STATUS current
			DESCRIPTION
				"Total number of currently active alarms 
				of major severity."
			::= { wsMgmtAlarms 10 }

		-- 1.3.6.1.4.1.388.14.4.1.4.11
		wsMgmWarningAlarmsCount OBJECT-TYPE
			SYNTAX Unsigned32
			MAX-ACCESS read-only
			STATUS current
			DESCRIPTION
				"Total number of currently active alarms 
				of warning severity."
			::= { wsMgmtAlarms 11 }

		-- 1.3.6.1.4.1.388.14.4.1.4.12
		wsMgmInfoAlarmsCount OBJECT-TYPE
			SYNTAX Unsigned32
			MAX-ACCESS read-only
			STATUS current
			DESCRIPTION
				"Total number of currently active alarms 
				of informational severity."
			::= { wsMgmtAlarms 12 }

		-- 1.3.6.1.4.1.388.14.4.1.4.13
		wsMgmNormalAlarmsCount OBJECT-TYPE
			SYNTAX Unsigned32
			MAX-ACCESS read-only
			STATUS current
			DESCRIPTION
				"Total number of currently active alarms 
				of normal severity."
			::= { wsMgmtAlarms 13 }

		-- 1.3.6.1.4.1.388.14.4.1.4.14
		wsMgmUnacknowledgedCriticalAlarmsCount OBJECT-TYPE
			SYNTAX Unsigned32
			MAX-ACCESS read-only
			STATUS current
			DESCRIPTION
				"Total number of current unacknowledged alarms with severity
				'critical'."
			::= { wsMgmtAlarms 14 }

		-- 1.3.6.1.4.1.388.14.4.1.4.15
		wsMgmUnacknowledgedMajorAlarmsCount OBJECT-TYPE
			SYNTAX Unsigned32
			MAX-ACCESS read-only
			STATUS current
			DESCRIPTION
				"Total number of current unacknowledged alarms with severity
				'major'."
			::= { wsMgmtAlarms 15 }

		-- 1.3.6.1.4.1.388.14.4.1.4.16
		wsMgmUnacknowledgedWarningAlarmsCount OBJECT-TYPE
			SYNTAX Unsigned32
			MAX-ACCESS read-only
			STATUS current
			DESCRIPTION
				"Total number of current unacknowledged alarms with severity
				'warning'."
			::= { wsMgmtAlarms 16 }

		-- 1.3.6.1.4.1.388.14.4.1.4.17
		wsMgmUnacknowledgedInfoAlarmsCount OBJECT-TYPE
			SYNTAX Unsigned32
			MAX-ACCESS read-only
			STATUS current
			DESCRIPTION
				"Total number of current unacknowledged alarms with severity
				'informational'."
			::= { wsMgmtAlarms 17 }

		-- 1.3.6.1.4.1.388.14.4.1.4.18
		wsMgmUnacknowledgedNormalAlarmsCount OBJECT-TYPE
			SYNTAX Unsigned32
			MAX-ACCESS read-only
			STATUS current
			DESCRIPTION
				"Total number of current unacknowledged alarms with severity
				'normal'."
			::= { wsMgmtAlarms 18 }

		-- 1.3.6.1.4.1.388.14.4.1.4.19
		wsMgmUnacknowledgedCriticalAlarmsCountSinceBoot OBJECT-TYPE
			SYNTAX Unsigned32
			MAX-ACCESS read-only
			STATUS current
			DESCRIPTION
				"Total number of unacknowledged alarms with severity
				'critical' that have been generated since system boot.
				This number could be different from the current number of
				unacknowledged alarms with severity 'critical' in cases
				where alarms get deleted from alarm log either manually or
				during alarm-log rollover."
			::= { wsMgmtAlarms 19 }

		-- 1.3.6.1.4.1.388.14.4.1.4.20
		wsMgmUnacknowledgedMajorAlarmsCountSinceBoot OBJECT-TYPE
			SYNTAX Unsigned32
			MAX-ACCESS read-only
			STATUS current
			DESCRIPTION
				"Total number of unacknowledged alarms with severity 'major'
				that have been generated since system boot.
				This number could be different from the current number of
				unacknowledged alarms with severity 'major in cases where
				alarms get deleted from alarm log either manually or during
				alarm-log rollover."
			::= { wsMgmtAlarms 20 }

		-- 1.3.6.1.4.1.388.14.4.1.4.21
		wsMgmUnacknowledgedWarningAlarmsCountSinceBoot OBJECT-TYPE
			SYNTAX Unsigned32
			MAX-ACCESS read-only
			STATUS current
			DESCRIPTION
				"Total number of unacknowledged alarms with severity 'warning'
				that have been generated since system boot.
				This number could be different from the current number of
				unacknowledged alarms with severity 'warning' in cases
				where alarms get deleted from alarm log either manually or
				during alarm-log rollover."
			::= { wsMgmtAlarms 21 }

		-- 1.3.6.1.4.1.388.14.4.1.4.22
		wsMgmUnacknowledgedInfoAlarmsCountSinceBoot OBJECT-TYPE
			SYNTAX Unsigned32
			MAX-ACCESS read-only
			STATUS current
			DESCRIPTION
				"Total number of unacknowledged alarms with severity
				'informational' that have been generated since system boot.
				This number could be different from the current number of
				unacknowledged alarms with severity 'informational'
				in cases where alarms get deleted from alarm log either
				manually or during alarm-log rollover."
			::= { wsMgmtAlarms 22 }

		-- 1.3.6.1.4.1.388.14.4.1.4.23
		wsMgmUnacknowledgedNormalAlarmsCountSinceBoot OBJECT-TYPE
			SYNTAX Unsigned32
			MAX-ACCESS read-only
			STATUS current
			DESCRIPTION
				"Total number of unacknowledged alarms with severity 'normal'
				that have been generated since system boot.
				This number could be different from the current number of
				unacknowledged alarms with severity 'normal' in cases where
				alarms get deleted from alarm log either manually or
				during alarm-log rollover."
			::= { wsMgmtAlarms 23 }

		-- 1.3.6.1.4.1.388.14.4.1.5
		wsMgmtCert OBJECT IDENTIFIER ::= { wsMgmtMib 5 }

		-- 1.3.6.1.4.1.388.14.4.1.5.2
		wsMgmtCertCurrent OBJECT IDENTIFIER ::= { wsMgmtCert 2 }

		-- 1.3.6.1.4.1.388.14.4.1.5.2.1
		wsMgmtCertCurrentCountry OBJECT-TYPE
			SYNTAX DisplayString (SIZE (0..2))
			MAX-ACCESS read-only
			STATUS obsolete
			DESCRIPTION
				"Description."
			::= { wsMgmtCertCurrent 1 }

		-- 1.3.6.1.4.1.388.14.4.1.5.2.2
		wsMgmtCertCurrentState OBJECT-TYPE
			SYNTAX DisplayString (SIZE (0..128))
			MAX-ACCESS read-only
			STATUS obsolete
			DESCRIPTION
				"Description."
			::= { wsMgmtCertCurrent 2 }

		-- 1.3.6.1.4.1.388.14.4.1.5.2.3
		wsMgmtCertCurrentCity OBJECT-TYPE
			SYNTAX DisplayString (SIZE (0..128))
			MAX-ACCESS read-only
			STATUS obsolete
			DESCRIPTION
				"Description."
			::= { wsMgmtCertCurrent 3 }

		-- 1.3.6.1.4.1.388.14.4.1.5.2.4
		wsMgmtCertCurrentOrg OBJECT-TYPE
			SYNTAX DisplayString (SIZE (0..64))
			MAX-ACCESS read-only
			STATUS obsolete
			DESCRIPTION
				"Description."
			::= { wsMgmtCertCurrent 4 }

		-- 1.3.6.1.4.1.388.14.4.1.5.2.6
		wsMgmtCertCurrentOrgUnit OBJECT-TYPE
			SYNTAX DisplayString (SIZE (0..64))
			MAX-ACCESS read-only
			STATUS obsolete
			DESCRIPTION
				"Description."
			::= { wsMgmtCertCurrent 6 }

		-- 1.3.6.1.4.1.388.14.4.1.5.2.7
		wsMgmtCertCurrentCommonName OBJECT-TYPE
			SYNTAX DisplayString (SIZE (0..64))
			MAX-ACCESS read-only
			STATUS obsolete
			DESCRIPTION
				"Description."
			::= { wsMgmtCertCurrent 7 }

		-- 1.3.6.1.4.1.388.14.4.1.5.2.8
		wsMgmtCertCurrentIssuer OBJECT-TYPE
			SYNTAX OCTET STRING (SIZE (0..600))
			MAX-ACCESS read-only
			STATUS obsolete
			DESCRIPTION
				"Description."
			::= { wsMgmtCertCurrent 8 }

		-- 1.3.6.1.4.1.388.14.4.1.5.2.9
		wsMgmtCertCurrentValidStart OBJECT-TYPE
			SYNTAX DisplayString (SIZE (0..64))
			MAX-ACCESS read-only
			STATUS obsolete
			DESCRIPTION
				"Description."
			::= { wsMgmtCertCurrent 9 }

		-- 1.3.6.1.4.1.388.14.4.1.5.2.10
		wsMgmtCertCurrentValidEnd OBJECT-TYPE
			SYNTAX DisplayString (SIZE (0..64))
			MAX-ACCESS read-only
			STATUS obsolete
			DESCRIPTION
				"Description."
			::= { wsMgmtCertCurrent 10 }

		-- 1.3.6.1.4.1.388.14.4.1.5.2.11
		wsMgmtCertCurrentTrustPoint OBJECT-TYPE
			SYNTAX DisplayString
			MAX-ACCESS read-only
			STATUS obsolete
			DESCRIPTION
				"trust point of the current cert, will always get local in rel1.0"
			::= { wsMgmtCertCurrent 11 }

		-- 1.3.6.1.4.1.388.14.4.1.5.3
		wsMgmtCertCreate OBJECT IDENTIFIER ::= { wsMgmtCert 3 }

		-- 1.3.6.1.4.1.388.14.4.1.5.3.2
		wsMgmtCertFileName OBJECT-TYPE
			SYNTAX DisplayString
			MAX-ACCESS read-write
			STATUS obsolete
			DESCRIPTION
				"Description."
			::= { wsMgmtCertCreate 2 }

		-- 1.3.6.1.4.1.388.14.4.1.5.3.3
		wsMgmtCertAction OBJECT-TYPE
			SYNTAX INTEGER
				{
				query(1),
				remove(2),
				install(3),
				createSelf(4),
				createReq(5),
				idle(6)
				}
			MAX-ACCESS read-write
			STATUS obsolete
			DESCRIPTION
				"Description."
			::= { wsMgmtCertCreate 3 }

		-- 1.3.6.1.4.1.388.14.4.1.5.3.4
		wsMgmtCertStatus OBJECT-TYPE
			SYNTAX DisplayString
			MAX-ACCESS read-only
			STATUS obsolete
			DESCRIPTION
				"Description."
			::= { wsMgmtCertCreate 4 }

		-- 1.3.6.1.4.1.388.14.4.1.5.3.5
		wsMgmtCertCountry OBJECT-TYPE
			SYNTAX DisplayString (SIZE (0..2))
			MAX-ACCESS read-write
			STATUS obsolete
			DESCRIPTION
				"Description."
			::= { wsMgmtCertCreate 5 }

		-- 1.3.6.1.4.1.388.14.4.1.5.3.6
		wsMgmtCertState OBJECT-TYPE
			SYNTAX DisplayString (SIZE (0..128))
			MAX-ACCESS read-write
			STATUS obsolete
			DESCRIPTION
				"Description."
			::= { wsMgmtCertCreate 6 }

		-- 1.3.6.1.4.1.388.14.4.1.5.3.7
		wsMgmtCertCity OBJECT-TYPE
			SYNTAX DisplayString (SIZE (0..128))
			MAX-ACCESS read-write
			STATUS obsolete
			DESCRIPTION
				"Description."
			::= { wsMgmtCertCreate 7 }

		-- 1.3.6.1.4.1.388.14.4.1.5.3.8
		wsMgmtCertOrg OBJECT-TYPE
			SYNTAX DisplayString (SIZE (0..64))
			MAX-ACCESS read-write
			STATUS obsolete
			DESCRIPTION
				"Description."
			::= { wsMgmtCertCreate 8 }

		-- 1.3.6.1.4.1.388.14.4.1.5.3.9
		wsMgmtCertOrgUnit OBJECT-TYPE
			SYNTAX DisplayString (SIZE (0..64))
			MAX-ACCESS read-write
			STATUS obsolete
			DESCRIPTION
				"Description."
			::= { wsMgmtCertCreate 9 }

		-- 1.3.6.1.4.1.388.14.4.1.5.3.10
		wsMgmtCertCommonName OBJECT-TYPE
			SYNTAX DisplayString (SIZE (0..64))
			MAX-ACCESS read-write
			STATUS obsolete
			DESCRIPTION
				"Description."
			::= { wsMgmtCertCreate 10 }

		-- 1.3.6.1.4.1.388.14.4.1.5.3.11
		wsMgmtCertIssuer OBJECT-TYPE
			SYNTAX DisplayString (SIZE (0..64))
			MAX-ACCESS read-write
			STATUS obsolete
			DESCRIPTION
				"Description."
			::= { wsMgmtCertCreate 11 }

		-- 1.3.6.1.4.1.388.14.4.1.5.3.12
		wsMgmtCertEmail OBJECT-TYPE
			SYNTAX DisplayString (SIZE (0..64))
			MAX-ACCESS read-write
			STATUS obsolete
			DESCRIPTION
				"Description."
			::= { wsMgmtCertCreate 12 }

		-- 1.3.6.1.4.1.388.14.4.1.5.3.13
		wsMgmtCertPwd OBJECT-TYPE
			SYNTAX DisplayString (SIZE (0..20))
			MAX-ACCESS read-write
			STATUS obsolete
			DESCRIPTION
				"Description."
			::= { wsMgmtCertCreate 13 }

		-- 1.3.6.1.4.1.388.14.4.1.5.3.14
		wsMgmtCertCompany OBJECT-TYPE
			SYNTAX DisplayString (SIZE (0..64))
			MAX-ACCESS read-write
			STATUS obsolete
			DESCRIPTION
				"Description."
			::= { wsMgmtCertCreate 14 }

		-- 1.3.6.1.4.1.388.14.4.1.5.3.15
		wsMgmtCertValidStart OBJECT-TYPE
			SYNTAX DisplayString (SIZE (0..64))
			MAX-ACCESS read-only
			STATUS obsolete
			DESCRIPTION
				"Description."
			::= { wsMgmtCertCreate 15 }

		-- 1.3.6.1.4.1.388.14.4.1.5.3.16
		wsMgmtCertValidEnd OBJECT-TYPE
			SYNTAX DisplayString (SIZE (0..64))
			MAX-ACCESS read-only
			STATUS obsolete
			DESCRIPTION
				"Description."
			::= { wsMgmtCertCreate 16 }

		-- 1.3.6.1.4.1.388.14.4.1.5.3.17
		wsMgmtCertTrustPoint OBJECT-TYPE
			SYNTAX DisplayString
			MAX-ACCESS read-write
			STATUS obsolete
			DESCRIPTION
				"trust point of the cert, will only accept local in rel 1.0"
			::= { wsMgmtCertCreate 17 }

		-- 1.3.6.1.4.1.388.14.4.1.5.4
		wsMgmtCertViewTable OBJECT-TYPE
			SYNTAX SEQUENCE OF WsMgmtCertViewEntry
			MAX-ACCESS not-accessible
			STATUS current
			DESCRIPTION
				"Shows a list of all enrolled certificates."
			::= { wsMgmtCert 4 }

		-- 1.3.6.1.4.1.388.14.4.1.5.4.1
		wsMgmtCertViewEntry OBJECT-TYPE
			SYNTAX WsMgmtCertViewEntry
			MAX-ACCESS not-accessible
			STATUS current
			DESCRIPTION
				"Description."
			INDEX { wsMgmtCertViewTrustpoint, wsMgmtCertViewType }
			::= { wsMgmtCertViewTable 1 }

		WsMgmtCertViewEntry ::=
			SEQUENCE { 
				wsMgmtCertViewTrustpoint
					DisplayString,
				wsMgmtCertViewType
					INTEGER,
				wsMgmtCertViewSubjectCommonName
					DisplayString,
				wsMgmtCertViewSubjectOrgUnit
					DisplayString,
				wsMgmtCertViewSubjectOrg
					DisplayString,
				wsMgmtCertViewSubjectCity
					DisplayString,
				wsMgmtCertViewSubjectState
					DisplayString,
				wsMgmtCertViewSubjectCountry
					DisplayString,
				wsMgmtCertViewSubjectEmail
					DisplayString,
				wsMgmtCertViewIssuerCommonName
					DisplayString,
				wsMgmtCertViewIssuerOrgUnit
					DisplayString,
				wsMgmtCertViewIssuerOrg
					DisplayString,
				wsMgmtCertViewIssuerCity
					DisplayString,
				wsMgmtCertViewIssuerState
					DisplayString,
				wsMgmtCertViewIssuerCountry
					DisplayString,
				wsMgmtCertViewIssuerEmail
					DisplayString,
				wsMgmtCertViewValidStart
					DisplayString,
				wsMgmtCertViewValidEnd
					DisplayString
			 }

		-- 1.3.6.1.4.1.388.14.4.1.5.4.1.1
		wsMgmtCertViewTrustpoint OBJECT-TYPE
			SYNTAX DisplayString (SIZE (2..64))
			MAX-ACCESS read-only
			STATUS current
			DESCRIPTION
				"Name of the trustpoint"
			::= { wsMgmtCertViewEntry 1 }

		-- 1.3.6.1.4.1.388.14.4.1.5.4.1.2
		wsMgmtCertViewType OBJECT-TYPE
			SYNTAX INTEGER
				{
				serverCert(4),
				caCert(8)
				}
			MAX-ACCESS read-only
			STATUS current
			DESCRIPTION
				"Type of certificate: CA certificate or server certificate."
			::= { wsMgmtCertViewEntry 2 }

		-- 1.3.6.1.4.1.388.14.4.1.5.4.1.3
		wsMgmtCertViewSubjectCommonName OBJECT-TYPE
			SYNTAX DisplayString (SIZE (2..64))
			MAX-ACCESS read-only
			STATUS current
			DESCRIPTION
				"Contains 6 fields corresponding to Common Name, Organizational unit, 
				Organization,  Location, State and Country"
			::= { wsMgmtCertViewEntry 3 }

		-- 1.3.6.1.4.1.388.14.4.1.5.4.1.4
		wsMgmtCertViewSubjectOrgUnit OBJECT-TYPE
			SYNTAX DisplayString (SIZE (2..64))
			MAX-ACCESS read-only
			STATUS current
			DESCRIPTION
				"Description."
			::= { wsMgmtCertViewEntry 4 }

		-- 1.3.6.1.4.1.388.14.4.1.5.4.1.5
		wsMgmtCertViewSubjectOrg OBJECT-TYPE
			SYNTAX DisplayString (SIZE (2..64))
			MAX-ACCESS read-only
			STATUS current
			DESCRIPTION
				"Description."
			::= { wsMgmtCertViewEntry 5 }

		-- 1.3.6.1.4.1.388.14.4.1.5.4.1.6
		wsMgmtCertViewSubjectCity OBJECT-TYPE
			SYNTAX DisplayString (SIZE (2..128))
			MAX-ACCESS read-only
			STATUS current
			DESCRIPTION
				"Description."
			::= { wsMgmtCertViewEntry 6 }

		-- 1.3.6.1.4.1.388.14.4.1.5.4.1.7
		wsMgmtCertViewSubjectState OBJECT-TYPE
			SYNTAX DisplayString (SIZE (2..128))
			MAX-ACCESS read-only
			STATUS current
			DESCRIPTION
				"Description."
			::= { wsMgmtCertViewEntry 7 }

		-- 1.3.6.1.4.1.388.14.4.1.5.4.1.8
		wsMgmtCertViewSubjectCountry OBJECT-TYPE
			SYNTAX DisplayString (SIZE (2))
			MAX-ACCESS read-only
			STATUS current
			DESCRIPTION
				"Description."
			::= { wsMgmtCertViewEntry 8 }

		-- 1.3.6.1.4.1.388.14.4.1.5.4.1.9
		wsMgmtCertViewSubjectEmail OBJECT-TYPE
			SYNTAX DisplayString (SIZE (2..64))
			MAX-ACCESS read-only
			STATUS current
			DESCRIPTION
				"Description."
			::= { wsMgmtCertViewEntry 9 }

		-- 1.3.6.1.4.1.388.14.4.1.5.4.1.10
		wsMgmtCertViewIssuerCommonName OBJECT-TYPE
			SYNTAX DisplayString (SIZE (2..64))
			MAX-ACCESS read-only
			STATUS current
			DESCRIPTION
				"Name of authority who issues the certficate"
			::= { wsMgmtCertViewEntry 10 }

		-- 1.3.6.1.4.1.388.14.4.1.5.4.1.11
		wsMgmtCertViewIssuerOrgUnit OBJECT-TYPE
			SYNTAX DisplayString (SIZE (2..64))
			MAX-ACCESS read-only
			STATUS current
			DESCRIPTION
				"Description."
			::= { wsMgmtCertViewEntry 11 }

		-- 1.3.6.1.4.1.388.14.4.1.5.4.1.12
		wsMgmtCertViewIssuerOrg OBJECT-TYPE
			SYNTAX DisplayString (SIZE (2..64))
			MAX-ACCESS read-only
			STATUS current
			DESCRIPTION
				"Description."
			::= { wsMgmtCertViewEntry 12 }

		-- 1.3.6.1.4.1.388.14.4.1.5.4.1.13
		wsMgmtCertViewIssuerCity OBJECT-TYPE
			SYNTAX DisplayString (SIZE (2..128))
			MAX-ACCESS read-only
			STATUS current
			DESCRIPTION
				"Description."
			::= { wsMgmtCertViewEntry 13 }

		-- 1.3.6.1.4.1.388.14.4.1.5.4.1.14
		wsMgmtCertViewIssuerState OBJECT-TYPE
			SYNTAX DisplayString (SIZE (2..128))
			MAX-ACCESS read-only
			STATUS current
			DESCRIPTION
				"Description."
			::= { wsMgmtCertViewEntry 14 }

		-- 1.3.6.1.4.1.388.14.4.1.5.4.1.15
		wsMgmtCertViewIssuerCountry OBJECT-TYPE
			SYNTAX DisplayString (SIZE (2))
			MAX-ACCESS read-only
			STATUS current
			DESCRIPTION
				"Description."
			::= { wsMgmtCertViewEntry 15 }

		-- 1.3.6.1.4.1.388.14.4.1.5.4.1.16
		wsMgmtCertViewIssuerEmail OBJECT-TYPE
			SYNTAX DisplayString (SIZE (2..64))
			MAX-ACCESS read-only
			STATUS current
			DESCRIPTION
				"Description."
			::= { wsMgmtCertViewEntry 16 }

		-- 1.3.6.1.4.1.388.14.4.1.5.4.1.17
		wsMgmtCertViewValidStart OBJECT-TYPE
			SYNTAX DisplayString
			MAX-ACCESS read-only
			STATUS current
			DESCRIPTION
				"Date on which the certificate starts to be valid"
			::= { wsMgmtCertViewEntry 17 }

		-- 1.3.6.1.4.1.388.14.4.1.5.4.1.18
		wsMgmtCertViewValidEnd OBJECT-TYPE
			SYNTAX DisplayString
			MAX-ACCESS read-only
			STATUS current
			DESCRIPTION
				"Date of expiry of the certificate"
			::= { wsMgmtCertViewEntry 18 }

		-- 1.3.6.1.4.1.388.14.4.1.5.5
		wsMgmtCertConfigTable OBJECT-TYPE
			SYNTAX SEQUENCE OF WsMgmtCertConfigEntry
			MAX-ACCESS not-accessible
			STATUS current
			DESCRIPTION
				"Table in which trustpoints can be configured"
			::= { wsMgmtCert 5 }

		-- 1.3.6.1.4.1.388.14.4.1.5.5.1
		wsMgmtCertConfigEntry OBJECT-TYPE
			SYNTAX WsMgmtCertConfigEntry
			MAX-ACCESS not-accessible
			STATUS current
			DESCRIPTION
				"Description."
			INDEX { wsMgmtCertConfigTrustpoint }
			::= { wsMgmtCertConfigTable 1 }

		WsMgmtCertConfigEntry ::=
			SEQUENCE { 
				wsMgmtCertConfigTrustpoint
					DisplayString,
				wsMgmtCertConfigKey
					DisplayString,
				wsMgmtCertConfigCommonName
					DisplayString,
				wsMgmtCertConfigOrgUnit
					DisplayString,
				wsMgmtCertConfigOrg
					DisplayString,
				wsMgmtCertConfigCompany
					DisplayString,
				wsMgmtCertConfigCity
					DisplayString,
				wsMgmtCertConfigState
					DisplayString,
				wsMgmtCertConfigCountry
					DisplayString,
				wsMgmtCertConfigFqdn
					DisplayString,
				wsMgmtCertConfigIP
					IpAddress,
				wsMgmtCertConfigEmail
					DisplayString,
				wsMgmtCertConfigPassword
					Password,
				wsMgmtCertConfigRowStatus
					AbbrRowStatus
			 }

		-- 1.3.6.1.4.1.388.14.4.1.5.5.1.1
		wsMgmtCertConfigTrustpoint OBJECT-TYPE
			SYNTAX DisplayString (SIZE (2..64))
			MAX-ACCESS read-create
			STATUS current
			DESCRIPTION
				"Name of the trustpoint"
			::= { wsMgmtCertConfigEntry 1 }

		-- 1.3.6.1.4.1.388.14.4.1.5.5.1.2
		wsMgmtCertConfigKey OBJECT-TYPE
			SYNTAX DisplayString (SIZE (2..64))
			MAX-ACCESS read-create
			STATUS current
			DESCRIPTION
				"Label of the RSA keypair associated with the certificate."
			::= { wsMgmtCertConfigEntry 2 }

		-- 1.3.6.1.4.1.388.14.4.1.5.5.1.3
		wsMgmtCertConfigCommonName OBJECT-TYPE
			SYNTAX DisplayString (SIZE (2..64))
			MAX-ACCESS read-create
			STATUS current
			DESCRIPTION
				"Common name of the trustpoint specified in the Subject Alternative Name 
				extension of the certificate request /selfsigned certificate"
			::= { wsMgmtCertConfigEntry 3 }

		-- 1.3.6.1.4.1.388.14.4.1.5.5.1.4
		wsMgmtCertConfigOrgUnit OBJECT-TYPE
			SYNTAX DisplayString (SIZE (2..64))
			MAX-ACCESS read-create
			STATUS current
			DESCRIPTION
				"Organizational unit to which the certificate belongs specified in the 
				Subject Alternative Name extension of the certificate request/selfsigned 
				certificate"
			::= { wsMgmtCertConfigEntry 4 }

		-- 1.3.6.1.4.1.388.14.4.1.5.5.1.5
		wsMgmtCertConfigOrg OBJECT-TYPE
			SYNTAX DisplayString (SIZE (2..64))
			MAX-ACCESS read-create
			STATUS current
			DESCRIPTION
				"Organizational to which the certificate belongs specified in the Subject 
				Alternative Name extension of the certificate request /selfsigned 
				certificate"
			::= { wsMgmtCertConfigEntry 5 }

		-- 1.3.6.1.4.1.388.14.4.1.5.5.1.6
		wsMgmtCertConfigCompany OBJECT-TYPE
			SYNTAX DisplayString (SIZE (2..64))
			MAX-ACCESS read-create
			STATUS current
			DESCRIPTION
				"Company to which the certificate is issued to specified in 
				the Subject Alternative Name extension of the certificate 
				request /selfsigned certificate"
			::= { wsMgmtCertConfigEntry 6 }

		-- 1.3.6.1.4.1.388.14.4.1.5.5.1.7
		wsMgmtCertConfigCity OBJECT-TYPE
			SYNTAX DisplayString (SIZE (2..128))
			MAX-ACCESS read-create
			STATUS current
			DESCRIPTION
				"City of the company to which the certificate is issued to specified in 
				the Subject Alternative Name extension of the certificate request /
				selfsigned certificate."
			::= { wsMgmtCertConfigEntry 7 }

		-- 1.3.6.1.4.1.388.14.4.1.5.5.1.8
		wsMgmtCertConfigState OBJECT-TYPE
			SYNTAX DisplayString (SIZE (2..128))
			MAX-ACCESS read-create
			STATUS current
			DESCRIPTION
				"State of the company to which the certificate is issued to specified in 
				the Subject Alternative Name extension of the certificate request /
				selfsigned certificate."
			::= { wsMgmtCertConfigEntry 8 }

		-- 1.3.6.1.4.1.388.14.4.1.5.5.1.9
		wsMgmtCertConfigCountry OBJECT-TYPE
			SYNTAX DisplayString (SIZE (2))
			MAX-ACCESS read-create
			STATUS current
			DESCRIPTION
				"Country of the company to which the certificate is issued to specified in 
				the Subject Alternative Name extension of the certificate request /
				selfsigned certificate."
			::= { wsMgmtCertConfigEntry 9 }

		-- 1.3.6.1.4.1.388.14.4.1.5.5.1.10
		wsMgmtCertConfigFqdn OBJECT-TYPE
			SYNTAX DisplayString (SIZE (9..64))
			MAX-ACCESS read-create
			STATUS current
			DESCRIPTION
				"Fully qualified domain name of the certificate specified in 
				the Subject Alternative Name extension of the certificate 
				request /selfsigned certificate"
			::= { wsMgmtCertConfigEntry 10 }

		-- 1.3.6.1.4.1.388.14.4.1.5.5.1.11
		wsMgmtCertConfigIP OBJECT-TYPE
			SYNTAX IpAddress
			MAX-ACCESS read-create
			STATUS current
			DESCRIPTION
				"IP address specified in the Subject Alternative Name extension of 
				the certificate request /selfsigned certificate"
			::= { wsMgmtCertConfigEntry 11 }

		-- 1.3.6.1.4.1.388.14.4.1.5.5.1.12
		wsMgmtCertConfigEmail OBJECT-TYPE
			SYNTAX DisplayString (SIZE (2..64))
			MAX-ACCESS read-create
			STATUS current
			DESCRIPTION
				"Email address specified in the Subject Alternative Name extension of 
				the certificate request /selfsigned certificate"
			::= { wsMgmtCertConfigEntry 12 }

		-- 1.3.6.1.4.1.388.14.4.1.5.5.1.13
		wsMgmtCertConfigPassword OBJECT-TYPE
			SYNTAX Password (SIZE (4..20))
			MAX-ACCESS read-create
			STATUS current
			DESCRIPTION
				"Password specified in the Subject Alternative Name extension of 
				the certificate request /selfsigned certificate"
			::= { wsMgmtCertConfigEntry 13 }

		-- 1.3.6.1.4.1.388.14.4.1.5.5.1.14
		wsMgmtCertConfigRowStatus OBJECT-TYPE
			SYNTAX AbbrRowStatus
			MAX-ACCESS read-create
			STATUS current
			DESCRIPTION
				"Create/delete"
			::= { wsMgmtCertConfigEntry 14 }

		-- 1.3.6.1.4.1.388.14.4.1.5.6
		wsMgmtCertCreateTable OBJECT-TYPE
			SYNTAX SEQUENCE OF WsMgmtCertCreateEntry
			MAX-ACCESS not-accessible
			STATUS current
			DESCRIPTION
				"Table to enroll/delete certs/requests"
			::= { wsMgmtCert 6 }

		-- 1.3.6.1.4.1.388.14.4.1.5.6.1
		wsMgmtCertCreateEntry OBJECT-TYPE
			SYNTAX WsMgmtCertCreateEntry
			MAX-ACCESS not-accessible
			STATUS current
			DESCRIPTION
				"Description."
			INDEX { wsMgmtCertConfigTrustpoint }
			::= { wsMgmtCertCreateTable 1 }

		WsMgmtCertCreateEntry ::=
			SEQUENCE { 
				wsMgmtCertCreateStatus
					INTEGER,
				wsMgmtCertCreateAction
					INTEGER
			 }

		-- 1.3.6.1.4.1.388.14.4.1.5.6.1.1
		wsMgmtCertCreateStatus OBJECT-TYPE
			SYNTAX INTEGER
				{
				idle(1),
				enrolled(2),
				notEnrolled(3)
				}
			MAX-ACCESS read-only
			STATUS current
			DESCRIPTION
				"Indicates status of enrollment."
			DEFVAL { idle }
			::= { wsMgmtCertCreateEntry 1 }

		-- 1.3.6.1.4.1.388.14.4.1.5.6.1.2
		wsMgmtCertCreateAction OBJECT-TYPE
			SYNTAX INTEGER
				{
				enrollSelfSigned(1),
				enrollReq(2),
				delServerCert(3),
				delCACert(4),
				idle(5)
				}
			MAX-ACCESS read-write
			STATUS current
			DESCRIPTION
				"Action for enrollment/deletion of cert/request"
			DEFVAL { idle }
			::= { wsMgmtCertCreateEntry 2 }

		-- 1.3.6.1.4.1.388.14.4.1.5.7
		wsMgmtCertKeyTable OBJECT-TYPE
			SYNTAX SEQUENCE OF WsMgmtCertKeyEntry
			MAX-ACCESS not-accessible
			STATUS current
			DESCRIPTION
				"Table to create RSA keypairs"
			::= { wsMgmtCert 7 }

		-- 1.3.6.1.4.1.388.14.4.1.5.7.1
		wsMgmtCertKeyEntry OBJECT-TYPE
			SYNTAX WsMgmtCertKeyEntry
			MAX-ACCESS not-accessible
			STATUS current
			DESCRIPTION
				"Description."
			INDEX { wsMgmtCertKeyLabel }
			::= { wsMgmtCertKeyTable 1 }

		WsMgmtCertKeyEntry ::=
			SEQUENCE { 
				wsMgmtCertKeyLabel
					DisplayString,
				wsMgmtCertKeySize
					INTEGER,
				wsMgmtCertKeyRowStatus
					AbbrRowStatus
			 }

		-- 1.3.6.1.4.1.388.14.4.1.5.7.1.1
		wsMgmtCertKeyLabel OBJECT-TYPE
			SYNTAX DisplayString (SIZE (2..64))
			MAX-ACCESS read-create
			STATUS current
			DESCRIPTION
				"Label of the RSA key pair"
			::= { wsMgmtCertKeyEntry 1 }

		-- 1.3.6.1.4.1.388.14.4.1.5.7.1.2
		wsMgmtCertKeySize OBJECT-TYPE
			SYNTAX INTEGER (1..32 | 1024..2048)
			MAX-ACCESS read-create
			STATUS current
			DESCRIPTION
				"Size of the keypair. This variable is only used for creating the key. 
				Once a key is created, this variable does not have any significance."
			::= { wsMgmtCertKeyEntry 2 }

		-- 1.3.6.1.4.1.388.14.4.1.5.7.1.3
		wsMgmtCertKeyRowStatus OBJECT-TYPE
			SYNTAX AbbrRowStatus
			MAX-ACCESS read-create
			STATUS current
			DESCRIPTION
				"Description."
			::= { wsMgmtCertKeyEntry 3 }

		-- 1.3.6.1.4.1.388.14.4.1.5.8
		wsMgmtCertNumTrustPoint OBJECT-TYPE
			SYNTAX Integer32 (0..6)
			MAX-ACCESS read-only
			STATUS current
			DESCRIPTION
				"Description."
			::= { wsMgmtCert 8 }

		-- 1.3.6.1.4.1.388.14.4.1.7
		wsMgmtNwDiscovery OBJECT IDENTIFIER ::= { wsMgmtMib 7 }

		-- 1.3.6.1.4.1.388.14.4.1.7.2
		wsMgmtNetworkDiscoveryTable OBJECT-TYPE
			SYNTAX SEQUENCE OF WsMgmtNetworkDiscoveryEntry
			MAX-ACCESS not-accessible
			STATUS current
			DESCRIPTION
				"Description."
			::= { wsMgmtNwDiscovery 2 }

		-- 1.3.6.1.4.1.388.14.4.1.7.2.1
		wsMgmtNetworkDiscoveryEntry OBJECT-TYPE
			SYNTAX WsMgmtNetworkDiscoveryEntry
			MAX-ACCESS not-accessible
			STATUS current
			DESCRIPTION
				"Description."
			INDEX { wsMgmtDiscoveredDeviceIpAddr }
			::= { wsMgmtNetworkDiscoveryTable 1 }

		WsMgmtNetworkDiscoveryEntry ::=
			SEQUENCE { 
				wsMgmtDiscoveredDeviceIpAddr
					IpAddress,
				wsMgmtDiscoveredDeviceHwVersion
					DisplayString,
				wsMgmtDiscoveredDeviceSwVersion
					DisplayString,
				wsMgmtDiscoveredDeviceClusterId
					Unsigned32,
				wsMgmtDiscoveredDeviceName
					DisplayString,
				wsMgmtDiscoveredDeviceLocation
					DisplayString,
				wsMgmtDiscoveredDeviceDescr
					DisplayString,
				wsMgmtDiscoveredDeviceDiscoveryProfileName
					DisplayString,
				wsMgmtDiscoveredDeviceDiscoveryTime
					DateAndTime,
				wsMgmtDiscoveredNetworkDevicesTableRow
					RowStatus
			 }

		-- 1.3.6.1.4.1.388.14.4.1.7.2.1.1
		wsMgmtDiscoveredDeviceIpAddr OBJECT-TYPE
			SYNTAX IpAddress
			MAX-ACCESS read-create
			STATUS current
			DESCRIPTION
				"Description."
			::= { wsMgmtNetworkDiscoveryEntry 1 }

		-- 1.3.6.1.4.1.388.14.4.1.7.2.1.2
		wsMgmtDiscoveredDeviceHwVersion OBJECT-TYPE
			SYNTAX DisplayString (SIZE (1..128))
			MAX-ACCESS read-create
			STATUS current
			DESCRIPTION
				"Description."
			::= { wsMgmtNetworkDiscoveryEntry 2 }

		-- 1.3.6.1.4.1.388.14.4.1.7.2.1.3
		wsMgmtDiscoveredDeviceSwVersion OBJECT-TYPE
			SYNTAX DisplayString (SIZE (1..128))
			MAX-ACCESS read-create
			STATUS current
			DESCRIPTION
				"Description."
			::= { wsMgmtNetworkDiscoveryEntry 3 }

		-- 1.3.6.1.4.1.388.14.4.1.7.2.1.4
		wsMgmtDiscoveredDeviceClusterId OBJECT-TYPE
			SYNTAX Unsigned32 (1..65535)
			MAX-ACCESS read-create
			STATUS current
			DESCRIPTION
				"Description."
			::= { wsMgmtNetworkDiscoveryEntry 4 }

		-- 1.3.6.1.4.1.388.14.4.1.7.2.1.5
		wsMgmtDiscoveredDeviceName OBJECT-TYPE
			SYNTAX DisplayString
			MAX-ACCESS read-create
			STATUS current
			DESCRIPTION
				"Description."
			::= { wsMgmtNetworkDiscoveryEntry 5 }

		-- 1.3.6.1.4.1.388.14.4.1.7.2.1.6
		wsMgmtDiscoveredDeviceLocation OBJECT-TYPE
			SYNTAX DisplayString
			MAX-ACCESS read-create
			STATUS current
			DESCRIPTION
				"Description."
			::= { wsMgmtNetworkDiscoveryEntry 6 }

		-- 1.3.6.1.4.1.388.14.4.1.7.2.1.7
		wsMgmtDiscoveredDeviceDescr OBJECT-TYPE
			SYNTAX DisplayString
			MAX-ACCESS read-create
			STATUS current
			DESCRIPTION
				"Description."
			::= { wsMgmtNetworkDiscoveryEntry 7 }

		-- 1.3.6.1.4.1.388.14.4.1.7.2.1.8
		wsMgmtDiscoveredDeviceDiscoveryProfileName OBJECT-TYPE
			SYNTAX DisplayString (SIZE (1..128))
			MAX-ACCESS read-create
			STATUS current
			DESCRIPTION
				"Description."
			::= { wsMgmtNetworkDiscoveryEntry 8 }

		-- 1.3.6.1.4.1.388.14.4.1.7.2.1.9
		wsMgmtDiscoveredDeviceDiscoveryTime OBJECT-TYPE
			SYNTAX DateAndTime
			MAX-ACCESS read-create
			STATUS current
			DESCRIPTION
				"Description."
			::= { wsMgmtNetworkDiscoveryEntry 9 }

		-- 1.3.6.1.4.1.388.14.4.1.7.2.1.10
		wsMgmtDiscoveredNetworkDevicesTableRow OBJECT-TYPE
			SYNTAX RowStatus
			MAX-ACCESS read-create
			STATUS current
			DESCRIPTION
				"Description."
			::= { wsMgmtNetworkDiscoveryEntry 10 }

		-- 1.3.6.1.4.1.388.14.4.1.7.1
		wsMgmtNetworkDiscoveryProfilesTable OBJECT-TYPE
			SYNTAX SEQUENCE OF WsMgmtNetworkDiscoveryProfilesEntry
			MAX-ACCESS not-accessible
			STATUS current
			DESCRIPTION
				"Description."
			::= { wsMgmtNwDiscovery 1 }

		-- 1.3.6.1.4.1.388.14.4.1.7.1.1
		wsMgmtNetworkDiscoveryProfilesEntry OBJECT-TYPE
			SYNTAX WsMgmtNetworkDiscoveryProfilesEntry
			MAX-ACCESS not-accessible
			STATUS current
			DESCRIPTION
				"Description."
			INDEX { wsMgmtDiscoveryProfileIndex }
			::= { wsMgmtNetworkDiscoveryProfilesTable 1 }

		WsMgmtNetworkDiscoveryProfilesEntry ::=
			SEQUENCE { 
				wsMgmtDiscoveryProfileIndex
					Integer32,
				wsMgmtDiscoveryProfileName
					DisplayString,
				wsMgmtDiscoveryStartIPAddr
					IpAddress,
				wsMgmtDiscoveryEndIPAddr
					IpAddress,
				wsMgmtDiscoverySnmpVersion
					INTEGER,
				wsMgmtDiscoveryLastDoneTime
					DateAndTime,
				wsMgmtDiscoveryLastDoneStatus
					INTEGER,
				wsMgmtDiscoveryProfileRowStatus
					RowStatus
			 }

		-- 1.3.6.1.4.1.388.14.4.1.7.1.1.1
		wsMgmtDiscoveryProfileIndex OBJECT-TYPE
			SYNTAX Integer32 (1..127)
			MAX-ACCESS read-only
			STATUS current
			DESCRIPTION
				"Description."
			::= { wsMgmtNetworkDiscoveryProfilesEntry 1 }

		-- 1.3.6.1.4.1.388.14.4.1.7.1.1.2
		wsMgmtDiscoveryProfileName OBJECT-TYPE
			SYNTAX DisplayString (SIZE (4..128))
			MAX-ACCESS read-write
			STATUS current
			DESCRIPTION
				"Description."
			::= { wsMgmtNetworkDiscoveryProfilesEntry 2 }

		-- 1.3.6.1.4.1.388.14.4.1.7.1.1.3
		wsMgmtDiscoveryStartIPAddr OBJECT-TYPE
			SYNTAX IpAddress
			MAX-ACCESS read-write
			STATUS current
			DESCRIPTION
				"Description."
			::= { wsMgmtNetworkDiscoveryProfilesEntry 3 }

		-- 1.3.6.1.4.1.388.14.4.1.7.1.1.4
		wsMgmtDiscoveryEndIPAddr OBJECT-TYPE
			SYNTAX IpAddress
			MAX-ACCESS read-write
			STATUS current
			DESCRIPTION
				"Description."
			::= { wsMgmtNetworkDiscoveryProfilesEntry 4 }

		-- 1.3.6.1.4.1.388.14.4.1.7.1.1.5
		wsMgmtDiscoverySnmpVersion OBJECT-TYPE
			SYNTAX INTEGER
				{
				snmpV1V2c(1),
				snmpV3(2),
				snmpV1V2candsnmpV3(3)
				}
			MAX-ACCESS read-write
			STATUS current
			DESCRIPTION
				"Description."
			::= { wsMgmtNetworkDiscoveryProfilesEntry 5 }

		-- 1.3.6.1.4.1.388.14.4.1.7.1.1.6
		wsMgmtDiscoveryLastDoneTime OBJECT-TYPE
			SYNTAX DateAndTime
			MAX-ACCESS read-only
			STATUS current
			DESCRIPTION
				"Description."
			::= { wsMgmtNetworkDiscoveryProfilesEntry 6 }

		-- 1.3.6.1.4.1.388.14.4.1.7.1.1.7
		wsMgmtDiscoveryLastDoneStatus OBJECT-TYPE
			SYNTAX INTEGER
				{
				neverDone(1),
				successful(2),
				abandoned(3),
				failed(4)
				}
			MAX-ACCESS read-only
			STATUS current
			DESCRIPTION
				"Description."
			DEFVAL { 1 }
			::= { wsMgmtNetworkDiscoveryProfilesEntry 7 }

		-- 1.3.6.1.4.1.388.14.4.1.7.1.1.8
		wsMgmtDiscoveryProfileRowStatus OBJECT-TYPE
			SYNTAX RowStatus
			MAX-ACCESS read-write
			STATUS current
			DESCRIPTION
				"Description."
			::= { wsMgmtNetworkDiscoveryProfilesEntry 8 }

		-- 1.3.6.1.4.1.388.14.4.1.8
		wsMgmtKey OBJECT IDENTIFIER ::= { wsMgmtMib 8 }

		-- 1.3.6.1.4.1.388.14.4.1.8.1
		wsMgmtGenKey OBJECT-TYPE
			SYNTAX Unsigned32
			MAX-ACCESS read-only
			STATUS current
			DESCRIPTION
				"gen key for mgmt"
			::= { wsMgmtKey 1 }

		-- 1.3.6.1.4.1.388.14.4.1.11
		wsMgmtSsh OBJECT IDENTIFIER ::= { wsMgmtMib 11 }

		-- 1.3.6.1.4.1.388.14.4.1.11.1
		wsMgmtSshEnable OBJECT-TYPE
			SYNTAX TruthValue
			MAX-ACCESS read-write
			STATUS current
			DESCRIPTION
				"Description."
			::= { wsMgmtSsh 1 }

		-- 1.3.6.1.4.1.388.14.4.1.11.2
		wsMgmtSshPort OBJECT-TYPE
			SYNTAX Integer32
			MAX-ACCESS read-write
			STATUS current
			DESCRIPTION
				"Description."
			::= { wsMgmtSsh 2 }

		-- 1.3.6.1.4.1.388.14.4.1.11.5
		wsMgmtSshKeyPairName OBJECT-TYPE
			SYNTAX DisplayString (SIZE (0..128))
			MAX-ACCESS read-write
			STATUS current
			DESCRIPTION
				"Description."
			::= { wsMgmtSsh 5 }

		-- 1.3.6.1.4.1.388.14.4.1.13
		wsMgmtTelnet OBJECT IDENTIFIER ::= { wsMgmtMib 13 }

		-- 1.3.6.1.4.1.388.14.4.1.13.1
		wsMgmtTelnetEnable OBJECT-TYPE
			SYNTAX TruthValue
			MAX-ACCESS read-write
			STATUS current
			DESCRIPTION
				"Description."
			::= { wsMgmtTelnet 1 }

		-- 1.3.6.1.4.1.388.14.4.1.13.2
		wsMgmtTelnetPort OBJECT-TYPE
			SYNTAX Integer32
			MAX-ACCESS read-write
			STATUS current
			DESCRIPTION
				"Description."
			::= { wsMgmtTelnet 2 }

		-- 1.3.6.1.4.1.388.14.4.1.14
		wsMgmtFtp OBJECT IDENTIFIER ::= { wsMgmtMib 14 }

		-- 1.3.6.1.4.1.388.14.4.1.14.1
		wsMgmtFtpEnable OBJECT-TYPE
			SYNTAX TruthValue
			MAX-ACCESS read-write
			STATUS current
			DESCRIPTION
				"Enable the FTP server"
			::= { wsMgmtFtp 1 }

		-- 1.3.6.1.4.1.388.14.4.1.14.2
		wsMgmtFtpRoot OBJECT-TYPE
			SYNTAX DisplayString
			MAX-ACCESS read-write
			STATUS current
			DESCRIPTION
				"Set the root dir of the FTP server"
			::= { wsMgmtFtp 2 }

		-- 1.3.6.1.4.1.388.14.4.1.14.3
		wsMgmtFtpPwd OBJECT-TYPE
			SYNTAX DisplayString
			MAX-ACCESS read-write
			STATUS current
			DESCRIPTION
				"Set the password for the FTP server"
			::= { wsMgmtFtp 3 }

		-- 1.3.6.1.4.1.388.14.4.1.100
		wsMgmtConformance OBJECT IDENTIFIER ::= { wsMgmtMib 100 }

		-- 1.3.6.1.4.1.388.14.4.1.100.1
		wsMgmtCompliances OBJECT IDENTIFIER ::= { wsMgmtConformance 1 }

		-- 1.3.6.1.4.1.388.14.4.1.100.1.1
		wsMgmtCompliance MODULE-COMPLIANCE
			STATUS current
			DESCRIPTION 
				"Description."
			MODULE -- this module
				MANDATORY-GROUPS { wsMgmtGroup }
			::= { wsMgmtCompliances 1 }

		-- 1.3.6.1.4.1.388.14.4.1.100.2
		wsMgmtGroups OBJECT IDENTIFIER ::= { wsMgmtConformance 2 }

		-- 1.3.6.1.4.1.388.14.4.1.100.2.2
		wsMgmtGroup OBJECT-GROUP
			OBJECTS { wsMgmtSystemReset, wsMgmtSystemFactoryDefaultCfg, wsMgmtSnmpV2Switch, wsMgmtHttpEnable, wsMgmtAlarmStatus, 
				wsMgmtAlarmSeverity, wsMgmtAlarmTimestamp, wsMgmtAlarmRowStatus, wsMgmtClearAllAlarms, wsMgmtAcknowledgeAllAlarms, 
				wsMgmtAlarmIndex, wsMgmtModuleName, wsMgmtSnmpV3Switch, wsMgmtHttpsEnable, wsMgmtNewAlarmsCount, 
				wsMgmtTotalAlarmsCount, wsMgmtGenKey, wsMgmtCertCreateAction, wsMgmtCertKeyLabel, wsMgmtCertKeySize, 
				wsMgmtCertNumTrustPoint, wsMgmtCertCreateStatus, wsMgmtCertKeyRowStatus, wsMgmtSshEnable, wsMgmtSshPort, 
				wsMgmtSshKeyPairName, wsMgmtTelnetEnable, wsMgmtTelnetPort, wsMgmtAlarmMessage, wsMgmtAlarmTypeID, 
				wsMgmtAlarmTypeName, wsMgmtCertConfigTrustpoint, wsMgmtCertConfigKey, wsMgmtCertConfigCommonName, wsMgmtCertConfigOrgUnit, 
				wsMgmtCertConfigOrg, wsMgmtCertConfigState, wsMgmtCertConfigCity, wsMgmtCertConfigCountry, wsMgmtCertConfigFqdn, 
				wsMgmtCertConfigIP, wsMgmtCertConfigEmail, wsMgmtCertConfigPassword, wsMgmtCertConfigCompany, wsMgmtCertViewType, 
				wsMgmtCertConfigRowStatus, wsMgmtCertViewTrustpoint, wsMgmtCertViewValidStart, wsMgmtAlarmsIndexLow, wsMgmtAlarmsIndexHigh, 
				wsMgmCriticalAlarmsCount, wsMgmMajorAlarmsCount, wsMgmWarningAlarmsCount, wsMgmInfoAlarmsCount, wsMgmNormalAlarmsCount, 
				wsMgmtTotalAlarmsCountSinceBoot, wsMgmtFtpEnable, wsMgmtFtpRoot, wsMgmtFtpPwd, wsMgmtDiscoveredNetworkDevicesTableRow, 
				wsMgmtDiscoveredDeviceDiscoveryTime, wsMgmtDiscoveredDeviceDiscoveryProfileName, wsMgmtDiscoveredDeviceDescr, wsMgmtDiscoveredDeviceLocation, wsMgmtDiscoveredDeviceName, 
				wsMgmtDiscoveredDeviceClusterId, wsMgmtDiscoveredDeviceSwVersion, wsMgmtDiscoveredDeviceHwVersion, wsMgmtDiscoveredDeviceIpAddr, wsMgmtDiscoveryProfileRowStatus, 
				wsMgmtDiscoveryLastDoneStatus, wsMgmtDiscoveryLastDoneTime, wsMgmtDiscoverySnmpVersion, wsMgmtDiscoveryEndIPAddr, wsMgmtDiscoveryStartIPAddr, 
				wsMgmtDiscoveryProfileName, wsMgmtDiscoveryProfileIndex, wsMgmtHttpTrustpoint, wsMgmUnacknowledgedCriticalAlarmsCountSinceBoot, wsMgmUnacknowledgedMajorAlarmsCountSinceBoot, 
				wsMgmUnacknowledgedWarningAlarmsCountSinceBoot, wsMgmUnacknowledgedInfoAlarmsCountSinceBoot, wsMgmUnacknowledgedNormalAlarmsCountSinceBoot, wsMgmUnacknowledgedMajorAlarmsCount, wsMgmUnacknowledgedWarningAlarmsCount, 
				wsMgmUnacknowledgedInfoAlarmsCount, wsMgmUnacknowledgedNormalAlarmsCount, wsMgmUnacknowledgedCriticalAlarmsCount, wsMgmtCertViewValidEnd, wsMgmtCertViewSubjectCommonName, 
				wsMgmtCertViewSubjectOrgUnit, wsMgmtCertViewSubjectOrg, wsMgmtCertViewSubjectCity, wsMgmtCertViewSubjectState, wsMgmtCertViewSubjectCountry, 
				wsMgmtCertViewSubjectEmail, wsMgmtCertViewIssuerCommonName, wsMgmtCertViewIssuerOrgUnit, wsMgmtCertViewIssuerOrg, wsMgmtCertViewIssuerCity, 
				wsMgmtCertViewIssuerState, wsMgmtCertViewIssuerCountry, wsMgmtCertViewIssuerEmail }
			STATUS current
			DESCRIPTION 
				"Description."
			::= { wsMgmtGroups 2 }

		-- 1.3.6.1.4.1.388.14.4.1.100.2.3
		wsMgmtObsoleteGroup OBJECT-GROUP
			OBJECTS { wsMgmtCertCurrentCountry, wsMgmtCertCurrentState, wsMgmtCertCurrentCity, wsMgmtCertCurrentOrg, wsMgmtCertCurrentOrgUnit, 
				wsMgmtCertCurrentCommonName, wsMgmtCertCurrentIssuer, wsMgmtCertCurrentValidStart, wsMgmtCertCurrentValidEnd, wsMgmtCertCurrentTrustPoint, 
				wsMgmtCertFileName, wsMgmtCertAction, wsMgmtCertStatus, wsMgmtCertCountry, wsMgmtCertState, 
				wsMgmtCertCity, wsMgmtCertOrg, wsMgmtCertOrgUnit, wsMgmtCertCommonName, wsMgmtCertIssuer, 
				wsMgmtCertEmail, wsMgmtCertPwd, wsMgmtCertCompany, wsMgmtCertValidStart, wsMgmtCertValidEnd, 
				wsMgmtCertTrustPoint, wsMgmtGenKey }
			STATUS obsolete
			DESCRIPTION 
				"Description."
			::= { wsMgmtGroups 3 }
	END
