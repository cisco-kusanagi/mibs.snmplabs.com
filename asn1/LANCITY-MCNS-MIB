LANCITY-MCNS-MIB DEFINITIONS ::= BEGIN

IMPORTS
    MODULE-IDENTITY, OBJECT-TYPE, Integer32, IpAddress, Counter32, TimeTicks
--    ,Unsigned32
            FROM SNMPv2-SMI
    RowStatus, TruthValue, DisplayString, MacAddress
            FROM SNMPv2-TC

--    OBJECT-GROUP, MODULE-COMPLIANCE
--            FROM SNMPv2-CONF
    TRAP-TYPE
            FROM RFC-1215
    ifIndex
            FROM IF-MIB
    dot1dTpPort
            FROM BRIDGE-MIB
    lancity
            FROM LANCITY-MIB
    docsDevEvText, docsDevNmAccessEntry
	    FROM DOCS-CABLE-DEVICE-MIB
    TenthdBmV
            FROM DOCS-IF-MIB;

lancityMcnsMib MODULE-IDENTITY
    LAST-UPDATED    "9903302222Z" -- March 30, 1999
    ORGANIZATION    "Bay Networks Broadband Technologies Division"
    CONTACT-INFO
         "Dale Hokanson
          Postal: Bay Networks
                  Broadband Technologies Division
                  200 Bulfinch Drive
                  Andover, MA 01810
                  U.S.A.
          Phone:  +1 978 682 1600
          E-mail: support@lancity.com"

    DESCRIPTION
        "This is the portion of the Lancity enterprise MIB that applies
         to MCNS cable modems and related devices."

    ::= { lancity 60 }

-- lancity MCNS product id's group

lancityMcnsProducts   OBJECT IDENTIFIER ::= { lancityMcnsMib 1 }

lancityMcnsProdIdCMTS OBJECT IDENTIFIER ::= { lancityMcnsProducts 1 }

lancityMcnsProdIdCM   OBJECT IDENTIFIER ::= { lancityMcnsProducts 2 }
 

-- lancity MCNS MIB groups
lccmtsif      OBJECT IDENTIFIER ::= { lancityMcnsMib 2 }  -- CMTS RF interface
lccmif        OBJECT IDENTIFIER ::= { lancityMcnsMib 3 }  -- CM RF interface
lcifcommon    OBJECT IDENTIFIER ::= { lancityMcnsMib 4 }  -- RF common, CM/CMTS

lccmtsdevice  OBJECT IDENTIFIER ::= { lancityMcnsMib 5 }  -- CMTS as a device
lccmdevice    OBJECT IDENTIFIER ::= { lancityMcnsMib 6 }  -- CM as a device
lcdevicecommon OBJECT IDENTIFIER ::= { lancityMcnsMib 7 } -- device common

lctrapvars OBJECT IDENTIFIER ::= { lcdevicecommon 4 } --device common trap vars
                                  --(trap variables must have OID's associated
                                  -- with them, thus we keep them in a separate
                                  -- group).		           

-- --------------------------------------------------------------------------
-- Begin CMTS Interface section
-- --------------------------------------------------------------------------

lcCmtsUpstreamTable OBJECT-TYPE
    SYNTAX          SEQUENCE OF LcCmtsUpstreamEntry
    MAX-ACCESS      not-accessible
    STATUS          current
    DESCRIPTION
        "Defines properties of upstream channels, from the CMTS."
    ::= { lccmtsif 1 }

lcCmtsUpstreamEntry OBJECT-TYPE
    SYNTAX          LcCmtsUpstreamEntry
    MAX-ACCESS      not-accessible
    STATUS          current
    DESCRIPTION
        "Defines properties of an upstream channel, from the CMTS."
    INDEX           { ifIndex }
    ::= { lcCmtsUpstreamTable 1 }

LcCmtsUpstreamEntry ::= SEQUENCE {
	lcCmtsUpMinimumMapSize		INTEGER,
	lcCmtsUpMaximumMapSize		INTEGER,
	lcCmtsUpContentionPerMap	INTEGER,
	lcCmtsUpRequestDataAllowed	INTEGER,
	lcCmtsUpMaxDataInContention	INTEGER,
	lcCmtsUpInitialRangingInterval	INTEGER,
	lcCmtsUpHighPriorityThreshold	INTEGER,
	lcCmtsUpGuaranteedThreshold	INTEGER,
	lcCmtsUpPublicationDelay	INTEGER,
	lcCmtsUpNFlowControlledMaps	Counter32,
	lcCmtsUpNNonFlowControlledMaps	Counter32,
	lcCmtsUpChannelPower            TenthdBmV,
	lcCmtsUpInputPowerWindow	TenthdBmV
	}

lcCmtsUpMinimumMapSize OBJECT-TYPE
	SYNTAX INTEGER
	MAX-ACCESS read-write
	STATUS current
	DESCRIPTION
        "Minimum number of slots to be mapped in each Map PDU."
	::= { lcCmtsUpstreamEntry 1 }


lcCmtsUpMaximumMapSize OBJECT-TYPE
	SYNTAX INTEGER
	MAX-ACCESS read-write
	STATUS current
	DESCRIPTION
        "Maximum number of slots to be mapped in each Map PDU."
	::= { lcCmtsUpstreamEntry 2 }

lcCmtsUpContentionPerMap	OBJECT-TYPE
	SYNTAX		INTEGER
	MAX-ACCESS	read-write
	STATUS		current
	DESCRIPTION
        "The number of mini-slots allotted to contention (REQ or REQ-DATA)
	 per MAP PDU."
	::= { lcCmtsUpstreamEntry 3 }


lcCmtsUpRequestDataAllowed  OBJECT-TYPE
	SYNTAX INTEGER { allowed(1), disallowed(2), adaptive(3) }
	MAX-ACCESS read-write
	STATUS current
	DESCRIPTION
        "Specifies whether or not the CMTS will allow contention data on this
	upstream interface."
	::= { lcCmtsUpstreamEntry 4 }

--
-- This object would be more intuitive if expressed in terms of payload bytes,
-- rather than mini-slots.
--

lcCmtsUpMaxDataInContention	OBJECT-TYPE
	SYNTAX		INTEGER
	MAX-ACCESS	read-write
	STATUS		current
	DESCRIPTION
        "The number of mini-slots that may be used for a single upstream
	 contention transmission."
	::= { lcCmtsUpstreamEntry 5 }


lcCmtsUpInitialRangingInterval OBJECT-TYPE
	SYNTAX INTEGER
	UNITS "microseconds"
	MAX-ACCESS read-write
	STATUS current
	DESCRIPTION
        "The duration, in microseconds, of the initial ranging interval. This interval
	is used by unranged modems to enter the network, and so must be long
	enough to admit the most distant modem."
	::= { lcCmtsUpstreamEntry 6 }


lcCmtsUpHighPriorityThreshold OBJECT-TYPE
	SYNTAX INTEGER
	MAX-ACCESS read-write
	STATUS current
	DESCRIPTION
        "Weighting of high priority queue is-a-vis normal priority queue."
	::= { lcCmtsUpstreamEntry 7 }


lcCmtsUpGuaranteedThreshold OBJECT-TYPE
	SYNTAX INTEGER (0..100)
	MAX-ACCESS read-write
	STATUS current
	DESCRIPTION
        "Permitted aggregate CIR, as a percentage of the overall channel bandwidth."
	::= { lcCmtsUpstreamEntry 8 }


lcCmtsUpPublicationDelay OBJECT-TYPE
	SYNTAX INTEGER
	UNITS "microseconds"
	MAX-ACCESS read-only
	STATUS current
	DESCRIPTION
        "A sum of architectural constants, parameters, and network status
	(RTD) that governs the difference between the publication time of the
	MAP and its effectiveness."
	::= { lcCmtsUpstreamEntry 9 }


lcCmtsUpNFlowControlledMaps OBJECT-TYPE
	SYNTAX Counter32
	MAX-ACCESS read-only
	STATUS current
	DESCRIPTION
        "The number of Map PDUs that were generated under
	flow-controlled (prioritized) conditions."
	::= { lcCmtsUpstreamEntry 10 }


lcCmtsUpNNonFlowControlledMaps OBJECT-TYPE
	SYNTAX Counter32
	MAX-ACCESS read-only
	STATUS current
	DESCRIPTION
	"The number of Map PDUs that were generated under FIFO conditions."
	::= { lcCmtsUpstreamEntry 11 }

lcCmtsUpChannelPower OBJECT-TYPE
	SYNTAX      TenthdBmV
	MAX-ACCESS  read-write
	STATUS      current
	DESCRIPTION
	"The CMTS receiver input power level, which is the nominal
	 receive power level for upstream data.
         This value will be automatically scaled by the CMTS if the
         channel's width is changed."
	::= { lcCmtsUpstreamEntry 12 }
	
lcCmtsUpInputPowerWindow OBJECT-TYPE
	SYNTAX	    TenthdBmV	
	MAX-ACCESS  read-write
	STATUS      current
	DESCRIPTION
	"The CMTS receiver input power window (+/- tenths dB) at which 
	a CM is allowed to operated in.  This value has the range
	of 20 -150 tenths of dB which represents windows +/- 2 dB to 
	a window of +/- 15 dB.  The theoretical upper limit of 
        this range is 9 dB."
	::= { lcCmtsUpstreamEntry 13 }


lcCmtsCurrentTemp OBJECT-TYPE
	SYNTAX INTEGER
	MAX-ACCESS read-only
	STATUS current
	DESCRIPTION
        "Current temperature of a CMTS device in degrees 
         Celsius."
	::= { lccmtsif 2 }

lcCmtsHighTempThreshold OBJECT-TYPE
	SYNTAX INTEGER (0..100)
	MAX-ACCESS read-write
	STATUS current
	DESCRIPTION
        "High temperature threshold limit of a CMTS device in degrees
         Celsius, above which an event occurs to signal that the 
         threshold has been exceeded.  The device temperature is read
         once per minute and compared to this threshold value.  A trap
         is sent out if the event's priority indicates that a trap
         is to be sent (refer to the docsDevEvControlTable object in
	 DOCS-CABLE-DEVICE-MIB).  The priority of this event is critical(3)."
	DEFVAL  { 100 }	
	::= { lccmtsif 3 }

lccmtsUpstreamIngressAvoidance OBJECT IDENTIFIER ::= { lccmtsif 4 }  -- CMTS Ingress avoidance interface.

--Ingress Avoidance Enable Table
lcCmtsUpstreamIngressAvoidanceEnableTable OBJECT-TYPE
    SYNTAX          SEQUENCE OF LcCmtsIngressAvoidanceEnableEntry
    MAX-ACCESS      not-accessible
    STATUS          current
    DESCRIPTION
        "Defines which upstreams are enabling this feature and which
         metrics to use."
    ::= {lccmtsUpstreamIngressAvoidance 1 }

lcCmtsIngressAvoidanceEnableEntry OBJECT-TYPE
    SYNTAX          LcCmtsIngressAvoidanceEnableEntry
    MAX-ACCESS      not-accessible
    STATUS          current
    DESCRIPTION
        "Defines which upstreams are enabling this feature and which
         metrics to use."
    INDEX           { ifIndex }
    ::= { lcCmtsUpstreamIngressAvoidanceEnableTable 1 }

LcCmtsIngressAvoidanceEnableEntry ::= SEQUENCE {
	lcCmtsIngressAvoidanceEnable	INTEGER,
	lcCmtsMetric1Enable		INTEGER
	}

lcCmtsIngressAvoidanceEnable OBJECT-TYPE
	SYNTAX INTEGER {off(0), on(1)}
	MAX-ACCESS read-write
	STATUS current
	DESCRIPTION
        "Enable Ingress Avoidance for the Upstream."
	::= { lcCmtsIngressAvoidanceEnableEntry 1 }

lcCmtsMetric1Enable OBJECT-TYPE
	SYNTAX INTEGER {off(0), on(1)}
	MAX-ACCESS read-write
	STATUS current
	DESCRIPTION
        "Enable the metric associated with Ingress Avoidance."
	::= { lcCmtsIngressAvoidanceEnableEntry 2 }


--Ingress Avoidance Frequency Configuration Table
lcCmtsIngressAvoidanceFrequencyConfigTable OBJECT-TYPE
    SYNTAX          SEQUENCE OF LcCmtsIngressAvoidanceFrequencyConfigEntry
    MAX-ACCESS      not-accessible
    STATUS          current
    DESCRIPTION
        "Defines the provisioned frequencies per carrier path."
    ::= {lccmtsUpstreamIngressAvoidance 2 }

lcCmtsIngressAvoidanceFrequencyConfigEntry OBJECT-TYPE
    SYNTAX          LcCmtsIngressAvoidanceFrequencyConfigEntry
    MAX-ACCESS      not-accessible
    STATUS          current
    DESCRIPTION
        "Defines which upstreams are enabling this feature and which
         metrics to use."
    INDEX           {lcCmtsCarrierPathIndex,lcCmtsFreqConfigIndex}
    ::= { lcCmtsIngressAvoidanceFrequencyConfigTable 1 }

LcCmtsIngressAvoidanceFrequencyConfigEntry ::= SEQUENCE {
	lcCmtsCarrierPathIndex		INTEGER,	
	lcCmtsFreqConfigIndex	        INTEGER,
	lcCmtsFreqAvailable		INTEGER,
	lcCmtsStartFrequency		INTEGER,
	lcCmtsStopFrequency		INTEGER
	}

lcCmtsCarrierPathIndex OBJECT-TYPE
	SYNTAX INTEGER 
	MAX-ACCESS not-accessible
	STATUS current
	DESCRIPTION
        "Carrier path index for the frequency ranges."
	::= { lcCmtsIngressAvoidanceFrequencyConfigEntry 1 }

	lcCmtsFreqConfigIndex OBJECT-TYPE
	SYNTAX INTEGER 
	MAX-ACCESS not-accessible
	STATUS current
	DESCRIPTION
        "Index for frequency ranges for each carrier path."
	::= { lcCmtsIngressAvoidanceFrequencyConfigEntry 2 }

lcCmtsFreqAvailable OBJECT-TYPE
	SYNTAX INTEGER {no(0), yes(1)}
	MAX-ACCESS read-write
	STATUS current
	DESCRIPTION
        "Allow frequency range to be used for the carrier path."
	::= { lcCmtsIngressAvoidanceFrequencyConfigEntry 3 }

lcCmtsStartFrequency OBJECT-TYPE
	SYNTAX INTEGER
	MAX-ACCESS read-write
	STATUS current
	DESCRIPTION
        "Beginning frequency in the frequency range (Hz).  Range must
	 be within the 5-42 MHz range and start must be less than or
	 equal to stop frequency."
	::= { lcCmtsIngressAvoidanceFrequencyConfigEntry 4 }

lcCmtsStopFrequency OBJECT-TYPE
	SYNTAX INTEGER
	MAX-ACCESS read-write
	STATUS current
	DESCRIPTION
        "End frequency in the frequency range (Hz).  Range must
	 be within the 5-42 MHz range and start must be less than or
	 equal to stop frequency."
	::= { lcCmtsIngressAvoidanceFrequencyConfigEntry 5 }


--Ingress Avoidance Change Preference Table
lcCmtsIngressAvoidanceChangePrefTable OBJECT-TYPE
    SYNTAX          SEQUENCE OF LcCmtsIngressAvoidanceChangePrefEntry
    MAX-ACCESS      not-accessible
    STATUS          current
    DESCRIPTION
        "Defines carrier paths (Physical Connectivity) and channel groups
         for each upstream."
    ::= {lccmtsUpstreamIngressAvoidance 3 }

lcCmtsIngressAvoidanceChangePrefEntry OBJECT-TYPE
    SYNTAX          LcCmtsIngressAvoidanceChangePrefEntry
    MAX-ACCESS      not-accessible
    STATUS          current
    DESCRIPTION
        "Defines carrier paths (Physical Connectivity) and channel groups
        for each upstream."
    INDEX           {ifIndex}
    ::= { lcCmtsIngressAvoidanceChangePrefTable 1 }

LcCmtsIngressAvoidanceChangePrefEntry ::= SEQUENCE {
	lcCmtsChangePreference		INTEGER
	}

lcCmtsChangePreference OBJECT-TYPE
	SYNTAX INTEGER {profile(1),frequency(2)}
	MAX-ACCESS read-write
	STATUS current
	DESCRIPTION
        "Defines which type of change is the prefered change if ingress
	 avoidance detects a problem in the current configuration."
	::= { lcCmtsIngressAvoidanceChangePrefEntry 1 }

--Ingress Avoidance Threshold Table
lcCmtsIngressAvoidanceThresholdTable OBJECT-TYPE
    SYNTAX          SEQUENCE OF LcCmtsIngressAvoidanceThresholdEntry
    MAX-ACCESS      not-accessible
    STATUS          current
    DESCRIPTION
        "Defines threshold for each of the ingress avoidance
	available metrics."
    ::= {lccmtsUpstreamIngressAvoidance 4 }

lcCmtsIngressAvoidanceThresholdEntry OBJECT-TYPE
    SYNTAX          LcCmtsIngressAvoidanceThresholdEntry
    MAX-ACCESS      not-accessible
    STATUS          current
    DESCRIPTION
        "Defines threshold for each of the ingress avoidance
	available metrics."
    INDEX           {ifIndex}
    ::= { lcCmtsIngressAvoidanceThresholdTable 1 }

LcCmtsIngressAvoidanceThresholdEntry ::= SEQUENCE {
	lcCmtsMetric1GreenToYellow		INTEGER,	
	lcCmtsMetric1YellowToRed		INTEGER
	}

lcCmtsMetric1GreenToYellow OBJECT-TYPE
	SYNTAX INTEGER 
	MAX-ACCESS read-write
	STATUS current
	DESCRIPTION
        "Defines the green to yellow threshold for a particular
	metric."
	::= { lcCmtsIngressAvoidanceThresholdEntry 1 }

lcCmtsMetric1YellowToRed OBJECT-TYPE
	SYNTAX INTEGER 
	MAX-ACCESS read-write
	STATUS current
	DESCRIPTION
        "Defines the yellow to red threshold for a particular
	metric.  A drop below this level will cause an ingress
	avoidance action if the metric is enabled."
	::= { lcCmtsIngressAvoidanceThresholdEntry 2 }



--Ingress Avoidance Profile Table
lcCmtsIngressAvoidanceProfileTable OBJECT-TYPE
    SYNTAX          SEQUENCE OF LcCmtsIngressAvoidanceProfileEntry
    MAX-ACCESS      not-accessible
    STATUS          current
    DESCRIPTION
        "Defines with profile in the Tranmission table will be
	used for ingress avoidance.  The order from 1-3 is the
	desired order for profile use."
    ::= {lccmtsUpstreamIngressAvoidance 5 }

lcCmtsIngressAvoidanceProfileEntry OBJECT-TYPE
    SYNTAX          LcCmtsIngressAvoidanceProfileEntry
    MAX-ACCESS      not-accessible
    STATUS          current
    DESCRIPTION
        "Defines with profile in the Tranmission table will be
	used for ingress avoidance.  The order from 1-3 is the
	desired order for profile use."
    INDEX           {lcCmtsProfileCarrierPathIndex, lcCmtsProfilePreference}
    ::= { lcCmtsIngressAvoidanceProfileTable 1 }

LcCmtsIngressAvoidanceProfileEntry ::= SEQUENCE {
	lcCmtsProfileCarrierPathIndex	INTEGER,
	lcCmtsProfilePreference		INTEGER,	
	lcCmtsStatus			INTEGER,
	lcCmtsTransmissionProfileIndex	INTEGER
	}

lcCmtsProfileCarrierPathIndex OBJECT-TYPE
	SYNTAX INTEGER 
	MAX-ACCESS not-accessible
	STATUS current
	DESCRIPTION
        "Carrier path index for the profile table."
	::= {lcCmtsIngressAvoidanceProfileEntry 1 }

lcCmtsProfilePreference OBJECT-TYPE
	SYNTAX INTEGER 
	MAX-ACCESS not-accessible
	STATUS current
	DESCRIPTION
        "Profile index per carrier path."
	::= { lcCmtsIngressAvoidanceProfileEntry 2 }

lcCmtsStatus OBJECT-TYPE
	SYNTAX INTEGER {off(0), on(1)}
	MAX-ACCESS read-write
	STATUS current
	DESCRIPTION
        "Defines whether or not the particular profile is enabled
	for use in ingress avoidance."
	::= { lcCmtsIngressAvoidanceProfileEntry 3 }

lcCmtsTransmissionProfileIndex OBJECT-TYPE
	SYNTAX INTEGER 
	MAX-ACCESS read-write
	STATUS current
	DESCRIPTION
        "Describes the index into the transmission profile table."
	::= { lcCmtsIngressAvoidanceProfileEntry 4 }


--Ingress Avoidance TransmissionProfile Table
lcCmtsIngressAvoidanceTxProfileTable OBJECT-TYPE
    SYNTAX          SEQUENCE OF LcCmtsIngressAvoidanceTxProfileEntry
    MAX-ACCESS      not-accessible
    STATUS          current
    DESCRIPTION
        "Defines Modulation Profile and Bandwidth.  Coding Efficiency
	is calculated based on the entries."
    ::= {lccmtsUpstreamIngressAvoidance 6 }

lcCmtsIngressAvoidanceTxProfileEntry OBJECT-TYPE
    SYNTAX          LcCmtsIngressAvoidanceTxProfileEntry
    MAX-ACCESS      not-accessible
    STATUS          current
    DESCRIPTION
        "Defines with profile in the Tranmission table will be
	used for ingress avoidance.  The order from 1-3 is the
	desired order for profile use."
    INDEX           {lcCmtsTxProfileIndex}
    ::= { lcCmtsIngressAvoidanceTxProfileTable 1 }

LcCmtsIngressAvoidanceTxProfileEntry ::= SEQUENCE {
	lcCmtsTxProfileIndex		INTEGER,	
	lcCmtsModulationProfileIndex	INTEGER,	
	lcCmtsBandwidth			INTEGER,
	lcCmtsCodingEfficiency		INTEGER
	}

lcCmtsTxProfileIndex OBJECT-TYPE
	SYNTAX INTEGER 
	MAX-ACCESS not-accessible
	STATUS current
	DESCRIPTION
        "Index for the transmission profile table."
	::= {lcCmtsIngressAvoidanceTxProfileEntry 1 }

lcCmtsModulationProfileIndex OBJECT-TYPE
	SYNTAX INTEGER 
	MAX-ACCESS read-write
	STATUS current
	DESCRIPTION
        "Index into the MCNS Upstream Modulation Table."
	::= { lcCmtsIngressAvoidanceTxProfileEntry 2 }

lcCmtsBandwidth OBJECT-TYPE
	SYNTAX INTEGER 
	MAX-ACCESS read-write
	STATUS current
	DESCRIPTION
        "Bandwidth to be used with the modulation profile selected."
	::= { lcCmtsIngressAvoidanceTxProfileEntry 3 }

lcCmtsCodingEfficiency OBJECT-TYPE
	SYNTAX INTEGER 
	MAX-ACCESS read-only
	STATUS current
	DESCRIPTION
        "Coding efficiency is calculated based on the modulation
	profile and bandwidth selected.  This number represents 
	information bytes/second for the given settings.  This
	calculation in based on short and long data grants and
	a min and max size packet transmitted for each type of grant."
	::= { lcCmtsIngressAvoidanceTxProfileEntry 4 }

--Ingress Avoidance Metric Config Table
lcCmtsIngressAvoidanceMetricConfigTable OBJECT-TYPE
    SYNTAX          SEQUENCE OF LcCmtsIngressAvoidanceMetricConfigEntry
    MAX-ACCESS      not-accessible
    STATUS          current
    DESCRIPTION
        "Defines the aging multipliers and calculation timers for
	each metric."
    ::= {lccmtsUpstreamIngressAvoidance 7 }

lcCmtsIngressAvoidanceMetricConfigEntry OBJECT-TYPE
    SYNTAX          LcCmtsIngressAvoidanceMetricConfigEntry
    MAX-ACCESS      not-accessible
    STATUS          current
    DESCRIPTION
        "Defines the aging multipliers and calculation timers for
	each metric."
    INDEX           {lcCmtsMetricIndex}
    ::= { lcCmtsIngressAvoidanceMetricConfigTable 1 }

LcCmtsIngressAvoidanceMetricConfigEntry ::= SEQUENCE {
	lcCmtsMetricIndex		INTEGER,	
	lcCmtsAgingMultiplier		INTEGER,	
	lcCmtsCalculationTimer		INTEGER
	}

lcCmtsMetricIndex OBJECT-TYPE
	SYNTAX INTEGER 
	MAX-ACCESS not-accessible
	STATUS current
	DESCRIPTION
        "Metric Index."
	::= {lcCmtsIngressAvoidanceMetricConfigEntry 1 }

lcCmtsAgingMultiplier OBJECT-TYPE
	SYNTAX INTEGER 
	MAX-ACCESS read-write
	STATUS current
	DESCRIPTION
        "Metric aging multilpler in hundreths."
	::= { lcCmtsIngressAvoidanceMetricConfigEntry 2 }

lcCmtsCalculationTimer OBJECT-TYPE
	SYNTAX INTEGER 
	MAX-ACCESS read-write
	STATUS current
	DESCRIPTION
        "Frequency at which metrics should be calculated in milliseconds."
	::= { lcCmtsIngressAvoidanceMetricConfigEntry 3 }


--Ingress Avoidance Frequency Status Table
lcCmtsIngressAvoidanceFreqStatusTable OBJECT-TYPE
    SYNTAX          SEQUENCE OF LcCmtsIngressAvoidanceFreqStatusEntry
    MAX-ACCESS      not-accessible
    STATUS          current
    DESCRIPTION
        "This table is a status table for all frequency ranges 
	allowed per carrier path."
    ::= {lccmtsUpstreamIngressAvoidance 8 }

lcCmtsIngressAvoidanceFreqStatusEntry OBJECT-TYPE
    SYNTAX          LcCmtsIngressAvoidanceFreqStatusEntry
    MAX-ACCESS      not-accessible
    STATUS          current
    DESCRIPTION
        "This table is a status table for all frequency ranges 
	allowed per carrier path."
    INDEX           {lcCmtsFreqStatusCarrierPathIndex,lcCmtsFreqStatusFreqIndex}
    ::= { lcCmtsIngressAvoidanceFreqStatusTable 1 }

LcCmtsIngressAvoidanceFreqStatusEntry ::= SEQUENCE {
	lcCmtsFreqStatusCarrierPathIndex INTEGER,	
	lcCmtsFreqStatusFreqIndex	INTEGER,
	lcCmtsFreqStatusFreq		INTEGER,	
	lcCmtsFreqStatusFc		INTEGER,
	lcCmtsFreqStatusAvailable	INTEGER,
	lcCmtsFreqStatusStatus		INTEGER,
	lcCmtsFreqStatusTimeLastUsed	TimeTicks,
	lcCmtsFreqStatusUpTime		TimeTicks	
	}

lcCmtsFreqStatusCarrierPathIndex OBJECT-TYPE
	SYNTAX INTEGER 
	MAX-ACCESS not-accessible
	STATUS current
	DESCRIPTION
        "Carrier Paths for each frequency."
	::= {lcCmtsIngressAvoidanceFreqStatusEntry 1 }

lcCmtsFreqStatusFreqIndex OBJECT-TYPE
	SYNTAX INTEGER 
	MAX-ACCESS not-accessible
	STATUS current
	DESCRIPTION
        "Frequency index for carrier path."
	::= {lcCmtsIngressAvoidanceFreqStatusEntry 2 }
	
lcCmtsFreqStatusFreq OBJECT-TYPE
	SYNTAX INTEGER 
	MAX-ACCESS read-only
	STATUS current
	DESCRIPTION
        "Frequency in Hz."
	::= { lcCmtsIngressAvoidanceFreqStatusEntry 3 }

lcCmtsFreqStatusFc OBJECT-TYPE
	SYNTAX INTEGER {no(0), yes(1)} 
	MAX-ACCESS read-only
	STATUS current
	DESCRIPTION
        "Denotes whether or not this is a center frequency."
	::= { lcCmtsIngressAvoidanceFreqStatusEntry 4 }

lcCmtsFreqStatusAvailable OBJECT-TYPE
	SYNTAX INTEGER {no(0), yes(1), inuse(2), reserved(3) } 
	MAX-ACCESS read-only
	STATUS current
	DESCRIPTION
        "Denotes whether or not this is available.
	 no - frequency is not available for ingress avoidance.
	 yes - frequency is not being used and is available for ingress avoidance.
	 inuse - frequency is actively being used by an upstream.
	 reserved - frequency is reserved by an upstream channel which is currently down."
	::= { lcCmtsIngressAvoidanceFreqStatusEntry 5 }

lcCmtsFreqStatusStatus OBJECT-TYPE
	SYNTAX INTEGER {unk(0)} 
	MAX-ACCESS read-only
	STATUS current
	DESCRIPTION
        "Denotes status of frequency.  Large integers represents
	the channel is extremely bad.  Zero/UNK represents a Good
	frequency to try."
	::= { lcCmtsIngressAvoidanceFreqStatusEntry 6 }

lcCmtsFreqStatusTimeLastUsed OBJECT-TYPE
	SYNTAX TimeTicks 
	MAX-ACCESS read-only
	STATUS current
	DESCRIPTION
        "Denotes time since this frequency was last used."
	::= { lcCmtsIngressAvoidanceFreqStatusEntry 7 }

lcCmtsFreqStatusUpTime OBJECT-TYPE
	SYNTAX TimeTicks  
	MAX-ACCESS read-only
	STATUS current
	DESCRIPTION
        "Denotes up time last time used or current up time on 
	this frequency."
	::= { lcCmtsIngressAvoidanceFreqStatusEntry 8 }


--Ingress Avoidance Health Status Table
lcCmtsUpstreamIngressAvoidanceHealthTable OBJECT-TYPE
    SYNTAX          SEQUENCE OF LcCmtsIngressAvoidanceHealthEntry
    MAX-ACCESS      not-accessible
    STATUS          current
    DESCRIPTION
        "Displays the health of each upstream channel."
    ::= {lccmtsUpstreamIngressAvoidance 9 }

lcCmtsIngressAvoidanceHealthEntry OBJECT-TYPE
    SYNTAX          LcCmtsIngressAvoidanceHealthEntry
    MAX-ACCESS      not-accessible
    STATUS          current
    DESCRIPTION
        "Displays the health of each upstream channel."
    INDEX           { ifIndex }
    ::= { lcCmtsUpstreamIngressAvoidanceHealthTable 1 }

LcCmtsIngressAvoidanceHealthEntry ::= SEQUENCE {
	lcCmtsHealthProfile		INTEGER,
	lcCmtsHealthFc			INTEGER,
	lcCmtsHealthUpTime		TimeTicks,
	lcCmtsMetric1Status		INTEGER,
	lcCmtsMetric1Value		INTEGER
	}

lcCmtsHealthProfile OBJECT-TYPE
	SYNTAX INTEGER
	MAX-ACCESS read-only
	STATUS current
	DESCRIPTION
        "Upstream Ingress Avoidance Profile Index."
	::= { lcCmtsIngressAvoidanceHealthEntry 1 }

lcCmtsHealthFc OBJECT-TYPE
	SYNTAX INTEGER 
	MAX-ACCESS read-only
	STATUS current
	DESCRIPTION
        "Center frequency for the upstream channel."
	::= { lcCmtsIngressAvoidanceHealthEntry 2 }

lcCmtsHealthUpTime OBJECT-TYPE
	SYNTAX TimeTicks 
	MAX-ACCESS read-only
	STATUS current
	DESCRIPTION
        "Time the channel has been up in this configuration."
	::= { lcCmtsIngressAvoidanceHealthEntry 3 }

lcCmtsMetric1Status OBJECT-TYPE
	SYNTAX INTEGER {red(0),yellow(1),green(2)} 
	MAX-ACCESS read-only
	STATUS current
	DESCRIPTION
        "Current state of the upstream channel using the
	thresholds set in the threshold table."
	::= { lcCmtsIngressAvoidanceHealthEntry 4 }

lcCmtsMetric1Value OBJECT-TYPE
	SYNTAX INTEGER 
	MAX-ACCESS read-only
	STATUS current
	DESCRIPTION
        "Current value for the metric."
	::= { lcCmtsIngressAvoidanceHealthEntry 5 }



--Ingress Avoidance Carrier Path Configuration Table
lcCmtsMultiUsConfigTable OBJECT-TYPE
    SYNTAX          SEQUENCE OF LcCmtsMultiUsConfigEntry
    MAX-ACCESS      not-accessible
    STATUS          current
    DESCRIPTION
        "Defines carrier paths (Physical Connectivity) and channel groups
         for each upstream."
    ::= {lccmtsif 5}


lcCmtsMultiUsConfigEntry OBJECT-TYPE
    SYNTAX          LcCmtsMultiUsConfigEntry
    MAX-ACCESS      not-accessible
    STATUS          current
    DESCRIPTION
        "Defines carrier paths (Physical Connectivity) and channel groups
        for each upstream."
    INDEX           {ifIndex}
    ::= { lcCmtsMultiUsConfigTable 1 }

LcCmtsMultiUsConfigEntry ::= SEQUENCE {
	lcCmtsCarrierPath		INTEGER,	
	lcCmtsChannelGroup		INTEGER
	}

lcCmtsCarrierPath OBJECT-TYPE
	SYNTAX INTEGER 
	MAX-ACCESS read-write
	STATUS current
	DESCRIPTION
        "Defines physical connectivity to each upstream receiver
         ifIndexes with the same carrier path cannot operate on
	 the same frequencies."
	::= { lcCmtsMultiUsConfigEntry 1 }

lcCmtsChannelGroup OBJECT-TYPE
	SYNTAX INTEGER 
	MAX-ACCESS read-write
	STATUS current
	DESCRIPTION
        "Defines which upstreams must operate on the same frequencies.
	 Value of zero means that a given upstream is independant of all
	 other upstream channels.  Any upstream with the same value must
	 operate on the same frequency."
	::= { lcCmtsMultiUsConfigEntry 2 }





lcCmtsFrontFanOn OBJECT-TYPE
	SYNTAX TruthValue
	MAX-ACCESS read-only
	STATUS current
	DESCRIPTION
        "Current on/off state of the CMTS fan closest to the front
         of the chassis.  If the fan is on, true is returned.
         If the fan is off, false is returned."
	::= { lccmtsif 6 }

lcCmtsMiddleFanOn OBJECT-TYPE
	SYNTAX TruthValue
	MAX-ACCESS read-only
	STATUS current
	DESCRIPTION
        "Current on/off state of the CMTS fan closest to the middle
         of the chassis.  If the fan is on, true is returned.
         If the fan is off, false is returned."
	::= { lccmtsif 7 }

lcCmtsBackFanOn OBJECT-TYPE
	SYNTAX TruthValue
	MAX-ACCESS read-only
	STATUS current
	DESCRIPTION
        "Current on/off state of the CMTS fan closest to the back
         of the chassis.  If the fan is on, true is returned.
         If the fan is off, false is returned."
	::= { lccmtsif 8 }

--Euro DOCSIS - additional IF configuration
lccmtsifconfig      OBJECT IDENTIFIER ::= { lccmtsif 9 }

lcCmtsAnnex OBJECT-TYPE
	SYNTAX INTEGER {annexA(0), annexB(1)}  
	MAX-ACCESS read-write
	STATUS current
	DESCRIPTION
        "FEC mode - Default is Annex B which is the North American Standard
	Annex A is used for Euro DOCSIS."
	::= { lccmtsifconfig 1 }

lcCmtsFrequencySplit OBJECT-TYPE
	SYNTAX INTEGER {standard(0), euroDOCSIS(1)}  
	MAX-ACCESS read-write
	STATUS current
	DESCRIPTION
        "Upstream/Downstream Frequency Split.  The standard North American
	split is 5-42/50-862 MHz.  Euro DOCSIS Split is 5-65/100-862 MHz."
	::= { lccmtsifconfig 2 }



lcEvSyslog2 OBJECT-TYPE
        SYNTAX      IpAddress
        MAX-ACCESS  read-write
        STATUS      current
        DESCRIPTION
            "The IP address of a 2nd Syslog server. If 0.0.0.0, syslog
             transmission is inhibited."
	::= { lccmtsif 10 }

lcEvSyslog3 OBJECT-TYPE
        SYNTAX      IpAddress
        MAX-ACCESS  read-write
        STATUS      current
        DESCRIPTION
            "The IP address of a 3rd Syslog server. If 0.0.0.0, syslog
             transmission is inhibited."
	::= { lccmtsif 11 }


-- ********************************************************************************

lcCpeMacToCmMacTable OBJECT-TYPE
        SYNTAX      SEQUENCE OF LcCpeMacToCmMacEntry
        MAX-ACCESS  not-accessible
        STATUS      current
        DESCRIPTION
            "This is a table to provide a mechanism for finding the
             MAC address of the CM to which a CPE device is connected.
             The table is indexed by the MAC address of the device
             whose associated CM is being sought.   There is exactly
             one row in this table for each MAC address learned by
             the CMTS.  It is possible to have entries in this table
             that have no associated CM MAC address and those entries
             are denoted by a CM MAC address of 00 00 00 00 00 00."
    ::= { lccmtsif 16 }

lcCpeMacToCmMacEntry OBJECT-TYPE
        SYNTAX      LcCpeMacToCmMacEntry
        MAX-ACCESS  not-accessible
        STATUS      current
        DESCRIPTION
            "A row in the lcCpeMacToCmMacTable.
             An entry in this table exists for each MAC address
             that has been learned by the CMTS and is present in
             it Forwarding Database."
        INDEX   { lcCpeMac }
        ::= { lcCpeMacToCmMacTable 1 }

LcCpeMacToCmMacEntry ::= SEQUENCE {
                lcCpeMac     MacAddress,
                lcCmMac      MacAddress
        }

lcCpeMac OBJECT-TYPE
        SYNTAX      MacAddress
        MAX-ACCESS  not-accessible
        STATUS      current
        DESCRIPTION
            "A MAC address in the CMTS Forwarding Database.  This is
             the index into the lcCpeMacToCmMacTable."
        ::= { lcCpeMacToCmMacEntry 1 }

lcCmMac OBJECT-TYPE
        SYNTAX      MacAddress
        MAX-ACCESS  read-only
        STATUS      current
        DESCRIPTION
            "The MAC address of the CM to which the index MAC address
             is connected.  For entries learned on the Ethernet side
             of the CMTS bridge this value will be 00 00 00 00 00 00
             which indicates no CM associativity.  For a CM MAC entry
             this value will be the same as the index, that is the
             MAC address of the CM itself.  For a CPE device on the 
             Cable side of the CMTS bridge this value will be the MAC
             address of the CM to which that CPE device is connected."
        ::= { lcCpeMacToCmMacEntry 2 }

-- ********************************************************************************

-- ********************************************************************************

lcCmCountsTable OBJECT-TYPE
        SYNTAX      SEQUENCE OF LcCmCountsEntry
        MAX-ACCESS  not-accessible
        STATUS      current
        DESCRIPTION
            "This is a table to provide the number of active and
             registered modems on each upstream and for the entire
             system.  Active modems are those that have performed
             at least an initial ranging and have not yet been
             ranging-aborted, ranging-timedout, or de-registered.
             This table is populated from the Registrar CM entries
             functions."
    ::= { lccmtsif 19 }

lcCmCountsEntry OBJECT-TYPE
        SYNTAX      LcCmCountsEntry
        MAX-ACCESS  not-accessible
        STATUS      current
        DESCRIPTION
            "A row in the lcCmCountsTable.
             An entry in this table exists for each upstream
             channel on the CMTS (1-8) and for the system totals."
        INDEX   { lcCmCountsRowNum }
        ::= { lcCmCountsTable 1 }

LcCmCountsEntry ::= SEQUENCE {
                lcCmCountsRowNum     Counter32,
                lcActiveCmCounts     Counter32,
                lcRegisteredCmCounts Counter32
        }

lcCmCountsRowNum OBJECT-TYPE
        SYNTAX      Counter32
        MAX-ACCESS  not-accessible
        STATUS      current
        DESCRIPTION
            "A row index into the lcCmCountsTable. Indices
             1 through 8 correspond to upstream channels
             and index 9 corresponds to the system totals."
        ::= { lcCmCountsEntry 1 }

lcActiveCmCounts OBJECT-TYPE
        SYNTAX      Counter32
        MAX-ACCESS  read-only
        STATUS      current
        DESCRIPTION
            "The number of CMs on this channel that have performed
             an initial ranging and are still marked as operational
             by the CMTS."
        ::= { lcCmCountsEntry 2 }

lcRegisteredCmCounts OBJECT-TYPE
        SYNTAX      Counter32
        MAX-ACCESS  read-only
        STATUS      current
        DESCRIPTION
            "The number of CMs on this channel that are currently
             registered with the CMTS."
        ::= { lcCmCountsEntry 3 }

-- ********************************************************************************


-- --------------------------------------------------------------------------
-- Begin CM Interface section
-- --------------------------------------------------------------------------

-- --------------------------------------------------------------------------
-- Begin CMTS Device section
-- --------------------------------------------------------------------------

lccmtsProvisioning OBJECT IDENTIFIER ::= { lccmtsdevice 1 }

lcProvisioningControl OBJECT-TYPE
    SYNTAX            INTEGER {
                              use-dhcp-and-tftp(1),
                              use-dhcp(2),
                              use-tftp(3),
                              use-nvram(4)
                              }
    MAX-ACCESS        read-write
    STATUS            current
    DESCRIPTION
        "Controls the use of file-based provisioning by the CMTS. If set to:
          use-dhcp-and-tftp(1) the CMTS will use DHCP to find its IP
                               address, subnet mask, default router,
                               and TFTP server. Configuration
                               parameters will be provisioned from a
                               TFTP'ed parameter file,
          use-dhcp         (2) DHCP will be used to find the IP
                               address, subnet mask, and
                               defaultrouter, but all other parameters
                               will come from NVRAM,
          use-tftp         (3) The CMTS will use NVRAM for its IP
                               address, but other configured
                               parameters will be loaded via TFTP,
          use-nvram        (4) All operational parameters are taken
                               from nonvolatile RAM."
    ::= { lccmtsProvisioning 1 }

lcConfigIpAddress  OBJECT-TYPE
    SYNTAX         IpAddress
    MAX-ACCESS     read-write
    STATUS         current
    DESCRIPTION
        "The IP address of the CMTS; provides a writable equivalent of
        ipAdEntAddr. If set to null (0.0.0.0), the address must be provided
        through DHCP."
    ::= { lccmtsProvisioning 2 }

lcConfigIpSubnet   OBJECT-TYPE
    SYNTAX         IpAddress
    MAX-ACCESS     read-write
    STATUS         current
    DESCRIPTION
        "The subnet mask corresponding to lcConfigIpAddress; provides a
        writable equivalent of ipAdEntNetMask."
    ::= { lccmtsProvisioning 3 }

lcConfigIpGateway  OBJECT-TYPE
    SYNTAX         IpAddress
    MAX-ACCESS     read-write
    STATUS         current
    DESCRIPTION
        "The Gateway address defines the next hop router (forwarder) destination
        for non-local IP packets."
    ::= { lccmtsProvisioning 4 }

lcConfigTftpAddress OBJECT-TYPE
    SYNTAX         IpAddress
    MAX-ACCESS     read-write
    STATUS         current
    DESCRIPTION
        "The IP address of the TFTP Server supplying provisioning
                 configuration data."
    ::= { lccmtsProvisioning 5 }

lcConfigTftpFilename OBJECT-TYPE
       SYNTAX	DisplayString (SIZE (0..128))
       MAX-ACCESS read-write
       STATUS     current
       DESCRIPTION
		"The default filename on the TFTP Server for acquiring provisioning
                 configuration data (may be overridden by DHCP)."
    ::= { lccmtsProvisioning 6 }

lcConfigTimeServerAddress OBJECT-TYPE
    SYNTAX         IpAddress
    MAX-ACCESS     read-write
    STATUS         current
    DESCRIPTION
        "The IP address of the Time Server (RFC868) supplying provisioning
                 time."
    ::= { lccmtsProvisioning 7 }

lcConfigTimeoffset OBJECT-TYPE
       SYNTAX	INTEGER
       MAX-ACCESS read-write
       STATUS     current
       DESCRIPTION
		"Time offset in seconds to apply to 
                 provisioned GMT time"
    ::= { lccmtsProvisioning 8 }

lcConfigSNTPAddress OBJECT-TYPE
       SYNTAX	IpAddress
       MAX-ACCESS read-write
       STATUS     current
       DESCRIPTION
		"The IP Address of the SNTP Timer Server supplying
                 provisioning time"
    ::= { lccmtsProvisioning 9 }

-- The following table was derived from the Wellfleet console MIB.
-- Provision is made for more than one serial port, although only
-- one is supported on the intended device.
 
lcSerialPortTable OBJECT-TYPE
    SYNTAX  SEQUENCE OF LcSerialPortEntry
    MAX-ACCESS  not-accessible
    STATUS  current
    DESCRIPTION
        "Configuration of system serial port(s)"
    ::= { lccmtsdevice 2 }
 
lcSerialPortEntry OBJECT-TYPE
    SYNTAX  LcSerialPortEntry
    MAX-ACCESS  not-accessible
    STATUS  current
    DESCRIPTION
        "Information for each serial port."
    INDEX   { lcSerialPortNumber }
    ::= { lcSerialPortTable 1 }
 
LcSerialPortEntry ::= SEQUENCE {
        lcSerialPortNumber
            INTEGER,
        lcSerialPortBaudRate
            INTEGER,
        lcSerialPortDataBits
            INTEGER,
        lcSerialPortParity
            INTEGER,
        lcSerialPortStopBits
            INTEGER,
        lcSerialPortModemEnable
            INTEGER
    }
 
lcSerialPortNumber OBJECT-TYPE
    SYNTAX  INTEGER
    MAX-ACCESS  not-accessible
    STATUS  current
    DESCRIPTION
            "Index for this table."
    ::= { lcSerialPortEntry 1 }
 
lcSerialPortBaudRate OBJECT-TYPE
    SYNTAX  INTEGER {
                    baudrate1200b(1200),
                    baudrate2400b(2400),
                    baudrate4800b(4800),
                    baudrate7200b(7200),
                    baudrate9600b(9600),
                    baudrate12000b(12000),
                    baudrate14400b(14400),
                    baudrate19200b(19200),
                    baudrate28800b(28800),
                    baudrate38k(38400),
                    baudrate56k(57600),
                    baudrate64k(64000),
                    baudrate76k(76800),
                    baudrate96k(96000),
                    baudrate115k(115200)
                    }
    MAX-ACCESS  read-write
    STATUS  current
    DESCRIPTION
        "Baud rate configured on this Serial Port"
    DEFVAL  { baudrate9600b }
    ::= { lcSerialPortEntry 2 }
 
lcSerialPortDataBits OBJECT-TYPE
    SYNTAX  INTEGER
    MAX-ACCESS  read-write
    STATUS  current
    DESCRIPTION
        "Number of data bits configured on this Serial Port"
    DEFVAL  { 8 }
    ::= { lcSerialPortEntry 3 }
 
lcSerialPortParity OBJECT-TYPE
    SYNTAX  INTEGER {
                none(1),
                odd(2),
                even(3)
            }
    MAX-ACCESS  read-write
    STATUS  current
    DESCRIPTION
        "Type of parity configured on this Serial Port"
    DEFVAL  { none }
    ::= { lcSerialPortEntry 4 }

lcSerialPortStopBits OBJECT-TYPE
    SYNTAX  INTEGER {
                s1bit(1),
                s15bit(2),
                s2bit(3)
            }
    MAX-ACCESS  read-write
    STATUS  current
    DESCRIPTION
        "Number of stop bits configured on this Serial Port"
    DEFVAL  { s1bit }
    ::= { lcSerialPortEntry 5 }

lcSerialPortModemEnable OBJECT-TYPE
    SYNTAX  INTEGER {
                enabled(1),
                disabled(2)
            }
    MAX-ACCESS  read-write
    STATUS  current
    DESCRIPTION
        "Enable the Serial Port to run with modem leads enabled"
    DEFVAL  { disabled }
    ::= { lcSerialPortEntry 6 }
 

-- factory default for the following table is a single entry with a 
-- mask of zero. That is, all modems are allowed to register.

lcModemVendorTable	OBJECT-TYPE
	SYNTAX		SEQUENCE OF LcModemVendorEntry
	MAX-ACCESS	not-accessible
	STATUS		current
	DESCRIPTION
	"This table defines modems that are allowed to register with this 
	 CMTS.  Modem vendors are identified by the OUI portion of the 
	 MAC address used by the modem for registration. In order to 
	 allow further differentiation based on particular models, the 
	 entire MAC address may be masked and used to screen registrations."
	::= { lccmtsdevice 3 }

lcModemVendorEntry	OBJECT-TYPE
	SYNTAX		LcModemVendorEntry
	MAX-ACCESS	not-accessible
	STATUS		current
	DESCRIPTION
	"This entry identifies a class of modems which are allowed to register
	 with this CMTS."
	INDEX           { lcModemVendorIndex }
	::= { lcModemVendorTable 1 }

LcModemVendorEntry ::= SEQUENCE {
	lcModemVendorIndex	INTEGER,
	lcModemVendorControl	RowStatus,
	lcModemVendorMacAddress	MacAddress,
	lcModemVendorMask	MacAddress
	}

lcModemVendorIndex	OBJECT-TYPE
	SYNTAX		INTEGER
	MAX-ACCESS	not-accessible
	STATUS		current
	DESCRIPTION
	"An arbitrary index defining an instance of this entry. Ordering is not 
	 meaningful."
	::= { lcModemVendorEntry 1 }


lcModemVendorControl	OBJECT-TYPE
	SYNTAX		RowStatus
	MAX-ACCESS	read-create
	STATUS		current
	DESCRIPTION
	"This object controls the creation and deletion of rows in this table."
	::= { lcModemVendorEntry 2 }


lcModemVendorMacAddress	OBJECT-TYPE
	SYNTAX		MacAddress
	MAX-ACCESS	read-create
	STATUS		current
	DESCRIPTION
	"When masked, identifies a group of modems that are allowed to register
	 at this CMTS. Note that the LSB of the first octet is the multicast bit;
	 since it cannot identify a modem, it is defined to be zero."
	::= { lcModemVendorEntry 3 }


lcModemVendorMask	OBJECT-TYPE
	SYNTAX		MacAddress
	MAX-ACCESS	read-create
	STATUS		current
	DESCRIPTION
	"Applied to the MAC address to identify which modems are allowed to register
	 at this CMTS. Ordinarily, the OUI portion is used to identify particular
	 vendors, but arbitrary masks can be used. The LSB of the first octet is
	 the multicast bit and is defined to be zero."
	DEFVAL { 'ffffff000000'h }
	::= { lcModemVendorEntry 4 }


lccmtsDPStatistics OBJECT IDENTIFIER ::= { lccmtsdevice 4 }

lcDPStatisticsInterval OBJECT-TYPE
    SYNTAX            INTEGER 
    MAX-ACCESS        read-write
    STATUS            current
    DESCRIPTION
        "Controls the interval at which data rates are calculated on the CMTS."
    ::= { lccmtsDPStatistics 1 }

lcDPStatisticsTable OBJECT-TYPE
    SYNTAX  SEQUENCE OF LcDPStatisticsEntry
    MAX-ACCESS  not-accessible
    STATUS  current
    DESCRIPTION
        "The table contains the last calculated statistics for data rates for
	each port on the CMTS."
    ::= { lccmtsDPStatistics 2 }
 
lcDPStatisticsEntry OBJECT-TYPE
    SYNTAX  LcDPStatisticsEntry
    MAX-ACCESS  not-accessible
    STATUS  current
    DESCRIPTION
	"The Entry contains the last calculated statistics for data rates for
	one port on the CMTS."

    INDEX   { dot1dTpPort }
    ::= { lcDPStatisticsTable 1 }
 
LcDPStatisticsEntry ::= SEQUENCE {
        lcDPStatisticsTxFrameRate
            INTEGER,
        lcDPStatisticsRxFrameRate
            INTEGER,
        lcDPStatisticsTxOctetRate
            INTEGER,
        lcDPStatisticsRxOctetRate
            INTEGER
    }
 
lcDPStatisticsTxFrameRate OBJECT-TYPE
    SYNTAX            INTEGER 
    MAX-ACCESS        read-only
    STATUS            current
    DESCRIPTION
        "The last calculated frames per second transmitted on this port."
    ::= { lcDPStatisticsEntry 1 }

lcDPStatisticsRxFrameRate OBJECT-TYPE
    SYNTAX            INTEGER 
    MAX-ACCESS        read-only
    STATUS            current
    DESCRIPTION
        "The last calculated frames per second received on this port."
    ::= { lcDPStatisticsEntry 2 }

lcDPStatisticsTxOctetRate OBJECT-TYPE
    SYNTAX            INTEGER 
    MAX-ACCESS        read-only
    STATUS            current
    DESCRIPTION
        "The last calculated octets per second transmitted on this port."
    ::= { lcDPStatisticsEntry 3 }

lcDPStatisticsRxOctetRate OBJECT-TYPE
    SYNTAX            INTEGER 
    MAX-ACCESS        read-only
    STATUS            current
    DESCRIPTION
        "The last calculated octets per second received on this port."
    ::= { lcDPStatisticsEntry 4 }

 

lccmtsDPConfiguration OBJECT IDENTIFIER ::= { lccmtsdevice 5 }

lcForwardingMode OBJECT-TYPE
    SYNTAX            INTEGER {
                              none(1),
                              dhcp-arp(2)
                              }
    MAX-ACCESS        read-write
    STATUS            current
    DESCRIPTION
	"Controls the Forwarding Data Base Learning Mode.  If set 
	to none(1), the CMTS uses transparent learning.  If set to 
	dhcp-arp(2), the CMTS uses Layer-3 switching based on DHCP
	and ARP.  Mode dhcp-arp(2) is not allowed if FunnelMode is
	enabled(2).  The default is none(1)."
    ::= { lccmtsDPConfiguration 1 }

lcProxyArp OBJECT-TYPE
    SYNTAX            INTEGER {
                              enable(1),
                              disable(2)
                              }
    MAX-ACCESS        read-write
    STATUS            current
    DESCRIPTION
        "Controls Proxy ARP on the CMTS when it is in transparent learning 
	mode.  If set to enable(1), the CMTS responds to an ARP received 
	from the Cable when the IP Address is known and responds to an ARP 
	received from the Ethernet when the IP Address in known to be on 
	the Cable.  If set to disable(2), CMTS does not respond to any ARPs.
	Proxy ARP cannot be enabled if FunnelMode is enabled(2).  The
	default is disabled(2)."
    ::= { lccmtsDPConfiguration 2 }

lcProxyArpTimeout OBJECT-TYPE
    SYNTAX            INTEGER
    MAX-ACCESS        read-write
    STATUS            current
    DESCRIPTION
        "Controls the timeout (in seconds) of the Proxy Arp cache entries."
    ::= { lccmtsDPConfiguration 3 }

lcArpSpoofingProtection OBJECT-TYPE
    SYNTAX            INTEGER {
                              enable(1),
                              disable(2)
                              }
    MAX-ACCESS        read-write
    STATUS            current
    DESCRIPTION
        "Controls ARP Spoofing Protection on the CMTS when it is in 
	layer-3 switching  mode (Mode B).  CMTS must be in MODE B 
	for ARP Spoofing Protection to work.  
	If set to enable(1), the CMTS will not forward or glean 
	information from ARP packets received from the Cable interface 
	whose sender's IP address does not match the IP address for the 
	sender's hardware address as learned from DHCP gleaning.
	If set to disable(2), the CMTS will forward the ARP packet 
	and will update its ARP cache with the IP address in the ARP."
    ::= { lccmtsDPConfiguration 4 }

lcFunnelMode OBJECT-TYPE
    SYNTAX            INTEGER {
                              enable(1),
                              disable(2)
                              }
    MAX-ACCESS        read-write
    STATUS            current
    DESCRIPTION
        "Controls whether or not the CMTS is in Funnel Mode. 
	If set to enable(1), all upstream data packets are sent out the
	ethernet port. If set to disable(2), all packets are processed
	normally. Funnel mode is not allowed if ProxyArp is enabled(1)
	or ForwardingMode is not none(1).  The default is disabled(2)."
    ::= { lccmtsDPConfiguration 5 }

lcDeregCmAgeTime OBJECT-TYPE
    SYNTAX            INTEGER (30..432000)
    UNITS             "seconds"
    MAX-ACCESS        read-write
    STATUS            current
    DESCRIPTION
        "The time-to-live of a CM entry in the FDB for a CM that has
	been de-registered.  This interval is expressed as the number
	of seconds between de-registration and removal from the FDB.
	If the CM ranges during this time interval aging is cancelled.

        The default interval is 172800 seconds (48 hours)."
    ::= { lccmtsDPConfiguration 6 }

lcRngNotRegCmAgeTime OBJECT-TYPE
    SYNTAX            INTEGER (30..432000)
    UNITS             "seconds"
    MAX-ACCESS        read-write
    STATUS            current
    DESCRIPTION
        "The time-to-live of a CM entry in the FDB for a CM that has
	performed an initial ranging request but has not yet completed
	registration.  This interval is expressed as the number
	of seconds between receipt of the initial ranging request
	and removal from the FDB.  If the CM registers this time
	interval is cancelled.

        The default interval is 120 seconds."
    ::= { lccmtsDPConfiguration 7 }


lcUsedot1dTpAgingTime OBJECT-TYPE
    SYNTAX            INTEGER {
                              enable(1),
                              disable(2)
                              }
    MAX-ACCESS        read-write
    STATUS            current
    DESCRIPTION
        "This object determines whether the default time-to-live of an entry
	 in the FDB as specified by the dot1dTpAgingTime object is to
	 be used or not.  This setting is only meaningful for FDB entries
	 learned on the Cable interface when Mode B (DHCP-ARP) forwarding
	 is enabled.

	 If enabled in Mode B, then the DHCP lease time is NOT used to
	 specify the aging time for entries, but rather the setting for
	 dot1dTpAgingTime is used.

	 This object has no effect in Mode A (transparent) bridging mode.

         The default is disable (do NOT use dot1dTpAgingTime)."
    ::= { lccmtsDPConfiguration 8 }



lccmtsHwRevisions OBJECT IDENTIFIER ::= { lccmtsdevice 6 }

lccmtsHwRevArbCPLD OBJECT-TYPE
    SYNTAX            INTEGER 
    MAX-ACCESS        read-only
    STATUS            current
    DESCRIPTION
        "The hardware revision number for the Arb CPLD chip."
    ::= { lccmtsHwRevisions 1 }

lccmtsHwRevTxCPLD OBJECT-TYPE
    SYNTAX            INTEGER 
    MAX-ACCESS        read-only
    STATUS            current
    DESCRIPTION
        "The hardware revision number for the Tx CPLD chip."
    ::= { lccmtsHwRevisions 2 }

lccmtsHwRevAFFPGA OBJECT-TYPE
    SYNTAX            INTEGER 
    MAX-ACCESS        read-only
    STATUS            current
    DESCRIPTION
        "The hardware revision number for the AFFPGA chip."
    ::= { lccmtsHwRevisions 3 }

lccmtsHwRevGT64010 OBJECT-TYPE
    SYNTAX            INTEGER 
    MAX-ACCESS        read-only
    STATUS            current
    DESCRIPTION
        "The hardware revision number for the Galileo GT-64010 chip."
    ::= { lccmtsHwRevisions 4 }

lccmtsHwRevPLX9080 OBJECT-TYPE
    SYNTAX            INTEGER 
    MAX-ACCESS        read-only
    STATUS            current
    DESCRIPTION
        "The hardware revision number for the PLX PCI 9080 chip."
    ::= { lccmtsHwRevisions 5 }

lccmtsHwRevBCM3210 OBJECT-TYPE
    SYNTAX            INTEGER 
    MAX-ACCESS        read-only
    STATUS            current
    DESCRIPTION
        "The hardware revision number for the Broadcom 3210 chip."
    ::= { lccmtsHwRevisions 6 }

lccmtsHwRevBCM3033 OBJECT-TYPE
    SYNTAX            INTEGER 
    MAX-ACCESS        read-only
    STATUS            current
    DESCRIPTION
        "The hardware revision number for the Broadcom 3033 chip."
    ::= { lccmtsHwRevisions 7 }

lccmtsHwRevSunset OBJECT-TYPE
    SYNTAX            INTEGER 
    MAX-ACCESS        read-only
    STATUS            current
    DESCRIPTION
        "The hardware revision number for the Sunset transmitter."
    ::= { lccmtsHwRevisions 8 }

lccmtsHwRevDEC21143 OBJECT-TYPE
    SYNTAX            INTEGER 
    MAX-ACCESS        read-only
    STATUS            current
    DESCRIPTION
        "The hardware revision number for the DEC 21143 Ethernet chip."
    ::= { lccmtsHwRevisions 9 }

lccmtsHwRevLXT970A OBJECT-TYPE
    SYNTAX            INTEGER 
    MAX-ACCESS        read-only
    STATUS            current
    DESCRIPTION
        "The hardware revision number for the LXT970 Ethernet PHY A chip."
    ::= { lccmtsHwRevisions 10 }

lccmtsHwRevLXT970B OBJECT-TYPE
    SYNTAX            INTEGER 
    MAX-ACCESS        read-only
    STATUS            current
    DESCRIPTION
        "The hardware revision number for the LXT970 Ethernet PHY B chip."
    ::= { lccmtsHwRevisions 11 }


lccmtsHwRevRfRxTable OBJECT-TYPE
    SYNTAX  SEQUENCE OF LccmtsHwRevRfRxEntry
    MAX-ACCESS  not-accessible
    STATUS  current
    DESCRIPTION
        "The table contains hardware revision numbers for the chips of
	each upstream RF receiver channel in the CMTS."
    ::= { lccmtsHwRevisions 12 }
 
lccmtsHwRevRfRxEntry OBJECT-TYPE
    SYNTAX  LccmtsHwRevRfRxEntry
    MAX-ACCESS  not-accessible
    STATUS  current
    DESCRIPTION
        "The table contains hardware revision numbers for the chips of
	one upstream RF receiver channel in the CMTS."

    INDEX  { ifIndex }
    ::= { lccmtsHwRevRfRxTable 1 }
 
LccmtsHwRevRfRxEntry ::= SEQUENCE {
	lccmtsHwRevBCM3137
            INTEGER,
	lccmtsHwRevRipsaw
            INTEGER
    }
 
lccmtsHwRevBCM3137 OBJECT-TYPE
    SYNTAX            INTEGER 
    MAX-ACCESS        read-only
    STATUS            current
    DESCRIPTION
        "The hardware revision number for this Broadcom 3033 chip."
    ::= { lccmtsHwRevRfRxEntry 1 }

lccmtsHwRevRipsaw OBJECT-TYPE
    SYNTAX            INTEGER 
    MAX-ACCESS        read-only
    STATUS            current
    DESCRIPTION
        "The hardware revision number for this Ripsaw receiver."
    ::= { lccmtsHwRevRfRxEntry 2 }

lccmtsPoliceTolerance OBJECT IDENTIFIER ::= { lccmtsdevice 7 }

lccmtsUpPolice OBJECT-TYPE
	SYNTAX		INTEGER (0..100)
	MAX-ACCESS 	read-write
	STATUS      	current
    	DESCRIPTION
        "The tolerance percentage to apply to configured maximum Upstream bit 
	 rate.  This allows for minor differences in shaping algoithms by not 
	 policing to the edge.  The default valued is 0% which will police to
	 the edge."
    	DEFVAL  	{ 0 }	
    	::= { lccmtsPoliceTolerance 1 }

lccmtsDnPolice OBJECT-TYPE
    	SYNTAX      	INTEGER (0..100)
	MAX-ACCESS 	read-write
	STATUS         	current
    	DESCRIPTION
        "The tolerance percentage to apply to configured maximum Downstream bit 
	 rate.  This allows for minor differences in shaping algoithms by not 
	 policing to the edge.  The default valued is 0% which will police to
	 the edge."
	DEFVAL  	{ 0 }	
    	::= { lccmtsPoliceTolerance 2 }


lccmtsBOOTPRelay OBJECT IDENTIFIER ::= { lccmtsdevice 8 }

lccmtsBOOTPRelayControl OBJECT-TYPE
    SYNTAX            INTEGER {
                              disabled(1),
                              enabled-relay-only(2),
                              enabled-relay-tagging(3),
                              enabled-cm-only-relay(4)
                              }
    MAX-ACCESS        read-write
    STATUS            current
    DESCRIPTION
        "Controls the operation of the CMTS BOOTP Relay function as listed. If set to:
         disabled(1)             The CMTS will process BOOTP/DHCP packets
                                 without special relay processing (this is the
                                 boot-time default),
         enabled-relay-only(2)   BOOTP/DHCP packets will be intercepted using the
                                 relay function described in RFC-1542, and server
                                 targets will be selected based not only on non-zero IP
                                 addresses in the server target table, but also based
                                 on whether the client is a registered CM, or unregistered
                                 and assumed to be a CPE host; That is, requests from CMs
                                 and CPE hosts may be sent to different servers, if desired.
         enabled-relay-tagging(3) BOOTP/DHCP packets will be tagged with Agent info containing
                                 the MAC address of the modem through which this request
                                 originated, in Remote ID format.
         enabled-cm-only-relay(4) BOOTP/DHCP packets will be intercepted using the
                                 relay function described in RFC-1542, and server
                                 targets will be selected based on non-zero IP
                                 addresses in the server target table for CM hosts ONLY.
                                 Requests from CPE hosts will be handled without special
                                 relay processing."
    ::= { lccmtsBOOTPRelay 1 }

lccmtsBOOTPRelaySvrTargetTable OBJECT-TYPE
    SYNTAX  SEQUENCE OF LccmtsBOOTPRelaySvrTargetEntry
    MAX-ACCESS  not-accessible
    STATUS  current
    DESCRIPTION
        "The table contains BOOTP Server target addresses, and discrimination
         parameters for selective targeting based upon registered CM addresses."
    ::= { lccmtsBOOTPRelay 2 }
 
lccmtsBOOTPRelaySvrTargetEntry OBJECT-TYPE
    SYNTAX  LccmtsBOOTPRelaySvrTargetEntry
    MAX-ACCESS  not-accessible
    STATUS  current
    DESCRIPTION
	"Each entry contains one BOOTP Server target IP address, which can be
         unicast, multicast or broadcast, and, optionally, discrimination
         parameters for selective targeting based upon registered CM addresses."
    INDEX   { lccmtsBOOTPRelayIndex }
    ::= { lccmtsBOOTPRelaySvrTargetTable 1 }

LccmtsBOOTPRelaySvrTargetEntry ::= SEQUENCE {
        lccmtsBOOTPRelayIndex
            INTEGER,
        lccmtsBOOTPRelaySvrTargetIP
            IpAddress,
        lccmtsBOOTPRelayClntSelectionMask
            INTEGER,
        lccmtsBOOTPRelaySvrTargetHits
            Counter32,
        lccmtsBOOTPRelayRowStatus
            RowStatus
    }

lccmtsBOOTPRelayIndex OBJECT-TYPE
    SYNTAX      INTEGER (1..10)
    MAX-ACCESS  not-accessible
    STATUS      current
    DESCRIPTION
	"The index value which uniquely identifies an entry
         in the lccmtsBOOTPRelayTable."
    ::= { lccmtsBOOTPRelaySvrTargetEntry 1 }

lccmtsBOOTPRelaySvrTargetIP OBJECT-TYPE
    SYNTAX            IpAddress 
    MAX-ACCESS        read-create
    STATUS            current
    DESCRIPTION
        "The IP (uni/multi/broad)cast address of targeted BOOTP server(s).
         If row is notInService(2), this entry is ignored."
    ::= { lccmtsBOOTPRelaySvrTargetEntry 2 }

lccmtsBOOTPRelayClntSelectionMask OBJECT-TYPE
    SYNTAX            INTEGER {
                              target-handles-CM-only(1),
                              target-handles-CPE-only(2),
                              target-handles-any(3)
                              }
    MAX-ACCESS        read-create
    STATUS            current
    DESCRIPTION
        "Controls the selection of BOOTP Servers based upon client status. If set to:
          target-handles-CM-only(1)  Client BOOTP/DHCP packets will be sent to this server
                                     address *ONLY* if client is a registered CM,
          target-handles-CPE-only(2) Client BOOTP/DHCP packets will be sent to this server
                                     address *ONLY* if client is NOT a registered CM, i.e
                                     presumed to be a CPE/host on the far side of a CM,
          target-handles-any(3)      Any client (CM or CPE) BOOTP/DHCP request will be sent
                                     to this server address."
    ::= { lccmtsBOOTPRelaySvrTargetEntry 3 }

lccmtsBOOTPRelaySvrTargetHits OBJECT-TYPE
    SYNTAX            Counter32 
    MAX-ACCESS        read-only
    STATUS            current
    DESCRIPTION
        "Counts # times a client request was copied to this target,
         regardless of CM discrimintation."
    ::= { lccmtsBOOTPRelaySvrTargetEntry 4 }

lccmtsBOOTPRelayRowStatus OBJECT-TYPE
        SYNTAX      RowStatus
        MAX-ACCESS  read-create
        STATUS      current
        DESCRIPTION
            "Controls and reflects the status of rows in this table.
             Only notInService(2) and active(1) states are supported - default
             is notInService."
    ::= { lccmtsBOOTPRelaySvrTargetEntry 5 }

lccmtsBOOTPRelayBadLengthDiscards        OBJECT-TYPE
    SYNTAX            Counter32 
    MAX-ACCESS        read-only
    STATUS            current
    DESCRIPTION
        "Counts # times an outgoing packet was silently dropped,
         due to having a miscalculated length value."
    ::= { lccmtsBOOTPRelay 3  }

lccmtsBOOTPRelayLocalOriginDiscards      OBJECT-TYPE
    SYNTAX            Counter32 
    MAX-ACCESS        read-only
    STATUS            current
    DESCRIPTION
        "Counts # times an outgoing packet was silently dropped,
         due to originating in the CMTS (should never happen!)."
    ::= { lccmtsBOOTPRelay 4  }

lccmtsBOOTPRelayExcessiveHopsDiscards    OBJECT-TYPE
    SYNTAX            Counter32 
    MAX-ACCESS        read-only
    STATUS            current
    DESCRIPTION
        "Counts # times an outgoing packet was silently dropped,
         due to an excessive hop count before increment."
    ::= { lccmtsBOOTPRelay 5  }

lccmtsBOOTPRelayGatewayAddrCopies        OBJECT-TYPE
    SYNTAX            Counter32 
    MAX-ACCESS        read-only
    STATUS            current
    DESCRIPTION
        "Counts # times an incoming packet had our (CMTS) address
         copied into the giaddr field."
    ::= { lccmtsBOOTPRelay 6  }

lccmtsBOOTPRelayLocalAddrSinks           OBJECT-TYPE
    SYNTAX            Counter32 
    MAX-ACCESS        read-only
    STATUS            current
    DESCRIPTION
        "Counts # times an incoming packet was selected for local processing,
         due to having a CMTS CHADDR."
    ::= { lccmtsBOOTPRelay 7  }

lccmtsBOOTPRelayWrongGatewayAddrDiscards OBJECT-TYPE
    SYNTAX            Counter32 
    MAX-ACCESS        read-only
    STATUS            current
    DESCRIPTION
        "Counts # times an incoming packet was silently dropped,
         due to server inserting the wrong gateway addr (i.e. not ours)."
    ::= { lccmtsBOOTPRelay 8  }

lccmtsBOOTPRelayNoCopyBufDiscards        OBJECT-TYPE
    SYNTAX            Counter32 
    MAX-ACCESS        read-only
    STATUS            current
    DESCRIPTION
        "Counts # times a packet was silently dropped,
         due to lack of a malloc'd copy buffer."
    ::= { lccmtsBOOTPRelay 9  }

lccmtsBOOTPRelayMiscSilentDiscards       OBJECT-TYPE
    SYNTAX            Counter32 
    MAX-ACCESS        read-only
    STATUS            current
    DESCRIPTION
        "Counts # times an outgoing packet was silently dropped,
         due to a variety of reasons not specifically tracked."
    ::= { lccmtsBOOTPRelay 10 }

lccmtsBOOTPRelayNoEpilBufDiscards        OBJECT-TYPE
    SYNTAX            Counter32 
    MAX-ACCESS        read-only
    STATUS            current
    DESCRIPTION
        "Counts # times an outgoing packet was dropped,
         due to a lack of Epilogue UDP/IP buffers."
    ::= { lccmtsBOOTPRelay 11 }

lccmtsBOOTPRelayClntDstPortDiscards      OBJECT-TYPE
    SYNTAX            Counter32 
    MAX-ACCESS        read-only
    STATUS            current
    DESCRIPTION
        "Counts # times an incoming packet was dropped,
         due to a destination port of BOOTP CLIENT."
    ::= { lccmtsBOOTPRelay 12 }

lccmtsBOOTPRelayRawRequests              OBJECT-TYPE
    SYNTAX            Counter32 
    MAX-ACCESS        read-only
    STATUS            current
    DESCRIPTION
        "Counts # times an incoming packet was processed as
         a raw request (subject to further filtering)."
    ::= { lccmtsBOOTPRelay 13 }

lccmtsBOOTPRelayRawReplies               OBJECT-TYPE
    SYNTAX            Counter32 
    MAX-ACCESS        read-only
    STATUS            current
    DESCRIPTION
        "Counts # times an incoming packet was processed as
         a raw reply (subject to further filtering)."
    ::= { lccmtsBOOTPRelay 14 }

lccmtsBOOTPRelayRqstFromCM               OBJECT-TYPE
    SYNTAX            Counter32 
    MAX-ACCESS        read-only
    STATUS            current
    DESCRIPTION
        "Counts # times an incoming request came from a modem."
    ::= { lccmtsBOOTPRelay 15 }

lccmtsBOOTPRelayRqstFromCPE              OBJECT-TYPE
    SYNTAX            Counter32 
    MAX-ACCESS        read-only
    STATUS            current
    DESCRIPTION
        "Counts # times an incoming request came from
         Customer Premises Equipment."
    ::= { lccmtsBOOTPRelay 16 }

lccmtsBOOTPRelayDPCATVPuts               OBJECT-TYPE    
    SYNTAX            Counter32 
    MAX-ACCESS        read-only
    STATUS            current
    DESCRIPTION
        "Counts # times an outgoing packet was sent to
         the cable DP_put routine."
    ::= { lccmtsBOOTPRelay 17 }

lccmtsBOOTPRelayDPEnetPuts               OBJECT-TYPE    
    SYNTAX            Counter32 
    MAX-ACCESS        read-only
    STATUS            current
    DESCRIPTION
        "Counts # times an outgoing packet was sent to
         the ethernet DP_put routine."
    ::= { lccmtsBOOTPRelay 18 }

lccmtsBOOTPRelayEpilUDPBufSends          OBJECT-TYPE
    SYNTAX            Counter32 
    MAX-ACCESS        read-only
    STATUS            current
    DESCRIPTION
        "Counts # times an outgoing packet was sent to
         the Epilogue UDP_send routine."
    ::= { lccmtsBOOTPRelay 19 }

lccmtsBOOTPRelayNullMACTags              OBJECT-TYPE   
    SYNTAX            Counter32 
    MAX-ACCESS        read-only
    STATUS            current
    DESCRIPTION
        "Counts # times an outgoing packet was tagged with
         a null CM macaddress."
    ::= { lccmtsBOOTPRelay 20 }

lccmtsBOOTPRelayNonNullMACTags           OBJECT-TYPE
    SYNTAX            Counter32 
    MAX-ACCESS        read-only
    STATUS            current
    DESCRIPTION
        "Counts # times an outgoing packet was tagged with
         a non-null CM macaddress."
    ::= { lccmtsBOOTPRelay 21 }

lccmtsBOOTPRelayWrongPortRqstDiscards    OBJECT-TYPE
    SYNTAX            Counter32 
    MAX-ACCESS        read-only
    STATUS            current
    DESCRIPTION
        "Counts # times an incoming request packet was discarded
         due to originating on a port other than cable."
    ::= { lccmtsBOOTPRelay 22 }

lccmtsBOOTPRelayWrongPortReplyDiscards   OBJECT-TYPE
    SYNTAX            Counter32 
    MAX-ACCESS        read-only
    STATUS            current
    DESCRIPTION
        "Counts # times an incoming reply packet was discarded
         due to originating on a port other than enet."
    ::= { lccmtsBOOTPRelay 23 }

lccmtsDNSResolver OBJECT IDENTIFIER ::= { lccmtsdevice 9 }

lccmtsDNSResolverControl OBJECT-TYPE
    SYNTAX            INTEGER {
                              disabled(1),
                              enabled(2)
                              }
    MAX-ACCESS        read-write
    STATUS            current
    DESCRIPTION
        "Controls the operation of the DNS Resolver function as listed. If set to:
          disabled(1)            The CMTS will not resolve names into addresses
                                 using DNS, returning a blank record for all lookups,
          enabled(2)             DNS reply packets will be processed and the results
                                 returned in the response record."
    ::= { lccmtsDNSResolver 1 }

lccmtsDNSResolverServiceType    OBJECT-TYPE
    SYNTAX            INTEGER {
                              recursiveOnly(1),
                              iterativeOnly(2),
                              recursiveAndIterative(3)
                              }
    MAX-ACCESS        read-only
    STATUS            current
    DESCRIPTION
        "Kind of DNS resolution service provided:
         recursiveOnly(1) indicates a stub resolver.
         iterativeOnly(2) indicates a normal full service
         resolver.
         recursiveAndIterative(3) indicates a full-service
         resolver which performs a mix of recursive and iterative
         queries."
    ::= { lccmtsDNSResolver 2 }

lccmtsDNSResolverServersCfgd    OBJECT-TYPE
    SYNTAX      INTEGER (1..10)
    MAX-ACCESS  read-only
    STATUS      current
    DESCRIPTION
	"The numbers indicates the total number of enabled servers
         configured by the operator."
    ::= { lccmtsDNSResolver 3 }

lccmtsDNSResolverServerTable    OBJECT-TYPE
    SYNTAX  SEQUENCE OF LccmtsDNSResolverServerEntry
    MAX-ACCESS  not-accessible
    STATUS  current
    DESCRIPTION
        "This table contains DNS Server addresses, and hierarchical
         selection parameters for Name Server lookups."
    ::= { lccmtsDNSResolver 4 }
 
lccmtsDNSResolverServerEntry OBJECT-TYPE
    SYNTAX  LccmtsDNSResolverServerEntry
    MAX-ACCESS  not-accessible
    STATUS  current
    DESCRIPTION
	"Each entry contains one DNS Server target IP address, its dot
         notation name, and its status (active or notInService)."
    INDEX   { lccmtsDNSResolverIndex }
    ::= { lccmtsDNSResolverServerTable 1 }

LccmtsDNSResolverServerEntry ::= SEQUENCE {
        lccmtsDNSResolverIndex
            INTEGER,
        lccmtsDNSResolverServerIP
            IpAddress,
        lccmtsDNSResolverServerPriority
            INTEGER,
        lccmtsDNSResolverServerName
            DisplayString,
        lccmtsDNSResolverRowStatus
            RowStatus
    }

lccmtsDNSResolverIndex OBJECT-TYPE
    SYNTAX      INTEGER (1..10)
    MAX-ACCESS  not-accessible
    STATUS      current
    DESCRIPTION
	"The index value which uniquely identifies an entry
         in the lccmtsDNSResolverTable."
    ::= { lccmtsDNSResolverServerEntry 1 }

lccmtsDNSResolverServerIP OBJECT-TYPE
    SYNTAX      IpAddress 
    MAX-ACCESS  read-write
    STATUS      current
    DESCRIPTION
        "The IP address of a DNS server.
         If row status is notInService(2), this entry is ignored."
    ::= { lccmtsDNSResolverServerEntry 2 }

lccmtsDNSResolverServerPriority OBJECT-TYPE
    SYNTAX      INTEGER (1..10)
    MAX-ACCESS  read-write
    STATUS      current
    DESCRIPTION
	"Precedence (priority) ordering of this entry in the
         server lookup hierarchy. Highest legal number is highest
         priority, lowest number is lowest priority."
    ::= { lccmtsDNSResolverServerEntry 3 }

lccmtsDNSResolverServerName OBJECT-TYPE
    SYNTAX      DisplayString (SIZE (0..64))
    MAX-ACCESS  read-write
    STATUS      current
    DESCRIPTION
        "The dot notation name of the DNS server."
    ::= { lccmtsDNSResolverServerEntry 4 }

lccmtsDNSResolverRowStatus OBJECT-TYPE
        SYNTAX      RowStatus
        MAX-ACCESS  read-write
        STATUS      current
        DESCRIPTION
            "Controls and reflects the status of rows in this table.
             Only notInService(2) and active(1) states are supported - default
             is notInService."
    ::= { lccmtsDNSResolverServerEntry 5 }


--
--  CMTS implementation of docsDevServer GROUP, which must not be implemented
--  for a CMTS in RFC2669.MIB (mcnscm.MIB) and so here it is!
--

--
-- The following group describes server access and parameters used for
-- initial provisioning and bootstrapping.
--

lccmtsDevServer OBJECT IDENTIFIER ::= { lccmtsdevice 10 }

lccmtsDevServerBootState OBJECT-TYPE
        SYNTAX INTEGER {
            operational(1),
            disabled(2),
            waitingForDhcpOffer(3),
            waitingForDhcpResponse(4),
            waitingForTimeServer(5),
            waitingForTftp(6),
            refusedByCmts(7),
            forwardingDenied(8),
            other(9),
            unknown(10)
        }
        MAX-ACCESS  read-only
        STATUS      current
        DESCRIPTION
            "If operational(1), the device has completed loading and
             processing of configuration parameters and the CMTS has
             completed the Registration exchange.
             If disabled(2) then the device was administratively
             disabled, possibly by being refused network access in the
             configuration file.
             If waitingForDhcpOffer(3) then a DHCP Discover has been
             transmitted and no offer has yet been received.
             If waitingForDhcpResponse(4) then a DHCP Request has been
             transmitted and no response has yet been received.
             If waitingForTimeServer(5) then a Time Request has been
             transmitted and no response has yet been received.
             If waitingForTftp(6) then a request to the TFTP parameter
             server has been made and no response received.
             If refusedByCmts(7) then the Registration Request/Response
             exchange with the CMTS failed.
             If forwardingDenied(8) then the registration process
             completed, but the network access option in the received
             configuration file prohibits forwarding. "
        ::= { lccmtsDevServer 1 }

lccmtsDevServerDhcp OBJECT-TYPE
        SYNTAX      IpAddress
        MAX-ACCESS  read-only
        STATUS      current
        DESCRIPTION
            "The IP address of the DHCP server that assigned an IP
             address to this device. Returns 0.0.0.0 if DHCP was not
             used for IP address assignment."
        ::= { lccmtsDevServer 2 }

lccmtsDevServerTime OBJECT-TYPE
        SYNTAX      IpAddress
        MAX-ACCESS  read-only
        STATUS      current
        DESCRIPTION
            "The IP address of the Time server (RFC-868)."
        ::= { lccmtsDevServer 3 }

lccmtsDevServerTftp OBJECT-TYPE
        SYNTAX      IpAddress
        MAX-ACCESS  read-only
        STATUS      current
        DESCRIPTION
            "The IP address of the TFTP server responsible for
             downloading provisioning and configuration parameters
             to this device."
        ::= { lccmtsDevServer 4 }

lccmtsDevServerConfigFile OBJECT-TYPE
        SYNTAX      DisplayString
        MAX-ACCESS  read-only
        STATUS      current
        DESCRIPTION
            "The name of the device configuration file read from the
             TFTP server."
        ::= { lccmtsDevServer 5 }


-- --------------------------------------------------------------------------
-- Begin CM Device section
-- --------------------------------------------------------------------------

-- The following is shipped with an MCNS factory default (for
-- North America). It is only expected to be changed for a small number
-- of systems.
--
--      from       to    HRC?     step     channel width
--    747 MHz   555 MHz   no      6 MHz        6 MHz
--    753 MHz   855 MHz   no      6 MHz        6 MHz
--    549 MHz   321 MHz   no      6 MHz        6 MHz
--    855 MHz   477 MHz   yes     6 MHz        6 MHz
--    747 MHz   555 MHz   no      6 MHz        6 MHz
--    753 MHz   855 MHz   no      6 MHz        6 MHz
--    315 MHz    93 MHz   no      6 MHz        6 MHz
--    471 MHz    93 MHz   yes     6 MHz        6 MHz

lcScanningFrequencyTable OBJECT-TYPE
    SYNTAX          SEQUENCE OF LcScanningFrequencyEntry
    MAX-ACCESS      not-accessible
    STATUS          current
    DESCRIPTION
        "Defines the frequencies and scanning order used by the modem
         to find the downstream channel."
    ::= { lccmdevice 1 }

lcScanningFrequencyEntry OBJECT-TYPE
    SYNTAX          LcScanningFrequencyEntry
    MAX-ACCESS      not-accessible
    STATUS          current
    DESCRIPTION
        "Defines a range of channels to be used by the modem to find the
        downstream channel."
    INDEX { lcScanIndex }
    ::= { lcScanningFrequencyTable 1 }

LcScanningFrequencyEntry ::= SEQUENCE {
        lcScanControl       RowStatus,
        lcScanIndex         INTEGER,
        lcScanFreqStart     Integer32,
        lcScanFreqEnd       Integer32,
        lcScanUseHrc        TruthValue,
        lcScanStep          Integer32,
        lcScanChannelWidth  Integer32
        }

lcScanControl       OBJECT-TYPE
    SYNTAX          RowStatus
    MAX-ACCESS      read-create
    STATUS          current
    DESCRIPTION
        "Controls the creation and deletion of rows in this table. See RFC-1903
         for definition of enumeration."
    ::= { lcScanningFrequencyEntry 1 }



lcScanIndex         OBJECT-TYPE
    SYNTAX          INTEGER (1..16)
    MAX-ACCESS      read-create
    STATUS          current
    DESCRIPTION
        "An ad-hoc index for defining the scanning order for this table."
    ::= { lcScanningFrequencyEntry 2 }


lcScanFreqStart     OBJECT-TYPE
    SYNTAX          Integer32
    UNITS           "kilohertz"
    MAX-ACCESS      read-create
    STATUS          current
    DESCRIPTION
        "The center frequency of the first channel to scan in this range."
    -- No DEFVAL for this object.
    ::= { lcScanningFrequencyEntry 3 }


lcScanFreqEnd       OBJECT-TYPE
    SYNTAX          Integer32
    UNITS           "kilohertz"
    MAX-ACCESS      read-create
    STATUS          current
    DESCRIPTION
        "The center frequency of the last channel to scan in this range. This
        may be higher or lower than lcScanFreqStart."
    -- DEFVAL is equal to lcScanFreqStart.
    ::= { lcScanningFrequencyEntry 4 }


lcScanUseHrc        OBJECT-TYPE
    SYNTAX          TruthValue
    MAX-ACCESS      read-create
    STATUS          current
    DESCRIPTION
        "If TRUE then the range is to use the HRC channels which correspond to
        the Std/IRC channels whose center frequencies are defined by FreqStart
        and FreqEnd (i.e. offset the values in FreqStart and FreqEnd before 
        using them)."
    DEFVAL { 2 } -- false
    ::= { lcScanningFrequencyEntry 5 }


lcScanStep          OBJECT-TYPE
    SYNTAX          Integer32
    UNITS           "kilohertz"
    MAX-ACCESS      read-create
    STATUS          current
    DESCRIPTION
        "The absolute value of the increment (or decrement) to use in stepping
        through this range."
    -- DEFVAL equals lcScanChannelWidth
    ::= { lcScanningFrequencyEntry 6 }


lcScanChannelWidth              OBJECT-TYPE
    SYNTAX          Integer32
    UNITS           "kilohertz"
    MAX-ACCESS      read-create
    STATUS          current
    DESCRIPTION
        "The channel width to use for this range. Only 6000 and 8000 are 
         allowed."
    DEFVAL { 6000 }
    ::= { lcScanningFrequencyEntry 7 }


lccmAddress OBJECT IDENTIFIER ::= { lccmdevice 2 }

lccmIpAddress  OBJECT-TYPE
    SYNTAX         IpAddress
    MAX-ACCESS     read-write
    STATUS         current
    DESCRIPTION
        "The IP address of the CM; provides a writable equivalent of
        ipAdEntAddr. If set to null (0.0.0.0), the address must be provided
        through DHCP."
    ::= { lccmAddress 1 }


lccmIpSubnet   OBJECT-TYPE
    SYNTAX         IpAddress
    MAX-ACCESS     read-write
    STATUS         current
    DESCRIPTION
        "The subnet mask corresponding to lcCMIpAddress; provides a
        writable equivalent of ipAdEntNetMask."
    ::= { lccmAddress 2 }



-- the trap type control table
 
-- The trap type control table contains an entry for each
-- type of trap supported by the system 
 
          lcTrapTypeTable OBJECT-TYPE
              SYNTAX  SEQUENCE OF LcTrapTypeEntry
              MAX-ACCESS  not-accessible
              STATUS  current
              DESCRIPTION
          	"The trap type control table contains an entry for each
          	type of trap supported by the system."
          ::= { lcdevicecommon 1 }
 
          lcTrapTypeEntry OBJECT-TYPE
              SYNTAX  LcTrapTypeEntry
              MAX-ACCESS  not-accessible
              STATUS  current
              DESCRIPTION
                      "An entry in this table defines a particular trap 
			type supported by the system."
              INDEX   { lcTrapTypeIndex }
              ::= { lcTrapTypeTable 1 }
 
           LcTrapTypeEntry ::=
              SEQUENCE {
                  lcTrapTypeIndex   INTEGER,
                  lcTrapTypeStatus  INTEGER
              }
 
--
-- NOTE: The trap values in this table must match their corresponding
--       trap numbering in sm.h.  For example, SM_LC_MCAST_TRAP is
--       #define'd to be 9 in sm.h, so its enumerated value is 9 here.
--       As another example, SM_EVENT_HANDLER_TRAP is #defined to be 8 in
--       sm.h, but 8 is not a defined enumeration here, because 
--       event handler traps are NOT controlled from this table, they
--       are controlled through event handler tables.
--
        lcTrapTypeIndex OBJECT-TYPE
            SYNTAX  INTEGER {
				coldstartTrap(1),
				warmstartTrap(2),
				linkUpTrap(3),
				linkDownTrap(4),
				authenticationFailureTrap(5),
				topologyChangeTrap(6),
				newRootTrap(7),
-- Skip 8
				lcMcastJoinTrap(9)
			    }
            MAX-ACCESS  read-only
            STATUS  current
            DESCRIPTION
                "The variable is the index of this entry in the 
		lcTrapTypeTable."
            ::= { lcTrapTypeEntry 1 }
 
        lcTrapTypeStatus OBJECT-TYPE
            SYNTAX  INTEGER {
                sendTrap(1),   --this type of trap should be sent 
                noTrap(2)      --this type of trap should NOT be sent 
                }
            MAX-ACCESS  read-write
            STATUS  current
            DESCRIPTION
                "This variable controls whether this type of trap
		is generated by this device."
            ::= { lcTrapTypeEntry 2 }


lcBootedAlbumFilename OBJECT-TYPE
       SYNTAX	DisplayString (SIZE (0..255))
       MAX-ACCESS read-only
       STATUS     current
       DESCRIPTION
		"The filename that is embedded in the flash album header of
                 the currently booted album software image"
	::= { lcdevicecommon 2 }

lcBootedAlbumSequenceNumber OBJECT-TYPE
       SYNTAX	Counter32 
       MAX-ACCESS read-only
       STATUS     current
       DESCRIPTION
		"The sequence number of the currently loaded software image."
	::= { lcdevicecommon 3 }

lcIpFiltSendDu OBJECT-TYPE
        SYNTAX  INTEGER {
                on(1),  -- send DU if packet filtered 
                off(2)  -- do NOT send DU if packet filtered 
                }
        MAX-ACCESS  read-write
        STATUS  current
        DESCRIPTION
                "This variable specifies whether a 'destination unreachable'
                ICMP message is sent when a packet is filtered due to
                IP protocol filtering."
	::= { lcdevicecommon 5 }


lcIpFiltIcmp9 OBJECT-TYPE
        SYNTAX  INTEGER {
                on(1),  -- do NOT forward ICMP Type 9 packets
                off(2)  -- forward ICMP Type 9 packets
                }
        MAX-ACCESS  read-write
        STATUS  current
        DESCRIPTION
                "This variable specifies whether ICMP Type 9 packets
                are forwarded or filtered on all interfaces."
	::= { lcdevicecommon 16 }


lcMulticastGroup OBJECT IDENTIFIER ::= { lcdevicecommon 6 }

lcMcastControl OBJECT-TYPE
	SYNTAX INTEGER { 
		pass(1), 
		discard(2), 
		igmp(3), 
		trap(4) 
		}
	MAX-ACCESS read-write
	STATUS current
	DESCRIPTION
        "Action to take on receiving an IP multicast packet bound for the
	 subscriber network. If pass(1), the CM acts as a bridge, transparently
	 forwarding all multicast packets. If filter(2), all IP multicast
	 packets are discarded. If igmp(3) then the CM acts as an IGMP proxy
	 and only forwards packets whose addresses were requested by the
	 subscriber. If trap(4) then the CM transmits IGMP queries on the
         subscriber side. On receiving Reports, it transmits an SNMP trap.
         Multicast packets are forwarded, and presumably blocked by SNMP-
         managed filters."
	::= { lcMulticastGroup 1 }

lcMcastAddressTable OBJECT-TYPE
    SYNTAX          SEQUENCE OF LcMcastAddressEntry
    MAX-ACCESS      not-accessible
    STATUS          current
    DESCRIPTION
	"Describes the current state of multicast address filtering being
	 performed by the IGMP proxy."
    ::= { lcMulticastGroup 2 }

lcMcastAddressEntry OBJECT-TYPE
    SYNTAX          LcMcastAddressEntry
    MAX-ACCESS      not-accessible
    STATUS          current
    DESCRIPTION
	"Describes the current state of a multicast address controlled by
	 the IGMP proxy."
    INDEX { lcMcastAddress }
    ::= { lcMcastAddressTable 1 }

LcMcastAddressEntry ::= SEQUENCE {
	lcMcastAddress 		IpAddress,
	lcMcastAdminState       RowStatus,
	lcMcastOperState        INTEGER,
	lcMcastTtl		TimeTicks
	}

lcMcastAddress		OBJECT-TYPE
	SYNTAX		IpAddress
	MAX-ACCESS	not-accessible
	STATUS		current
	DESCRIPTION
	"The IP multicast address being managed."
	::= { lcMcastAddressEntry 1 }

lcMcastAdminState	OBJECT-TYPE
	SYNTAX		RowStatus
	MAX-ACCESS	read-create
	STATUS		current
	DESCRIPTION
	"Controls addition of static entries or deletion of any entries in this
	 table."
	::= { lcMcastAddressEntry 2 }

lcMcastOperState	OBJECT-TYPE
	SYNTAX		INTEGER { nonmember(1), delaying(2), idle(3), static(4) }
	MAX-ACCESS	read-only
	STATUS		current
	DESCRIPTION
	"Reflects the IGMP state of this address. If static(4), the entry was created
	 as a result of management action, and the entry is not subject to the IGMP
	 protocol."
	::= { lcMcastAddressEntry 3 }

lcMcastTtl		OBJECT-TYPE
	SYNTAX		TimeTicks
	MAX-ACCESS	read-only
	STATUS		current
	DESCRIPTION
	"Time-to-live for this entry. Will return zero for static entries."
	::= { lcMcastAddressEntry 4 }


lcMcastTrapAddress	OBJECT-TYPE
	SYNTAX		IpAddress
	MAX-ACCESS	not-accessible
	STATUS		current
	DESCRIPTION
	"The IP multicast address that is included in the lcMcastJoin
	 trap. This object only exists for purposes of inclusion in the
	 trap message."
	::= { lcMulticastGroup 3 }

lcRestartFromFactoryDefaults    OBJECT-TYPE
        SYNTAX          TruthValue
        MAX-ACCESS      read-write
        STATUS          current
        DESCRIPTION
        "Setting this object to true(1) causes the device to reset. When
         restarting, it will have forgotten all configuration parameters
         that are normally stored in nonvolatile memory. The device will
         start up as if delivered from the factory. Reading this object 
         always returns false(2)."
        ::= { lcdevicecommon 7 }



lcPhyTable OBJECT-TYPE
    SYNTAX          SEQUENCE OF LcPhyEntry
    MAX-ACCESS      not-accessible
    STATUS          current
    DESCRIPTION
        "Determines how the ETHERNET PHYs are configured and  operating"
    ::= { lcdevicecommon 8 }


lcPhyEntry OBJECT-TYPE
    SYNTAX          LcPhyEntry
    MAX-ACCESS      not-accessible
    STATUS          current
    DESCRIPTION
        "Determines how an ETHERNET PHYs is configured and operating"
    INDEX { lcPhyIndex }
    ::= { lcPhyTable 1 }


LcPhyEntry ::= SEQUENCE {
        lcPhyIndex         INTEGER,
        lcPhyEnable        TruthValue,
        lcPhyAutoNegotiate TruthValue,
        lcPhyActive        TruthValue,
        lcPhySpeed         Integer32,
        lcPhyFullDuplex    TruthValue
        }


lcPhyIndex         OBJECT-TYPE
    SYNTAX          INTEGER {
                        primary(1),
                        aux1(2)
                    }
    MAX-ACCESS      read-only
    STATUS          current
    DESCRIPTION
        "Name/Index for each ETHERNET PHY"
    ::= { lcPhyEntry 1 }


lcPhyEnable        OBJECT-TYPE
    SYNTAX          TruthValue
    MAX-ACCESS      read-write
    STATUS          current
    DESCRIPTION
        "If true, this PHY may be used. If false, this will not be used."
    DEFVAL { 1 } -- true
    ::= { lcPhyEntry 2 }


lcPhyAutoNegotiate  OBJECT-TYPE
    SYNTAX          TruthValue
    MAX-ACCESS      read-write
    STATUS          current
    DESCRIPTION
        "If true, this PHY autonegotiates if active. If false,
         this PHY is manually configured if active."
    DEFVAL { 1 } -- true
    ::= { lcPhyEntry 3 }


lcPhyActive         OBJECT-TYPE
    SYNTAX          TruthValue
    MAX-ACCESS      read-only
    STATUS          current
    DESCRIPTION
        "If true, this PHY is the one being used. If false,
         this PHY is not being used."
    ::= { lcPhyEntry 4 }


lcPhySpeed         OBJECT-TYPE
    SYNTAX          Integer32
    MAX-ACCESS      read-write
    STATUS          current
    DESCRIPTION
        "Determines the speed for this PHY. If lcPhyAutoNegotiate is
         true, writes to this value are prohibited. If lcPhyAutoNegotiate is
         false, this PHY will be force to this speed. Valid values are 
         10000000 and 100000000"
    DEFVAL { 10000000 } -- 10 MB
    ::= { lcPhyEntry 5 }


lcPhyFullDuplex         OBJECT-TYPE
    SYNTAX          TruthValue
    MAX-ACCESS      read-write
    STATUS          current
    DESCRIPTION
        "Determines the duplex mode for this PHY. If lcPhyAutoNegotiate is
         true, writes to this value are prohibited. If lcPhyAutoNegotiate is
         false, this PHY will be force to this duplex mode"
    DEFVAL { 2 } -- false
    ::= { lcPhyEntry 6 }

lcStickyYellowTable	OBJECT-TYPE
	SYNTAX		SEQUENCE OF LcStickyYellowEntry
	MAX-ACCESS	not-accessible
	STATUS		current
	DESCRIPTION
	"This table provides a maintenance-history area where
	 notes about the device may be stored. The contents of
	 this table are entirely for human benefit and have
	 no effect on the operation of the device. Up to 8 entries
	 of up to 80 characters each may be stored."
	::= { lcdevicecommon 9 }

lcStickyYellowEntry	OBJECT-TYPE
	SYNTAX		LcStickyYellowEntry
	MAX-ACCESS	not-accessible
	STATUS		current
	DESCRIPTION
	"Each entry provides a line of text of maintenance history."
	INDEX { lcStickyYellowIndex }
	::= { lcStickyYellowTable 1 }

LcStickyYellowEntry ::= SEQUENCE {
	lcStickyYellowIndex	INTEGER,
	lcStickyYellowPad	DisplayString
	}

lcStickyYellowIndex	OBJECT-TYPE
	SYNTAX		INTEGER
	MAX-ACCESS	not-accessible
	STATUS		current
	DESCRIPTION
	"Provides an index by which to distinguish up to 8 lines
	 of text."
	::= { lcStickyYellowEntry 1 }

lcStickyYellowPad	OBJECT-TYPE
	SYNTAX		DisplayString
	MAX-ACCESS	read-create
	STATUS		current
	DESCRIPTION
	"Contents of this object are for the benefit of a human operator
	 and may be used for any information, such as maintenance history,
	 that the operator wishes to associate with the device. Contents
	 of this object have no effect on the operation of the device.
	 Setting this object to any non-null value either creates the
	 row or overwrites previous text. Setting to the the null 
	 string deletes the row. Set's longer than 80 characters are
	 truncated."
	::= { lcStickyYellowEntry 2 }

lcResetFilters          OBJECT-TYPE
        SYNTAX          TruthValue
        MAX-ACCESS      read-write
        STATUS          current
        DESCRIPTION
        "Setting this object to true(1) causes the device to reset the
	 following Docsis MIB objects as follows, so that filters are
   	 no longer applied to traffic:
		 docsDevFilterLLCDefault is set to accept(2).
		 docsDevFilterIpDefault  is set to accept(2).
		 All entries in the docsDevFilterLLCTable are destroyed.
		 All entries in the docsDevFilterIpTable are destroyed.
         Note that the device is not reset; filters are destroyed on the fly.
         Reading this object always returns false(2).
	 This object can be used to clear out previously set filters 
         without having to know all the instances of existing entries."
        ::= { lcdevicecommon 10 }

lcResetNmAccessTable    OBJECT-TYPE
        SYNTAX          TruthValue
        MAX-ACCESS      read-write
        STATUS          current
        DESCRIPTION
        "Setting this object to true(1) causes the device to destroy all
	 docsDevNmAccessTable entries, such that the table is empty.
         The DOCSIS Cable Device MIB specifies that it the table is
         empty, access to SNMP objects is unrestricted.
         Note that the device is not reset; entries are destroyed on the fly.
         Reading this object always returns false(2).
	 This object can be used to clear out previously set entries
         in the docsDevNmAccessTable without having to know all the 
         instances of existing entries."
        ::= { lcdevicecommon 11 }

lcFlashPersistenceSwitch  OBJECT-TYPE
	SYNTAX BITS {
		nmAccess(0),
		llcIpFilters(1)
	}
        MAX-ACCESS      read-write
        STATUS          current
	DESCRIPTION
	"Specifies the flash persistence behavior of the associated
	 MIB objects.

	 lcFlashPersistenceSwitch MIB object is itself saved to flash.
	 At modem startup, the value of lcFlashPersistenceSwitch is read
	 from flash and used to determine how to initialize the associated
	 MIB objects.  At runtime, lcFlashPersistenceSwitch is used to 
	 determine whether or not modifications made to the enumerated 
	 MIB objects are saved to flash.

	 The factory default is no bits set; thus, none of the enumerated
	 MIB objects are initialized from flash, and subsequent modifications
	 to the enumerated MIB objects are not saved to flash.

	 If a bit value is set at startup, the associated MIB object will
	 be initialized from flash memory, and subsequent modifications will
	 be saved to flash.
	 If a bit is set at runtime, the associated MIB object is immediately
	 written to flash, and subsequent modifications will be saved to flash.

	 If a bit value is not set at startup, factory default values will be
	 used to initialize the associated MIB object, and subsequent
	 modifications will not be saved to flash memory.
	 If a bit is cleared during runtime, subsequent modifications to the
	 associated MIB object will not be saved to flash.

	 The nmAccess(0) bit effects the docsDevNmAccessTable.
	 The llcIpFilters(1) bit effects docsDevFilterLLCDefault, 
	 docsDevFilterLLCTable, docsDevFilterIpDefault, and 
	 docsDevFilterIpTable. "
        ::= { lcdevicecommon 12 }
	
lcConcatenationEnabled OBJECT-TYPE
    SYNTAX          TruthValue
    MAX-ACCESS      read-write
    STATUS          current
    DESCRIPTION
        "For modem, this determines if concatenation should be turned on
	 or not, when it is supported by the headend.
	 For headend, this determines if concatenation support is desirable
	 and possible (only possible on 3210B or later chips)."
    ::= { lcdevicecommon 13 }

lcConsoleAccess OBJECT IDENTIFIER ::= { lcdevicecommon 14 }

lcConsoleUserTable      OBJECT-TYPE
        SYNTAX  SEQUENCE OF LcConsoleUserEntry
        MAX-ACCESS  not-accessible
        STATUS  current
        DESCRIPTION
        "Defines user names, passwords, and access privileges for
         console and telnet access to the device. This table is
         primarily a repository for user names and passwords, as the
         accesss rights are actually defined in other tables. This 
         table points to the lcConsoleLevelTable, which in turn may
         point to docsDevNmAccessTable. Access to this table itself 
         is restricted in the same manner as docsDevNmAccessTable; 
         that is, the operator must have write privileges to be able 
         to read this table (with exception of being able to read
	 their own entry)."
        ::= { lcConsoleAccess 1 }

lcConsoleUserEntry      OBJECT-TYPE
        SYNTAX  LcConsoleUserEntry
        MAX-ACCESS  not-accessible
        STATUS  current
        DESCRIPTION
        "Describes the attributes of a single user login."
        INDEX { lcConsoleUserIndex }
        ::= { lcConsoleUserTable 1 }

LcConsoleUserEntry ::= SEQUENCE {
        lcConsoleUserIndex    INTEGER,
        lcConsoleUserStatus   RowStatus,
        lcConsoleUserName     DisplayString,
        lcConsoleUserPassword DisplayString,
        lcConsoleUserLevel    INTEGER
        }

lcConsoleUserIndex      OBJECT-TYPE
        SYNTAX  INTEGER
        MAX-ACCESS  not-accessible
        STATUS  current
        DESCRIPTION
        "Provides an index to this table. Provides no semantics."
        ::= { lcConsoleUserEntry 1 }

lcConsoleUserStatus     OBJECT-TYPE
        SYNTAX  RowStatus
        MAX-ACCESS  read-create
        STATUS  current
        DESCRIPTION
        "Controls additions and deletions from this table. May 
         only be set to createAndGo or destroy."
        ::= { lcConsoleUserEntry 2 }

lcConsoleUserName       OBJECT-TYPE
        SYNTAX  DisplayString
        MAX-ACCESS  read-create
        STATUS  current
        DESCRIPTION
        "User login name, as used for the console or telnet.  Deletion
	 of the currently logged in account results in being logged out."
        DEFVAL { "root" }
        ::= { lcConsoleUserEntry 3 }

lcConsoleUserPassword   OBJECT-TYPE
        SYNTAX  DisplayString
        MAX-ACCESS  read-create
        STATUS  current
        DESCRIPTION
        "The user's password, as used for the console or telnet.
         This is an MD5 hashed string, and returns
	 a 32 character ASCII representation of the hex 16 byte value
	 when a get is attempted.  
	 For set operations, the value for the set must be the
	 32 byte ASCII representation of the 16 byte hex MD5 hash
	 value.  See RFC 1321 for MD5 hash operations.
	 The default value is the MD5 hash of the null string."
        DEFVAL { "" }
        ::= { lcConsoleUserEntry 4 }

lcConsoleUserLevel      OBJECT-TYPE
        SYNTAX  INTEGER
        MAX-ACCESS  read-create
        STATUS  current
        DESCRIPTION
        "The index of a row in lcConsoleLevelTable which defines
         the access privileges for this user. If the referenced
         row does not exist then access is not allowed."
         DEFVAL { 1 }
        ::= { lcConsoleUserEntry 5 }


lcConsoleLevelTable     OBJECT-TYPE
        SYNTAX  SEQUENCE OF LcConsoleLevelEntry
        MAX-ACCESS  not-accessible
        STATUS  current
        DESCRIPTION
        "Defines access privilege levels for the console and for
         telnet. Entries in this table are referenced by the 
         lcConsoleUserTable. This table, in turn, will reference
         docsDevNmAccessTable."
        ::= { lcConsoleAccess 2 }

lcConsoleLevelEntry     OBJECT-TYPE
        SYNTAX  LcConsoleLevelEntry
        MAX-ACCESS  not-accessible
        STATUS  current
        DESCRIPTION
        "Defines a specific console privilege level in terms of
         access method and access name."
        INDEX { lcConsoleLevelIndex }
        ::= { lcConsoleLevelTable 1 }

LcConsoleLevelEntry ::= SEQUENCE {
        lcConsoleLevelIndex   INTEGER,
        lcConsoleLevelStatus  RowStatus,
        lcConsoleLevelName    DisplayString,
        lcConsoleLevelMethod  INTEGER,
        lcConsoleLevelSecurityName DisplayString
        }

lcConsoleLevelIndex     OBJECT-TYPE
        SYNTAX  INTEGER
        MAX-ACCESS  not-accessible
        STATUS  current
        DESCRIPTION
        "Provides an index to this table, referenced by lcConsoleUserLevel.
         Provides no ordering or other semantics."
        ::= { lcConsoleLevelEntry 1 }

lcConsoleLevelStatus    OBJECT-TYPE
        SYNTAX  RowStatus
        MAX-ACCESS  read-create
        STATUS  current
        DESCRIPTION
        "Controls additions and deletions from this table. May 
         only be set to createAndGo or destroy."
        ::= { lcConsoleLevelEntry 2 }

lcConsoleLevelName      OBJECT-TYPE
        SYNTAX  DisplayString
        MAX-ACCESS  read-create
        STATUS  current
        DESCRIPTION
        "A label which can be attached to this access Level as
         a mnemonic aid. Not used operationally."
        DEFVAL { "" }
        ::= { lcConsoleLevelEntry 3 }

lcConsoleLevelMethod    OBJECT-TYPE
        SYNTAX  INTEGER { snmpv1(1) }
        MAX-ACCESS  read-create
        STATUS  current
        DESCRIPTION
        "Defines which SNMP access method is used to validate 
         requests from this level. If snmpv1(1), then read-only, 
         read-write, and sundry other privileges are derived
         from docsDevNmAccessTable and lcNmAccessExtensionTable."
        DEFVAL { snmpv1 }
        ::= { lcConsoleLevelEntry 4 }

lcConsoleLevelSecurityName  OBJECT-TYPE
        SYNTAX  DisplayString
        MAX-ACCESS  read-create
        STATUS  current
        DESCRIPTION
        "If snmpv1 access is used, this value supplies the
         community string. "
        DEFVAL { "" }
        ::= { lcConsoleLevelEntry 5 }


lcNmAccessExtensionTable  OBJECT-TYPE
        SYNTAX          SEQUENCE OF LcNmAccessExtensionEntry
        MAX-ACCESS      not-accessible
        STATUS          current
        DESCRIPTION
        "Further qualifies the privileges accorded to each row of the
         docsDevNmAccessTable. This table provides a set of specific
         privileges for users who are either using SNMPv1 directly or
         who are using SNMPv1-based access through the console."
        ::= { lcdevicecommon 15 }

lcNmAccessExtensionEntry  OBJECT-TYPE
        SYNTAX          LcNmAccessExtensionEntry
        MAX-ACCESS      not-accessible
        STATUS          current
        DESCRIPTION
        "Qualifies the privileges accorded to a row of docsDevNmAccessTable."
        AUGMENTS { docsDevNmAccessEntry }
        ::= { lcNmAccessExtensionTable 1 }

LcNmAccessExtensionEntry ::= SEQUENCE {
        lcNmAccessAdditionalPrivileges   BITS
        }

lcNmAccessAdditionalPrivileges  OBJECT-TYPE
        SYNTAX          BITS  {
                                resetAllowed(0),
                                accountManager(1)
                              }
        MAX-ACCESS      read-create
        STATUS          current
        DESCRIPTION
        "Defines additional privileges allowed a user. The resetAllowed bit
         (value 0x80) allows an operator with a read-only account the privilege
         of resetting the CMTS from either a telnet or console session using 
	 the CLI reset command, in addition to all other privileges allowed by
         the docsDevNmAccessTable for a read/only account.  The resetAllowed 
	 bit does not allow the user to use the 'factory' option of the reset 
	 command.  The resetAllowed bit does not allow the user remote SNMP 
	 write access to either the docsDevResetNow or the 
	 lcRestartFromFactoryDefault MIBs.  A read/write entry gets reset 
	 ability automatically, so setting resetAllowed for read/write entries
	 is not necessary.  The accountManager bit (value 0x40) allows a 
	 read/write account to perform the additional account management 
	 function of creation, modification, and deletion of accounts, in 
	 addition to any other privileges accorded by docsDevNmAccessTable.  
	 Read/only accounts do not access the accountManager bit."
        ::= { lcNmAccessExtensionEntry 1 }


lcTelnetAllowedSessions  OBJECT-TYPE
        SYNTAX          INTEGER  
        MAX-ACCESS      read-write
        STATUS          current
        DESCRIPTION
        "Indicates the number of remote telnet access sessions allowed.
	 A value of 0 indicates remote telnet access is denied.  A maximum
	 of 5 is allowed."
	DEFVAL { 5 }
	::= { lcConsoleAccess 3 }

lcSessionInactivityTimeout  OBJECT-TYPE
        SYNTAX          INTEGER (0..10080)
	UNITS           "minutes"
        MAX-ACCESS      read-write
        STATUS          current
        DESCRIPTION
        "The session inactivity timeout value in minutes.  A 
         value of 0 indicates no session timeout.  The maximum timeout
	 is one week.  Applies to all sessions (both Command line and 
	 Telnet sessions), but each session maintains a separate 
	 inactivity timer.  This timer starts after a successful
	 login, and is restarted every time a command is entered.
	 If this timer expires, the associated session is terminated.
	 Termination of the console results in a user logout.  
	 Termination of a telnet session results in a user logout and
         a telnet disconnect process."
	::= { lcConsoleAccess 4 }




-- Group to define variables returned in traps that aren't already
-- defined in other groups.
-- Trap variables must have OID's associated with them.

-- Authentication Failure Trap variables, an extention to
-- the rfc1215 authentication failure trap, which doesn't
-- specify variables.
lcAuthFailErrorStatus OBJECT-TYPE
       SYNTAX  INTEGER {
                   nmAccessTableRestriction(1),       
		   noWriteAccessToMibVar(2),
		   other(3)
               }
       MAX-ACCESS not-accessible
       STATUS     current
       DESCRIPTION
	       "The reason for failure to validate the SNMP request.
               nmAccessTableRestriction(1) indicates that the requesting 
               network management station (NMS) does not have appropriate
               permission to perform the SNMP request, because it either
               does not match an ip address in the docsDevNmAccessTable, or
               the community string in the SNMP request did not match the 
               community string in docsDevNmAccessTable for the requesting NMS,
	       or the docsDevNmAccessControl value specified in the 
	       docsDevNmAccessTable for this NMS was not sufficient to allow 
               access for the SNMP request type (either 'get' or 'set'), or
	       finally the SNMP request from this NMS is not accepted on the 
	       interface (ethernet or CATV) that the request was received.
	       noWriteAccessToMibVar(2) indicates that an SNMP set request
               was received for a mib variable whose write access control is
               set.
	       other(3) indicates an nonspecific error."
       ::= { lctrapvars 1 }
 

lcAuthFailCommunityString OBJECT-TYPE
       SYNTAX	DisplayString (SIZE (0..255))
       MAX-ACCESS not-accessible
       STATUS     current
       DESCRIPTION
		"This the community string received in a Get/Set SNMP 
	        request that did not pass authentication tests. This 
	        object is returned in the authenticationFailure trap."
	::= { lctrapvars 2 }

lcAuthFailIpAddr OBJECT-TYPE	
       SYNTAX	IpAddress
       MAX-ACCESS not-accessible
       STATUS     current
       DESCRIPTION
		"This is the source address of a Get/Set SNMP request
	        that did not pass authentication tests.  This object is
	        returned in the authenticationFailure trap."
	::= { lctrapvars 3 }

lcAuthFailInterface OBJECT-TYPE	
       SYNTAX  INTEGER {
                   ethernet(1),       
		   catv(2),
		   other(3)
               }
       MAX-ACCESS not-accessible
       STATUS     current
       DESCRIPTION
		"This is the interface port on which was received a Get/Set 
 	        SNMP request that did not pass authentication tests.
	        This object is returned in the authenticationFailure trap."
	::= { lctrapvars 4 }


-- This group contains the traps.

-- For lancity traps, use id group 1850-1899
lcMcastJoin TRAP-TYPE
    ENTERPRISE   lancity
    VARIABLES    { lcMcastTrapAddress }
    DESCRIPTION
        "Generated when lcMcastControl is set to trap(4) and an
	 initial IGMP Report is received from the subscriber network."
    ::= 1850 


-- The following trap text has been generated from
-- eh_Table_cpp.pl and written to eh_trap.mib, and hand-inserted 
-- into this mib. 
--
-- BE SURE this is editted to contain the latest creation of eh_trap.mib!!!
-- NOTE: some traps are NOT generated by the event handler,
--       such as the lcMcastJoin trap.
--       Those traps are defined above, and their trap numbers
--       are taken from the group 1850-1899.
--
--
--
-- eh_trap.mib - event handler SNMP traps
--
-- This file is automatically generated from eh_table_cpp.pl.
-- Created: Wed Aug  4 15:37:54 EDT 1999

--

lcErrKernelFailure TRAP-TYPE
    ENTERPRISE   lancity
    VARIABLES    {docsDevEvText}
    DESCRIPTION
        "	System tasking failure"
    ::= 100

lcErrNuSendItemFailure TRAP-TYPE
    ENTERPRISE   lancity
    VARIABLES    {docsDevEvText}
    DESCRIPTION
        "	NU_Send_Item failed but task will try to send again"
    ::= 101

lcErrUnknown TRAP-TYPE
    ENTERPRISE   lancity
    VARIABLES    {docsDevEvText}
    DESCRIPTION
        "	Unknown error SNMP Trap"
    ::= 200

lcErrSystemError TRAP-TYPE
    ENTERPRISE   lancity
    VARIABLES    {docsDevEvText}
    DESCRIPTION
        "	System error, some sort of exception.  Displayed are the
	EPC, Cause, BadVaddr and Status registers."
    ::= 201

lcErrTest TRAP-TYPE
    ENTERPRISE   lancity
    VARIABLES    {docsDevEvText}
    DESCRIPTION
        "	Testing error handling"
    ::= 202

lcErrAssert TRAP-TYPE
    ENTERPRISE   lancity
    VARIABLES    {docsDevEvText}
    DESCRIPTION
        "	Assertion failed"
    ::= 203

lcErrShutdown TRAP-TYPE
    ENTERPRISE   lancity
    VARIABLES    {docsDevEvText}
    DESCRIPTION
        "	Shutdown initiated"
    ::= 204

lcErrFshReset TRAP-TYPE
    ENTERPRISE   lancity
    VARIABLES    {docsDevEvText}
    DESCRIPTION
        "	Event log was cleared."
    ::= 205

lcErrRptReset TRAP-TYPE
    ENTERPRISE   lancity
    VARIABLES    {docsDevEvText}
    DESCRIPTION
        "	Event reporting set to default values."
    ::= 206

lcErrSystemError2 TRAP-TYPE
    ENTERPRISE   lancity
    VARIABLES    {docsDevEvText}
    DESCRIPTION
        "	System error, some sort of exception, further details
	for the 4700 processor, specifically the ErrorEPC and
	CacheError registers."
    ::= 207

lcErrWatchdogReset TRAP-TYPE
    ENTERPRISE   lancity
    VARIABLES    {docsDevEvText}
    DESCRIPTION
        "	The system was reset because the watchdog timer fired.
	This means the software was not operating normally, in
	that the watchdog timer should be periodically cleared
	to prevent this reset from occurring."
    ::= 208

lcMsgBacktrace TRAP-TYPE
    ENTERPRISE   lancity
    VARIABLES    {docsDevEvText}
    DESCRIPTION
        "	Info about a system error: calling stack display, helpful
	for problem analysis."
    ::= 209

lcMsgBacktraceEnded TRAP-TYPE
    ENTERPRISE   lancity
    VARIABLES    {docsDevEvText}
    DESCRIPTION
        "	Info about a system error: calling stack display reached the
	top and further info is displayed as to whether this was a normal or
	unexpected termination."
    ::= 210

lcMsgBacktrace2 TRAP-TYPE
    ENTERPRISE   lancity
    VARIABLES    {docsDevEvText}
    DESCRIPTION
        "	Info about a system error: called routine arguments display,
	helpful for problem analysis."
    ::= 211

lcMsgDSMakeHistoryEntry TRAP-TYPE
    ENTERPRISE   lancity
    VARIABLES    {docsDevEvText}
    DESCRIPTION
        "	Nuke history trace."
    ::= 212

lcMsgPowerSwitchCrash TRAP-TYPE
    ENTERPRISE   lancity
    VARIABLES    {docsDevEvText}
    DESCRIPTION
        "
	helpful for problem analysis."
    ::= 213

lcMsgNullEvent TRAP-TYPE
    ENTERPRISE   lancity
    VARIABLES    {docsDevEvText}
    DESCRIPTION
        "
	helpful for problem analysis."
    ::= 214

lcErrRegMemory TRAP-TYPE
    ENTERPRISE   lancity
    VARIABLES    {docsDevEvText}
    DESCRIPTION
        "	Unable to allocate memory for initial ranging"
    ::= 300

lcErrRegRestartRegistration TRAP-TYPE
    ENTERPRISE   lancity
    VARIABLES    {docsDevEvText}
    DESCRIPTION
        "	Re-starting registration for modem"
    ::= 301

lcErrRegNoInitSid TRAP-TYPE
    ENTERPRISE   lancity
    VARIABLES    {docsDevEvText}
    DESCRIPTION
        "	Unable to allocate initial service ID for modem"
    ::= 302

lcErrRegRangingFailed TRAP-TYPE
    ENTERPRISE   lancity
    VARIABLES    {docsDevEvText}
    DESCRIPTION
        "	Ranging retries exceeded for modem"
    ::= 303

lcErrRegInvalidRanging TRAP-TYPE
    ENTERPRISE   lancity
    VARIABLES    {docsDevEvText}
    DESCRIPTION
        "	Invalid ranging request received from modem"
    ::= 304

lcErrRegRangingTimeout TRAP-TYPE
    ENTERPRISE   lancity
    VARIABLES    {docsDevEvText}
    DESCRIPTION
        "	Ranging timed out for modem"
    ::= 305

lcErrRegInvalidRegistration TRAP-TYPE
    ENTERPRISE   lancity
    VARIABLES    {docsDevEvText}
    DESCRIPTION
        "	Invalid registration request received from modem"
    ::= 306

lcErrRegNoModemIp TRAP-TYPE
    ENTERPRISE   lancity
    VARIABLES    {docsDevEvText}
    DESCRIPTION
        "       Registration request from modem did not have Modem
         IP Address TLV (12)."
    ::= 307

lcErrRegNoIpAtAll TRAP-TYPE
    ENTERPRISE   lancity
    VARIABLES    {docsDevEvText}
    DESCRIPTION
        "       Registration request from modem did not have Modem
        IP Address TLV (12) or TFTP Server Provisioned Modem Address
        (20) so IP address 0.0.0.0 was assigned."
    ::= 308

lcErrRegUnpackingFail TRAP-TYPE
    ENTERPRISE   lancity
    VARIABLES    {docsDevEvText}
    DESCRIPTION
        "       Unable to unpack the TLV data in the registration request received from modem"
    ::= 309

lcErrRegRegisteredAlready TRAP-TYPE
    ENTERPRISE   lancity
    VARIABLES    {docsDevEvText}
    DESCRIPTION
        "       Modem is already registered as another SID"
    ::= 310

lcErrRegValidationFail TRAP-TYPE
    ENTERPRISE   lancity
    VARIABLES    {docsDevEvText}
    DESCRIPTION
        "       Registration request data in error, failed validation test."
    ::= 311

lcErrRegNoRegSid TRAP-TYPE
    ENTERPRISE   lancity
    VARIABLES    {docsDevEvText}
    DESCRIPTION
        "       Registration request failed because no SID was available."
    ::= 312

lcErrCmctrlGenericEmergency TRAP-TYPE
    ENTERPRISE   lancity
    VARIABLES    {docsDevEvText}
    DESCRIPTION
        "	Control Task fatal error is reported "
    ::= 400

lcErrCmctrlGenericDebug TRAP-TYPE
    ENTERPRISE   lancity
    VARIABLES    {docsDevEvText}
    DESCRIPTION
        "	Control Task fatal error is reported "
    ::= 401

lcErrCmctrlUccNotSupported TRAP-TYPE
    ENTERPRISE   lancity
    VARIABLES    {docsDevEvText}
    DESCRIPTION
        "	Upstream Change Channel not currently supported."
    ::= 402

lcErrCtInvalidEvent TRAP-TYPE
    ENTERPRISE   lancity
    VARIABLES    {docsDevEvText}
    DESCRIPTION
        "	Invalid ITM type received."
    ::= 403

lcErrLossOfSynch TRAP-TYPE
    ENTERPRISE   lancity
    VARIABLES    {docsDevEvText}
    DESCRIPTION
        "	Synchronization Lost."
    ::= 404

lcErrAcquiredSynch TRAP-TYPE
    ENTERPRISE   lancity
    VARIABLES    {docsDevEvText}
    DESCRIPTION
        "	Synchronization acquired on frequency."
    ::= 405

lcErrCmctrlUcdComplete TRAP-TYPE
    ENTERPRISE   lancity
    VARIABLES    {docsDevEvText}
    DESCRIPTION
        "	UCD Complete."
    ::= 406

lcErrCmctrlUccRx TRAP-TYPE
    ENTERPRISE   lancity
    VARIABLES    {docsDevEvText}
    DESCRIPTION
        "	UCC received for channel."
    ::= 407

lcErrRescan TRAP-TYPE
    ENTERPRISE   lancity
    VARIABLES    {docsDevEvText}
    DESCRIPTION
        "	Rescan cause."
    ::= 408

lcErrLostPulse TRAP-TYPE
    ENTERPRISE   lancity
    VARIABLES    {docsDevEvText}
    DESCRIPTION
        "	Lost Pulse."
    ::= 409

lcErrLostSynch TRAP-TYPE
    ENTERPRISE   lancity
    VARIABLES    {docsDevEvText}
    DESCRIPTION
        "	Lost Synch."
    ::= 410

lcErrIrqPhy1 TRAP-TYPE
    ENTERPRISE   lancity
    VARIABLES    {docsDevEvText}
    DESCRIPTION
        "	FEC Lost Lock."
    ::= 411

lcErrIrqPhy2 TRAP-TYPE
    ENTERPRISE   lancity
    VARIABLES    {docsDevEvText}
    DESCRIPTION
        "	Phy2 IRQ."
    ::= 412

lcErrCtRangeAbort TRAP-TYPE
    ENTERPRISE   lancity
    VARIABLES    {docsDevEvText}
    DESCRIPTION
        "	Ranging aborted by CMTS "
    ::= 413

lcErrCtTxAdjustments TRAP-TYPE
    ENTERPRISE   lancity
    VARIABLES    {docsDevEvText}
    DESCRIPTION
        "	TX adjusted by CMTS "
    ::= 414

lcErrCtRangingComplete TRAP-TYPE
    ENTERPRISE   lancity
    VARIABLES    {docsDevEvText}
    DESCRIPTION
        "	Ranging Complete "
    ::= 415

lcErrUnexpectedBpdu TRAP-TYPE
    ENTERPRISE   lancity
    VARIABLES    {docsDevEvText}
    DESCRIPTION
        "	Unexpected spanning tree packet format received"
    ::= 500

lcErrAllocatorInternal TRAP-TYPE
    ENTERPRISE   lancity
    VARIABLES    {docsDevEvText}
    DESCRIPTION
        "	Internal inconsistency in Upstream Scheduler due to CMTS malfunction. Contact Customer Support."
    ::= 600

lcErrAllocatorResource TRAP-TYPE
    ENTERPRISE   lancity
    VARIABLES    {docsDevEvText}
    DESCRIPTION
        "	Downstream transmitter hang reported by scheduler. CMTS is reset to clear transmittter problem. If this happens repeatedly, contact Customer Support."
    ::= 601

lcErrHedpBufCountError TRAP-TYPE
    ENTERPRISE   lancity
    VARIABLES    {docsDevEvText}
    DESCRIPTION
        "	Initialization Mismatched Buffer Counts"
    ::= 700

lcErrHedpIpSecurityAlarm TRAP-TYPE
    ENTERPRISE   lancity
    VARIABLES    {docsDevEvText}
    DESCRIPTION
        "	IP Address moved from MAC addresss ... to MAC address ...."
    ::= 701

lcErrHedpMacSecurityAlarm TRAP-TYPE
    ENTERPRISE   lancity
    VARIABLES    {docsDevEvText}
    DESCRIPTION
        "	MAC Address moved from port & said to port & said"
    ::= 702

lcErrHedpHashResources TRAP-TYPE
    ENTERPRISE   lancity
    VARIABLES    {docsDevEvText}
    DESCRIPTION
        "	Address Hash Table resource exhausted"
    ::= 703

lcErrHedpHashLookup TRAP-TYPE
    ENTERPRISE   lancity
    VARIABLES    {docsDevEvText}
    DESCRIPTION
        "	Address Hash Table lookup failed"
    ::= 704

lcErrHedpInvalidMacFrame TRAP-TYPE
    ENTERPRISE   lancity
    VARIABLES    {docsDevEvText}
    DESCRIPTION
        "	Data Path received an Invalid MAC Header"
    ::= 705

lcErrHedpNonsupportedEhdr TRAP-TYPE
    ENTERPRISE   lancity
    VARIABLES    {docsDevEvText}
    DESCRIPTION
        "	Data Path received Extended Header that is not supported"
    ::= 706

lcErrHedpInvalidEhdr TRAP-TYPE
    ENTERPRISE   lancity
    VARIABLES    {docsDevEvText}
    DESCRIPTION
        "	Data Path received invalid or note supported Extended Header"
    ::= 707

lcErrHedpLookupFailed TRAP-TYPE
    ENTERPRISE   lancity
    VARIABLES    {docsDevEvText}
    DESCRIPTION
        "MAC Address was not found when DP was informed of CM's registration/inoperability"
    ::= 708

lcErrHedpMtdDebug TRAP-TYPE
    ENTERPRISE   lancity
    VARIABLES    {docsDevEvText}
    DESCRIPTION
        "DP MTD found null buffer address in enet_tx_desc_get or mac_tx_desc_get"
    ::= 709

lcErrHedpInvalidEhdr28 TRAP-TYPE
    ENTERPRISE   lancity
    VARIABLES    {docsDevEvText}
    DESCRIPTION
        "	Data Path received invalid Extended Header"
    ::= 710

lcErrHedpInvalidEhdr56 TRAP-TYPE
    ENTERPRISE   lancity
    VARIABLES    {docsDevEvText}
    DESCRIPTION
        "	Data Path received invalid Extended Header"
    ::= 711

lcErrHedpInvalidEhdr84 TRAP-TYPE
    ENTERPRISE   lancity
    VARIABLES    {docsDevEvText}
    DESCRIPTION
        "	Data Path received invalid Extended Header"
    ::= 712

lcErrHedpInvalidEhdr112 TRAP-TYPE
    ENTERPRISE   lancity
    VARIABLES    {docsDevEvText}
    DESCRIPTION
        "	Data Path received invalid Extended Header"
    ::= 713

lcErrHedpMtdOccurred TRAP-TYPE
    ENTERPRISE   lancity
    VARIABLES    {docsDevEvText}
    DESCRIPTION
        "DP MTD occurred debug message"
    ::= 714

lcErrHedpMtdOccurred2 TRAP-TYPE
    ENTERPRISE   lancity
    VARIABLES    {docsDevEvText}
    DESCRIPTION
        "DP MTD occurred debug message#2"
    ::= 715

lcErrHedpMtdOccurred3 TRAP-TYPE
    ENTERPRISE   lancity
    VARIABLES    {docsDevEvText}
    DESCRIPTION
        "DP MTD occurred debug message#3"
    ::= 716

lcErrHedpDhcpTrace TRAP-TYPE
    ENTERPRISE   lancity
    VARIABLES    {docsDevEvText}
    DESCRIPTION
        "DP DHCP Trace encountered error: invalid ethernet length "
    ::= 717

lcErrHedpDescNotSupported TRAP-TYPE
    ENTERPRISE   lancity
    VARIABLES    {docsDevEvText}
    DESCRIPTION
        "CATV/Ethernet Rx descriptor received with FIRST + LAST not set "
    ::= 718

lcErrHedpRxTooLong TRAP-TYPE
    ENTERPRISE   lancity
    VARIABLES    {docsDevEvText}
    DESCRIPTION
        "CATV/Ethernet Rx descriptor received with FIRST + LAST not set "
    ::= 719

lcErrHedpDump1 TRAP-TYPE
    ENTERPRISE   lancity
    VARIABLES    {docsDevEvText}
    DESCRIPTION
        "	dump data "
    ::= 720

lcErrHedpDump2 TRAP-TYPE
    ENTERPRISE   lancity
    VARIABLES    {docsDevEvText}
    DESCRIPTION
        "	dump data "
    ::= 721

lcErrSmGenericEmergency TRAP-TYPE
    ENTERPRISE   lancity
    VARIABLES    {docsDevEvText}
    DESCRIPTION
        "	System Manager fatal error is reported. Contact Customer Support. "
    ::= 800

lcErrSmGenericDebug TRAP-TYPE
    ENTERPRISE   lancity
    VARIABLES    {docsDevEvText}
    DESCRIPTION
        "	System Manager debug information is reported "
    ::= 801

lcErrSmMallocFailure TRAP-TYPE
    ENTERPRISE   lancity
    VARIABLES    {docsDevEvText}
    DESCRIPTION
        "	System Manager reports: SM_alloc() memory allocation failed"
    ::= 802

lcErrSmFreeFailure TRAP-TYPE
    ENTERPRISE   lancity
    VARIABLES    {docsDevEvText}
    DESCRIPTION
        "	System Manager reports: SM_free() memory release failed"
    ::= 803

lcErrSmRestart TRAP-TYPE
    ENTERPRISE   lancity
    VARIABLES    {docsDevEvText}
    DESCRIPTION
        "	System Manager reports: Restart"
    ::= 804

lcErrSmTempTooHigh TRAP-TYPE
    ENTERPRISE   lancity
    VARIABLES    {docsDevEvText}
    DESCRIPTION
        "	Device Temperature Exceeded Specified Temperature Threshold"
    ::= 805

lcErrSmProcSpeedNotice TRAP-TYPE
    ENTERPRISE   lancity
    VARIABLES    {docsDevEvText}
    DESCRIPTION
        "	CPU speed detected to be: %d
"
    ::= 806

lcSmProcNoTimeServerDhcp TRAP-TYPE
    ENTERPRISE   lancity
    VARIABLES    {docsDevEvText}
    DESCRIPTION
        "	Time server not specified in DHCP offer"
    ::= 807

lcSmProcTimeServerDhcp TRAP-TYPE
    ENTERPRISE   lancity
    VARIABLES    {docsDevEvText}
    DESCRIPTION
        "	Time server specified in DHCP offer"
    ::= 808

lcSmProcTimeServerContacted TRAP-TYPE
    ENTERPRISE   lancity
    VARIABLES    {docsDevEvText}
    DESCRIPTION
        "	Time server contacted"
    ::= 809

lcSmProcTimeServerNotContacted TRAP-TYPE
    ENTERPRISE   lancity
    VARIABLES    {docsDevEvText}
    DESCRIPTION
        "	Time server not contacted"
    ::= 810

lcErrSmBadTrapType TRAP-TYPE
    ENTERPRISE   lancity
    VARIABLES    {docsDevEvText}
    DESCRIPTION
        "	A trap was requested specifying an unknown trap type"
    ::= 811

lcErrSmBadTrapMsgCreation TRAP-TYPE
    ENTERPRISE   lancity
    VARIABLES    {docsDevEvText}
    DESCRIPTION
        "	Error creating trap packet for a particular trap type"
    ::= 812

lcErrSmMibPrvsnError TRAP-TYPE
    ENTERPRISE   lancity
    VARIABLES    {docsDevEvText}
    DESCRIPTION
        "	System Manager reports: Error processing a provisioned SNMP object"
    ::= 813

lcDhcpMissingBasic TRAP-TYPE
    ENTERPRISE   lancity
    VARIABLES    {docsDevEvText}
    DESCRIPTION
        "	A DHCP offer was received which is unacceptable because it
 	lacks either yiaddr, siaddr, or filename. The filename is always
 	needed at the CM; it appears at the CMTS only if TFTP provisioning
 	is required."
    ::= 814

lcDhcpMissingRequired TRAP-TYPE
    ENTERPRISE   lancity
    VARIABLES    {docsDevEvText}
    DESCRIPTION
        "	A DHCP offer was received which is unacceptable because it
 	lacks an option required by the device. The tag is from RFC2132."
    ::= 815

lcDhcpMissingRouter TRAP-TYPE
    ENTERPRISE   lancity
    VARIABLES    {docsDevEvText}
    DESCRIPTION
        "	A DHCP offer was received which lacks a gateway address."
    ::= 816

lcSmTimeserverIcmp TRAP-TYPE
    ENTERPRISE   lancity
    VARIABLES    {docsDevEvText}
    DESCRIPTION
        "	An ICMP message (probably destination unreachable) was
	received when attempting to query the time server."
    ::= 817

lcErrPrvsnGenericError TRAP-TYPE
    ENTERPRISE   lancity
    VARIABLES    {docsDevEvText}
    DESCRIPTION
        "	System Manager reports: Error processing a provisioned SNMP object"
    ::= 819

lcErrSmGenericInformation TRAP-TYPE
    ENTERPRISE   lancity
    VARIABLES    {docsDevEvText}
    DESCRIPTION
        "	System Manager reports information"
    ::= 820

lcErrSmTftpFileTooBig TRAP-TYPE
    ENTERPRISE   lancity
    VARIABLES    {docsDevEvText}
    DESCRIPTION
        "	TFTP get of Provisioning file failed because the file
	size received exceeds the receive buffer size"
    ::= 821

lcErrSmDhcpGotNak TRAP-TYPE
    ENTERPRISE   lancity
    VARIABLES    {docsDevEvText}
    DESCRIPTION
        "	DHCP received a NAK from the server and the
	offer is rejected"
    ::= 822

lcErrSmDhcpIncompleteOffer TRAP-TYPE
    ENTERPRISE   lancity
    VARIABLES    {docsDevEvText}
    DESCRIPTION
        "	The DHCP OFFER from the specified server
	does not have all required fields and is being 
	ignored.  A previous log entry will have the specific
        error describing which entry was missing."
    ::= 823

lcErrSmDhcpNoOffer TRAP-TYPE
    ENTERPRISE   lancity
    VARIABLES    {docsDevEvText}
    DESCRIPTION
        "	DHCP discover received no offers or
	offers that were silently ignored"
    ::= 824

lcErrSmDhcpSentDecline TRAP-TYPE
    ENTERPRISE   lancity
    VARIABLES    {docsDevEvText}
    DESCRIPTION
        "	DHCP offer declined because it contained
	an IP address that is in used by another station"
    ::= 825

lcErrSmBootpRelayCantWork TRAP-TYPE
    ENTERPRISE   lancity
    VARIABLES    {docsDevEvText}
    DESCRIPTION
        "	No IP address is assigned so BOOTP Relay
	functionality cannot work.  This means that
	CMs behind this CMTS will not register"
    ::= 826

lcErrSmBootpRelayNowWorks TRAP-TYPE
    ENTERPRISE   lancity
    VARIABLES    {docsDevEvText}
    DESCRIPTION
        "	IP address is assigned so BOOTP Relay
	functionality can now work"
    ::= 827

lcErrFiltGenericDebug TRAP-TYPE
    ENTERPRISE   lancity
    VARIABLES    {docsDevEvText}
    DESCRIPTION
        "	Filter Module reports debug information"
    ::= 1200

lcErrFiltInvalidFlashValue TRAP-TYPE
    ENTERPRISE   lancity
    VARIABLES    {docsDevEvText}
    DESCRIPTION
        "	Filter Module reports an invalid flash value was read"
    ::= 1201

lcErrFiltIpTblEntryNotActive TRAP-TYPE
    ENTERPRISE   lancity
    VARIABLES    {docsDevEvText}
    DESCRIPTION
        "	Error attempting to remove IP table entry which is not
         active"
    ::= 1202

lcErrFiltLlcTblEntryNotActive TRAP-TYPE
    ENTERPRISE   lancity
    VARIABLES    {docsDevEvText}
    DESCRIPTION
        "	Error attempting to remove LLC table entry which is not
         active"
    ::= 1203

lcErrFiltGenericInformation TRAP-TYPE
    ENTERPRISE   lancity
    VARIABLES    {docsDevEvText}
    DESCRIPTION
        "	Filter Module reports information"
    ::= 1204

lcErrSmSwUpgradeGenericNotice TRAP-TYPE
    ENTERPRISE   lancity
    VARIABLES    {docsDevEvText}
    DESCRIPTION
        "	Software upgrade reports information"
    ::= 1300

lcErrSmSwUpgradeFail TRAP-TYPE
    ENTERPRISE   lancity
    VARIABLES    {docsDevEvText}
    DESCRIPTION
        "	Software upgrade failure notice"
    ::= 1301

lcErrSmSwUpgradeFailReset TRAP-TYPE
    ENTERPRISE   lancity
    VARIABLES    {docsDevEvText}
    DESCRIPTION
        "	Software upgrade failure occured resulting in a reset"
    ::= 1302

lcErrSmSwUpgradeCompletion TRAP-TYPE
    ENTERPRISE   lancity
    VARIABLES    {docsDevEvText}
    DESCRIPTION
        "	Software Upgrade Succeeded"
    ::= 1303

lcErrSmSwUpgradeCancelled TRAP-TYPE
    ENTERPRISE   lancity
    VARIABLES    {docsDevEvText}
    DESCRIPTION
        "	Software upgrade was cancelled "
    ::= 1304

lcErrSmSwUpgradeOverride TRAP-TYPE
    ENTERPRISE   lancity
    VARIABLES    {docsDevEvText}
    DESCRIPTION
        "	Software Upgrade was cancelled by a new request"
    ::= 1305

lcErrSmFlashProgrammingError TRAP-TYPE
    ENTERPRISE   lancity
    VARIABLES    {docsDevEvText}
    DESCRIPTION
        "	Software upgrade flash programming failure"
    ::= 1306

lcErrSmFlashProgrammingErrorReset TRAP-TYPE
    ENTERPRISE   lancity
    VARIABLES    {docsDevEvText}
    DESCRIPTION
        "	Software upgrade flash programming failure resulting in a reset"
    ::= 1307

lcErrSmFlashEraseFail TRAP-TYPE
    ENTERPRISE   lancity
    VARIABLES    {docsDevEvText}
    DESCRIPTION
        "	Software upgrade flash erase failure"
    ::= 1308

lcErrSmFlashEraseFailReset TRAP-TYPE
    ENTERPRISE   lancity
    VARIABLES    {docsDevEvText}
    DESCRIPTION
        "	Software upgrade flash erase failure resulting in a reset"
    ::= 1309

lcErrSmFlashCorruptionReset TRAP-TYPE
    ENTERPRISE   lancity
    VARIABLES    {docsDevEvText}
    DESCRIPTION
        "	Software Upgrade: unknown flash id"
    ::= 1310

lcErrSmFlashBlockInvalidReset TRAP-TYPE
    ENTERPRISE   lancity
    VARIABLES    {docsDevEvText}
    DESCRIPTION
        "	Software Upgrade: invalid flash runtime info block"
    ::= 1311

lcErrSmSwUpgradeTftpError TRAP-TYPE
    ENTERPRISE   lancity
    VARIABLES    {docsDevEvText}
    DESCRIPTION
        "	Software upgrade failed, tftp error, upgrade is aborted"
    ::= 1312

lcErrSmSwUpgradeTftpErrorReset TRAP-TYPE
    ENTERPRISE   lancity
    VARIABLES    {docsDevEvText}
    DESCRIPTION
        "	Software upgrade failed due to a tftp error, system is
	reset to retry"
    ::= 1313

lcErrSmSwUpgradeAllocFail TRAP-TYPE
    ENTERPRISE   lancity
    VARIABLES    {docsDevEvText}
    DESCRIPTION
        "	Software upgrade NU_Alloc_Memory failure"
    ::= 1314

lcErrSmSwUpgradeGenericError TRAP-TYPE
    ENTERPRISE   lancity
    VARIABLES    {docsDevEvText}
    DESCRIPTION
        "	Software Upgrade error reported"
    ::= 1315

lcErrSmSwUpgradeProductError TRAP-TYPE
    ENTERPRISE   lancity
    VARIABLES    {docsDevEvText}
    DESCRIPTION
        "	Product code in software upgrade file is not correct
	for the system being upgraded"
    ::= 1316

lcErrSmSwUpgradeTftpMsg TRAP-TYPE
    ENTERPRISE   lancity
    VARIABLES    {docsDevEvText}
    DESCRIPTION
        "	There was a TFTP error during software upgrade.  Possible errors
         are that the upgrade file does not exist, or the docsDevSwServer
         address is not correct, or the transfer failed in the middle of
         the transfer."
    ::= 1317

lcErrScnBadFrequency TRAP-TYPE
    ENTERPRISE   lancity
    VARIABLES    {docsDevEvText}
    DESCRIPTION
        "	Directed by provisioning to unreachable downstream frequency"
    ::= 1400

lcScnTunerBroken TRAP-TYPE
    ENTERPRISE   lancity
    VARIABLES    {docsDevEvText}
    DESCRIPTION
        "	Tuner Failure"
    ::= 1401

lcScnTunerHung TRAP-TYPE
    ENTERPRISE   lancity
    VARIABLES    {docsDevEvText}
    DESCRIPTION
        "	Tuner is not responding"
    ::= 1402

lcScnStartUp TRAP-TYPE
    ENTERPRISE   lancity
    VARIABLES    {docsDevEvText}
    DESCRIPTION
        "	Begin Scanning"
    ::= 1403

lcErrCliGeneral TRAP-TYPE
    ENTERPRISE   lancity
    VARIABLES    {docsDevEvText}
    DESCRIPTION
        "	Console Interface failure"
    ::= 1500

lcInfoCliLogin TRAP-TYPE
    ENTERPRISE   lancity
    VARIABLES    {docsDevEvText}
    DESCRIPTION
        "	Console Interface user logged in"
    ::= 1501

lcInfoCliLogout TRAP-TYPE
    ENTERPRISE   lancity
    VARIABLES    {docsDevEvText}
    DESCRIPTION
        "	Console Interface user logged out"
    ::= 1502

lcInfoCliLoginFail TRAP-TYPE
    ENTERPRISE   lancity
    VARIABLES    {docsDevEvText}
    DESCRIPTION
        "	Console Interface user login fail"
    ::= 1503

lcInfoCliSessionTimeout TRAP-TYPE
    ENTERPRISE   lancity
    VARIABLES    {docsDevEvText}
    DESCRIPTION
        "	Console Interface user timed out"
    ::= 1504

lcInfoCliCommand TRAP-TYPE
    ENTERPRISE   lancity
    VARIABLES    {docsDevEvText}
    DESCRIPTION
        "	Console Interface command"
    ::= 1505

lcInfoCliConsoleSnmpSet TRAP-TYPE
    ENTERPRISE   lancity
    VARIABLES    {docsDevEvText}
    DESCRIPTION
        "	Console Interface user snmp set"
    ::= 1506

lcInfoCliTelnetSnmpSet TRAP-TYPE
    ENTERPRISE   lancity
    VARIABLES    {docsDevEvText}
    DESCRIPTION
        "	Telnet Interface user snmp set"
    ::= 1507

lcErrBcmInitFailure TRAP-TYPE
    ENTERPRISE   lancity
    VARIABLES    {docsDevEvText}
    DESCRIPTION
        "	Could not initialize network interface parts"
    ::= 1600

lcMsgNoPowerTables TRAP-TYPE
    ENTERPRISE   lancity
    VARIABLES    {docsDevEvText}
    DESCRIPTION
        "	Power/correction tables for the BCM3037 were not found in the
	manufacturing block as expected.  The power and correction were
	estimated instead."
    ::= 1601

lcErrBcmReceiverHwRev TRAP-TYPE
    ENTERPRISE   lancity
    VARIABLES    {docsDevEvText}
    DESCRIPTION
        "	The receiver has an improper hardware revision."
    ::= 1602

lcErrCmMtd TRAP-TYPE
    ENTERPRISE   lancity
    VARIABLES    {docsDevEvText}
    DESCRIPTION
        "	MAX Transit Delay on CATV"
    ::= 1700

lcErrCmPciParity TRAP-TYPE
    ENTERPRISE   lancity
    VARIABLES    {docsDevEvText}
    DESCRIPTION
        "	PCI Parity Error"
    ::= 1701

lcErrMibSnmpReset TRAP-TYPE
    ENTERPRISE   lancity
    VARIABLES    {docsDevEvText}
    DESCRIPTION
        "	System Reset by docsDevResetNow MIB variable"
    ::= 1800

lcErrGalPciParity TRAP-TYPE
    ENTERPRISE   lancity
    VARIABLES    {docsDevEvText}
    DESCRIPTION
        "	PCI parity error detected"
    ::= 1900

lcErrBpEnabled TRAP-TYPE
    ENTERPRISE   lancity
    VARIABLES    {docsDevEvText}
    DESCRIPTION
        "	Baseline Privacy configuration settings are present."
    ::= 2000

lcErrBpHardwareInitFailure TRAP-TYPE
    ENTERPRISE   lancity
    VARIABLES    {docsDevEvText}
    DESCRIPTION
        "	Failure initializing hardware."
    ::= 2001

lcErrBpKeyWriteFailure TRAP-TYPE
    ENTERPRISE   lancity
    VARIABLES    {docsDevEvText}
    DESCRIPTION
        "	Failure writing traffic key to hardware."
    ::= 2002

lcErrBpVectWriteFailure TRAP-TYPE
    ENTERPRISE   lancity
    VARIABLES    {docsDevEvText}
    DESCRIPTION
        "	Failure writing initialization vector to hardware."
    ::= 2003

lcErrBpHardcodedRsaKeyPair TRAP-TYPE
    ENTERPRISE   lancity
    VARIABLES    {docsDevEvText}
    DESCRIPTION
        "	Using hardcoded RSA key pair since flash key invalid."
    ::= 2004

lcErrHebpAuthEncryptFailure TRAP-TYPE
    ENTERPRISE   lancity
    VARIABLES    {docsDevEvText}
    DESCRIPTION
        "	Failure encrypting authorization key."
    ::= 2100

lcErrHebpHardwareInitFailure TRAP-TYPE
    ENTERPRISE   lancity
    VARIABLES    {docsDevEvText}
    DESCRIPTION
        "	Failure initializing hardware."
    ::= 2101

lcErrHebpKeyWriteFailure TRAP-TYPE
    ENTERPRISE   lancity
    VARIABLES    {docsDevEvText}
    DESCRIPTION
        "	Failure writing traffic key to hardware."
    ::= 2102

lcErrHebpVectWriteFailure TRAP-TYPE
    ENTERPRISE   lancity
    VARIABLES    {docsDevEvText}
    DESCRIPTION
        "	Failure writing initialization vector to hardware."
    ::= 2103

lcErrHebpMacsDontMatch TRAP-TYPE
    ENTERPRISE   lancity
    VARIABLES    {docsDevEvText}
    DESCRIPTION
        "	The Source MAC Address of a BP Key Management message
	is not equivalent to the MAC Address passed in the message's
	CM identification field."
    ::= 2104

lcErrHebpAttemptedPubKeyChange TRAP-TYPE
    ENTERPRISE   lancity
    VARIABLES    {docsDevEvText}
    DESCRIPTION
        "	A CM has made a BP Authorization Request but a CM with the
	same MAC address, and different public key, is already authorized."
    ::= 2105

lcErrCruInitFailure TRAP-TYPE
    ENTERPRISE   lancity
    VARIABLES    {docsDevEvText}
    DESCRIPTION
        "	The CMTS hardware could not be initialized due to an FPGA
	programming failure."
    ::= 2200

lcErrMfgTlvReadError TRAP-TYPE
    ENTERPRISE   lancity
    VARIABLES    {docsDevEvText}
    DESCRIPTION
        "	Error reading TLV type from flash."
    ::= 2300

lcErrUcNoHw TRAP-TYPE
    ENTERPRISE   lancity
    VARIABLES    {docsDevEvText}
    DESCRIPTION
        "	The CMTS hardware could not be initialized because the
        up-converter was not detected."
    ::= 2400

lcErrUcNoCal TRAP-TYPE
    ENTERPRISE   lancity
    VARIABLES    {docsDevEvText}
    DESCRIPTION
        "	The CMTS hardware could not be initialized because the
        up-converter calibration data could not be found."
    ::= 2401

lcErrUcNoLock TRAP-TYPE
    ENTERPRISE   lancity
    VARIABLES    {docsDevEvText}
    DESCRIPTION
        "	The CMTS hardware could not lock onto the downstream
	frequency."
    ::= 2402

lcErrUcPowerSupply TRAP-TYPE
    ENTERPRISE   lancity
    VARIABLES    {docsDevEvText}
    DESCRIPTION
        "	The CMTS up-converter power supply failed"
    ::= 2403

lcErrUcOutputPower TRAP-TYPE
    ENTERPRISE   lancity
    VARIABLES    {docsDevEvText}
    DESCRIPTION
        "	The CMTS downstream output power could not reach the desired
	level"
    ::= 2404

lcErrPacDsConfigFailure TRAP-TYPE
    ENTERPRISE   lancity
    VARIABLES    {docsDevEvText}
    DESCRIPTION
        "The downstream channel configuration is incompatible with the CMTS hardware; the downstream channel is disabled"
    ::= 2500

lcErrPacUsConfigFailure TRAP-TYPE
    ENTERPRISE   lancity
    VARIABLES    {docsDevEvText}
    DESCRIPTION
        "The upstream channel configuration is incompatible with the CMTS hardware; the upstream channel is disabled"
    ::= 2501

lcPacDsCenterFreqChange TRAP-TYPE
    ENTERPRISE   lancity
    VARIABLES    {docsDevEvText}
    DESCRIPTION
        "Downstream Center Frequency has been changed"
    ::= 2502

lcPacDsBandwidthChange TRAP-TYPE
    ENTERPRISE   lancity
    VARIABLES    {docsDevEvText}
    DESCRIPTION
        "Downstream Channel Width has been changed"
    ::= 2503

lcPacDsModulationChange TRAP-TYPE
    ENTERPRISE   lancity
    VARIABLES    {docsDevEvText}
    DESCRIPTION
        "Downstream Modulation Type has been changed"
    ::= 2504

lcPacDsInterleaveChange TRAP-TYPE
    ENTERPRISE   lancity
    VARIABLES    {docsDevEvText}
    DESCRIPTION
        "Downstream Interleave has been changed"
    ::= 2505

lcPacDsPowerChange TRAP-TYPE
    ENTERPRISE   lancity
    VARIABLES    {docsDevEvText}
    DESCRIPTION
        "Downstream Channel Power has been changed"
    ::= 2506

lcErrTestMacHeader TRAP-TYPE
    ENTERPRISE   lancity
    VARIABLES    {docsDevEvText}
    DESCRIPTION
        "Test being run - MAC Header"
    ::= 2600

lcErrTestEhdr20 TRAP-TYPE
    ENTERPRISE   lancity
    VARIABLES    {docsDevEvText}
    DESCRIPTION
        "Test being run - Extended Header"
    ::= 2601

lcIngressAvoidanceActionTaken TRAP-TYPE
    ENTERPRISE   lancity
    VARIABLES    {docsDevEvText}
    DESCRIPTION
        "The ingress avoidance feature has automatically changed frequency, modulation profile and bandwidth"
    ::= 2700

lcErrCruFrontFanStatusOff TRAP-TYPE
    ENTERPRISE   lancity
    VARIABLES    {docsDevEvText}
    DESCRIPTION
        "       Front fan is not functioning properly or is powered down."
    ::= 2800

lcErrCruFrontFanStatusOn TRAP-TYPE
    ENTERPRISE   lancity
    VARIABLES    {docsDevEvText}
    DESCRIPTION
        "       Front fan is now functioning properly."
    ::= 2801

lcErrCruMiddleFanStatusOff TRAP-TYPE
    ENTERPRISE   lancity
    VARIABLES    {docsDevEvText}
    DESCRIPTION
        "       Middle fan is not functioning properly or is powered down."
    ::= 2802

lcErrCruMiddleFanStatusOn TRAP-TYPE
    ENTERPRISE   lancity
    VARIABLES    {docsDevEvText}
    DESCRIPTION
        "       Middle fan is now functioning properly."
    ::= 2803

lcErrCruBackFanStatusOff TRAP-TYPE
    ENTERPRISE   lancity
    VARIABLES    {docsDevEvText}
    DESCRIPTION
        "       Back fan is not functioning properly or is powered down."
    ::= 2804

lcErrCruBackFanStatusOn TRAP-TYPE
    ENTERPRISE   lancity
    VARIABLES    {docsDevEvText}
    DESCRIPTION
        "       Back fan is now functioning properly."
    ::= 2805

lcErrTelnetMallocFailure TRAP-TYPE
    ENTERPRISE   lancity
    VARIABLES    {docsDevEvText}
    DESCRIPTION
        "	Telnet reports: TELNET_malloc() memory allocation failed"
    ::= 3000

lcErrTelnetFreeFailure TRAP-TYPE
    ENTERPRISE   lancity
    VARIABLES    {docsDevEvText}
    DESCRIPTION
        "	Telnet reports: TELNET_free() memory release failed"
    ::= 3001

lcErrTelnetTcbCreateFailure TRAP-TYPE
    ENTERPRISE   lancity
    VARIABLES    {docsDevEvText}
    DESCRIPTION
        "	Telnet reports: TELNET_Init() tcb_create() failed"
    ::= 3002

lcErrTelnetTnCreateListenerFailure TRAP-TYPE
    ENTERPRISE   lancity
    VARIABLES    {docsDevEvText}
    DESCRIPTION
        "	Telnet reports: TELNET_Init() tn_create_listener() failed"
    ::= 3003

lcErrTelnetTcpStartFailure TRAP-TYPE
    ENTERPRISE   lancity
    VARIABLES    {docsDevEvText}
    DESCRIPTION
        "	Telnet reports: TELNET_Init() tcp_start() failed"
    ::= 3004


END
