--			Ascend mibbill MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBBILL-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibbillingProfile  OBJECT IDENTIFIER ::= { configuration 61}

	-- The mibbillingProfile table
	--
	-- This table contains parameters for the mibbillingProfile profile
	--

    mibbillingProfileTable	OBJECT-TYPE
	SYNTAX		SEQUENCE OF MibbillingProfileEntry
	ACCESS		not-accessible
	STATUS		mandatory
	DESCRIPTION	"A list of mibbillingProfile profile entries."
	::= { mibbillingProfile 1 }

    mibbillingProfileEntry	OBJECT-TYPE
	SYNTAX		MibbillingProfileEntry
	ACCESS		not-accessible
	STATUS		mandatory
	DESCRIPTION	"A mibbillingProfile entry containing objects that
			 maps to the parameters of mibbillingProfile profile."
	INDEX		{ billingProfile-Index-o }
	::= { mibbillingProfileTable 1 }

    MibbillingProfileEntry ::=
	SEQUENCE {
	    billingProfile-Index-o
		INTEGER,
	    billingProfile-SystemDs0Minutes
		INTEGER,
	    billingProfile-Action-o
		INTEGER
	}

    billingProfile-Index-o	OBJECT-TYPE
	SYNTAX	INTEGER
	ACCESS	read-only
	STATUS	mandatory
	DESCRIPTION	""
	::= { mibbillingProfileEntry 1 }

    billingProfile-SystemDs0Minutes	OBJECT-TYPE
	SYNTAX	INTEGER
	ACCESS	read-write
	STATUS	mandatory
	DESCRIPTION	"This counts the number of DS0 minutes which the system has billed for all ports."
	::= { mibbillingProfileEntry 2 }

    billingProfile-Action-o	OBJECT-TYPE
	SYNTAX	INTEGER {
		    noAction (1),
		    createProfile (2),
		    deleteProfile (3)
		}
	ACCESS	read-write
	STATUS	mandatory
	DESCRIPTION	""
	::= { mibbillingProfileEntry 3 }


	-- The mibbillingProfile__port_ds0_minutes table
	--
	-- This table contains parameters for the mibbillingProfile__port_ds0_minutes profile
	--

    mibbillingProfile-PortDs0MinutesTable	OBJECT-TYPE
	SYNTAX		SEQUENCE OF MibbillingProfile-PortDs0MinutesEntry
	ACCESS		not-accessible
	STATUS		mandatory
	DESCRIPTION	"A list of mibbillingProfile__port_ds0_minutes profile entries."
	::= { mibbillingProfile 2 }

    mibbillingProfile-PortDs0MinutesEntry	OBJECT-TYPE
	SYNTAX		MibbillingProfile-PortDs0MinutesEntry
	ACCESS		not-accessible
	STATUS		mandatory
	DESCRIPTION	"A mibbillingProfile__port_ds0_minutes entry containing objects that
			 maps to the parameters of mibbillingProfile__port_ds0_minutes profile."
	INDEX		{ billingProfile-PortDs0Minutes-Index-o, billingProfile-PortDs0Minutes-Index1-o }
	::= { mibbillingProfile-PortDs0MinutesTable 1 }

    MibbillingProfile-PortDs0MinutesEntry ::=
	SEQUENCE {
	    billingProfile-PortDs0Minutes-Index-o
		INTEGER,
	    billingProfile-PortDs0Minutes-Index1-o
		INTEGER,
	    billingProfile-PortDs0Minutes
		INTEGER
	}

    billingProfile-PortDs0Minutes-Index-o	OBJECT-TYPE
	SYNTAX	INTEGER
	ACCESS	read-only
	STATUS	mandatory
	DESCRIPTION	""
	::= { mibbillingProfile-PortDs0MinutesEntry 1 }

    billingProfile-PortDs0Minutes-Index1-o	OBJECT-TYPE
	SYNTAX	INTEGER
	ACCESS	read-only
	STATUS	mandatory
	DESCRIPTION	""
	::= { mibbillingProfile-PortDs0MinutesEntry 2 }

    billingProfile-PortDs0Minutes	OBJECT-TYPE
	SYNTAX	INTEGER
	ACCESS	read-write
	STATUS	mandatory
	DESCRIPTION	"Counts each of the ports DS0 minutes."
	::= { mibbillingProfile-PortDs0MinutesEntry 3 }

END
