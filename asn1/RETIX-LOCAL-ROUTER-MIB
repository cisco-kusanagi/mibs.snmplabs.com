-- 
-- Copyright 1993 Retix, The OpenNetworking Company.
--
-- Retix Local Bridge/Router MIB ( produt name Retix 4760 )
-- Version 1.0  
--
-- Date : 12 Jan 1993
--
-- RETIX
-- 2401 Colorado Ave,
-- Santa Monica,
-- CA 90404, USA
--


	RETIX-LOCAL-ROUTER-MIB { iso org(3) dod(6) internet(1) mgmt(2) 1 }

	DEFINITIONS ::= BEGIN

	IMPORTS
	mgmt, OBJECT-TYPE, NetworkAddress, IpAddress,
	Counter, Gauge, TimeTicks
	FROM RFC1065-SMI;
	mib     OBJECT IDENTIFIER ::= { mgmt 1 }

	private    	OBJECT IDENTIFIER ::= { internet 4 }
	enterprises   	OBJECT IDENTIFIER ::= { private 1 }
	system     	OBJECT IDENTIFIER ::= { mib 1 }
	interfaces     	OBJECT IDENTIFIER ::= { mib 2 }
	at     		OBJECT IDENTIFIER ::= { mib 3 }
	ip     		OBJECT IDENTIFIER ::= { mib 4 }
	icmp     	OBJECT IDENTIFIER ::= { mib 5 }
	tcp     	OBJECT IDENTIFIER ::= { mib 6 }
	udp     	OBJECT IDENTIFIER ::= { mib 7 }



	-- Retix Specific Groups

	
	retix               OBJECT IDENTIFIER ::= {enterprises 72 } 

	product             OBJECT IDENTIFIER ::= {retix 8 } 
	rtxlocal          OBJECT IDENTIFIER ::= {retix 9 } 


	s3agentSW          OBJECT IDENTIFIER ::= {rtxlocal 1} 
	s3agentHW          OBJECT IDENTIFIER ::= {rtxlocal 2}
	s3agentIpProtocol  OBJECT IDENTIFIER ::= {rtxlocal 3}
	s3snmpAgent        OBJECT IDENTIFIER ::= {rtxlocal 4}
	brdgcommon      OBJECT IDENTIFIER ::= {rtxlocal 5}
	locbrdg          OBJECT IDENTIFIER ::= {rtxlocal 6}
	ieee8023          OBJECT IDENTIFIER ::= {rtxlocal 7}
	locrouter          OBJECT IDENTIFIER ::= {rtxlocal 8}

	p2265m             OBJECT IDENTIFIER ::= {product 3 } 
	p4660              OBJECT IDENTIFIER ::= {product 4 } 
	p4760              OBJECT IDENTIFIER ::= {product 8 } 



	-- the System group

	sysDescr OBJECT-TYPE
		SYNTAX  OCTET STRING
		ACCESS  read-only
		STATUS  mandatory
		DESCRIPTION  ""
		::= { system 1 }

	sysObjectID OBJECT-TYPE
		SYNTAX  OBJECT IDENTIFIER
		ACCESS  read-only
		STATUS  mandatory
		DESCRIPTION  ""
		::= { system 2 }

	sysUpTime OBJECT-TYPE
		SYNTAX  TimeTicks
		ACCESS  read-only
		STATUS  mandatory
		DESCRIPTION  ""
		::= { system 3 }

--
--	Interfaces group elements
--

	ifNumber OBJECT-TYPE
		SYNTAX  INTEGER
		ACCESS  read-only
		STATUS  mandatory
		DESCRIPTION  ""
		::= { interfaces 1 }

	-- the Interfaces table

	ifTable OBJECT-TYPE
		SYNTAX  SEQUENCE OF IfEntry
		ACCESS  not-accessible
		STATUS  mandatory
		DESCRIPTION  ""
		::= { interfaces 2 }

	ifEntry OBJECT-TYPE
		SYNTAX  IfEntry
		ACCESS  not-accessible
		STATUS  mandatory
		DESCRIPTION  ""
		INDEX { ifIndex }
		::= { ifTable 1 }

	IfEntry ::= SEQUENCE {
		ifIndex
			INTEGER,
		ifDescr
			OCTET STRING,
		ifType
			INTEGER,
		ifMtu
			INTEGER,
		ifSpeed
			Gauge,
		ifPhysAddress
			OCTET STRING,
		ifAdminStatus
			INTEGER,
		ifOperStatus
			INTEGER,
		ifLastChange
			TimeTicks,
		ifInOctets
			Counter,
		ifInUcastPkts
			Counter,
		ifInNUcastPkts
			Counter,
		ifInDiscards
			Counter,
		ifInErrors
			Counter,
		ifInUnknownProtos
			Counter,
		ifOutOctets
			Counter,
		ifOutUcastPkts
			Counter,
		ifOutNUcastPkts
			Counter,
		ifOutDiscards
			Counter,
		ifOutErrors
			Counter,
		ifOutQLen
			Gauge
		}

	ifIndex OBJECT-TYPE
		SYNTAX  INTEGER
		ACCESS  read-only
		STATUS  mandatory
		DESCRIPTION  ""
		::= { ifEntry 1 }

	ifDescr OBJECT-TYPE
		SYNTAX  OCTET STRING
		ACCESS  read-only
		STATUS  mandatory
		DESCRIPTION  ""
		::= { ifEntry 2 }

	ifType OBJECT-TYPE
		SYNTAX  INTEGER {
			other(1),     -- none of the following
		regular1822(2),
		hdh1822(3),
		ddn-x25(4),
		rfc877-x25(5),
		ethernet-csmacd(6),
		iso88023-csmacd(7),
		iso88024-tokenBus(8),
		iso88025-tokenRing(9),
		iso88026-man(10),
		starLan(11),
		proteon-10MBit(12),
		proteon-80MBit(13),
		hyperchannel(14),
		fddi(15),
		lapb(16),
		sdlc(17),
		t1-carrier(18),
		cept(19),
		basicIsdn(20),
		primaryIsdn(21),
		proprietaryserial(22),
		propPointToPointSerial(23)
		}
		ACCESS  read-only
		STATUS  mandatory
		DESCRIPTION  ""
		::= { ifEntry 3 }

	ifMtu OBJECT-TYPE
		SYNTAX  INTEGER
		ACCESS  read-only
		STATUS  mandatory
		DESCRIPTION  ""
		::= { ifEntry 4 }

	ifSpeed OBJECT-TYPE
		SYNTAX  Gauge
		ACCESS  read-only
		STATUS  mandatory
		DESCRIPTION  ""
		::= { ifEntry 5 }

	ifPhysAddress OBJECT-TYPE
		SYNTAX  OCTET STRING
		ACCESS  read-only
		STATUS  mandatory
		DESCRIPTION  ""
		::= { ifEntry 6 }

	ifAdminStatus OBJECT-TYPE
		SYNTAX  INTEGER {
		up(1),        -- ready to pass packets
			down(2),
			testing(3)    -- in some test mode
			}
		ACCESS  read-write
		STATUS  mandatory
		DESCRIPTION  ""
		::= { ifEntry 7 }

	ifOperStatus OBJECT-TYPE
		SYNTAX  INTEGER {
			up(1),	-- ready to pass packets
			down(2),
			testing(3)    -- in some test mode
			}
		ACCESS  read-only
		STATUS  mandatory
		DESCRIPTION  ""
		::= { ifEntry 8 }

	ifLastChange OBJECT-TYPE
		SYNTAX  TimeTicks
		ACCESS  read-only
		STATUS  mandatory
		DESCRIPTION  ""
		::= { ifEntry 9 }

	ifInOctets OBJECT-TYPE
		SYNTAX  Counter
		ACCESS  read-only
		STATUS  mandatory
		DESCRIPTION  ""
		::= { ifEntry 10 }

	ifInUcastPkts OBJECT-TYPE
		SYNTAX  Counter
		ACCESS  read-only
		STATUS  mandatory
		DESCRIPTION  ""
		::=  { ifEntry 11 }

	ifInNUcastPkts OBJECT-TYPE
		SYNTAX  Counter
		ACCESS  read-only
		STATUS  mandatory
		DESCRIPTION  ""
		::= { ifEntry 12 }

	ifInDiscards OBJECT-TYPE
		SYNTAX  Counter
		ACCESS  read-only
		STATUS  mandatory
		DESCRIPTION  ""
		::= { ifEntry 13 }

	ifInErrors OBJECT-TYPE
		SYNTAX  Counter
		ACCESS  read-only
		STATUS  mandatory
		DESCRIPTION  ""
		::= { ifEntry 14 }

	ifInUnknownProtos OBJECT-TYPE
		SYNTAX  Counter
		ACCESS  read-only
		STATUS  mandatory
		DESCRIPTION  ""
		::= { ifEntry 15 }

	ifOutOctets OBJECT-TYPE
		SYNTAX  Counter
		ACCESS  read-only
		STATUS  mandatory
		DESCRIPTION  ""
		::= { ifEntry 16 }

	ifOutUcastPkts OBJECT-TYPE
		SYNTAX  Counter
		ACCESS  read-only
		STATUS  mandatory
		DESCRIPTION  ""
		::= { ifEntry 17 }

	ifOutNUcastPkts OBJECT-TYPE
		SYNTAX  Counter
		ACCESS  read-only
		STATUS  mandatory
		DESCRIPTION  ""
		::= { ifEntry 18 }

	ifOutDiscards OBJECT-TYPE
		SYNTAX  Counter
		ACCESS  read-only
		STATUS  mandatory
		DESCRIPTION  ""
		::= { ifEntry 19 }

	ifOutErrors OBJECT-TYPE
		SYNTAX  Counter
		ACCESS  read-only
		STATUS  mandatory
		DESCRIPTION  ""
		::= { ifEntry 20 }

	ifOutQLen OBJECT-TYPE
		SYNTAX  Gauge
		ACCESS  read-only
		STATUS  mandatory
		DESCRIPTION  ""
		::= { ifEntry 21 }

--
--	at group elements
--

--	atTable OBJECT IDENTIFIER ::= { at 1 }


	atTable OBJECT-TYPE
		SYNTAX  SEQUENCE OF AtEntry
		ACCESS  not-accessible
		STATUS  mandatory
		DESCRIPTION  ""
		::=  { at 1 }

	atEntry OBJECT-TYPE
		SYNTAX  AtEntry
		ACCESS  not-accessible
		STATUS  mandatory
		DESCRIPTION  ""
		::=  { atTable 1 }

	AtEntry ::= SEQUENCE {
		atIfIndex
			INTEGER,
		atPhysAddress
			OCTET STRING,
		atNetAddress
			IpAddress
		}

	atIfIndex OBJECT-TYPE
		SYNTAX  INTEGER
		ACCESS  read-write
		STATUS  mandatory
		DESCRIPTION  ""
		::=  { atEntry 1 }

	atPhysAddress OBJECT-TYPE
		SYNTAX  OCTET STRING
		ACCESS  read-write
		STATUS  mandatory
		DESCRIPTION  ""
		::=  { atEntry 2 }

	atNetAddress OBJECT-TYPE
		SYNTAX  IpAddress
		ACCESS  read-write
		STATUS  mandatory
		DESCRIPTION  ""
		::=  { atEntry 3 }

--
--	IP group elements
--

	ipForwarding OBJECT-TYPE
		SYNTAX  INTEGER
		ACCESS  read-only
		STATUS  mandatory
		DESCRIPTION  ""
		::=  { ip 1 }

	ipDefaultTTL OBJECT-TYPE
		SYNTAX  INTEGER
		ACCESS  read-write
		STATUS  mandatory
		DESCRIPTION  ""
		::=  { ip 2 }

	ipInReceives OBJECT-TYPE
		SYNTAX  Counter
		ACCESS  read-only
		STATUS  mandatory
		DESCRIPTION  ""
		::=  { ip 3 }

	ipInHdrErrors OBJECT-TYPE
		SYNTAX  Counter
		ACCESS  read-only
		STATUS  mandatory
		DESCRIPTION  ""
		::=  { ip 4 }

	ipInAddrErrors OBJECT-TYPE
		SYNTAX  Counter
		ACCESS  read-only
		STATUS  mandatory
		DESCRIPTION  ""
		::=  { ip 5 }

	ipForwDatagrams OBJECT-TYPE
		SYNTAX  Counter
		ACCESS  read-only
		STATUS  mandatory
		DESCRIPTION  ""
		::=  { ip 6 }

	ipInUnknowsProtos OBJECT-TYPE
		SYNTAX  Counter
		ACCESS  read-only
		STATUS  mandatory
		DESCRIPTION  ""
		::=  { ip 7 }

	ipInDiscard OBJECT-TYPE
		SYNTAX  Counter
		ACCESS  read-only
		STATUS  mandatory
		DESCRIPTION  ""
		::=  { ip 8 }

	ipInDelivers OBJECT-TYPE
		SYNTAX  Counter
		ACCESS  read-only
		STATUS  mandatory
		DESCRIPTION  ""
		::=  { ip 9 }

	ipOutRequest OBJECT-TYPE
		SYNTAX  Counter
		ACCESS  read-only
		STATUS  mandatory
		DESCRIPTION  ""
		::=  { ip 10 }

	ipOutDiscard OBJECT-TYPE
		SYNTAX  Counter
		ACCESS  read-only
		STATUS  mandatory
		DESCRIPTION  ""
		::=  { ip 11 }

	ipOutNoRoutes OBJECT-TYPE
		SYNTAX  Counter
		ACCESS  read-only
		STATUS  mandatory
		DESCRIPTION  ""
		::=  { ip 12 }

	ipReasmTimeout OBJECT-TYPE
		SYNTAX  INTEGER
		ACCESS  read-only
		STATUS  mandatory
		DESCRIPTION  ""
		::=  { ip 13 }

	ipReasmReqds OBJECT-TYPE
		SYNTAX  Counter
		ACCESS  read-only
		STATUS  mandatory
		DESCRIPTION  ""
		::=  { ip 14 }

	ipReasmOKs OBJECT-TYPE
		SYNTAX  Counter
		ACCESS  read-only
		STATUS  mandatory
		DESCRIPTION  ""
		::=  { ip 15 }

	ipReasmFails OBJECT-TYPE
		SYNTAX  Counter
		ACCESS  read-only
		STATUS  mandatory
		DESCRIPTION  ""
		::=  { ip 16 }

	ipFragOKs OBJECT-TYPE
		SYNTAX  Counter
		ACCESS  read-only
		STATUS  mandatory
		DESCRIPTION  ""
		::=  { ip 17 }

	ipFragFails OBJECT-TYPE
		SYNTAX  Counter
		ACCESS  read-only
		STATUS  mandatory
		DESCRIPTION  ""
		::=  { ip 18 }

	ipFragCreates OBJECT-TYPE
		SYNTAX  Counter
		ACCESS  read-only
		STATUS  mandatory
		DESCRIPTION  ""
		::=  { ip 19 }

-- ------------------------------------------------------
--	ipAddrTable objects
-- ------------------------------------------------------

	ipAddrTable OBJECT-TYPE
		SYNTAX  SEQUENCE OF IpAddrEntry
		ACCESS  not-accessible
		STATUS  mandatory
		DESCRIPTION  ""
		::=  { ip 20 }

	ipAddrEntry OBJECT-TYPE
		SYNTAX  IpAddrEntry
		ACCESS  not-accessible
		STATUS  mandatory
		DESCRIPTION  ""
		INDEX { ipAdEntAddr }
		::=  { ipAddrTable 1 }

	IpAddrEntry ::= SEQUENCE {
			ipAdEntAddr
				IpAddress,
			ipAdEntIfIndex
				INTEGER,
			ipAdEntNetMask
				IpAddress,
			ipAdEntBcastAddr
				INTEGER
				}

	ipAdEntAddr OBJECT-TYPE
		SYNTAX IpAddress 
		ACCESS read-only
		STATUS mandatory
		DESCRIPTION  ""
		::= { ipAddrEntry 1 }

	ipAdEntIfIndex OBJECT-TYPE
		SYNTAX INTEGER 
		ACCESS read-only
		STATUS mandatory
		DESCRIPTION  ""
		::= { ipAddrEntry 2 }

	ipAdEntNetMask OBJECT-TYPE
		SYNTAX IpAddress 
		ACCESS read-only
		STATUS mandatory
		DESCRIPTION  ""
		::= { ipAddrEntry 3 }

	ipAdEntBcastAddr OBJECT-TYPE
		SYNTAX INTEGER 
		ACCESS read-only
		STATUS mandatory
		DESCRIPTION  ""
		::= { ipAddrEntry 4 }

-- ------------------------------------------------------
--	ipRoutingTable objects
-- --------------------------------------------------------

	ipRoutingTable OBJECT-TYPE
		SYNTAX  SEQUENCE OF IpRouteEntry
		ACCESS  not-accessible
		STATUS  mandatory
		DESCRIPTION  ""
		::=  { ip 21 }

	ipRouteEntry OBJECT-TYPE
		SYNTAX  IpRouteEntry
		ACCESS  not-accessible
		STATUS  mandatory
		DESCRIPTION  ""
		INDEX { ipRouteDest }
		::=  { ipRoutingTable 1 }

	IpRouteEntry ::= SEQUENCE {
			ipRouteDest
				IpAddress,
			ipRouteIfIndex
				INTEGER,
			ipRouteMetric1
				INTEGER,
			ipRouteMetric2
				INTEGER,
			ipRouteMetric3
				INTEGER,
			ipRouteMetric4
				INTEGER,
			ipRouteNextHop
				IpAddress,
			ipRouteType
				INTEGER,
			ipRouteProto
				INTEGER,
			ipRouteAge
				INTEGER
			}

	ipRouteDest OBJECT-TYPE
		SYNTAX IpAddress 
		ACCESS read-write
		STATUS mandatory
		DESCRIPTION  ""
		::= { ipRouteEntry 1 }

	ipRouteIfIndex OBJECT-TYPE
		SYNTAX INTEGER 
		ACCESS read-write
		STATUS mandatory
		DESCRIPTION  ""
		::= { ipRouteEntry 2 }

	ipRouteMetric1 OBJECT-TYPE
		SYNTAX INTEGER 
		ACCESS read-write
		STATUS mandatory
		DESCRIPTION  ""
		::= { ipRouteEntry 3 }

	ipRouteMetric2 OBJECT-TYPE
		SYNTAX INTEGER 
		ACCESS read-write
		STATUS mandatory
		DESCRIPTION  ""
		::= { ipRouteEntry 4 }

	ipRouteMetric3 OBJECT-TYPE
		SYNTAX INTEGER 
		ACCESS read-write
		STATUS mandatory
		DESCRIPTION  ""
		::= { ipRouteEntry 5 }

	ipRouteMetric4 OBJECT-TYPE
		SYNTAX INTEGER 
		ACCESS read-write
		STATUS mandatory
		DESCRIPTION  ""
		::= { ipRouteEntry 6 }

	ipRouteNextHop OBJECT-TYPE
		SYNTAX IpAddress 
		ACCESS read-write
		STATUS mandatory
		DESCRIPTION  ""
		::= { ipRouteEntry 7 }

	ipRouteType OBJECT-TYPE
		SYNTAX INTEGER {
			other (1),	-- none of the following
			invalid (2),	-- an invalidated route	
			direct (3),	-- route to directly connected network
			remote (4) 	-- host/network/sub-network
		}
		ACCESS read-write
		STATUS mandatory
		DESCRIPTION  ""
		::= { ipRouteEntry 8 }

	ipRouteProto OBJECT-TYPE
		SYNTAX INTEGER {
			other (1),	-- none of the following
			local (2),	-- none protocol info., manual config
					-- entries
			netmgmt (3),	-- set via a network management protocol
			icmp (4),	-- obtained via icmp
			egp (5),	-- gateway routing protocols
			ggp (6),	
			hello (7),	
			rip (8),
			is-is (9),
			es-is (10),
			ciscoIgrp (11),
			bbnSpfIgp (12),
			oigp (13)
			}	
		ACCESS read-only
		STATUS mandatory
		DESCRIPTION  ""
		::= { ipRouteEntry 9 }

	ipRouteAge OBJECT-TYPE
		SYNTAX INTEGER 
		ACCESS read-write
		STATUS mandatory
		DESCRIPTION  ""
		::= { ipRouteEntry 10 }

-- 
--	icmp group elements
--

	icmpInMsgs OBJECT-TYPE
		SYNTAX Counter 
		ACCESS read-only
		STATUS mandatory
		DESCRIPTION  ""
		::= { icmp 1 }

	icmpInErrors OBJECT-TYPE
		SYNTAX Counter 
		ACCESS read-only
		STATUS mandatory
		DESCRIPTION  ""
		::= { icmp 2 }

	icmpInDestUnreachs OBJECT-TYPE
		SYNTAX Counter 
		ACCESS read-only
		STATUS mandatory
		DESCRIPTION  ""
		::= { icmp 3 }

	icmpInTimeExcds OBJECT-TYPE
		SYNTAX Counter 
		ACCESS read-only
		STATUS mandatory
		DESCRIPTION  ""
		::= { icmp 4 }

	icmpInParmProbs OBJECT-TYPE
		SYNTAX Counter 
		ACCESS read-only
		STATUS mandatory
		DESCRIPTION  ""
		::= { icmp 5 }

	icmpInSrcQuenchs OBJECT-TYPE
		SYNTAX Counter 
		ACCESS read-only
		STATUS mandatory
		DESCRIPTION  ""
		::= { icmp 6 }

	icmpInRedirects OBJECT-TYPE
		SYNTAX Counter 
		ACCESS read-only
		STATUS mandatory
		DESCRIPTION  ""
		::= { icmp 7 }

	icmpInEchos OBJECT-TYPE
		SYNTAX Counter 
		ACCESS read-only
		STATUS mandatory
		DESCRIPTION  ""
		::= { icmp 8 }

	icmpInEchoReps OBJECT-TYPE
		SYNTAX Counter 
		ACCESS read-only
		STATUS mandatory
		DESCRIPTION  ""
		::= { icmp 9 }

	icmpInTimestamps OBJECT-TYPE
		SYNTAX Counter 
		ACCESS read-only
		STATUS mandatory
		DESCRIPTION  ""
		::= { icmp 10 }

	icmpInTimestampReps OBJECT-TYPE
		SYNTAX Counter 
		ACCESS read-only
		STATUS mandatory
		DESCRIPTION  ""
		::= { icmp 11 }

	icmpInAddrMasks OBJECT-TYPE
		SYNTAX Counter 
		ACCESS read-only
		STATUS mandatory
		DESCRIPTION  ""
		::= { icmp 12 }

	icmpInAddrMaskReps OBJECT-TYPE
		SYNTAX Counter 
		ACCESS read-only
		STATUS mandatory
		DESCRIPTION  ""
		::= { icmp 13 }

	icmpOutMsgs OBJECT-TYPE
		SYNTAX Counter 
		ACCESS read-only
		STATUS mandatory
		DESCRIPTION  ""
		::= { icmp 14 }

	icmpOutErrors OBJECT-TYPE
		SYNTAX Counter 
		ACCESS read-only
		STATUS mandatory
		DESCRIPTION  ""
		::= { icmp 15 }

	icmpOutDestUnreachs OBJECT-TYPE
		SYNTAX Counter 
		ACCESS read-only
		STATUS mandatory
		DESCRIPTION  ""
		::= { icmp 16 }

	icmpOutTimeExcds OBJECT-TYPE
		SYNTAX Counter 
		ACCESS read-only
		STATUS mandatory
		DESCRIPTION  ""
		::= { icmp 17 }

	icmpOutParmProbs OBJECT-TYPE
		SYNTAX Counter 
		ACCESS read-only
		STATUS mandatory
		DESCRIPTION  ""
		::= { icmp 18 }

	icmpOutSrcQuenchs OBJECT-TYPE
		SYNTAX Counter 
		ACCESS read-only
		STATUS mandatory
		DESCRIPTION  ""
		::= { icmp 19 }

	icmpOutRedirects OBJECT-TYPE
		SYNTAX Counter 
		ACCESS read-only
		STATUS mandatory
		DESCRIPTION  ""
		::= { icmp 20 }

	icmpOutEchos OBJECT-TYPE
		SYNTAX Counter 
		ACCESS read-only
		STATUS mandatory
		DESCRIPTION  ""
		::= { icmp 21 }

	icmpOutEchoReps OBJECT-TYPE
		SYNTAX Counter 
		ACCESS read-only
		STATUS mandatory
		DESCRIPTION  ""
		::= { icmp 22 }

	icmpOutTimestamps OBJECT-TYPE
		SYNTAX Counter 
		ACCESS read-only
		STATUS mandatory
		DESCRIPTION  ""
		::= { icmp 23 }

	icmpOutTimestampReps OBJECT-TYPE
		SYNTAX Counter 
		ACCESS read-only
		STATUS mandatory
		DESCRIPTION  ""
		::= { icmp 24 }

	icmpOutTAddrMasks OBJECT-TYPE
		SYNTAX Counter 
		ACCESS read-only
		STATUS mandatory
		DESCRIPTION  ""
		::= { icmp 25 }

	icmpOutTAddrMaskReps OBJECT-TYPE
		SYNTAX Counter 
		ACCESS read-only
		STATUS mandatory
		DESCRIPTION  ""
		::= { icmp 26 }

--
--	udp group elements
--

	udpInDatagrams OBJECT-TYPE
		SYNTAX Counter 
		ACCESS read-only
		STATUS mandatory
		DESCRIPTION  ""
		::= { udp 1 }

	udpNoPorts OBJECT-TYPE
		SYNTAX Counter 
		ACCESS read-only
		STATUS mandatory
		DESCRIPTION  ""
		::= { udp 2 }

	udpInErrors OBJECT-TYPE
		SYNTAX Counter 
		ACCESS read-only
		STATUS mandatory
		DESCRIPTION  ""
		::= { udp 3 }

	udpOutDatagrams OBJECT-TYPE
		SYNTAX Counter 
		ACCESS read-only
		STATUS mandatory
		DESCRIPTION  ""
		::= { udp 4 }

--
--	s3agentSW group elements
--

	s3agentType OBJECT-TYPE
		SYNTAX INTEGER {
			t323 (9),	-- AUI Local Bridge
			t356 (10)	-- Ethernet Remote Bridge
			}
		ACCESS read-only
		STATUS mandatory
		DESCRIPTION  ""
		::= { s3agentSW 1}

	s3agentFwVer OBJECT-TYPE
		SYNTAX INTEGER 
		ACCESS read-only
		STATUS mandatory
		DESCRIPTION  ""
		::= { s3agentSW 2}

	s3agentSwMajorVer OBJECT-TYPE
		SYNTAX INTEGER 
		ACCESS read-only
		STATUS mandatory
		DESCRIPTION  ""
		::= { s3agentSW 3}

	s3agentSwMinorVer OBJECT-TYPE
		SYNTAX INTEGER 
		ACCESS read-only
		STATUS mandatory
		DESCRIPTION  ""
		::= { s3agentSW 4}

	s3agentBootProtocol OBJECT-TYPE
		SYNTAX INTEGER {
			bootp-tftp(2)
			}
		ACCESS read-only
		STATUS mandatory
		DESCRIPTION  ""
		::= { s3agentSW 5}

	s3agentBootFile OBJECT-TYPE
		SYNTAX OCTET STRING (SIZE(64))
		ACCESS read-write
		STATUS mandatory
		DESCRIPTION  ""
		::= { s3agentSW 6}


	s3agentAuthTrap OBJECT-TYPE
		SYNTAX INTEGER {
			disable(1),	-- disable authentication traps
			enable(2)	-- enable authentication traps
			}
		ACCESS read-write
		STATUS mandatory
		DESCRIPTION  ""
		::= { s3agentSW 7}

	s3agentLocation OBJECT-TYPE
		SYNTAX OCTET STRING (SIZE(64))
		ACCESS read-write
		STATUS mandatory
		DESCRIPTION  ""
		::= { s3agentSW 8}

	s3agentMIBlevel OBJECT-TYPE
		SYNTAX INTEGER
		ACCESS read-only
		STATUS mandatory
		DESCRIPTION  ""
		::= { s3agentSW 9}

	s3agentfeatureLevel OBJECT-TYPE
		SYNTAX INTEGER
		ACCESS read-only
		STATUS mandatory
		DESCRIPTION  ""
		::= { s3agentSW 10}

	s3agentMySlotID OBJECT-TYPE
		SYNTAX INTEGER
		ACCESS read-only
		STATUS mandatory
		DESCRIPTION  ""
		::= { s3agentSW 11}


--
--	trap receiver objects
-- 


--	trapRcvrTable OBJECT IDENTIFIER ::= {s3snmpAgent 3}


	trapRcvrTable OBJECT-TYPE
		SYNTAX  SEQUENCE OF TrapRcvrEntry
		ACCESS  not-accessible
		STATUS  mandatory
		DESCRIPTION  ""
		::=  { s3snmpAgent 3 }

	s3agentTrap OBJECT-TYPE
		SYNTAX  TrapRcvrEntry
		ACCESS  not-accessible
		STATUS  mandatory
		DESCRIPTION  ""
		INDEX   { s3agentTrapRcvrNetAddr }
		::=  { trapRcvrTable 1 }

	TrapRcvrEntry ::= SEQUENCE {
				s3agentTrapRcvrNetAddr
					IpAddress,
				s3agentTrapRcvrStatus
					INTEGER,
				s3agentTrapRcvrComm
					OCTET STRING,
				s3agentTrapRcvrAgeTime
					TimeTicks

				}

	s3agentTrapRcvrNetAddr OBJECT-TYPE
		SYNTAX  IpAddress
		ACCESS  read-write
		STATUS  mandatory
		DESCRIPTION  ""
		::=  { s3agentTrap 1 }

	s3agentTrapRcvrStatus OBJECT-TYPE
		SYNTAX  INTEGER
		ACCESS  read-write
		STATUS  mandatory
		DESCRIPTION  ""
		::=  { s3agentTrap 2 }

	s3agentTrapRcvrComm OBJECT-TYPE
		SYNTAX  OCTET STRING (SIZE(0..20))
		ACCESS  read-write
		STATUS  mandatory
		DESCRIPTION  ""
		::=  { s3agentTrap 3 }

	s3agentTrapRcvrAgeTime OBJECT-TYPE
		SYNTAX  TimeTicks
		ACCESS  read-write
		STATUS  mandatory
		DESCRIPTION  ""
		::=  { s3agentTrap 4 }
--
--	AccessPolicy mib objects
--

	bcomBpduTimer OBJECT-TYPE
		SYNTAX  INTEGER
		ACCESS  read-write
		STATUS  mandatory
		DESCRIPTION  ""
		::=  { brdgcommon 1 }

	bcomDefaultBpduTimer OBJECT-TYPE
		SYNTAX  INTEGER
		ACCESS  read-write
		STATUS  mandatory
		DESCRIPTION  ""
		::=  { brdgcommon 2 }


	snmpAccessPolicyObject        	OBJECT IDENTIFIER ::= {brdgcommon 3 } 

	snmpAccessPolicyTable OBJECT-TYPE
		SYNTAX  SEQUENCE OF SnmpAccessPolicyEntry
		ACCESS  not-accessible
		STATUS  mandatory
		DESCRIPTION  ""
		::=  { snmpAccessPolicyObject 1 }

	snmpAccessPolicyEntry OBJECT-TYPE
		SYNTAX  SnmpAccessPolicyEntry
		ACCESS  not-accessible
		STATUS  mandatory
		DESCRIPTION  ""
		INDEX   { accessPolicyIndex }
		::=  { snmpAccessPolicyTable 1 }

	 SnmpAccessPolicyEntry ::= SEQUENCE {
		accessPolicyIndex
			INTEGER,
		communityName
			OCTET STRING (SIZE(0..10)),
		accessMode
			INTEGER,
		snmpAccessPolicyType
			INTEGER
		}

	accessPolicyIndex OBJECT-TYPE
		SYNTAX  INTEGER
		ACCESS  read-write
		STATUS  mandatory
		DESCRIPTION  ""
		::=  { snmpAccessPolicyEntry 1 }

	communityName OBJECT-TYPE
		SYNTAX  OCTET STRING ( SIZE (0..10))
		ACCESS  read-write
		STATUS  mandatory
		DESCRIPTION  ""
		::=  { snmpAccessPolicyEntry 2 }

	accessMode OBJECT-TYPE
		SYNTAX  INTEGER
		ACCESS  read-write
		STATUS  mandatory
		DESCRIPTION  ""
		::=  { snmpAccessPolicyEntry 3 }

	snmpAccessPolicyType OBJECT-TYPE
		SYNTAX  INTEGER
		ACCESS  read-write
		STATUS  mandatory
		DESCRIPTION  ""
		::=  { snmpAccessPolicyEntry 4 }

	snmpAccessPolicyAction OBJECT-TYPE
		SYNTAX  INTEGER
		ACCESS  write-only
		STATUS  mandatory
		DESCRIPTION  ""
		::=  { snmpAccessPolicyObject 2 }

	snmpAccessPolicyPage OBJECT-TYPE
		SYNTAX  OCTET STRING (SIZE(256))
		ACCESS  read-only
		STATUS  mandatory
		DESCRIPTION  ""
		::=  { snmpAccessPolicyObject 3 }

--
--	hardware mib objects
--

	s3agentStatus OBJECT-TYPE
		SYNTAX INTEGER {
			offline(1),
			online(2)
			}
		ACCESS read-only
		STATUS mandatory
		DESCRIPTION  ""
		::= { s3agentHW 1 }

	s3agentMdaHwVer OBJECT-TYPE
		SYNTAX INTEGER
		ACCESS read-only
		STATUS mandatory
		DESCRIPTION  ""
		::= { s3agentHW 2 }

	s3agentMode OBJECT-TYPE
		SYNTAX INTEGER {
			primary(1),
			secondary(2)
			}
		ACCESS read-only
		STATUS mandatory
		DESCRIPTION  ""
		::= { s3agentHW 3 }

	s3agentReset OBJECT-TYPE
		SYNTAX INTEGER {
			noReset(1),
			reset(2)
			}
		ACCESS read-write
		STATUS mandatory
		DESCRIPTION  ""
		::= { s3agentHW 4 }

	s3agentRestart OBJECT-TYPE
		SYNTAX INTEGER {
			noRestart(1),
			restart(2)
			}
		ACCESS read-write
		STATUS mandatory
		DESCRIPTION  ""
		::= { s3agentHW 5 }

	s3agentBootMode OBJECT-TYPE
		SYNTAX INTEGER {
			eeprom(1),
			other(2)
			}
		ACCESS read-write
		STATUS mandatory
		DESCRIPTION  ""
		::= { s3agentHW 6 }

	s3agentWriteEeprom OBJECT-TYPE
		SYNTAX INTEGER {
			noWriteEeprom(1),
			writeEeprom(2)
			}
		ACCESS read-write
		STATUS mandatory
		DESCRIPTION  ""
		::= { s3agentHW 7 }

	s3agentBaudRate OBJECT-TYPE
		SYNTAX Gauge
		ACCESS read-write
		STATUS mandatory
		DESCRIPTION  ""
		::= { s3agentHW 8 }

	s3agentInitString OBJECT-TYPE
		SYNTAX  OCTET STRING (SIZE (64))
		ACCESS  read-write
		STATUS  mandatory
		DESCRIPTION  ""
		::= { s3agentHW 9 }

	--  IEEE8023 Group

	ieee8023Table OBJECT-TYPE
		SYNTAX  SEQUENCE OF Ieee8023Entry
		ACCESS  not-accessible
		STATUS  mandatory
		DESCRIPTION  ""
		::= { ieee8023 1 }

	ieee8023Entry OBJECT-TYPE
		SYNTAX  Ieee8023Entry
		ACCESS  not-accessible
		STATUS  mandatory
		DESCRIPTION  ""
		INDEX   { ieee8023Index }
		::= { ieee8023Table 1 }

	Ieee8023Entry ::= SEQUENCE {
		ieee8023Index
			INTEGER,
		ieee8023FramesTransmittedOks
			Counter,
		ieee8023SingleCollisionFrames
			Counter,
		ieee8023MultipleCollisionFrames
			Counter,
		ieee8023OctetsTransmittedOks
			Counter,
		ieee8023DeferredTransmissions
			Counter,
		ieee8023MulticastFramesTransmittedOks
			Counter,
		ieee8023BroadcastFramesTransmittedOks
			Counter,
		ieee8023LateCollisions
			Counter,
		ieee8023ExcessiveCollisions
			Counter,
		ieee8023InternalMACTransmitErrors
			Counter,
		ieee8023CarrierSenseErrors
			Counter,
		ieee8023ExcessiveDeferrals
			Counter,
		ieee8023FramesReceivedOks
			Counter,
		ieee8023OctetsReceivedOks
			Counter,
		ieee8023MulticastFramesReceivedOks
			Counter,
		ieee8023BroadcastFramesReceivedOks
			Counter,
		ieee8023FrameTooLongs
			Counter,
		ieee8023AlignmentErrors
			Counter,
		ieee8023FCSErrors
			Counter,
		ieee8023inRangeLengthErrors
			Counter,
		ieee8023outOfRangeLengthFields
			Counter,
		ieee8023InternalMACReceiveErrors
			Counter,
		ieee8023InitializeMAC
			INTEGER,
		ieee8023PromiscuousReceiveStatus
			INTEGER,
		ieee8023MACSubLayerStatus
			INTEGER,
		ieee8023TransmitStatus
			INTEGER,
		ieee8023MulticastReceiveStatus
			INTEGER,
		ieee8023MACAddress
			OCTET STRING (SIZE(6)),
		ieee8023SQETestErrors
			Counter
		}

	ieee8023Index   OBJECT-TYPE
		SYNTAX  INTEGER
		ACCESS  read-only
		STATUS  mandatory
		DESCRIPTION  ""
		::= { ieee8023Entry 1 }
	
	ieee8023FramesTransmittedOks OBJECT-TYPE
		SYNTAX  Counter
		ACCESS  read-only
		STATUS  mandatory
		DESCRIPTION  ""
		::= { ieee8023Entry 2 }
	
	ieee8023SingleCollisionFrames OBJECT-TYPE
		SYNTAX  Counter
		ACCESS  read-only
		STATUS  mandatory
		DESCRIPTION  ""
		::= { ieee8023Entry 3 }
	
	ieee8023MultipleCollisionFrames OBJECT-TYPE
		SYNTAX  Counter
		ACCESS  read-only
		STATUS  mandatory
		DESCRIPTION  ""
		::= { ieee8023Entry 4 }
	
	ieee8023OctetsTransmittedOks OBJECT-TYPE
		SYNTAX  Counter
		ACCESS  read-only
		STATUS  optional
		DESCRIPTION  ""
		::= { ieee8023Entry 5 }
	
	ieee8023DeferredTransmissions OBJECT-TYPE
		SYNTAX  Counter
		ACCESS  read-only
		STATUS  optional
		DESCRIPTION  ""
		::= { ieee8023Entry 6 }
	
	ieee8023MulticastFramesTransmittedOks OBJECT-TYPE
		SYNTAX  Counter
		ACCESS  read-only
		STATUS  optional
		DESCRIPTION  ""
		::= { ieee8023Entry 7 }
	
	ieee8023BroadcastFramesTransmittedOks OBJECT-TYPE
		SYNTAX  Counter
		ACCESS  read-only
		STATUS  optional
		DESCRIPTION  ""
		::= { ieee8023Entry 8 }
	
	ieee8023LateCollisions OBJECT-TYPE
		SYNTAX  Counter
		ACCESS  read-only
		STATUS  optional
		DESCRIPTION  ""
		::= { ieee8023Entry 9 }
	
	ieee8023ExcessiveCollisions OBJECT-TYPE
		SYNTAX  Counter
		ACCESS  read-only
		STATUS  optional
		DESCRIPTION  ""
		::= { ieee8023Entry 10 }
	ieee8023InternalMACTransmitErrors OBJECT-TYPE
		SYNTAX  Counter
		ACCESS  read-only
		STATUS  optional
		DESCRIPTION  ""
		::= { ieee8023Entry 11 }
	
	ieee8023CarrierSenseErrors OBJECT-TYPE
		SYNTAX  Counter
		ACCESS  read-only
		STATUS  optional
		DESCRIPTION  ""
		::= { ieee8023Entry 12 }

	ieee8023ExcessiveDeferrals OBJECT-TYPE
		SYNTAX  Counter
		ACCESS  read-only
		STATUS  optional
		DESCRIPTION  ""
		::= { ieee8023Entry 13 }

	ieee8023FramesReceivedOks OBJECT-TYPE
		SYNTAX  Counter
		ACCESS  read-only
		STATUS  mandatory
		DESCRIPTION  ""
		::= { ieee8023Entry 14 }
	
	ieee8023OctetsReceivedOks OBJECT-TYPE
		SYNTAX  Counter
		ACCESS  read-only
		STATUS  optional
		DESCRIPTION  ""
		::= { ieee8023Entry 15 }
	
	ieee8023MulticastFramesReceivedOks OBJECT-TYPE
		SYNTAX  Counter
		ACCESS  read-only
		STATUS  optional
		DESCRIPTION  ""
		::= { ieee8023Entry 16 }
	
	ieee8023BroadcastFramesReceivedOks OBJECT-TYPE
		SYNTAX  Counter
		ACCESS  read-only
		STATUS  optional
		DESCRIPTION  ""
		::= { ieee8023Entry 17 }
	
	ieee8023FrameTooLongs OBJECT-TYPE
		SYNTAX  Counter
		ACCESS  read-only
		STATUS  optional
		DESCRIPTION  ""
		::= { ieee8023Entry 18 }
	
	ieee8023AlignmentErrors OBJECT-TYPE
		SYNTAX  Counter
		ACCESS  read-only
		STATUS  mandatory
		DESCRIPTION  ""
		::= { ieee8023Entry 19 }
	
	ieee8023FCSErrors OBJECT-TYPE
		SYNTAX  Counter
		ACCESS  read-only
		STATUS  mandatory
		DESCRIPTION  ""
		::= { ieee8023Entry 20 }
	ieee8023inRangeLengthErrors OBJECT-TYPE
		SYNTAX  Counter
		ACCESS  read-only
		STATUS  optional
		DESCRIPTION  ""
		::= { ieee8023Entry 21 }
	
	ieee8023outOfRangeLengthFields OBJECT-TYPE
		SYNTAX  Counter
		ACCESS  read-only
		STATUS  optional
		DESCRIPTION  ""
		::= { ieee8023Entry 22 }
	ieee8023InternalMACReceiveErrors OBJECT-TYPE
		SYNTAX  Counter
		ACCESS  read-only
		STATUS  optional
		DESCRIPTION  ""
		::= { ieee8023Entry 23 }
	
	ieee8023InitializeMAC OBJECT-TYPE
		SYNTAX  INTEGER {
			initialize (1)
			}
		ACCESS  read-write
		STATUS  mandatory
		DESCRIPTION  ""
		::= { ieee8023Entry 24 }
	ieee8023PromiscuousReceiveStatus OBJECT-TYPE
		SYNTAX  INTEGER {
			enabled (1)
			}
		ACCESS  read-only
		STATUS  optional
		DESCRIPTION  ""
		::= { ieee8023Entry 25 }
	
	ieee8023MACSubLayerStatus OBJECT-TYPE
		SYNTAX  INTEGER {
			enabled (1)
			}
		ACCESS  read-only
		STATUS  optional
		DESCRIPTION  ""
		::= { ieee8023Entry 26 }
	ieee8023TransmitStatus OBJECT-TYPE
		SYNTAX  INTEGER {
			enabled (1),
			disabled (2)
			}
		ACCESS  read-write
		STATUS  optional
		DESCRIPTION  ""
		::= { ieee8023Entry 27 }
	
	ieee8023MulticastReceiveStatus OBJECT-TYPE
		SYNTAX  INTEGER {
			enabled (1)
			}
		ACCESS  read-write
		STATUS  optional
		DESCRIPTION  ""
		::= { ieee8023Entry 28 }
	ieee8023MACAddress OBJECT-TYPE
		SYNTAX  OCTET STRING (SIZE (6))
		ACCESS  read-only
		STATUS  optional
		DESCRIPTION  ""
		::= { ieee8023Entry 29 }
	ieee8023SQETestErrors OBJECT-TYPE
		SYNTAX  Counter
		ACCESS  read-only
		STATUS  mandatory
		DESCRIPTION  ""
		::= { ieee8023Entry 30 }


	-- in locbrdg group

	locbrdgNumber OBJECT-TYPE
		SYNTAX INTEGER
		ACCESS read-only
		STATUS mandatory
		DESCRIPTION  ""
		::= { locbrdg 1 }

	 locbrdgTable OBJECT-TYPE
		SYNTAX SEQUENCE OF LocbrdgEntry
		ACCESS not-accessible
		STATUS mandatory
		DESCRIPTION  ""
		::= { locbrdg 2 }

	 locbrdgEntry OBJECT-TYPE
		SYNTAX LocbrdgEntry
		ACCESS not-accessible
		STATUS mandatory
		DESCRIPTION  ""
		INDEX { locbrdgIndex }
		::= { locbrdgTable 1 }



	 LocbrdgEntry ::= SEQUENCE {
     		locbrdgIndex          		INTEGER,
     		locbrdgTransmitOnCrs		INTEGER,
     		locbrdgBroadcastRX		INTEGER,
     		locbrdgLanPathCost		INTEGER,
     		locbrdgLanDefaultPathCost      	INTEGER,
     		locbrdgLanPortSpatState		INTEGER,
    		locbrdgPortPriority		INTEGER,
     		locbrdgDefaultPortPriority     	INTEGER,
     		locbrdgDesignatedRoot		OCTET STRING (SIZE(6)),
     		locbrdgDesignatedCost		INTEGER,
     		locbrdgDesignatedPort		INTEGER,
     		locbrdgDesignatedBridge		OCTET STRING (SIZE(6)),
     		locbrdgTopologyChangeAck       	INTEGER,
     		locbrdgId       		OCTET STRING (SIZE(6)) 
		}

	 locbrdgIndex OBJECT-TYPE
		SYNTAX INTEGER 
		ACCESS read-only
		STATUS mandatory
		DESCRIPTION  ""
		::= { locbrdgEntry 1 }


	 locbrdgTransmitOnCrs OBJECT-TYPE
		SYNTAX INTEGER
		ACCESS read-write
		STATUS mandatory
		DESCRIPTION  ""
		::= { locbrdgEntry 2 }


	 locbrdgBroadcastRX OBJECT-TYPE
		SYNTAX INTEGER
		ACCESS read-write
		STATUS mandatory
		DESCRIPTION  ""
		::= { locbrdgEntry 3 }


	 locbrdgLanPathCost OBJECT-TYPE
		SYNTAX INTEGER
		ACCESS read-only
		STATUS mandatory
		DESCRIPTION  ""
		::= { locbrdgEntry 4 }


	 locbrdgLanDefaultPathCost OBJECT-TYPE
		SYNTAX INTEGER
		ACCESS read-write
		STATUS mandatory
		DESCRIPTION  ""
		::= { locbrdgEntry 5 }


	 locbrdgLanPortSpatState OBJECT-TYPE
		SYNTAX INTEGER
		ACCESS read-only
		STATUS mandatory
		DESCRIPTION  ""
		::= { locbrdgEntry 6 }


	 locbrdgPortPriority OBJECT-TYPE
		SYNTAX INTEGER
		ACCESS read-only
		STATUS mandatory
		DESCRIPTION  ""
		::= { locbrdgEntry 7 }


	 locbrdgDefaultPortPriority OBJECT-TYPE
		SYNTAX INTEGER
		ACCESS read-write
		STATUS mandatory
		DESCRIPTION  ""
		::= { locbrdgEntry 8 }


	 locbrdgDesignatedRoot OBJECT-TYPE
		SYNTAX OCTET STRING (SIZE(6))
		ACCESS read-only
		STATUS mandatory
		DESCRIPTION  ""
		::= { locbrdgEntry 9 }

	 locbrdgDesignatedCost OBJECT-TYPE
		SYNTAX INTEGER
		ACCESS read-only
		STATUS mandatory
		DESCRIPTION  ""
		::= { locbrdgEntry 10 }

	 locbrdgDesignatedPort OBJECT-TYPE
		SYNTAX INTEGER
		ACCESS read-only
		STATUS mandatory
		DESCRIPTION  ""
		::= { locbrdgEntry 11 }


	 locbrdgDesignatedBridge OBJECT-TYPE
		SYNTAX OCTET STRING (SIZE(6))
		ACCESS read-only
		STATUS mandatory
		DESCRIPTION  ""
		::= { locbrdgEntry 12 }


	 locbrdgTopologyChangeAck OBJECT-TYPE
		SYNTAX INTEGER
		ACCESS read-only
		STATUS mandatory
		DESCRIPTION  ""
		::= { locbrdgEntry 13 }

	 locbrdgId OBJECT-TYPE
		SYNTAX OCTET STRING (SIZE(6)) 
		ACCESS read-only
		STATUS optional
		DESCRIPTION  ""
		::= { locbrdgEntry 14 }



	 locbrdgBridgeMode OBJECT-TYPE
		SYNTAX INTEGER
		ACCESS read-write
		STATUS mandatory
		DESCRIPTION  ""
		::= { locbrdg 3 }

	 locbrdgDefaultBridgeMode OBJECT-TYPE
		SYNTAX INTEGER
		ACCESS read-write
		STATUS mandatory
		DESCRIPTION  ""
		::= { locbrdg 4 }



	 locbrdgFilterMatches OBJECT-TYPE
		SYNTAX INTEGER
		ACCESS read-write
		STATUS mandatory
		DESCRIPTION  ""
		::= { locbrdg 5 }


	 locbrdgSpanTreeMode OBJECT-TYPE
		SYNTAX INTEGER
		ACCESS read-write
		STATUS mandatory
		DESCRIPTION  ""
		::= { locbrdg 6 }


	 locbrdgDefaultSpanTreeMode OBJECT-TYPE
		SYNTAX INTEGER
		ACCESS read-write
		STATUS mandatory
		DESCRIPTION  ""
		::= { locbrdg 7 }



	 locbrdgSpatHelloTimer OBJECT-TYPE
		SYNTAX INTEGER (1..10)
		ACCESS read-write
		STATUS optional
		DESCRIPTION  ""
		::= { locbrdg 8 }


	 locbrdgDefaultSpatHelloTimer OBJECT-TYPE
		SYNTAX INTEGER (1..10)
		ACCESS read-write
		STATUS mandatory
		DESCRIPTION  ""
		::= { locbrdg 9 }

	 locbrdgHoldTime OBJECT-TYPE
		SYNTAX INTEGER 
		ACCESS read-only
		STATUS optional
		DESCRIPTION  ""
		::= { locbrdg 10 }


	 locbrdgSpatVersion OBJECT-TYPE
		SYNTAX INTEGER {
			revisionC(3),	-- ready to pass packets
			revision8(8)
		}
		ACCESS read-only
		STATUS optional
		DESCRIPTION  ""
		::= { locbrdg 11 }

	 locbrdgDefaultSpatVersion OBJECT-TYPE
		SYNTAX INTEGER {
			revisionC(3),	-- ready to pass packets
			revision8(8)
		}
		ACCESS read-write
		STATUS mandatory
		DESCRIPTION  ""
		::= { locbrdg 12 }


	 locbrdgMaxAge OBJECT-TYPE
		SYNTAX INTEGER (6..40)
		ACCESS read-only
		STATUS optional
		DESCRIPTION  ""
		::= { locbrdg 13 }



	 locbrdgDefaultBridgeMaxAge OBJECT-TYPE
		SYNTAX INTEGER (6..40)
		ACCESS read-write
		STATUS mandatory
		DESCRIPTION  ""
		::= { locbrdg 14 }


	 locbrdgLiveBridgeForwardDelay OBJECT-TYPE
		SYNTAX INTEGER (4..30)
		ACCESS read-only
		STATUS mandatory
		DESCRIPTION  ""
		::= { locbrdg 15 }


	 locbrdgBridgeForwardDelay OBJECT-TYPE
		SYNTAX INTEGER (4..30)
		ACCESS read-write
		STATUS optional
		DESCRIPTION  ""
		::= { locbrdg 16 }


	 locbrdgDefaultBridgeForwardDelay OBJECT-TYPE
		SYNTAX INTEGER (4..30)
		ACCESS read-write
		STATUS mandatory
		DESCRIPTION  ""
		::= { locbrdg 17 }


	 locbrdgTopologyChangeCount OBJECT-TYPE
		SYNTAX INTEGER 
		ACCESS read-only
		STATUS mandatory
		DESCRIPTION  ""
		::= { locbrdg 18 }




locbrdgRangeDataBaseTable   OBJECT IDENTIFIER ::= {locbrdg 19}



	 locbrdgRangeTable OBJECT-TYPE
		SYNTAX SEQUENCE OF LocbrdgRangeEntry
		ACCESS not-accessible
		STATUS mandatory
		DESCRIPTION  ""
		::= { locbrdgRangeDataBaseTable 1 }


	 locbrdgRangeEntry OBJECT-TYPE
		SYNTAX LocbrdgRangeEntry 
		ACCESS not-accessible
		STATUS mandatory
		DESCRIPTION  ""
		::= { locbrdgRangeTable  1 }


	 LocbrdgRangeEntry ::= SEQUENCE {
          	locbrdgSourceLower 	OCTET STRING,
	    	locbrdgSourceUpper 	OCTET STRING,
	    	locbrdgDestLower 	OCTET STRING,
	    	locbrdgDestUpper 	OCTET STRING,
	    	locbrdgTypeLower 	INTEGER,
          	locbrdgTypeUpper 	INTEGER,
		locbrdgRangeType	INTEGER
          }

	 locbrdgSourceLower OBJECT-TYPE
		SYNTAX OCTET STRING ( SIZE (6)) 
		ACCESS read-write
		STATUS mandatory
		DESCRIPTION  ""
		::= { locbrdgRangeEntry 1 }


	 locbrdgSourceUpper OBJECT-TYPE
		SYNTAX OCTET STRING ( SIZE (6)) 
		ACCESS read-write
		STATUS mandatory
		DESCRIPTION  ""
		::= { locbrdgRangeEntry 2 }



	 locbrdgDestLower OBJECT-TYPE
		SYNTAX OCTET STRING ( SIZE (6)) 
		ACCESS read-write
		STATUS mandatory
		DESCRIPTION  ""
		::= { locbrdgRangeEntry 3 }


	 locbrdgDestUpper OBJECT-TYPE
		SYNTAX OCTET STRING ( SIZE (6)) 
		ACCESS read-write
		STATUS mandatory
		DESCRIPTION  ""
		::= { locbrdgRangeEntry 4 }


	 locbrdgTypeLower OBJECT-TYPE
		SYNTAX INTEGER 
		ACCESS read-write
		STATUS mandatory
		DESCRIPTION  ""
		::= { locbrdgRangeEntry 5 }


	 locbrdgTypeUpper OBJECT-TYPE
		SYNTAX INTEGER 
		ACCESS read-write
		STATUS mandatory
		DESCRIPTION  ""
		::= { locbrdgRangeEntry 6 } 
		
	locbrdgRangeType OBJECT-TYPE
		SYNTAX INTEGER 
		ACCESS read-write
		STATUS mandatory
		DESCRIPTION  ""
		::= { locbrdgRangeEntry 7 }


	 locbrdgRangeTablePage OBJECT-TYPE
		SYNTAX OCTET STRING (SIZE (480))
		ACCESS read-only
		STATUS mandatory
		DESCRIPTION  ""
		::= { locbrdgRangeDataBaseTable 2 }

	 locbrdgRangeTableAction OBJECT-TYPE
		SYNTAX INTEGER
		ACCESS read-write
		STATUS mandatory
		DESCRIPTION  ""
		::= { locbrdgRangeDataBaseTable 3 }

	locbrdgFilterDataBaseTable   OBJECT IDENTIFIER ::= {locbrdg 20}


	 locbrdgFilterTable OBJECT-TYPE
		SYNTAX SEQUENCE OF LocbrdgFilterEntry
		ACCESS not-accessible
		STATUS mandatory
		DESCRIPTION  ""
		::= { locbrdgFilterDataBaseTable 1 }



	 locbrdgFilterEntry OBJECT-TYPE
		SYNTAX LocbrdgFilterEntry
		ACCESS not-accessible
		STATUS mandatory
		DESCRIPTION  ""
		INDEX  { locbrdgFilterEntryMacAddress }
		::= { locbrdgFilterTable 1 }

	-- filter data base table

     	LocbrdgFilterEntry ::= SEQUENCE {
          	locbrdgFilterEntryMacAddress OCTET STRING,
          	locbrdgFilterEntryDisposition INTEGER,
          	locbrdgFilterEntryStatus INTEGER,
          	locbrdgFilterEntryType INTEGER
          	}

	 locbrdgFilterEntryMacAddress OBJECT-TYPE
		SYNTAX OCTET STRING ( SIZE (6))
		ACCESS read-write
		STATUS mandatory
		DESCRIPTION  ""
		::= { locbrdgFilterEntry 1 }



	 locbrdgFilterEntryDisposition OBJECT-TYPE
		SYNTAX INTEGER
		ACCESS read-write
		STATUS mandatory
		DESCRIPTION  ""
		::= { locbrdgFilterEntry 2 }



	 locbrdgFilterEntryStatus OBJECT-TYPE
		SYNTAX INTEGER
		ACCESS read-only
		STATUS mandatory
		DESCRIPTION  ""
		::= { locbrdgFilterEntry 3 }

	 locbrdgFilterEntryType OBJECT-TYPE
		SYNTAX INTEGER
		ACCESS read-write
		STATUS mandatory
		DESCRIPTION  ""
		::= { locbrdgFilterEntry 4 }

	 locbrdgFilterAction OBJECT-TYPE
		SYNTAX INTEGER
		ACCESS read-write
		STATUS mandatory
		DESCRIPTION  ""
		::= { locbrdgFilterDataBaseTable 2 }



	 locbrdgFilterPage OBJECT-TYPE
		SYNTAX SEQUENCE OF LocbrdgFilterPageValue
		ACCESS not-accessible
		STATUS mandatory
		DESCRIPTION  ""
		::= { locbrdgFilterDataBaseTable 3 }


	 locbrdgFilterPageValue OBJECT-TYPE
		SYNTAX OCTET STRING ( SIZE (0..640))
		ACCESS read-only
		STATUS mandatory
		DESCRIPTION  ""
		::= { locbrdgFilterPage 1 }




	 locbrdgLiveSpatHelloTimer OBJECT-TYPE
		SYNTAX INTEGER
		ACCESS read-only
		STATUS mandatory
		DESCRIPTION  ""
		::= { locbrdg 21 }

	 locbrdgLiveMaxAge OBJECT-TYPE
		SYNTAX INTEGER
		ACCESS read-only
		STATUS mandatory
		DESCRIPTION  ""
		::= { locbrdg 22 }

	 locbrdgDefaultHoldTime OBJECT-TYPE
		SYNTAX INTEGER
		ACCESS read-write
		STATUS mandatory
		DESCRIPTION  ""
		::= { locbrdg 23 }

	 locbrdgPriority OBJECT-TYPE
		SYNTAX INTEGER
		ACCESS read-write
		STATUS mandatory
		DESCRIPTION  ""
		::= { locbrdg 24 }

	 locbrdgDefaultPriority OBJECT-TYPE
		SYNTAX INTEGER
		ACCESS read-write
		STATUS mandatory
		DESCRIPTION  ""
		::= { locbrdg 25 }


-- ------------------------------------------------------------
-- locrouter related objects
-- ------------------------------------------------------------

	locRouterStatus OBJECT-TYPE
		SYNTAX INTEGER
		ACCESS read-write
		STATUS mandatory
		DESCRIPTION  ""
		::= { locrouter 1 }

	locRouterProxyArpStatus OBJECT-TYPE
		SYNTAX INTEGER
		ACCESS read-write
		STATUS mandatory
		DESCRIPTION  ""
		::= { locrouter 2 }

	locRouterSourceQuenchStatus OBJECT-TYPE
		SYNTAX INTEGER
		ACCESS read-write
		STATUS mandatory
		DESCRIPTION  ""
		::= { locrouter 3 }

	locRouterArpTimeOut OBJECT-TYPE
		SYNTAX TimeTicks
		ACCESS read-write
		STATUS mandatory
		DESCRIPTION  ""
		::= { locrouter 4 }

		  END
