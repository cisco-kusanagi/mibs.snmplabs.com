--
--              STOP !!!   READ THIS!!!
--              =======================
--
--
-- Do you understand the rules for adding new message / event / disconnect / MIB codes?
--
--
-- (1) First allocate new codes in the MAINLINE branch.
--
--      Adding a comment is not sufficient.
--
-- (2) Backmerge to other branch where you need them.
--
-- (3) Do not remove codes that are no longer needed.
--
--      Obsolete codes should not be reused for another purpose.
--
-- (4) Never change any existing numbers.
--
--      Many of these numbers are visible to customers.
--      They should never change between releases.
--
--      A customer might have some process to look for certain error message
--      codes in a log file. It would be most unfortunate if the same error
--      message used a different code in a later release.
--
-- (5) Merge conflicts should happen only when someone doesn't follow the rules.
--
--      The MAINLINE branch is the authority in case of any discrepancies.
--
-- (6) Look for additional rules in this file.
--
--      Sometimes a last or max value needs to be updated.
--      Sometimes a corresponding change needs to be made in some other file.
--
--	In this particular case, boxer/common/msg/snmp_xdr_defs.x must be kept in sync.
--
-- (7) Review rule (1).  Do not simply add them to other branches.
--
--      Ignoring this will cause problems, and extra cleanup work, weeks or months later.
--
--
--
-- Failure to follow these rules will result in duplicate use of the same numbers and a
-- big mess to clean up later when merging branches.
--
--
-- Contact releng team for help if you have any doubts.
--

STARENT-MIB DEFINITIONS ::= BEGIN

IMPORTS
    MODULE-IDENTITY,
    OBJECT-TYPE,
    enterprises,
    Integer32,
    Gauge32,
    Counter32,
    Counter64,
    Unsigned32,
    NOTIFICATION-TYPE,
    IpAddress
        FROM SNMPv2-SMI
    TEXTUAL-CONVENTION,
    DisplayString,
    DateAndTime,
    TruthValue
        FROM SNMPv2-TC
    Ipv6Address
	FROM IPV6-TC
    MODULE-COMPLIANCE,
    OBJECT-GROUP,
    NOTIFICATION-GROUP
        FROM SNMPv2-CONF
    InetAddressType,
    InetAddress
        FROM INET-ADDRESS-MIB
    radiusAuthServerIndex,
    radiusAuthServerAddress
        FROM RADIUS-AUTH-CLIENT-MIB
    radiusAccServerIndex,
    radiusAccServerAddress
        FROM RADIUS-ACC-CLIENT-MIB;

starentMIB MODULE-IDENTITY
    LAST-UPDATED "201806270000Z" --Jun  27, 2018
    ORGANIZATION "Cisco Systems, Inc."
    CONTACT-INFO
	"    Email:     support@starentnetworks.com
             Web:       www.cisco.com

                        Cisco Systems, Inc.
                        30 International Place
                        Tewksbury, MA  01876
			(978) 851-1100"
    DESCRIPTION
	"Cisco Systems ASR 5xxx series of multimedia core platforms (ASR 5000,
	ASR 5500)
	
	Designed exclusively for mobile and fixed mobile converged applications,
	Cisco's ASR 5xxx series products provide a high-performance, highly intelligent
	platform ideally suited for development in mobile operator networks
	to fulfill key multimedia core networking functions.  The platform features 2G/3G/4G
	and WiFi multi-service access indepedent capabilities coupled with a carrier class
	high-availability design.  Harnessing subscriber awareness with an abundant supply
	of distributed processing resources, the ASR 5xxx series offers a variety of high touch
	Inline Services to enable service providers to monetize the value of the network
	while enriching the overall subscriber experience."

    REVISION      "201809020000Z"
    DESCRIPTION
      " Added Traps 1399 to 1400 for UIDH URL Host Database 
        starUidhURLHostDatabaseUpgradeFailureStatus,
        starUidhURLHostDatabaseUpgradeSuccessStatus,
      "
    REVISION      "201809010000Z"
    DESCRIPTION
      " Added Traps 1401 to 1402 for critical events for Smart Licensing
        starSmartLicenseFeatureOOC,
        starSmartLicenseFeatureOOCClear,
      "
    REVISION      "201806270000Z"
    DESCRIPTION
      "Added trap no 1398 for IFTask Boot Config Application on card<card-num>-cpu<cpu-num>."
 

    REVISION      "201805290000Z"
    DESCRIPTION
      "Added trap no 1394,1395,1396,1397 for Chassis Throughput."
    
    REVISION      "201804190000Z"
    DESCRIPTION
      "Added trap no 1392 for Sx Peer Node Associated."


    REVISION      "201804160000Z"
    DESCRIPTION
      "Added trap no 1388, 1389, 1390, 1391 for Control plane monitor packet loss on DI platform
        starThreshControlPlaneMonitor5MinsLoss,
        starThreshClearControlPlaneMonitor5MinsLoss,
        starThreshControlPlaneMonitor60MinsLoss,
        starThreshClearControlPlaneMonitor60MinsLoss
      "  

    REVISION      "201804040000Z"
    DESCRIPTION
      "Added trap no 1384, 1385, 1386, 1387 for Data plane monitor packet loss on DI platform
        starThreshDataPlaneMonitor5MinsLoss,
        starThreshClearDataPlaneMonitor5MinsLoss,
        starThreshDataPlaneMonitor60MinsLoss,
        starThreshClearDataPlaneMonitor60MinsLoss
      "  

    REVISION      "201803260000Z"
    DESCRIPTION
      "Added Trap datatype starSxFailureCause 192"

    REVISION      "201803250000Z"
    DESCRIPTION
     "Added trap no 1382, 1383 for Sx Path failure.
      Added Trap datatype starSxInterfaceType 187
      Added Trap datatype starSxSelfAddr 188
      Added Trap datatype starSxPeerAddr 189
      Added Trap datatype starSxPeerNewRecTimeStamp 190
      Added Trap datatype starSxPeerOldRecTimeStamp 191"

    REVISION      "201712120000Z"
    DESCRIPTION
     "Added trap no 1378 ,1379, 1380.1381 for ADC license , 
      Added Trap datatype starP2PPluginVersion 185
      Added Trap datatype starADCLicenseExpiryDate 186"
    
    REVISION      "201709200000Z"
    DESCRIPTION
     "Added trap no 1376, which informs about change in nic bonding of a port
      It is informational trap
      Added Trap datatype starMacaddress 184"
  

    REVISION      "201709130000Z"
    DESCRIPTION
      "Added IKEv2 error traps for Control packet flooding.
      "

    REVISION      "201709120000Z"
    DESCRIPTION
      "Added IFTask Health Failure traps. 
             starIFTaskHealthFailure
      "

    REVISION      "201708160000Z"
    DESCRIPTION
      "Added IPSEC UDP error traps for Peer based Source-IP. 
      "

    REVISION      "201706220000Z"
    DESCRIPTION
      "Added IPSEC UDP error traps for System level. 
      "  

    REVISION      "201707210000Z"
    DESCRIPTION 
      "Added trap 1363 and 1364 for total-volume and total-volume clear 
       Added objects starRuleBaseName, starRuleDefName starGroupOfRuledef 
      "
    
    REVISION      "201705110000Z"
    DESCRIPTION
      "Added trap no 1362, which informs about change in Logging Level of a facility 
       (which is inferior to default Logging Level i.e., error) by an user
        LogLevelChanged 
      "  
   
    REVISION      "201704260000Z"
    DESCRIPTION
      "Added trap no 1361, which informs about Logging Event IDs been disabled by an user
        DisabledEventIDs 
      "  
        
    REVISION      "201704150000Z"
    DESCRIPTION
      " Added Traps 1349 to 1356 for critical events for Smart Licensing
        starSmartLicenseServiceOOC,
        starSmartLicenseServiceOOCClear,
        starSmartLicenseEvalMode,
        starSmartLicenseEvalModeClear,
        starSmartLicenseEvalModeExpire,
        starSmartLicenseEvalModeExpireClear,
        starSmartLicenseCSSMConntectionFail,
        starSmartLicenseCSSMConnectionFailClear
      "

    REVISION      "201702150000Z"
    DESCRIPTION
      "Hat heartbeat loss on the card w.r.t peer cards for DI platform
        starThreshHatHb5MinsLoss,
        starThreshClearHatHb5MinsLoss,
        starThreshHatHb60MinsLoss,
        starThreshClearHatHb60MinsLoss
      "  

    REVISION      "201601150000Z"
    DESCRIPTION
      " Added additional argument starSlotSerialNumber to applicable threshold port traps"
  
     REVISION      "201702270000Z"
     DESCRIPTION
       "Maximum Concurrent CLI Sessions enforcement on StarOS
         starGlobalCLISessionsLimit,
         starUserCLISessionsLimit
       "  

     REVISION      "201702150000Z"
     DESCRIPTION
       "Hat heartbeat loss on the card w.r.t peer cards for DI platform
         starThreshHatHb5MinsLoss,
         starThreshClearHatHb5MinsLoss,
         starThreshHatHb60MinsLoss,
         starThreshClearHatHb60MinsLoss
       "  

    REVISION      "201612220000Z"
    DESCRIPTION
       "Added trap nos. 1534, 1535 and 1536 with the following variables
         starDiameterVpnName,
         starDiameterRlfContext,
         starDiameterPeerName,
         starDiameterEndpointName,
         starDiameterRlfECode
         starDiameterRlfTps,
         starDiameterRlfDelayTolerance,
         starDiameterRlfQueuePercent,
         starDiameterDiamproxyInstance
       "
    REVISION      "201612200000Z"
      DESCRIPTION
       " DOS Attack & Decryption Fail Traps  added."
    REVISION      "201609160000Z"
      DESCRIPTION
       "Log Source (LS) log volume threshold is added."
    REVISION      "201608230000Z"
     DESCRIPTION
      "Added Management Card switchover due to HD Raid unrecoverable failure trap"
   REVISION      "201607270000Z"
    DESCRIPTION
    " Added additional argument starSlotSerialNumber to all related traps"
    REVISION      "201607040000Z"
     DESCRIPTION
      "Mark the unsupported traps to obsolete"
    REVISION      "201606230000Z"
     DESCRIPTION
      "Corrected the names of the traps in StarOS and Starent.my file"
   REVISION      "201606220000Z"
    DESCRIPTION
     "Added SI and DI keywords in Traps" 
   REVISION      "201605120000Z"
    DESCRIPTION
     "Added DDF Reload Trap" 
   
   REVISION      "201604180000Z"
    DESCRIPTION
    " Removed starThreshDiscRsn, and added correct object to starThreshSNXDisconnectReason and 
    starThreshClearSNXDisconnectReason"

   REVISION      "201604120000Z"
    DESCRIPTION
    " Streamlined all the numbers from 21.x to 17.x"

   REVISION      "201604120000Z"
    DESCRIPTION
    " Corrected Traps and MIB oid numbers "

   REVISION      "201604110000Z"
    DESCRIPTION
    " Corrected few trap numbers and  errors in mib file"
 
   REVISION      "201509140000Z"
    DESCRIPTION
    " Added trap no. 1312  with the following variables
            starStatFilesizeLimit,
            starStatFilesizeMeasured
    
      Added trap no. 1313  with the following variables
            starStatFilesizeLimit,
            starStatFilesizeMeasured
    "
    REVISION      "201509110000Z"
    DESCRIPTION
    " Removed  trap number 1191(starSEAGWServiceStart) and 1192(starSEAGWServiceStop) definition added"
    
    REVISION      "201411040000Z"
    DESCRIPTION
    " Removed  trap number 1533 and 1534 and replaced with 1290 and 1291 supporting code"
    REVISION      "201410300000Z"
    DESCRIPTION
    " Added  trap number 1288 and 1289 supporting code"

    REVISION      "201410080000Z"
    DESCRIPTION
    " Added trap no. 1282 with the following variables
            starGTPCRLFSessMgrInst,
            starGTPCRLFVPNName,
            starGTPCRLFVPNId,
            starGTPCRLFContextName,
            starGTPCRLFCurrAppTPS
                        
      Added trap no. 1283 with the following variables
            starGTPCRLFSessMgrInst,
            starGTPCRLFVPNName,
            starGTPCRLFVPNId,
            starGTPCRLFContextName,
            starGTPCRLFCurrAppDelayTol

      Added trap no. 1284 with the following variables
            starGTPCRLFSessMgrInst,
            starGTPCRLFVPNName,
            starGTPCRLFVPNId,
            starGTPCRLFContextName,

      Added trap no. 1285 with the following variables
            starGTPCRLFSessMgrInst,
            starGTPCRLFVPNName,
            starGTPCRLFVPNId,
            starGTPCRLFContextName,
    "
    REVISION      "201408040000Z"
    DESCRIPTION
    " Added starNpudriverECCError trap supporting code"  
    REVISION      "201407230000Z"
    DESCRIPTION
    " removing the extra 1533 and 1534 traps"
    REVISION      "201407160000Z"
    DESCRIPTION
    " Added starNpudriverECCError trap(reserving the trap id) at 1281"
    REVISION      "201406110000Z"
    DESCRIPTION
    " Added Severity in starChassisCrashListFull Traps"          
    REVISION      "201405080000Z"
    DESCRIPTION
    " Added starBFDSessUp, starBFDSessDown and starSRPSwitchoverOccured Traps"          
    REVISION      "201404250000Z"
    DESCRIPTION
    " Added MME Related threshold traps from 440 to 445"
    REVISION      "201302200000Z"
    DESCRIPTION
    " Removing SGSN substring from trap number 1219 and 1220"
    REVISION      "201302200000Z"
    DESCRIPTION
    " Extended starChassisType to support KVM QvPC-SI chassis"
    REVISION      "201312060000Z"
    DESCRIPTION
    " Corrected IPv6 from IPv4 to trap number 1200"
    REVISION      "201312050000Z"
    DESCRIPTION
        "Fixed following issues
        1. Revision not in reverse chronological order
        2. not-accessible starent Index objects are modified to 
           MAX-ACCESS  accessible-for-notify for those sent in trap"
    REVISION      "201311220000Z"
    DESCRIPTION
    "Added two MIBs (starMRMEServiceStart, starMRMEServiceStop) for MRME service
     starMRMEServiceStart- starentTraps 1264
     starMRMEServiceStop-  starentTraps 1265
    Added two MIBs (starThreshPerServiceSAMOGSessions,
    starThreshClearPerServiceSAMOGSessions) for per service samog-service
     starThreshPerServiceSAMOGSessions- starentTraps 519
     starThreshClearPerServiceSAMOGSessions -  starentTraps 520"
    REVISION      "201310040000Z"
    DESCRIPTION
        "Changed following notification names
            starThreshAAAAcctArchiveQueue-1,
            starThreshClearAAAAcctArchiveQueue-1,
            starThreshAAAAcctArchiveQueue-2,
            starThreshClearAAAAcctArchiveQueue-2,
            starThreshAAAAcctArchiveQueue-3,
            starThreshClearAAAAcctArchiveQueue-3
        to
            starThreshAAAAcctArchiveQueue1,
            starThreshClearAAAAcctArchiveQueue1,
            starThreshAAAAcctArchiveQueue2,
            starThreshClearAAAAcctArchiveQueue2,
            starThreshAAAAcctArchiveQueue3,
            starThreshClearAAAAcctArchiveQueue3.
            
        Added , in starLIRcvryErrType object.
        
        Changed StarUDPPortNum object to starUDPPortNum object in
        following notifications:
            starECSreaddressServerDown,
            starECSreaddressServerUp.
            
        Added definition for starMMEInitialDisallowReason object.
        
        Added new number for QvPC-SI platform in starChassisType object."
    REVISION      "201309270000Z"
    DESCRIPTION
    " Added missing object starFractE1TribTimeslots to starSDHFractE1LMIUp 
      notification , changed MAX-ACCESS to accessible-for-notify from
      not-accessible for the following objects  
         starFractE1TribSlot,
         starFractE1TribPort,
         starFractE1TribPath,
         starFractE1TribTug2, 
         starFractE1TribTu12  
      and moved starFractE1TribBundNum object to obsolete state."
        
    REVISION      "201309250000Z"
    DESCRIPTION
        "Change starSlotPort to storSlotNum in ApsChannelMismatch trap 1150"
    REVISION      "201307230000Z"
    DESCRIPTION
        "Replaced underscore sign with hyphen from starServiceType enum "
    REVISION      "201307150000Z"
    DESCRIPTION
        "Modified SEVERITY from ERROR to MAJOR for following traps:
        starPortDown,
        starSRPConnDown,
        starLAGGroupDown.
        
        Changed starPortSlot, starPortNum, starContextName and starSRPIpAddress
        objects access to accessible-for-notify."
    REVISION      "201307100000Z"
    DESCRIPTION
        "Changed the name of trap starThreshNAPTPortChunks to starThreshNATPortChunks and 
        starThreshClearNAPTPortChunks to starThreshClearNATPortChunks"
    REVISION      "201306260000Z"
    DESCRIPTION
    "Changed the APS related traps according to the implementation present in trap_api.c
    following traps are modified:
    starApsCommandSuccess,
    starApsCommandFailure,
    starApsSwitchSuccess,
    starApsSwitchFailure,
    starApsModeMismatch,
    starApsChannelMismatch,
    starApsByteMismatch,
    starApsFeProtLineFailure,
    starApsLossOfRedundancy,
    starApsLossOfRedundancyClear."

    REVISION      "201306110000Z"
    DESCRIPTION
        "Changed object type from starContextName to starCLIContext for the 
        following traps:

        starLocalUserAdded, 
        starLocalUserRemoved, 
        starOsShellAccessed, 
        starTestModeEntered, 
        starLicenseFeaturesModified, 
        starHiddenAccessEnabled, 
        starHiddenAccessDisabled." 
    REVISION      "201306040000Z"
    DESCRIPTION
            " Added the missing objects and modified the summary field for 
             starTechSuppPasswdChanged trap"
    REVISION      "201305240000Z"
    DESCRIPTION
            "Corrected starChassisCrashListFull description section"

    REVISION      "201305220000Z"
    DESCRIPTION   "changed starEGTPInterfaceType Enum in trap number 1112"
    REVISION      "201305070000Z"
    DESCRIPTION
    "changed starEGTPInterfaceType Enum
    changed STATE and SEVERITY fields for All APS, 
    related notifications."

    REVISION      "201304250001Z"
    DESCRIPTION
        "Deprecated following traps
         starCardSPCSwitchoverStart,
         starCardSPCSwitchoverComplete,
         starCardSPCSwitchoverFailed
         starCardPACMigrateStart,
         starCardPACMigrateComplete,
         starCardPACMigrateFailed,

         Added following traps for above trap as respective replacement
         starCardSwitchoverStart,
         starCardSwitchoverComplete,
         starCardSwitchoverFailed,
         starCardMigrateStart,
         starCardMigrateComplete,
         starCardMigrateFailed"
    REVISION      "201304250000Z"
    DESCRIPTION
    "Added two MIBs (starSAMOGServiceStart, starSAMOGServiceStop) for SAMOG service.
        starSAMOGServiceStart- starentTraps 1251
        starSAMOGServiceStop-  starentTraps 1252"
    REVISION      "201304180000Z"
    DESCRIPTION
        "Changed SUMMARY clause for starLongDurTimerExpiry notification.
        
        Changed MAX-ACCESS to accessible-for-notify for following objects:
        starSubMSID,
        starSubName,
        starSubTimerDuration,
        starSubLongDurTimeoutAction,
        starSubSetupTime,
        starSubHomeAddr,
        starSubHomeAddrv6."
    REVISION      "201304160000Z"
    DESCRIPTION
    "changed STATE and SEVERITY fields for starSDHPathHopUp, 
    starSDHE1TribUp and starSDHFractE1LMIDown notifications."
    REVISION      "201304090000Z"
    DESCRIPTION
	"Added trap no. 1251 with the following variables
        starPMIPVpnName,
        starPMIPServName,
        starPMIPSelfAddrType,
        starPMIPSelfAddr,
        starPMIPPeerAddrType,
        starPMIPPeerAddr,
        starPMIPPeerOldRstCnt,
        starPMIPPeerNewRstCnt,
        starPMIPPeerSessCnt,
        starPMIPFailureReason
        
        Added trap no. 1252 with the following variables
        starPMIPVpnName,
        starPMIPServName,
        starPMIPSelfAddrType,
        starPMIPSelfAddr,
        starPMIPPeerAddrType,
        starPMIPPeerAddr"
    REVISION      "201304050000Z"
    DESCRIPTION
	" Added the following flags in APS related traps"

    REVISION      "201304040000Z"
    DESCRIPTION
    "changed SEVERITY level from INFORMATIONAL to WARNING for 
    starSGSNRMMemWarn notification."

    REVISION      "201303260000Z"
    DESCRIPTION
	"Added trap no. 1177, with the following variables
        starSlotNum,
        starCardType,
        starPortSlot"
    REVISION      "201303180000Z"
    DESCRIPTION
        "Modified starPCFUnreachable description section
         Updated correct object name starEISServerVPNName in 
         starEISServerAlive
         starEISServerDead traps.
         Added starPCFReachable trap support"
    REVISION      "201303110000Z"
    DESCRIPTION
        "Changed starFanNum range in SYNTAX and MAX-ACCESS.
        Added starFanLocation ASR5500 fan location details.
        Changed SUMMARY clause for following traps 
            starFanFailed,
            starFanRemoved,
            starFanInserted,"

    REVISION      "201303060000Z"
    DESCRIPTION
        "Changed SYNTAX clause from Integer32 to Gauge32 for
        following objects:
        starCPUUser,
        starCPUSystem,
        starCPUIdle,
        starCPUIO,
        starCPUIRQ,
        starCPUMemUsed,
        starCPUMemCached

        Changed SYNTAX clause from Integer32 to Gauge32 and also
        changed range for following objects:
        starCPULoad1Min,
        starCPULoad5Min,
        starCPULoad15Min,
        starCPUNumProcesses."

    REVISION      "201302280000Z"
    DESCRIPTION
        "Added context name to the OBJECTS and updated ARGUMENTS field for the following traps:

        starLocalUserAdded,
        starLocalUserRemoved,
        starOsShellAccessed,
        starTestModeEntered,
        starLicenseFeaturesModified,
        starHiddenAccessEnabled,
        starHiddenAccessDisabled"

    REVISION      "201302260000Z"
    DESCRIPTION
        "Changed starThreshMeasuredPct SYNTAX from Integer32 to Gauge32.

        Changed starPortNum object range.

        Changed SUMMARY clause in starM3UAPCUnavailable and
        starM3UAPCAvailable traps.

        Changed objects from starThreshInt and starThreshMeasuredInt to
        starThreshPct and starThreshMeasuredPct and also changed SUMMARY
        and ARGUMENTS clauses in following traps:

        starThreshIPPoolAvail,
        starThreshClearIPPoolAvail,
        starThreshIPPoolHold,
        starThreshClearIPPoolHold,
        starThreshIPPoolUsed,
        starThreshClearIPPoolUsed,
        starThreshIPPoolRelease,
        starThreshClearIPPoolRelease,
        starThreshIPPoolFree,
        starThreshClearIPPoolFree,
        starThreshNATPortChunks,
        starThreshClearNATPortChunks,
        starThreshPortHighActivity,
        starThreshClearPortHighActivity,
        starThreshTpoDnsFailure,
        starThreshClearTpoDnsFailure,
        starThreshDnsLookupFailure,
        starThreshClearDnsLookupFailure,
        starThreshBGPRoutes,
        starThreshClearBGPRoutes.
   
        Changed SUMMARY and ARGUMENTS clauses in following traps:
        starThreshCPUUtilization,
        starThreshClearCPUUtilization,
        starThreshCPUUtilization10Sec,
        starThreshClearCPUUtilization10Sec,
        starThreshCPUMemUsage,
        starThreshClearCPUMemUsage,
        starThreshCPUOrbsWarn,
        starThreshClearCPUOrbsWarn,
        starThreshCPUOrbsCritical,
        starThreshClearCPUOrbsCritical,
        starThreshCPUCryptoCoresUtilization,
        starThreshClearCPUCryptoCoresUtilization,
        starThreshLicense,
        starThreshClearLicense,
        starThreshPortRxUtil,
        starThreshClearPortRxUtil,
        starThreshPortTxUtil,
        starThreshClearPortTxUtil,
        starThreshAAAAuthFailRate,
        starThreshClearAAAAuthFailRate,
        starThreshAAAAcctFailRate,
        starThreshClearAAAAcctFailRate,
        starThreshAAARetryRate,
        starThreshClearAAARetryRate,
        starThreshAAAMgrQueue,
        starThreshClearAAAMgrQueue,
        starThreshAAAAcctArchiveQueue-1,
        starThreshClearAAAAcctArchiveQueue-1,
        starThreshAAAAcctArchiveQueue-2,
        starThreshClearAAAAcctArchiveQueue-2,
        starThreshAAAAcctArchiveQueue-3,
        starThreshClearAAAAcctArchiveQueue-3,
        starThreshRPSetupFailRate,
        starThreshClearRPSetupFailRate,
        starThreshPPPSetupFailRate,
        starThreshClearPPPSetupFailRate,
        starThreshStorageUtilization,
        starThreshClearStorageUtilization,
        starThreshIPSECIKEFailRate,
        starThreshClearIPSECIKEFailRate,
        starThreshEPDGIKEV2SetupFailureRate,
        starThreshClearEPDGIKEV2SetupFailureRate,
        starThreshNPUUtilization,
        starThreshClearNPUUtilization,
        starThreshDiameterRetryRate,
        starThreshClearDiameterRetryRate,
        starThreshSystemCapacity,
        starThreshClearSystemCapacity,
        starThreshEDRFileSpace,
        starThreshClearEDRFileSpace,
        starThreshCDRFileSpace,
        starThreshClearCDRFileSpace,
        starThreshCardTemperatureNearPowerOffLimit,
        starThreshClearCardTemperaturePowerOffLimit."
    REVISION      "201212040000Z"
    DESCRIPTION
        "Changed SYNTAX clause for starPortNum and starRedundantPortNum objects"
    REVISION      "201209250000Z"
    DESCRIPTION
    "Changed starSlotMappingTable table DESCRIPTION."
    REVISION      "201207230000Z"
    DESCRIPTION
        "Removed starSGSNAllocated and starSGSNUsed obeects and added
        starThreshInt and starThreshMeasuredInt objects for starSGSNRMCPUWarn,
        starSGSNRMCPUWarnClear, starSGSNRMMemWarn, starSGSNRMMemWarnClear,
        starRMCPUOver, starRMCPUOverClear, starSGSNRMMemOver and
        starSGSNRMMemOverClear."
    REVISION      "201207130000Z"
    DESCRIPTION
        "Changed object from starServiceVpnID to starServiceVpnName and
        arguments macro in starSessionRejectNoResource Notification.
        
        Added commas(,) in ARGUMENTS field of starServiceLossLCClear
        Trap definition.
    
        Added additional object starCPUSlot and starCPUNumber in
        starThreshCPUOrbsWarn, starThreshClearCPUOrbsWarn,
        starThreshCPUOrbsCritical and starThreshClearCPUOrbsCritical traps."
    REVISION      "201207090000Z"
    DESCRIPTION
	"starSAEGWSessThreshold and starSAEGWSessThresholdClear Notification 
    objects have been added.
    Fixed starServiceLossLCClear ARGUMENTS field information."
    REVISION      "201205150000Z"
    DESCRIPTION
    "ASR5500 slot types are added in StarentSlotType"
    REVISION      "201204130000Z"
    DESCRIPTION
	"The Notifications starThreshPortSpecRxUtil,starThreshClearPortSpecRxUtil,
    starThreshPortSpecTxUtil,starThreshClearPortSpecTxUtil has been moved to 
    deprecated state."
    REVISION      "201204050000Z"
    DESCRIPTION
	"The object starPowerFilterUnitFailed has been moved to deprecated state"
    REVISION      "201110140000Z"
    DESCRIPTION
	"The latest version of this MIB module"
    ::= { enterprises 8164 }

-- Textual Conventions

StarentSlotType ::= TEXTUAL-CONVENTION
    STATUS current
    DESCRIPTION
	"Describes the type of a slot.  Each slot in the chassis is build to contain
         specific type(s) of cards.  Only a card of one of the appropriate types
         can be put into a specific slot."
    SYNTAX INTEGER {
	       unknown(1),
               pactac(2),
	       spc(3),
	       lc(4),
               rcc(5),
	       spio(6)
           }

StarentCardType ::= TEXTUAL-CONVENTION
    STATUS current
    DESCRIPTION
	"Describes the type of a card.  Each type represents a physically different
         card which would have a unique part number."
         SYNTAX INTEGER {
             none(1),
             unknown(2),
             spc(3),
             pac(4),
             spio(5),
             rcc(6),
             lceth(7),
             lcgeth(8),
             lcds3(9),
             tac(10),
             lcoc3(11),
             lcoc12(12),
             smc(13),
             psc(14),
             lcqgeth(15),
             lctgeth(16),
             vmc(17),
             vpc(18),
             vlceth1p(19),
             lcgeth2(20),
             lceth2(21),
             psc2(22),
             psc3(23),
             pscA(24),       -- Packet Services Card A
             ppc(25),        -- Packet Processing Card
             lcchan3p2(26),  -- Channelized Line card 2 Port
             lcchan3p4(27),  -- Channelized Line card 4 Port
             fanctrl6(28),   -- Fan control revision 6
             vioc(29),       -- Virtual I/O Card
             gpdsp(30),      -- GP-DSP Daughter Card
             xme(31),        -- XME Daughter Card
             vop(32),        -- VOP Daughter Card
             edc(33),        -- EDC card
             mio(34),        -- Management & I/O Card
             mio10g10p(35),  -- Management & 10x10Gb I/O Card
             mio10g20p(36),  -- Management & 20x10Gb I/O Card
             mio40g2p(37),   -- Management & 2x40Gb I/O Card
             mio40g4p(38),   -- Management & 4x40Gb I/O Card
             mio40g12p(39),  -- Management & 12x40Gb I/O Card
             miodc(40),      -- MIO Daughter Card
             fsc(41),        -- Fabric Card
             dpc(42),        -- Data Processing Card
             mdpc(43),       -- M Data Processing Card
             dpcdc(44),      -- DPC Daughter Card
             ssc(45),        -- System Status Card
             voc(46),        -- Virtual Card
             cfc(47),        -- Control Function Virtual Card
             sfc1p(48),      -- 1-Port Service Function Virtual Card
             sfc2p(49),      -- 2-Port Service Function Virtual Card
             sfc3p(50),      -- 3-Port Service Function Virtual Card
             sfc4p(51),      -- 4-Port Service Function Virtual Card
             dpc2(52),       -- Data Processing Card 2
	     mio2(53)	     -- Management & I/O Card 2
         }

StarentVersionNum ::= TEXTUAL-CONVENTION
    DISPLAY-HINT "256a"
    STATUS current
    DESCRIPTION
        " "
    SYNTAX OCTET STRING (SIZE (0..256))

StarRelayState ::= TEXTUAL-CONVENTION
    STATUS current
    DESCRIPTION
        "The state of a Central Office (CO) relay."
    SYNTAX INTEGER {
               off(1),
               on(2),
	       unknown(3)
           }

StarLongDurTimeoutAction ::= TEXTUAL-CONVENTION
    STATUS current
    DESCRIPTION
        "The action taken by the system upon detection of a long-duration session"
    SYNTAX INTEGER {
		 unknown(0),
		 detection(1),
	         disconnection(2),
		 notapplicable(3),
		 dormantdisconnection(4),
		 dormantdetection(5)
               }

StarShortName ::= TEXTUAL-CONVENTION
    DISPLAY-HINT "32a"
    STATUS current
    DESCRIPTION
        "A short identification string.  Follows the same conventions
         as the DisplayString TEXTUAL-CONVENTION."
    SYNTAX OCTET STRING (SIZE (1..32))

StarShortID ::= TEXTUAL-CONVENTION
    DISPLAY-HINT "17a"
    STATUS current
    DESCRIPTION
        "An abbreviated form for identifying a service, composed of the first 8 characters
	 of the context name, and the first 8 characters of a service name, seperated by (:)"
    SYNTAX OCTET STRING (SIZE (1..17))

StarMediumID ::= TEXTUAL-CONVENTION
    DISPLAY-HINT "25a"
    STATUS current
    DESCRIPTION
        "An abbreviated form for identifying a context-specific object, composed of the first 8 characters
	 of the context name, and the first 16 characters of the object name, seperated by (:)"
    SYNTAX OCTET STRING (SIZE (1..25))

StarENBID ::= TEXTUAL-CONVENTION
    DISPLAY-HINT "16a"
    STATUS current
    DESCRIPTION
	"An eNodeB identifier in the form aaa:bbb:cccccccc"
    SYNTAX OCTET STRING (SIZE (1..16))

StarQOSTPAction ::= TEXTUAL-CONVENTION
    STATUS current
    DESCRIPTION
	"Traffic Policing Action"
    SYNTAX INTEGER {
		unknown(0),
		notapplicable(1),
		transmit(2),
		drop(3),
		loweripprecedence(4)
		}

 StarOSPFNeighborState ::= TEXTUAL-CONVENTION
     STATUS current
     DESCRIPTION
 	"OSPF Neighbore State"
     SYNTAX INTEGER {
 		unknown(0),
 		down(1),
 		attempt(2),
 		init(3),
 		twoway(4),
 		exstart(5),
 		exchange(6),
 		loading(7),
 		full(8)
 		}

starentMIBObjects OBJECT IDENTIFIER ::= { starentMIB 1 }

-- Chassis table

starentChassis OBJECT IDENTIFIER ::= { starentMIBObjects 1 }

starChassisCriticalCO OBJECT-TYPE
    SYNTAX     StarRelayState
    MAX-ACCESS read-only
    STATUS     current
    DESCRIPTION
        "The current state of the Critical Central Office (CO) relay"
    ::= { starentChassis 1 }

starChassisMajorCO OBJECT-TYPE
    SYNTAX     StarRelayState
    MAX-ACCESS read-only
    STATUS     current
    DESCRIPTION
        "The current state of the Major Central Office (CO) relay"
    ::= { starentChassis 2 }

starChassisMinorCO OBJECT-TYPE
    SYNTAX     StarRelayState
    MAX-ACCESS read-only
    STATUS     current
    DESCRIPTION
        "The current state of the Minor Central Office (CO) relay"
    ::= { starentChassis 3 }

starChassisAction OBJECT-TYPE
    SYNTAX     INTEGER {
		   noaction(1),
                   aco(2),
                   reset(3)
               }
    MAX-ACCESS read-write
    STATUS     current
    DESCRIPTION
        "Trigger to perform certain system-wide operations.

         noaction(1) performs no operation.  It is the normal value received
         when this attribute is read.

         aco(2) triggers the Alarm Cut-Off, which shuts off all of the
         Central Office (CO) audible/visual relays.

         reset(3) triggers a system-wide restart.  It will completely
         disrupt service on the device."
    ::= { starentChassis 5 }

starTimeTicks OBJECT-TYPE
    SYNTAX     Unsigned32
    MAX-ACCESS read-only
    STATUS     current
    DESCRIPTION
        "Time ticks since the Epoch"
    ::= { starentChassis 6 }

starChassisAudibleAlarm OBJECT-TYPE
    SYNTAX     StarRelayState
    MAX-ACCESS read-only
    STATUS     current
    DESCRIPTION
        "The current state of the chassis Audible Alarm"
    ::= { starentChassis 7 }

starChassisUTCTime OBJECT-TYPE
    SYNTAX     DateAndTime
    MAX-ACCESS read-only
    STATUS     current
    DESCRIPTION
	"The current time on the chassis, in UTC format"
    ::= { starentChassis 8 }

starChassisLocalTime OBJECT-TYPE
    SYNTAX     DateAndTime
    MAX-ACCESS read-only
    STATUS     current
    DESCRIPTION
	"The current time on the chassis, converted to the local timezone"
    ::= { starentChassis 9 }

starChassisType OBJECT-TYPE
    SYNTAX     INTEGER {
               unknown(0),
	       st16(1),
               st40(2),
               xt2(3),
               st20(4),
	           asr5000(5),
	           asr5500(6),
               ssi(7),
	       ssi-kvm-guest(8),
	       ssi-kvm-vsm-guest(9),
	       qvpc-di(10)
             }
    MAX-ACCESS read-only
    STATUS     current
    DESCRIPTION
       "The type of physical chassis"
       ::= { starentChassis 10 }

starChassisDescription OBJECT-TYPE
    SYNTAX     DisplayString
    MAX-ACCESS read-only
    STATUS     current
    DESCRIPTION
       "A brief description of the chassis"
       ::= { starentChassis 11 }

starChassisSWRevision OBJECT-TYPE
    SYNTAX DisplayString
    MAX-ACCESS read-only
    STATUS current
    DESCRIPTION
       "The software revision running on the chassis"
       ::= { starentChassis 12 }

starChassisPeakCpuUsage OBJECT-TYPE
    SYNTAX      Integer32(1..10000)
    UNITS       "percentage times 100"
    MAX-ACCESS  read-only
    STATUS      current
    DESCRIPTION

    "Percentage of the system level peak cpu usage.starChassisPeakCpuUsage 
    is the percentage value times 100; for example,2.3% would be represented as 230"
       ::= { starentChassis 13 }

starChassisPeakMemoryUsage OBJECT-TYPE
    SYNTAX      Integer32(1..2097152)
    UNITS       "KB"
    MAX-ACCESS  read-only
    STATUS      current
    DESCRIPTION
       "The system level peak memory usage, in kilobytes, 
       rounded down (i.e. 1023 bytes = 0 kilobytes)"
       ::= { starentChassis 14}
       
-- Slot table

starentSlots OBJECT IDENTIFIER ::= { starentMIBObjects 2 }

starSlotTable OBJECT-TYPE
    SYNTAX  SEQUENCE OF StarSlotEntry
    MAX-ACCESS  not-accessible
    STATUS  current
    DESCRIPTION
	    "A table containing information on all of the slots"
    ::= { starentSlots 1 }

starSlotEntry OBJECT-TYPE
    SYNTAX  StarSlotEntry
    MAX-ACCESS  not-accessible
    STATUS  current
    DESCRIPTION
            "Information about a particular slot"
    INDEX   { starSlotNum }
    ::= { starSlotTable 1 }

StarSlotEntry ::=
    SEQUENCE {
        starSlotNum	        	Integer32,
	starSlotType            	StarentSlotType,
        starCardType            	StarentCardType,
	starCardOperState       	INTEGER,
        starCardAdminState              INTEGER,
        starCardRevision        	StarentVersionNum,
	starCardLastStateChange 	DateAndTime,
	starCardMode                    INTEGER,
	starCardPacStandbyPriority      Gauge32,
        starCardHaltIssued              INTEGER,
	starCardLock	        	INTEGER,
	starCardRebootPending   	INTEGER,
	starCardUsable                  INTEGER,
	starCardSinglePOF		INTEGER,
	starCardAttachment		INTEGER,
	starCardTemperature		Gauge32,
	starSlotVoltage1dot5		Gauge32,
	starSlotVoltage1dot5LowThresh	Gauge32,
	starSlotVoltage1dot5HighThresh	Gauge32,
	starSlotVoltage1dot8		Gauge32,
	starSlotVoltage1dot8LowThresh	Gauge32,
	starSlotVoltage1dot8HighThresh	Gauge32,
	starSlotVoltage2dot5		Gauge32,
	starSlotVoltage2dot5LowThresh	Gauge32,
	starSlotVoltage2dot5HighThresh	Gauge32,
	starSlotVoltage3dot3		Gauge32,
	starSlotVoltage3dot3LowThresh	Gauge32,
	starSlotVoltage3dot3HighThresh	Gauge32,
	starSlotVoltage5dot0		Gauge32,
	starSlotVoltage5dot0LowThresh	Gauge32,
	starSlotVoltage5dot0HighThresh	Gauge32,
	starSlotNumPorts                Gauge32,
	starSlotAction                  INTEGER,
	starSlotVoltageState            INTEGER,
	starSlotNumCPU                  Integer32,
	starSlotPartNumber              DisplayString,
	starSlotPartRevision		DisplayString,
	starSlotSerialNumber		DisplayString,
	starSlotCLEICode		DisplayString,
	starSlotCiscoModelName		DisplayString,
	starSlotCiscoHardwareRev	DisplayString,
	starSlotCiscoSerialNumber	DisplayString,
	starDeviceNum			Integer32,
	starSerdesNum			Integer32,
        starDdfDev                      INTEGER
    }

starSlotNum OBJECT-TYPE
    SYNTAX  Integer32(1..48)
    MAX-ACCESS  accessible-for-notify
    STATUS  current
    DESCRIPTION
	"The slot number"
    ::= { starSlotEntry 1 }

starSlotType OBJECT-TYPE
    SYNTAX  StarentSlotType
    MAX-ACCESS  read-only
    STATUS  current
    DESCRIPTION
	"The type of the slot."
    ::= { starSlotEntry 2 }

starCardType OBJECT-TYPE
    SYNTAX  StarentCardType
    MAX-ACCESS  read-only
    STATUS  current
    DESCRIPTION
        "The type of the card which is plugged into a slot"
    ::= { starSlotEntry 3 }

starCardOperState OBJECT-TYPE
    SYNTAX  INTEGER {
		unknown(1),
                empty(2),
		offline(3),
                booting(4),
	 	ready(5),
                standby(6),
		active(7),
		migratefrom(8),
		migrateto(9),
                starting(10),
                initializing(11),
                secondary(12)
            }
    MAX-ACCESS  read-only
    STATUS      current
    DESCRIPTION
        "The current operational state of the card"
    ::= { starSlotEntry 4 }

starCardAdminState OBJECT-TYPE
    SYNTAX      INTEGER {
		  unknown(1),
		  enabled(2),
		  disabled(3)
	        }
    MAX-ACCESS  read-only
    STATUS      current
    DESCRIPTION
	"The administrative state of the card"
    ::= { starSlotEntry 5 }

starCardRevision OBJECT-TYPE
    SYNTAX      StarentVersionNum
    MAX-ACCESS  read-only
    STATUS      current
    DESCRIPTION
        "The revision number of the card that is physically present in this slot"
    ::= { starSlotEntry 6 }

starCardLastStateChange OBJECT-TYPE
    SYNTAX      DateAndTime
    MAX-ACCESS  read-only
    STATUS      current
    DESCRIPTION
        "The time when the last state change occurred for this row.  A manager
         could poll this variable to determine if information has changed."
    ::= { starSlotEntry 7 }

starCardMode OBJECT-TYPE
    SYNTAX  INTEGER {
	        unknown(1),
                notapplicable(2),
                standby(3),
                active(4),
		activepac(5),
		activetac(6),
		activepsc(7),
		activevpc(8),
		activedpc(9)
            }
    MAX-ACCESS  read-only
    STATUS      current
    DESCRIPTION
        "The desired mode of the card.  This field is applicable only to slots which can contain
         PAC/PSC and TAC cards.  The active(4) value is obsolete and has been replaces with
         activepac(5) and activetac(6)"
    ::= { starSlotEntry 8 }

starCardPacStandbyPriority OBJECT-TYPE
    SYNTAX      Gauge32
    MAX-ACCESS  read-only
    STATUS      current
    DESCRIPTION
	" "
    ::= { starSlotEntry 9 }

starCardHaltIssued OBJECT-TYPE
    SYNTAX  INTEGER {
		notapplicable(1),
		yes(2),
		no(3)
            }
    MAX-ACCESS  read-only
    STATUS      current
    DESCRIPTION
        "Only applicable to SPC cards"
    ::= { starSlotEntry 10 }

starCardLock OBJECT-TYPE
    SYNTAX  INTEGER {
		unknown(1),
		locked(2),
		unlocked(3)
            }
    MAX-ACCESS  read-only
    STATUS      current
    DESCRIPTION
        "Identifies if the card lock is currently engaged.  A value of locked(2)
         means that the lock is engaged, and thus the card could not be removed
         from the chassis.  A value of unlocked(3) means that the lock is not
         engaged, and an operator could remove the card from the chassis.  A value
         of unknown(1) should represent that there is no card physically in
         the slot."
    ::= { starSlotEntry 11 }

starCardRebootPending OBJECT-TYPE
    SYNTAX  INTEGER {
		no(1),
		yes(2)
	    }
    MAX-ACCESS  read-only
    STATUS      current
    DESCRIPTION
        "Identifies if a reboot operation is currently pending for this card."
    ::= { starSlotEntry 12 }

starCardUsable OBJECT-TYPE
    SYNTAX  INTEGER {
		no(1),
		yes(2)
	    }
    MAX-ACCESS  read-only
    STATUS      current
    DESCRIPTION
        "Identifies if the card is currently usable."
    ::= { starSlotEntry 13 }

starCardSinglePOF OBJECT-TYPE
    SYNTAX      INTEGER {
		    notapplicable(1),
		    no(2),
		    yes(3)
                }
    MAX-ACCESS  read-only
    STATUS      current
    DESCRIPTION
        "Identifies if this card represents a single point of failure (POF).  A value
         of no(1) indicates that this card is supported by a redundant card which can
         take over in the event of a failure.  A value of yes(2) indicates that this
         card does not have a redundant partner, and that a failure of this card
         could result in service interruption."
    ::= { starSlotEntry 14 }

starCardAttachment OBJECT-TYPE
    SYNTAX      INTEGER {
		    connected(1),
		    unconnected(2)
                }
    MAX-ACCESS  read-only
    STATUS      current
    DESCRIPTION
        "Identifies if the card is currently attached to another card (a PAC/PSC attached
         to a line card, or visa versa, for example"
    ::= { starSlotEntry 15 }

starCardTemperature OBJECT-TYPE
    SYNTAX      Gauge32
    UNITS       "degrees Celcius"
    MAX-ACCESS  read-only
    STATUS      current
    DESCRIPTION
        "The temperature, in degrees Celcius, as measured on the card.  A value of 0
         indicates that the temperature cannot be read, or that the card is not
         present.  The maximum measurable temperature is 70 C"
    ::= { starSlotEntry 16 }

--
-- All of the "voltage"-related starSlot items are obsolete.  As systems evolved and different cards
-- have different internal voltages these values had less meaning.  The starSlotVoltageState
-- provides an overall state for the card.
--

starSlotVoltage1dot5 OBJECT-TYPE
    SYNTAX      Gauge32
    UNITS       "millivolts"
    MAX-ACCESS  read-only
    STATUS      obsolete
    DESCRIPTION
	"The current voltage, in millivolts, of the nominal 1.5V power supply.
         The working range for this card is the range defined by variables
         starSlotVoltage1dot5LowThresh and starSlotVoltage1dot5HighThresh.
         A value of 0 indicates that this voltage level is not present on this
         card, or that the card is not present.

	 This attribute is obsolete."
    ::= { starSlotEntry 20 }

starSlotVoltage1dot5LowThresh OBJECT-TYPE
    SYNTAX      Gauge32
    UNITS       "millivolts"
    MAX-ACCESS  read-only
    STATUS      obsolete
    DESCRIPTION
        "The voltage level, in millivolts, which is the lowest allowable value
         for the nominal 1.5V power supply.  A value of 0 indicates that there
         is no card present.

	 This attribute is obsolete."
    ::= { starSlotEntry 21 }

starSlotVoltage1dot5HighThresh OBJECT-TYPE
    SYNTAX      Gauge32
    UNITS       "millivolts"
    MAX-ACCESS  read-only
    STATUS      obsolete
    DESCRIPTION
        "The voltage level, in millivolts, which is the highest allowable value
         for the nominal 1.5V power supply.  A value of 0 indicates that there
         is no card present.

	 This attribute is obsolete."
    ::= { starSlotEntry 22 }

starSlotVoltage1dot8 OBJECT-TYPE
    SYNTAX      Gauge32
    UNITS       "millivolts"
    MAX-ACCESS  read-only
    STATUS      obsolete
    DESCRIPTION
	"The current voltage, in millivolts, of the nominal 1.8V power supply.
         The working range for this card is the range defined by variables
         starSlotVoltage1dot8LowThresh and starSlotVoltage1dot8HighThresh.
         A value of 0 indicates that this voltage level is not present on this
         card, or that the card is not present.

	 This attribute is obsolete."
    ::= { starSlotEntry 23 }

starSlotVoltage1dot8LowThresh OBJECT-TYPE
    SYNTAX      Gauge32
    UNITS       "millivolts"
    MAX-ACCESS  read-only
    STATUS      obsolete
    DESCRIPTION
        "The voltage level, in millivolts, which is the lowest allowable value
         for the nominal 1.8V power supply.  A value of 0 indicates that there
         is no card present.

	 This attribute is obsolete."
    ::= { starSlotEntry 24 }

starSlotVoltage1dot8HighThresh OBJECT-TYPE
    SYNTAX      Gauge32
    UNITS       "millivolts"
    MAX-ACCESS  read-only
    STATUS      obsolete
    DESCRIPTION
        "The voltage level, in millivolts, which is the highest allowable value
         for the nominal 1.8V power supply.  A value of 0 indicates that there
         is no card present.

	 This attribute is obsolete."
    ::= { starSlotEntry 25 }

starSlotVoltage2dot5 OBJECT-TYPE
    SYNTAX      Gauge32
    UNITS       "millivolts"
    MAX-ACCESS  read-only
    STATUS      obsolete
    DESCRIPTION
	"The current voltage, in millivolts, of the nominal 2.5V power supply.
         The working range for this card is the range defined by variables
         starSlotVoltage2dot5LowThresh and starSlotVoltage2dot5HighThresh.
         A value of 0 indicates that the voltage cannot be read, or that the
         card is not present.

	 This attribute is obsolete."
    ::= { starSlotEntry 26 }

starSlotVoltage2dot5LowThresh OBJECT-TYPE
    SYNTAX      Gauge32
    UNITS       "millivolts"
    MAX-ACCESS  read-only
    STATUS      obsolete
    DESCRIPTION
        "The voltage level, in millivolts, which is the lowest allowable value
         for the nominal 2.5V power supply.  A value of 0 indicates that there
         is no card present.

	 This attribute is obsolete."
    ::= { starSlotEntry 27 }

starSlotVoltage2dot5HighThresh OBJECT-TYPE
    SYNTAX      Gauge32
    UNITS       "millivolts"
    MAX-ACCESS  read-only
    STATUS      obsolete
    DESCRIPTION
        "The voltage level, in millivolts, which is the highest allowable value
         for the nominal 2.5V power supply.  A value of 0 indicates that there
         is no card present.

	 This attribute is obsolete."
    ::= { starSlotEntry 28 }

starSlotVoltage3dot3 OBJECT-TYPE
    SYNTAX      Gauge32
    UNITS       "millivolts"
    MAX-ACCESS  read-only
    STATUS      obsolete
    DESCRIPTION
	"The current voltage, in millivolts, of the nominal 3.3V power supply.
         The working range for this card is the range defined by variables
         starSlotVoltage3dot3LowThresh and starSlotVoltage3dot3HighThresh.
         A value of 0 indicates that the voltage cannot be read, or that the
         card is not present.

	 This attribute is obsolete."
    ::= { starSlotEntry 29 }

starSlotVoltage3dot3LowThresh OBJECT-TYPE
    SYNTAX      Gauge32
    UNITS       "millivolts"
    MAX-ACCESS  read-only
    STATUS      obsolete
    DESCRIPTION
        "The voltage level, in millivolts, which is the lowest allowable value
         for the nominal 3.3V power supply.  A value of 0 indicates that there
         is no card present.

	 This attribute is obsolete."
    ::= { starSlotEntry 30 }

starSlotVoltage3dot3HighThresh OBJECT-TYPE
    SYNTAX      Gauge32
    UNITS       "millivolts"
    MAX-ACCESS  read-only
    STATUS      obsolete
    DESCRIPTION
        "The voltage level, in millivolts, which is the highest allowable value
         for the nominal 3.3V power supply.  A value of 0 indicates that there
         is no card present.

	 This attribute is obsolete."
    ::= { starSlotEntry 31 }

starSlotVoltage5dot0 OBJECT-TYPE
    SYNTAX      Gauge32
    UNITS       "millivolts"
    MAX-ACCESS  read-only
    STATUS      obsolete
    DESCRIPTION
	"The current voltage, in millivolts, of the nominal 5.0V power supply.
         The working range for this card is the range defined by variables
         starSlotVoltage5dot0LowThresh and starSlotVoltage5dot0HighThresh.
         A value of 0 indicates that the voltage cannot be read, or that the
         card is not present.

	 This attribute is obsolete."
    ::= { starSlotEntry 32 }

starSlotVoltage5dot0LowThresh OBJECT-TYPE
    SYNTAX      Gauge32
    UNITS       "millivolts"
    MAX-ACCESS  read-only
    STATUS      obsolete
    DESCRIPTION
        "The voltage level, in millivolts, which is the lowest allowable value
         for the nominal 5.0V power supply.  A value of 0 indicates that there
         is no card present.

	 This attribute is obsolete."
    ::= { starSlotEntry 33 }

starSlotVoltage5dot0HighThresh OBJECT-TYPE
    SYNTAX      Gauge32
    UNITS       "millivolts"
    MAX-ACCESS  read-only
    STATUS      obsolete
    DESCRIPTION
        "The voltage level, in millivolts, which is the highest allowable value
         for the nominal 5.0V power supply.  A value of 0 indicates that there
         is no card present.

	 This attribute is obsolete."
    ::= { starSlotEntry 34 }

starSlotNumPorts OBJECT-TYPE
    SYNTAX      Gauge32
    MAX-ACCESS  read-only
    STATUS      current
    DESCRIPTION
        "Number of data ports on this card.  This value will be 0 for cards that
         do not contain ports, such as SPC/SMC/PAC/PSC/TAC cards, or for slots which do
         not contain a card.

	 This attribute is obsolete."
    ::= { starSlotEntry 35 }

starSlotAction OBJECT-TYPE
    SYNTAX     INTEGER {
		   noaction(1),
                   reset(2)
               }
    MAX-ACCESS read-write
    STATUS     current
    DESCRIPTION
        "Trigger to perform certain slot operations.

         noaction(1) performs no operation.  It is the normal value received
         when this attribute is read.

         reset(2) causes the slot to be reset"
    ::= { starSlotEntry 36 }

starSlotVoltageState OBJECT-TYPE
    SYNTAX     INTEGER {
                 unknown(0),
                 normal(1),
                 outofrange(2)
               }
    MAX-ACCESS read-only
    STATUS     current
    DESCRIPTION
       "The state of the voltage supplies on the card.  A value of unknown(0)
       means that the state cannot be identified; normal(1) represents a properly
       functioning card; outofrange(2) indicates that one or more voltage sources
       are not within their specified operating range."
    ::= { starSlotEntry 37 }

starSlotNumCPU OBJECT-TYPE
   SYNTAX     Integer32
   MAX-ACCESS read-only
   STATUS     current
   DESCRIPTION
      "The number of general-purpose CPUs on this card"
   ::= { starSlotEntry 38 }

starSlotPartNumber OBJECT-TYPE
   SYNTAX     DisplayString
   MAX-ACCESS read-only
   STATUS     current
   DESCRIPTION
      "The part number of this card"
   ::= { starSlotEntry 39 }

starSlotPartRevision OBJECT-TYPE
   SYNTAX     DisplayString
   MAX-ACCESS read-only
   STATUS     current
   DESCRIPTION
      "The revision number of this card"
   ::= { starSlotEntry 40 }

starSlotSerialNumber OBJECT-TYPE
   SYNTAX     DisplayString
   MAX-ACCESS read-only
   STATUS     current
   DESCRIPTION
      "The serial number of this card"
   ::= { starSlotEntry 41 }

starSlotCLEICode OBJECT-TYPE
   SYNTAX     DisplayString
   MAX-ACCESS read-only
   STATUS     current
   DESCRIPTION
      "The CLEI code of this card"
   ::= { starSlotEntry 42 }

starSlotCiscoModelName OBJECT-TYPE
   SYNTAX     DisplayString
   MAX-ACCESS read-only
   STATUS     current
   DESCRIPTION
      "Cisco-defined Product Identifier (PID).  The PID is an alphanumeric identifier used to
       identify specific Cisco product hardware, and may be up to 18 characters in length.

       starSlotCiscoModelName will be blank (zero characters) if no PID is available."
   ::= { starSlotEntry 43 }

starSlotCiscoHardwareRev OBJECT-TYPE
   SYNTAX     DisplayString
   MAX-ACCESS read-only
   STATUS     current
   DESCRIPTION
      "Cisco-defined Version Identifier (VID).  The VID is used to track the version of the
       Customer-Orderable Cisco Product Identifier (PID) [starSlotCiscoModelName].  The
       data convention for VID is 'V' followed by a two digit number.  VID numbering typically
       begins at 'V01' but can be initiated at a higher value.

       starSlotCiscoHardwareRev will be blank (zero characters) if no VID is available."
   ::= { starSlotEntry 44 }

starSlotCiscoSerialNumber OBJECT-TYPE
   SYNTAX     DisplayString
   MAX-ACCESS read-only
   STATUS     current
   DESCRIPTION
      "Cisco-defined Serial Number (SN).  The SN is an 11 character identifier used in conjunction
       with the Cisco Product Identifier (PID) [starSlotCiscoModelName] to identify a unique
       product or Field Replaceable Unit (FRU) of a product.


       starSlotCiscoSerialNumber will be blank (zero characters) if no VID is available."
   ::= { starSlotEntry 45 }

starDeviceNum OBJECT-TYPE
    SYNTAX  Integer32(1..4)
    MAX-ACCESS  accessible-for-notify
    STATUS  current
    DESCRIPTION
	"The device number"
    ::= { starSlotEntry 46 }

starSerdesNum OBJECT-TYPE
    SYNTAX  Integer32(0..127)
    MAX-ACCESS  accessible-for-notify
    STATUS  current
    DESCRIPTION
	"The serdes lane index number"
    ::= { starSlotEntry 47 }


-- Card Mapping Table

starentSlotMapping OBJECT IDENTIFIER ::= { starentMIBObjects 3 }

starSlotMappingTable OBJECT-TYPE
    SYNTAX     SEQUENCE OF StarSlotMappingEntry
    MAX-ACCESS not-accessible
    STATUS     current
    DESCRIPTION
        "A table identifying all of the slot mappings. This table
        is applicable only to starChassisType ASR5000 platform."
    ::= { starentSlotMapping 1 }

starSlotMappingEntry OBJECT-TYPE
    SYNTAX     StarSlotMappingEntry
    MAX-ACCESS not-accessible
    STATUS     current
    DESCRIPTION
        "Information about a particular slot mapping"
    INDEX      { starSlotMappingNum }
    ::= { starSlotMappingTable 1 }

StarSlotMappingEntry ::=
    SEQUENCE {
	starSlotMappingNum	Integer32,
	starSlotMappingType	INTEGER,
	starSlotMappingRCCNum   Integer32,
	starSlotMappingToSlot	Integer32
    }

starSlotMappingNum OBJECT-TYPE
    SYNTAX     Integer32(17..48)
    MAX-ACCESS not-accessible
    STATUS     current
    DESCRIPTION
        "The slot number.  This always represents a slot in the back of the chassis."
    ::= { starSlotMappingEntry 1 }

starSlotMappingType OBJECT-TYPE
    SYNTAX     INTEGER {
		    unknown(1),
                    none(2),
                    direct(3),
                    rcc(4),
                    cross(5)
               }
    MAX-ACCESS read-only
    STATUS     current
    DESCRIPTION
        "The type of the slot mapping.  The value none(1) represents that there is no mapping,
         which typically represents that there is no card present in this slot."
    ::= { starSlotMappingEntry 2 }

starSlotMappingRCCNum OBJECT-TYPE
    SYNTAX     Integer32(0..2)
    MAX-ACCESS read-only
    STATUS     current
    DESCRIPTION
        "Identifies which RCC card is responsible for this mapping.  This value is only
         valid if the value of starSlotMappingType is rcc(3)."
    ::= { starSlotMappingEntry 3 }

starSlotMappingToSlot OBJECT-TYPE
    SYNTAX     Integer32(1..16)
    MAX-ACCESS read-only
    STATUS     current
    DESCRIPTION
        "The slot number this slot is mapped to.  This always represents a slot in the
         front of the chassis"
   ::= { starSlotMappingEntry 4 }

-- Fan Table

starentFans OBJECT IDENTIFIER ::= { starentMIBObjects 4 }

starFanTable OBJECT-TYPE
    SYNTAX     SEQUENCE OF StarFanEntry
    MAX-ACCESS not-accessible
    STATUS     current
    DESCRIPTION
        "A table containing information on all of the fan controllers"
    ::= { starentFans 1 }

starFanEntry OBJECT-TYPE
    SYNTAX     StarFanEntry
    MAX-ACCESS not-accessible
    STATUS     current
    DESCRIPTION
        "Information about a particular fan controller"
    INDEX { starFanNum }
    ::= { starFanTable 1 }

StarFanEntry ::=
    SEQUENCE {
        starFanNum      Integer32,
        starFanLocation INTEGER,
        starFanStatus   Integer32,
        starFanSpeed    INTEGER
    }

starFanNum OBJECT-TYPE
    SYNTAX     Integer32(1..4)
    MAX-ACCESS accessible-for-notify
    STATUS     current
    DESCRIPTION
        "The fan controller number"
    ::= { starFanEntry 1 }

starFanLocation OBJECT-TYPE
    SYNTAX     INTEGER {
        upper(1),
        lower(2),
        lowerFront(3),
        lowerRear(4),
        upperFront(5),
        upperRear(6)
    }
    MAX-ACCESS read-only
    STATUS     current
    DESCRIPTION
        "The physical location of the fan controller"
    ::= { starFanEntry 2 }

starFanStatus OBJECT-TYPE
    SYNTAX     Integer32
    MAX-ACCESS read-only
    STATUS     current
    DESCRIPTION
        "A bitmask representing the status of the fan tray.
		0x01     All Fans Good
		0x02     Multiple Fans Bad
		0x04     Single Fan Bad
		0x08     HB Error
		0x10     COM A Error
		0x20     COM B Error
		0x40     COMM Error
		0x80	 Not Present
		0x100    Present
		0x200    Filter Clogged
	        0x400    Unknown

	 A normal, properly functioning fan tray would show 0x101 (257 decimal), meaning
	 it is present (0x100) and all fans are working (0x1)"
    ::= { starFanEntry 3 }

starFanSpeed OBJECT-TYPE
    SYNTAX     INTEGER {
		   unknown(1),
		   speed50(2),
		   speed55(3),
		   speed60(4),
		   speed65(5),
		   speed70(6),
		   speed75(7),
		   speed80(8),
		   speed85(9),
		   speed90(10),
		   speed95(11),
		   speed100(12)
               }
    MAX-ACCESS read-only
    STATUS     current
    DESCRIPTION
        "The speed of the fans controlled by this fan controller.
         The values represent the percentage that the speed is running relative
         to the maximum possible speed, speed100(12)"
    ::= { starFanEntry 4 }

-- log Table
-- Note that this table isn't expected to have an SNMP implementation; it is provided
-- to define Object Identifiers for use in log-related traps, which are implemented
-- This table may be useless, as we're not keeping on-disk logs except through syslogd
starentLogs OBJECT IDENTIFIER ::= { starentMIBObjects 5 }

starLogTable OBJECT-TYPE
    SYNTAX     SEQUENCE OF StarLogEntry
    MAX-ACCESS not-accessible
    STATUS     current
    DESCRIPTION
        "A table containing information about all of the system logs"
    ::= { starentLogs 1 }

starLogEntry OBJECT-TYPE
    SYNTAX     StarLogEntry
    MAX-ACCESS not-accessible
    STATUS     current
    DESCRIPTION
        "Information about a particular system log"
    INDEX { starLogName }
    ::= { starLogTable 1 }

StarLogEntry ::=
    SEQUENCE {
        starLogName     StarShortName,
        starLogCurSize  Gauge32,
        starLogMaxSize  Gauge32,
        starLogText     OCTET STRING
    }

starLogName OBJECT-TYPE
    SYNTAX     StarShortName
    MAX-ACCESS accessible-for-notify
    STATUS     current
    DESCRIPTION
        "The name of the system log"
    ::= { starLogEntry 1 }

starLogCurSize OBJECT-TYPE
    SYNTAX     Gauge32
    MAX-ACCESS read-only
    STATUS     current
    DESCRIPTION
        "The size, in bytes, of this log"
    ::= { starLogEntry 2 }

starLogMaxSize OBJECT-TYPE
    SYNTAX     Gauge32
    MAX-ACCESS read-only
    STATUS     current
    DESCRIPTION
        "The maximum size, in bytes, of this log"
    ::= { starLogEntry 3 }

starLogText OBJECT-TYPE
    SYNTAX     OCTET STRING (SIZE (1..512))
    MAX-ACCESS read-only
    STATUS     current
    DESCRIPTION
	"For use in LogMsg trap"
    ::= { starLogEntry 4 }

-- trap management, ala RFC-1224

starentAlertMan OBJECT IDENTIFIER ::= { starentMIBObjects 8 }
starentFeedback OBJECT IDENTIFIER ::= { starentAlertMan 1 }

starMaxAlertsPerTime OBJECT-TYPE
    SYNTAX     Unsigned32
    MAX-ACCESS read-only
    STATUS     current
    DESCRIPTION
        "The maximum number of SNMP Traps which will be sent within
         the time period specified by starWindowTime"
    ::= { starentFeedback 1 }

starWindowTime OBJECT-TYPE
    SYNTAX     Unsigned32
    UNITS      "seconds"
    MAX-ACCESS read-only
    STATUS     current
    DESCRIPTION
        "The amount of time within which no more than starMaxAlertsPerTime
         SNMP Traps will be sent."
    ::= { starentFeedback 2 }

starAlertSendingEnabled OBJECT-TYPE
    SYNTAX     TruthValue
    MAX-ACCESS read-only
    STATUS     current
    DESCRIPTION
        "Shows if SNMP traps are currently enabled or disabled.  Traps are disabled
         when more than starMaxAlertsPerTime traps are sent within the
         starWindowTime time period.  A value of true(1) indicates that traps
         will still be sent.  A value of false(2) indicates that traps are no
         longer being generated"
    ::= { starentFeedback 3 }

starentPolledLog OBJECT IDENTIFIER ::= { starentAlertMan 2 }

-- power table, provided for use in traps only

starentPower OBJECT IDENTIFIER ::= { starentMIBObjects 9 }

starPowerTable OBJECT-TYPE
    SYNTAX     SEQUENCE OF StarPowerEntry
    MAX-ACCESS not-accessible
    STATUS     current
    DESCRIPTION
        "A table containing information about all power filters"
    ::= { starentPower 1 }

starPowerEntry OBJECT-TYPE
    SYNTAX     StarPowerEntry
    MAX-ACCESS not-accessible
    STATUS     current
    DESCRIPTION
        "Information about a particular power filter"
    INDEX { starPowerNumber }
    ::= { starPowerTable 1 }

StarPowerEntry ::=
    SEQUENCE {
	starPowerNumber                INTEGER,
        starPowerState                 INTEGER
    }

starPowerNumber OBJECT-TYPE
    SYNTAX     INTEGER {
	           powerA(1),
                   powerB(2)
	       }
    MAX-ACCESS accessible-for-notify
    STATUS     current
    DESCRIPTION
        "The identifying number for this power filter."
    ::= { starPowerEntry 1 }

starPowerState  OBJECT-TYPE
    SYNTAX     INTEGER {
		   active(1),
		   failed(2),
		   notpresent(3)
               }
    MAX-ACCESS read-only
    STATUS     current
    DESCRIPTION
        "The state of the power filter.  The value active(1) means that the
         power filter is present and operational.  The value failed(2) means
         that the power filter is present, but not operational.  The value
         not-present(3) means that the power filter is not physically present
         in the system."
    ::= { starPowerEntry 2 }

-- CPU table

starentCPU OBJECT IDENTIFIER ::= { starentMIBObjects 10 }

starCPUTable OBJECT-TYPE
    SYNTAX     SEQUENCE OF StarCPUEntry
    MAX-ACCESS not-accessible
    STATUS     current
    DESCRIPTION
        "A table containing information about all CPUs"
    ::= { starentCPU 1 }

starCPUEntry OBJECT-TYPE
    SYNTAX     StarCPUEntry
    MAX-ACCESS not-accessible
    STATUS     current
    DESCRIPTION
        "Information about a particular CPU"
    INDEX { starCPUSlot, starCPUNumber }
    ::= { starCPUTable 1 }

StarCPUEntry ::=
    SEQUENCE {
	starCPUSlot             Integer32,
	starCPUNumber           Integer32,
	starCPUUser             Gauge32,
	starCPUSystem           Gauge32,
	starCPUIdle             Gauge32,
	starCPUIO               Gauge32,
	starCPUIRQ              Gauge32,
	starCPULoad1Min         Gauge32,
	starCPULoad5Min         Gauge32,
	starCPULoad15Min        Gauge32,
	starCPUMemTotal         Integer32,
	starCPUMemUsed          Gauge32,
	starCPUNumProcesses     Gauge32,
	starCPUMemCached        Gauge32,
  starCPUCoreNumber       Integer32
  }

starCPUSlot OBJECT-TYPE
    SYNTAX     Integer32(1..48)
    MAX-ACCESS accessible-for-notify
    STATUS     current
    DESCRIPTION
        "The slot number of the card holding this CPU"
    ::= { starCPUEntry 1 }

starCPUNumber OBJECT-TYPE
    SYNTAX     Integer32(0..3)
    MAX-ACCESS accessible-for-notify
    STATUS     current
    DESCRIPTION
        "The CPU number within this card.  Numbers begin at 0."
    ::= { starCPUEntry 2 }

starCPUUser OBJECT-TYPE
    SYNTAX     Gauge32(1..10000)
    UNITS      "percentage times 100"
    MAX-ACCESS read-only
    STATUS     current
    DESCRIPTION
        "Percentage of the CPU spent running user processes.
         starCPUUser is the percentage value times 100; for example,
         2.3% would be represented as 230."
    ::= { starCPUEntry 3 }

starCPUSystem OBJECT-TYPE
    SYNTAX     Gauge32(1..10000)
    UNITS      "percentage times 100"
    MAX-ACCESS read-only
    STATUS     current
    DESCRIPTION
        "Percentage of the CPU spent running system processes.
         starCPUSystem is the percentage value times 100; for example,
         2.3% would be represented as 230."
    ::= { starCPUEntry 4 }

starCPUIdle OBJECT-TYPE
    SYNTAX     Gauge32(1..10000)
    UNITS      "percentage times 100"
    MAX-ACCESS read-only
    STATUS     current
    DESCRIPTION
        "Percentage of the CPU spent idle.
         starCPUIdle is the percentage value times 100; for example,
         2.3% would be represented as 230."
    ::= { starCPUEntry 6 }

starCPUIO OBJECT-TYPE
    SYNTAX     Gauge32(1..10000)
    UNITS      "percentage times 100"
    MAX-ACCESS read-only
    STATUS     current
    DESCRIPTION
        "Percentage of the CPU spent running io processes.
         starCPUIo is the percentage value times 100; for example,
         2.3% would be represented as 230."
    ::= { starCPUEntry 7 }

starCPUIRQ OBJECT-TYPE
    SYNTAX     Gauge32(1..10000)
    UNITS      "percentage times 100"
    MAX-ACCESS read-only
    STATUS     current
    DESCRIPTION
        "Percentage of the CPU spent running irq processes.
         starCPUIrq is the percentage value times 100; for example,
         2.3% would be represented as 230."
    ::= { starCPUEntry 8 }

starCPULoad1Min OBJECT-TYPE
    SYNTAX     Gauge32(1..10000)
    UNITS      "processes times 100"
    MAX-ACCESS read-only
    STATUS     current
    DESCRIPTION
        "The average CPU load over the last minute.  The CPU load is defined
         to be the number of processes who are ready to run.
	 starCPULoad1Min is the average number of processes times 100; for
	 example, 2.45 would be represented as 245."
    ::= { starCPUEntry 11 }

starCPULoad5Min OBJECT-TYPE
    SYNTAX     Gauge32(1..10000)
    UNITS      "processes times 100"
    MAX-ACCESS read-only
    STATUS     current
    DESCRIPTION
        "The average CPU load over the last 5 minutes.  The CPU load is defined
         to be the number of processes who are ready to run.
	 starCPULoad5Min is the average number of processes times 100; for
	 example, 2.45 would be represented as 245."
    ::= { starCPUEntry 12 }

starCPULoad15Min OBJECT-TYPE
    SYNTAX     Gauge32(1..10000)
    UNITS      "processes times 100"
    MAX-ACCESS read-only
    STATUS     current
    DESCRIPTION
        "The average CPU load over the last 15 minutes.  The CPU load is defined
         to be the number of processes who are ready to run.
	 starCPULoad15Min is the average number of processes times 100; for
	 example, 2.45 would be represented as 245."
    ::= { starCPUEntry 13 }

starCPUMemTotal OBJECT-TYPE
    SYNTAX	Integer32(1..2147483647)
    UNITS       "KB"
    MAX-ACCESS  read-only
    STATUS      current
    DESCRIPTION
	"The total amount of memory dedicated to this CPU, in kilobytes"
    ::= { starCPUEntry 14 }

starCPUMemUsed OBJECT-TYPE
    SYNTAX	Gauge32(1..2147483647)
    UNITS       "KB"
    MAX-ACCESS  read-only
    STATUS      current
    DESCRIPTION
	"The total amount of memory consumed by this CPU, in kilobytes"
    ::= { starCPUEntry 15 }

starCPUNumProcesses OBJECT-TYPE
    SYNTAX      Gauge32(1..32768)
    UNITS       "processes"
    MAX-ACCESS  read-only
    STATUS      current
    DESCRIPTION
	"The total number of processes which exist on this CPU"
    ::= { starCPUEntry 16 }

starCPUMemCached OBJECT-TYPE
    SYNTAX	Gauge32(1..2147483647)
    UNITS       "KB"
    MAX-ACCESS  read-only
    STATUS      current
    DESCRIPTION
	"The total amount of memory consumed by the (reusable) memory cache on this CPU, in kilobytes"
    ::= { starCPUEntry 17 }

starCPUCoreNumber OBJECT-TYPE
    SYNTAX     Integer32(0..48)
    MAX-ACCESS read-only
    STATUS     current
    DESCRIPTION
        "The CPU core number within this card."
    ::= { starCPUEntry 18 }

-- Session In Progress

starentSessInP OBJECT IDENTIFIER ::= { starentMIBObjects 12 }

starSessInProgCalls OBJECT-TYPE
    SYNTAX     Gauge32
    MAX-ACCESS read-only
    STATUS     current
    DESCRIPTION
	"The number of sessions current in progress"
    ::= { starentSessInP 1 }

starSessInProgActiveCalls OBJECT-TYPE
    SYNTAX     Gauge32
    MAX-ACCESS read-only
    STATUS     current
    DESCRIPTION
	"The number of sessions with active calls"
    ::= { starentSessInP 2 }

starSessInProgDormantCalls OBJECT-TYPE
    SYNTAX     Gauge32
    MAX-ACCESS read-only
    STATUS     current
    DESCRIPTION
	"The number of sessions assocated with dormant calls"
    ::= { starentSessInP 3 }

starSessInProgArrived OBJECT-TYPE
    SYNTAX     Gauge32
    MAX-ACCESS read-only
    STATUS     current
    DESCRIPTION
	"The number of sessions in the arrived state"
    ::= { starentSessInP 4 }

starSessInProgLCPNeg OBJECT-TYPE
    SYNTAX     Gauge32
    MAX-ACCESS read-only
    STATUS     current
    DESCRIPTION
	"The number of sessions in the link control protocol negotiation state"
    ::= { starentSessInP 5 }

starSessInProgLCPUp OBJECT-TYPE
    SYNTAX     Gauge32
    MAX-ACCESS read-only
    STATUS     current
    DESCRIPTION
	"The number of sessions in the link control protocol up state"
    ::= { starentSessInP 6 }

starSessInProgAuthenticating OBJECT-TYPE
    SYNTAX     Gauge32
    MAX-ACCESS read-only
    STATUS     current
    DESCRIPTION
	"The number of sessions in the authenticating state"
    ::= { starentSessInP 7 }

starSessInProgAuthenticated OBJECT-TYPE
    SYNTAX     Gauge32
    MAX-ACCESS read-only
    STATUS     current
    DESCRIPTION
	"The number of sessions in the authenticated state"
    ::= { starentSessInP 8 }

starSessInProgIPCPUp OBJECT-TYPE
    SYNTAX     Gauge32
    MAX-ACCESS read-only
    STATUS     current
    DESCRIPTION
	"The number of sessions in the IP control protocol up state"
    ::= { starentSessInP 9 }

starSessInProgSIPConn OBJECT-TYPE
    SYNTAX     Gauge32
    MAX-ACCESS read-only
    STATUS     current
    DESCRIPTION
	"The number of sessions in the Simple IP connected state"
    ::= { starentSessInP 10 }

starSessInProgMIPConn OBJECT-TYPE
    SYNTAX     Gauge32
    MAX-ACCESS read-only
    STATUS     current
    DESCRIPTION
	"The number of sessions in the Mobile IP connected state"
    ::= { starentSessInP 11 }

starSessInProgDisc OBJECT-TYPE
    SYNTAX     Gauge32
    MAX-ACCESS read-only
    STATUS     current
    DESCRIPTION
	"The number of sessions in the disconnecting state"
    ::= { starentSessInP 12 }

-- NPU table
-- These objects are defined only for use in traps

starentNPUMgr OBJECT IDENTIFIER ::= { starentMIBObjects 11 }

starNPUMgrTable OBJECT-TYPE
    SYNTAX     SEQUENCE OF StarNPUMgrEntry
    MAX-ACCESS not-accessible
    STATUS     current
    DESCRIPTION
        "A table containing information about all NPU Managers"
    ::= { starentNPUMgr 1 }

starNPUMgrEntry OBJECT-TYPE
    SYNTAX     StarNPUMgrEntry
    MAX-ACCESS not-accessible
    STATUS     current
    DESCRIPTION
        "Information about a particular NPU Manager"
    INDEX { starNPUMgrNumber }
    ::= { starNPUMgrTable 1 }

StarNPUMgrEntry ::=
    SEQUENCE {
	starNPUMgrNumber			Integer32
    }

starNPUMgrNumber OBJECT-TYPE
    SYNTAX     Integer32(1..65535)
    MAX-ACCESS accessible-for-notify
    STATUS     current
    DESCRIPTION
        "The identity of this NPU"
    ::= { starNPUMgrEntry 1 }

--

starentSessMgr OBJECT IDENTIFIER ::= { starentMIBObjects 13 }

starSessMgrCount OBJECT-TYPE
    SYNTAX     Gauge32
    MAX-ACCESS read-only
    STATUS     current
    DESCRIPTION
	"The total number of session manager instances"
    ::= { starentSessMgr 1 }

starSessTtlArrived OBJECT-TYPE
    SYNTAX     Gauge32
    MAX-ACCESS read-only
    STATUS     current
    DESCRIPTION
	"The total number of requested sessions"
    ::= { starentSessMgr 2 }

starSessTtlRejected OBJECT-TYPE
    SYNTAX     Gauge32
    MAX-ACCESS read-only
    STATUS     current
    DESCRIPTION
        "The total number of rejected sessions"
    ::= { starentSessMgr 3 }

starSessTtlConnected OBJECT-TYPE
    SYNTAX     Gauge32
    MAX-ACCESS read-only
    STATUS     current
    DESCRIPTION
        "The total number of sessions which were connected"
    ::= { starentSessMgr 4 }

starSessTtlAuthSucc OBJECT-TYPE
    SYNTAX     Gauge32
    MAX-ACCESS read-only
    STATUS     current
    DESCRIPTION
        "The total number of sessions where authentication was successful"
    ::= { starentSessMgr 5 }

starSessTtlAuthFail OBJECT-TYPE
    SYNTAX     Gauge32
    MAX-ACCESS read-only
    STATUS     current
    DESCRIPTION
        "The total number of sessions which failed authentication"
    ::= { starentSessMgr 6 }

starSessTtlLCPUp OBJECT-TYPE
    SYNTAX     Gauge32
    MAX-ACCESS read-only
    STATUS     current
    DESCRIPTION
        "The total number of sessions in the link control protocol up state"
    ::= { starentSessMgr 7 }

starSessTtlIPCPUp OBJECT-TYPE
    SYNTAX     Gauge32
    MAX-ACCESS read-only
    STATUS     current
    DESCRIPTION
        "The total number of IP control protocol up state"
    ::= { starentSessMgr 8 }

starSessTtlSrcViol OBJECT-TYPE
    SYNTAX     Gauge32
    MAX-ACCESS read-only
    STATUS     current
    DESCRIPTION
        "The total number of sessions which had an invalid source"
    ::= { starentSessMgr 9 }

starSessTtlKeepFail OBJECT-TYPE
    SYNTAX     Gauge32
    MAX-ACCESS read-only
    STATUS     current
    DESCRIPTION
        "The total number of sessions which had a keep alive failure"
    ::= { starentSessMgr 10 }

starSessTtlOctForwarded OBJECT-TYPE
    SYNTAX     Counter32
    UNITS      "Megabytes"
    MAX-ACCESS read-only
    STATUS     deprecated
    DESCRIPTION
        "The total number of octets forwarded (data + control)"
    ::= { starentSessMgr 11 }

starSessTtlRPRegAccept OBJECT-TYPE
    SYNTAX     Counter32
    MAX-ACCESS read-only
    STATUS     current
    DESCRIPTION
        "The total number of Initial RRQ Accepted"
    ::= { starentSessMgr 12 }

starSessTtlRPRegAcceptInterPDSN OBJECT-TYPE
    SYNTAX     Counter32
    MAX-ACCESS read-only
    STATUS     current
    DESCRIPTION
        "The total number of Inter PDSN Handoff RRQ Accepted"
    ::= { starentSessMgr 13 }

starSessCurrPPPSessions OBJECT-TYPE
    SYNTAX     Gauge32
    MAX-ACCESS read-only
    STATUS     current
    DESCRIPTION
	"The current number of PPP sessions"
    ::= { starentSessMgr 14 }

starSessTtlTxBytes OBJECT-TYPE
    SYNTAX     Counter32
    UNITS      "Megabytes"
    MAX-ACCESS read-only
    STATUS     deprecated
    DESCRIPTION
        "The total number of bytes transmitted from mobiles"
    ::= { starentSessMgr 15 }

starSessTtlRxBytes OBJECT-TYPE
    SYNTAX     Counter32
    UNITS      "Megabytes"
    MAX-ACCESS read-only
    STATUS     deprecated
    DESCRIPTION
        "The total number of bytes received by mobiles"
    ::= { starentSessMgr 16 }

starSessTtlSIPTxBytes OBJECT-TYPE
    SYNTAX     Counter32
    UNITS      "Megabytes"
    MAX-ACCESS read-only
    STATUS     deprecated
    DESCRIPTION
        "The total number of bytes transmitted from mobiles using SIP"
    ::= { starentSessMgr 17 }

starSessTtlSIPRxBytes OBJECT-TYPE
    SYNTAX     Counter32
    UNITS      "Megabytes"
    MAX-ACCESS read-only
    STATUS     deprecated
    DESCRIPTION
        "The total number of bytes received by mobiles using SIP"
    ::= { starentSessMgr 18 }

starSessTtlMIPTxBytes OBJECT-TYPE
    SYNTAX     Counter32
    UNITS      "Megabytes"
    MAX-ACCESS read-only
    STATUS     deprecated
    DESCRIPTION
        "The total number of bytes transmitted from mobiles using MIP"
    ::= { starentSessMgr 19 }

starSessTtlMIPRxBytes OBJECT-TYPE
    SYNTAX     Counter32
    UNITS      "Megabytes"
    MAX-ACCESS read-only
    STATUS     deprecated
    DESCRIPTION
        "The total number of bytes received by mobiles using MIP"
    ::= { starentSessMgr 20 }

starSessTtlOctForwardedGB OBJECT-TYPE
    SYNTAX     Counter32
    UNITS      "Gigabytes"
    MAX-ACCESS read-only
    STATUS     deprecated
    DESCRIPTION
        "The total number of octets forwarded (data + control)"
    ::= { starentSessMgr 21 }

starSessTtlOctForwardedRev1 OBJECT-TYPE
    SYNTAX     Counter64
    UNITS      "Megabytes"
    MAX-ACCESS read-only
    STATUS     current
    DESCRIPTION
        "The total number of octets forwarded (data + control).
        This object deprecates the old starSessTtlOctForwarded object."
    ::= { starentSessMgr 22 }

starSessTtlTxBytesRev1 OBJECT-TYPE
    SYNTAX     Counter64
    UNITS      "Megabytes"
    MAX-ACCESS read-only
    STATUS     current
    DESCRIPTION
        "The total number of bytes transmitted from mobiles.
        This object deprecates the old starSessTtlTxBytes object."
    ::= { starentSessMgr 23 }

starSessTtlRxBytesRev1 OBJECT-TYPE
    SYNTAX     Counter64
    UNITS      "Megabytes"
    MAX-ACCESS read-only
    STATUS     current
    DESCRIPTION
        "The total number of bytes received by mobiles.
        This object deprecates the old starSessTtlRxBytes object."
    ::= { starentSessMgr 24 }

starSessTtlSIPTxBytesRev1 OBJECT-TYPE
    SYNTAX     Counter64
    UNITS      "Megabytes"
    MAX-ACCESS read-only
    STATUS     current
    DESCRIPTION
        "The total number of bytes transmitted from mobiles using SIP.
        This object deprecates the old starSessTtlSIPTxBytes object."
    ::= { starentSessMgr 25 }

starSessTtlSIPRxBytesRev1 OBJECT-TYPE
    SYNTAX     Counter64
    UNITS      "Megabytes"
    MAX-ACCESS read-only
    STATUS     current
    DESCRIPTION
        "The total number of bytes received by mobiles using SIP.
        This object deprecates the old starSessTtlSIPRxBytes object."
    ::= { starentSessMgr 26 }

starSessTtlMIPTxBytesRev1 OBJECT-TYPE
    SYNTAX     Counter64
    UNITS      "Megabytes"
    MAX-ACCESS read-only
    STATUS     current
    DESCRIPTION
        "The total number of bytes transmitted from mobiles using MIP.
        This object deprecates the old starSessTtlMIPTxBytes object."
    ::= { starentSessMgr 27 }

starSessTtlMIPRxBytesRev1 OBJECT-TYPE
    SYNTAX     Counter64
    UNITS      "Megabytes"
    MAX-ACCESS read-only
    STATUS     current
    DESCRIPTION
        "The total number of bytes received by mobiles using MIP.
        This object deprecates the old starSessTtlMIPRxBytes object."
    ::= { starentSessMgr 28 }

starSessTtlOctForwardedGBRev1 OBJECT-TYPE
    SYNTAX     Counter64
    UNITS      "Gigabytes"
    MAX-ACCESS read-only
    STATUS     current
    DESCRIPTION
        "The total number of octets forwarded (data + control).
        This object deprecates the old starSessTtlOctForwardedGB object."
    ::= { starentSessMgr 29 }

-- AAA

starentAAAMgr OBJECT IDENTIFIER ::= { starentMIBObjects 14 }

starAAAMgrCount OBJECT-TYPE
    SYNTAX     Gauge32
    MAX-ACCESS read-only
    STATUS     current
    DESCRIPTION
        "The total number of AAA manager instances"
    ::= { starentAAAMgr 1 }

starAAATtlRequests OBJECT-TYPE
    SYNTAX     Counter32
    MAX-ACCESS read-only
    STATUS     current
    DESCRIPTION
        "The total number of AAA requests"
    ::= { starentAAAMgr 2 }

starAAATtlAuthRequests OBJECT-TYPE
    SYNTAX     Counter32
    MAX-ACCESS read-only
    STATUS     current
    DESCRIPTION
        "The total number of AAA authentication requests"
    ::= { starentAAAMgr 3 }

starAAATtlAcctRequests OBJECT-TYPE
    SYNTAX     Counter32
    MAX-ACCESS read-only
    STATUS     current
    DESCRIPTION
        "The total number of AAA accounting requests"
    ::= { starentAAAMgr 4 }

starAAACurRequests OBJECT-TYPE
    SYNTAX     Gauge32
    MAX-ACCESS read-only
    STATUS     current
    DESCRIPTION
        "The current number of AAA requests"
    ::= { starentAAAMgr 5 }

starAAACurAuthRequests OBJECT-TYPE
    SYNTAX     Gauge32
    MAX-ACCESS read-only
    STATUS     current
    DESCRIPTION
        "The current number of AAA authentication requests"
    ::= { starentAAAMgr 6 }

starAAACurAcctRequests OBJECT-TYPE
    SYNTAX     Gauge32
    MAX-ACCESS read-only
    STATUS     current
    DESCRIPTION
        "The current number of AAA accounting requests"
    ::= { starentAAAMgr 7 }

starAAATtlAcctSess OBJECT-TYPE
    SYNTAX     Counter32
    MAX-ACCESS read-only
    STATUS     current
    DESCRIPTION
        "The total number of AAA accounting sessions"
    ::= { starentAAAMgr 8 }

starAAACurAcctSess OBJECT-TYPE
    SYNTAX     Gauge32
    MAX-ACCESS read-only
    STATUS     current
    DESCRIPTION
        "The current number of AAA accounting sessions"
    ::= { starentAAAMgr 9 }

starAAATtlAuthSuccess OBJECT-TYPE
    SYNTAX     Counter32
    MAX-ACCESS read-only
    STATUS     current
    DESCRIPTION
        "The total number of AAA authentication successes"
    ::= { starentAAAMgr 10 }

starAAATtlAuthFailure OBJECT-TYPE
    SYNTAX     Counter32
    MAX-ACCESS read-only
    STATUS     current
    DESCRIPTION
        "The total number of AAA authentication failures"
    ::= { starentAAAMgr 11 }


-- A11

starentA11Mgr OBJECT IDENTIFIER ::= { starentMIBObjects 15 }

starA11MgrCount OBJECT-TYPE
    SYNTAX     Gauge32
    MAX-ACCESS read-only
    STATUS     current
    DESCRIPTION
        "The total number of A11 manager instances"
    ::= { starentA11Mgr 1 }

starA11TtlArrived OBJECT-TYPE
    SYNTAX     Counter32
    MAX-ACCESS read-only
    STATUS     current
    DESCRIPTION
        "The total number of A11 session requests"
    ::= { starentA11Mgr 2 }

starA11TtlRejected OBJECT-TYPE
    SYNTAX     Counter32
    MAX-ACCESS read-only
    STATUS     current
    DESCRIPTION
        "The total number of rejected A11 sessions"
    ::= { starentA11Mgr 3 }

starA11TtlDemultiplexed OBJECT-TYPE
    SYNTAX     Counter32
    MAX-ACCESS read-only
    STATUS     current
    DESCRIPTION
        "The total number of demultiplexed A11 sessions"
    ::= { starentA11Mgr 4 }

starA11TtlDereg OBJECT-TYPE
    SYNTAX     Counter32
    MAX-ACCESS read-only
    STATUS     current
    DESCRIPTION
        "The total number of A11 deregistrations"
    ::= { starentA11Mgr 5 }

starA11CurActive OBJECT-TYPE
    SYNTAX     Gauge32
    MAX-ACCESS read-only
    STATUS     current
    DESCRIPTION
        "The current number of active A11 sessions"
    ::= { starentA11Mgr 6 }


-- HA

starentHAMgr OBJECT IDENTIFIER ::= { starentMIBObjects 16 }

starHAMgrCount OBJECT-TYPE
    SYNTAX     Gauge32
    MAX-ACCESS read-only
    STATUS     current
    DESCRIPTION
        "The total number of home agent manager instances"
    ::= { starentHAMgr 1 }

starHATtlArrived OBJECT-TYPE
    SYNTAX     Counter32
    MAX-ACCESS read-only
    STATUS     current
    DESCRIPTION
        "The total number of home agent session requests"
    ::= { starentHAMgr 2 }

starHATtlRejected OBJECT-TYPE
    SYNTAX     Counter32
    MAX-ACCESS read-only
    STATUS     current
    DESCRIPTION
        "The total number of rejected home agent sessions"
    ::= { starentHAMgr 3 }

starHATtlDemultiplexed OBJECT-TYPE
    SYNTAX     Counter32
    MAX-ACCESS read-only
    STATUS     current
    DESCRIPTION
        "The total number of demultiplexed home agent sessions"
    ::= { starentHAMgr 4 }

starHATtlDereg OBJECT-TYPE
    SYNTAX     Counter32
    MAX-ACCESS read-only
    STATUS     current
    DESCRIPTION
        "The total number of home agent deregistrations"
    ::= { starentHAMgr 5 }

starHACurActive OBJECT-TYPE
    SYNTAX     Gauge32
    MAX-ACCESS read-only
    STATUS     current
    DESCRIPTION
        "The total number of active home agent sessions"
    ::= { starentHAMgr 6 }


-- FA

starentFAMgr OBJECT IDENTIFIER ::= { starentMIBObjects 17 }

starFAMgrCount OBJECT-TYPE
    SYNTAX     Gauge32
    MAX-ACCESS read-only
    STATUS     current
    DESCRIPTION
        "The total number of foreign agent manager instances"
    ::= { starentFAMgr 1 }

starFATtlArrived OBJECT-TYPE
    SYNTAX     Counter32
    MAX-ACCESS read-only
    STATUS     current
    DESCRIPTION
        "The total number of foreign agent session requests"
    ::= { starentFAMgr 2 }

starFATtlRejected OBJECT-TYPE
    SYNTAX     Counter32
    MAX-ACCESS read-only
    STATUS     current
    DESCRIPTION
        "The total number of rejected foreign agent sessions"
    ::= { starentFAMgr 3 }

starFATtlDemultiplexed OBJECT-TYPE
    SYNTAX     Counter32
    MAX-ACCESS read-only
    STATUS     current
    DESCRIPTION
        "The total number of demultiplexed foreign agent sessions"
    ::= { starentFAMgr 4 }

starFATtlDereg OBJECT-TYPE
    SYNTAX     Counter32
    MAX-ACCESS read-only
    STATUS     current
    DESCRIPTION
        "The total number of foreign agent deregistrations"
    ::= { starentFAMgr 5 }

starFACurActive OBJECT-TYPE
    SYNTAX     Gauge32
    MAX-ACCESS read-only
    STATUS     current
    DESCRIPTION
        "The current number of active foreign agent sessions"
    ::= { starentFAMgr 6 }


-- Service Manager
-- Note that this table isn't expected to have an SNMP implementation; these objects are defined
-- for use within traps

starentService OBJECT IDENTIFIER ::= { starentMIBObjects 18 }

starServiceTable OBJECT-TYPE
    SYNTAX	SEQUENCE OF StarServiceEntry
    MAX-ACCESS  not-accessible
    STATUS      current
    DESCRIPTION
        " "
    ::= { starentService 1 }

starServiceEntry OBJECT-TYPE
    SYNTAX      StarServiceEntry
    MAX-ACCESS  not-accessible
    STATUS      current
    DESCRIPTION
        "Information on a particular Service Manager"
    INDEX { starServiceVpnID, starServiceSvcID }
    ::= { starServiceTable 1 }

StarServiceEntry ::=
    SEQUENCE {
        starServiceVpnID		Gauge32,
	starServiceSvcID		Gauge32,
        starServiceVpnName		DisplayString,
	starServiceServName		DisplayString,
	starServiceSubLimit             Unsigned32,
	starServiceSubCurrent           Gauge32,
	starServiceType			INTEGER,
	starServiceFAIpAddr		IpAddress,
	starServiceHAIpAddr		IpAddress
    }

starServiceVpnID OBJECT-TYPE
    SYNTAX     Gauge32
    MAX-ACCESS not-accessible
    STATUS     current
    DESCRIPTION
        "The internal identification of the VPN (context)"
    ::= { starServiceEntry 1 }

starServiceSvcID OBJECT-TYPE
    SYNTAX     Gauge32
    MAX-ACCESS not-accessible
    STATUS     current
    DESCRIPTION
        "The internal identification of this service; unique within a specific context"
    ::= { starServiceEntry 2 }

starServiceVpnName OBJECT-TYPE
    SYNTAX     DisplayString
    MAX-ACCESS read-only
    STATUS     current
    DESCRIPTION
        "The name of this VPN (context)"
    ::= { starServiceEntry 3 }

starServiceServName OBJECT-TYPE
    SYNTAX     DisplayString
    MAX-ACCESS read-only
    STATUS     current
    DESCRIPTION
        "The name of this service"
    ::= { starServiceEntry 4 }

starServiceSubLimit OBJECT-TYPE
    SYNTAX     Unsigned32
    MAX-ACCESS read-only
    STATUS     current
    DESCRIPTION
	"The configured subscriber limit"
    ::= { starServiceEntry 5 }

starServiceSubCurrent OBJECT-TYPE
    SYNTAX     Gauge32
    MAX-ACCESS read-only
    STATUS     current
    DESCRIPTION
	"The current number of subscribers limit"
    ::= { starServiceEntry 6 }

starServiceType OBJECT-TYPE
    SYNTAX INTEGER {
        unknown(1),
	pdsn(2),
	ggsn(3),
	ha(4),
	fa(5),
	l2tpserver(6),
	lac(7),
	lns(8),
	closedrp(9),
	ecs(10),
	cscf(11),
	ipsg(12),
	evdoreva(13),
	asngw(14),
	pdif(15),
	asnpc(16),
	mipv6ha(17),
	phsgw(18),
	phspc(19),
	sgw(20),
	pgw(21),
	mag(22),
	gprs(23),
	hsgw(24),
	sgsn(25),
	mme(26),
	pdg(27),
	standalonefa(28),
	imsue(29),
	fng(30),
    pccpolicy(31),
    pccquota(32),
    pccaf(33),
    hnbgw(34),
    non-anchor-phs-gateway(35),
    combination-3g-4g-gateway(36),
    epdg(37),
    pcp(38),
    henbgw-access(39),
    henbgw-network(40),
    wsg(41),
    samog(42),
    saegw(43),
    ppp-lback(44),
    dhcp(45),
    imsa(46),
    diameter(47),
    dhcpv6(48),
    lma(49),
    crdt-ctl(50),
    mme-hss(51),
    sgs(52),
    cbs(53),
    egtp-ingress(54),
    egtp-egress(55),
    egtp(56),
    gtpu(57),
    sgtpc(58),
    egtp-sv(59),
    megad(60),
    pcc(61),
    ipne(62),
    mseg(63),
    bng(64),
    gs(65),
    map(66),
    iups(67),
    sgtp(68),
    lcs(69),
    mme-embms(70)
    }
    MAX-ACCESS read-only
    STATUS     current
    DESCRIPTION
	"The type of service"
    ::= { starServiceEntry 7 }

starServiceFAIpAddr OBJECT-TYPE
    SYNTAX     IpAddress
    MAX-ACCESS read-only
    STATUS     current
    DESCRIPTION
	"The IP address for an FA service.  Where unknown or not applicable
	 this will contain all zeroes."
    ::= { starServiceEntry 8 }

starServiceHAIpAddr OBJECT-TYPE
    SYNTAX     IpAddress
    MAX-ACCESS read-only
    STATUS     current
    DESCRIPTION
	"The IP address for an HA service.  Where unknown or not applicable
	 this will contain all zeroes."
    ::= { starServiceEntry 9 }

-- CLI
-- Note that this table isn't expected to have an SNMP implementation; these objects are defined
-- for use within traps

starentCLIMgr OBJECT IDENTIFIER ::= { starentMIBObjects 19 }

starCLITable OBJECT-TYPE
    SYNTAX	SEQUENCE OF StarCLIEntry
    MAX-ACCESS  not-accessible
    STATUS      current
    DESCRIPTION
        "A table containing information on all interactive CLI sessions"
    ::= { starentCLIMgr 1 }

starCLIEntry OBJECT-TYPE
    SYNTAX      StarCLIEntry
    MAX-ACCESS  not-accessible
    STATUS      current
    DESCRIPTION
        "Information on a particular CLI Session"
    INDEX { starCLIID }
    ::= { starCLITable 1 }

StarCLIEntry ::=
    SEQUENCE {
        starCLIID                       Gauge32,
	starCLIUsername                 DisplayString,
        starCLITtyname                  DisplayString,
        starCLIPrivs                    DisplayString,
	starCLIType                     INTEGER,
    starCLIRemoteIpAddrType         InetAddressType,
	starCLIRemoteIpAddr		        InetAddress,
	starCLIContext			DisplayString,
	starCLIDatabaseUsername		DisplayString,
        starCLIActiveCount              Counter32,
        starCLIMaxCount                 Counter32, 
        starCLIEventIDStart             Counter32,
        starCLIEventIDEnd               Counter32,
	starCLILogLevelChanged          DisplayString
    }

starCLIID OBJECT-TYPE
    SYNTAX     Gauge32
    MAX-ACCESS not-accessible
    STATUS     current
    DESCRIPTION
        "The internal identifier of this CLI session."
    ::= { starCLIEntry 1 }

starCLIUsername OBJECT-TYPE
    SYNTAX     DisplayString
    MAX-ACCESS read-only
    STATUS     current
    DESCRIPTION
        "The name of the user logged into this CLI session, or 'unknown' if not none"
    ::= { starCLIEntry 2 }

starCLITtyname OBJECT-TYPE
    SYNTAX     DisplayString
    MAX-ACCESS read-only
    STATUS     current
    DESCRIPTION
        "The name of the TTY device for this CLI session"
    ::= { starCLIEntry 3 }

starCLIPrivs OBJECT-TYPE
    SYNTAX     DisplayString
    MAX-ACCESS read-only
    STATUS     current
    DESCRIPTION
        "The user presentable form of the privilege level of this CLI session"
    ::= { starCLIEntry 4 }

starCLIType OBJECT-TYPE
    SYNTAX     INTEGER {
		 unknown(0),
		 commandline(1),
		 ftp(2)
	       }
    MAX-ACCESS read-only
    STATUS     current
    DESCRIPTION
	"The type of CLI; commandline(1) represents the normal interactive command line;
	 ftp(2) represents an incoming FTP session"
    ::= { starCLIEntry 5 }

starCLIRemoteIpAddrType OBJECT-TYPE
    SYNTAX     InetAddressType
    MAX-ACCESS read-only
    STATUS     current
    DESCRIPTION
	"The type of remote IP address used to access this CLI session."
    ::= { starCLIEntry 6 }

starCLIRemoteIpAddr OBJECT-TYPE
    SYNTAX     InetAddress
    MAX-ACCESS read-only
    STATUS     current
    DESCRIPTION
	"The remote IP address used to access this CLI session.  Where unknown or
	 not applicable (such as access through a serial port) this will be 0"
    ::= { starCLIEntry 7 }

starCLIContext OBJECT-TYPE
    SYNTAX     DisplayString
    MAX-ACCESS read-only
    STATUS     current
    DESCRIPTION
	"The context (VPN) currently being managed/viewed by the CLI session."
    ::= { starCLIEntry 8 }

starCLIDatabaseUsername OBJECT-TYPE
    SYNTAX     DisplayString
    MAX-ACCESS read-only
    STATUS     current
    DESCRIPTION
        "The username of the user record in the database which was acted upon by the CLI session"
    ::= { starCLIEntry 9 }

starCLIActiveCount OBJECT-TYPE
    SYNTAX     Counter32
    MAX-ACCESS read-only
    STATUS     current
    DESCRIPTION
	"Active CLI Sessions Value"
    ::= { starCLIEntry 10 }

starCLIMaxCount OBJECT-TYPE
    SYNTAX     Counter32
    MAX-ACCESS read-only
    STATUS     current
    DESCRIPTION
	"Maximum CLI Sessions Limit"
    ::= { starCLIEntry 11 }

starCLIEventIDStart OBJECT-TYPE
    SYNTAX     Counter32
    MAX-ACCESS read-only
    STATUS     current
    DESCRIPTION
	"EventID Range From Value"
    ::= { starCLIEntry 12 }

starCLIEventIDEnd OBJECT-TYPE
    SYNTAX     Counter32
    MAX-ACCESS read-only
    STATUS     current
    DESCRIPTION
	"EventID Range To Value"
    ::= { starCLIEntry 13 }

starCLILogLevelChanged OBJECT-TYPE
    SYNTAX     DisplayString
    MAX-ACCESS read-only
    STATUS     current
    DESCRIPTION
	"Description about change in logging level of a facility by an user"
    ::= { starCLIEntry 14 }

-- Task Manager
-- Note that this table isn't expected to have an SNMP implementation; these objects are defined
-- for use within traps

starentTaskMgr OBJECT IDENTIFIER ::= { starentMIBObjects 20 }

starTaskTable OBJECT-TYPE
    SYNTAX	SEQUENCE OF StarTaskEntry
    MAX-ACCESS  not-accessible
    STATUS      current
    DESCRIPTION
        "A table containing information about all active tasks"
    ::= { starentTaskMgr 1 }

starTaskEntry OBJECT-TYPE
    SYNTAX      StarTaskEntry
    MAX-ACCESS  not-accessible
    STATUS      current
    DESCRIPTION
        "Information on a particular Task"
    INDEX { starTaskFacility, starTaskInstance }
    ::= { starTaskTable 1 }

StarTaskEntry ::=
    SEQUENCE {
	starTaskFacility                Unsigned32,
        starTaskInstance                Unsigned32,
        starTaskFacilityName            DisplayString,
        starTaskCard                    Unsigned32,
        starTaskCPU                     Unsigned32
    }

starTaskFacility OBJECT-TYPE
    SYNTAX     Unsigned32
    MAX-ACCESS not-accessible
    STATUS     current
    DESCRIPTION
        "The internal facility identifier"
    ::= { starTaskEntry 1 }

starTaskInstance OBJECT-TYPE
    SYNTAX     Unsigned32
    MAX-ACCESS accessible-for-notify
    STATUS     current
    DESCRIPTION
        "The internal instance identifier which uniquely idenfies this task
         without a given facility"
    ::= { starTaskEntry 2 }

starTaskFacilityName OBJECT-TYPE
    SYNTAX     DisplayString
    MAX-ACCESS read-only
    STATUS     current
    DESCRIPTION
        "The name of the facility for this task"
    ::= { starTaskEntry 3 }

starTaskCard OBJECT-TYPE
    SYNTAX     Unsigned32
    MAX-ACCESS read-only
    STATUS     current
    DESCRIPTION
        "The slot number of the card where this task is running"
    ::= { starTaskEntry 4 }

starTaskCPU OBJECT-TYPE
    SYNTAX     Unsigned32
    MAX-ACCESS read-only
    STATUS     current
    DESCRIPTION
        "The CPU number where this task is running"
    ::= { starTaskEntry 5 }

-- PPP Stats

starentPPP OBJECT IDENTIFIER ::= { starentMIBObjects 21 }

starPPPStatTable OBJECT-TYPE
    SYNTAX     SEQUENCE OF StarPPPStatEntry
    MAX-ACCESS not-accessible
    STATUS     current
    DESCRIPTION
        "A table containing PPP Stats"
    ::= { starentPPP 1 }

starPPPStatEntry OBJECT-TYPE
    SYNTAX     StarPPPStatEntry
    MAX-ACCESS not-accessible
    STATUS     current
    DESCRIPTION
        "The statistics for an individual entry for a PPP context and service"
    INDEX { IMPLIED starPPPStatSvcID }
    ::= { starPPPStatTable 1 }

StarPPPStatEntry ::=
    SEQUENCE {
        starPPPStatVpnID             Gauge32,
        starPPPStatSvcID             StarShortID,
        starPPPStatVpnName           DisplayString,
        starPPPStatServName          DisplayString,
        starPPPStatInit              Counter32,
        starPPPStatReneg             Counter32,
        starPPPStatSuccess           Counter32,
        starPPPStatFailed            Counter32,
        starPPPStatReleased          Counter32,
        starPPPStatReleasedLocal     Counter32,
        starPPPStatReleasedRemote    Counter32,
        starPPPStatLcpFailMaxRetry   Counter32,
        starPPPStatLcpFailOption     Counter32,
        starPPPStatIpcpFailMaxRetry  Counter32,
        starPPPStatIpcpFailOption    Counter32,
        starPPPStatCcpFail           Counter32,
        starPPPStatAuthFail          Counter32,
        starPPPStatLcpEntered        Counter32,
        starPPPStatAuthEntered       Counter32,
        starPPPStatIpcpEntered       Counter32,
        starPPPStatRenegPdsn         Counter32,
        starPPPStatRenegMobil        Counter32,
        starPPPStatRenegAddrMismatch Counter32,
        starPPPStatRenegOther        Counter32,
        starPPPStatChapAuthAttempt   Counter32,
        starPPPStatPapAuthAttempt    Counter32,
        starPPPStatMSChapAuthAttempt Counter32,
        starPPPStatChapAuthFail      Counter32,
        starPPPStatPapAuthFail       Counter32,
        starPPPStatMSChapAuthFail    Counter32,
        starPPPStatStacComp          Counter32,
        starPPPStatMppcComp          Counter32,
        starPPPStatDeflComp          Counter32,
        starPPPStatFscErrs           Counter32,
        starPPPStatUnknProto         Counter32,
        starPPPStatBadAddr           Counter32,
        starPPPStatBadCtrl           Counter32,
        starPPPStatVjComp            Counter32,
        starPPPStatDiscLcpRemote     Counter32,
        starPPPStatDiscRpRemote      Counter32,
        starPPPStatDiscAdmin         Counter32,
        starPPPStatDiscIdleTimeout   Counter32,
        starPPPStatDiscAbsTimeout    Counter32,
        starPPPStatDiscPPPKeepalive  Counter32,
        starPPPStatDiscNoResource    Counter32,
        starPPPStatDiscMisc          Counter32,
	starPPPStatFailedReneg            Counter32,
	starPPPStatLcpFailUnknown         Counter32,
        starPPPStatIpcpFailUnknown        Counter32,
	starPPPStatAuthAbort              Counter32,
	starPPPStatLowerLayerDisc         Counter32,
	starPPPStatLcpSuccess             Counter32,
	starPPPStatAuthSuccess            Counter32,
	starPPPStatRenegLowerLayerHandoff Counter32,
	starPPPStatRenegParamUpdate       Counter32,
        starPPPStatChapAuthSuccess        Counter32,
        starPPPStatPapAuthSuccess         Counter32,
        starPPPStatMSChapAuthSuccess      Counter32,
        starPPPStatChapAuthAbort          Counter32,
        starPPPStatPapAuthAbort           Counter32,
        starPPPStatMSChapAuthAbort        Counter32,
	starPPPStatSessSkipAuth           Counter32,
	starPPPStatNegComp                Counter32,
	starPPPStatCCPNegFailComp         Counter32,
	starPPPStatDiscLocalLowerLayer    Counter32,
	starPPPStatDiscAddFlowFail        Counter32,
	starPPPStatDiscMaxRetriesLCP      Counter32,
	starPPPStatDiscMaxRetriesIPCP     Counter32,
	starPPPStatDiscMaxSetupTimer      Counter32,
	starPPPStatDiscInvalidDestVpn     Counter32,
	starPPPStatDiscOptNegFailLCP      Counter32,
	starPPPStatDiscOptNegFailIPCP     Counter32,
	starPPPStatDiscNoRemoteIpAddr     Counter32,
	starPPPStatDiscCallTypeDetectFail Counter32,
	starPPPStatDiscRemoteDiscUpLayer  Counter32,
	starPPPStatDiscLongDuraTimeout    Counter32,
	starPPPStatDiscAuthFail           Counter32,
	starPPPStatLCPEchoTotalReq        Counter32,
	starPPPStatLCPEchoReqResent       Counter32,
	starPPPStatLCPEchoRepRecved       Counter32,
	starPPPStatLCPEchoReqTimeout      Counter32,
	starPPPStatRecvErrBadCtrlField    Counter32,
	starPPPStatRecvErrBadPacketLen    Counter32,
	starPPPStatRemoteTerm             Counter32,
	starPPPStatMiscFail               Counter32
    }

starPPPStatVpnID OBJECT-TYPE
    SYNTAX     Gauge32
    MAX-ACCESS not-accessible
    STATUS     current
    DESCRIPTION
        "The internal identification of the PPP VPN (context)"
    ::= { starPPPStatEntry 1 }

starPPPStatSvcID OBJECT-TYPE
    SYNTAX     StarShortID
    MAX-ACCESS not-accessible
    STATUS     current
    DESCRIPTION
        "The service identification is made up from first 8 chars of context name
         and first 8 chars of service name separated by (:)"
    ::= { starPPPStatEntry 2 }

starPPPStatVpnName OBJECT-TYPE
    SYNTAX     DisplayString
    MAX-ACCESS read-only
    STATUS     current
    DESCRIPTION
        "The name of the PPP VPN (context)"
    ::= { starPPPStatEntry 3 }

starPPPStatServName OBJECT-TYPE
    SYNTAX     DisplayString
    MAX-ACCESS read-only
    STATUS     current
    DESCRIPTION
        "The name of the PPP service"
    ::= { starPPPStatEntry 4 }

starPPPStatInit OBJECT-TYPE
    SYNTAX     Counter32
    MAX-ACCESS read-only
    STATUS     current
    DESCRIPTION
        "The number of initialized PPP sessions for the associated VPN service"
    ::= { starPPPStatEntry 5 }

starPPPStatReneg OBJECT-TYPE
    SYNTAX     Counter32
    MAX-ACCESS read-only
    STATUS     current
    DESCRIPTION
        "The number of PPP session renegotiations for the associated VPN service"
    ::= { starPPPStatEntry 6 }

starPPPStatSuccess OBJECT-TYPE
    SYNTAX     Counter32
    MAX-ACCESS read-only
    STATUS     current
    DESCRIPTION
        "The number of PPP session negotiation successes for the associated VPN service "
    ::= { starPPPStatEntry 7 }

starPPPStatFailed OBJECT-TYPE
    SYNTAX     Counter32
    MAX-ACCESS read-only
    STATUS     current
    DESCRIPTION
        "The number of PPP session negotiation failures for the associated VPN service"
    ::= { starPPPStatEntry 8 }

starPPPStatReleased OBJECT-TYPE
    SYNTAX     Counter32
    MAX-ACCESS read-only
    STATUS     current
    DESCRIPTION
        "The number of PPP sessions released for the associated VPN service"
    ::= { starPPPStatEntry 9 }

starPPPStatReleasedLocal OBJECT-TYPE
    SYNTAX     Counter32
    MAX-ACCESS read-only
    STATUS     current
    DESCRIPTION
        "The number of PPP sessions where the release was initiated locally for the associated VPN service"
    ::= { starPPPStatEntry 10 }

starPPPStatReleasedRemote OBJECT-TYPE
    SYNTAX     Counter32
    MAX-ACCESS read-only
    STATUS     current
    DESCRIPTION
        "The number of PPP sessions where the release was initiated remotely for the associated VPN service"
    ::= { starPPPStatEntry 11 }

starPPPStatLcpFailMaxRetry OBJECT-TYPE
    SYNTAX     Counter32
    MAX-ACCESS read-only
    STATUS     current
    DESCRIPTION
        "The number of PPP sessions which failed to bring up the link control protocol
         due to excessive retries for the associated VPN service"
    ::= { starPPPStatEntry 12 }

starPPPStatLcpFailOption OBJECT-TYPE
    SYNTAX     Counter32
    MAX-ACCESS read-only
    STATUS     current
    DESCRIPTION
        "The number of PPP sessions which failed to bring up the link control protocol
	 due to an invalid option being received for the associated VPN service"
    ::= { starPPPStatEntry 13 }

starPPPStatIpcpFailMaxRetry OBJECT-TYPE
    SYNTAX     Counter32
    MAX-ACCESS read-only
    STATUS     current
    DESCRIPTION
        "The number of PPP sessions which failed to start the IP control protocol
	 due to excessive retries for the associated VPN service"
    ::= { starPPPStatEntry 14 }

starPPPStatIpcpFailOption OBJECT-TYPE
    SYNTAX     Counter32
    MAX-ACCESS read-only
    STATUS     current
    DESCRIPTION
        "The number of PPP sessions which failed to start the IP control protocol due to
	 an invalid option being received for the associated VPN service"
    ::= { starPPPStatEntry 15 }

starPPPStatCcpFail OBJECT-TYPE
    SYNTAX     Counter32
    MAX-ACCESS read-only
    STATUS     current
    DESCRIPTION
        "The number of PPP sessions which failed to initialize the CCP"
    ::= { starPPPStatEntry 16 }

starPPPStatAuthFail OBJECT-TYPE
    SYNTAX     Counter32
    MAX-ACCESS read-only
    STATUS     current
    DESCRIPTION
        "The number of PPP sessions which failed authentication for the associated VPN"
    ::= { starPPPStatEntry 17 }

starPPPStatLcpEntered OBJECT-TYPE
    SYNTAX     Counter32
    MAX-ACCESS read-only
    STATUS     current
    DESCRIPTION
        "The number of PPP sessions which successfully initialized the link control protocol"
    ::= { starPPPStatEntry 18 }

starPPPStatAuthEntered OBJECT-TYPE
    SYNTAX     Counter32
    MAX-ACCESS read-only
    STATUS     current
    DESCRIPTION
        "The number of PPP sessions which were successfully authenticated"
    ::= { starPPPStatEntry 19 }

starPPPStatIpcpEntered OBJECT-TYPE
    SYNTAX     Counter32
    MAX-ACCESS read-only
    STATUS     current
    DESCRIPTION
        "The number of PPP sessions which successfully initialized the IP control protocol"
    ::= { starPPPStatEntry 20 }

starPPPStatRenegPdsn OBJECT-TYPE
    SYNTAX     Counter32
    MAX-ACCESS read-only
    STATUS     current
    DESCRIPTION
        "The number of PPP sessions which renegotiated the PDSN service access"
    ::= { starPPPStatEntry 21 }

starPPPStatRenegMobil OBJECT-TYPE
    SYNTAX     Counter32
    MAX-ACCESS read-only
    STATUS     current
    DESCRIPTION
        "The number of PPP sessions which renegotiated the Mobile IP service access"
    ::= { starPPPStatEntry 22 }

starPPPStatRenegAddrMismatch OBJECT-TYPE
    SYNTAX     Counter32
    MAX-ACCESS read-only
    STATUS     current
    DESCRIPTION
        "The number of PPP sessions which had an IP address mismatch during renegotiation"
    ::= { starPPPStatEntry 23 }

starPPPStatRenegOther OBJECT-TYPE
    SYNTAX     Counter32
    MAX-ACCESS read-only
    STATUS     current
    DESCRIPTION
        "The number of PPP sessions which failed renegotiation for reasons other than IP
	 address mismatch"
    ::= { starPPPStatEntry 24 }

starPPPStatChapAuthAttempt OBJECT-TYPE
    SYNTAX     Counter32
    MAX-ACCESS read-only
    STATUS     current
    DESCRIPTION
        "The number of PPP CHAP authentication attempts for the associated VPN service"
    ::= { starPPPStatEntry 25 }

starPPPStatPapAuthAttempt OBJECT-TYPE
    SYNTAX     Counter32
    MAX-ACCESS read-only
    STATUS     current
    DESCRIPTION
        "The number of PPP PAP authentication attempts for the associated VPN service"
    ::= { starPPPStatEntry 26 }

starPPPStatMSChapAuthAttempt OBJECT-TYPE
    SYNTAX     Counter32
    MAX-ACCESS read-only
    STATUS     current
    DESCRIPTION
        "The number of PPP MSCHAP authentication attempts for the associated VPN service"
    ::= { starPPPStatEntry 27 }

starPPPStatChapAuthFail OBJECT-TYPE
    SYNTAX     Counter32
    MAX-ACCESS read-only
    STATUS     current
    DESCRIPTION
        "The number of PPP CHAP authentication attempt failures for the associated VPN service"
    ::= { starPPPStatEntry 28 }

starPPPStatPapAuthFail OBJECT-TYPE
    SYNTAX     Counter32
    MAX-ACCESS read-only
    STATUS     current
    DESCRIPTION
        "The number of PPP PAP authentication failures for the associated VPN service"
    ::= { starPPPStatEntry 29 }

starPPPStatMSChapAuthFail OBJECT-TYPE
    SYNTAX     Counter32
    MAX-ACCESS read-only
    STATUS     current
    DESCRIPTION
        "The number of PPP MSCHAP authentication failures for the associated VPN service"
    ::= { starPPPStatEntry 30 }

starPPPStatStacComp OBJECT-TYPE
    SYNTAX     Counter32
    MAX-ACCESS read-only
    STATUS     current
    DESCRIPTION
        "The number of PPP sessions which had STAC compression enabled for the associated
	 VPN service"
    ::= { starPPPStatEntry 31 }

starPPPStatMppcComp OBJECT-TYPE
    SYNTAX     Counter32
    MAX-ACCESS read-only
    STATUS     current
    DESCRIPTION
        "The number of PPP sessions which had MPPC compression enabled for the
	 associated VPN service"
    ::= { starPPPStatEntry 32 }

starPPPStatDeflComp OBJECT-TYPE
    SYNTAX     Counter32
    MAX-ACCESS read-only
    STATUS     current
    DESCRIPTION
        "The number of PPP sessions which had DEFLATE compression enabled for the
	 associated VPN service"
    ::= { starPPPStatEntry 33 }

starPPPStatFscErrs OBJECT-TYPE
    SYNTAX     Counter32
    MAX-ACCESS read-only
    STATUS     current
    DESCRIPTION
        "The number of PPP forward sequence control errors in messaging"
    ::= { starPPPStatEntry 34 }

starPPPStatUnknProto OBJECT-TYPE
    SYNTAX     Counter32
    MAX-ACCESS read-only
    STATUS     current
    DESCRIPTION
        "The number of PPP sessions which failed due to an unknown protocol received
	 for the associated VPN service"
    ::= { starPPPStatEntry 35 }

starPPPStatBadAddr OBJECT-TYPE
    SYNTAX     Counter32
    MAX-ACCESS read-only
    STATUS     current
    DESCRIPTION
        "The number of PPP sessions which failed due to a bad address being received
	 for the associated VPN service"
    ::= { starPPPStatEntry 36 }

starPPPStatBadCtrl OBJECT-TYPE
    SYNTAX     Counter32
    MAX-ACCESS read-only
    STATUS     current
    DESCRIPTION
        "The number of PPP sessions in which a bad control sequence was received"
    ::= { starPPPStatEntry 37 }

starPPPStatVjComp OBJECT-TYPE
    SYNTAX     Counter32
    MAX-ACCESS read-only
    STATUS     current
    DESCRIPTION
        "The number of PPP sessions which had VJ header compression enabled for the
	 associated VPN service"
    ::= { starPPPStatEntry 38 }

starPPPStatDiscLcpRemote OBJECT-TYPE
    SYNTAX     Counter32
    MAX-ACCESS read-only
    STATUS     current
    DESCRIPTION
        "The number of PPP sessions which were disconnected via the link control protocol
	 from the remote end for the associated VPN service"
    ::= { starPPPStatEntry 39 }

starPPPStatDiscRpRemote OBJECT-TYPE
    SYNTAX     Counter32
    MAX-ACCESS read-only
    STATUS     current
    DESCRIPTION
        "The number of PPP sessions which were disconnected by the remote via the R-P
	 interface for the associated VPN service"
    ::= { starPPPStatEntry 40 }

starPPPStatDiscAdmin OBJECT-TYPE
    SYNTAX     Counter32
    MAX-ACCESS read-only
    STATUS     current
    DESCRIPTION
        "The number of PPP sessions which were disconnected by a local administrator
	 for the associated VPN service"
    ::= { starPPPStatEntry 41 }

starPPPStatDiscIdleTimeout OBJECT-TYPE
    SYNTAX     Counter32
    MAX-ACCESS read-only
    STATUS     current
    DESCRIPTION
        "The number of PPP sessions disconnected due to session idle timer expiration for
	 the associated VPN service"
    ::= { starPPPStatEntry 42 }

starPPPStatDiscAbsTimeout OBJECT-TYPE
    SYNTAX     Counter32
    MAX-ACCESS read-only
    STATUS     current
    DESCRIPTION
        "The number of PPP sessions disconnected due to the session absolute timer expiration
	 for the associated VPN service"
    ::= { starPPPStatEntry 43 }

starPPPStatDiscPPPKeepalive OBJECT-TYPE
    SYNTAX     Counter32
    MAX-ACCESS read-only
    STATUS     current
    DESCRIPTION
        "The number of PPP sessions disconnected due to PPP keep alive failure for the
	 associated VPN service"
    ::= { starPPPStatEntry 44 }

starPPPStatDiscNoResource OBJECT-TYPE
    SYNTAX     Counter32
    MAX-ACCESS read-only
    STATUS     current
    DESCRIPTION
        "The number of PPP sessions disconnected due to local resource shortage for the
	 associated VPN service"
    ::= { starPPPStatEntry 45 }

starPPPStatDiscMisc OBJECT-TYPE
    SYNTAX     Counter32
    MAX-ACCESS read-only
    STATUS     current
    DESCRIPTION
        "The number of PPP sessions disconnected due to any cause which does not match
	 any other existing disconnect statistics for the associated VPN service"
    ::= { starPPPStatEntry 46 }

starPPPStatFailedReneg OBJECT-TYPE
    SYNTAX     Counter32
    MAX-ACCESS read-only
    STATUS     current
    DESCRIPTION
        "The number of failed PPP renegotiations the associated VPN service"
    ::= { starPPPStatEntry 47 }

starPPPStatLcpFailUnknown OBJECT-TYPE
    SYNTAX     Counter32
    MAX-ACCESS read-only
    STATUS     current
    DESCRIPTION
        "The number of failed PPP LCP that are due to unknown reasons
	 for the associated VPN service"
    ::= { starPPPStatEntry 48 }

starPPPStatIpcpFailUnknown  OBJECT-TYPE
    SYNTAX     Counter32
    MAX-ACCESS read-only
    STATUS     current
    DESCRIPTION
        "The number of failed PPP IPCP that are due to unknown reasons
	 for the associated VPN service"
    ::= { starPPPStatEntry 49 }

starPPPStatAuthAbort  OBJECT-TYPE
    SYNTAX     Counter32
    MAX-ACCESS read-only
    STATUS     current
    DESCRIPTION
        "The number of aborted PPP authentications
	 for the associated VPN service"
    ::= { starPPPStatEntry 50 }

starPPPStatLowerLayerDisc OBJECT-TYPE
    SYNTAX     Counter32
    MAX-ACCESS read-only
    STATUS     current
    DESCRIPTION
        "The number of Failed PPP session due to RP disconnect
	 for the associated VPN service"
    ::= { starPPPStatEntry 51 }

starPPPStatLcpSuccess  OBJECT-TYPE
    SYNTAX     Counter32
    MAX-ACCESS read-only
    STATUS     current
    DESCRIPTION
        "The number of successful PPP LCPs
	 for the associated VPN service"
    ::= { starPPPStatEntry 52 }

starPPPStatAuthSuccess OBJECT-TYPE
    SYNTAX     Counter32
    MAX-ACCESS read-only
    STATUS     current
    DESCRIPTION
        "The number of successful PPP authentications
	 for the associated VPN service"
    ::= { starPPPStatEntry 53 }

starPPPStatRenegLowerLayerHandoff OBJECT-TYPE
    SYNTAX     Counter32
    MAX-ACCESS read-only
    STATUS     current
    DESCRIPTION
        "The number of PPP renigotiations for RP handoff
	 for the associated VPN service"
    ::= { starPPPStatEntry 54 }

starPPPStatRenegParamUpdate  OBJECT-TYPE
    SYNTAX     Counter32
    MAX-ACCESS read-only
    STATUS     current
    DESCRIPTION
        "The number of PPP renigotiations for parameter update
	 for the associated VPN service"
    ::= { starPPPStatEntry 55 }

starPPPStatChapAuthSuccess OBJECT-TYPE
    SYNTAX     Counter32
    MAX-ACCESS read-only
    STATUS     current
    DESCRIPTION
        "The number of successful PPP CHAP authentications
	 for the associated VPN service"
    ::= { starPPPStatEntry 56 }

starPPPStatPapAuthSuccess  OBJECT-TYPE
    SYNTAX     Counter32
    MAX-ACCESS read-only
    STATUS     current
    DESCRIPTION
        "The number of successful PPP PAP authentications
	 for the associated VPN service"
    ::= { starPPPStatEntry 57 }

starPPPStatMSChapAuthSuccess OBJECT-TYPE
    SYNTAX     Counter32
    MAX-ACCESS read-only
    STATUS     current
    DESCRIPTION
        "The number of successful PPP MSCHAP authentications
	 for the associated VPN service"
    ::= { starPPPStatEntry 58 }

starPPPStatChapAuthAbort OBJECT-TYPE
    SYNTAX     Counter32
    MAX-ACCESS read-only
    STATUS     current
    DESCRIPTION
        "The number of aboted PPP CHAP authentications
	 for the associated VPN service"
    ::= { starPPPStatEntry 59 }

starPPPStatPapAuthAbort OBJECT-TYPE
    SYNTAX     Counter32
    MAX-ACCESS read-only
    STATUS     current
    DESCRIPTION
        "The number of aboted PPP PAP authentications
	 for the associated VPN service"
    ::= { starPPPStatEntry 60 }

starPPPStatMSChapAuthAbort OBJECT-TYPE
    SYNTAX     Counter32
    MAX-ACCESS read-only
    STATUS     current
    DESCRIPTION
        "The number of aboted PPP MSCHAP authentications
	 for the associated VPN service"
    ::= { starPPPStatEntry 61 }

starPPPStatSessSkipAuth OBJECT-TYPE
    SYNTAX     Counter32
    MAX-ACCESS read-only
    STATUS     current
    DESCRIPTION
        "The number of PPP sessions that skipped authentications
	 for the associated VPN service"
    ::= { starPPPStatEntry 62 }

starPPPStatNegComp OBJECT-TYPE
    SYNTAX     Counter32
    MAX-ACCESS read-only
    STATUS     current
    DESCRIPTION
        "The number of PPP sessions that negotiated compressions
	 for the associated VPN service"
    ::= { starPPPStatEntry 63 }

starPPPStatCCPNegFailComp OBJECT-TYPE
    SYNTAX     Counter32
    MAX-ACCESS read-only
    STATUS     current
    DESCRIPTION
        "The number of PPP sessions that failed compression negotiation
	 for the associated VPN service"
    ::= { starPPPStatEntry 64 }

starPPPStatDiscLocalLowerLayer OBJECT-TYPE
    SYNTAX     Counter32
    MAX-ACCESS read-only
    STATUS     current
    DESCRIPTION
        "The number of disconnected PPP sessions due to local RP disconnect
	 for the associated VPN service"
    ::= { starPPPStatEntry 65 }

starPPPStatDiscAddFlowFail OBJECT-TYPE
    SYNTAX     Counter32
    MAX-ACCESS read-only
    STATUS     current
    DESCRIPTION
        "The number of disconnected PPP sessions due to failure in adding new flow
	 for the associated VPN service"
    ::= { starPPPStatEntry 66 }

starPPPStatDiscMaxRetriesLCP OBJECT-TYPE
    SYNTAX     Counter32
    MAX-ACCESS read-only
    STATUS     current
    DESCRIPTION
        "The number of disconnected PPP sessions due to max retries for LCP
	 for the associated VPN service"
    ::= { starPPPStatEntry 67 }

starPPPStatDiscMaxRetriesIPCP OBJECT-TYPE
    SYNTAX     Counter32
    MAX-ACCESS read-only
    STATUS     current
    DESCRIPTION
        "The number of disconnected PPP sessions due to max retries for IPCP
	 for the associated VPN service"
    ::= { starPPPStatEntry 68 }

starPPPStatDiscMaxSetupTimer OBJECT-TYPE
    SYNTAX     Counter32
    MAX-ACCESS read-only
    STATUS     current
    DESCRIPTION
        "The number of disconnected PPP sessions due to max setup time out
	 for the associated VPN service"
    ::= { starPPPStatEntry 69 }

starPPPStatDiscInvalidDestVpn OBJECT-TYPE
    SYNTAX     Counter32
    MAX-ACCESS read-only
    STATUS     current
    DESCRIPTION
        "The number of disconnected PPP sessions due to invalid destination VPN
	 for the associated VPN service"
    ::= { starPPPStatEntry 70 }

starPPPStatDiscOptNegFailLCP OBJECT-TYPE
    SYNTAX     Counter32
    MAX-ACCESS read-only
    STATUS     current
    DESCRIPTION
        "The number of disconnected PPP sessions due to invalid destination VPN
	 for the associated VPN service"
    ::= { starPPPStatEntry 71 }

starPPPStatDiscOptNegFailIPCP OBJECT-TYPE
    SYNTAX     Counter32
    MAX-ACCESS read-only
    STATUS     current
    DESCRIPTION
        "The number of disconnected PPP sessions due to failed IPCP option negotiation
	 for the associated VPN service"
    ::= { starPPPStatEntry 72 }

starPPPStatDiscNoRemoteIpAddr OBJECT-TYPE
    SYNTAX     Counter32
    MAX-ACCESS read-only
    STATUS     current
    DESCRIPTION
        "The number of disconnected PPP sessions due to no remote ip address
	 for the associated VPN service"
    ::= { starPPPStatEntry 73 }

starPPPStatDiscCallTypeDetectFail OBJECT-TYPE
    SYNTAX     Counter32
    MAX-ACCESS read-only
    STATUS     current
    DESCRIPTION
        "The number of disconnected PPP sessions due to failure detecting call type
	 for the associated VPN service"
    ::= { starPPPStatEntry 74 }

starPPPStatDiscRemoteDiscUpLayer OBJECT-TYPE
    SYNTAX     Counter32
    MAX-ACCESS read-only
    STATUS     current
    DESCRIPTION
        "The number of disconnected PPP sessions due to failure detecting call type
	 for the associated VPN service"
    ::= { starPPPStatEntry 75 }

starPPPStatDiscLongDuraTimeout OBJECT-TYPE
    SYNTAX     Counter32
    MAX-ACCESS read-only
    STATUS     current
    DESCRIPTION
        "The number of disconnected PPP sessions due to long duration time out
	 for the associated VPN service"
    ::= { starPPPStatEntry 76 }

starPPPStatDiscAuthFail OBJECT-TYPE
    SYNTAX     Counter32
    MAX-ACCESS read-only
    STATUS     current
    DESCRIPTION
        "The number of disconnected PPP sessions due to failed authentication
	 for the associated VPN service"
    ::= { starPPPStatEntry 77 }

starPPPStatLCPEchoTotalReq OBJECT-TYPE
    SYNTAX     Counter32
    MAX-ACCESS read-only
    STATUS     current
    DESCRIPTION
        "The total number of PPP LCP echo requests
	 for the associated VPN service"
    ::= { starPPPStatEntry 78 }

starPPPStatLCPEchoReqResent OBJECT-TYPE
    SYNTAX     Counter32
    MAX-ACCESS read-only
    STATUS     current
    DESCRIPTION
        "The total number of PPP LCP echo requests resent
	 for the associated VPN service"
    ::= { starPPPStatEntry 79 }

starPPPStatLCPEchoRepRecved OBJECT-TYPE
    SYNTAX     Counter32
    MAX-ACCESS read-only
    STATUS     current
    DESCRIPTION
        "The total number of PPP LCP echo replys received
	 for the associated VPN service"
    ::= { starPPPStatEntry 80 }

starPPPStatLCPEchoReqTimeout OBJECT-TYPE
    SYNTAX     Counter32
    MAX-ACCESS read-only
    STATUS     current
    DESCRIPTION
        "The total number of PPP LCP echo requests time out
	 for the associated VPN service"
    ::= { starPPPStatEntry 81 }

starPPPStatRecvErrBadCtrlField OBJECT-TYPE
    SYNTAX     Counter32
    MAX-ACCESS read-only
    STATUS     current
    DESCRIPTION
        "The total number of received PPP error due to bad control fields
	 for the associated VPN service"
    ::= { starPPPStatEntry 82 }

starPPPStatRecvErrBadPacketLen OBJECT-TYPE
    SYNTAX     Counter32
    MAX-ACCESS read-only
    STATUS     current
    DESCRIPTION
        "The total number of received PPP error due to bad packet length
	 for the associated VPN service"
    ::= { starPPPStatEntry 83 }

starPPPStatRemoteTerm OBJECT-TYPE
    SYNTAX     Counter32
    MAX-ACCESS read-only
    STATUS     current
    DESCRIPTION
        "The total number of PPP remote terminations
	 for the associated VPN service"
    ::= { starPPPStatEntry 84 }

starPPPStatMiscFail OBJECT-TYPE
    SYNTAX     Counter32
    MAX-ACCESS read-only
    STATUS     current
    DESCRIPTION
        "The number of misc PPP failures
	 for the associated VPN service"
    ::= { starPPPStatEntry 85 }


-- MIPHA Stats

starentMIPHA OBJECT IDENTIFIER ::= { starentMIBObjects 22 }

starMIPHAStatTable OBJECT-TYPE
    SYNTAX     SEQUENCE OF StarMIPHAStatEntry
    MAX-ACCESS not-accessible
    STATUS     current
    DESCRIPTION
        "A table containing MIP HA Stats"
    ::= { starentMIPHA 1 }

starMIPHAStatEntry OBJECT-TYPE
    SYNTAX     StarMIPHAStatEntry
    MAX-ACCESS not-accessible
    STATUS     current
    DESCRIPTION
        "The Mobile IP home agent statistics for a specific VPN (context) and service"
    INDEX { IMPLIED starMIPHAStatSvcID }
    ::= { starMIPHAStatTable 1 }

StarMIPHAStatEntry ::=
    SEQUENCE {
        starMIPHAStatVpnID                 Gauge32,
        starMIPHAStatSvcID                 StarShortID,
        starMIPHAStatVpnName               DisplayString,
        starMIPHAStatServName              DisplayString,
        starMIPHAStatDisconnects           Counter32,
        starMIPHAStatExpiry                Counter32,
        starMIPHAStatDereg                 Counter32,
        starMIPHAStatAdminDrop             Counter32,
        starMIPHAStatRegRecvTotal          Counter32,
        starMIPHAStatRegRecvInitial        Counter32,
        starMIPHAStatRegRecvRenew          Counter32,
        starMIPHAStatRegRecvDereg          Counter32,
        starMIPHAStatRegAcceptTotal        Counter32,
        starMIPHAStatRegAcceptReg          Counter32,
        starMIPHAStatRegAcceptRenew        Counter32,
        starMIPHAStatRegAcceptDereg        Counter32,
        starMIPHAStatRegDeniedTotal        Counter32,
        starMIPHAStatRegDeniedInitial      Counter32,
        starMIPHAStatRegDeniedRenew        Counter32,
        starMIPHAStatRegDeniedDereg        Counter32,
        starMIPHAStatRegReplyTotal         Counter32,
        starMIPHAStatRegReplyAcceptReg     Counter32,
        starMIPHAStatRegReplyAcceptDereg   Counter32,
        starMIPHAStatRegReplyDenied        Counter32,
        starMIPHAStatRegReplyBadReq        Counter32,
        starMIPHAStatRegReplyMismatchID    Counter32,
        starMIPHAStatRegReplyAdminProhib   Counter32,
        starMIPHAStatRegReplyUnspecErr     Counter32,
        starMIPHAStatRegReplyNoResource    Counter32,
        starMIPHAStatRegReplyMnAuthFail    Counter32,
        starMIPHAStatRegReplyFAAuthFail    Counter32,
        starMIPHAStatRegReplySimulBind     Counter32,
        starMIPHAStatRegReplyUnknownHA     Counter32,
        starMIPHAStatRegReplyRevTunUnav    Counter32,
        starMIPHAStatRegReplyRevTunMand    Counter32,
        starMIPHAStatRegReplyEncapUnav     Counter32,
        starMIPHAStatRegReplySendError     Counter32,
	starMIPHAStatFARevocations         Counter32,
	starMIPHAStatRegAcceptHO           Counter32,
	starMIPHAStatRegDeniedHO           Counter32,
	starMIPHAStatRegDiscardTotal       Counter32
    }

starMIPHAStatVpnID OBJECT-TYPE
    SYNTAX     Gauge32
    MAX-ACCESS read-only
    STATUS     current
    DESCRIPTION
        "The internal identification of the home agent Mobile IP VPN (context)"
    ::= { starMIPHAStatEntry 1 }

starMIPHAStatSvcID OBJECT-TYPE
    SYNTAX     StarShortID
    MAX-ACCESS not-accessible
    STATUS     current
    DESCRIPTION
        "The service identification is made up from first 8 chars of context name
         and first 8 chars of service name separated by (:)"
    ::= { starMIPHAStatEntry 2 }

starMIPHAStatVpnName OBJECT-TYPE
    SYNTAX     DisplayString
    MAX-ACCESS read-only
    STATUS     current
    DESCRIPTION
        "The name of the VPN (context)"
    ::= { starMIPHAStatEntry 3 }

starMIPHAStatServName OBJECT-TYPE
    SYNTAX     DisplayString
    MAX-ACCESS read-only
    STATUS     current
    DESCRIPTION
        "The Mobile IP home agent service name"
    ::= { starMIPHAStatEntry 4 }

starMIPHAStatDisconnects OBJECT-TYPE
    SYNTAX     Counter32
    MAX-ACCESS read-only
    STATUS     current
    DESCRIPTION
        "The number of session disconnects for the associated Mobile IP home agent VPN service"
    ::= { starMIPHAStatEntry 5 }

starMIPHAStatExpiry OBJECT-TYPE
    SYNTAX     Counter32
    MAX-ACCESS read-only
    STATUS     current
    DESCRIPTION
        "The number of session expirations for the associated Mobile IP home agent VPN service"
    ::= { starMIPHAStatEntry 6 }

starMIPHAStatDereg OBJECT-TYPE
    SYNTAX     Counter32
    MAX-ACCESS read-only
    STATUS     current
    DESCRIPTION
        "The number of session deregistrations for the associated Mobile IP home agent VPN service"
    ::= { starMIPHAStatEntry 7 }

starMIPHAStatAdminDrop OBJECT-TYPE
    SYNTAX     Counter32
    MAX-ACCESS read-only
    STATUS     current
    DESCRIPTION
        "The number of session disconnects due to administrator actions
	 for the associated Mobile IP home agent VPN"
    ::= { starMIPHAStatEntry 8 }

starMIPHAStatRegRecvTotal OBJECT-TYPE
    SYNTAX     Counter32
    MAX-ACCESS read-only
    STATUS     current
    DESCRIPTION
        "The number of session registrations received for the associated Mobile IP home agent VPN service"
    ::= { starMIPHAStatEntry 9 }

starMIPHAStatRegRecvInitial OBJECT-TYPE
    SYNTAX     Counter32
    MAX-ACCESS read-only
    STATUS     current
    DESCRIPTION
        "The number of initial session registrations received for the associated Mobile IP home agent VPN service"
    ::= { starMIPHAStatEntry 10 }

starMIPHAStatRegRecvRenew OBJECT-TYPE
    SYNTAX     Counter32
    MAX-ACCESS read-only
    STATUS     current
    DESCRIPTION
        "The number of session registration renewals received for the associated Mobile IP home agent VPN service"
    ::= { starMIPHAStatEntry 11 }

starMIPHAStatRegRecvDereg OBJECT-TYPE
    SYNTAX     Counter32
    MAX-ACCESS read-only
    STATUS     current
    DESCRIPTION
        "The number of session deregistrations received for the associated Mobile IP home agent VPN service"
    ::= { starMIPHAStatEntry 12 }

starMIPHAStatRegAcceptTotal OBJECT-TYPE
    SYNTAX     Counter32
    MAX-ACCESS read-only
    STATUS     current
    DESCRIPTION
        "The number of session registrations accepted for the associated Mobile IP home agent VPN service"
    ::= { starMIPHAStatEntry 13 }

starMIPHAStatRegAcceptReg OBJECT-TYPE
    SYNTAX     Counter32
    MAX-ACCESS read-only
    STATUS     current
    DESCRIPTION
        "The number of session registrations accepted for the associated Mobile IP home agent VPN service"
    ::= { starMIPHAStatEntry 14 }

starMIPHAStatRegAcceptRenew OBJECT-TYPE
    SYNTAX     Counter32
    MAX-ACCESS read-only
    STATUS     current
    DESCRIPTION
        "The number of session registration renewals accepted for the associated Mobile IP home agent VPN service"
    ::= { starMIPHAStatEntry 15 }

starMIPHAStatRegAcceptDereg OBJECT-TYPE
    SYNTAX     Counter32
    MAX-ACCESS read-only
    STATUS     current
    DESCRIPTION
        "The number of session deregistrations accepted for the associated Mobile IP home agent VPN service"
    ::= { starMIPHAStatEntry 16 }

starMIPHAStatRegDeniedTotal OBJECT-TYPE
    SYNTAX     Counter32
    MAX-ACCESS read-only
    STATUS     current
    DESCRIPTION
        "The number of session registrations denied for the associated Mobile IP home agent VPN service"
    ::= { starMIPHAStatEntry 17 }

starMIPHAStatRegDeniedInitial OBJECT-TYPE
    SYNTAX     Counter32
    MAX-ACCESS read-only
    STATUS     current
    DESCRIPTION
        "The number of session initial registrations denied for the associated Mobile IP home agent VPN service"
    ::= { starMIPHAStatEntry 18 }

starMIPHAStatRegDeniedRenew OBJECT-TYPE
    SYNTAX     Counter32
    MAX-ACCESS read-only
    STATUS     current
    DESCRIPTION
        "The number of session registration renewals denied for the associated Mobile IP home agent VPN service"
    ::= { starMIPHAStatEntry 19 }

starMIPHAStatRegDeniedDereg OBJECT-TYPE
    SYNTAX     Counter32
    MAX-ACCESS read-only
    STATUS     current
    DESCRIPTION
        "The number of session deregistrations denied for the associated Mobile IP home agent VPN service"
    ::= { starMIPHAStatEntry 20 }

starMIPHAStatRegReplyTotal OBJECT-TYPE
    SYNTAX     Counter32
    MAX-ACCESS read-only
    STATUS     current
    DESCRIPTION
        "The total number of session registration replies for the associated Mobile IP home agent VPN service"
    ::= { starMIPHAStatEntry 21 }

starMIPHAStatRegReplyAcceptReg OBJECT-TYPE
    SYNTAX     Counter32
    MAX-ACCESS read-only
    STATUS     current
    DESCRIPTION
        "The number of session registration replies accepted indicating registration
	 for the associated Mobile IP home agent VPN service"
    ::= { starMIPHAStatEntry 22 }

starMIPHAStatRegReplyAcceptDereg OBJECT-TYPE
    SYNTAX     Counter32
    MAX-ACCESS read-only
    STATUS     current
    DESCRIPTION
        "The number of session registration replies accepted indicated deregistration
	 for the associated Mobile IP home agent VPN service"
    ::= { starMIPHAStatEntry 23 }

starMIPHAStatRegReplyDenied OBJECT-TYPE
    SYNTAX     Counter32
    MAX-ACCESS read-only
    STATUS     current
    DESCRIPTION
        "The number of session registration replies which were denied
	 for the associated Mobile IP home agent VPN service"
    ::= { starMIPHAStatEntry 24 }

starMIPHAStatRegReplyBadReq OBJECT-TYPE
    SYNTAX     Counter32
    MAX-ACCESS read-only
    STATUS     current
    DESCRIPTION
        "The number of session registration replies indicating a bad request
	 for the associated Mobile IP home agent VPN service"
    ::= { starMIPHAStatEntry 25 }

starMIPHAStatRegReplyMismatchID OBJECT-TYPE
    SYNTAX     Counter32
    MAX-ACCESS read-only
    STATUS     current
    DESCRIPTION
        "The number of session registration replies indicating an ID mismatch
	 for the associated Mobile IP home agent VPN service"
    ::= { starMIPHAStatEntry 26 }

starMIPHAStatRegReplyAdminProhib OBJECT-TYPE
    SYNTAX     Counter32
    MAX-ACCESS read-only
    STATUS     current
    DESCRIPTION
        "The number of session registration replies indicating administrator prohibition
	 for the associated Mobile IP home agent VPN service"
    ::= { starMIPHAStatEntry 27 }

starMIPHAStatRegReplyUnspecErr OBJECT-TYPE
    SYNTAX     Counter32
    MAX-ACCESS read-only
    STATUS     current
    DESCRIPTION
        "The number of session registration replies with an unspecified error
	 for the associated Mobile IP home agent VPN service"
    ::= { starMIPHAStatEntry 28 }

starMIPHAStatRegReplyNoResource OBJECT-TYPE
    SYNTAX     Counter32
    MAX-ACCESS read-only
    STATUS     current
    DESCRIPTION
        "The number of session registration replies indicating no resources
	 for the associated Mobile IP home agent VPN service"
    ::= { starMIPHAStatEntry 29 }

starMIPHAStatRegReplyMnAuthFail OBJECT-TYPE
    SYNTAX     Counter32
    MAX-ACCESS read-only
    STATUS     current
    DESCRIPTION
        "The number of session registration replies indication mobile number authentication failure
	 for the associated Mobile IP home agent VPN service"
    ::= { starMIPHAStatEntry 30 }

starMIPHAStatRegReplyFAAuthFail OBJECT-TYPE
    SYNTAX     Counter32
    MAX-ACCESS read-only
    STATUS     current
    DESCRIPTION
        "The number of session registration replies indicating a foreign agent authentication
	 failure for the associated Mobile IP home agent VPN service"
    ::= { starMIPHAStatEntry 31 }

starMIPHAStatRegReplySimulBind OBJECT-TYPE
    SYNTAX     Counter32
    MAX-ACCESS read-only
    STATUS     current
    DESCRIPTION
        "The number of session registration replies indicating a simultaneous bind condition
	 for the associated Mobile IP home agent VPN service"
    ::= { starMIPHAStatEntry 32 }

starMIPHAStatRegReplyUnknownHA OBJECT-TYPE
    SYNTAX     Counter32
    MAX-ACCESS read-only
    STATUS     current
    DESCRIPTION
        "The number of session registration replies indicating unknown home agent
	 for the associated Mobile IP home agent VPN service"
    ::= { starMIPHAStatEntry 33 }

starMIPHAStatRegReplyRevTunUnav OBJECT-TYPE
    SYNTAX     Counter32
    MAX-ACCESS read-only
    STATUS     current
    DESCRIPTION
        "The number of session registration replies indicating no reverse tunnel available
	 for the associated Mobile IP home agent VPN service"
    ::= { starMIPHAStatEntry 34 }

starMIPHAStatRegReplyRevTunMand OBJECT-TYPE
    SYNTAX     Counter32
    MAX-ACCESS read-only
    STATUS     current
    DESCRIPTION
        "The number of session registration replies indicating reverse tunneling is
	 mandatory for the associated Mobile IP home agent VPN service"
    ::= { starMIPHAStatEntry 35 }

starMIPHAStatRegReplyEncapUnav OBJECT-TYPE
    SYNTAX     Counter32
    MAX-ACCESS read-only
    STATUS     current
    DESCRIPTION
        "The number of session registration replies indicating IP encapsulation was not
	 available for the associated Mobile IP home agent VPN service"
    ::= { starMIPHAStatEntry 36 }

starMIPHAStatRegReplySendError OBJECT-TYPE
    SYNTAX     Counter32
    MAX-ACCESS read-only
    STATUS     current
    DESCRIPTION
        "The number of session registration replies indicating a send error occurred
	 for the associated Mobile IP home agent VPN service"
    ::= { starMIPHAStatEntry 37 }

starMIPHAStatFARevocations OBJECT-TYPE
    SYNTAX     Counter32
    MAX-ACCESS read-only
    STATUS     current
    DESCRIPTION
        "The number of FA revocations
	 for the associated Mobile IP home agent VPN service"
    ::= { starMIPHAStatEntry 38 }

starMIPHAStatRegAcceptHO OBJECT-TYPE
    SYNTAX     Counter32
    MAX-ACCESS read-only
    STATUS     current
    DESCRIPTION
        "The number of hand over session registrations accepted
	 for the associated Mobile IP home agent VPN service"
    ::= { starMIPHAStatEntry 39 }

starMIPHAStatRegDeniedHO OBJECT-TYPE
    SYNTAX     Counter32
    MAX-ACCESS read-only
    STATUS     current
    DESCRIPTION
        "The number of hand over session registrations denied
	 for the associated Mobile IP home agent VPN service"
    ::= { starMIPHAStatEntry 40 }

starMIPHAStatRegDiscardTotal OBJECT-TYPE
    SYNTAX     Counter32
    MAX-ACCESS read-only
    STATUS     current
    DESCRIPTION
        "The number of session registrations discarded
	 for the associated Mobile IP home agent VPN service"
    ::= { starMIPHAStatEntry 41 }

-- MIPFA Stats

starentMIPFA OBJECT IDENTIFIER ::= { starentMIBObjects 23 }

starMIPFAStatTable OBJECT-TYPE
    SYNTAX     SEQUENCE OF StarMIPFAStatEntry
    MAX-ACCESS not-accessible
    STATUS     current
    DESCRIPTION
        "A table containing MIP FA Stats"
    ::= { starentMIPFA 1 }

starMIPFAStatEntry OBJECT-TYPE
    SYNTAX     StarMIPFAStatEntry
    MAX-ACCESS not-accessible
    STATUS     current
    DESCRIPTION
        "The statistics for a specific foreign agent Mobile IP VPN (context) service"
    INDEX { IMPLIED starMIPFAStatSvcID }
    ::= { starMIPFAStatTable 1 }

StarMIPFAStatEntry ::=
    SEQUENCE {
        starMIPFAStatVpnID                      Gauge32,
        starMIPFAStatSvcID                      StarShortID,
        starMIPFAStatVpnName                    DisplayString,
        starMIPFAStatServName                   DisplayString,
        starMIPFAStatAdvertSend                 Counter32,
        starMIPFAStatDiscExpiry                 Counter32,
        starMIPFAStatDiscDereg                  Counter32,
        starMIPFAStatDiscAdmin                  Counter32,
        starMIPFAStatAuthAttempt                Counter32,
        starMIPFAStatAuthSuccess                Counter32,
        starMIPFAStatAuthFailure                Counter32,
        starMIPFAStatRegRecvTotal               Counter32,
        starMIPFAStatRegRecvInitial             Counter32,
        starMIPFAStatRegRecvRenewal             Counter32,
        starMIPFAStatRegRecvDereg               Counter32,
        starMIPFAStatRegAcceptTotal             Counter32,
        starMIPFAStatRegAcceptInitial           Counter32,
        starMIPFAStatRegAcceptRenewal           Counter32,
        starMIPFAStatRegAcceptDereg             Counter32,
        starMIPFAStatRegDenTotal             Counter32,
        starMIPFAStatRegDenInitial           Counter32,
        starMIPFAStatRegDenRenewal           Counter32,
        starMIPFAStatRegDenDereg             Counter32,
        starMIPFAStatRegDiscardTotal         Counter32,
        starMIPFAStatRegDiscardInitial       Counter32,
        starMIPFAStatRegDiscardRenewal       Counter32,
        starMIPFAStatRegDiscardDereg         Counter32,
        starMIPFAStatRegRelayedTotal         Counter32,
        starMIPFAStatRegRelayedInitial       Counter32,
        starMIPFAStatRegRelayedRenewal       Counter32,
        starMIPFAStatRegRelayedDereg         Counter32,
        starMIPFAStatRegAuthFailTotal        Counter32,
        starMIPFAStatRegAuthFailInitial      Counter32,
        starMIPFAStatRegAuthFailRenewal      Counter32,
        starMIPFAStatRegAuthFailDereg        Counter32,
        starMIPFAStatRegDenPDSNTotal         Counter32,
        starMIPFAStatRegDenPDSNInitial       Counter32,
        starMIPFAStatRegDenPDSNRenewal       Counter32,
        starMIPFAStatRegDenPDSNDereg         Counter32,
        starMIPFAStatRegDenHATotal           Counter32,
        starMIPFAStatRegDenHAInitial         Counter32,
        starMIPFAStatRegDenHARenewal         Counter32,
        starMIPFAStatRegDenHADereg           Counter32,
        starMIPFAStatRegDenPDSNUnspec        Counter32,
        starMIPFAStatRegDenPDSNTimeout       Counter32,
        starMIPFAStatRegDenPDSNAdmin         Counter32,
        starMIPFAStatRegDenPDSNResources     Counter32,
        starMIPFAStatRegDenPDSNMnAuth        Counter32,
        starMIPFAStatRegDenPDSNHAAuth        Counter32,
        starMIPFAStatRegDenPDSNTooLong       Counter32,
        starMIPFAStatRegDenPDSNBadReq        Counter32,
        starMIPFAStatRegDenPDSNEncapUnav     Counter32,
        starMIPFAStatRegDenPDSNRevTunUnav    Counter32,
        starMIPFAStatRegDenPDSNRevTunMand    Counter32,
        starMIPFAStatRegDenHAFAAuth          Counter32,
        starMIPFAStatRegDenHABadReq          Counter32,
        starMIPFAStatRegDenHAMismatchID      Counter32,
        starMIPFAStatRegDenHASimulBind       Counter32,
        starMIPFAStatRegDenHAUnknownHA       Counter32,
        starMIPFAStatRegDenHARevRunUnavail   Counter32,
        starMIPFAStatRegRplRcvTotal           Counter32,
        starMIPFAStatRegRplRcvTotalRly        Counter32,
        starMIPFAStatRegRplRcvErrors          Counter32,
        starMIPFAStatRegRplRcvInitial         Counter32,
        starMIPFAStatRegRplRcvInitialRly      Counter32,
        starMIPFAStatRegRplRcvRenewal         Counter32,
        starMIPFAStatRegRplRcvRenewalRly      Counter32,
        starMIPFAStatRegRplRcvDereg           Counter32,
        starMIPFAStatRegRplRcvDeregRly        Counter32,
        starMIPFAStatRegRplSentTotal          Counter32,
        starMIPFAStatRegRplSentAcceptReg      Counter32,
        starMIPFAStatRegRplSentAcceptDereg    Counter32,
        starMIPFAStatRegRplSentBadReq         Counter32,
        starMIPFAStatRegRplSentTooLong        Counter32,
        starMIPFAStatRegRplSentMnAuthFail     Counter32,
        starMIPFAStatRegRplSentHAAuthFail     Counter32,
        starMIPFAStatRegRplSentAdminProhib    Counter32,
        starMIPFAStatRegRplSentNoResources    Counter32,
        starMIPFAStatRegRplSentRevTunUnav     Counter32,
        starMIPFAStatRegRplSentRevTunMand     Counter32,
        starMIPFAStatRegRplSentSendErrors     Counter32,
	starMIPFAStatRegDenPDSNBadReply         Counter32,
	starMIPFAStatRegDenPDSNMissNAI          Counter32,
	starMIPFAStatRegDenPDSNMissHomeAgent    Counter32,
	starMIPFAStatRegDenPDSNMissHomeAddr     Counter32,
	starMIPFAStatRegDenPDSNUnknChallenge    Counter32,
	starMIPFAStatRegDenPDSNMissChallenge    Counter32,
	starMIPFAStatRegDenPDSNStaleChallenge   Counter32,
	starMIPFAStatRegDenPDSNMNTooDistant     Counter32,
	starMIPFAStatRegDenPDSNStyleUnavail     Counter32,
	starMIPFAStatRegDenPDSNHANetUnreach     Counter32,
	starMIPFAStatRegDenPDSNHAHostUnreach    Counter32,
	starMIPFAStatRegDenPDSNHAPortUnreach    Counter32,
	starMIPFAStatRegDenPDSNHAUnreach        Counter32,
	starMIPFAStatRegDenPDSNInvCOA           Counter32,
	starMIPFAStatRegReqSentInitTotal        Counter32,
	starMIPFAStatRegReqSentInitResend       Counter32,
	starMIPFAStatRegReqSentRenewTotal       Counter32,
	starMIPFAStatRegReqSentRenewResend      Counter32,
	starMIPFAStatRegReqSentDeregTotal       Counter32,
	starMIPFAStatRegReqSentDeregResend      Counter32,
	starMIPFAStatRegRplSentMNTooDistant     Counter32,
	starMIPFAStatRegRplSentInvCOA           Counter32,
	starMIPFAStatRegRplSentHANetUnreach     Counter32,
	starMIPFAStatRegRplSentHAHostUnreach    Counter32,
	starMIPFAStatRegRplSentHAPortUnreach    Counter32,
	starMIPFAStatRegRplSentHAUnreach        Counter32,
	starMIPFAStatRegRplSentRegTimeout       Counter32,
	starMIPFAStatRegRplSentMissNAI          Counter32,
	starMIPFAStatRegRplSentMissHomeAgent    Counter32,
	starMIPFAStatRegRplSentMissHomeAddr     Counter32,
	starMIPFAStatRegRplSentUnknChallenge    Counter32,
	starMIPFAStatRegRplSentMissChallenge    Counter32,
	starMIPFAStatRegRplSentStaleChallenge   Counter32,
	starMIPFAStatRegRplSentBadReply         Counter32
}

starMIPFAStatVpnID OBJECT-TYPE
    SYNTAX     Gauge32
    MAX-ACCESS read-only
    STATUS     current
    DESCRIPTION
        "Internal identication of the foreign agent Mobile IP VPN (context)"
    ::= { starMIPFAStatEntry 1 }

starMIPFAStatSvcID OBJECT-TYPE
    SYNTAX     StarShortID
    MAX-ACCESS not-accessible
    STATUS     current
    DESCRIPTION
        "The service identification is made up from first 8 chars of context name
         and first 8 chars of service name separated by (:)"
    ::= { starMIPFAStatEntry 2 }

starMIPFAStatVpnName OBJECT-TYPE
    SYNTAX     DisplayString
    MAX-ACCESS read-only
    STATUS     current
    DESCRIPTION
        "The foreign agent mobile IP VPN (context) name"
    ::= { starMIPFAStatEntry 3 }

starMIPFAStatServName OBJECT-TYPE
    SYNTAX     DisplayString
    MAX-ACCESS read-only
    STATUS     current
    DESCRIPTION
        "The Mobile IP foreign agent service name"
    ::= { starMIPFAStatEntry 4 }

starMIPFAStatAdvertSend OBJECT-TYPE
    SYNTAX     Counter32
    MAX-ACCESS read-only
    STATUS     current
    DESCRIPTION
        "The number of advertisements sent for the associated Mobile IP foreign agent VPN service"
    ::= { starMIPFAStatEntry 5 }

starMIPFAStatDiscExpiry OBJECT-TYPE
    SYNTAX     Counter32
    MAX-ACCESS read-only
    STATUS     current
    DESCRIPTION
        "The number of session disconnects due to expiration for the associated Mobile IP foreign agent VPN service"
    ::= { starMIPFAStatEntry 6 }

starMIPFAStatDiscDereg OBJECT-TYPE
    SYNTAX     Counter32
    MAX-ACCESS read-only
    STATUS     current
    DESCRIPTION
        "The number of session disconnects due to deregistration for the associated Mobile IP foreign agent VPN service"
    ::= { starMIPFAStatEntry 7 }

starMIPFAStatDiscAdmin OBJECT-TYPE
    SYNTAX     Counter32
    MAX-ACCESS read-only
    STATUS     current
    DESCRIPTION
        "The number of dession disconnects due to administrator action for the associated Mobile IP foreign agent VPN service"
    ::= { starMIPFAStatEntry 8 }

starMIPFAStatAuthAttempt OBJECT-TYPE
    SYNTAX     Counter32
    MAX-ACCESS read-only
    STATUS     current
    DESCRIPTION
        "The number of session authentication attempts for the associated Mobile IP foreign agent VPN service"
    ::= { starMIPFAStatEntry 9 }

starMIPFAStatAuthSuccess OBJECT-TYPE
    SYNTAX     Counter32
    MAX-ACCESS read-only
    STATUS     current
    DESCRIPTION
        "The number of session authentication successes for the associated Mobile IP foreign agent VPN service"
    ::= { starMIPFAStatEntry 10 }

starMIPFAStatAuthFailure OBJECT-TYPE
    SYNTAX     Counter32
    MAX-ACCESS read-only
    STATUS     current
    DESCRIPTION
        "The number of session authentication failures for the associated Mobile IP foreign agent VPN service"
    ::= { starMIPFAStatEntry 11 }

starMIPFAStatRegRecvTotal OBJECT-TYPE
    SYNTAX     Counter32
    MAX-ACCESS read-only
    STATUS     current
    DESCRIPTION
        "The total number of session registrations received for the associated Mobile IP foreign agent VPN service"
    ::= { starMIPFAStatEntry 12 }

starMIPFAStatRegRecvInitial OBJECT-TYPE
    SYNTAX     Counter32
    MAX-ACCESS read-only
    STATUS     current
    DESCRIPTION
        "The number of initial session registrations received for the associated Mobile IP foreign agent VPN service"
    ::= { starMIPFAStatEntry 13 }

starMIPFAStatRegRecvRenewal OBJECT-TYPE
    SYNTAX     Counter32
    MAX-ACCESS read-only
    STATUS     current
    DESCRIPTION
        "The number of session registration renewals for the associated Mobile IP foreign agent VPN service"
    ::= { starMIPFAStatEntry 14 }

starMIPFAStatRegRecvDereg OBJECT-TYPE
    SYNTAX     Counter32
    MAX-ACCESS read-only
    STATUS     current
    DESCRIPTION
        "The number of session deregistrations for the associated Mobile IP foreign agent VPN service"
    ::= { starMIPFAStatEntry 15 }

starMIPFAStatRegAcceptTotal OBJECT-TYPE
    SYNTAX     Counter32
    MAX-ACCESS read-only
    STATUS     current
    DESCRIPTION
        "The total number of session registrations accepted for the associated Mobile IP foreign agent VPN service"
    ::= { starMIPFAStatEntry 16 }

starMIPFAStatRegAcceptInitial OBJECT-TYPE
    SYNTAX     Counter32
    MAX-ACCESS read-only
    STATUS     current
    DESCRIPTION
        "The number of initial session registrations accepted for the associated Mobile IP foreign agent VPN service"
    ::= { starMIPFAStatEntry 17 }

starMIPFAStatRegAcceptRenewal OBJECT-TYPE
    SYNTAX     Counter32
    MAX-ACCESS read-only
    STATUS     current
    DESCRIPTION
        "The number of session registration renewals accepted for the associated Mobile IP foreign agent VPN service"
    ::= { starMIPFAStatEntry 18 }

starMIPFAStatRegAcceptDereg OBJECT-TYPE
    SYNTAX     Counter32
    MAX-ACCESS read-only
    STATUS     current
    DESCRIPTION
        "The number of session deregistrations accepted for the associated Mobile IP foreign agent VPN service"
    ::= { starMIPFAStatEntry 19 }

starMIPFAStatRegDenTotal OBJECT-TYPE
    SYNTAX     Counter32
    MAX-ACCESS read-only
    STATUS     current
    DESCRIPTION
        "The total number of session registrations denied for the associated Mobile IP foreign agent VPN service"
    ::= { starMIPFAStatEntry 20 }

starMIPFAStatRegDenInitial OBJECT-TYPE
    SYNTAX     Counter32
    MAX-ACCESS read-only
    STATUS     current
    DESCRIPTION
        "The number of initial session registrations denied for the associated Mobile IP foreign agent VPN service"
    ::= { starMIPFAStatEntry 21 }

starMIPFAStatRegDenRenewal OBJECT-TYPE
    SYNTAX     Counter32
    MAX-ACCESS read-only
    STATUS     current
    DESCRIPTION
        "The number of session registration renewals denied for the associated Mobile IP foreign agent VPN service"
    ::= { starMIPFAStatEntry 22 }

starMIPFAStatRegDenDereg OBJECT-TYPE
    SYNTAX     Counter32
    MAX-ACCESS read-only
    STATUS     current
    DESCRIPTION
        "The number of session deregistrations denied for the associated Mobile IP foreign agent VPN service"
    ::= { starMIPFAStatEntry 23 }

starMIPFAStatRegDiscardTotal OBJECT-TYPE
    SYNTAX     Counter32
    MAX-ACCESS read-only
    STATUS     current
    DESCRIPTION
        "The total number of session registrations discarded for the associated Mobile IP foreign agent VPN service"
    ::= { starMIPFAStatEntry 24 }

starMIPFAStatRegDiscardInitial OBJECT-TYPE
    SYNTAX     Counter32
    MAX-ACCESS read-only
    STATUS     current
    DESCRIPTION
        "The total number of session registrations discarded for the associated Mobile IP foreign agent VPN service"
    ::= { starMIPFAStatEntry 25 }

starMIPFAStatRegDiscardRenewal OBJECT-TYPE
    SYNTAX     Counter32
    MAX-ACCESS read-only
    STATUS     current
    DESCRIPTION
        "The number of session registration renewals discarded for the associated Mobile IP foreign agent VPN service"
    ::= { starMIPFAStatEntry 26 }

starMIPFAStatRegDiscardDereg OBJECT-TYPE
    SYNTAX     Counter32
    MAX-ACCESS read-only
    STATUS     current
    DESCRIPTION
        "The number of dession reregistrations discarded for the associated Mobile IP foreign agent VPN service"
    ::= { starMIPFAStatEntry 27 }

starMIPFAStatRegRelayedTotal OBJECT-TYPE
    SYNTAX     Counter32
    MAX-ACCESS read-only
    STATUS     current
    DESCRIPTION
        "The total number of session registrations relayed for the associated Mobile IP foreign agent VPN service"
    ::= { starMIPFAStatEntry 28 }

starMIPFAStatRegRelayedInitial OBJECT-TYPE
    SYNTAX     Counter32
    MAX-ACCESS read-only
    STATUS     current
    DESCRIPTION
        "The number of initial session registrations relayed for the associated Mobile IP foreign agent VPN service"
    ::= { starMIPFAStatEntry 29 }

starMIPFAStatRegRelayedRenewal OBJECT-TYPE
    SYNTAX     Counter32
    MAX-ACCESS read-only
    STATUS     current
    DESCRIPTION
        "The number of dession registration renewals relayed for the associated Mobile IP foreign agent VPN service"
    ::= { starMIPFAStatEntry 30 }

starMIPFAStatRegRelayedDereg OBJECT-TYPE
    SYNTAX     Counter32
    MAX-ACCESS read-only
    STATUS     current
    DESCRIPTION
        "The number of session deregistrations relayed for the associated Mobile IP foreign agent VPN service"
    ::= { starMIPFAStatEntry 31 }

starMIPFAStatRegAuthFailTotal OBJECT-TYPE
    SYNTAX     Counter32
    MAX-ACCESS read-only
    STATUS     current
    DESCRIPTION
        "The total number of session registration authentication failures for the associated Mobile IP foreign agent VPN service"
    ::= { starMIPFAStatEntry 32 }

starMIPFAStatRegAuthFailInitial OBJECT-TYPE
    SYNTAX     Counter32
    MAX-ACCESS read-only
    STATUS     current
    DESCRIPTION
        "The number of initial session registration failures for the associated Mobile IP foreign agent VPN service"
    ::= { starMIPFAStatEntry 33 }

starMIPFAStatRegAuthFailRenewal OBJECT-TYPE
    SYNTAX     Counter32
    MAX-ACCESS read-only
    STATUS     current
    DESCRIPTION
        "The number of session registration renewal failures for the associated Mobile IP foreign agent VPN service"
    ::= { starMIPFAStatEntry 34 }

starMIPFAStatRegAuthFailDereg OBJECT-TYPE
    SYNTAX     Counter32
    MAX-ACCESS read-only
    STATUS     current
    DESCRIPTION
        "The number of session deregistration authentication failures for the associated Mobile IP foreign agent VPN service"
    ::= { starMIPFAStatEntry 35 }

starMIPFAStatRegDenPDSNTotal OBJECT-TYPE
    SYNTAX     Counter32
    MAX-ACCESS read-only
    STATUS     current
    DESCRIPTION
        "The total number of PDSN session registrations denied for the associated Mobile IP foreign agent VPN service"
    ::= { starMIPFAStatEntry 36 }

starMIPFAStatRegDenPDSNInitial OBJECT-TYPE
    SYNTAX     Counter32
    MAX-ACCESS read-only
    STATUS     current
    DESCRIPTION
        "The number of initial PDSN session registrations denied for the associated Mobile IP foreign agent VPN service"
    ::= { starMIPFAStatEntry 37 }

starMIPFAStatRegDenPDSNRenewal OBJECT-TYPE
    SYNTAX     Counter32
    MAX-ACCESS read-only
    STATUS     current
    DESCRIPTION
        "The number of PDSN session registration renewals denied for the associated Mobile IP foreign agent VPN service"
    ::= { starMIPFAStatEntry 38 }

starMIPFAStatRegDenPDSNDereg OBJECT-TYPE
    SYNTAX     Counter32
    MAX-ACCESS read-only
    STATUS     current
    DESCRIPTION
        "The number of PDSN session deregistrations denied for the associated Mobile IP foreign agent VPN service"
    ::= { starMIPFAStatEntry 39 }

starMIPFAStatRegDenHATotal OBJECT-TYPE
    SYNTAX     Counter32
    MAX-ACCESS read-only
    STATUS     current
    DESCRIPTION
        "The total number of session deregistrations denied by the home agent
	 for the associated Mobile IP foreign agent VPN service"
    ::= { starMIPFAStatEntry 40 }

starMIPFAStatRegDenHAInitial OBJECT-TYPE
    SYNTAX     Counter32
    MAX-ACCESS read-only
    STATUS     current
    DESCRIPTION
        "The number of initial session registrations denied by the home agent
	 for the associated Mobile IP foreign agent VPN service"
    ::= { starMIPFAStatEntry 41 }

starMIPFAStatRegDenHARenewal OBJECT-TYPE
    SYNTAX     Counter32
    MAX-ACCESS read-only
    STATUS     current
    DESCRIPTION
        "The number of session registration renewals denied by the home agent
	 for the associated Mobile IP foreign agent VPN service"
    ::= { starMIPFAStatEntry 42 }

starMIPFAStatRegDenHADereg OBJECT-TYPE
    SYNTAX     Counter32
    MAX-ACCESS read-only
    STATUS     current
    DESCRIPTION
        "The number of session deregistrations denied by the home agent
	 for the associated Mobile IP foreign agent VPN service"
    ::= { starMIPFAStatEntry 43 }

starMIPFAStatRegDenPDSNUnspec OBJECT-TYPE
    SYNTAX     Counter32
    MAX-ACCESS read-only
    STATUS     current
    DESCRIPTION
        "The number of PDSN session registrations denied for an unspecified reason
	 for the associated Mobile IP foreign agent VPN service"
    ::= { starMIPFAStatEntry 44 }

starMIPFAStatRegDenPDSNTimeout OBJECT-TYPE
    SYNTAX     Counter32
    MAX-ACCESS read-only
    STATUS     current
    DESCRIPTION
        "The number of PDSN session registrations denied due to timer expiration
	 for the associated Mobile IP foreign agent VPN service"
    ::= { starMIPFAStatEntry 45 }

starMIPFAStatRegDenPDSNAdmin OBJECT-TYPE
    SYNTAX     Counter32
    MAX-ACCESS read-only
    STATUS     current
    DESCRIPTION
        "The number of PDSN session registrations denied due to administrator prohibition
	 for the associated Mobile IP foreign agent VPN service"
    ::= { starMIPFAStatEntry 46 }

starMIPFAStatRegDenPDSNResources OBJECT-TYPE
    SYNTAX     Counter32
    MAX-ACCESS read-only
    STATUS     current
    DESCRIPTION
        "The number of PDSN session registrations denied due to no resources
	 for the associated Mobile IP foreign agent VPN service"
    ::= { starMIPFAStatEntry 47 }

starMIPFAStatRegDenPDSNMnAuth OBJECT-TYPE
    SYNTAX     Counter32
    MAX-ACCESS read-only
    STATUS     current
    DESCRIPTION
        "The number of PDSN session registrations denied due to mobile number authentication
	 for the associated Mobile IP foreign agent VPN service"
    ::= { starMIPFAStatEntry 48 }

starMIPFAStatRegDenPDSNHAAuth OBJECT-TYPE
    SYNTAX     Counter32
    MAX-ACCESS read-only
    STATUS     current
    DESCRIPTION
        "The number of PDSN session registrations denied by the home agent
	 for the associated Mobile IP foreign agent VPN service"
    ::= { starMIPFAStatEntry 49 }

starMIPFAStatRegDenPDSNTooLong OBJECT-TYPE
    SYNTAX     Counter32
    MAX-ACCESS read-only
    STATUS     current
    DESCRIPTION
        "The number of PDSN session registrations denied due to a life too long indication
	 for the associated Mobile IP foreign agent VPN service"
    ::= { starMIPFAStatEntry 50 }

starMIPFAStatRegDenPDSNBadReq OBJECT-TYPE
    SYNTAX     Counter32
    MAX-ACCESS read-only
    STATUS     current
    DESCRIPTION
        "The number of PDSN session registrations denied due to a bad request indication
	 for the associated Mobile IP foreign agent VPN service"
    ::= { starMIPFAStatEntry 51 }

starMIPFAStatRegDenPDSNEncapUnav OBJECT-TYPE
    SYNTAX     Counter32
    MAX-ACCESS read-only
    STATUS     current
    DESCRIPTION
        "The number of PDSN session registrations denied due to no IP encapsulation available
	 for the associated Mobile IP foreign agent VPN service"
    ::= { starMIPFAStatEntry 52 }

starMIPFAStatRegDenPDSNRevTunUnav OBJECT-TYPE
    SYNTAX     Counter32
    MAX-ACCESS read-only
    STATUS     current
    DESCRIPTION
        "The number of PDSN session registrations denied due to no reverse tunnel available
	 for the associated Mobile IP foreign agent VPN service"
    ::= { starMIPFAStatEntry 53 }

starMIPFAStatRegDenPDSNRevTunMand OBJECT-TYPE
    SYNTAX     Counter32
    MAX-ACCESS read-only
    STATUS     current
    DESCRIPTION
        "The number of PDSN session registration denied due to reverse tunneling being
	 mandatory for the associated Mobile IP foreign agent VPN service"
    ::= { starMIPFAStatEntry 54 }

starMIPFAStatRegDenHAFAAuth OBJECT-TYPE
    SYNTAX     Counter32
    MAX-ACCESS read-only
    STATUS     current
    DESCRIPTION
        "The number of PDSN registrations denied by the home agent due to authentication
	 failure for the associated Mobile IP foreign agent VPN service"
    ::= { starMIPFAStatEntry 55 }

starMIPFAStatRegDenHABadReq OBJECT-TYPE
    SYNTAX     Counter32
    MAX-ACCESS read-only
    STATUS     current
    DESCRIPTION
        "The number of session registration denied by the home agent due to the request
	 being invalid for the associated Mobile IP foreign agent VPN service"
    ::= { starMIPFAStatEntry 56 }

starMIPFAStatRegDenHAMismatchID OBJECT-TYPE
    SYNTAX     Counter32
    MAX-ACCESS read-only
    STATUS     current
    DESCRIPTION
        "The number of session registrations denied by the home agent due to an ID
	 mismatch for the associated Mobile IP foreign agent VPN service"
    ::= { starMIPFAStatEntry 57 }

starMIPFAStatRegDenHASimulBind OBJECT-TYPE
    SYNTAX     Counter32
    MAX-ACCESS read-only
    STATUS     current
    DESCRIPTION
        "The number of session registrations denied by the home agent due to a simultaneous
	 bind attempt for the associated Mobile IP foreign agent VPN service"
    ::= { starMIPFAStatEntry 58 }

starMIPFAStatRegDenHAUnknownHA OBJECT-TYPE
    SYNTAX     Counter32
    MAX-ACCESS read-only
    STATUS     current
    DESCRIPTION
        "The number of session registrations denied by the home agent for an unknown reason
	 for the associated Mobile IP foreign agent VPN service"
    ::= { starMIPFAStatEntry 59 }

starMIPFAStatRegDenHARevRunUnavail OBJECT-TYPE
    SYNTAX     Counter32
    MAX-ACCESS read-only
    STATUS     current
    DESCRIPTION
        "The number of session registrations denied by the home agent due to no reverse
	 tunnel being available for the associated Mobile IP foreign agent VPN service"
    ::= { starMIPFAStatEntry 60 }

starMIPFAStatRegRplRcvTotal OBJECT-TYPE
    SYNTAX     Counter32
    MAX-ACCESS read-only
    STATUS     current
    DESCRIPTION
        "The total number of session registration replies received
	 for the associated Mobile IP foreign agent VPN service"
    ::= { starMIPFAStatEntry 61 }

starMIPFAStatRegRplRcvTotalRly OBJECT-TYPE
    SYNTAX     Counter32
    MAX-ACCESS read-only
    STATUS     current
    DESCRIPTION
        "The total number of session registration replies relayed
	 for the associated Mobile IP foreign agent VPN service"
    ::= { starMIPFAStatEntry 62 }

starMIPFAStatRegRplRcvErrors OBJECT-TYPE
    SYNTAX     Counter32
    MAX-ACCESS read-only
    STATUS     current
    DESCRIPTION
        "The total number of session registration replies received indicating errors
	 for the associated Mobile IP foreign agent VPN service"
    ::= { starMIPFAStatEntry 63 }

starMIPFAStatRegRplRcvInitial OBJECT-TYPE
    SYNTAX     Counter32
    MAX-ACCESS read-only
    STATUS     current
    DESCRIPTION
        "The number of initial session registration replies received
	 for the associated Mobile IP foreign agent VPN service"
    ::= { starMIPFAStatEntry 64 }

starMIPFAStatRegRplRcvInitialRly OBJECT-TYPE
    SYNTAX     Counter32
    MAX-ACCESS read-only
    STATUS     current
    DESCRIPTION
        "The number of initial session registration replies relayed
	 for the associated Mobile IP foreign agent VPN service"
    ::= { starMIPFAStatEntry 65 }

starMIPFAStatRegRplRcvRenewal OBJECT-TYPE
    SYNTAX     Counter32
    MAX-ACCESS read-only
    STATUS     current
    DESCRIPTION
        "The number of session registration renewal replies received
	 for the associated Mobile IP foreign agent VPN service"
    ::= { starMIPFAStatEntry 66 }

starMIPFAStatRegRplRcvRenewalRly OBJECT-TYPE
    SYNTAX     Counter32
    MAX-ACCESS read-only
    STATUS     current
    DESCRIPTION
        "The number of session registration renewal replies received
	 for the associated Mobile IP foreign agent VPN service"
    ::= { starMIPFAStatEntry 67 }

starMIPFAStatRegRplRcvDereg OBJECT-TYPE
    SYNTAX     Counter32
    MAX-ACCESS read-only
    STATUS     current
    DESCRIPTION
        "The number of session registration replies received indicating deregistration
	 for the associated Mobile IP foreign agent VPN service"
    ::= { starMIPFAStatEntry 68 }

starMIPFAStatRegRplRcvDeregRly OBJECT-TYPE
    SYNTAX     Counter32
    MAX-ACCESS read-only
    STATUS     current
    DESCRIPTION
        "The number of session registration replies relayed indicating deregistration
	 for the associated Mobile IP foreign agent VPN service"
    ::= { starMIPFAStatEntry 69 }

starMIPFAStatRegRplSentTotal OBJECT-TYPE
    SYNTAX     Counter32
    MAX-ACCESS read-only
    STATUS     current
    DESCRIPTION
        "The total number of session registration replies sent
	 for the associated Mobile IP foreign agent VPN service"
    ::= { starMIPFAStatEntry 70 }

starMIPFAStatRegRplSentAcceptReg OBJECT-TYPE
    SYNTAX     Counter32
    MAX-ACCESS read-only
    STATUS     current
    DESCRIPTION
        "The number of session registration replies which were sent and accepted
	 for the associated Mobile IP foreign agent VPN service"
    ::= { starMIPFAStatEntry 71 }

starMIPFAStatRegRplSentAcceptDereg OBJECT-TYPE
    SYNTAX     Counter32
    MAX-ACCESS read-only
    STATUS     current
    DESCRIPTION
        "The number of session registration replies which were sent and accepted indication
	 deregistration for the associated Mobile IP foreign agent VPN service"
    ::= { starMIPFAStatEntry 72 }

starMIPFAStatRegRplSentBadReq OBJECT-TYPE
    SYNTAX     Counter32
    MAX-ACCESS read-only
    STATUS     current
    DESCRIPTION
        "The number of session registration replies which were sent indicating the request
	 was invalid for the associated Mobile IP foreign agent VPN service"
    ::= { starMIPFAStatEntry 73 }

starMIPFAStatRegRplSentTooLong OBJECT-TYPE
    SYNTAX     Counter32
    MAX-ACCESS read-only
    STATUS     current
    DESCRIPTION
        "The number of session registration replies which were sent indicating life too long
	 for the associated Mobile IP foreign agent VPN service"
    ::= { starMIPFAStatEntry 74 }

starMIPFAStatRegRplSentMnAuthFail OBJECT-TYPE
    SYNTAX     Counter32
    MAX-ACCESS read-only
    STATUS     current
    DESCRIPTION
        "The number of session registration replies which were sent indicating mobile number
	 authentication failure for the associated Mobile IP foreign agent VPN service"
    ::= { starMIPFAStatEntry 75 }

starMIPFAStatRegRplSentHAAuthFail OBJECT-TYPE
    SYNTAX     Counter32
    MAX-ACCESS read-only
    STATUS     current
    DESCRIPTION
        "The number of session registration replies which were sent indicating home agent
	 authentication failure for the associated Mobile IP foreign agent VPN service"
    ::= { starMIPFAStatEntry 76 }

starMIPFAStatRegRplSentAdminProhib OBJECT-TYPE
    SYNTAX     Counter32
    MAX-ACCESS read-only
    STATUS     current
    DESCRIPTION
        "The number of session registration replies which were sent indicating prohibited
	 by the administration for the associated Mobile IP foreign agent VPN service"
    ::= { starMIPFAStatEntry 77 }

starMIPFAStatRegRplSentNoResources OBJECT-TYPE
    SYNTAX     Counter32
    MAX-ACCESS read-only
    STATUS     current
    DESCRIPTION
        "The number of session registration replies which were sent indicating no resources
	 available for the associated Mobile IP foreign agent VPN service"
    ::= { starMIPFAStatEntry 78 }

starMIPFAStatRegRplSentRevTunUnav OBJECT-TYPE
    SYNTAX     Counter32
    MAX-ACCESS read-only
    STATUS     current
    DESCRIPTION
        "The number of session registration replies which were sent indicating no reverse
	 tunnel available for the associated Mobile IP foreign agent VPN service"
    ::= { starMIPFAStatEntry 79 }

starMIPFAStatRegRplSentRevTunMand OBJECT-TYPE
    SYNTAX     Counter32
    MAX-ACCESS read-only
    STATUS     current
    DESCRIPTION
        "The number of session registration replies which were sent indicating reverse
	 tunneling was mandatory for the associated Mobile IP foreign agent VPN service"
    ::= { starMIPFAStatEntry 80 }

starMIPFAStatRegRplSentSendErrors OBJECT-TYPE
    SYNTAX     Counter32
    MAX-ACCESS read-only
    STATUS     current
    DESCRIPTION
        "The number of session registration replies which were sent indicating there were
	 errors in transmission for the associated Mobile IP foreign agent VPN service"
    ::= { starMIPFAStatEntry 81 }

starMIPFAStatRegDenPDSNBadReply OBJECT-TYPE
    SYNTAX     Counter32
    MAX-ACCESS read-only
    STATUS     current
    DESCRIPTION
        "The number of session registrations denied by PDSN due to bad relply from HA
	 for the associated Mobile IP foreign agent VPN service"
    ::= { starMIPFAStatEntry 82 }

starMIPFAStatRegDenPDSNMissNAI OBJECT-TYPE
    SYNTAX     Counter32
    MAX-ACCESS read-only
    STATUS     current
    DESCRIPTION
        "The number of session registrations denied by PDSN due to missing NAI
	 for the associated Mobile IP foreign agent VPN service"
    ::= { starMIPFAStatEntry 83 }

starMIPFAStatRegDenPDSNMissHomeAgent OBJECT-TYPE
    SYNTAX     Counter32
    MAX-ACCESS read-only
    STATUS     current
    DESCRIPTION
        "The number of session registrations denied by PDSN due to missing home agent
	 for the associated Mobile IP foreign agent VPN service"
    ::= { starMIPFAStatEntry 84 }

starMIPFAStatRegDenPDSNMissHomeAddr OBJECT-TYPE
    SYNTAX     Counter32
    MAX-ACCESS read-only
    STATUS     current
    DESCRIPTION
        "The number of session registrations denied by PDSN due to missing home address
	 for the associated Mobile IP foreign agent VPN service"
    ::= { starMIPFAStatEntry 85 }

starMIPFAStatRegDenPDSNUnknChallenge OBJECT-TYPE
    SYNTAX     Counter32
    MAX-ACCESS read-only
    STATUS     current
    DESCRIPTION
        "The number of session registrations denied by PDSN due to unknown challenge
	 for the associated Mobile IP foreign agent VPN service"
    ::= { starMIPFAStatEntry 86 }

starMIPFAStatRegDenPDSNMissChallenge OBJECT-TYPE
    SYNTAX     Counter32
    MAX-ACCESS read-only
    STATUS     current
    DESCRIPTION
        "The number of session registrations denied by PDSN due to missing challenge
	 for the associated Mobile IP foreign agent VPN service"
    ::= { starMIPFAStatEntry 87 }

starMIPFAStatRegDenPDSNStaleChallenge OBJECT-TYPE
    SYNTAX     Counter32
    MAX-ACCESS read-only
    STATUS     current
    DESCRIPTION
        "The number of session registrations denied by PDSN due to stale challenge
	 for the associated Mobile IP foreign agent VPN service"
    ::= { starMIPFAStatEntry 88 }

starMIPFAStatRegDenPDSNMNTooDistant OBJECT-TYPE
    SYNTAX     Counter32
    MAX-ACCESS read-only
    STATUS     current
    DESCRIPTION
        "The number of session registrations denied by PDSN due to MN too distant
	 for the associated Mobile IP foreign agent VPN service"
    ::= { starMIPFAStatEntry 89 }

starMIPFAStatRegDenPDSNStyleUnavail OBJECT-TYPE
    SYNTAX     Counter32
    MAX-ACCESS read-only
    STATUS     current
    DESCRIPTION
        "The number of session registration denied by PDSN due to style not available
	 for the associated Mobile IP foreign agent VPN service"
    ::= { starMIPFAStatEntry 90 }

starMIPFAStatRegDenPDSNHANetUnreach OBJECT-TYPE
    SYNTAX     Counter32
    MAX-ACCESS read-only
    STATUS     current
    DESCRIPTION
        "The number of session registrations denied by PDSN due to HA network unreachable
	 for the associated Mobile IP foreign agent VPN service"
    ::= { starMIPFAStatEntry 91 }

starMIPFAStatRegDenPDSNHAHostUnreach OBJECT-TYPE
    SYNTAX     Counter32
    MAX-ACCESS read-only
    STATUS     current
    DESCRIPTION
        "The number of session registrations denied by PDSN due to HA host unreachable
	 for the associated Mobile IP foreign agent VPN service"
    ::= { starMIPFAStatEntry 92 }

starMIPFAStatRegDenPDSNHAPortUnreach OBJECT-TYPE
    SYNTAX     Counter32
    MAX-ACCESS read-only
    STATUS     current
    DESCRIPTION
        "The number of session registrations denied by PDSN due to HA port unreachable
	 for the associated Mobile IP foreign agent VPN service"
    ::= { starMIPFAStatEntry 93 }

starMIPFAStatRegDenPDSNHAUnreach OBJECT-TYPE
    SYNTAX     Counter32
    MAX-ACCESS read-only
    STATUS     current
    DESCRIPTION
        "The number of session registrations denied by PDSN
	 due to HA unreachable for misc reasons
	 for the associated Mobile IP foreign agent VPN service"
    ::= { starMIPFAStatEntry 94 }

starMIPFAStatRegDenPDSNInvCOA OBJECT-TYPE
    SYNTAX     Counter32
    MAX-ACCESS read-only
    STATUS     current
    DESCRIPTION
        "The number of session registrations denied by PDSN due to invalid COA
	 for the associated Mobile IP foreign agent VPN service"
    ::= { starMIPFAStatEntry 95 }

starMIPFAStatRegReqSentInitTotal OBJECT-TYPE
    SYNTAX     Counter32
    MAX-ACCESS read-only
    STATUS     current
    DESCRIPTION
        "The number of initial session registrations
	 for the associated Mobile IP foreign agent VPN service"
    ::= { starMIPFAStatEntry 96 }

starMIPFAStatRegReqSentInitResend OBJECT-TYPE
    SYNTAX     Counter32
    MAX-ACCESS read-only
    STATUS     current
    DESCRIPTION
        "The number of initial session registrations retried
	 for the associated Mobile IP foreign agent VPN service"
    ::= { starMIPFAStatEntry 97 }

starMIPFAStatRegReqSentRenewTotal OBJECT-TYPE
    SYNTAX     Counter32
    MAX-ACCESS read-only
    STATUS     current
    DESCRIPTION
        "The number of renewal session registrations
	 for the associated Mobile IP foreign agent VPN service"
    ::= { starMIPFAStatEntry 98 }

starMIPFAStatRegReqSentRenewResend  OBJECT-TYPE
    SYNTAX     Counter32
    MAX-ACCESS read-only
    STATUS     current
    DESCRIPTION
        "The number of renewal session registrations retried
	 for the associated Mobile IP foreign agent VPN service"
    ::= { starMIPFAStatEntry 99 }

starMIPFAStatRegReqSentDeregTotal OBJECT-TYPE
    SYNTAX     Counter32
    MAX-ACCESS read-only
    STATUS     current
    DESCRIPTION
        "The number of session deregistrations
	 for the associated Mobile IP foreign agent VPN service"
    ::= { starMIPFAStatEntry 100 }

starMIPFAStatRegReqSentDeregResend OBJECT-TYPE
    SYNTAX     Counter32
    MAX-ACCESS read-only
    STATUS     current
    DESCRIPTION
        "The number of session deregistrations retried
	 for the associated Mobile IP foreign agent VPN service"
    ::= { starMIPFAStatEntry 101 }

starMIPFAStatRegRplSentMNTooDistant OBJECT-TYPE
    SYNTAX     Counter32
    MAX-ACCESS read-only
    STATUS     current
    DESCRIPTION
        "The number of session registration reply that indicate MN too distant
	 for the associated Mobile IP foreign agent VPN service"
    ::= { starMIPFAStatEntry 102 }

starMIPFAStatRegRplSentInvCOA OBJECT-TYPE
    SYNTAX     Counter32
    MAX-ACCESS read-only
    STATUS     current
    DESCRIPTION
        "The number of session registration reply that indicate invalid COA
	 for the associated Mobile IP foreign agent VPN service"
    ::= { starMIPFAStatEntry 103 }

starMIPFAStatRegRplSentHANetUnreach OBJECT-TYPE
    SYNTAX     Counter32
    MAX-ACCESS read-only
    STATUS     current
    DESCRIPTION
        "The number of session registration reply that indicate HA network unreachable
	 for the associated Mobile IP foreign agent VPN service"
    ::= { starMIPFAStatEntry 104 }

starMIPFAStatRegRplSentHAHostUnreach OBJECT-TYPE
    SYNTAX     Counter32
    MAX-ACCESS read-only
    STATUS     current
    DESCRIPTION
        "The number of session registration reply that indicate HA host unreachable
	 for the associated Mobile IP foreign agent VPN service"
    ::= { starMIPFAStatEntry 105 }

starMIPFAStatRegRplSentHAPortUnreach OBJECT-TYPE
    SYNTAX     Counter32
    MAX-ACCESS read-only
    STATUS     current
    DESCRIPTION
        "The number of session registration reply that indicate HA port unreachable
	 for the associated Mobile IP foreign agent VPN service"
    ::= { starMIPFAStatEntry 106 }

starMIPFAStatRegRplSentHAUnreach OBJECT-TYPE
    SYNTAX     Counter32
    MAX-ACCESS read-only
    STATUS     current
    DESCRIPTION
        "The number of session registration reply that indicate
	 HA unreachable due to misc reasons
	 for the associated Mobile IP foreign agent VPN service"
    ::= { starMIPFAStatEntry 107 }

starMIPFAStatRegRplSentRegTimeout OBJECT-TYPE
    SYNTAX     Counter32
    MAX-ACCESS read-only
    STATUS     current
    DESCRIPTION
        "The number of session registration reply that indicate registration time out
	 for the associated Mobile IP foreign agent VPN service"
    ::= { starMIPFAStatEntry 108 }

starMIPFAStatRegRplSentMissNAI OBJECT-TYPE
    SYNTAX     Counter32
    MAX-ACCESS read-only
    STATUS     current
    DESCRIPTION
        "The number of session registration reply that indicate NAI missing
	 for the associated Mobile IP foreign agent VPN service"
    ::= { starMIPFAStatEntry 109 }

starMIPFAStatRegRplSentMissHomeAgent OBJECT-TYPE
    SYNTAX     Counter32
    MAX-ACCESS read-only
    STATUS     current
    DESCRIPTION
        "The number of session registration reply that indicate HA missing
	 for the associated Mobile IP foreign agent VPN service"
    ::= { starMIPFAStatEntry 110 }

starMIPFAStatRegRplSentMissHomeAddr OBJECT-TYPE
    SYNTAX     Counter32
    MAX-ACCESS read-only
    STATUS     current
    DESCRIPTION
        "The number of session registration reply that indicate home address missing
	 for the associated Mobile IP foreign agent VPN service"
    ::= { starMIPFAStatEntry 111 }

starMIPFAStatRegRplSentUnknChallenge OBJECT-TYPE
    SYNTAX     Counter32
    MAX-ACCESS read-only
    STATUS     current
    DESCRIPTION
        "The number of session registration reply that indicate unknown challenge
	 for the associated Mobile IP foreign agent VPN service"
    ::= { starMIPFAStatEntry 112 }

starMIPFAStatRegRplSentMissChallenge OBJECT-TYPE
    SYNTAX     Counter32
    MAX-ACCESS read-only
    STATUS     current
    DESCRIPTION
        "The number of session registration reply that indicate challenge missing
	 for the associated Mobile IP foreign agent VPN service"
    ::= { starMIPFAStatEntry 113 }

starMIPFAStatRegRplSentStaleChallenge OBJECT-TYPE
    SYNTAX     Counter32
    MAX-ACCESS read-only
    STATUS     current
    DESCRIPTION
        "The number of session registration reply that indicate stale challenge
	 for the associated Mobile IP foreign agent VPN service"
    ::= { starMIPFAStatEntry 114 }

starMIPFAStatRegRplSentBadReply OBJECT-TYPE
    SYNTAX     Counter32
    MAX-ACCESS read-only
    STATUS     current
    DESCRIPTION
        "The number of session registration reply that indicate bad reply
	 for the associated Mobile IP foreign agent VPN service"
    ::= { starMIPFAStatEntry 115 }

-- RP Stats

starentRP OBJECT IDENTIFIER ::= { starentMIBObjects 24 }

starRPStatTable OBJECT-TYPE
    SYNTAX     SEQUENCE OF StarRPStatEntry
    MAX-ACCESS not-accessible
    STATUS     current
    DESCRIPTION
        "A table containing MIP FA Stats"
    ::= { starentRP 1 }

starRPStatEntry OBJECT-TYPE
    SYNTAX     StarRPStatEntry
    MAX-ACCESS not-accessible
    STATUS     current
    DESCRIPTION
        "The statistics for a specific R-P VPN (context) service"
    INDEX { IMPLIED starRPStatSvcID }
    ::= { starRPStatTable 1 }

StarRPStatEntry ::=
    SEQUENCE {
        starRPStatVpnID             Gauge32,
        starRPStatSvcID             StarShortID,
        starRPStatVpnName           DisplayString,
        starRPStatServName          DisplayString,
        starRPRegRecvTotal          Counter32,
        starRPRegAcceptTotal        Counter32,
        starRPRegDeniedTotal        Counter32,
        starRPRegDiscardTotal       Counter32,
        starRPRegAcceptInitial      Counter32,
        starRPRegAcceptIntraPDSN    Counter32,
        starRPRegAcceptInterPDSN    Counter32,
        starRPRegDeniedInitial      Counter32,
        starRPRegAcceptRenew        Counter32,
        starRPRegDeniedRenew        Counter32,
        starRPRegAcceptDereg        Counter32,
        starRPRegDeniedDereg        Counter32,
        starRPRegSendError          Counter32,
        starRPRegHashError          Counter32,
        starRPRegDecodeError        Counter32,
        starRPRegUnhandled          Counter32,
        starRPRegAirlinkSeqError    Counter32,
        starRPRegDenyUnspec         Counter32,
        starRPRegDenyAdminProhib    Counter32,
        starRPRegDenyNoResource     Counter32,
        starRPRegDenyAuth           Counter32,
        starRPRegDenyMismatchID     Counter32,
        starRPRegDenyBadRequest     Counter32,
        starRPRegDenyUnknownPDSN    Counter32,
        starRPRegDenyRevTunUnav     Counter32,
        starRPRegDenyRevTunReq      Counter32,
        starRPRegDenyUnrecogVend    Counter32,
        starRPRegUpdTotal           Counter32,
        starRPRegUpdAccept          Counter32,
        starRPRegUpdDenied          Counter32,
        starRPRegUpdUnack           Counter32,
        starRPRegUpdTrans           Counter32,
        starRPRegUpdRetrans         Counter32,
        starRPRegUpdReceived        Counter32,
        starRPRegUpdDiscard         Counter32,
        starRPRegUpdSendError       Counter32,
        starRPRegUpdUplyrInit       Counter32,
        starRPRegUpdOther           Counter32,
        starRPRegUpdHandoff         Counter32,
        starRPRegUpdDenyUnspec      Counter32,
        starRPRegUpdDenyAdminProhib Counter32,
        starRPRegUpdDenyAuth        Counter32,
        starRPRegUpdDenyMismatchID  Counter32,
        starRPRegUpdDenyBadRequest  Counter32,
        starRPSecViolations         Counter32,
        starRPSecBadAuth            Counter32,
        starRPSecBadID              Counter32,
        starRPSecBadSpi             Counter32,
        starRPSecMissingMnHAAuth    Counter32,
        starRPSecMissingRegUpdate   Counter32,
	starRPRegRecvInitial                  Counter32,
	starRPRegAcceptActvStartIntraPDSN     Counter32,
	starRPRegAcceptActvStopIntraPDSN      Counter32,
	starRPRegRecvRenew                    Counter32,
	starRPRegActvStartRenew               Counter32,
	starRPRegActvStopRenew                Counter32,
	starRPRegRecvDereg                    Counter32,
	starRPRegAcceptActvStopDereg          Counter32,
	starRPDiscSessAbsent                  Counter32,
	starRPDiscNoMemory                    Counter32,
	starRPDiscMalformed                   Counter32,
	starRPDiscAuthFail                    Counter32,
	starRPDiscInternalBounce              Counter32,
	starRPDiscInpuQueueExceeded           Counter32,
	starRPDiscMismatchedId                Counter32,
	starRPDiscInvPacketLen                Counter32,
	starRPDiscMisc                        Counter32,
	starRP1xTxBytes                       Counter32,
	starRP1xRxBytes                       Counter32,
	starRP1xTxPackets                     Counter32,
	starRP1xRxPackets                     Counter32,
	starRPDoTxBytes                       Counter32,
	starRPDoRxBytes                       Counter32,
	starRPDoTxPackets                     Counter32,
	starRPDoRxPackets                     Counter32
            }

starRPStatVpnID OBJECT-TYPE
    SYNTAX     Gauge32
    MAX-ACCESS read-only
    STATUS     current
    DESCRIPTION
        "The internal identification of the R-P VPN (context)"
    ::= { starRPStatEntry 1 }

starRPStatSvcID OBJECT-TYPE
    SYNTAX     StarShortID
    MAX-ACCESS not-accessible
    STATUS     current
    DESCRIPTION
        "The service identification is made up from first 8 chars of context name
         and first 8 chars of service name separated by (:)"
    ::= { starRPStatEntry 2 }

starRPStatVpnName OBJECT-TYPE
    SYNTAX     DisplayString
    MAX-ACCESS read-only
    STATUS     current
    DESCRIPTION
        "The R-P VPN (context) name"
    ::= { starRPStatEntry 3 }

starRPStatServName OBJECT-TYPE
    SYNTAX     DisplayString
    MAX-ACCESS read-only
    STATUS     current
    DESCRIPTION
        "The R-P service name"
    ::= { starRPStatEntry 4 }

starRPRegRecvTotal OBJECT-TYPE
    SYNTAX     Counter32
    MAX-ACCESS read-only
    STATUS     current
    DESCRIPTION
        "The total number of session registrations received for the associated R-P VPN service"
    ::= { starRPStatEntry 5 }

starRPRegAcceptTotal OBJECT-TYPE
    SYNTAX     Counter32
    MAX-ACCESS read-only
    STATUS     current
    DESCRIPTION
        "The total number of session registrations accepted for the associated R-P VPN service"
    ::= { starRPStatEntry 6 }

starRPRegDeniedTotal OBJECT-TYPE
    SYNTAX     Counter32
    MAX-ACCESS read-only
    STATUS     current
    DESCRIPTION
        "The total number of session registrations denied for the associated R-P VPN service"
    ::= { starRPStatEntry 7 }

starRPRegDiscardTotal OBJECT-TYPE
    SYNTAX     Counter32
    MAX-ACCESS read-only
    STATUS     current
    DESCRIPTION
        "The total number of session registrations discarded for the associated R-P VPN service"
    ::= { starRPStatEntry 8 }

starRPRegAcceptInitial OBJECT-TYPE
    SYNTAX     Counter32
    MAX-ACCESS read-only
    STATUS     current
    DESCRIPTION
        "The total number of initial session registrations accepted for the associated R-P VPN service"
    ::= { starRPStatEntry 9 }

starRPRegAcceptIntraPDSN OBJECT-TYPE
    SYNTAX     Counter32
    MAX-ACCESS read-only
    STATUS     obsolete
    DESCRIPTION
        "The number of Intra-PDSN session registrations accepted for the associated R-P VPN service"
    ::= { starRPStatEntry 10 }

starRPRegAcceptInterPDSN OBJECT-TYPE
    SYNTAX     Counter32
    MAX-ACCESS read-only
    STATUS     current
    DESCRIPTION
        "The number of Inter-PDSN session registrations accepted for the associated R-P VPN service"
    ::= { starRPStatEntry 11 }

starRPRegDeniedInitial OBJECT-TYPE
    SYNTAX     Counter32
    MAX-ACCESS read-only
    STATUS     current
    DESCRIPTION
        "The number of initial session registrations denied for the associated R-P VPN service"
    ::= { starRPStatEntry 12 }

starRPRegAcceptRenew OBJECT-TYPE
    SYNTAX     Counter32
    MAX-ACCESS read-only
    STATUS     current
    DESCRIPTION
        "The number of session registration renewals accepted for the associated R-P VPN service"
    ::= { starRPStatEntry 13 }

starRPRegDeniedRenew OBJECT-TYPE
    SYNTAX     Counter32
    MAX-ACCESS read-only
    STATUS     current
    DESCRIPTION
        "The number of session registration renewals denied for the associated R-P VPN service"
    ::= { starRPStatEntry 14 }

starRPRegAcceptDereg OBJECT-TYPE
    SYNTAX     Counter32
    MAX-ACCESS read-only
    STATUS     current
    DESCRIPTION
        "The number of session deregistrations accepted for the associated R-P VPN service"
    ::= { starRPStatEntry 15 }

starRPRegDeniedDereg OBJECT-TYPE
    SYNTAX     Counter32
    MAX-ACCESS read-only
    STATUS     current
    DESCRIPTION
        "The number of session deregistrations denied for the associated R-P VPN service"
    ::= { starRPStatEntry 16 }

starRPRegSendError OBJECT-TYPE
    SYNTAX     Counter32
    MAX-ACCESS read-only
    STATUS     current
    DESCRIPTION
        "The number of session registrations with errors in transmission
	  for the associated R-P VPN service"
    ::= { starRPStatEntry 17 }

starRPRegHashError OBJECT-TYPE
    SYNTAX     Counter32
    MAX-ACCESS read-only
    STATUS     current
    DESCRIPTION
        "The number of session registrations with hash errors for the associated R-P VPN service"
    ::= { starRPStatEntry 18 }

starRPRegDecodeError OBJECT-TYPE
    SYNTAX     Counter32
    MAX-ACCESS read-only
    STATUS     current
    DESCRIPTION
        "The number of sessions registrations with decode errors for the associated R-P VPN service"
    ::= { starRPStatEntry 19 }

starRPRegUnhandled OBJECT-TYPE
    SYNTAX     Counter32
    MAX-ACCESS read-only
    STATUS     current
    DESCRIPTION
        "The number of session registrations unable to by proceeded for the associated R-P VPN service"
    ::= { starRPStatEntry 20 }

starRPRegAirlinkSeqError OBJECT-TYPE
    SYNTAX     Counter32
    MAX-ACCESS read-only
    STATUS     current
    DESCRIPTION
        "The number of session registrations with air link sequence errors for the associated R-P VPN service"
    ::= { starRPStatEntry 21 }

starRPRegDenyUnspec OBJECT-TYPE
    SYNTAX     Counter32
    MAX-ACCESS read-only
    STATUS     current
    DESCRIPTION
        "The number of session registrations denied for an unspecified reason
	  for the associated R-P VPN service"
    ::= { starRPStatEntry 22 }

starRPRegDenyAdminProhib OBJECT-TYPE
    SYNTAX     Counter32
    MAX-ACCESS read-only
    STATUS     current
    DESCRIPTION
        "The number of session registrations denied due to administrator prohibition
	  for the associated R-P VPN service"
    ::= { starRPStatEntry 23 }

starRPRegDenyNoResource OBJECT-TYPE
    SYNTAX     Counter32
    MAX-ACCESS read-only
    STATUS     current
    DESCRIPTION
        "The number of session registrations denied due to no resources available
	  for the associated R-P VPN service"
    ::= { starRPStatEntry 24 }

starRPRegDenyAuth OBJECT-TYPE
    SYNTAX     Counter32
    MAX-ACCESS read-only
    STATUS     current
    DESCRIPTION
        "The number of session registrations denied due to authentication failure
	  for the associated R-P VPN service"
    ::= { starRPStatEntry 25 }

starRPRegDenyMismatchID OBJECT-TYPE
    SYNTAX     Counter32
    MAX-ACCESS read-only
    STATUS     current
    DESCRIPTION
        "The number of session registrations denied due to an ID mismatch
	  for the associated R-P VPN service"
    ::= { starRPStatEntry 26 }

starRPRegDenyBadRequest OBJECT-TYPE
    SYNTAX     Counter32
    MAX-ACCESS read-only
    STATUS     current
    DESCRIPTION
        "The number of session registrations denied due to the request being invalid
	 for the associated R-P VPN service"
    ::= { starRPStatEntry 27 }

starRPRegDenyUnknownPDSN OBJECT-TYPE
    SYNTAX     Counter32
    MAX-ACCESS read-only
    STATUS     current
    DESCRIPTION
        "The number of session registrations denied due to the packet data service not
	 being recognized for the associated R-P VPN service"
    ::= { starRPStatEntry 28 }

starRPRegDenyRevTunUnav OBJECT-TYPE
    SYNTAX     Counter32
    MAX-ACCESS read-only
    STATUS     current
    DESCRIPTION
        "The number of session registrations denied due to no reverse tunnel being available
	  for the associated R-P VPN service"
    ::= { starRPStatEntry 29 }

starRPRegDenyRevTunReq OBJECT-TYPE
    SYNTAX     Counter32
    MAX-ACCESS read-only
    STATUS     current
    DESCRIPTION
        "The number of session registrations denied due to reverse tunneling being
	 mandatory  for the associated R-P VPN service"
    ::= { starRPStatEntry 30 }

starRPRegDenyUnrecogVend OBJECT-TYPE
    SYNTAX     Counter32
    MAX-ACCESS read-only
    STATUS     current
    DESCRIPTION
        "The number of session registrations denied due to the vendor not being recognized
	 for the associated R-P VPN service"
    ::= { starRPStatEntry 31 }

starRPRegUpdTotal OBJECT-TYPE
    SYNTAX     Counter32
    MAX-ACCESS read-only
    STATUS     current
    DESCRIPTION
        "The total number of session registration updates for the associated R-P VPN service"
    ::= { starRPStatEntry 32 }

starRPRegUpdAccept OBJECT-TYPE
    SYNTAX     Counter32
    MAX-ACCESS read-only
    STATUS     current
    DESCRIPTION
        "The number of session registration updates which were accepted for the associated R-P VPN service"
    ::= { starRPStatEntry 33 }

starRPRegUpdDenied OBJECT-TYPE
    SYNTAX     Counter32
    MAX-ACCESS read-only
    STATUS     current
    DESCRIPTION
        "The number of session registration updates which were denied for the associated R-P VPN service"
    ::= { starRPStatEntry 34 }

starRPRegUpdUnack OBJECT-TYPE
    SYNTAX     Counter32
    MAX-ACCESS read-only
    STATUS     current
    DESCRIPTION
        "The number of session registration updates which were not acknowledged
	 for the associated R-P VPN service"
    ::= { starRPStatEntry 35 }

starRPRegUpdTrans OBJECT-TYPE
    SYNTAX     Counter32
    MAX-ACCESS read-only
    STATUS     current
    DESCRIPTION
        "The number of session registration updates sent for the associated R-P VPN service"
    ::= { starRPStatEntry 36 }

starRPRegUpdRetrans OBJECT-TYPE
    SYNTAX     Counter32
    MAX-ACCESS read-only
    STATUS     current
    DESCRIPTION
        "The number of session registration updates resent for the associated R-P VPN service"
    ::= { starRPStatEntry 37 }

starRPRegUpdReceived OBJECT-TYPE
    SYNTAX     Counter32
    MAX-ACCESS read-only
    STATUS     current
    DESCRIPTION
        "The number of session registration updates received for the associated R-P VPN service"
    ::= { starRPStatEntry 38 }

starRPRegUpdDiscard OBJECT-TYPE
    SYNTAX     Counter32
    MAX-ACCESS read-only
    STATUS     current
    DESCRIPTION
        "The number of session registration updates discarded for the associated R-P VPN service"
    ::= { starRPStatEntry 39 }

starRPRegUpdSendError OBJECT-TYPE
    SYNTAX     Counter32
    MAX-ACCESS read-only
    STATUS     current
    DESCRIPTION
        "The number of session registration updates with errors in transmission
	 for the associated R-P VPN service"
    ::= { starRPStatEntry 40 }

starRPRegUpdUplyrInit OBJECT-TYPE
    SYNTAX     Counter32
    MAX-ACCESS read-only
    STATUS     current
    DESCRIPTION
        "The number of session registration updates with up-link reinitializations"
    ::= { starRPStatEntry 41 }

starRPRegUpdOther OBJECT-TYPE
    SYNTAX     Counter32
    MAX-ACCESS read-only
    STATUS     current
    DESCRIPTION
        "The number of session registration updates with a reason of 'other'
	 for the associated R-P VPN service"
    ::= { starRPStatEntry 42 }

starRPRegUpdHandoff OBJECT-TYPE
    SYNTAX     Counter32
    MAX-ACCESS read-only
    STATUS     current
    DESCRIPTION
        "The number of session registration updates due to a mobile hand-off
	 for the associated R-P VPN service"
    ::= { starRPStatEntry 43 }

starRPRegUpdDenyUnspec OBJECT-TYPE
    SYNTAX     Counter32
    MAX-ACCESS read-only
    STATUS     current
    DESCRIPTION
        "The number of session registration updates denied for an unspecified
	 reason for the associated R-P VPN service"
    ::= { starRPStatEntry 44 }

starRPRegUpdDenyAdminProhib OBJECT-TYPE
    SYNTAX     Counter32
    MAX-ACCESS read-only
    STATUS     current
    DESCRIPTION
        "The number of session registration updates denied due to administration
	 prohibition for the associated R-P VPN service"
    ::= { starRPStatEntry 45 }

starRPRegUpdDenyAuth OBJECT-TYPE
    SYNTAX     Counter32
    MAX-ACCESS read-only
    STATUS     current
    DESCRIPTION
        "The number of session registration updates denied due to authentication
	 failure for the associated R-P VPN service"
    ::= { starRPStatEntry 46 }

starRPRegUpdDenyMismatchID OBJECT-TYPE
    SYNTAX     Counter32
    MAX-ACCESS read-only
    STATUS     current
    DESCRIPTION
        "The number of session registration updates denied due to an ID mismatch
	 for the associated R-P VPN service"
    ::= { starRPStatEntry 47 }

starRPRegUpdDenyBadRequest OBJECT-TYPE
    SYNTAX     Counter32
    MAX-ACCESS read-only
    STATUS     current
    DESCRIPTION
        "The number of session registration updates denied due to the request being
	 invalid for the associated R-P VPN service"
    ::= { starRPStatEntry 48 }

starRPSecViolations OBJECT-TYPE
    SYNTAX     Counter32
    MAX-ACCESS read-only
    STATUS     current
    DESCRIPTION
        "The total number of session security violations for the associated R-P VPN service"
    ::= { starRPStatEntry 49 }

starRPSecBadAuth OBJECT-TYPE
    SYNTAX     Counter32
    MAX-ACCESS read-only
    STATUS     current
    DESCRIPTION
        "The total number of session security authentication violations for the associated R-P VPN service"
    ::= { starRPStatEntry 50 }

starRPSecBadID OBJECT-TYPE
    SYNTAX     Counter32
    MAX-ACCESS read-only
    STATUS     current
    DESCRIPTION
        "The total number of session security ID violations for the associated R-P VPN service"
    ::= { starRPStatEntry 51 }

starRPSecBadSpi OBJECT-TYPE
    SYNTAX     Counter32
    MAX-ACCESS read-only
    STATUS     current
    DESCRIPTION
        "The total number of session security SPI violations for the associated R-P VPN service"
    ::= { starRPStatEntry 52 }

starRPSecMissingMnHAAuth OBJECT-TYPE
    SYNTAX     Counter32
    MAX-ACCESS read-only
    STATUS     current
    DESCRIPTION
        "The total number of session security missing mobile number home agent
	 authentication violation for the associated R-P VPN service"
    ::= { starRPStatEntry 53 }

starRPSecMissingRegUpdate OBJECT-TYPE
    SYNTAX     Counter32
    MAX-ACCESS read-only
    STATUS     current
    DESCRIPTION
        "The total number of session missing registration update violations
	 for the associated R-P VPN service"
    ::= { starRPStatEntry 54 }

starRPRegRecvInitial  OBJECT-TYPE
    SYNTAX     Counter32
    MAX-ACCESS read-only
    STATUS     current
    DESCRIPTION
        "The total number of initial session registration
	 for the associated R-P VPN service"
    ::= { starRPStatEntry 55 }

starRPRegAcceptActvStartIntraPDSN OBJECT-TYPE
    SYNTAX     Counter32
    MAX-ACCESS read-only
    STATUS     current
    DESCRIPTION
        "The number of accepted registration request during
	 intraPDSN handoff which contains active start
	 for the associated R-P VPN service"
    ::= { starRPStatEntry 56 }

starRPRegAcceptActvStopIntraPDSN OBJECT-TYPE
    SYNTAX     Counter32
    MAX-ACCESS read-only
    STATUS     current
    DESCRIPTION
        "The number of accepted registration request during
	 intraPDSN handoff which contains active stop
	 for the associated R-P VPN service"
    ::= { starRPStatEntry 57 }

starRPRegRecvRenew OBJECT-TYPE
    SYNTAX     Counter32
    MAX-ACCESS read-only
    STATUS     current
    DESCRIPTION
        "The number of received renew registration request
	 for the associated R-P VPN service"
    ::= { starRPStatEntry 58 }

starRPRegActvStartRenew OBJECT-TYPE
    SYNTAX     Counter32
    MAX-ACCESS read-only
    STATUS     current
    DESCRIPTION
        "The number of received renew registration request that contains active start
	 for the associated R-P VPN service"
    ::= { starRPStatEntry 59 }

starRPRegActvStopRenew OBJECT-TYPE
    SYNTAX     Counter32
    MAX-ACCESS read-only
    STATUS     current
    DESCRIPTION
        "The number of received renew registration request that contains active stop
	 for the associated R-P VPN service"
    ::= { starRPStatEntry 60 }

starRPRegRecvDereg OBJECT-TYPE
    SYNTAX     Counter32
    MAX-ACCESS read-only
    STATUS     current
    DESCRIPTION
        "The number of received deregistration request
	 for the associated R-P VPN service"
    ::= { starRPStatEntry 61 }

starRPRegAcceptActvStopDereg OBJECT-TYPE
    SYNTAX     Counter32
    MAX-ACCESS read-only
    STATUS     current
    DESCRIPTION
        "The number of accepted deregistration request that contains active stop
	 for the associated R-P VPN service"
    ::= { starRPStatEntry 62 }

starRPDiscSessAbsent   OBJECT-TYPE
    SYNTAX     Counter32
    MAX-ACCESS read-only
    STATUS     current
    DESCRIPTION
        "The number of registration request discarded due to no session
	 for the associated R-P VPN service"
    ::= { starRPStatEntry 63 }

starRPDiscNoMemory  OBJECT-TYPE
    SYNTAX     Counter32
    MAX-ACCESS read-only
    STATUS     current
    DESCRIPTION
        "The number of registration request discarded due to no memory
	 for the associated R-P VPN service"
    ::= { starRPStatEntry 64 }

starRPDiscMalformed OBJECT-TYPE
    SYNTAX     Counter32
    MAX-ACCESS read-only
    STATUS     current
    DESCRIPTION
        "The number of registration request discarded because malformed
	 for the associated R-P VPN service"
    ::= { starRPStatEntry 65 }

starRPDiscAuthFail OBJECT-TYPE
    SYNTAX     Counter32
    MAX-ACCESS read-only
    STATUS     current
    DESCRIPTION
        "The number of registration request discarded because authentication failed
	 for the associated R-P VPN service"
    ::= { starRPStatEntry 66 }

starRPDiscInternalBounce OBJECT-TYPE
    SYNTAX     Counter32
    MAX-ACCESS read-only
    STATUS     current
    DESCRIPTION
        "The number of registration request discarded because internal bounce
	 for the associated R-P VPN service"
    ::= { starRPStatEntry 67 }

starRPDiscInpuQueueExceeded OBJECT-TYPE
    SYNTAX     Counter32
    MAX-ACCESS read-only
    STATUS     current
    DESCRIPTION
        "The number of registration request discarded because internal queue exceeded
	 for the associated R-P VPN service"
    ::= { starRPStatEntry 68 }

starRPDiscMismatchedId OBJECT-TYPE
    SYNTAX     Counter32
    MAX-ACCESS read-only
    STATUS     current
    DESCRIPTION
        "The number of registration request discarded because mismatched ID
	 for the associated R-P VPN service"
    ::= { starRPStatEntry 69 }

starRPDiscInvPacketLen OBJECT-TYPE
    SYNTAX     Counter32
    MAX-ACCESS read-only
    STATUS     current
    DESCRIPTION
        "The number of registration request discarded because invalid packet length
	 for the associated R-P VPN service"
    ::= { starRPStatEntry 70 }

starRPDiscMisc OBJECT-TYPE
    SYNTAX     Counter32
    MAX-ACCESS read-only
    STATUS     current
    DESCRIPTION
        "The number of registration request discarded due to misc reasons
	 for the associated R-P VPN service"
    ::= { starRPStatEntry 71 }

starRP1xTxBytes OBJECT-TYPE
    SYNTAX     Counter32 
    UNITS      "Megabytes"
    MAX-ACCESS read-only
    STATUS     current
    DESCRIPTION
        "The number of 1x bytes transmitted, in megabytes"
    ::= { starRPStatEntry 72 }

starRP1xRxBytes OBJECT-TYPE
    SYNTAX     Counter32
    UNITS      "Megabytes"
    MAX-ACCESS read-only
    STATUS     current
    DESCRIPTION
        "The number of 1x bytes received, in megabytes"
    ::= { starRPStatEntry 73 }

starRP1xTxPackets OBJECT-TYPE
    SYNTAX     Counter32
    UNITS      "Thousands"
    MAX-ACCESS read-only
    STATUS     current
    DESCRIPTION
        "The number of 1x packets transmitted, in thousands"
    ::= { starRPStatEntry 74 }

starRP1xRxPackets OBJECT-TYPE
    SYNTAX     Counter32
    UNITS      "Thousands"
    MAX-ACCESS read-only
    STATUS     current
    DESCRIPTION
        "The number of 1x packets received, in thousands"
    ::= { starRPStatEntry 75 }

starRPDoTxBytes OBJECT-TYPE
    SYNTAX     Counter32
    UNITS      "Megabytes"
    MAX-ACCESS read-only
    STATUS     current
    DESCRIPTION
        "The number of Do bytes transmitted, in megabytes"
    ::= { starRPStatEntry 76 }

starRPDoRxBytes OBJECT-TYPE
    SYNTAX     Counter32
    UNITS      "Megabytes"
    MAX-ACCESS read-only
    STATUS     current
    DESCRIPTION
        "The number of Do bytes received, in megabytes"
    ::= { starRPStatEntry 77 }

starRPDoTxPackets OBJECT-TYPE
    SYNTAX     Counter32
    UNITS      "Thousands"
    MAX-ACCESS read-only
    STATUS     current
    DESCRIPTION
        "The number of Do packets transmitted, in thousands"
    ::= { starRPStatEntry 78 }

starRPDoRxPackets OBJECT-TYPE
    SYNTAX     Counter32
    UNITS      "Thousands"
    MAX-ACCESS read-only
    STATUS     current
    DESCRIPTION
        "The number of Do packets received, in thousands"
    ::= { starRPStatEntry 79 }

--Subscriber; these objects are provided for use in SNMP Traps only

starentSubscriber OBJECT IDENTIFIER ::= { starentMIBObjects 26 }

starSubTable OBJECT-TYPE
    SYNTAX     SEQUENCE OF StarSubEntry
    MAX-ACCESS not-accessible
    STATUS     current
    DESCRIPTION
        "A table containing subscriber information"
    ::= { starentSubscriber 1 }

starSubEntry OBJECT-TYPE
    SYNTAX     StarSubEntry

    MAX-ACCESS not-accessible
    STATUS     current
    DESCRIPTION
        "Information for a specific Subscriber"
    INDEX { starSubMSID, starSubName }
    ::= { starSubTable 1 }

StarSubEntry ::=
    SEQUENCE {
	starSubContext              DisplayString,
        starSubMSID                 OCTET STRING,
        starSubName                 OCTET STRING,
	starSubTimerDuration        Unsigned32,
        starSubLongDurTimeoutAction INTEGER,
	starSubSetupTime            DateAndTime,
	starSubHomeAddr             IpAddress,
	starSubHomeAddrv6	    Ipv6Address
    }

starSubContext OBJECT-TYPE
    SYNTAX     DisplayString
    MAX-ACCESS accessible-for-notify
    STATUS     current
    DESCRIPTION
        "The context the subscriber is in"
    ::= { starSubEntry 1 }

starSubMSID OBJECT-TYPE
    SYNTAX     OCTET STRING (SIZE (1..16))
    MAX-ACCESS accessible-for-notify
    STATUS     current
    DESCRIPTION
        "The MSID of the subscriber"
    ::= { starSubEntry 2 }

starSubName OBJECT-TYPE
    SYNTAX     OCTET STRING (SIZE (1..128))
    MAX-ACCESS accessible-for-notify
    STATUS     current
    DESCRIPTION
        "The name of the subscriber"
    ::= { starSubEntry 3 }

starSubTimerDuration OBJECT-TYPE
    SYNTAX     Unsigned32
    MAX-ACCESS accessible-for-notify
    STATUS     current
    DESCRIPTION
        "The length of the long-duration timer in seconds"
    ::= { starSubEntry 4 }

starSubLongDurTimeoutAction OBJECT-TYPE
    SYNTAX     StarLongDurTimeoutAction
    MAX-ACCESS accessible-for-notify
    STATUS     current
    DESCRIPTION
	"The action taken by the system upon detection of a long-duration session"
    ::= { starSubEntry 5 }

starSubSetupTime OBJECT-TYPE
    SYNTAX     DateAndTime
    MAX-ACCESS accessible-for-notify
    STATUS     current
    DESCRIPTION
        "The time when the call was setup"
    ::= { starSubEntry 6 }

starSubHomeAddr OBJECT-TYPE
    SYNTAX     IpAddress
    MAX-ACCESS accessible-for-notify
    STATUS     current
    DESCRIPTION
        "The ipv4 home address."
    ::= { starSubEntry 7 }

starSubHomeAddrv6 OBJECT-TYPE
    SYNTAX     Ipv6Address
    MAX-ACCESS accessible-for-notify
    STATUS     current
    DESCRIPTION
        "The ipv6 home address."
    ::= { starSubEntry 8 }

-- EIS; these objects are provided for use in SNMP Traps only

starentEISServer OBJECT IDENTIFIER ::= { starentMIBObjects 27 }

starEISServerTable OBJECT-TYPE
    SYNTAX	SEQUENCE OF StarEISServerEntry
    MAX-ACCESS  not-accessible
    STATUS      current
    DESCRIPTION
	"A table containing EIS Server information"
    ::= { starentEISServer 1 }

starEISServerEntry OBJECT-TYPE
    SYNTAX	StarEISServerEntry
    MAX-ACCESS  not-accessible
    STATUS      current
    DESCRIPTION
        "Information for a specific EIS Server"
    INDEX { starEISServerVPNID, starEISServerAddr }
    ::= { starEISServerTable 1 }

StarEISServerEntry ::=
    SEQUENCE {
	starEISServerVPNID	Gauge32,
	starEISServerAddr	IpAddress,
	starEISServerVPNName    DisplayString
    }

starEISServerVPNID OBJECT-TYPE
    SYNTAX	Gauge32
    MAX-ACCESS  not-accessible
    STATUS      current
    DESCRIPTION
	"The VPN ID for the EIS Server"
    ::= { starEISServerEntry 1 }

starEISServerAddr OBJECT-TYPE
    SYNTAX      IpAddress
    MAX-ACCESS  accessible-for-notify
    STATUS      current
    DESCRIPTION
        "The IP Address for the EIS Server"
    ::= { starEISServerEntry 2 }

starEISServerVPNName OBJECT-TYPE
    SYNTAX      DisplayString
    MAX-ACCESS  accessible-for-notify
    STATUS      current
    DESCRIPTION
	"The VPN Name for this EIS Server"
    ::= { starEISServerEntry 3 }

-- Threshold; these objects are provided for use in SNMP Traps only

starentThresholds OBJECT IDENTIFIER ::= { starentMIBObjects 28 }

starThreshMeasuredPct OBJECT-TYPE
    SYNTAX     Gauge32(0..100)
    UNITS      "Percent"
    MAX-ACCESS accessible-for-notify
    STATUS     current
    DESCRIPTION
        "The measured value of a thresholded parameter"
    ::= { starentThresholds 1 }

starThreshPct OBJECT-TYPE
    SYNTAX     Integer32(0..100)
    UNITS      "Percent"
    MAX-ACCESS accessible-for-notify
    STATUS     current
    DESCRIPTION
        "The configured value of a thresholded parameter"
    ::= { starentThresholds 2 }

starThreshMeasuredInt OBJECT-TYPE
    SYNTAX     Gauge32
    MAX-ACCESS accessible-for-notify
    STATUS     current
    DESCRIPTION
        "The measured value of a thresholded parameter"
    ::= { starentThresholds 3 }

starThreshInt OBJECT-TYPE
    SYNTAX     Unsigned32
    MAX-ACCESS accessible-for-notify
    STATUS     current
    DESCRIPTION
        "The configured value of a thresholded parameter"
    ::= { starentThresholds 4 }

starThreshMeasuredMB OBJECT-TYPE
    SYNTAX     Gauge32
    UNITS      "Megabytes"
    MAX-ACCESS accessible-for-notify
    STATUS     current
    DESCRIPTION
        "The measured value of a thresholded parameter"
    ::= { starentThresholds 5 }

starThreshMB OBJECT-TYPE
    SYNTAX     Unsigned32
    UNITS      "Megabytes"
    MAX-ACCESS accessible-for-notify
    STATUS     current
    DESCRIPTION
        "The configured value of a thresholded parameter"
    ::= { starentThresholds 6 }

starThreshMeasuredGB OBJECT-TYPE
    SYNTAX     Gauge32
    UNITS      "Gigabytes"
    MAX-ACCESS accessible-for-notify
    STATUS     current
    DESCRIPTION
        "The measured value of a thresholded parameter"
    ::= { starentThresholds 7 }

starThreshGB OBJECT-TYPE
    SYNTAX     Unsigned32
    UNITS      "Gigabytes"
    MAX-ACCESS accessible-for-notify
    STATUS     current
    DESCRIPTION
        "The configured value of a thresholded parameter"
    ::= { starentThresholds 8 }

starThreshPeriodInt OBJECT-TYPE
    SYNTAX     Integer32(30..600) 
    UNITS      "Seconds"
    MAX-ACCESS accessible-for-notify
    STATUS     current
    DESCRIPTION
        "The configured value of a thresholded parameter"
    ::= { starentThresholds 9 }

starThreshDeviceNum OBJECT-TYPE
    SYNTAX     Integer32(1..4) 
    MAX-ACCESS accessible-for-notify
    STATUS     current
    DESCRIPTION
        "The configured value of a thresholded parameter"
    ::= { starentThresholds 10 }

starentPort OBJECT IDENTIFIER ::= { starentMIBObjects 29 }

starPortTable OBJECT-TYPE
    SYNTAX	SEQUENCE OF StarPortEntry
    MAX-ACCESS  not-accessible
    STATUS      current
    DESCRIPTION
	"A table containing Port information"
    ::= { starentPort 1 }

starPortEntry OBJECT-TYPE
    SYNTAX	StarPortEntry
    MAX-ACCESS  not-accessible
    STATUS      current
    DESCRIPTION
        "Information for a specific Port"
    INDEX { starPortSlot, starPortNum }
    ::= { starPortTable 1 }

StarPortEntry ::=
    SEQUENCE {
	starPortSlot            Integer32,
        starPortNum             Integer32,
	starPortType            INTEGER,
	starPortTypeDescr	DisplayString,
	starPortAdminState	INTEGER,
	starPortOperState	INTEGER,
        starPortOperMode        INTEGER,
	starPortLinkState	INTEGER,
	starRedundantPortSlot	Integer32,
	starRedundantPortNum	Integer32,
	starPortRxBytes         Counter32,
	starPortTxBytes         Counter32,
	starPortRxFrames        Counter32,
	starPortTxFrames        Counter32,
        starPortRxDiscards      Counter32,
        starPortTxDiscards      Counter32,
        starPortRxErrors        Counter32,
        starPortTxErrors        Counter32
    }

starPortSlot OBJECT-TYPE
    SYNTAX	Integer32(1..48)
    MAX-ACCESS  accessible-for-notify
    STATUS      current
    DESCRIPTION
	"The Slot number for this port"
    ::= { starPortEntry 1 }

starPortNum OBJECT-TYPE
    SYNTAX      Integer32(1..29)
    MAX-ACCESS  accessible-for-notify
    STATUS      current
    DESCRIPTION
        "The Port number within this slot"
    ::= { starPortEntry 2 }

starPortType OBJECT-TYPE
    SYNTAX	INTEGER {
		    none(0),
		    ethernet10100(1),
		    ethernet1000dualmedia(2),
		    ethernet1000(3),
		    ds3(4),
		    oc3atm(5),
		    oc12atm(6),
		    ds3e(7),
		    rs232(8),
		    bitst1e1(9),
		    virtualethernet(10),
		    ether10g(11),
		    ether100g(12)
		}
    MAX-ACCESS read-only
    STATUS     current
    DESCRIPTION
	" "
    ::= { starPortEntry 3 }

starPortTypeDescr OBJECT-TYPE
    SYNTAX	DisplayString
    MAX-ACCESS  read-only
    STATUS      current
    DESCRIPTION
	"A texual representing of the starPortType attribute"
    ::= { starPortEntry 4 }

starPortAdminState OBJECT-TYPE
    SYNTAX      INTEGER {
		    unknown(0),
		    enabled(1),
		    disabled(2)
		}
    MAX-ACCESS  read-only
    STATUS      current
    DESCRIPTION
	"The administrative start of the port"
    ::= { starPortEntry 5 }

starPortOperState OBJECT-TYPE
    SYNTAX	INTEGER {
		    unknown(0),
		    up(1),
		    down(2),
		    notapplicable(3)
		}
    MAX-ACCESS	read-only
    STATUS      current
    DESCRIPTION
	" "
    ::= { starPortEntry 6 }

starPortOperMode OBJECT-TYPE
    SYNTAX	INTEGER {
		    unknown(0),
		    active(1),
		    standby(2)
		}
    MAX-ACCESS	read-only
    STATUS      current
    DESCRIPTION
	" "
    ::= { starPortEntry 7 }

starPortLinkState OBJECT-TYPE
    SYNTAX      INTEGER {
		    unknown(0),
		    up(1),
		    down(2)
		}
    MAX-ACCESS  read-only
    STATUS	current
    DESCRIPTION
	" "
    ::= { starPortEntry 8 }

starRedundantPortSlot OBJECT-TYPE
    SYNTAX	Integer32(0..48)
    MAX-ACCESS  read-only
    STATUS      current
    DESCRIPTION
	"The Slot number for the port the current port is redundant with, or 0 if unknown"
    ::= { starPortEntry 9 }

starRedundantPortNum OBJECT-TYPE
    SYNTAX      Integer32(0..29)
    MAX-ACCESS  read-only
    STATUS      current
    DESCRIPTION
        "The Port number for the port the current port is redundant with, or 0 if unknown"
    ::= { starPortEntry 10 }

starPortRxBytes OBJECT-TYPE
    SYNTAX      Counter32
    UNITS       "Megabytes"
    MAX-ACCESS  read-only
    STATUS      current
    DESCRIPTION
	"The number of bytes successfully received, in megabytes.
	 For ports of type rs232(8) or bitst1e1(9) this value will always be zero."
    ::= { starPortEntry 11 }

starPortTxBytes OBJECT-TYPE
    SYNTAX      Counter32
    UNITS       "Megabytes"
    MAX-ACCESS  read-only
    STATUS      current
    DESCRIPTION
	"The number of bytes successfully transmitted, in megabytes.
	 For ports of type rs232(8) or bitst1e1(9) this value will always be zero."
    ::= { starPortEntry 12 }

starPortRxFrames OBJECT-TYPE
    SYNTAX      Counter32
    UNITS       "Thousands"
    MAX-ACCESS  read-only
    STATUS      current
    DESCRIPTION
	"The number of frames successfully received, in thousands.
	 For ports of type rs232(8) or bitst1e1(9) this value will always be zero.
	 For ports of type oc3atm(5) and oc12atm(6) this is the count of cells received"
    ::= { starPortEntry 13 }

starPortTxFrames OBJECT-TYPE
    SYNTAX      Counter32
    UNITS       "Thousands"
    MAX-ACCESS  read-only
    STATUS      current
    DESCRIPTION
	"The number of frames successfully transmitted, in thousands.
	 For ports of type rs232(8) or bitst1e1(9) this value will always be zero.
	 For ports of type oc3atm(5) and oc12atm(6) this is the count of cells received"
    ::= { starPortEntry 14 }

starPortRxDiscards OBJECT-TYPE
    SYNTAX      Counter32
    MAX-ACCESS  read-only
    STATUS      current
    DESCRIPTION
        "The number of inbound packets which were chosen to be discarded even though no 
         errors had been detected to prevent their being deliverable to a higher-layer 
         protocol. One possible reason for discarding such a packet could be to free up 
         buffer space. "
    ::= { starPortEntry 15 }

starPortTxDiscards OBJECT-TYPE
    SYNTAX      Counter32
    MAX-ACCESS  read-only
    STATUS      current
    DESCRIPTION
        "The number of outbound packets which were chosen to be discarded even though 
         no errors had been detected to prevent their being transmitted. One possible reason 
         for discarding such a packet could be to free up buffer space."
    ::= { starPortEntry 16 }

starPortRxErrors OBJECT-TYPE
    SYNTAX      Counter32
    MAX-ACCESS  read-only
    STATUS      current
    DESCRIPTION
        "The number of inbound packets that contained errors preventing them from being 
         deliverable to a higher-layer protocol." 
    ::= { starPortEntry 17 }

starPortTxErrors OBJECT-TYPE
    SYNTAX      Counter32
    UNITS       "Thousands"
    MAX-ACCESS  read-only
    STATUS      current
    DESCRIPTION
        "The number of outbound packets that could not be transmitted because of errors."
    ::= { starPortEntry 18 }

starentIPPool OBJECT IDENTIFIER ::= { starentMIBObjects 30 }

starIPPoolTable OBJECT-TYPE
    SYNTAX	SEQUENCE OF StarIPPoolEntry
    MAX-ACCESS  not-accessible
    STATUS      current
    DESCRIPTION
	"A table containing IP Pool information"
    ::= { starentIPPool 1 }

starIPPoolEntry OBJECT-TYPE
    SYNTAX	StarIPPoolEntry
    MAX-ACCESS  not-accessible
    STATUS      current
    DESCRIPTION
        "Information for a specific IP Pool"
    INDEX { IMPLIED starIPPoolID }
    ::= { starIPPoolTable 1 }

StarIPPoolEntry ::=
    SEQUENCE {
	starIPPoolVpnID         Gauge32,
        starIPPoolID            StarMediumID,
	starIPPoolContext	DisplayString,
        starIPPoolGroup		DisplayString,
	starIPPoolName          OCTET STRING,
	starIPPoolType          INTEGER,
	starIPPoolState         INTEGER,
	starIPPoolStartAddr     IpAddress,
	starIPPoolMaskorEndAddr IpAddress,
	starIPPoolPriority      Integer32,
	starIPPoolUsed          Gauge32,
	starIPPoolHold          Gauge32,
	starIPPoolRelease       Gauge32,
	starIPPoolFree          Gauge32
    }

starIPPoolVpnID OBJECT-TYPE
    SYNTAX	Gauge32
    MAX-ACCESS  read-only
    STATUS      current
    DESCRIPTION
	"The context ID for this pool"
    ::= { starIPPoolEntry 1 }

starIPPoolID OBJECT-TYPE
    SYNTAX	StarMediumID
    MAX-ACCESS  not-accessible
    STATUS      current
    DESCRIPTION
	"The service identification is made up from first 8 chars of context name
         and the pool name (max 32 chars ) separated by (:)"
    ::= { starIPPoolEntry 2 }

starIPPoolContext OBJECT-TYPE
    SYNTAX	DisplayString
    MAX-ACCESS  read-only
    STATUS      current
    DESCRIPTION
	"The context name string for this pool"
    ::= { starIPPoolEntry 3 }

starIPPoolGroup OBJECT-TYPE
    SYNTAX      DisplayString
    MAX-ACCESS  read-only
    STATUS      current
    DESCRIPTION
        "The name of the group to which the IP pool belongs"
    ::= { starIPPoolEntry 4 }

starIPPoolName OBJECT-TYPE
    SYNTAX      OCTET STRING (SIZE (1..32))
    MAX-ACCESS  read-only
    STATUS      current
    DESCRIPTION
        "The name of the IP pool"
    ::= { starIPPoolEntry 5 }

starIPPoolType OBJECT-TYPE
    SYNTAX      INTEGER {
	 	  unknown(0),
		  private(1),
		  public(2),
		  static(3),
		  resource(4),
		  nat(5)
                }
    MAX-ACCESS  read-only
    STATUS      current
    DESCRIPTION
        "The type of the pool"
    ::= { starIPPoolEntry 6 }

starIPPoolState OBJECT-TYPE
    SYNTAX      INTEGER {
	 	  unknown(0),
		  good(1),
		  pendingdelete(2),
		  alarm(3),
		  resize(4),
		  inactive(5)
                }
    MAX-ACCESS  read-only
    STATUS      current
    DESCRIPTION
        "The state of the pool"
    ::= { starIPPoolEntry 7 }

starIPPoolStartAddr OBJECT-TYPE
    SYNTAX      IpAddress
    MAX-ACCESS  read-only
    STATUS      current
    DESCRIPTION
        "The start IP address of the pool"
    ::= { starIPPoolEntry 8 }

starIPPoolMaskorEndAddr OBJECT-TYPE
    SYNTAX      IpAddress
    MAX-ACCESS  read-only
    STATUS      current
    DESCRIPTION
        "The mask or end IP address of the pool"
    ::= { starIPPoolEntry 9 }

starIPPoolPriority OBJECT-TYPE
    SYNTAX      Integer32
    MAX-ACCESS  read-only
    STATUS      current
    DESCRIPTION
        "The priority of the pool"
    ::= { starIPPoolEntry 10 }

starIPPoolUsed OBJECT-TYPE
    SYNTAX      Gauge32
    MAX-ACCESS  read-only
    STATUS      current
    DESCRIPTION
        "The number of IP addresses in USED state in the pool"
    ::= { starIPPoolEntry 11 }

starIPPoolHold OBJECT-TYPE
    SYNTAX      Gauge32
    MAX-ACCESS  read-only
    STATUS      current
    DESCRIPTION
        "The number of IP addresses in HOLD state in the pool"
    ::= { starIPPoolEntry 12 }

starIPPoolRelease OBJECT-TYPE
    SYNTAX      Gauge32
    MAX-ACCESS  read-only
    STATUS      current
    DESCRIPTION
        "The number of IP addresses in RELEASE state in the pool"
    ::= { starIPPoolEntry 13 }

starIPPoolFree OBJECT-TYPE
    SYNTAX      Gauge32
    MAX-ACCESS  read-only
    STATUS      current
    DESCRIPTION
        "The number of IP addresses in FREE state in the pool"
    ::= { starIPPoolEntry 14 }

starentIPPoolGroup OBJECT IDENTIFIER ::= { starentMIBObjects 64 }

starIPPoolGroupTable OBJECT-TYPE
    SYNTAX	SEQUENCE OF StarIPPoolGroupEntry
    MAX-ACCESS  not-accessible
    STATUS      current
    DESCRIPTION
	"A table containing IP Pool Group information"
    ::= { starentIPPoolGroup 1 }

starIPPoolGroupEntry OBJECT-TYPE
    SYNTAX	StarIPPoolGroupEntry
    MAX-ACCESS  not-accessible
    STATUS      current
    DESCRIPTION
        "Information for a specific IP Pool Group"
    INDEX { IMPLIED starIPPoolGroupID}
    ::= { starIPPoolGroupTable 1 }

StarIPPoolGroupEntry ::=
    SEQUENCE {
        starIPPoolGroupVpnID    Gauge32,	
        starIPPoolGroupID       StarMediumID,
        starIPPoolGroupName     DisplayString,
        starIPPoolGroupVpnName  DisplayString,
        starIPPoolGroupUsed     Gauge32, 
        starIPPoolGroupHold     Gauge32,
        starIPPoolGroupRelease  Gauge32,
        starIPPoolGroupFree     Gauge32,
        starIPPoolGroupPctUsed  Integer32,
        starIPPoolGroupAvail    Gauge32
    }

starIPPoolGroupVpnID OBJECT-TYPE
    SYNTAX      Gauge32  
    MAX-ACCESS  not-accessible
    STATUS      current
    DESCRIPTION
        "The context ID for this pool group"
    ::= { starIPPoolGroupEntry 1 }

starIPPoolGroupID OBJECT-TYPE
    SYNTAX	StarMediumID
    MAX-ACCESS  not-accessible
    STATUS      current
    DESCRIPTION
	"The service identification is made up from first 8 chars of context name
         and first 16 chars of pool group name separated by (:)"
    ::= { starIPPoolGroupEntry 2 }

starIPPoolGroupName OBJECT-TYPE
    SYNTAX      DisplayString
    MAX-ACCESS  read-only
    STATUS      current
    DESCRIPTION
        "The name of the IP pool group"
    ::= { starIPPoolGroupEntry 3 }

starIPPoolGroupVpnName OBJECT-TYPE
    SYNTAX	DisplayString
    MAX-ACCESS  read-only
    STATUS      current
    DESCRIPTION
	"The context name string for this pool group"
    ::= { starIPPoolGroupEntry 4 }

starIPPoolGroupUsed OBJECT-TYPE
    SYNTAX      Gauge32
    MAX-ACCESS  read-only
    STATUS      current
    DESCRIPTION
        "The number of IP addresses in USED state in the pool group"
    ::= { starIPPoolGroupEntry 5 }

starIPPoolGroupHold OBJECT-TYPE
    SYNTAX      Gauge32
    MAX-ACCESS  read-only
    STATUS      current
    DESCRIPTION
        "The number of IP addresses in HOLD state in the pool group"
    ::= { starIPPoolGroupEntry 6 }

starIPPoolGroupRelease OBJECT-TYPE
    SYNTAX      Gauge32
    MAX-ACCESS  read-only
    STATUS      current
    DESCRIPTION
        "The number of IP addresses in RELEASE state in the pool group"
    ::= { starIPPoolGroupEntry 7 }

starIPPoolGroupFree OBJECT-TYPE
    SYNTAX      Gauge32
    MAX-ACCESS  read-only
    STATUS      current
    DESCRIPTION
        "The number of IP addresses in FREE state in the pool group"
    ::= { starIPPoolGroupEntry 8 }

starIPPoolGroupPctUsed OBJECT-TYPE
    SYNTAX     Integer32(0..10000)
    UNITS      "percentage times 100"
    MAX-ACCESS  read-only
    STATUS      current
    DESCRIPTION
        "The percentage of IP addresses in USED state in the pool group is the 
	 percentage value times 100; for example,2.3% would be represented as 230"
    ::= { starIPPoolGroupEntry 9 }

starIPPoolGroupAvail OBJECT-TYPE
    SYNTAX      Gauge32
    MAX-ACCESS  read-only
    STATUS      current
    DESCRIPTION
        "The number of IP addresses in AVAILABLE state in the pool group"
    ::= { starIPPoolGroupEntry 10 }

-- Objects used only in traps

starentTrapData OBJECT IDENTIFIER ::= { starentMIBObjects 31 }

starCongestionPolicy OBJECT-TYPE
    SYNTAX      INTEGER {
		  reject(1),
		  redirect(2),
		  drop(3)
    }
    MAX-ACCESS  accessible-for-notify
    STATUS      current
    DESCRIPTION
       "The policy invoked for congestion events"
    ::= { starentTrapData 1 }

starCongestionResourceType OBJECT-TYPE
    SYNTAX      INTEGER {
		  systemcpu(1),
		  servicecpu(2),
		  averagememory(3),
		  queuesize(4),
		  queuedelay(5),
		  license(6),
		  portutil(7),
		  rxportutil(8),
		  txportutil(9),
		  rxperportutil(10),
		  txperportutil(11),
		  servicecapacity(12)
		}
    MAX-ACCESS  accessible-for-notify
    STATUS      current
    DESCRIPTION
       "The resource type for a congestion event"
    ::= { starentTrapData 2 }

starPTACConfig OBJECT-TYPE
    SYNTAX      Integer32(0..14)
    MAX-ACCESS  accessible-for-notify
    STATUS      current
    DESCRIPTION
       "The number of PACs/PSCs//TACs configured in the system"
    ::= { starentTrapData 3 }

starPTACActive OBJECT-TYPE
    SYNTAX      Integer32(0..14)
    MAX-ACCESS  accessible-for-notify
    STATUS      current
    DESCRIPTION
       "The number of PACs/PSCs/TACs active in the system"
    ::= { starentTrapData 4 }

starContextName OBJECT-TYPE
    SYNTAX      DisplayString
    MAX-ACCESS  accessible-for-notify
    STATUS      current
    DESCRIPTION
       "The name of a context configured on the IMG"
    ::= { starentTrapData 5 }

starInterfaceName OBJECT-TYPE
    SYNTAX      DisplayString
    MAX-ACCESS  accessible-for-notify
    STATUS      current
    DESCRIPTION
       "The name of an interface"
    ::= { starentTrapData 6 }

starPCFAddress OBJECT-TYPE
    SYNTAX      IpAddress
    MAX-ACCESS  accessible-for-notify
    STATUS      current
    DESCRIPTION
       "The IP address of a PCF"
    ::= { starentTrapData 7 }

starPeerAddress OBJECT-TYPE
    SYNTAX      IpAddress
    MAX-ACCESS  accessible-for-notify
    STATUS      current
    DESCRIPTION
       "Peer Address"
    ::= { starentTrapData 8 }

-- License traps

starLicensedSessions OBJECT-TYPE
    SYNTAX 	Unsigned32
    MAX-ACCESS  accessible-for-notify
    STATUS      current
    DESCRIPTION
	"The number of sessions enabled by the software license"
    ::= { starentTrapData 9 }

starCurrentSessions OBJECT-TYPE
    SYNTAX 	Gauge32
    MAX-ACCESS  accessible-for-notify
    STATUS      current
    DESCRIPTION
	"The number of current sessions in use against a software license"
    ::= { starentTrapData 10 }

starL3Address OBJECT-TYPE
    SYNTAX      IpAddress
    MAX-ACCESS  accessible-for-notify
    STATUS      current
    DESCRIPTION
	"L3 Address"
    ::= { starentTrapData 11 }

starUDPPortNum OBJECT-TYPE
    SYNTAX      Integer32(1..65535)
    MAX-ACCESS  accessible-for-notify
    STATUS      current
    DESCRIPTION
	"UDP Port Number"
    ::= { starentTrapData 12 }

starSRPIpAddress OBJECT-TYPE
    SYNTAX      IpAddress
    MAX-ACCESS  accessible-for-notify
    STATUS      current
    DESCRIPTION
	"SRP IP Address"
    ::= { starentTrapData 13 }

starBGPPeerIpAddress OBJECT-TYPE
    SYNTAX      IpAddress
    MAX-ACCESS  accessible-for-notify
    STATUS      current
    DESCRIPTION
	"BGP Peer IP Address"
    ::= { starentTrapData 14 }

starContFiltCFFilename OBJECT-TYPE
    SYNTAX      DisplayString
    MAX-ACCESS  accessible-for-notify
    STATUS      current
    DESCRIPTION
	"File name for the OPTCMDB"
    ::= { starentTrapData 15 }

starContFiltCFErrorCode OBJECT-TYPE
    SYNTAX     	INTEGER {
                  unknownerror(1),
                  notavailable(2),
                  loadfailure(3)
                }
    MAX-ACCESS  accessible-for-notify
    STATUS      current
    DESCRIPTION
       "Error code"
    ::= { starentTrapData 16 }

starFecthedFromAAAMgr OBJECT-TYPE
    SYNTAX     Integer32
    MAX-ACCESS accessible-for-notify
    STATUS     current
    DESCRIPTION
        "The number calls fetched from aaa mgr"
    ::= { starentTrapData 17 }

starPriorToAudit OBJECT-TYPE
    SYNTAX     Integer32
    MAX-ACCESS accessible-for-notify
    STATUS     current
    DESCRIPTION
        "The number calls prior to audit"
    ::= { starentTrapData 18 }

starPassedAudits OBJECT-TYPE
    SYNTAX     Integer32
    MAX-ACCESS accessible-for-notify
    STATUS     current
    DESCRIPTION
        "The number of calls passed audit"
    ::= { starentTrapData 19 }

starCallsRecovered OBJECT-TYPE
    SYNTAX     Integer32
    MAX-ACCESS accessible-for-notify
    STATUS     current
    DESCRIPTION
        "The number of calls recovered"
    ::= { starentTrapData 20 }

starAllCallLines OBJECT-TYPE
    SYNTAX     Integer32
    MAX-ACCESS accessible-for-notify
    STATUS     current
    DESCRIPTION
        "The number of a11 call lines"
    ::= { starentTrapData 21 }

starElapsedMs OBJECT-TYPE
    SYNTAX     Integer32
    MAX-ACCESS accessible-for-notify
    STATUS     current
    DESCRIPTION
        "The audit time elapsed in ms"
    ::= { starentTrapData 22 }

starCDRFilename OBJECT-TYPE
    SYNTAX     DisplayString
    MAX-ACCESS accessible-for-notify
    STATUS     current
    DESCRIPTION
	"The name of a CDR (EDR/UDR) file"
    ::= { starentTrapData 23 }

-- Diameter

starDiameterVpnName OBJECT-TYPE
    SYNTAX      DisplayString
    MAX-ACCESS  accessible-for-notify
    STATUS      current
    DESCRIPTION
	"Diameter VPN (Context) Name"
    ::= { starentTrapData 24 }

starDiameterPeerAddr OBJECT-TYPE
    SYNTAX      IpAddress
    MAX-ACCESS  accessible-for-notify
    STATUS      current
    DESCRIPTION
	"Diameter Peer Address"
    ::= { starentTrapData 25 }

starDiameterEndpointName OBJECT-TYPE
    SYNTAX      DisplayString
    MAX-ACCESS  accessible-for-notify
    STATUS      current
    DESCRIPTION
	"Diameter Endpoint Name"
    ::= { starentTrapData 26 }

starDiameterPeerAddrIpv6 OBJECT-TYPE
    SYNTAX      Ipv6Address
    MAX-ACCESS  accessible-for-notify
    STATUS      current
    DESCRIPTION
	"Diameter Peer Address"
    ::= { starentTrapData 34 }

starInterfaceIPAddress OBJECT-TYPE
    SYNTAX      IpAddress
    MAX-ACCESS  accessible-for-notify
    STATUS      current
    DESCRIPTION
        "Interface IP Address"
    ::= { starentTrapData 27 }


starOSPFNeighborRouterID OBJECT-TYPE
    SYNTAX      IpAddress
    MAX-ACCESS  accessible-for-notify
    STATUS      current
    DESCRIPTION
	"Interface IP Address"
    ::= { starentTrapData 28 }

starOSPFFromState OBJECT-TYPE
    SYNTAX      StarOSPFNeighborState
    MAX-ACCESS  accessible-for-notify
    STATUS      current
    DESCRIPTION
	"FROM state for OSPF Neighbor"
    ::= { starentTrapData 29 }

starOSPFToState OBJECT-TYPE
    SYNTAX      StarOSPFNeighborState
    MAX-ACCESS  accessible-for-notify
    STATUS      current
    DESCRIPTION
	"TO state for OSPF Neighbor"
    ::= { starentTrapData 30 }

starBLFilename OBJECT-TYPE
    SYNTAX      DisplayString
    MAX-ACCESS  accessible-for-notify
    STATUS      current
    DESCRIPTION
	"File name for the OPTBLDB"
    ::= { starentTrapData 31 }

starBLErrorCode OBJECT-TYPE
    SYNTAX      INTEGER {
		  unknownerror(1),
		  notavailable(2),
                  loadfailure(3)
                }
    MAX-ACCESS  accessible-for-notify
    STATUS      current
    DESCRIPTION
       "Error code"
    ::= { starentTrapData 32 }

starDiameterECode OBJECT-TYPE
    SYNTAX      INTEGER {
    		   notcomplete(1),
		   hostnamemismatch(2),
		   hostrealmmismatch(3),
		   securitymismatch(4),
		   tlssertificateerror(5),
		   tlshandshakeerror(6),
		   authappidmismatch(7)
		}
    MAX-ACCESS  accessible-for-notify
    STATUS      current
    DESCRIPTION
	"Diameter Cause Code"
    ::= { starentTrapData 33 }

starContFiltCFUpgradeFilename OBJECT-TYPE
    SYNTAX      DisplayString
    MAX-ACCESS  accessible-for-notify
    STATUS      current
    DESCRIPTION
	"File name for the Full or Incremental OPTCMDB"
    ::= { starentTrapData 35 }

starContFiltCFUpgradeErrorCode OBJECT-TYPE
  SYNTAX      INTEGER {
                unknownerror(1),
                upgradefullfailure(2),
                upgradeincrfailure(3)
              }

    MAX-ACCESS  accessible-for-notify
    STATUS      current
    DESCRIPTION
       "Error code"
    ::= { starentTrapData 36 }

starBLUpgradeFilename OBJECT-TYPE
    SYNTAX      DisplayString
    MAX-ACCESS  accessible-for-notify
    STATUS      current
    DESCRIPTION
	"File name for the Full OPTBLDB"
    ::= { starentTrapData 37 }

starBLUpgradeErrorCode OBJECT-TYPE
  SYNTAX       INTEGER {
                  unknownerror(1),
                  upgradefullfailure(2)
              }

    MAX-ACCESS  accessible-for-notify
    STATUS      current
    DESCRIPTION
       "Error code"
    ::= { starentTrapData 38 }

starDynPkgFilename OBJECT-TYPE
    SYNTAX      DisplayString
    MAX-ACCESS  accessible-for-notify
    STATUS      current
    DESCRIPTION
    "File name for the DynPkg"
    ::= { starentTrapData 39 }

starDynCFErrorCode OBJECT-TYPE
    SYNTAX      INTEGER {
        unknownerror(1),
        notavailable(2),
        loadfailure(3)
    }
    MAX-ACCESS  accessible-for-notify
    STATUS      current
    DESCRIPTION
    "Error code"
    ::= { starentTrapData 40 }

starDynPkgUpgradeFilename OBJECT-TYPE
        SYNTAX      DisplayString
        MAX-ACCESS  accessible-for-notify
        STATUS      current
        DESCRIPTION
        "File name for the Full DynPkg"
        ::= { starentTrapData 41 }

starDynCFUpgradeErrorCode OBJECT-TYPE
        SYNTAX      INTEGER {
          unknownerror(1),
          upgradefullfailure(2)
        }

        MAX-ACCESS  accessible-for-notify
        STATUS      current
        DESCRIPTION
        "Error code"
        ::= { starentTrapData 42 }

starCscfSessCongestionResourceType OBJECT-TYPE
    SYNTAX      INTEGER {
		  cpu(1),
		  memory(2)
		}
    MAX-ACCESS  accessible-for-notify
    STATUS      current
    DESCRIPTION
       "Cscf Session resource type for a congestion event"
    ::= { starentTrapData 43 }

starSmgrId OBJECT-TYPE
    SYNTAX      Integer32(1..255)
    MAX-ACCESS  accessible-for-notify
    STATUS      current
    DESCRIPTION
	"Session Manager Instance ID"
    ::= { starentTrapData 44 }
								      
-- EGTP traps

starEGTPVpnName OBJECT-TYPE
    SYNTAX     DisplayString
    MAX-ACCESS accessible-for-notify
    STATUS     current
    DESCRIPTION
        "The name of this VPN (context)"
    ::= { starentTrapData 45 }

starEGTPServName OBJECT-TYPE
    SYNTAX     DisplayString
    MAX-ACCESS accessible-for-notify
    STATUS     current
    DESCRIPTION
        "The name of this service"
    ::= { starentTrapData 46 }

starEGTPInterfaceType OBJECT-TYPE
    SYNTAX      INTEGER {
		  invalid(0),
		  sgwingress(1),
		  sgwegress(2),
		  pgwingress(3),
		  sgsn(4)
                }
    MAX-ACCESS  accessible-for-notify
    STATUS      current
    DESCRIPTION
        "Egtp interface type"
    ::= { starentTrapData 47 }

starEGTPSelfPort OBJECT-TYPE
    SYNTAX     Gauge32
    MAX-ACCESS accessible-for-notify
    STATUS     current
    DESCRIPTION
        "The Port number of the EGTP"
    ::= { starentTrapData 48 }

starEGTPSelfAddr OBJECT-TYPE
    SYNTAX     IpAddress
    MAX-ACCESS accessible-for-notify
    STATUS     current
    DESCRIPTION
        "The IP Address of the EGTP"
    ::= { starentTrapData 49 }

starEGTPPeerPort OBJECT-TYPE
    SYNTAX     Gauge32
    MAX-ACCESS accessible-for-notify
    STATUS     current
    DESCRIPTION
        "The Port number of the PeerNode"
    ::= { starentTrapData  50 }

starEGTPPeerAddr OBJECT-TYPE
    SYNTAX     IpAddress
    MAX-ACCESS accessible-for-notify
    STATUS     current
    DESCRIPTION
        "The IP Address of the PeerNode"
    ::= { starentTrapData  51 }

starEGTPPeerOldRstCnt OBJECT-TYPE
    SYNTAX     Gauge32
    MAX-ACCESS accessible-for-notify
    STATUS     current
    DESCRIPTION
        "EGTP peer old restart counter"
    ::= { starentTrapData 52 }

starEGTPPeerNewRstCnt OBJECT-TYPE
    SYNTAX     Gauge32
    MAX-ACCESS accessible-for-notify
    STATUS     current
    DESCRIPTION
        "EGTP peer new restart counter"
    ::= { starentTrapData 53 }

starEGTPPeerSessCnt OBJECT-TYPE
    SYNTAX     Gauge32
    MAX-ACCESS accessible-for-notify
    STATUS     current
    DESCRIPTION
        "EGTP peer session count"
    ::= { starentTrapData 54 }

starEGTPFailureReason OBJECT-TYPE
    SYNTAX      INTEGER {
		  unknown(0),
		  restartcounterchange(1),
                  noresponsefrompeer(2)
                }
    MAX-ACCESS  accessible-for-notify
    STATUS      current
    DESCRIPTION
        "Egtp path failure reason"
    ::= { starentTrapData 55 }

starGSSCDRLossConfigured OBJECT-TYPE
       SYNTAX     Unsigned32
       MAX-ACCESS accessible-for-notify
       STATUS     current
       DESCRIPTION
       "The configured value of threshold CDR Loss at GSS"
       ::= { starentTrapData 56 }

starGSSCDRLossMeasured OBJECT-TYPE
      SYNTAX     Unsigned32
      MAX-ACCESS accessible-for-notify
      STATUS     current
      DESCRIPTION
      "The Measured value of CDR Loss at GSS"
      ::= { starentTrapData 57 }

starLicenseKey OBJECT-TYPE
    SYNTAX     Unsigned32
    MAX-ACCESS accessible-for-notify
    STATUS     current
    DESCRIPTION
        "The license key"
    ::= { starentTrapData 58 }

starLicenseExpiryDate OBJECT-TYPE
    SYNTAX     DateAndTime
    MAX-ACCESS accessible-for-notify
    STATUS     current
    DESCRIPTION
        "The license expiration date/time"
    ::= { starentTrapData 59 }

starLicenseDaysRemaining OBJECT-TYPE
    SYNTAX     Unsigned32
    MAX-ACCESS accessible-for-notify
    STATUS     current
    DESCRIPTION
        "The number of days remaining before the license expires"
    ::= { starentTrapData 60 }

starLicenseDaysAfterExpiry OBJECT-TYPE
    SYNTAX     Unsigned32
    MAX-ACCESS accessible-for-notify
    STATUS     current
    DESCRIPTION
        "The number of days after the license has expired"
    ::= { starentTrapData 61 }

starNPUSlot OBJECT-TYPE
    SYNTAX  Integer32(1..48)
    MAX-ACCESS accessible-for-notify 
    STATUS  current
    DESCRIPTION
	"The NPU slot number"
    ::= { starentTrapData 62 }

starSPRServerIpAddr OBJECT-TYPE
    SYNTAX     IpAddress
    MAX-ACCESS accessible-for-notify
    STATUS     current
    DESCRIPTION
        "The IP Address of the SSC Server"
    ::= { starentTrapData 63 }

-- MVG objects,used for traps only

starMVGEndpointName OBJECT-TYPE
    SYNTAX      DisplayString
    MAX-ACCESS  accessible-for-notify
    STATUS      current
    DESCRIPTION
	"MVG Endpoint Name"
    ::= { starentTrapData 66 }

starMVGCauseCode OBJECT-TYPE
    SYNTAX      INTEGER {
        servernotreachable(1),
        servicereachable(2)
    }
    MAX-ACCESS  accessible-for-notify
    STATUS      current
    DESCRIPTION
	"MVG Cause Code"
    ::= { starentTrapData 69 }

starMVGProtocolType OBJECT-TYPE
    SYNTAX      INTEGER {
        protocolhttp(1),
        protocoltcp(2),
        protocolicmp(3)
    }
    MAX-ACCESS  accessible-for-notify
    STATUS      current
    DESCRIPTION
	"MVG Protocol Types"
    ::= { starentTrapData 68 }


starPCCNtfyIntfPeerName OBJECT-TYPE
    SYNTAX      DisplayString
    MAX-ACCESS  accessible-for-notify
    STATUS      current
    DESCRIPTION
        " IPCF Event Notification Interface Peer Name "
    ::= { starentTrapData 73 }

starECSTotalDNSLearntIPThresholdInstance OBJECT-TYPE    
    SYNTAX      Integer32(1..65535)
    MAX-ACCESS  accessible-for-notify
    STATUS      current
    DESCRIPTION 
    " ACSMgr Instance Id"
    ::= { starentTrapData 74 }

starECSTotalDNSLearntIPThresholdconfigured OBJECT-TYPE
    SYNTAX      Integer32 (1..100)
    MAX-ACCESS  accessible-for-notify
    STATUS      current
    DESCRIPTION
    " Configured Threshold value in Percentage"
    ::= { starentTrapData 75 }

starECSTotalDNSLearntIPThresholdmeasured OBJECT-TYPE
    SYNTAX      Integer32 (1..100)
    MAX-ACCESS  accessible-for-notify
    STATUS      current
    DESCRIPTION 
    " Measured value in Percentage"
    ::= { starentTrapData 76 }

 starPeerAddressIpv6 OBJECT-TYPE
    SYNTAX      Ipv6Address
    MAX-ACCESS  accessible-for-notify
    STATUS      current
    DESCRIPTION
       "Peer Ipv6 Address"
    ::= { starentTrapData 77 }

starLAGPartner OBJECT-TYPE
    SYNTAX     DisplayString
    MAX-ACCESS accessible-for-notify
    STATUS     current
    DESCRIPTION
        "The name of this service"
    ::= { starentTrapData 78 }

starSGSServiceVpnName OBJECT-TYPE
    SYNTAX      DisplayString
    MAX-ACCESS  accessible-for-notify
    STATUS      current
    DESCRIPTION
       "SGS service context name"
    ::= { starentTrapData 79 }

starSGSServiceServName OBJECT-TYPE
    SYNTAX      DisplayString
    MAX-ACCESS  accessible-for-notify
    STATUS      current
    DESCRIPTION
       "SGS service name"
    ::= { starentTrapData 80 }

starVLRName OBJECT-TYPE
    SYNTAX      DisplayString
    MAX-ACCESS  accessible-for-notify
    STATUS      current
    DESCRIPTION
       "VLR name"
    ::= { starentTrapData 81 }

starVLRIpAddr1 OBJECT-TYPE
    SYNTAX      IpAddress
    MAX-ACCESS  accessible-for-notify
    STATUS      current
    DESCRIPTION
        "VLR IP Address1"
    ::= { starentTrapData 82 }

starVLRIpAddr2 OBJECT-TYPE
    SYNTAX      IpAddress
    MAX-ACCESS  accessible-for-notify
    STATUS      current
    DESCRIPTION
        "VLR IP Address2"
    ::= { starentTrapData 83 }

starVLRPortNum OBJECT-TYPE
    SYNTAX      Integer32(1..65535)
    MAX-ACCESS  accessible-for-notify
    STATUS      current
    DESCRIPTION
        "VLR Port Number"
    ::= { starentTrapData 84 }

starCongestionType OBJECT-TYPE
    SYNTAX      INTEGER {
                  critical(1),
                  major(2),
                  minor(3)
                }
    MAX-ACCESS  accessible-for-notify
    STATUS      current
    DESCRIPTION
       "The type congestion threshold hit"
    ::= { starentTrapData 85 }

starCongestionActionProfileName OBJECT-TYPE
    SYNTAX      DisplayString
    MAX-ACCESS  accessible-for-notify
    STATUS      current
    DESCRIPTION
       "The name of a action profile asscociated with the threshold type"
    ::= { starentTrapData 86 }


starSessMgrFlowInstId OBJECT-TYPE
    SYNTAX      Integer32(1..65535)
    MAX-ACCESS accessible-for-notify
    STATUS     current
    DESCRIPTION
        "Session Manager instance ID"
    ::= { starentTrapData 87 }        

starSessMgrFlowPDNNo OBJECT-TYPE
    SYNTAX      Integer32(1..65535)
    MAX-ACCESS accessible-for-notify
    STATUS     current
    DESCRIPTION
        "Tota PDNs Available"
    ::= { starentTrapData 88 }        

starSessMgrFlowMemUsage OBJECT-TYPE
    SYNTAX      Integer32(1..65535)
    MAX-ACCESS accessible-for-notify
    STATUS     current
    DESCRIPTION
        "Totat Memory Usage of this instance"
    ::= { starentTrapData 89 }        

starSessMgrFlowCounter OBJECT-TYPE
    SYNTAX      Integer32(1..65535)
    MAX-ACCESS accessible-for-notify
    STATUS     current
    DESCRIPTION
        "Session Manager Active Flows"
    ::= { starentTrapData 90 }        

starSessMgrTotalFlowCount OBJECT-TYPE
    SYNTAX      Integer32(1..65535)
    MAX-ACCESS accessible-for-notify
    STATUS     current
    DESCRIPTION
        "Session Manager Active Flows"
    ::= { starentTrapData 91 }        

starHENBGWServiceVpnName OBJECT-TYPE
    SYNTAX      DisplayString
    MAX-ACCESS  accessible-for-notify
    STATUS      current
    DESCRIPTION
       "HENBGW Service VPN Name"
    ::= { starentTrapData 92 }

starHENBGWServiceServName OBJECT-TYPE
    SYNTAX      DisplayString
    MAX-ACCESS  accessible-for-notify
    STATUS      current
    DESCRIPTION
       "HENBGW Service Name"
    ::= { starentTrapData 93 }

starHENBGWServiceLogicalENBId OBJECT-TYPE
    SYNTAX      DisplayString
    MAX-ACCESS  accessible-for-notify
    STATUS      current
    DESCRIPTION
       "HENBGW Service Logical Enodb ID"
    ::= { starentTrapData 94 }

starHENBGWServiceMMEServName OBJECT-TYPE
    SYNTAX      DisplayString
    MAX-ACCESS  accessible-for-notify
    STATUS      current
    DESCRIPTION
       "HENBGW Service MME Name"
    ::= { starentTrapData 95 }

starHENBGWServiceSelfAddr OBJECT-TYPE
    SYNTAX      IpAddress
    MAX-ACCESS  not-accessible
    STATUS      current
    DESCRIPTION
        "HENBGW Service Self IP Address"
    ::= { starentTrapData 96 }

starHENBGWServicePeerAddr OBJECT-TYPE
    SYNTAX      IpAddress
    MAX-ACCESS  accessible-for-notify
    STATUS      current
    DESCRIPTION
        "HENBGW Service Peer IP Address"
    ::= { starentTrapData 97 }

starHENBGWServiceSelfPort  OBJECT-TYPE
    SYNTAX      Integer32(1..65535)
    MAX-ACCESS  not-accessible
    STATUS      current
    DESCRIPTION
        "HENBGW Service Self Port Number"
    ::= { starentTrapData 98 }

starHENBGWServicePeerPort  OBJECT-TYPE
    SYNTAX      Integer32(1..65535)
    MAX-ACCESS  accessible-for-notify
    STATUS      current
    DESCRIPTION
        "HENBGW Service Peer Port Number"
    ::= { starentTrapData 99 }

starNPUSlotNumber OBJECT-TYPE
    SYNTAX      Integer32(1..65535)
    MAX-ACCESS accessible-for-notify
    STATUS     current
    DESCRIPTION
        "NPU Slot Number"
    ::= { starentTrapData 100 }

starNPUCPUNumber OBJECT-TYPE
    SYNTAX      Integer32(1..65535)
    MAX-ACCESS accessible-for-notify
    STATUS     current
    DESCRIPTION
        "NPU CPU Number"
    ::= { starentTrapData 101 }

starNPUNPUNumber OBJECT-TYPE
    SYNTAX      Integer32(1..65535)
    MAX-ACCESS accessible-for-notify
    STATUS     current
    DESCRIPTION
        "NPU's NPU Number"
    ::= { starentTrapData 102 }

starChassisCrashList  OBJECT-TYPE
    SYNTAX      TruthValue
    MAX-ACCESS  accessible-for-notify
    STATUS      current
    DESCRIPTION
        "Chassis Crash List Full"
    ::= { starentTrapData 103 }

starLIRcvryErrType OBJECT-TYPE
    SYNTAX      INTEGER {
        syncerror(0),
        readerror(1),
        writeerror(2),
        integrityerror(3)
    }
    MAX-ACCESS  accessible-for-notify
    STATUS      current
    DESCRIPTION
	"LI Recovery Error Types"
    ::= { starentTrapData 104 }

starLIRcvryErrString OBJECT-TYPE
    SYNTAX      DisplayString
    MAX-ACCESS  accessible-for-notify
    STATUS      current
    DESCRIPTION
       "LI Recovery Error String"
    ::= { starentTrapData 105 }

-- PMIP

starPMIPVpnName OBJECT-TYPE
    SYNTAX     DisplayString
    MAX-ACCESS accessible-for-notify
    STATUS     current
    DESCRIPTION
        "The name of this VPN (context)"
    ::= { starentTrapData 106 }

starPMIPServName OBJECT-TYPE
    SYNTAX     DisplayString
    MAX-ACCESS accessible-for-notify
    STATUS     current
    DESCRIPTION
        "The name of this service"
    ::= { starentTrapData 107 }

starPMIPSelfAddrType OBJECT-TYPE
    SYNTAX     InetAddressType
    MAX-ACCESS accessible-for-notify
    STATUS     current
    DESCRIPTION
        "The IP Address of the PMIP"
    ::= { starentTrapData 108 }

starPMIPSelfAddr OBJECT-TYPE
    SYNTAX     InetAddress
    MAX-ACCESS accessible-for-notify
    STATUS     current
    DESCRIPTION
        "The IP Address of the PMIP"
    ::= { starentTrapData 109 }

starPMIPPeerAddrType OBJECT-TYPE
    SYNTAX     InetAddressType
    MAX-ACCESS accessible-for-notify
    STATUS     current
    DESCRIPTION
        "The IP Address of the PMIP"
    ::= { starentTrapData 110 }

starPMIPPeerAddr OBJECT-TYPE
    SYNTAX     InetAddress
    MAX-ACCESS accessible-for-notify
    STATUS     current
    DESCRIPTION
        "The IP Address of the PMIP"
    ::= { starentTrapData 111 }

starPMIPPeerOldRstCnt OBJECT-TYPE
    SYNTAX     Counter32
    MAX-ACCESS accessible-for-notify
    STATUS     current
    DESCRIPTION
        "PMIP peer old restart counter"
    ::= { starentTrapData 112 }

starPMIPPeerNewRstCnt OBJECT-TYPE
    SYNTAX     Counter32
    MAX-ACCESS accessible-for-notify
    STATUS     current
    DESCRIPTION
        "PMIP peer new restart counter"
    ::= { starentTrapData 113 }

starPMIPPeerSessCnt OBJECT-TYPE
    SYNTAX     Counter32
    MAX-ACCESS accessible-for-notify
    STATUS     current
    DESCRIPTION
        "PMIP peer session count"
    ::= { starentTrapData 114 }


starPMIPFailureReason OBJECT-TYPE
    SYNTAX      INTEGER {
                         unknown(0),
                         heartbeatrsprestartchange(1),
                         noresponsefrompeer(2)
                }
    MAX-ACCESS  accessible-for-notify
    STATUS      current
    DESCRIPTION
        "PMIP path failure reason"
    ::= { starentTrapData 115 }

starMMEInitialDisallowReason OBJECT-TYPE
    SYNTAX      DisplayString
    MAX-ACCESS  accessible-for-notify
    STATUS      current
    DESCRIPTION
        "MME initial connection disallow reason."
    ::= { starentTrapData 116 }

starSLSServiceVpnName OBJECT-TYPE
    SYNTAX      DisplayString
    MAX-ACCESS  accessible-for-notify
    STATUS      current
    DESCRIPTION
       "SLS service context name"
    ::= { starentTrapData 117 }

starSLSServiceServName OBJECT-TYPE
    SYNTAX      DisplayString
    MAX-ACCESS  accessible-for-notify
    STATUS      current
    DESCRIPTION
       "SLS service name"
    ::= { starentTrapData 118 }

starESMLCId OBJECT-TYPE
    SYNTAX      Integer32(0..255)
    MAX-ACCESS  accessible-for-notify
    STATUS      current
    DESCRIPTION
       "ESMLC Id"
    ::= { starentTrapData 119 }

starESMLCIpAddr1 OBJECT-TYPE
    SYNTAX      IpAddress
    MAX-ACCESS  accessible-for-notify
    STATUS      current
    DESCRIPTION
        "ESMLC IP Address1"
    ::= { starentTrapData 120 }

starESMLCIpAddr2 OBJECT-TYPE
    SYNTAX      IpAddress
    MAX-ACCESS  accessible-for-notify
    STATUS      current
    DESCRIPTION
        "ESMLC IP Address2"
    ::= { starentTrapData 121 }

starESMLCPortNum OBJECT-TYPE
    SYNTAX      Integer32(1..65535)
    MAX-ACCESS  accessible-for-notify
    STATUS      current
    DESCRIPTION
        "ESMLC Port Number"
    ::= { starentTrapData 122 }

starSBCServiceVpnName OBJECT-TYPE
    SYNTAX      DisplayString
    MAX-ACCESS  accessible-for-notify
    STATUS      current
    DESCRIPTION
       "SBc service context name"
    ::= { starentTrapData 123 }

starSBCServiceServName OBJECT-TYPE
    SYNTAX      DisplayString
    MAX-ACCESS  accessible-for-notify
    STATUS      current
    DESCRIPTION
       "SBc service name"
    ::= { starentTrapData 124 }

starPeerId OBJECT-TYPE
    SYNTAX      Integer32(0..255)
    MAX-ACCESS  accessible-for-notify
    STATUS      current
    DESCRIPTION
       "Peer Id"
    ::= { starentTrapData 125 }

starPeerIpAddr OBJECT-TYPE
    SYNTAX      IpAddress
    MAX-ACCESS  accessible-for-notify
    STATUS      current
    DESCRIPTION
        "Peer IP Address"
    ::= { starentTrapData 126 }

starPeerPortNum OBJECT-TYPE
    SYNTAX      Integer32(1..65535)
    MAX-ACCESS  accessible-for-notify
    STATUS      current
    DESCRIPTION
        "Peer Port Number"
    ::= { starentTrapData 127 }

starBfdSrcAddressType OBJECT-TYPE
    SYNTAX      InetAddressType
    MAX-ACCESS  accessible-for-notify
    STATUS      current
    DESCRIPTION
        "This object specifies IP address type of the source IP
         address of this BFD session. Only values unknown(0),
         ipv4(1), ipv6(2), or ipv6z(4) have to be supported.
         The value of unknown(0) is allowed only when the session
         is singleHop(1) and the source IP address of this BFD
         session is derived from the outgoing interface, or when
         the BFD session is not associated with a specific
         interface."
    ::= { starentTrapData 128 }

starBfdSrcAddress OBJECT-TYPE
    SYNTAX      InetAddress
    MAX-ACCESS  accessible-for-notify
    STATUS      current
    DESCRIPTION
        "This object specifies the source IP address of this BFD
         session."
    ::= { starentTrapData 129 }

starBfdDstAddressType OBJECT-TYPE
    SYNTAX      InetAddressType
    MAX-ACCESS  accessible-for-notify
    STATUS      current
    DESCRIPTION
        "This object specifies IP address type of the neighboring IP
         address which is being monitored with this BFD session.
         Only values unknown(0), ipv4(1), ipv6(2), or ipv6z(4)
         have to be supported. The value of unknown(0) is allowed
         only when the session is singleHop(1) and the outgoing
         interface is of type point-to-point, or when the BFD
         session is not associated with a specific interface."
    ::= { starentTrapData 130 }

starBfdDstAddress OBJECT-TYPE
    SYNTAX      InetAddress
    MAX-ACCESS  accessible-for-notify
    STATUS      current
    DESCRIPTION
        "This object specifies the neighboring IP address which is
         being monitored with this BFD session."
    ::= { starentTrapData 131 }

starBfdLocalDisc OBJECT-TYPE
    SYNTAX     Unsigned32
    MAX-ACCESS accessible-for-notify
    STATUS     current
    DESCRIPTION
        "This object specifies the local discriminator for this BFD
         session, used to uniquely identify it"
       ::= { starentTrapData 132 }

starBfdRemDisc OBJECT-TYPE
    SYNTAX     Unsigned32
    MAX-ACCESS accessible-for-notify
    STATUS     current
    DESCRIPTION
       "This object specifies the session discriminator chosen
        by the remote system for this BFD session.  The value may
        be zero(0) if the remote discriminator is not yet known
        or if the session is in the down or adminDown(1) state."
       ::= { starentTrapData 133 }       

starBfdSessDiagCode OBJECT-TYPE
    SYNTAX      INTEGER {
      noDiagnostic(0),
      controlDetectionTimeExpired(1),
      echoFunctionFailed(2),
      neighborSignaledSessionDown(3),
      forwardingPlaneReset(4),
      pathDown(5),
      concatenatedPathDown(6),
      administrativelyDown(7),
      reverseConcatenatedPathDown(8),
      misConnectivityDefect(9)
    }      
    MAX-ACCESS  accessible-for-notify
    STATUS      current
    DESCRIPTION
        "A diagnostic code specifying the local system's reason
         for the last transition of the session from up(4)
         to some other state."
    ::= { starentTrapData 134 }

starSRPSwitchReason OBJECT-TYPE
    SYNTAX      INTEGER {
      notDefined(0),
      aaaFailure(1),
      bgpFailure(2),
      bfdFailure(3),
      diameterFailure(4),
      hsrpSwitchover(5),
      chassisChassisBfdFailure(6),
      dualActive(7),
      dualStandby(8),
      deadTimerExpiry(9),
      forceStateChange(10),
      manualSwitchOver(11),
      egqcFailure(12)
    }      
    MAX-ACCESS  accessible-for-notify
    STATUS      current
    DESCRIPTION
        "A Switchover code specifying the SRP's Switchover reason.
         The following reasons would appear when chassis transitioning
         from Active to Standby State:
               notDefined(0),
               aaaFailure(1),
               bgpFailure(2),
               bfdFailure(3),
               diameterFailure(4),
               hsrpSwitchover(5),
               dualActive(7)
               manualSwitchOver(11),
               egqcFailure(12),
         The following reasons would appear when chassis transitioning
         from Standby to Pending Active State:
               notDefined(0),
               chassisChassisBfdFailure(6),
               deadTimerExpiry(9)
        "
    ::= { starentTrapData 135 }

starHENBGWServiceTLRI OBJECT-TYPE
    SYNTAX      Unsigned32 
    MAX-ACCESS  accessible-for-notify
    STATUS      current
    DESCRIPTION
        "HENBGW Service Overload Traffic load reduction indication percentage."
    ::= { starentTrapData 136 }

-- CBS START

starCBSServiceVpnName OBJECT-TYPE
    SYNTAX      DisplayString
    MAX-ACCESS  accessible-for-notify
    STATUS      current
    DESCRIPTION
       "CBS service context name"
    ::= { starentTrapData 139 }


starIuBcSelfPortNum OBJECT-TYPE
    SYNTAX      Integer32(1..65535)
    MAX-ACCESS  accessible-for-notify
    STATUS      current
    DESCRIPTION
        "IuBc Self Port Number"
    ::= { starentTrapData 140 }


starIuBcSelfIpAddr OBJECT-TYPE
    SYNTAX      IpAddress
    MAX-ACCESS  accessible-for-notify
    STATUS      current
    DESCRIPTION
        "IuBc Self IP Address"
    ::= { starentTrapData 141 }


starIuBcPeerPortNum OBJECT-TYPE
    SYNTAX      Integer32(1..65535)
    MAX-ACCESS  accessible-for-notify
    STATUS      current
    DESCRIPTION
        "Peer Port Number"
    ::= { starentTrapData 142 }


starIuBcPeerIpAddr OBJECT-TYPE
    SYNTAX      IpAddress
    MAX-ACCESS  accessible-for-notify
    STATUS      current
    DESCRIPTION
        "IuBc Peer IP Address"
    ::= { starentTrapData 143 }


starIuBcTcpConnCauseStr OBJECT-TYPE
    SYNTAX      DisplayString
    MAX-ACCESS  accessible-for-notify
    STATUS      current
    DESCRIPTION
        "IuBc Tcp Conn Cause Str"
    ::= { starentTrapData 144 }

starPhyPortId OBJECT-TYPE
    SYNTAX      Integer32
    MAX-ACCESS  accessible-for-notify
    STATUS      current
    DESCRIPTION
        "Physical Port Id as IfIndex"
    ::= { starentTrapData 145 }

starGTPCRLFSessMgrInst OBJECT-TYPE
    SYNTAX      Integer32
    MAX-ACCESS  accessible-for-notify
    STATUS      current
    DESCRIPTION
    "Session Manager Instance"
    ::= { starentTrapData 146 }

starGTPCRLFVPNName OBJECT-TYPE
    SYNTAX      DisplayString
    MAX-ACCESS  accessible-for-notify
    STATUS      current
    DESCRIPTION
    "The context name of VPN is "
    ::= { starentTrapData 147 }

starGTPCRLFVPNId OBJECT-TYPE
    SYNTAX      Integer32
    MAX-ACCESS  accessible-for-notify
    STATUS      current
    DESCRIPTION
    "The context Id of VPN is "
    ::= { starentTrapData 148 }

starGTPCRLFContextName OBJECT-TYPE
    SYNTAX      DisplayString
    MAX-ACCESS  accessible-for-notify
    STATUS      current
    DESCRIPTION
    "The name of Context is "
    ::= { starentTrapData 149 }

starGTPCRLFCurrAppTPS OBJECT-TYPE
    SYNTAX      Integer32
    MAX-ACCESS  accessible-for-notify
    STATUS      current
    DESCRIPTION
    "The current applied TPS value is "
    ::= { starentTrapData 150 }

starGTPCRLFCurrAppDelayTol OBJECT-TYPE
    SYNTAX      Integer32
    MAX-ACCESS  accessible-for-notify
    STATUS      current
    DESCRIPTION
    "The current applied delay Tolerance value is "
    ::= { starentTrapData 151 }

starBGPPeerIpv6Address OBJECT-TYPE
    SYNTAX      Ipv6Address
    MAX-ACCESS  accessible-for-notify
    STATUS      current
    DESCRIPTION 
        "Diameter Peer Address in IPv6"
    ::= { starentTrapData 152 }


-- CBS END    
-- MME-EMBMS START
starMMEEMBMSServiceVpnName OBJECT-TYPE
    SYNTAX      DisplayString
    MAX-ACCESS  accessible-for-notify
    STATUS      current
    DESCRIPTION
       "MME-EMBMS service context name"
    ::= { starentTrapData 153 }

starMMEEMBMSServiceServName OBJECT-TYPE
    SYNTAX      DisplayString
    MAX-ACCESS  accessible-for-notify
    STATUS      current
    DESCRIPTION
       "MME-EMBMS service name"
    ::= { starentTrapData 154 }

starMMEEMBMSPeerId OBJECT-TYPE
    SYNTAX      Integer32(0..255)
    MAX-ACCESS  accessible-for-notify
    STATUS      current
    DESCRIPTION
       "Peer Id"
    ::= { starentTrapData 155 }

starMMEEMBMSPeerIpAddr OBJECT-TYPE
    SYNTAX      IpAddress
    MAX-ACCESS  accessible-for-notify
    STATUS      current
    DESCRIPTION
        "Peer IP Address"
    ::= { starentTrapData 156 }

starMMEEMBMSPeerPortNum OBJECT-TYPE
    SYNTAX      Integer32(1..65535)
    MAX-ACCESS  accessible-for-notify
    STATUS      current
    DESCRIPTION
        "Peer Port Number"
    ::= { starentTrapData 157 }

starImsimgrInstId OBJECT-TYPE
    SYNTAX      Integer32
    MAX-ACCESS  accessible-for-notify
    STATUS      current
    DESCRIPTION
        "IMSI Manager Instance"
    ::= { starentTrapData 158 }

starLAGGroup OBJECT-TYPE
    SYNTAX      Integer32(1..29)
    MAX-ACCESS  accessible-for-notify
    STATUS      current
    DESCRIPTION
        "The group number of the LAG group"
    ::= { starentTrapData 159 }

starLAGMinlink OBJECT-TYPE
    SYNTAX      Integer32(1..29)
    MAX-ACCESS  accessible-for-notify
    STATUS      current
    DESCRIPTION
        "The Minlink configured for this lag_group"
    ::= { starentTrapData 160 }

starVRFName OBJECT-TYPE
    SYNTAX      DisplayString
    MAX-ACCESS  accessible-for-notify
    STATUS      current
    DESCRIPTION
       "VRF Name"
    ::= { starentTrapData 161 }

starStatFilesizeLimit OBJECT-TYPE
    SYNTAX      Integer32(1..29)
    MAX-ACCESS  accessible-for-notify
    STATUS      current
    DESCRIPTION
        "The Stat File Size in integer"
    ::= { starentTrapData 162 }

starStatFilesizeMeasured OBJECT-TYPE
    SYNTAX      Integer32(1..29)
    MAX-ACCESS  accessible-for-notify
    STATUS      current
    DESCRIPTION
        "The Stat file Size measured"
    ::= { starentTrapData 163 }

starTetheringDatabasePreDBVersion OBJECT-TYPE
    SYNTAX      DisplayString
    MAX-ACCESS  accessible-for-notify
    STATUS      current
    DESCRIPTION
       "Tethering Database Pre-DB Version"
    ::= { starentTrapData 164 }

starTetheringDatabaseUpgradeDBVersion OBJECT-TYPE
    SYNTAX      DisplayString
    MAX-ACCESS  accessible-for-notify
    STATUS      current
    DESCRIPTION
       "Tethering Database Upgrade DB Version"
    ::= { starentTrapData 165 }

starTetheringDatabaseUpgradeComment OBJECT-TYPE
    SYNTAX      DisplayString
    MAX-ACCESS  accessible-for-notify
    STATUS      current
    DESCRIPTION
       "Tethering Database Upgrade Comment String"
    ::= { starentTrapData 166 }

starDiscReasons OBJECT-TYPE
    SYNTAX     OCTET STRING (SIZE (1..512))
    MAX-ACCESS accessible-for-notify
    STATUS     current
    DESCRIPTION
        "Disconnect Reasons"
    ::= { starentTrapData 167 }

starDdfDev OBJECT-TYPE
    SYNTAX      INTEGER {
                    ddf0(0),
                    ddf1(1)
                }
    MAX-ACCESS  read-only
    STATUS      current
    DESCRIPTION
      "Identifies DDF Engine number that was reloaded"
    ::= { starentTrapData 168 }

starHdRaidMgmtCardSwitchoverCause OBJECT-TYPE
    SYNTAX      INTEGER {
                    unknown(0),
                    stuck(1)
                }
    MAX-ACCESS  read-only
    STATUS      current
    DESCRIPTION
       "Management Card Switchover due to HD Raid irrecoverable error cause"
    ::= { starentTrapData 169 }

starDiameterPeerName OBJECT-TYPE
    SYNTAX      DisplayString
    MAX-ACCESS  accessible-for-notify
    STATUS      current
    DESCRIPTION
    "Diameter Peer Name"
    ::= { starentTrapData 170}

starDiameterRlfContext OBJECT-TYPE
    SYNTAX      DisplayString
    MAX-ACCESS  accessible-for-notify
    STATUS      current
    DESCRIPTION
    "RLF Context Name"
    ::= { starentTrapData 171}

    
starDiameterRlfECode OBJECT-TYPE
    SYNTAX      INTEGER {
    	 thresholdgood(0),
		   thresholdover(1),
       overlimiterror(2)
		}
    MAX-ACCESS  accessible-for-notify
    STATUS      current
    DESCRIPTION
	"Diameter Rlf Status Code"
    ::= { starentTrapData 172 }

starDiameterRlfTps OBJECT-TYPE
    SYNTAX      Integer32
    MAX-ACCESS  accessible-for-notify
    STATUS      current
    DESCRIPTION
       "Diameter RLF Configured TPS"
    ::= { starentTrapData 173 }

starDiameterRlfDelayTolerance OBJECT-TYPE
    SYNTAX      Integer32
    MAX-ACCESS  accessible-for-notify
    STATUS      current
    DESCRIPTION
       "Diameter RLF Configured Delay Tolerance"
    ::= { starentTrapData 174 }

starDiameterRlfQueuePercent OBJECT-TYPE
    SYNTAX      Integer32(0..100)
    MAX-ACCESS  accessible-for-notify
    STATUS      current
    DESCRIPTION
       "Diameter RLF Current Queue Percentage"
    ::= { starentTrapData 175 }

starDiameterDiamproxyInstance OBJECT-TYPE
    SYNTAX      Integer32(1..144)
    MAX-ACCESS  accessible-for-notify
    STATUS      current
    DESCRIPTION
      "Diameter Proxy Instance Number"
    ::= { starentTrapData 176 }

starSmartLicenseServiceUsage OBJECT-TYPE
    SYNTAX     Unsigned32
    MAX-ACCESS accessible-for-notify
    STATUS     current
    DESCRIPTION
        "Smart License Service usage count"
    ::= { starentTrapData 177 }

starSmartLicenseServiceName OBJECT-TYPE
    SYNTAX     DisplayString
    MAX-ACCESS accessible-for-notify
    STATUS     current
    DESCRIPTION
        "Smart License Service name"
    ::= { starentTrapData 178 }

starSmartLicenseEvalModeRemaining OBJECT-TYPE
    SYNTAX     Unsigned32
    MAX-ACCESS accessible-for-notify
    STATUS     current
    DESCRIPTION
        "Renaming number of days the device can be used in Evaluation Mode"
    ::= { starentTrapData 179 }

starRuleBaseName OBJECT-TYPE 
    SYNTAX      DisplayString
    MAX-ACCESS  accessible-for-notify
    STATUS      current
    DESCRIPTION
       "Rulebase Name"
    ::= { starentTrapData 180 }

starRuleDefName OBJECT-TYPE 
    SYNTAX      DisplayString
    MAX-ACCESS  accessible-for-notify
    STATUS      current
    DESCRIPTION
       "Ruledef/GroupOfRuledef Name"
    ::= { starentTrapData 181 }

starGroupOfRuledef OBJECT-TYPE
    SYNTAX     INTEGER {
		  Ruledef(0),
		  GroupOfRuledef(1)
		}
    MAX-ACCESS accessible-for-notify
    STATUS     current
    DESCRIPTION
       "GroupOfRuledef flag"
    ::= { starentTrapData 182 }

starIKEv2DDoSUDPFailClearStr OBJECT-TYPE
    SYNTAX     Unsigned32
    MAX-ACCESS accessible-for-notify
    STATUS     current
    DESCRIPTION
        "CLear string for IKEv2 DDoS UDP Fail clear alarm"
    ::= { starentTrapData 183 }

starMacaddress OBJECT-TYPE
    SYNTAX      DisplayString
    MAX-ACCESS  accessible-for-notify
    STATUS      current
    DESCRIPTION
        "Mac Address for NicBondChange trap"
    ::= { starentTrapData 184 }

starP2PPluginVersion OBJECT-TYPE
    SYNTAX     DisplayString
    MAX-ACCESS accessible-for-notify
    STATUS     current
    DESCRIPTION
        "P2P Plugin Version for ADC license"
    ::= { starentTrapData 185 }

starADCLicenseExpiryDate OBJECT-TYPE
    SYNTAX     DateAndTime
    MAX-ACCESS accessible-for-notify
    STATUS     current
    DESCRIPTION
        "The license expiration date/time"
    ::= { starentTrapData 186 }

starSxInterfaceType OBJECT-TYPE
    SYNTAX      INTEGER {
		  invalid(0),
		  sxa(1),
		  sxb(2),
		  sxab(3)
    }
    MAX-ACCESS  accessible-for-notify
    STATUS      current
    DESCRIPTION
        "Sx interface type"
    ::= { starentTrapData 187 }

starSxSelfAddr OBJECT-TYPE
    SYNTAX     IpAddress
    MAX-ACCESS accessible-for-notify
    STATUS     current
    DESCRIPTION
        "The IP Address of the Sx Service"
    ::= { starentTrapData 188 }

starSxPeerAddr OBJECT-TYPE
    SYNTAX     IpAddress
    MAX-ACCESS accessible-for-notify
    STATUS     current
    DESCRIPTION
        "The IP Address of the Sx Peer Node"
    ::= { starentTrapData  189 }

starSxPeerNewRecTimeStamp OBJECT-TYPE
    SYNTAX     DateAndTime
    MAX-ACCESS accessible-for-notify
    STATUS     current
    DESCRIPTION
        "The New Recovery timestamp of the Peer"
    ::= { starentTrapData 190 }

starSxPeerOldRecTimeStamp OBJECT-TYPE
    SYNTAX     DateAndTime
    MAX-ACCESS accessible-for-notify
    STATUS     current
    DESCRIPTION
        "The Old Recovery timestamp of the Peer"
    ::= { starentTrapData 191 }

starSxFailureCause OBJECT-TYPE
    SYNTAX      INTEGER {
		  unknown(0),
		  no-response-from-peer(1),
		  recovery-timestamp-change-in-heartbeat-req-msg(2),
		  recovery-timestamp-change-in-heartbeat-rsp-msg(3),
		  recovery-timestamp-change-in-control-msg(4),
      heartbeat-rsp-received(5),
      heartbeat-req-received(6),
      sx-association-established(7),
      bfd-failure(8)
    }
    MAX-ACCESS  accessible-for-notify
    STATUS      current
    DESCRIPTION
        "Sx Path failure cause"
     ::= { starentTrapData 192 }   

starChassisThroughputLimit OBJECT-TYPE
    SYNTAX 	Gauge32
    MAX-ACCESS  accessible-for-notify
    STATUS      current
    DESCRIPTION
	"The committed chassis throughput"
    ::= { starentTrapData 193 }

starChassisThroughputMeasured OBJECT-TYPE
    SYNTAX 	Gauge32
    MAX-ACCESS  accessible-for-notify
    STATUS      current
    DESCRIPTION
	"The served chassis throughput"
    ::= { starentTrapData 194 }

starSmartLicenseFeatureUsage OBJECT-TYPE
    SYNTAX     Unsigned32
    MAX-ACCESS accessible-for-notify
    STATUS     current
    DESCRIPTION
        "Smart License Feature usage count"
    ::= { starentTrapData 195 }

starSmartLicenseFeatureName OBJECT-TYPE
    SYNTAX     DisplayString
    MAX-ACCESS accessible-for-notify
    STATUS     current
    DESCRIPTION
        "Smart License Feature name"
    ::= { starentTrapData 196 }


starCommonDatabasePreDBVersion OBJECT-TYPE
    SYNTAX      DisplayString
    MAX-ACCESS  accessible-for-notify
    STATUS      current
    DESCRIPTION
       "Common Database Pre-DB Version"
    ::= { starentTrapData 197 }

starCommonDatabaseUpgradeDBVersion OBJECT-TYPE
    SYNTAX      DisplayString
    MAX-ACCESS  accessible-for-notify
    STATUS      current
    DESCRIPTION
       "Common Database Upgrade DB Version"
    ::= { starentTrapData 198 }

starCommonDatabaseUpgradeComment OBJECT-TYPE
    SYNTAX      DisplayString
    MAX-ACCESS  accessible-for-notify
    STATUS      current
    DESCRIPTION
       "Common Database Upgrade Comment String"
    ::= { starentTrapData 199 }

starSxCPUPGroupName OBJECT-TYPE
    SYNTAX      OCTET STRING (SIZE (1..32))
    MAX-ACCESS  accessible-for-notify
    STATUS      current
    DESCRIPTION
        "The name of the CP or UP group"
     ::= { starentTrapData 200 }

-- MME-EMBMS END

-- L2TP objects, used for traps only

starentL2TP OBJECT IDENTIFIER ::= { starentMIBObjects 33 }

starL2TPTable OBJECT-TYPE
    SYNTAX     SEQUENCE OF StarL2TPEntry
    MAX-ACCESS not-accessible
    STATUS     current
    DESCRIPTION
        "A table containing L2TP related information"
    ::= { starentL2TP 1 }

starL2TPEntry OBJECT-TYPE
    SYNTAX     StarL2TPEntry
    MAX-ACCESS not-accessible
    STATUS     current
    DESCRIPTION
        "The statistics for a L2TP entry"
    INDEX { starL2TPLocalTunnelID, starL2TPPeerTunnelID }
    ::= { starL2TPTable 1 }

StarL2TPEntry ::=
    SEQUENCE {
	starL2TPLocalTunnelID        Unsigned32,
	starL2TPPeerTunnelID         Unsigned32,
        starL2TPContextName          DisplayString,
	starL2TPServiceName          DisplayString,
	starL2TPServiceTypeName      DisplayString,
	starL2TPLocalAddress         IpAddress,
	starL2TPPeerAddress          IpAddress
             }


starL2TPLocalTunnelID OBJECT-TYPE
    SYNTAX     Unsigned32
    MAX-ACCESS accessible-for-notify
    STATUS     current
    DESCRIPTION
        "The internal identification of the L2TP local tunnel ID"
    ::= { starL2TPEntry 1 }

starL2TPPeerTunnelID OBJECT-TYPE
    SYNTAX     Unsigned32
    MAX-ACCESS accessible-for-notify
    STATUS     current
    DESCRIPTION
        "The internal identification of the L2TP peer tunnel ID"
    ::= { starL2TPEntry 2 }

starL2TPContextName OBJECT-TYPE
    SYNTAX     DisplayString
    MAX-ACCESS accessible-for-notify
    STATUS     current
    DESCRIPTION
        "The name of the context"
    ::= { starL2TPEntry 3 }

starL2TPServiceName OBJECT-TYPE
    SYNTAX     DisplayString
    MAX-ACCESS accessible-for-notify
    STATUS     current
    DESCRIPTION
        "The name of the service"
    ::= { starL2TPEntry 4 }

starL2TPServiceTypeName OBJECT-TYPE
    SYNTAX     DisplayString
    MAX-ACCESS accessible-for-notify
    STATUS     current
    DESCRIPTION
        "The name of the service type"
    ::= { starL2TPEntry 5 }

starL2TPLocalAddress OBJECT-TYPE
    SYNTAX     IpAddress
    MAX-ACCESS accessible-for-notify
    STATUS     current
    DESCRIPTION
        "The local address of the service"
    ::= { starL2TPEntry 6 }

starL2TPPeerAddress OBJECT-TYPE
    SYNTAX     IpAddress
    MAX-ACCESS accessible-for-notify
    STATUS     current
    DESCRIPTION
        "The peer address of the service"
    ::= { starL2TPEntry 7 }

-- GGSN; these objects are provided for use in SNMP Traps only

starentGGSNService OBJECT IDENTIFIER ::= { starentMIBObjects 32 }

starGGSNSerTable OBJECT-TYPE
    SYNTAX     SEQUENCE OF StarGGSNSerEntry
    MAX-ACCESS not-accessible
    STATUS     current
    DESCRIPTION
        "A table containing GGSN related information"
    ::= { starentGGSNService 1 }

starGGSNSerEntry OBJECT-TYPE
    SYNTAX     StarGGSNSerEntry
    MAX-ACCESS not-accessible
    STATUS     current
    DESCRIPTION
        "The statistics for a specific GGSN service"
    INDEX { starGGSNSerVpnID, starGGSNSerSvcID }
    ::= { starGGSNSerTable 1 }

StarGGSNSerEntry ::=
    SEQUENCE {
        starGGSNSerVpnID             Gauge32,
        starGGSNSerSvcID             Gauge32,
        starSessGGSNVpnName          DisplayString,
        starSessGGSNServName         DisplayString,
        starSessGGSNPeerPort         Gauge32,
        starSessGGSNPeerAddr         IpAddress,
        starSessGGSNImsi             OCTET STRING,
        starSessGGSNSubsName         OCTET STRING,
        starSessGGSNAPNName          OCTET STRING,
	starSessGTPPGroupName        OCTET STRING
             }


starGGSNSerVpnID OBJECT-TYPE
    SYNTAX     Gauge32
    MAX-ACCESS not-accessible
    STATUS     current
    DESCRIPTION
        "The internal identification of the VPN (context)"
    ::= { starGGSNSerEntry 1 }

starGGSNSerSvcID OBJECT-TYPE
    SYNTAX     Gauge32
    MAX-ACCESS not-accessible
    STATUS     current
    DESCRIPTION
        "The internal identification of this service; unique within a specific context"
    ::= { starGGSNSerEntry 2 }

starSessGGSNVpnName OBJECT-TYPE
    SYNTAX     DisplayString
    MAX-ACCESS read-only
    STATUS     current
    DESCRIPTION
        "The name of this VPN (context)"
    ::= { starGGSNSerEntry 3 }

starSessGGSNServName OBJECT-TYPE
    SYNTAX     DisplayString
    MAX-ACCESS read-only
    STATUS     current
    DESCRIPTION
        "The name of this service"
    ::= { starGGSNSerEntry 4 }

starSessGGSNPeerPort OBJECT-TYPE
    SYNTAX     Gauge32
    MAX-ACCESS accessible-for-notify
    STATUS     current
    DESCRIPTION
        "The Peer Port for which PATH Failure has occured"
    ::= { starGGSNSerEntry 5 }

starSessGGSNPeerAddr  OBJECT-TYPE
    SYNTAX     IpAddress
    MAX-ACCESS read-only
    STATUS     current
    DESCRIPTION
        "The Peer Address for which PATH Failure has occured"
    ::= { starGGSNSerEntry 6 }

starSessGGSNImsi OBJECT-TYPE
    SYNTAX     OCTET STRING (SIZE (1..8))
    MAX-ACCESS accessible-for-notify
    STATUS     current
    DESCRIPTION
        "The IMSI of the subscriber"
    ::= { starGGSNSerEntry 7 }

starSessGGSNSubsName OBJECT-TYPE
    SYNTAX     OCTET STRING (SIZE (1..128))
    MAX-ACCESS accessible-for-notify
    STATUS     current
    DESCRIPTION
        "The name of the subscriber"
    ::= { starGGSNSerEntry 8 }

starSessGGSNAPNName OBJECT-TYPE
    SYNTAX     OCTET STRING (SIZE (1..64))
    MAX-ACCESS accessible-for-notify
    STATUS     current
    DESCRIPTION
        "The name of the APN"
    ::= { starGGSNSerEntry 9 }


starSessGTPPGroupName OBJECT-TYPE
    SYNTAX     OCTET STRING (SIZE (1..64))
    MAX-ACCESS accessible-for-notify
    STATUS     current
    DESCRIPTION
        "The name of the GTPP Group"
    ::= { starGGSNSerEntry 10 }



-- single subscriber info

-- This is used to perform a lookup on information on a single subscriber.  This is done in a
-- two-step process
--
-- 1. Use a SET pdu to provide the keys to lookup.  Set one or more of the fields
--    starSessSub1Context, starSessSub1NAI, starSessSub1MSID, starSessSub1IpAddr
--
--    The SET pdu returns once the query is complete.  This query can takes some time
--    especially on large systems, so do not use small retry timers.
--
-- 2. Use a GET pdu to retrieve the data.
--
-- Note that in some cases, multiple subscribers might match the given search criteria.
-- The starSessSub1LastResult field identifies if zero, one or multiple matches were found.
-- If multiple matches are found, data is returned for one of them.

starSessSub1 OBJECT IDENTIFIER ::= { starentMIBObjects 34 }

starSessSub1Context OBJECT-TYPE
    SYNTAX     DisplayString
    MAX-ACCESS read-write
    STATUS     current
    DESCRIPTION
        "The name of the context for this subscriber.

	 If a SET is received, triggers a lookup for a subscriber that matches the
	 specified search criteria and fills in the various objects in this row."
    ::= { starSessSub1 1 }

starSessSub1NAI OBJECT-TYPE
    SYNTAX     OCTET STRING (SIZE (1..128))
    MAX-ACCESS read-write
    STATUS     current
    DESCRIPTION
        "The NAI for this subscriber

	 If a SET is received, triggers a lookup for a subscriber that matches the
	 specified search criteria and fills in the various objects in this row."
    ::= { starSessSub1 2 }

starSessSub1MSID OBJECT-TYPE
    SYNTAX     OCTET STRING (SIZE (1..16))
    MAX-ACCESS read-write
    STATUS     current
    DESCRIPTION
        "The MSID for this subscriber

	 If a SET is received, triggers a lookup for a subscriber that matches the
	 specified search criteria and fills in the various objects in this row."
    ::= { starSessSub1 3 }

starSessSub1IpAddr OBJECT-TYPE
    SYNTAX     IpAddress
    MAX-ACCESS read-write
    STATUS     current
    DESCRIPTION
        "The remote IP address for this subscriber

	 If a SET is received, triggers a lookup for a subscriber that matches the
	 specified search criteria and fills in the various objects in this row."
    ::= { starSessSub1 4 }

starSessSub1LastResult OBJECT-TYPE
    SYNTAX     INTEGER {
		  unknown(0),
		  error(1),
		  nomatch(2),
		  onematch(3),
		  multimatch(4)
		}
    MAX-ACCESS read-only
    STATUS     current
    DESCRIPTION
	"The result of the last search.  A value of unknown(0) means that the query
	 wasn't created properly, or that no query has been performed; error(1)
	 indicates an internal error performing the query, this is an abnormal
	 condition that shouldn't normally be seen; nomatch(2) means that the
	 query did not find a matching subscriber; onematch(3) means that the
	 query found exactly one subscriber; multimatch(4) means that more than
	 one subscriber matched; the information for one (random) subscriber
	 was fetched"
    ::= { starSessSub1 5 }

starSessSub1ServiceName OBJECT-TYPE
    SYNTAX     OCTET STRING (SIZE (1..63))
    MAX-ACCESS read-only
    STATUS     current
    DESCRIPTION
        "The service name of the subscriber."
    ::= { starSessSub1 6 }

starSessSub1HAIpAddr OBJECT-TYPE
    SYNTAX     IpAddress
    MAX-ACCESS read-only
    STATUS     current
    DESCRIPTION
        "The HA IP address for FA MIP connections"
    ::= { starSessSub1 7 }

starSessSub1PeerIpAddr OBJECT-TYPE
    SYNTAX     IpAddress
    MAX-ACCESS read-only
    STATUS     current
    DESCRIPTION
        "The remote IP address of the peer.  The type of peer depends
	 on the session type.

	 Session Type           Peer
	 ------------		---------
	 PDSN			PCF
	 GGSN			SGSN
	 HA Mobile IP/HA IPSEC	FA
	 LAC			LNS
	 LNS			LAC"
    ::= { starSessSub1 8 }

starSessSub1InPackets OBJECT-TYPE
    SYNTAX     Counter32
    MAX-ACCESS read-only
    STATUS     current
    DESCRIPTION
        "The number of incoming packets for the subscriber"
    ::= { starSessSub1 9 }

starSessSub1InPacketsDropped OBJECT-TYPE
    SYNTAX     Counter32
    MAX-ACCESS read-only
    STATUS     current
    DESCRIPTION
        "The number of incoming packets dropped for the subscriber"
    ::= { starSessSub1 10 }

starSessSub1InBytes OBJECT-TYPE
    SYNTAX     Counter32
    UNITS      "KB"
    MAX-ACCESS read-only
    STATUS     current
    DESCRIPTION
        "The count of incoming bytes for the subscriber, in kilobytes,
	 rounded down (i.e. 1023 bytes = 0 kilobytes"
    ::= { starSessSub1 11 }

starSessSub1OutPackets OBJECT-TYPE
    SYNTAX     Counter32
    MAX-ACCESS read-only
    STATUS     current
    DESCRIPTION
        "The number of outgoing packets for the subscriber"
    ::= { starSessSub1 12 }

starSessSub1OutPacketsDropped OBJECT-TYPE
    SYNTAX     Counter32
    MAX-ACCESS read-only
    STATUS     current
    DESCRIPTION
        "The number of out going packets dropped for the subscriber"
    ::= { starSessSub1 13 }

starSessSub1OutBytes OBJECT-TYPE
    SYNTAX     Counter32
    UNITS      "KB"
    MAX-ACCESS read-only
    STATUS     current
    DESCRIPTION
        "The count of outgoing bytes for the subscriber, in kilobytes,
	 rounded down (i.e. 1023 bytes = 0 kilobytes"
    ::= { starSessSub1 14 }

starSessSub1Activity OBJECT-TYPE
    SYNTAX     Gauge32
    UNITS      "%"
    MAX-ACCESS read-only
    STATUS     current
    DESCRIPTION
        "TBD"
    ::= { starSessSub1 15 }

starSessSub1State OBJECT-TYPE
    SYNTAX     INTEGER {
		unknown(0),
		connecting(1),
		connected(2),
		disconnecting(3)
		}
    MAX-ACCESS read-only
    STATUS     current
    DESCRIPTION
        "The state of the subscriber"
    ::= { starSessSub1 16 }

starSessSub1CallID OBJECT-TYPE
    SYNTAX     Integer32
    MAX-ACCESS read-only
    STATUS     current
    DESCRIPTION
        "The internal call ID of the subscriber"
    ::= { starSessSub1 17 }

starSessSub1ConnectTime OBJECT-TYPE
    SYNTAX     DateAndTime
    MAX-ACCESS read-only
    STATUS     current
    DESCRIPTION
        "The connect time for the subscriber, in UTC.  The UNIX epoch (Jan 1, 1970) is used if no
	 value is available"
    ::= { starSessSub1 18 }

starSessSub1CallDuration OBJECT-TYPE
    SYNTAX     Counter32
    UNITS      "Seconds"
    MAX-ACCESS read-only
    STATUS     current
    DESCRIPTION
        "The duration of the call, in seconds"
    ::= { starSessSub1 19 }

starSessSub1TimeIdle OBJECT-TYPE
    SYNTAX     Gauge32
    UNITS      "Seconds"
    MAX-ACCESS read-only
    STATUS     current
    DESCRIPTION
        "The idle time of the call, in seconds"
    ::= { starSessSub1 20 }

starSessSub1AccessType OBJECT-TYPE
    SYNTAX     INTEGER {
		unknown(0),
		pdsnsimpleip(1),
		pdsnmobileip(2),
		hamobileip(3),
		ggsnpdptypeipv4(4),
		ggsnpdptypeppp(5),
		ggsnpdptypeipv6(6),
		lnsl2tp(7),
		haipsec(8),
		ipsg(9),
		pdsnsipmip(10),
		mipproxyfa(11),
		imsa(12),
		bcmcs(13),
		ggsnmip(14),
		ipprobe(15),
		ansgw(16)
	       }
    MAX-ACCESS read-only
    STATUS     current
    DESCRIPTION
        "The access type for the subscriber"
    ::= { starSessSub1 21 }

starSessSub1AccessTech OBJECT-TYPE
    SYNTAX     INTEGER {
		unknown(0),
		cdma1xrtt(1),
		cdmaevdo(2),
		cdmaother(3),
		wcdmautran(4),
		gprsgeran(5),
		gprsother(6),
		wirelesslan(7),
		ipsg(8),
		wimax(9),
		sip(10),
		other(11),
		cdmaevdoreva(12),
                pdif(13),
                phs(14),
                ehrpd(15),
                eutran(16),
                gan(17),
                hspa(18)
	       }
    MAX-ACCESS read-only
    STATUS     current
    DESCRIPTION
        "The access technology for the subscriber"
    ::= { starSessSub1 22 }

starSessSub1LinkStatus OBJECT-TYPE
    SYNTAX     INTEGER {
		unknown(0),
		active(1),
		dormant(2)
	       }
    MAX-ACCESS read-only
    STATUS     current
    DESCRIPTION
        "The link status for the subscriber"
    ::= { starSessSub1 23 }

starSessSub1NetworkType OBJECT-TYPE
    SYNTAX     INTEGER {
		unknown(0),
		ip(1),
		mobileip(2),
		l2tp(3),
		proxymobileip(4),
		ipinip(5),
		gre(6),
		ipv6inipv4(7)
	       }
    MAX-ACCESS read-only
    STATUS     current
    DESCRIPTION
        "The network type for the subscriber"
    ::= { starSessSub1 24 }

starSessSub1CarrierID OBJECT-TYPE
    SYNTAX     OCTET STRING (SIZE (0..6))
    MAX-ACCESS read-only
    STATUS     current
    DESCRIPTION
	"Carrier ID"
    ::= { starSessSub1 25 }

starSessSub1ESN OBJECT-TYPE
    SYNTAX     OCTET STRING (SIZE (0..15))
    MAX-ACCESS read-only
    STATUS     current
    DESCRIPTION
	"Electronic Serial Number"
    ::= { starSessSub1 26 }

starSessSub1GMTTimezoneOffset OBJECT-TYPE
    SYNTAX     Integer32
    UNITS      "Seconds"
    MAX-ACCESS read-only
    STATUS     current
    DESCRIPTION
	"Timezone offset from GMT, in seconds.  This is a signed value"
    ::= { starSessSub1 27 }

starSessSub1SessMgr OBJECT-TYPE
    SYNTAX     Unsigned32
    MAX-ACCESS read-only
    STATUS     current
    DESCRIPTION
	"The instance number of the session manager for this subscriber."
    ::= { starSessSub1 28 }

starSessSub1RemoteIPAddr OBJECT-TYPE
    SYNTAX     IpAddress
    MAX-ACCESS read-only
    STATUS     current
    DESCRIPTION
	"Remote IP Address"
    ::= { starSessSub1 29 }

starSessSub1Card OBJECT-TYPE
    SYNTAX     Integer32(1..16)
    MAX-ACCESS read-only
    STATUS     current
    DESCRIPTION
	"The card holding the session manager for this session.  Use in combination
	 with starSessSub1CPU"
    ::= { starSessSub1 30 }

starSessSub1CPU OBJECT-TYPE
    SYNTAX     Integer32(0..3)
    MAX-ACCESS read-only
    STATUS     current
    DESCRIPTION
	"The CPU holding the session manager for this session.  Use in combination
	 with starSessSub1Card"
    ::= { starSessSub1 31 }

starSessSub1TimeIdleLeft OBJECT-TYPE
    SYNTAX     Gauge32
    UNITS      "Seconds"
    MAX-ACCESS read-only
    STATUS     current
    DESCRIPTION
        "The remaining idle time of the call, in seconds.  A value of 0xffffffff is used if the call
	 does not have an idle timeout"
    ::= { starSessSub1 32 }

starSessSub1TimeLeft OBJECT-TYPE
    SYNTAX     Gauge32
    UNITS      "Seconds"
    MAX-ACCESS read-only
    STATUS     current
    DESCRIPTION
        "The remaining session time of the call, in seconds.  A value of 0xffffffff is used if the call
	 does not have a session timeout"
    ::= { starSessSub1 33 }

starSessSub1TimeLongDurLeft OBJECT-TYPE
    SYNTAX     Gauge32
    UNITS      "Seconds"
    MAX-ACCESS read-only
    STATUS     current
    DESCRIPTION
        "The remaining long duration time of the call, in seconds.  A value of 0xffffffff is used if the call
	 does not have a long duration timer"
    ::= { starSessSub1 34 }

starSessSub1LongDurAction OBJECT-TYPE
    SYNTAX	StarLongDurTimeoutAction
    MAX-ACCESS  read-only
    STATUS      current
    DESCRIPTION
	"The action to take when the long duration timer is reached"
    ::= { starSessSub1 35 }

starSessSub1AlwaysOn OBJECT-TYPE
    SYNTAX      INTEGER {
		  unknown(0),
		  enabled(1),
		  disabled(2)
		}
    MAX-ACCESS  read-only
    STATUS      current
    DESCRIPTION
	" "
    ::= { starSessSub1 36 }

starSessSub1IPPoolName OBJECT-TYPE
    SYNTAX	OCTET STRING (SIZE(0..31))
    MAX-ACCESS  read-only
    STATUS      current
    DESCRIPTION
	" "
    ::= { starSessSub1 37 }

starSessSub1VLANID OBJECT-TYPE
    SYNTAX      Unsigned32
    MAX-ACCESS  read-only
    STATUS      current
    DESCRIPTION
	"0 is returned if this is not applicable"
    ::= { starSessSub1 38 }

starSessSub1LNSIPAddr OBJECT-TYPE
    SYNTAX	IpAddress
    MAX-ACCESS  read-only
    STATUS	current
    DESCRIPTION
	"Only valid if starSessSub1NetworkType is l2tp(3), otherwise 0.0.0.0"
    ::= { starSessSub1 39 }

starSessSub1ProxyMIP OBJECT-TYPE
    SYNTAX      INTEGER {
		  unknown(0),
		  enabled(1),
		  disabled(2)
		}
    MAX-ACCESS  read-only
    STATUS      current
    DESCRIPTION
	" "
    ::= { starSessSub1 40 }

starSessSub1GGSNMIP OBJECT-TYPE
    SYNTAX      INTEGER {
		  unknown(0),
		  enabled(1),
		  disabled(2)
		}
    MAX-ACCESS  read-only
    STATUS      current
    DESCRIPTION
	" "
    ::= { starSessSub1 41 }

starSessSub1HomeAgentIpAddr OBJECT-TYPE
    SYNTAX     IpAddress
    MAX-ACCESS read-only
    STATUS     current
    DESCRIPTION
	"The IP address of the Home Agent.  This value is applicable only if one of the following
	 is true:
		1. The value of starSessSub1AccessType is pdsnmobileip(2)
		2. The value of starSessSub1ProxyMIP is enabled(1)
		3. The value of starSessSub1GGSNMIP is enabled(1)
	 If not applicable, a value of 0.0.0.0 will be returned"
    ::= { starSessSub1 42 }

starSessSub1LocalIPAddr OBJECT-TYPE
    SYNTAX     IpAddress
    MAX-ACCESS read-only
    STATUS     current
    DESCRIPTION
	"The Local IP address of the Home Agent.  This value is applicable only if one of the following
	 is true:
		1. The value of starSessSub1AccessType is pdsnsimpleip(1)
		2. The value of starSessSub1AccessType is ggsnpdptypeppp(5)
		3. The value of starSessSub1AccessType is lnsl2tp(7)
	 If not applicable, a value of 0.0.0.0 will be returned"
    ::= { starSessSub1 43 }

starSessSub1FAServiceName OBJECT-TYPE
    SYNTAX     OCTET STRING (SIZE (1..63))
    MAX-ACCESS read-only
    STATUS     current
    DESCRIPTION
        "The FA service name for the subscriber.  This value is applicable only if one of the following
	 is true:
		1. The value of starSessSub1AccessType is pdsnmobileip(2)
		2. The value of starSessSub1ProxyMIP is enabled(1)
		3. The value of starSessSub1GGSNMIP is enabled(1)
	"
    ::= { starSessSub1 44 }

starSessSub1FAVPNName OBJECT-TYPE
    SYNTAX     DisplayString
    MAX-ACCESS read-only
    STATUS     current
    DESCRIPTION
	"The FA VPN (Context) name.    This value is applicable only if one of the following
	 is true:
		1. The value of starSessSub1AccessType is pdsnmobileip(2)
		2. The value of starSessSub1ProxyMIP is enabled(1)
		3. The value of starSessSub1GGSNMIP is enabled(1)
	"
    ::= { starSessSub1 45 }

starSessSub1SourceVPN OBJECT-TYPE
    SYNTAX     DisplayString
    MAX-ACCESS read-only
    STATUS     current
    DESCRIPTION
	"The Source VPN (Context) name."
    ::= { starSessSub1 46 }

starSessSub1DestVPN OBJECT-TYPE
    SYNTAX     DisplayString
    MAX-ACCESS read-only
    STATUS     current
    DESCRIPTION
	"The Destination VPN (Context) name."
    ::= { starSessSub1 47 }

starSessSub1AAAVPN OBJECT-TYPE
    SYNTAX     DisplayString
    MAX-ACCESS read-only
    STATUS     current
    DESCRIPTION
	" "
    ::= { starSessSub1 48 }

starSessSub1AAADomain OBJECT-TYPE
    SYNTAX     DisplayString
    MAX-ACCESS read-only
    STATUS     current
    DESCRIPTION
	" "
    ::= { starSessSub1 49 }

starSessSub1AAAStart OBJECT-TYPE
    SYNTAX     Counter32
    MAX-ACCESS read-only
    STATUS     current
    DESCRIPTION
	" "
    ::= { starSessSub1 50 }

starSessSub1AAAStop OBJECT-TYPE
    SYNTAX     Counter32
    MAX-ACCESS read-only
    STATUS     current
    DESCRIPTION
	" "
    ::= { starSessSub1 51 }

starSessSub1AAAInterim OBJECT-TYPE
    SYNTAX     Counter32
    MAX-ACCESS read-only
    STATUS     current
    DESCRIPTION
	" "
    ::= { starSessSub1 52 }

starSessSub1AcctSessionID OBJECT-TYPE
    SYNTAX     OCTET STRING (SIZE(0..47))
    MAX-ACCESS read-only
    STATUS     current
    DESCRIPTION
	" "
    ::= { starSessSub1 53 }

starSessSub1AAARadiusGroup OBJECT-TYPE
    SYNTAX     OCTET STRING (SIZE(0..63))
    MAX-ACCESS read-only
    STATUS     current
    DESCRIPTION
	" "
    ::= { starSessSub1 54 }

starSessSub1AAARadiusAuthServerIPAddr OBJECT-TYPE
    SYNTAX     IpAddress
    MAX-ACCESS read-only
    STATUS     current
    DESCRIPTION
	" "
    ::= { starSessSub1 55 }

starSessSub1AAARadiusAcctServerIPAddr OBJECT-TYPE
    SYNTAX     IpAddress
    MAX-ACCESS read-only
    STATUS     current
    DESCRIPTION
	" "
    ::= { starSessSub1 56 }

starSessSub1NASIPAddr OBJECT-TYPE
    SYNTAX     IpAddress
    MAX-ACCESS read-only
    STATUS     current
    DESCRIPTION
	"NAS IP Address (D2)"
    ::= { starSessSub1 57 }

starSessSub1NexthopIPAddr OBJECT-TYPE
    SYNTAX     IpAddress
    MAX-ACCESS read-only
    STATUS     current
    DESCRIPTION
	" "
    ::= { starSessSub1 58 }

starSessSub1ActiveInACL OBJECT-TYPE
    SYNTAX     OCTET STRING (SIZE(0..79))
    MAX-ACCESS read-only
    STATUS     current
    DESCRIPTION
	" "
    ::= { starSessSub1 59 }

starSessSub1ActiveOutACL OBJECT-TYPE
    SYNTAX     OCTET STRING (SIZE(0..79))
    MAX-ACCESS read-only
    STATUS     current
    DESCRIPTION
	" "
    ::= { starSessSub1 60 }

starSessSub1ECSRulebase OBJECT-TYPE
    SYNTAX     OCTET STRING (SIZE(0..63))
    MAX-ACCESS read-only
    STATUS     current
    DESCRIPTION
        " "
    ::= { starSessSub1 61 }

starSessSub1InPlcyGrp OBJECT-TYPE
    SYNTAX     OCTET STRING (SIZE(0..15))
    MAX-ACCESS read-only
    STATUS     current
    DESCRIPTION
        " "
    ::= { starSessSub1 62 }

starSessSub1OutPlcyGrp OBJECT-TYPE
    SYNTAX     OCTET STRING (SIZE(0..15))
    MAX-ACCESS read-only
    STATUS     current
    DESCRIPTION
        " "
    ::= { starSessSub1 63 }

starSessSub1DownTrafPolState OBJECT-TYPE
    SYNTAX     INTEGER {
		 unknown(0),
		 enabled(1),
		 disabled(2)
	       }
    MAX-ACCESS read-only
    STATUS     current
    DESCRIPTION
	"Downlink traffic policing state"
    ::= { starSessSub1 64 }

starSessSub1DownCommDataRate OBJECT-TYPE
    SYNTAX	Unsigned32
    UNITS       "bps"
    MAX-ACCESS  read-only
    STATUS      current
    DESCRIPTION
	"Downlink committed data rate, in bps.  This value is only valid if
	 starSessSub1DownTrafPolState is enabled(1)"
    ::= { starSessSub1 65 }

starSessSub1DownPeakDataRate OBJECT-TYPE
    SYNTAX	Unsigned32
    UNITS       "bps"
    MAX-ACCESS  read-only
    STATUS      current
    DESCRIPTION
 	"Downlink peak data rate, in bps.  This value will be 0 if the value
 	 of starSessSub1DownTrafPolState is anything other than enabled(1)"
    ::= { starSessSub1 66 }

starSessSub1DownBurstSize OBJECT-TYPE
    SYNTAX	Unsigned32
    UNITS       "bytes"
    MAX-ACCESS  read-only
    STATUS      current
    DESCRIPTION
 	"Downlink burst size, in bytes.  This value will be 0 if the value
 	 of starSessSub1DownTrafPolState is anything other than enabled(1)"
    ::= { starSessSub1 67 }

starSessSub1DownExceedAction OBJECT-TYPE
    SYNTAX      StarQOSTPAction
    MAX-ACCESS  read-only
    STATUS      current
    DESCRIPTION
	"Downlink Exceed Action.  This value will be notapplicable(1) if the value
 	 of starSessSub1DownTrafPolState is anything other than enabled(1)"
    ::= { starSessSub1 68 }

starSessSub1DownViolateAction OBJECT-TYPE
    SYNTAX      StarQOSTPAction
    MAX-ACCESS  read-only
    STATUS      current
    DESCRIPTION
	"Downlink Violate Action.  This value will be notapplicable(1) if the value
 	 of starSessSub1DownTrafPolState is anything other than enabled(1)"
    ::= { starSessSub1 69 }

starSessSub1DownExceed OBJECT-TYPE
    SYNTAX      Counter32
    UNITS       "packets"
    MAX-ACCESS  read-only
    STATUS      current
    DESCRIPTION
	"Downlink packets exceeded bandwidth parameters"
    ::= { starSessSub1 70 }

starSessSub1DownViolate OBJECT-TYPE
    SYNTAX      Counter32
    UNITS       "packets"
    MAX-ACCESS  read-only
    STATUS      current
    DESCRIPTION
	"Downlink packets violated bandwidth parameters"
    ::= { starSessSub1 71 }

starSessSub1UpTrafPolState OBJECT-TYPE
    SYNTAX     INTEGER {
		 unknown(0),
		 enabled(1),
		 disabled(2)
	       }
    MAX-ACCESS read-only
    STATUS     current
    DESCRIPTION
	"Uplink traffic policing state"
    ::= { starSessSub1 72 }

starSessSub1UpCommDataRate OBJECT-TYPE
    SYNTAX	Unsigned32
    UNITS       "bps"
    MAX-ACCESS  read-only
    STATUS      current
    DESCRIPTION
	"Uplink committed data rate, in bps.  This value is only valid if
	 starSessSub1UpTrafPolState is enabled(1)"
    ::= { starSessSub1 73 }

starSessSub1UpPeakDataRate OBJECT-TYPE
    SYNTAX	Unsigned32
    UNITS       "bps"
    MAX-ACCESS  read-only
    STATUS      current
    DESCRIPTION
 	"Uplink peak data rate, in bps.  This value will be 0 if the value
 	 of starSessSub1UpTrafPolState is anything other than enabled(1)"
    ::= { starSessSub1 74 }

starSessSub1UpBurstSize OBJECT-TYPE
    SYNTAX	Unsigned32
    UNITS       "bytes"
    MAX-ACCESS  read-only
    STATUS      current
    DESCRIPTION
 	"Uplink burst size, in bytes.  This value will be 0 if the value
 	 of starSessSub1UpTrafPolState is anything other than enabled(1)"
    ::= { starSessSub1 75 }

starSessSub1UpExceedAction OBJECT-TYPE
    SYNTAX      StarQOSTPAction
    MAX-ACCESS  read-only
    STATUS      current
    DESCRIPTION
	"Uplink Exceed Action.  This value will be notapplicable(1) if the value
 	 of starSessSub1UpTrafPolState is anything other than enabled(1)"
    ::= { starSessSub1 76 }

starSessSub1UpViolateAction OBJECT-TYPE
    SYNTAX      StarQOSTPAction
    MAX-ACCESS  read-only
    STATUS      current
    DESCRIPTION
	"Uplink Violate Action.  This value will be notapplicable(1) if the value
 	 of starSessSub1UpTrafPolState is anything other than enabled(1)"
    ::= { starSessSub1 77 }

starSessSub1UpExceed OBJECT-TYPE
    SYNTAX      Counter32
    UNITS       "packets"
    MAX-ACCESS  read-only
    STATUS      current
    DESCRIPTION
	"Uplink packets exceeded bandwidth parameters"
    ::= { starSessSub1 78 }

starSessSub1UpViolate OBJECT-TYPE
    SYNTAX      Counter32
    UNITS       "packets"
    MAX-ACCESS  read-only
    STATUS      current
    DESCRIPTION
	"Uplink packets violated bandwidth parameters"
    ::= { starSessSub1 79 }

starSessSub1L3TunnelingState OBJECT-TYPE
    SYNTAX      INTEGER {
		  unknown(0),
		  enabled(1),
		  disabled(2)
		}
    MAX-ACCESS  read-only
    STATUS      current
    DESCRIPTION
	"Identifies if L3 tunneling is enabled.  This value should be enabled(1) if
	 starSessSub1NetworkType is ipinip(5) or gre(6)"
    ::= { starSessSub1 80 }

starSessSub1L3TunLocalIPAddr OBJECT-TYPE
    SYNTAX      IpAddress
    MAX-ACCESS  read-only
    STATUS      current
    DESCRIPTION
	"L3 tunnel local address.  This value is valid only if starSessSub1L3TunnelState
	 is enabled(1), other it will be 0.0.0.0"
    ::= { starSessSub1 81 }

starSessSub1L3TunRemoteIPAddr OBJECT-TYPE
    SYNTAX      IpAddress
    MAX-ACCESS  read-only
    STATUS      current
    DESCRIPTION
	"L3 tunnel remote address.  This value is valid only if starSessSub1L3TunnelState
	 is enabled(1), other it will be 0.0.0.0"
    ::= { starSessSub1 82 }

starSessSub1AddrViaDHCP OBJECT-TYPE
    SYNTAX      INTEGER {
		  unknown(0),
		  enabled(1),
		  disabled(2)
		}
    MAX-ACCESS  read-only
    STATUS      current
    DESCRIPTION
	" "
    ::= { starSessSub1 83 }

starSessSub1DHCPServName OBJECT-TYPE
    SYNTAX      OCTET STRING (SIZE(0..63))
    MAX-ACCESS  read-only
    STATUS      current
    DESCRIPTION
	"DHCP service name.  This value is only valid if starSessSub1DHCPAddrViaDHCP
	 is enabled(1)"
    ::= { starSessSub1 84 }

starSessSub1DHCPServIPAddr OBJECT-TYPE
    SYNTAX      IpAddress
    MAX-ACCESS  read-only
    STATUS      current
    DESCRIPTION
	"DHCP service IP address.  This value is only valid if starSessSub1DHCPAddrViaDHCP
	 is enabled(1), otherwise it will be 0.0.0.0"
    ::= { starSessSub1 85 }

starSessSub1AccessLinkIPFrag OBJECT-TYPE
    SYNTAX      INTEGER {
		  unkwnown(0),
		  normal(1),
		  dfignore(2),
		  dffragandicmp(3)
		}
    MAX-ACCESS  read-only
    STATUS      current
    DESCRIPTION
	" "
    ::= { starSessSub1 86 }

starSessSub1IgnoreDFBit OBJECT-TYPE
    SYNTAX     INTEGER {
		 unknown(0),
		 enabed(1),
		 disabled(2)
	       }
    MAX-ACCESS read-only
    STATUS     current
    DESCRIPTION
	"Ignore DF-bit data-tunnel"
    ::= { starSessSub1 87 }

starSessSub1MIPGratARPMode OBJECT-TYPE
    SYNTAX      INTEGER {
		  unkwnown(0),
		  notapplicable(1),
		  aggressive(2),
		  normal(3)
	 	}
    MAX-ACCESS  read-only
    STATUS	current
    DESCRIPTION
	"This field is only applicable if starSessSub1AccessType is hamobileip(3) or haipsec(8)"
    ::= { starSessSub1 88 }

starSessSub1ExtInlSrvrProc OBJECT-TYPE
    SYNTAX	INTEGER {
		  unknown(0),
		  enabled(1),
		  disabled(2)
		}
    MAX-ACCESS  read-only
    STATUS      current
    DESCRIPTION
	"The state of external inline server processing"
    ::= { starSessSub1 89 }

starSessSub1ExtInlSrvrIngrIPAddr OBJECT-TYPE
    SYNTAX	IpAddress
    MAX-ACCESS  read-only
    STATUS	current
    DESCRIPTION
	"The external inline server ingress IP address.  This value is only valid if
	 starSessSub1ExtInlSrvrProc is enabled(1)"
    ::= { starSessSub1 90 }

starSessSub1ExtInlSrvrIngrVLANTag OBJECT-TYPE
    SYNTAX	Unsigned32
    MAX-ACCESS  read-only
    STATUS	current
    DESCRIPTION
	"The external inline server ingress VLAN tag.  This value is only valid if
	 starSessSub1ExtInlSrvrProc is enabled(1)"
    ::= { starSessSub1 91 }

starSessSub1ExtInlSrvrEgrIPAddr OBJECT-TYPE
    SYNTAX	IpAddress
    MAX-ACCESS  read-only
    STATUS	current
    DESCRIPTION
	"The external inline server egress IP address.  This value is only valid if
	 starSessSub1ExtInlSrvrProc is enabled(1)"
    ::= { starSessSub1 92 }

starSessSub1ExtInlSrvrEgrVLANTag OBJECT-TYPE
    SYNTAX	Unsigned32
    MAX-ACCESS  read-only
    STATUS	current
    DESCRIPTION
	"The external inline server egress VLAN tag.  This value is only valid if
	 starSessSub1ExtInlSrvrProc is enabled(1)"
    ::= { starSessSub1 93 }

starSessSub1ExtInlSrvrVPNName OBJECT-TYPE
    SYNTAX	DisplayString
    MAX-ACCESS  read-only
    STATUS	current
    DESCRIPTION
	"The external inline server context (VPN).  This value is only valid if
	 starSessSub1ExtInlSrvrProc is enabled(1)"
    ::= { starSessSub1 94 }

starSessSub1RadAcctMode OBJECT-TYPE
    SYNTAX	INTEGER {
		  unknown(0),
		  flowbasedaux(1),
		  flowbasedall(2),
		  flowbasednone(3),
		  sessionbased(4)
		}
    MAX-ACCESS	read-only
    STATUS	current
    DESCRIPTION
	"Radius Accounting Mode"
    ::= { starSessSub1 95 }

starSessSub1InBytesDropped OBJECT-TYPE
    SYNTAX     Counter32
    UNITS      "KB"
    MAX-ACCESS read-only
    STATUS     current
    DESCRIPTION
        "The count of incoming bytes dropped for the subscriber, in kilobytes,
	 rounded down (i.e. 1023 bytes = 0 kilobytes"
    ::= { starSessSub1 96 }

starSessSub1OutBytesDropped OBJECT-TYPE
    SYNTAX     Counter32
    UNITS      "KB"
    MAX-ACCESS read-only
    STATUS     current
    DESCRIPTION
        "The count of outgoing bytes dropped for the subscriber, in kilobytes,
	 rounded down (i.e. 1023 bytes = 0 kilobytes"
    ::= { starSessSub1 97 }

starSessSub1PeakBPSTx OBJECT-TYPE
    SYNTAX     Gauge32
    UNITS      "Bytes per second"
    MAX-ACCESS read-only
    STATUS     current
    DESCRIPTION
	"Peak rate from user, in bytes per second"
    ::= { starSessSub1 98 }

starSessSub1PeakBPSRx OBJECT-TYPE
    SYNTAX     Gauge32
    UNITS      "Bytes per second"
    MAX-ACCESS read-only
    STATUS     current
    DESCRIPTION
	"Peak rate to user, in bytes per second"
    ::= { starSessSub1 99 }

starSessSub1AveBPSTx OBJECT-TYPE
    SYNTAX     Gauge32
    UNITS      "Bytes per second"
    MAX-ACCESS read-only
    STATUS     current
    DESCRIPTION
	"Average rate from user, in bytes per second"
    ::= { starSessSub1 100 }

starSessSub1AveBPSRx OBJECT-TYPE
    SYNTAX     Gauge32
    UNITS      "Bytes per second"
    MAX-ACCESS read-only
    STATUS     current
    DESCRIPTION
	"Average rate to user, in bytes per second"
    ::= { starSessSub1 101 }

starSessSub1SustBPSTx OBJECT-TYPE
    SYNTAX     Gauge32
    UNITS      "Bytes per second"
    MAX-ACCESS read-only
    STATUS     current
    DESCRIPTION
	"Sustained rate from user, in bytes per second"
    ::= { starSessSub1 102 }

starSessSub1SustBPSRx OBJECT-TYPE
    SYNTAX     Gauge32
    UNITS      "Bytes per second"
    MAX-ACCESS read-only
    STATUS     current
    DESCRIPTION
	"Sustained rate to user, in bytes per second"
    ::= { starSessSub1 103 }

starSessSub1PeakPPSTx OBJECT-TYPE
    SYNTAX     Gauge32
    UNITS      "Packets per second"
    MAX-ACCESS read-only
    STATUS     current
    DESCRIPTION
	"Peak rate from user, in packets per second"
    ::= { starSessSub1 104 }

starSessSub1PeakPPSRx OBJECT-TYPE
    SYNTAX     Gauge32
    UNITS      "Packets per second"
    MAX-ACCESS read-only
    STATUS     current
    DESCRIPTION
	"Peak rate to user, in packets per second"
    ::= { starSessSub1 105 }

starSessSub1AvePPSTx OBJECT-TYPE
    SYNTAX     Gauge32
    UNITS      "Packets per second"
    MAX-ACCESS read-only
    STATUS     current
    DESCRIPTION
	"Average rate from user, in packets per second"
    ::= { starSessSub1 106 }

starSessSub1AvePPSRx OBJECT-TYPE
    SYNTAX     Gauge32
    UNITS      "Packets per second"
    MAX-ACCESS read-only
    STATUS     current
    DESCRIPTION
	"Average rate to user, in packets per second"
    ::= { starSessSub1 107 }

starSessSub1SustPPSTx OBJECT-TYPE
    SYNTAX     Gauge32
    UNITS      "Packets per second"
    MAX-ACCESS read-only
    STATUS     current
    DESCRIPTION
	"Sustained rate from user, in packets per second"
    ::= { starSessSub1 108 }

starSessSub1SustPPSRx OBJECT-TYPE
    SYNTAX     Gauge32
    UNITS      "Packets per second"
    MAX-ACCESS read-only
    STATUS     current
    DESCRIPTION
	"Sustained rate to user, in packets per second"
    ::= { starSessSub1 109 }

starSessSub1ActivePct OBJECT-TYPE
    SYNTAX     Integer32(0..100)
    UNITS      "percent"
    MAX-ACCESS read-only
    STATUS     current
    DESCRIPTION
	"Link online/active percentage"
    ::= { starSessSub1 110 }

starSessSub1IPv4BadHdr OBJECT-TYPE
    SYNTAX     Counter32
    MAX-ACCESS read-only
    STATUS     current
    DESCRIPTION
	"IPv4 Bad Headers"
    ::= { starSessSub1 111 }

starSessSub1IPv4TtlExceeded OBJECT-TYPE
    SYNTAX     Counter32
    MAX-ACCESS read-only
    STATUS     current
    DESCRIPTION
	"IPv4 Total Exceeded"
    ::= { starSessSub1 112 }

starSessSub1IPv4FragSent OBJECT-TYPE
    SYNTAX     Counter32
    MAX-ACCESS read-only
    STATUS     current
    DESCRIPTION
	"IPv4 Fragments sent"
    ::= { starSessSub1 113 }

starSessSub1IPv4FragFail OBJECT-TYPE
    SYNTAX     Counter32
    MAX-ACCESS read-only
    STATUS     current
    DESCRIPTION
	"IPv4 Could Not Fragment errors"
    ::= { starSessSub1 114 }

starSessSub1IPv4InACLDrop OBJECT-TYPE
    SYNTAX     Counter32
    MAX-ACCESS read-only
    STATUS     current
    DESCRIPTION
	"IPv4 Input ACL Drops"
    ::= { starSessSub1 115 }

starSessSub1IPv4OutACLDrop OBJECT-TYPE
    SYNTAX     Counter32
    MAX-ACCESS read-only
    STATUS     current
    DESCRIPTION
	"IPv5 Output ACL Drops"
    ::= { starSessSub1 116 }

starSessSub1IPv4InCSSDownDrop OBJECT-TYPE
    SYNTAX     Counter32
    MAX-ACCESS read-only
    STATUS     current
    DESCRIPTION
	"IPv4 Input CSS Down Drops"
    ::= { starSessSub1 117 }

starSessSub1IPv4OutCSSDownDrop OBJECT-TYPE
    SYNTAX     Counter32
    MAX-ACCESS read-only
    STATUS     current
    DESCRIPTION
	"IPv4 Output CSS Down Drops"
    ::= { starSessSub1 118 }

starSessSub1IPv4OutXOFFDropPkt OBJECT-TYPE
    SYNTAX     Counter32
    UNITS      "packets"
    MAX-ACCESS read-only
    STATUS     current
    DESCRIPTION
	"IPv4 Output XOFF Packets Drop"
    ::= { starSessSub1 119 }

starSessSub1IPv4OutXOFFDropByte OBJECT-TYPE
    SYNTAX     Counter32
    MAX-ACCESS read-only
    STATUS     current
    DESCRIPTION
	"IPv4 Output XOFF Bytes Drop"
    ::= { starSessSub1 120 }

starSessSub1IPv4SrcViol OBJECT-TYPE
    SYNTAX     Counter32
    MAX-ACCESS read-only
    STATUS     current
    DESCRIPTION
	"IPv4 Source Violations"
    ::= { starSessSub1 121 }

starSessSub1IPv4ProxyDNSRedir OBJECT-TYPE
    SYNTAX     Counter32
    MAX-ACCESS read-only
    STATUS     current
    DESCRIPTION
	"IPv4 Proxy-DNS Redirect"
    ::= { starSessSub1 122 }

starSessSub1IPv4SrcProxyDNSPThru OBJECT-TYPE
    SYNTAX     Counter32
    MAX-ACCESS read-only
    STATUS     current
    DESCRIPTION
	"IPv4 Proxy-DNS Pass-Thru"
    ::= { starSessSub1 123 }

starSessSub1IPv4ProxyDNSDrop OBJECT-TYPE
    SYNTAX     Counter32
    MAX-ACCESS read-only
    STATUS     current
    DESCRIPTION
	"IPv4 Proxy-DNS Drop"
    ::= { starSessSub1 124 }

starSessSub1IPv4SrcViolNoAcct OBJECT-TYPE
    SYNTAX     Counter32
    MAX-ACCESS read-only
    STATUS     current
    DESCRIPTION
	"IPv4 Source Violations No Account"
    ::= { starSessSub1 125 }

starSessSub1IPv4SrcViolIgnored OBJECT-TYPE
    SYNTAX     Counter32
    MAX-ACCESS read-only
    STATUS     current
    DESCRIPTION
	"IPv4 Source Violations Ignored"
    ::= { starSessSub1 126 }

starSessSub1ExtInlSrvrTxPkt OBJECT-TYPE
    SYNTAX      Counter32
    UNITS       "packets"
    MAX-ACCESS  read-only
    STATUS	current
    DESCRIPTION
	"Packets transmitted to inline server.  This value is valid only if
	 the value of starSessSub1ExtInlSrvrProc is enabled(1)"
    ::= { starSessSub1 127 }

starSessSub1ExtInlSrvrRxPkt OBJECT-TYPE
    SYNTAX      Counter32
    UNITS       "packets"
    MAX-ACCESS  read-only
    STATUS	current
    DESCRIPTION
	"Packets received from inline server.  This value is valid only if
	 the value of starSessSub1ExtInlSrvrProc is enabled(1)"
    ::= { starSessSub1 128 }

starSessSub1IPv4ICMPDropPkt OBJECT-TYPE
    SYNTAX     Counter32
    UNITS       "packets"
    MAX-ACCESS read-only
    STATUS     current
    DESCRIPTION
	"IPv4 ICMP Packets dropped"
    ::= { starSessSub1 129 }

starSessSub1TunnelType OBJECT-TYPE
    SYNTAX     INTEGER {
		 unknown(0),
		 none(1),
		 pptp(2),
		 l2tp(3),
		 ah(4),
		 ipinip(5),
		 esp(6),
		 gre(7)
	       }
    MAX-ACCESS  read-only
    STATUS      current
    DESCRIPTION
	"Tunnel Type"
    ::= { starSessSub1 130 }

starSessSub1IPSECTunDownDropPkt OBJECT-TYPE
    SYNTAX	Counter32
    UNITS	"packets"
    MAX-ACCESS  read-only
    STATUS      current
    DESCRIPTION
	"Pool IPSEC tunnel down packets dropped.  This value is only valid if the
	 value of starSessSub1TunnelType is esp(6)"
    ::= { starSessSub1 131 }

starSessSub1IPSECFlowID OBJECT-TYPE
    SYNTAX      Integer32
    MAX-ACCESS	read-only
    STATUS	current
    DESCRIPTION
	"IP Pool IPSEC flow id.  This value is only valid if the
	 value of starSessSub1TunnelType is esp(6)"
    ::= { starSessSub1 132 }

starSessSub1DormancyTotal OBJECT-TYPE
    SYNTAX	Counter32
    MAX-ACCESS  read-only
    STATUS	current
    DESCRIPTION
	"Dormancy total.  This value is not valid if the value of
	 starSessSub1AccessType is ggsnpdptypeipv4(4) or ggsnpdptypeppp(5)"
    ::= { starSessSub1 133 }

starSessSub1HandoffTotal OBJECT-TYPE
    SYNTAX	Counter32
    MAX-ACCESS  read-only
    STATUS	current
    DESCRIPTION
	"Handoff total.  This value is not valid if the value of
	 starSessSub1AccessType is ggsnpdptypeipv4(4) or ggsnpdptypeppp(5)"
    ::= { starSessSub1 134 }

starSessSub1AccessFlows OBJECT-TYPE
    SYNTAX	Gauge32
    MAX-ACCESS  read-only
    STATUS	current
    DESCRIPTION
	"Access flows"
    ::= { starSessSub1 135 }

starSessSub1TFT OBJECT-TYPE
    SYNTAX	Gauge32
    MAX-ACCESS  read-only
    STATUS	current
    DESCRIPTION
	"Number of TFTs"
    ::= { starSessSub1 136 }

starSessSub1NASPort OBJECT-TYPE
    SYNTAX	Integer32
    MAX-ACCESS  read-only
    STATUS      current
    DESCRIPTION
	"NAS port"
    ::= { starSessSub1 137 }

starSessSub1CorrID OBJECT-TYPE
    SYNTAX      OCTET STRING (SIZE(0..47))
    MAX-ACCESS  read-only
    STATUS      current
    DESCRIPTION
	"ThreeGPP2-correlation-id (C2)"
    ::= { starSessSub1 139 }

starSessSub1L2TPPeerIPAddr OBJECT-TYPE
    SYNTAX	IpAddress
    MAX-ACCESS  read-only
    STATUS	current
    DESCRIPTION
	"L2TP Peer address.  This value is only valid if the value of
	 starSessSub1NetworkType is l2tp(3)"
    ::= { starSessSub1 140 }

starSessSub1IPv4EarlyPDURecv OBJECT-TYPE
    SYNTAX	Counter32
    MAX-ACCESS  read-only
    STATUS	current
    DESCRIPTION
	"IPv4 early PDU received"
    ::= { starSessSub1 141 }

-- Nw Reacheability Srvr; these objects are provided for use in SNMP Traps only

starentNwReachServer OBJECT IDENTIFIER ::= { starentMIBObjects 35 }

starNwReachTable OBJECT-TYPE
    SYNTAX	SEQUENCE OF StarNwReachEntry
    MAX-ACCESS  not-accessible
    STATUS      current
    DESCRIPTION
	"A table containing Network Reacheable Server information"
    ::= { starentNwReachServer 1 }

starNwReachEntry OBJECT-TYPE
    SYNTAX	StarNwReachEntry
    MAX-ACCESS  not-accessible
    STATUS      current
    DESCRIPTION
        "Information for a specific Ntw Reachable Server"
    INDEX { starNwReachName }
    ::= { starNwReachTable 1 }

StarNwReachEntry ::=
    SEQUENCE {
	starNwReachName            OCTET STRING,
	starNwReachSrvrAddr	   IpAddress
    }

starNwReachName OBJECT-TYPE
    SYNTAX      OCTET STRING (SIZE (1..16))
    MAX-ACCESS  accessible-for-notify
    STATUS      current
    DESCRIPTION
	"The Name for this Network Reacheable Server"
    ::= { starNwReachEntry 1 }

starNwReachSrvrAddr OBJECT-TYPE
    SYNTAX      IpAddress
    MAX-ACCESS  accessible-for-notify
    STATUS      current
    DESCRIPTION
        "The IP Address for the Network Reacheable Server"
    ::= { starNwReachEntry 2 }

-- IPSEC; these objects are provided for use in SNMP Traps only

starentIPSEC OBJECT IDENTIFIER ::= { starentMIBObjects 36 }

starIPSECContextName OBJECT-TYPE
    SYNTAX	DisplayString
    MAX-ACCESS	accessible-for-notify
    STATUS      current
    DESCRIPTION
	"The name of a context"
    ::= { starentIPSEC 1 }

starIPSECGroupName OBJECT-TYPE
    SYNTAX	DisplayString
    MAX-ACCESS  accessible-for-notify
    STATUS      current
    DESCRIPTION
	"The name of a crypto group"
    ::= { starentIPSEC 2 }

starIPSECTunLocalIpAddr OBJECT-TYPE
    SYNTAX	DisplayString
    MAX-ACCESS  accessible-for-notify
    STATUS      current
    DESCRIPTION
	"The local IP Address for an IPSEC tunnel"
    ::= { starentIPSEC 3 }

starIPSECTunRemoteIpAddr OBJECT-TYPE
    SYNTAX	DisplayString
    MAX-ACCESS  accessible-for-notify
    STATUS      current
    DESCRIPTION
	"The remote IP Address for an IPSEC tunnel"
    ::= { starentIPSEC 4 }

starIPSECPolicyName OBJECT-TYPE
    SYNTAX	DisplayString
    MAX-ACCESS  accessible-for-notify
    STATUS      current
    DESCRIPTION
	"An IPSEC policy name"
    ::= { starentIPSEC 5 }

starIPSECDynPolicyType OBJECT-TYPE
    SYNTAX	INTEGER {
		 unknown(0),
		 manual(1),
		 isakmp(2),
		 subscribertemplate(3),
		 subscribertunnel(4),
		 test(5),
		 dynamic(6)
		}
    MAX-ACCESS  accessible-for-notify
    STATUS      current
    DESCRIPTION
	"An IPSEC dynamic policy type.  Note that the value test(5) is used only for internal testing"
    ::= { starentIPSEC 6 }

starIPSECDynPolicyPayloadType OBJECT-TYPE
    SYNTAX	INTEGER {
		  unknown(0),
		  control(1),
		  data(2),
		  ipip(3),
		  gre(4),
		  test(5)
		}
    MAX-ACCESS  accessible-for-notify
    STATUS      current
    DESCRIPTION
	"An IPSEC dynamic policy payload type"
    ::= { starentIPSEC 7 }

starIPSECLocalGateway OBJECT-TYPE
    SYNTAX	IpAddress
    MAX-ACCESS  accessible-for-notify
    STATUS      current
    DESCRIPTION
	" "
    ::= { starentIPSEC 8 }

starIPSECRemoteGateway OBJECT-TYPE
    SYNTAX	IpAddress
    MAX-ACCESS  accessible-for-notify
    STATUS      current
    DESCRIPTION
	" "
    ::= { starentIPSEC 9 }


starentSIPRoute OBJECT IDENTIFIER ::= { starentMIBObjects 37 }

starSIPRouteTable OBJECT-TYPE
   SYNTAX     SEQUENCE OF StarSIPRouteEntry
   MAX-ACCESS not-accessible
   STATUS     current
   DESCRIPTION
         "A table containing SIPRoute related information"
   ::= { starentSIPRoute 1}

starSIPRouteEntry OBJECT-TYPE
   SYNTAX     StarSIPRouteEntry
   MAX-ACCESS not-accessible
   STATUS     current
   DESCRIPTION
      "The statistics for a specific SIPRoute service"
   INDEX { starSIPRouteVpnID }
   ::= { starSIPRouteTable 1 }

StarSIPRouteEntry ::=
    SEQUENCE {
     starSIPRouteVpnID             Gauge32,
     starSIPRouteVpnName           DisplayString,
     starSIPRouteVmgName           DisplayString,
     starSIPRouteAsName            DisplayString,
     starSIPRouteDestPartyNum      DisplayString,
     starSIPRouteReqNum            DisplayString
         }

starSIPRouteVpnID OBJECT-TYPE
   SYNTAX     Gauge32
   MAX-ACCESS not-accessible
   STATUS     current
   DESCRIPTION
         "The internal identification of the VPN (context)"
   ::= { starSIPRouteEntry 1 }


starSIPRouteVpnName OBJECT-TYPE
    SYNTAX     DisplayString
    MAX-ACCESS read-only
    STATUS     current
    DESCRIPTION
         "The name of this VPN (context)"
   ::= { starSIPRouteEntry 2 }

starSIPRouteVmgName OBJECT-TYPE
   SYNTAX     DisplayString
   MAX-ACCESS read-only
   STATUS     current
   DESCRIPTION
         "The name of this VMG (context)"
   ::= { starSIPRouteEntry 3 }

starSIPRouteAsName OBJECT-TYPE
   SYNTAX     DisplayString
   MAX-ACCESS read-only
   STATUS     current
   DESCRIPTION
         "The name of this AS (context)"
   ::= { starSIPRouteEntry 4 }

starSIPRouteDestPartyNum OBJECT-TYPE
   SYNTAX     DisplayString
   MAX-ACCESS read-only
   STATUS     current
   DESCRIPTION
         "The dest. party number"
   ::= { starSIPRouteEntry 5 }

starSIPRouteReqNum OBJECT-TYPE
   SYNTAX     DisplayString
   MAX-ACCESS read-only
   STATUS     current
   DESCRIPTION
         "The  request number"
   ::= { starSIPRouteEntry 6 }


starentRPServiceOption OBJECT IDENTIFIER ::= { starentMIBObjects 38 }

starRPServiceOptionTable OBJECT-TYPE
    SYNTAX     SEQUENCE OF StarRPServiceOptionEntry
    MAX-ACCESS not-accessible
    STATUS     current
    DESCRIPTION
	" "
    ::= { starentRPServiceOption 1 }

starRPServiceOptionEntry OBJECT-TYPE
    SYNTAX     StarRPServiceOptionEntry
    MAX-ACCESS not-accessible
    STATUS     current
    DESCRIPTION
	" "
    INDEX { starRPServiceOptionNum }
    ::= { starRPServiceOptionTable 1 }

StarRPServiceOptionEntry ::=
    SEQUENCE {
	starRPServiceOptionNum		Integer32,
	starRPServiceOptionCalls	Gauge32
    }

starRPServiceOptionNum OBJECT-TYPE
    SYNTAX     Integer32(1..255)
    MAX-ACCESS not-accessible
    STATUS     current
    DESCRIPTION
	" "
    ::= { starRPServiceOptionEntry 1 }

starRPServiceOptionCalls OBJECT-TYPE
    SYNTAX     Gauge32
    MAX-ACCESS read-only
    STATUS     current
    DESCRIPTION
	" "
    ::= { starRPServiceOptionEntry 2 }


-- PCF statistics

starentPCFStats OBJECT IDENTIFIER ::= { starentMIBObjects 39 }

starPCFStatTable OBJECT-TYPE
    SYNTAX     SEQUENCE OF StarPCFStatEntry
    MAX-ACCESS not-accessible
    STATUS     current
    DESCRIPTION
	"A table of per-PCF statistics"
    ::= { starentPCFStats 1 }

starPCFStatEntry OBJECT-TYPE
    SYNTAX     StarPCFStatEntry
    MAX-ACCESS not-accessible
    STATUS     current
    DESCRIPTION
	"The statistics for a specific PCF"
    INDEX { starPCFStatVpnID, starPCFStatIpAddr }
    ::= { starPCFStatTable 1 }

StarPCFStatEntry ::=
    SEQUENCE {
	starPCFStatVpnID                        Gauge32,
        starPCFStatIpAddr                       IpAddress,
        starPCFStatVpnName			DisplayString,
	starPCFStatRxPkts                       Counter32,
	starPCFStatTxPkts                       Counter32,
	starPCFStatRxBytes                      Counter32,
	starPCFStatTxBytes                      Counter32,
	starPCFStatTotalSessions                Counter32,
	starPCFStatCurrentSessions              Gauge32,
	starPCFStatCurrentActiveSessions        Gauge32,
	starPCFStatCurrentDormantSessions       Gauge32,
	starPCFStatCurrentSIPConnected          Gauge32,
	starPCFStatCurrentMIPConnected          Gauge32,
	starPCFStatCurrentPMIPConnected         Gauge32,
	starPCFStatCurrentL2TPLACConnected      Gauge32,
	starPCFStatCurrentOtherConnected        Gauge32
    }

starPCFStatVpnID OBJECT-TYPE
    SYNTAX     Gauge32
    MAX-ACCESS not-accessible
    STATUS     current
    DESCRIPTION
	" "
    ::= { starPCFStatEntry 1 }

starPCFStatIpAddr OBJECT-TYPE
    SYNTAX     IpAddress
    MAX-ACCESS not-accessible
    STATUS     current
    DESCRIPTION
	" "
    ::= { starPCFStatEntry 2 }

starPCFStatVpnName OBJECT-TYPE
    SYNTAX     DisplayString
    MAX-ACCESS read-only
    STATUS     current
    DESCRIPTION
        " "
    ::= { starPCFStatEntry 3 }

starPCFStatRxPkts OBJECT-TYPE
    SYNTAX     Counter32
    UNITS      "Millions"
    MAX-ACCESS read-only
    STATUS     current
    DESCRIPTION
	" "
    ::= { starPCFStatEntry 4 }

starPCFStatTxPkts OBJECT-TYPE
    SYNTAX     Counter32
    UNITS      "Millions"
    MAX-ACCESS read-only
    STATUS     current
    DESCRIPTION
	" "
    ::= { starPCFStatEntry 5 }

starPCFStatRxBytes OBJECT-TYPE
    SYNTAX     Counter32
    UNITS      "Megabytes"
    MAX-ACCESS read-only
    STATUS     current
    DESCRIPTION
	" "
    ::= { starPCFStatEntry 6 }

starPCFStatTxBytes OBJECT-TYPE
    SYNTAX     Counter32
    UNITS      "Megabytes"
    MAX-ACCESS read-only
    STATUS     current
    DESCRIPTION
	" "
    ::= { starPCFStatEntry 7 }

starPCFStatTotalSessions OBJECT-TYPE
    SYNTAX     Counter32
    MAX-ACCESS read-only
    STATUS     current
    DESCRIPTION
	" "
    ::= { starPCFStatEntry 8 }

starPCFStatCurrentSessions OBJECT-TYPE
    SYNTAX     Gauge32
    MAX-ACCESS read-only
    STATUS     current
    DESCRIPTION
	" "
    ::= { starPCFStatEntry 9 }

starPCFStatCurrentActiveSessions OBJECT-TYPE
    SYNTAX     Gauge32
    MAX-ACCESS read-only
    STATUS     current
    DESCRIPTION
	" "
    ::= { starPCFStatEntry 10 }

starPCFStatCurrentDormantSessions OBJECT-TYPE
    SYNTAX     Gauge32
    MAX-ACCESS read-only
    STATUS     current
    DESCRIPTION
	" "
    ::= { starPCFStatEntry 11 }

starPCFStatCurrentSIPConnected OBJECT-TYPE
    SYNTAX     Gauge32
    MAX-ACCESS read-only
    STATUS     current
    DESCRIPTION
	" "
    ::= { starPCFStatEntry 12 }

starPCFStatCurrentMIPConnected OBJECT-TYPE
    SYNTAX     Gauge32
    MAX-ACCESS read-only
    STATUS     current
    DESCRIPTION
	" "
    ::= { starPCFStatEntry 13 }

starPCFStatCurrentPMIPConnected OBJECT-TYPE
    SYNTAX     Gauge32
    MAX-ACCESS read-only
    STATUS     current
    DESCRIPTION
	" "
    ::= { starPCFStatEntry 14 }

starPCFStatCurrentL2TPLACConnected OBJECT-TYPE
    SYNTAX     Gauge32
    MAX-ACCESS read-only
    STATUS     current
    DESCRIPTION
	" "
    ::= { starPCFStatEntry 15 }

starPCFStatCurrentOtherConnected OBJECT-TYPE
    SYNTAX     Gauge32
    MAX-ACCESS read-only
    STATUS     current
    DESCRIPTION
	" "
    ::= { starPCFStatEntry 16 }

-- Per Service PCF statistics

starPCFTable OBJECT-TYPE
    SYNTAX     SEQUENCE OF StarPCFEntry
    MAX-ACCESS not-accessible
    STATUS     current
    DESCRIPTION
	"A table of per service PCF statistics"
    ::= { starentPCFStats 2 }

starPCFEntry OBJECT-TYPE
    SYNTAX    StarPCFEntry 
    MAX-ACCESS not-accessible
    STATUS     current
    DESCRIPTION
	"The statistics for a specific PCF per service"
    INDEX { starPCFSvcID, starPCFIpAddr }
    ::= { starPCFTable 1 }

StarPCFEntry ::=
    SEQUENCE {
	starPCFSvcID                             StarShortID,
        starPCFIpAddr                            IpAddress,
	starPCFVpnID                             Gauge32,
        starPCFVpnName		                 DisplayString,
	starPCFServName                          DisplayString,
        starPCFRrqRcvd                           Counter32,
        starPCFRrqAccepted                       Counter32,
        starPCFRrqDenied                         Counter32,
        starPCFRrqDiscarded                      Counter32,
        starPCFInitialRrqRcvd                    Counter32,
        starPCFInitialRrqAccepted                Counter32,
        starPCFIntraPDSNActiveHORrqAccepted      Counter32,
        starPCFIntraPDSNDormantHORrqAccepted     Counter32,
        starPCFInterPDSNHORrqAccepted            Counter32,
        starPCFInitialRrqDenied                  Counter32,
        starPCFInitialRrqDiscarded               Counter32,
        starPCFRenewRrqRcvd                      Counter32,
        starPCFRenewRrqAccepted                  Counter32,
        starPCFRenewActiveRrqAccepted            Counter32,
        starPCFRenewDormantRrqAccepted           Counter32,
        starPCFRenewRrqDenied                    Counter32,
        starPCFRenewRrqDiscarded                 Counter32,
        starPCFDeregRrqRcvd                      Counter32,
        starPCFDeregRrqAccepted                  Counter32,
        starPCFDeregDormantRrqAccepted           Counter32,
        starPCFDeregRrqDenied                    Counter32,
        starPCFDeregRrqDiscarded                 Counter32,
        starPCFIntraPDSNActiveAnidHORrqAccepted  Counter32,
        starPCFIntraPDSNDormantAnidHORrqAccepted Counter32,
	starPCFDeniedUnSpeReason                 Counter32,
        starPCFDeniedAdmProh                     Counter32,
        starPCFDeniedInsufResource               Counter32,
        starPCFDeniedMobNodeAuthFail             Counter32,
        starPCFDeniedIdentMismatch               Counter32,
        starPCFDeniedPoorFormedReq               Counter32,
        starPCFDeniedUnknownPDSNAddr             Counter32,
        starPCFDeniedRevTunnelUnavail            Counter32,
        starPCFDeniedRevTunnelRequire            Counter32,
        starPCFDeniedUnrecogVendorId             Counter32,
        starPCFDeniedSessionClosed               Counter32,
        starPCFDeniedBsnSessionInfoUnavail       Counter32,
        starPCFRegUpdTransmitted                  Counter32,
        starPCFRegUpdAccepted                    Counter32,
        starPCFRegUpdateRpLifetimeExpiry         Counter32,
        starPCFRegUpdateUpperLayerIntiated       Counter32,
        starPCFRegUpdateOtherReason              Counter32,
        starPCFRegUpdateHORelease                Counter32,
        starPCFRegUpdateSessmgrDied              Counter32,
        starPCFAuxA10ConnectionsSetup            Counter32,
        starPCFSessionsDenied                    Counter32,
        starPCFSessionsInit                      Counter32,
        starPCFSessionsReneg                     Counter32,
        starPCFDiscLcpRemote                     Counter32,
        starPCFDiscRpRemote                      Counter32,
        starPCFDiscRpLocal                       Counter32,
        starPCFDiscMaxIpcpRetr                   Counter32,
        starPCFDiscMaxIpv6cpRetr                 Counter32,
        starPCFDiscMaxLcpRetr                    Counter32,
        starPCFDiscAuthFail                      Counter32,
        starPCFDiscSessSetupTimeout              Counter32,
        starPCFDiscFlowAddFail                   Counter32,
        starPCFDiscInvDestContext                Counter32,
        starPCFDiscLcpOptFail                    Counter32,
        starPCFDiscIpcpOptFail                   Counter32,
        starPCFDiscIpv6cpOptFail                 Counter32,
        starPCFDiscNoRemIpAddr                   Counter32,
        starPCFDiscDetectionFail                 Counter32,
        starPCFDiscMisc                          Counter32,
        starPCFCurrentSessions                   Gauge32,
        starPCFSessionsSetup                     Counter32,
        starPCFSessionsRelsese                   Counter32,
        starPCFCurrentRevaSessions               Gauge32,
        starPCFRevaSessionsSetup                 Counter32,
        starPCFRevaSessionsRelsese               Counter32 
    }

starPCFSvcID OBJECT-TYPE
    SYNTAX    StarShortID 
    MAX-ACCESS not-accessible
    STATUS     current
    DESCRIPTION
	"The service identification is made up from first 8 chars of context name
	 and first 8 chars of service name separated by (:), with the lengh of this
	 structure at the beginning"
    ::= { starPCFEntry 1 }

starPCFIpAddr OBJECT-TYPE
    SYNTAX     IpAddress
    MAX-ACCESS not-accessible 
    STATUS     current
    DESCRIPTION
	"The PCF IP address"
    ::= { starPCFEntry 2 }

starPCFVpnID OBJECT-TYPE
    SYNTAX     Gauge32
    MAX-ACCESS read-only 
    STATUS     current
    DESCRIPTION
	"The internal identification of the VPN (context)"
    ::= { starPCFEntry 3 }

starPCFVpnName OBJECT-TYPE
    SYNTAX     DisplayString
    MAX-ACCESS read-only
    STATUS     current
    DESCRIPTION
        "The VPN (context) name"
    ::= { starPCFEntry 4 }

starPCFServName OBJECT-TYPE
    SYNTAX     DisplayString
    MAX-ACCESS read-only
    STATUS     current
    DESCRIPTION
        "The name of this service"
    ::= { starPCFEntry 5 }

starPCFRrqRcvd OBJECT-TYPE
    SYNTAX    Counter32 
    MAX-ACCESS read-only
    STATUS     current
    DESCRIPTION
        "Number of rrq received"
    ::= { starPCFEntry 6 }

starPCFRrqAccepted OBJECT-TYPE
    SYNTAX     Counter32
    MAX-ACCESS read-only
    STATUS     current
    DESCRIPTION
        "Number of rrq accepted"
    ::= { starPCFEntry 7 }

starPCFRrqDenied OBJECT-TYPE
    SYNTAX     Counter32
    MAX-ACCESS read-only
    STATUS     current
    DESCRIPTION
        "Number of rrq denied"
    ::= { starPCFEntry 8 }

starPCFRrqDiscarded OBJECT-TYPE
    SYNTAX     Counter32
    MAX-ACCESS read-only
    STATUS     current
    DESCRIPTION
        "Number of rrq discarded"
    ::= { starPCFEntry 9 }

starPCFInitialRrqRcvd OBJECT-TYPE
    SYNTAX     Counter32
    MAX-ACCESS read-only
    STATUS     current
    DESCRIPTION
        "Initial rrq received"
    ::= { starPCFEntry 10 }

starPCFInitialRrqAccepted OBJECT-TYPE
    SYNTAX     Counter32
    MAX-ACCESS read-only
    STATUS     current
    DESCRIPTION
        "Initial rrq accepted"
    ::= { starPCFEntry 11 }

starPCFIntraPDSNActiveHORrqAccepted OBJECT-TYPE
    SYNTAX     Counter32
    MAX-ACCESS read-only
    STATUS     current
    DESCRIPTION
        "Intra PDSN active handoff rrq accepted"
    ::= { starPCFEntry 12 }

starPCFIntraPDSNDormantHORrqAccepted OBJECT-TYPE
    SYNTAX     Counter32
    MAX-ACCESS read-only
    STATUS     current
    DESCRIPTION
        "Intra PDSN dormant handoff rrq accepted"
    ::= { starPCFEntry 13 }

starPCFInterPDSNHORrqAccepted OBJECT-TYPE
    SYNTAX     Counter32
    MAX-ACCESS read-only
    STATUS     current
    DESCRIPTION
        "Inter PDSN handoff rrq accpted"
    ::= { starPCFEntry 14 }

starPCFInitialRrqDenied OBJECT-TYPE
    SYNTAX     Counter32
    MAX-ACCESS read-only
    STATUS     current
    DESCRIPTION
        "Intial rrq denied"
    ::= { starPCFEntry 15 }

starPCFInitialRrqDiscarded OBJECT-TYPE
    SYNTAX     Counter32
    MAX-ACCESS read-only
    STATUS     current
    DESCRIPTION
        "Intial rrq discarded"
    ::= { starPCFEntry 16 }

starPCFRenewRrqRcvd OBJECT-TYPE
    SYNTAX     Counter32
    MAX-ACCESS read-only
    STATUS     current
    DESCRIPTION
        "Renew rrq received"
    ::= { starPCFEntry 17 }

starPCFRenewRrqAccepted OBJECT-TYPE
    SYNTAX     Counter32
    MAX-ACCESS read-only
    STATUS     current
    DESCRIPTION
        "Renew rrq accepted"
    ::= { starPCFEntry 18 }

starPCFRenewActiveRrqAccepted OBJECT-TYPE
    SYNTAX     Counter32
    MAX-ACCESS read-only
    STATUS     current
    DESCRIPTION
        "Renew active rrq accepted"
    ::= { starPCFEntry 19 }

starPCFRenewDormantRrqAccepted OBJECT-TYPE
    SYNTAX     Counter32
    MAX-ACCESS read-only
    STATUS     current
    DESCRIPTION
        "Renew dormant rrq accepted"
    ::= { starPCFEntry 20 }

starPCFRenewRrqDenied OBJECT-TYPE
    SYNTAX     Counter32
    MAX-ACCESS read-only
    STATUS     current
    DESCRIPTION
        "Renew rrq denied"
    ::= { starPCFEntry 21 }

starPCFRenewRrqDiscarded OBJECT-TYPE
    SYNTAX     Counter32
    MAX-ACCESS read-only
    STATUS     current
    DESCRIPTION
        "Renew rrq discarded"
    ::= { starPCFEntry 22 }

starPCFDeregRrqRcvd OBJECT-TYPE
    SYNTAX     Counter32
    MAX-ACCESS read-only
    STATUS     current
    DESCRIPTION
        "Deregistration rrq received"
    ::= { starPCFEntry 23 }

starPCFDeregRrqAccepted OBJECT-TYPE
    SYNTAX     Counter32
    MAX-ACCESS read-only
    STATUS     current
    DESCRIPTION
        "Deregistration rrq accepted"
    ::= { starPCFEntry 24 }

starPCFDeregDormantRrqAccepted OBJECT-TYPE
    SYNTAX     Counter32
    MAX-ACCESS read-only
    STATUS     current
    DESCRIPTION
        "Deregistration dormant rrq accepted"
    ::= { starPCFEntry 25 }

starPCFDeregRrqDenied OBJECT-TYPE
    SYNTAX     Counter32
    MAX-ACCESS read-only
    STATUS     current
    DESCRIPTION
        "Deregistration rrq denied"
    ::= { starPCFEntry 26 }

starPCFDeregRrqDiscarded OBJECT-TYPE
    SYNTAX     Counter32
    MAX-ACCESS read-only
    STATUS     current
    DESCRIPTION
        "Deregistration rrq discarded"
    ::= { starPCFEntry 27 }

starPCFIntraPDSNActiveAnidHORrqAccepted OBJECT-TYPE
    SYNTAX     Counter32
    MAX-ACCESS read-only
    STATUS     current
    DESCRIPTION
        "Intra PDSN active anid handoff rrq accepted"
    ::= { starPCFEntry 28 }

starPCFIntraPDSNDormantAnidHORrqAccepted OBJECT-TYPE
    SYNTAX     Counter32
    MAX-ACCESS read-only
    STATUS     current
    DESCRIPTION
        "Intra PDSN dormant anidhandoff rrq accepted"
    ::= { starPCFEntry 29 }

starPCFDeniedUnSpeReason OBJECT-TYPE
    SYNTAX     Counter32
    MAX-ACCESS read-only
    STATUS     current
    DESCRIPTION
        "Denied unspecified reason"
    ::= { starPCFEntry 30 }

starPCFDeniedAdmProh OBJECT-TYPE
    SYNTAX     Counter32
    MAX-ACCESS read-only
    STATUS     current
    DESCRIPTION
        "Denied admin prohibited"
    ::= { starPCFEntry 31 }

starPCFDeniedInsufResource OBJECT-TYPE
    SYNTAX     Counter32
    MAX-ACCESS read-only
    STATUS     current
    DESCRIPTION
        "Denied insufficient resources"
    ::= { starPCFEntry 32 }

starPCFDeniedMobNodeAuthFail OBJECT-TYPE
    SYNTAX     Counter32
    MAX-ACCESS read-only
    STATUS     current
    DESCRIPTION
        "Denied mobile node authentication failure"
    ::= { starPCFEntry 33 }

starPCFDeniedIdentMismatch OBJECT-TYPE
    SYNTAX     Counter32
    MAX-ACCESS read-only
    STATUS     current
    DESCRIPTION
        "Denied identification mismatch"
    ::= { starPCFEntry 34 }

starPCFDeniedPoorFormedReq OBJECT-TYPE
    SYNTAX     Counter32
    MAX-ACCESS read-only
    STATUS     current
    DESCRIPTION
        "Denied poor formed request"
    ::= { starPCFEntry 35 }

starPCFDeniedUnknownPDSNAddr OBJECT-TYPE
    SYNTAX     Counter32
    MAX-ACCESS read-only
    STATUS     current
    DESCRIPTION
        "Denied unknown PDSN address"
    ::= { starPCFEntry 36 }

starPCFDeniedRevTunnelUnavail OBJECT-TYPE
    SYNTAX     Counter32
    MAX-ACCESS read-only
    STATUS     current
    DESCRIPTION
        "Denied rev tunnel unavilable"
    ::= { starPCFEntry 37 }

starPCFDeniedRevTunnelRequire OBJECT-TYPE
    SYNTAX     Counter32
    MAX-ACCESS read-only
    STATUS     current
    DESCRIPTION
        "Denied rev tunnel required"
    ::= { starPCFEntry 38 }

starPCFDeniedUnrecogVendorId OBJECT-TYPE
    SYNTAX     Counter32
    MAX-ACCESS read-only
    STATUS     current
    DESCRIPTION
        "Denied unrecognized vendor id"
    ::= { starPCFEntry 39 }

starPCFDeniedSessionClosed OBJECT-TYPE
    SYNTAX     Counter32
    MAX-ACCESS read-only
    STATUS     current
    DESCRIPTION
        "Denied session closed"
    ::= { starPCFEntry 40 }

starPCFDeniedBsnSessionInfoUnavail OBJECT-TYPE
    SYNTAX     Counter32
    MAX-ACCESS read-only
    STATUS     current
    DESCRIPTION
        "Denied bsn session information unavilable"
    ::= { starPCFEntry 41 }

starPCFRegUpdTransmitted OBJECT-TYPE
    SYNTAX     Counter32
    MAX-ACCESS read-only
    STATUS     current
    DESCRIPTION
        "Registration updates transmitted"
    ::= { starPCFEntry 42 }

starPCFRegUpdAccepted OBJECT-TYPE
    SYNTAX     Counter32
    MAX-ACCESS read-only
    STATUS     current
    DESCRIPTION
        "Registration updates accepted"
    ::= { starPCFEntry 43 }

starPCFRegUpdateRpLifetimeExpiry OBJECT-TYPE
    SYNTAX     Counter32
    MAX-ACCESS read-only
    STATUS     current
    DESCRIPTION
        "Registration update rp life time expiry"
    ::= { starPCFEntry 44 }

starPCFRegUpdateUpperLayerIntiated OBJECT-TYPE
    SYNTAX     Counter32
    MAX-ACCESS read-only
    STATUS     current
    DESCRIPTION
        "Registration update upper layer intiated"
    ::= { starPCFEntry 45 }

starPCFRegUpdateOtherReason OBJECT-TYPE
    SYNTAX     Counter32
    MAX-ACCESS read-only
    STATUS     current
    DESCRIPTION
        "Registration update other reason"
    ::= { starPCFEntry 46 }

starPCFRegUpdateHORelease OBJECT-TYPE
    SYNTAX     Counter32
    MAX-ACCESS read-only
    STATUS     current
    DESCRIPTION
        "Registration update handoff release"
    ::= { starPCFEntry 47 }

starPCFRegUpdateSessmgrDied OBJECT-TYPE
    SYNTAX     Counter32
    MAX-ACCESS read-only
    STATUS     current
    DESCRIPTION
        "Registration update sessmgr denied "
    ::= { starPCFEntry 48 }

starPCFAuxA10ConnectionsSetup OBJECT-TYPE
    SYNTAX     Counter32
    MAX-ACCESS read-only
    STATUS     current
    DESCRIPTION
        "Aux a10 connections setup"
    ::= { starPCFEntry 49 }

starPCFSessionsDenied OBJECT-TYPE
    SYNTAX     Counter32
    MAX-ACCESS read-only
    STATUS     current
    DESCRIPTION
        "Number of sessions denied"
    ::= { starPCFEntry 50 }

starPCFSessionsInit OBJECT-TYPE
    SYNTAX     Counter32
    MAX-ACCESS read-only
    STATUS     current
    DESCRIPTION
        "Number of sessions initiated"
    ::= { starPCFEntry 51 }

starPCFSessionsReneg OBJECT-TYPE
    SYNTAX     Counter32
    MAX-ACCESS read-only
    STATUS     current
    DESCRIPTION
        "Number of PCF sessions renegotiated"
    ::= { starPCFEntry 52 }

starPCFDiscLcpRemote OBJECT-TYPE
    SYNTAX     Counter32
    MAX-ACCESS read-only
    STATUS     current
    DESCRIPTION
        "Disconnect reason lcp remote"
    ::= { starPCFEntry 53 }

starPCFDiscRpRemote OBJECT-TYPE
    SYNTAX     Counter32
    MAX-ACCESS read-only
    STATUS     current
    DESCRIPTION
        "Disconnect reason rp remote"
    ::= { starPCFEntry 54 }

starPCFDiscRpLocal OBJECT-TYPE
    SYNTAX     Counter32
    MAX-ACCESS read-only
    STATUS     current
    DESCRIPTION
        "Disconnect reason rp local"
    ::= { starPCFEntry 55 }

starPCFDiscMaxIpcpRetr OBJECT-TYPE
    SYNTAX     Counter32
    MAX-ACCESS read-only
    STATUS     current
    DESCRIPTION
        "Disconnect reason ppp maximum ipcp retries"
    ::= { starPCFEntry 56 }

starPCFDiscMaxIpv6cpRetr OBJECT-TYPE
    SYNTAX     Counter32
    MAX-ACCESS read-only
    STATUS     current
    DESCRIPTION
        "Disconnect reason max ipv6cp retries"
    ::= { starPCFEntry 57 }

starPCFDiscMaxLcpRetr OBJECT-TYPE
    SYNTAX     Counter32
    MAX-ACCESS read-only
    STATUS     current
    DESCRIPTION
        "Disconnect reason max lcp retries"
    ::= { starPCFEntry 58 }

starPCFDiscAuthFail OBJECT-TYPE
    SYNTAX     Counter32
    MAX-ACCESS read-only
    STATUS     current
    DESCRIPTION
        "Disconnect reason authentication failure"
    ::= { starPCFEntry 59 }

starPCFDiscSessSetupTimeout OBJECT-TYPE
    SYNTAX     Counter32
    MAX-ACCESS read-only
    STATUS     current
    DESCRIPTION
        "Disconnect reason session setup timeout"
    ::= { starPCFEntry 60 }

starPCFDiscFlowAddFail OBJECT-TYPE
    SYNTAX     Counter32
    MAX-ACCESS read-only
    STATUS     current
    DESCRIPTION
        "Disconnect reason flow add failure"
    ::= { starPCFEntry 61 }

starPCFDiscInvDestContext OBJECT-TYPE
    SYNTAX     Counter32
    MAX-ACCESS read-only
    STATUS     current
    DESCRIPTION
        "Disconnect reason invalid destination context"
    ::= { starPCFEntry 62 }

starPCFDiscLcpOptFail OBJECT-TYPE
    SYNTAX     Counter32
    MAX-ACCESS read-only
    STATUS     current
    DESCRIPTION
        "Disconnect reason lcp option failure"
    ::= { starPCFEntry 63 }

starPCFDiscIpcpOptFail OBJECT-TYPE
    SYNTAX     Counter32
    MAX-ACCESS read-only
    STATUS     current
    DESCRIPTION
        "Disconnect reason lcp option failure"
    ::= { starPCFEntry 64 }

starPCFDiscIpv6cpOptFail OBJECT-TYPE
    SYNTAX     Counter32
    MAX-ACCESS read-only
    STATUS     current
    DESCRIPTION
        "Disconnect reason ipv6cp option failure"
    ::= { starPCFEntry 65 }

starPCFDiscNoRemIpAddr OBJECT-TYPE
    SYNTAX     Counter32
    MAX-ACCESS read-only
    STATUS     current
    DESCRIPTION
        "Disconnect reason no ip remote ip address"
    ::= { starPCFEntry 66 }

starPCFDiscDetectionFail OBJECT-TYPE
    SYNTAX     Counter32
    MAX-ACCESS read-only
    STATUS     current
    DESCRIPTION
        "Disconnect reason detection failure"
    ::= { starPCFEntry 67 }

starPCFDiscMisc OBJECT-TYPE
    SYNTAX     Counter32
    MAX-ACCESS read-only
    STATUS     current
    DESCRIPTION
        "Disconnect reason misallaneous"
    ::= { starPCFEntry 68 }

starPCFCurrentSessions OBJECT-TYPE
    SYNTAX     Gauge32 
    MAX-ACCESS read-only
    STATUS     current
    DESCRIPTION
        "Current sessions"
    ::= { starPCFEntry 69 }

starPCFSessionsSetup OBJECT-TYPE
    SYNTAX     Counter32
    MAX-ACCESS read-only
    STATUS     current
    DESCRIPTION
        "Session setup"
    ::= { starPCFEntry 70 }

starPCFSessionsRelsese OBJECT-TYPE
    SYNTAX     Counter32
    MAX-ACCESS read-only
    STATUS     current
    DESCRIPTION
        "Sessions release"
    ::= { starPCFEntry 71 }

starPCFCurrentRevaSessions OBJECT-TYPE
    SYNTAX     Gauge32 
    MAX-ACCESS read-only
    STATUS     current
    DESCRIPTION
        "Current reva sessions"
    ::= { starPCFEntry 72 }

starPCFRevaSessionsSetup OBJECT-TYPE
    SYNTAX     Counter32
    MAX-ACCESS read-only
    STATUS     current
    DESCRIPTION
        "Reva session setup"
    ::= { starPCFEntry 73 }

starPCFRevaSessionsRelsese OBJECT-TYPE
    SYNTAX     Counter32
    MAX-ACCESS read-only
    STATUS     current
    DESCRIPTION
        "Reva session release"
    ::= { starPCFEntry 74 }

-- SIP Route Server
-- These objects are defined only for use in traps

starentSIPRouteServer OBJECT IDENTIFIER ::= { starentMIBObjects 40 }

starSIPRouteServerTable OBJECT-TYPE
   SYNTAX     SEQUENCE OF StarSIPRouteServerEntry
   MAX-ACCESS not-accessible
   STATUS     current
   DESCRIPTION
         "A table containing SIPRouteServer related information"
   ::= { starentSIPRouteServer 1}

starSIPRouteServerEntry OBJECT-TYPE
   SYNTAX     StarSIPRouteServerEntry
   MAX-ACCESS not-accessible
   STATUS     current
   DESCRIPTION
      "The statistics for a specific SIPRouteServer"
   INDEX { starSIPRouteServerVpnID }
   ::= { starSIPRouteServerTable 1 }

StarSIPRouteServerEntry ::=
    SEQUENCE {
     starSIPRouteServerVpnID             Gauge32,
     starSIPRouteServerVpnName           DisplayString,
     starSIPRouteServerVmgName           DisplayString,
     starSIPRouteServerAsName            DisplayString,
     starSIPRouteServerIpAddr	      IpAddress
         }

starSIPRouteServerVpnID OBJECT-TYPE
   SYNTAX     Gauge32
   MAX-ACCESS not-accessible
   STATUS     current
   DESCRIPTION
         "The internal identification of the VPN (context)"
   ::= { starSIPRouteServerEntry 1 }


starSIPRouteServerVpnName OBJECT-TYPE
    SYNTAX     DisplayString
    MAX-ACCESS read-only
    STATUS     current
    DESCRIPTION
         "The name of this VPN (context)"
   ::= { starSIPRouteServerEntry 2 }

starSIPRouteServerVmgName OBJECT-TYPE
   SYNTAX     DisplayString
   MAX-ACCESS read-only
   STATUS     current
   DESCRIPTION
         "The name of this VMG (context)"
   ::= { starSIPRouteServerEntry 3 }

starSIPRouteServerAsName OBJECT-TYPE
   SYNTAX     DisplayString
   MAX-ACCESS read-only
   STATUS     current
   DESCRIPTION
         "The name of this AS (context)"
   ::= { starSIPRouteServerEntry 4 }

starSIPRouteServerIpAddr OBJECT-TYPE
   SYNTAX     IpAddress
   MAX-ACCESS read-only
   STATUS     current
   DESCRIPTION
         "The Sip Route Server IP Address"
   ::= { starSIPRouteServerEntry 5 }


-- VIM Service
-- These objects are defined only for use in traps

starentVIMService OBJECT IDENTIFIER ::= { starentMIBObjects 41 }

starVIMServiceTable OBJECT-TYPE
   SYNTAX     SEQUENCE OF StarVIMServiceEntry
   MAX-ACCESS not-accessible
   STATUS     current
   DESCRIPTION
         "A table containing VIM's Service related information"
   ::= { starentVIMService 1 }

starVIMServiceEntry OBJECT-TYPE
   SYNTAX     StarVIMServiceEntry
   MAX-ACCESS not-accessible
   STATUS     current
   DESCRIPTION
      "The statistics for a specific VIM's Service"
   INDEX { starVIMServiceVpnID, starVIMServiceInstanceId }
   ::= { starVIMServiceTable 1 }

StarVIMServiceEntry ::=
    SEQUENCE {
     starVIMServiceVpnID                   Gauge32,
     starVIMServiceVpnName                 DisplayString,
     starVIMServiceInstanceId              Unsigned32,
     starVIMServiceFMDMaxCallRate          Unsigned32,
     starVIMServiceFMDContinuousLoadCount  Unsigned32
         }

starVIMServiceVpnID OBJECT-TYPE
   SYNTAX     Gauge32
   MAX-ACCESS not-accessible
   STATUS     current
   DESCRIPTION
         "The internal identification of the VPN (context)"
   ::= { starVIMServiceEntry 1 }


starVIMServiceVpnName OBJECT-TYPE
    SYNTAX     DisplayString
    MAX-ACCESS read-only
    STATUS     current
    DESCRIPTION
         "The name of this VPN (context)"
   ::= { starVIMServiceEntry 2 }

starVIMServiceInstanceId OBJECT-TYPE
   SYNTAX     Unsigned32
   MAX-ACCESS accessible-for-notify
   STATUS     current
   DESCRIPTION
         "The VIM Instance ID"
   ::= { starVIMServiceEntry 3 }

starVIMServiceFMDMaxCallRate OBJECT-TYPE
   SYNTAX     Unsigned32
   UNITS      "Calls per minute"
   MAX-ACCESS read-only
   STATUS     current
   DESCRIPTION
         "Configured FMD max call rate"
   ::= { starVIMServiceEntry 4 }

starVIMServiceFMDContinuousLoadCount OBJECT-TYPE
   SYNTAX     Unsigned32
   MAX-ACCESS read-only
   STATUS     current
   DESCRIPTION
         "Configured FMD continuous load count"
   ::= { starVIMServiceEntry 5 }

-- GTPP Storage Server, used for traps only
-- The GTPP Storage Server is an external entity, but the ST-16/ST-40 reports notifications
-- on its behalf

starentGSS OBJECT IDENTIFIER ::= { starentMIBObjects 42 }

starGSSClusterName OBJECT-TYPE
    SYNTAX      DisplayString
    MAX-ACCESS  accessible-for-notify
    STATUS      current
    DESCRIPTION
	"The name of the Storage Server Cluster"
    ::= { starentGSS 1 }

starGSSClusterNodeName OBJECT-TYPE
    SYNTAX      DisplayString
    MAX-ACCESS  accessible-for-notify
    STATUS      current
    DESCRIPTION
	"The name of a node within a Storage Server Cluster"
    ::= { starentGSS 2 }

starGSSClusterRgName OBJECT-TYPE
    SYNTAX      DisplayString
    MAX-ACCESS  accessible-for-notify
    STATUS      current
    DESCRIPTION
	"Resource Group"
    ::= { starentGSS 3 }

starGSSClusterRsName OBJECT-TYPE
    SYNTAX      DisplayString
    MAX-ACCESS  accessible-for-notify
    STATUS      current
    DESCRIPTION
	"Resource Name"
    ::= { starentGSS 4 }

starGSSClusterNodeState OBJECT-TYPE
    SYNTAX      DisplayString
    MAX-ACCESS  accessible-for-notify
    STATUS      current
    DESCRIPTION
	" "
    ::= { starentGSS 5 }

starGSSClusterPrevOnlineNode OBJECT-TYPE
    SYNTAX      DisplayString
    MAX-ACCESS  accessible-for-notify
    STATUS      current
    DESCRIPTION
	" "
    ::= { starentGSS 6 }

starGSSClusterFromNode OBJECT-TYPE
    SYNTAX      DisplayString
    MAX-ACCESS  accessible-for-notify
    STATUS      current
    DESCRIPTION
	" "
    ::= { starentGSS 7 }

starGSSClusterToNode OBJECT-TYPE
    SYNTAX      DisplayString
    MAX-ACCESS  accessible-for-notify
    STATUS      current
    DESCRIPTION
	" "
    ::= { starentGSS 8 }

starGSSDiskPath OBJECT-TYPE
    SYNTAX      DisplayString
    MAX-ACCESS  accessible-for-notify
    STATUS      current
    DESCRIPTION
	" "
    ::= { starentGSS 9 }

starGSSTransportPath OBJECT-TYPE
    SYNTAX      DisplayString
    MAX-ACCESS  accessible-for-notify
    STATUS      current
    DESCRIPTION
	" "
    ::= { starentGSS 10 }

starGSSIPMPGroupName OBJECT-TYPE
    SYNTAX      DisplayString
    MAX-ACCESS  accessible-for-notify
    STATUS      current
    DESCRIPTION
	" "
    ::= { starentGSS 11 }

starGSSInterfaceName OBJECT-TYPE
    SYNTAX      DisplayString
    MAX-ACCESS  accessible-for-notify
    STATUS      current
    DESCRIPTION
	" "
    ::= { starentGSS 12 }

--

starentPDIFSys OBJECT IDENTIFIER ::= { starentMIBObjects 43 }

starPDIFSysStatus OBJECT-TYPE
    SYNTAX     INTEGER {
		 unknown(0),
		 noservice(1),
		 active(2),
		 temporary(3),
		 outofservice(4)
	       }
    MAX-ACCESS read-only
    STATUS     current
    DESCRIPTION
	"The overall status of the chassis as a PDIF service.  A value of noservice(1) means that
	 the chassis is not configured/licensed for PDIF; active(2) indicates that at least one
	 PDIF service is available for processing sessions; temporary(3) indicates that PDIF is
	 running in a temporary capacity, such as running in standby mode during an online
	 upgrade; outofservice(4) indicates that no PDIF service is currently active,
	 but one or more PDIF services are configured"
    ::= { starentPDIFSys 1 }

starPDIFSysNumService OBJECT-TYPE
    SYNTAX	Unsigned32
    UNITS       "Services"
    MAX-ACCESS  read-only
    STATUS	current
    DESCRIPTION
	"The number of PDIF services configured"
    ::= { starentPDIFSys 2 }

starPDIFSysSessCurrent OBJECT-TYPE
    SYNTAX	Gauge32
    MAX-ACCESS	read-only
    STATUS	current
    DESCRIPTION
	"The number of current PDIF sessions for this chassis"
    ::= { starentPDIFSys 3 }

starPDIFSysSessCurrActive OBJECT-TYPE
    SYNTAX	Gauge32
    MAX-ACCESS	read-only
    STATUS	current
    DESCRIPTION
	"The number of currently active PDIF sessions for this chassis"
    ::= { starentPDIFSys 4 }

starPDIFSysSessCurrDormant OBJECT-TYPE
    SYNTAX	Gauge32
    MAX-ACCESS	read-only
    STATUS	current
    DESCRIPTION
	"The number of currently dormant PDIF sessions for this chassis"
    ::= { starentPDIFSys 5 }

starPDIFSysSessTtlSetup OBJECT-TYPE
    SYNTAX	Counter32
    MAX-ACCESS  read-only
    STATUS      current
    DESCRIPTION
	"The cumulative total number of PDIF sessions that has been setup"
    ::= { starentPDIFSys 6 }

starPDIFSysChildSACurrent OBJECT-TYPE
    SYNTAX	Gauge32
    MAX-ACCESS	read-only
    STATUS	current
    DESCRIPTION
	"The number of current PDIF child SAs for this chassis"
    ::= { starentPDIFSys 7 }

--

starentPDIFService OBJECT IDENTIFIER ::= { starentMIBObjects 44 }

starPDIFTable OBJECT-TYPE
    SYNTAX	SEQUENCE OF StarPDIFEntry
    MAX-ACCESS  not-accessible
    STATUS      current
    DESCRIPTION
	"A table of per-service PDIF information"
    ::= { starentPDIFService 1 }

starPDIFEntry OBJECT-TYPE
    SYNTAX	StarPDIFEntry
    MAX-ACCESS  not-accessible
    STATUS      current
    DESCRIPTION
	"The information for a PDIF service"
    INDEX { IMPLIED starPDIFSvcID }
    ::= { starPDIFTable 1 }

StarPDIFEntry ::=
    SEQUENCE {
	starPDIFSvcID              	StarShortID,
	starPDIFVpnID              	Gauge32,
	starPDIFVpnName		   	DisplayString,
	starPDIFServName	   	DisplayString,
	starPDIFStatus		   	INTEGER,
	starPDIFSessCurrent	   	Gauge32,
	starPDIFSessRemain	   	Gauge32,
	starPDIFSessCurrentActive  	Gauge32,
	starPDIFSessCurrentDormant 	Gauge32,
	starPDIFSessCurrentIpv6Active	Gauge32,
	starPDIFSessCurrentIpv6Dormant	Gauge32,
	starPDIFSessCurrentIpv4Active	Gauge32,
	starPDIFSessCurrentIpv4Dormant	Gauge32,
	starPDIFBindIpAddress		IpAddress,
	starPDIFBindIpPort		Integer32,
	starPDIFBindSlot		Integer32,
	starPDIFBindPort		Integer32
	}

starPDIFSvcID OBJECT-TYPE
    SYNTAX	StarShortID
    MAX-ACCESS not-accessible
    STATUS     current
    DESCRIPTION
        "The service identification is made up from first 8 chars of context name
         and first 8 chars of service name separated by (:)"
    ::= { starPDIFEntry 1 }

starPDIFVpnID OBJECT-TYPE
    SYNTAX     Gauge32
    MAX-ACCESS read-only
    STATUS     current
    DESCRIPTION
        "The internal identification of the VPN (context).  Note that this identifier can change due to
	 configuration changes and/or the restart of the PDIF device; in general starPDIFVpnName should
	 be used to identify the VPN (context)"
    ::= { starPDIFEntry 2 }

starPDIFVpnName OBJECT-TYPE
    SYNTAX     DisplayString
    MAX-ACCESS read-only
    STATUS     current
    DESCRIPTION
        "The VPN (context) name"
    ::= { starPDIFEntry 3 }

starPDIFServName OBJECT-TYPE
    SYNTAX     DisplayString
    MAX-ACCESS read-only
    STATUS     current
    DESCRIPTION
        "The name of this service"
    ::= { starPDIFEntry 4 }

starPDIFStatus OBJECT-TYPE
    SYNTAX     INTEGER {
		 unknown(0),
		 inservice(1),
		 outofservice(2)
		}
    MAX-ACCESS read-only
    STATUS     current
    DESCRIPTION
	"The state of this PDIF service.  The value unknown(0) indicates that the
	 system is unable to determine the status; inservice(1) indicates that the
	 service is available for processing sessions; outofservice(2) indicates that
	 the service is configured, but unavailable, either due to operator action
	 or due to a fault."
    ::= { starPDIFEntry 5 }

starPDIFSessCurrent OBJECT-TYPE
    SYNTAX	Gauge32
    MAX-ACCESS	read-only
    STATUS	current
    DESCRIPTION
	"The number of current sessions for this PDIF service."
    ::= { starPDIFEntry 6 }

starPDIFSessRemain OBJECT-TYPE
    SYNTAX	Gauge32
    MAX-ACCESS	read-only
    STATUS	current
    DESCRIPTION
	"A count of the remaining capacity for this PDIF service, in terms
	 of sessions.  If a session limit is configured for this PDIF service,
	 starPDIFSessRemain will identify the difference between this limit
	 and starPDIFSessCurrent.  If no individual limit has been configured
	 for this service, starPDIFSessRemain will identify the remaining
	 capacity for the entire chassis.  Note that in this latter case,
	 the value for starPDIFSessRemain cannot be summed across multiple
	 services."
    ::= { starPDIFEntry 7 }

starPDIFSessCurrentActive OBJECT-TYPE
    SYNTAX	Gauge32
    MAX-ACCESS	read-only
    STATUS	current
    DESCRIPTION
	"The number of currently active sessions for this PDIF service"
    ::= { starPDIFEntry 8 }

starPDIFSessCurrentDormant OBJECT-TYPE
    SYNTAX	Gauge32
    MAX-ACCESS	read-only
    STATUS	current
    DESCRIPTION
	"The number of currently dormant sessions for this PDIF service.  Note that this value
	 will always be 0, as the current system does not identify PDIF sessions as dormant."
    ::= { starPDIFEntry 9 }

starPDIFSessCurrentIpv6Active OBJECT-TYPE
    SYNTAX	Gauge32
    MAX-ACCESS	read-only
    STATUS	current
    DESCRIPTION
	"The number of currently active IPv6 sessions for this PDIF service.  Note that this value
	 will always be 0, as the current system does not support IPv6 sessions."
    ::= { starPDIFEntry 10 }

starPDIFSessCurrentIpv6Dormant OBJECT-TYPE
    SYNTAX	Gauge32
    MAX-ACCESS	read-only
    STATUS	current
    DESCRIPTION
	"The number of currently dormant IPv6 sessions for this PDIF service.  Note that this value
	 will always be 0, as the current system does not support IPv6 sessions."
    ::= { starPDIFEntry 11 }

starPDIFSessCurrentIpv4Active OBJECT-TYPE
    SYNTAX	Gauge32
    MAX-ACCESS	read-only
    STATUS	current
    DESCRIPTION
	"The number of currently active IPv4 sessions for this PDIF service.  Note that all PDIF
	 sessions are currently identified as 'active', and the value for starPDIFSessCurrentIpv4Dormant
	 will always be zero."
    ::= { starPDIFEntry 12 }

starPDIFSessCurrentIpv4Dormant OBJECT-TYPE
    SYNTAX	Gauge32
    MAX-ACCESS	read-only
    STATUS	current
    DESCRIPTION
	"The number of currently dormant IPv4 sessions for this PDIF service.  Note that all PDIF
	 sessions are currently identified as 'active', so the value for starPDIFSessCurrentIPv4Dormant
	 will always be zero."
    ::= { starPDIFEntry 13 }

starPDIFBindIpAddress OBJECT-TYPE
    SYNTAX	IpAddress
    MAX-ACCESS  read-only
    STATUS	current
    DESCRIPTION
	"The bind IP address for this PDIF service"
    ::= { starPDIFEntry 14 }

starPDIFBindIpPort OBJECT-TYPE
    SYNTAX	Integer32
    MAX-ACCESS  read-only
    STATUS	current
    DESCRIPTION
	"The bind IP port for this PDIF service"
    ::= { starPDIFEntry 15 }

starPDIFBindSlot OBJECT-TYPE
    SYNTAX	Integer32
    MAX-ACCESS  read-only
    STATUS	current
    DESCRIPTION
	"The physical slot number for the physical port which holds the interface
	 bound to the starPDIFBindIpAddress address."
    ::= { starPDIFEntry 16 }

starPDIFBindPort OBJECT-TYPE
    SYNTAX	Integer32
    MAX-ACCESS  read-only
    STATUS	current
    DESCRIPTION
	"The physical port number for the physical port which holds the interface
	 bound to the starPDIFBindIpAddress address."
    ::= { starPDIFEntry 17 }

--PDG     - START


starentPDGSys OBJECT IDENTIFIER ::= { starentMIBObjects 62 }

starPDGSysStatus OBJECT-TYPE
    SYNTAX     INTEGER {
                 unknown(0),
                 noservice(1),
                 active(2),
                 temporary(3),
                 outofservice(4)
               }
    MAX-ACCESS read-only
    STATUS     current
    DESCRIPTION
        "The overall status of the chassis as a PDG service.  A value of noservice(1) means that
         the chassis is not configured/licensed for PDG; active(2) indicates that at least one
         PDG service is available for processing sessions; temporary(3) indicates that PDG is
         running in a temporary capacity, such as running in standby mode during an online
         upgrade; outofservice(4) indicates that no PDG service is currently active,
         but one or more PDG services are configured"
    ::= { starentPDGSys 1 }

starPDGSysNumService OBJECT-TYPE
    SYNTAX      Unsigned32
    UNITS       "Services"
    MAX-ACCESS  read-only
    STATUS      current
    DESCRIPTION
        "The number of PDG services configured"
    ::= { starentPDGSys 2 }

starPDGSysSessCurrent OBJECT-TYPE
    SYNTAX      Gauge32
    MAX-ACCESS  read-only
    STATUS      current
    DESCRIPTION
        "The number of current PDG sessions for this chassis"
    ::= { starentPDGSys 3 }

starPDGSysSessCurrActive OBJECT-TYPE
    SYNTAX      Gauge32
    MAX-ACCESS  read-only
    STATUS      current
    DESCRIPTION
        "The number of currently active PDG sessions for this chassis"
    ::= { starentPDGSys 4 }

starPDGSysSessCurrDormant OBJECT-TYPE
    SYNTAX      Gauge32
    MAX-ACCESS  read-only
    STATUS      current
    DESCRIPTION
        "The number of currently dormant PDG sessions for this chassis"
    ::= { starentPDGSys 5 }

starPDGSysSessTtlSetup OBJECT-TYPE
    SYNTAX      Counter32
    MAX-ACCESS  read-only
    STATUS      current
    DESCRIPTION
        "The cumulative total number of PDG sessions that has been setup"
    ::= { starentPDGSys 6 }

starPDGSysChildSACurrent OBJECT-TYPE
    SYNTAX      Gauge32
    MAX-ACCESS  read-only
    STATUS      current
    DESCRIPTION
        "The number of current PDG child SAs for this chassis"
    ::= { starentPDGSys 7 }



starentPDGService OBJECT IDENTIFIER ::= { starentMIBObjects 63 }

starPDGTable OBJECT-TYPE
    SYNTAX      SEQUENCE OF StarPDGEntry
    MAX-ACCESS  not-accessible
    STATUS      current
    DESCRIPTION
        "A table of per-service PDG information"
    ::= { starentPDGService 1 }

starPDGEntry OBJECT-TYPE
    SYNTAX      StarPDGEntry
    MAX-ACCESS  not-accessible
    STATUS      current
    DESCRIPTION
        "The information for a PDG service"
    INDEX { IMPLIED starPDGSvcID }
    ::= { starPDGTable 1 }

StarPDGEntry ::=
    SEQUENCE {
        starPDGSvcID                   StarShortID,
        starPDGVpnID                   Gauge32,
        starPDGVpnName                 DisplayString,
        starPDGServName                DisplayString,
        starPDGStatus                  INTEGER,
        starPDGSessCurrent             Gauge32,
        starPDGSessRemain              Gauge32,
        starPDGSessCurrentActive       Gauge32,
        starPDGSessCurrentDormant      Gauge32,
        starPDGSessCurrentIpv6Active   Gauge32,
        starPDGSessCurrentIpv6Dormant  Gauge32,
        starPDGSessCurrentIpv4Active   Gauge32,
        starPDGSessCurrentIpv4Dormant  Gauge32,
        starPDGBindIpAddress           IpAddress,
        starPDGBindIpPort              Integer32,
        starPDGBindSlot                Integer32,
        starPDGBindPort                Integer32
        }

starPDGSvcID OBJECT-TYPE
    SYNTAX      StarShortID
    MAX-ACCESS not-accessible
    STATUS     current
    DESCRIPTION
        "The service identification is made up from first 8 chars of context name
         and first 8 chars of service name separated by (:)"
    ::= { starPDGEntry 1 }

starPDGVpnID OBJECT-TYPE
    SYNTAX     Gauge32
    MAX-ACCESS read-only
    STATUS     current
    DESCRIPTION
        "The internal identification of the VPN (context).  Note that this identifier can change due to
         configuration changes and/or the restart of the PDG device; in general starPDGVpnName should
         be used to identify the VPN (context)"
    ::= { starPDGEntry 2 }

starPDGVpnName OBJECT-TYPE
    SYNTAX     DisplayString
    MAX-ACCESS read-only
    STATUS     current
    DESCRIPTION
        "The VPN (context) name"
    ::= { starPDGEntry 3 }

starPDGServName OBJECT-TYPE
    SYNTAX     DisplayString
    MAX-ACCESS read-only
    STATUS     current
    DESCRIPTION
        "The name of this service"
    ::= { starPDGEntry 4 }

starPDGStatus OBJECT-TYPE
    SYNTAX     INTEGER {
                 unknown(0),
                 inservice(1),
                 outofservice(2)
                }
    MAX-ACCESS read-only
    STATUS     current
    DESCRIPTION
        "The state of this PDG service.  The value unknown(0) indicates that the
         system is unable to determine the status; inservice(1) indicates that the
         service is available for processing sessions; outofservice(2) indicates that
         the service is configured, but unavailable, either due to operator action
         or due to a fault."
    ::= { starPDGEntry 5 }

starPDGSessCurrent OBJECT-TYPE
    SYNTAX      Gauge32
    MAX-ACCESS  read-only
    STATUS      current
    DESCRIPTION
        "The number of current sessions for this PDG service."
    ::= { starPDGEntry 6 }

starPDGSessRemain OBJECT-TYPE
    SYNTAX      Gauge32
    MAX-ACCESS  read-only
    STATUS      current
    DESCRIPTION
        "A count of the remaining capacity for this PDG service, in terms
         of sessions.  If a session limit is configured for this PDG service,
         starPDGSessRemain will identify the difference between this limit
         and starPDGSessCurrent.  If no individual limit has been configured
         for this service, starPDGSessRemain will identify the remaining
         capacity for the entire chassis.  Note that in this latter case,
         the value for starPDGSessRemain cannot be summed across multiple
         services."
    ::= { starPDGEntry 7 }

starPDGSessCurrentActive OBJECT-TYPE
    SYNTAX      Gauge32
    MAX-ACCESS  read-only
    STATUS      current
    DESCRIPTION
        "The number of currently active sessions for this PDG service"
    ::= { starPDGEntry 8 }

starPDGSessCurrentDormant OBJECT-TYPE
    SYNTAX      Gauge32
    MAX-ACCESS  read-only
    STATUS      current
    DESCRIPTION
        "The number of currently dormant sessions for this PDG service"
    ::= { starPDGEntry 9 }

starPDGSessCurrentIpv6Active OBJECT-TYPE
    SYNTAX      Gauge32
    MAX-ACCESS  read-only
    STATUS      current
    DESCRIPTION
        "The number of currently active IPv6 sessions for this PDG service.  Note that this value
         will always be 0, as the current system does not support IPv6 sessions."
    ::= { starPDGEntry 10 }

starPDGSessCurrentIpv6Dormant OBJECT-TYPE
    SYNTAX      Gauge32
    MAX-ACCESS  read-only
    STATUS      current
    DESCRIPTION
        "The number of currently dormant IPv6 sessions for this PDG service.  Note that this value
         will always be 0, as the current system does not support IPv6 sessions."
    ::= { starPDGEntry 11 }

starPDGSessCurrentIpv4Active OBJECT-TYPE
    SYNTAX      Gauge32
    MAX-ACCESS  read-only
    STATUS      current
    DESCRIPTION
        "The number of currently active IPv4 sessions for this PDG service.  Note that all PDG
         sessions are currently identified as 'active', and the value for starPDGSessCurrentIPv4Dormant
         will always be zero."
    ::= { starPDGEntry 12 }

starPDGSessCurrentIpv4Dormant OBJECT-TYPE
    SYNTAX      Gauge32
    MAX-ACCESS  read-only
    STATUS      current
    DESCRIPTION
        "The number of currently dormant IPv4 sessions for this PDG service.  Note that all PDG
         sessions are currently identified as 'active', so the value for starPDGSessCurrentIPv4Dormant
         will always be zero."
    ::= { starPDGEntry 13 }

starPDGBindIpAddress OBJECT-TYPE
    SYNTAX      IpAddress
    MAX-ACCESS  read-only
    STATUS      current
    DESCRIPTION
        "The bind IP address for this PDG service"
    ::= { starPDGEntry 14 }

starPDGBindIpPort OBJECT-TYPE
    SYNTAX      Integer32
    MAX-ACCESS  read-only
    STATUS      current
    DESCRIPTION
        "The bind IP port for this PDG service"
    ::= { starPDGEntry 15 }

starPDGBindSlot OBJECT-TYPE
    SYNTAX      Integer32
    MAX-ACCESS  read-only
    STATUS      current
    DESCRIPTION
        "The physical slot number for the physical port which holds the interface
         bound to the starPDGBindIpAddress address."
    ::= { starPDGEntry 16 }

starPDGBindPort OBJECT-TYPE
    SYNTAX      Integer32
    MAX-ACCESS  read-only
    STATUS      current
    DESCRIPTION
        "The physical port number for the physical port which holds the interface
         bound to the starPDGBindIpAddress address."
    ::= { starPDGEntry 17 }



  -- PDG End

  
  -- HNBGW  -START

 
starentHNBGWService OBJECT IDENTIFIER ::= { starentMIBObjects 65 }


starHNBGWServTable OBJECT-TYPE    
    SYNTAX      SEQUENCE OF StarHNBGWServEntry
    MAX-ACCESS  not-accessible
    STATUS      current
    DESCRIPTION
        "A table containing HNBGW related information"
    ::= { starentHNBGWService 1 }


starHNBGWServEntry OBJECT-TYPE
    SYNTAX     StarHNBGWServEntry
    MAX-ACCESS not-accessible
    STATUS     current
    DESCRIPTION
	"The statistics for a specific HNBGW service"
    INDEX { starHNBGWServVpnID, starHNBGWServSvcID }
    ::= { starHNBGWServTable 1 }


StarHNBGWServEntry ::=
    SEQUENCE {
	starHNBGWServVpnID      Gauge32,  
	starHNBGWServSvcID      Gauge32,
	starSessHNBGWVpnName    DisplayString,
	starSessHNBGWServName   DisplayString,
	starSessHNBGWCsNwName   DisplayString,    
	starSessHNBGWPsNwName   DisplayString,
	starSessHNBGWSgsnPtCd   Integer32,
	starSessHNBGWMscPtCd    Integer32
     }


starHNBGWServVpnID OBJECT-TYPE
    SYNTAX     Gauge32
    MAX-ACCESS not-accessible
    STATUS     current
    DESCRIPTION
        "The internal identification of the VPN (context)"
    ::= { starHNBGWServEntry 1 }



starHNBGWServSvcID OBJECT-TYPE
    SYNTAX     Gauge32
    MAX-ACCESS not-accessible
    STATUS     current
    DESCRIPTION
        "The internal identification of this service; unique within a specific context"
    ::= { starHNBGWServEntry 2 }



starSessHNBGWVpnName OBJECT-TYPE
    SYNTAX     DisplayString
    MAX-ACCESS read-only
    STATUS     current
    DESCRIPTION
        "The name of this VPN (context)"
    ::= { starHNBGWServEntry 3 }



starSessHNBGWServName OBJECT-TYPE
    SYNTAX     DisplayString
    MAX-ACCESS read-only
    STATUS     current
    DESCRIPTION
        "The name of this Service"
    ::= { starHNBGWServEntry 4 }


starSessHNBGWCsNwName OBJECT-TYPE
    SYNTAX     DisplayString
    MAX-ACCESS read-only
    STATUS     current
    DESCRIPTION
        "The name of the CS NW"
    ::= { starHNBGWServEntry 5 }


starSessHNBGWPsNwName OBJECT-TYPE
    SYNTAX     DisplayString
    MAX-ACCESS read-only
    STATUS     current
    DESCRIPTION
        "The name of the PS NW"
    ::= { starHNBGWServEntry 6 }


starSessHNBGWSgsnPtCd OBJECT-TYPE
    SYNTAX     Integer32
    MAX-ACCESS read-only
    STATUS     current
    DESCRIPTION
        "SGSN Point Code"
    ::= { starHNBGWServEntry 7 }


starSessHNBGWMscPtCd OBJECT-TYPE
    SYNTAX     Integer32
    MAX-ACCESS read-only
    STATUS     current
    DESCRIPTION
        "MSC Point Code"
    ::= { starHNBGWServEntry 8 }


--End of HNBGW Service



    -- ALCAP Service

starentALCAPService OBJECT IDENTIFIER ::= { starentMIBObjects 66 }


starALCAPServTable OBJECT-TYPE     
    SYNTAX     SEQUENCE OF StarALCAPServEntry
    MAX-ACCESS not-accessible
    STATUS     current
    DESCRIPTION
        "A table containing ALCAP relate information"
    ::= { starentALCAPService 1 }


starALCAPServEntry OBJECT-TYPE
    SYNTAX     StarALCAPServEntry
    MAX-ACCESS not-accessible
    STATUS     current
    DESCRIPTION
        "The statistics for a specific ALCAP service"
    INDEX { starALCAPSerVpnID, starALCAPSerSvcID }
    ::= { starALCAPServTable 1 }


StarALCAPServEntry ::=
    SEQUENCE {
	starALCAPSerVpnID          Gauge32,   
	starALCAPSerSvcID          Gauge32,
	starSessALCAPVpnName       DisplayString,
	starSessALCAPServName      DisplayString,
	starSessALCAPAAL2NodeName  DisplayString, 
	starSessALCAPPathId        Integer32
    }


starALCAPSerVpnID OBJECT-TYPE
    SYNTAX     Gauge32
    MAX-ACCESS not-accessible
    STATUS     current
    DESCRIPTION
        "The internal identification of the VPN (context)"
    ::= { starALCAPServEntry 1 }


starALCAPSerSvcID OBJECT-TYPE
    SYNTAX     Gauge32
    MAX-ACCESS not-accessible
    STATUS     current
    DESCRIPTION
        "The internal identification of this service; unique within a specific context"
    ::= { starALCAPServEntry 2 }


starSessALCAPVpnName OBJECT-TYPE
    SYNTAX     DisplayString
    MAX-ACCESS read-only
    STATUS     current
    DESCRIPTION
        "The name of this VPN (context)"
    ::= { starALCAPServEntry 3 }


starSessALCAPServName OBJECT-TYPE
    SYNTAX     DisplayString
    MAX-ACCESS read-only
    STATUS     current
    DESCRIPTION
        "The name of this Service"
    ::= { starALCAPServEntry 4 }


starSessALCAPAAL2NodeName OBJECT-TYPE
    SYNTAX     DisplayString
    MAX-ACCESS read-only
    STATUS     current
    DESCRIPTION
        "The name of the AAL2 Node"
    ::= { starALCAPServEntry 5 }


starSessALCAPPathId OBJECT-TYPE
    SYNTAX     Integer32
    MAX-ACCESS read-only
    STATUS     current
    DESCRIPTION
        "The path id of AAL2 path"
    ::= { starALCAPServEntry 6 }

 -- ALCAP END

--FNG     - START


starentFNGSys OBJECT IDENTIFIER ::= { starentMIBObjects 60 }

starFNGSysStatus OBJECT-TYPE
    SYNTAX     INTEGER {
                 unknown(0),
                 noservice(1),
                 active(2),
                 temporary(3),
                 outofservice(4)
               }
    MAX-ACCESS read-only
    STATUS     current
    DESCRIPTION
        "The overall status of the chassis as a FNG service.  A value of noservice(1) means that
         the chassis is not configured/licensed for FNG; active(2) indicates that at least one
         FNG service is available for processing sessions; temporary(3) indicates that FNG is
         running in a temporary capacity, such as running in standby mode during an online
         upgrade; outofservice(4) indicates that no FNG service is currently active,
         but one or more FNG services are configured"
    ::= { starentFNGSys 1 }

starFNGSysNumService OBJECT-TYPE
    SYNTAX      Unsigned32
    UNITS       "Services"
    MAX-ACCESS  read-only
    STATUS      current
    DESCRIPTION
        "The number of FNG services configured"
    ::= { starentFNGSys 2 }

starFNGSysSessCurrent OBJECT-TYPE
    SYNTAX      Gauge32
    MAX-ACCESS  read-only
    STATUS      current
    DESCRIPTION
        "The number of current FNG sessions for this chassis"
    ::= { starentFNGSys 3 }

starFNGSysSessCurrActive OBJECT-TYPE
    SYNTAX      Gauge32
    MAX-ACCESS  read-only
    STATUS      current
    DESCRIPTION
        "The number of currently active FNG sessions for this chassis"
    ::= { starentFNGSys 4 }

starFNGSysSessCurrDormant OBJECT-TYPE
    SYNTAX      Gauge32
    MAX-ACCESS  read-only
    STATUS      current
    DESCRIPTION
        "The number of currently dormant FNG sessions for this chassis"
    ::= { starentFNGSys 5 }

starFNGSysSessTtlSetup OBJECT-TYPE
    SYNTAX      Counter32
    MAX-ACCESS  read-only
    STATUS      current
    DESCRIPTION
        "The cumulative total number of FNG sessions that has been setup"
    ::= { starentFNGSys 6 }

starFNGSysChildSACurrent OBJECT-TYPE
    SYNTAX      Gauge32
    MAX-ACCESS  read-only
    STATUS      current
    DESCRIPTION
        "The number of current FNG child SAs for this chassis"
    ::= { starentFNGSys 7 }



starentFNGService OBJECT IDENTIFIER ::= { starentMIBObjects 61 }

starFNGTable OBJECT-TYPE
    SYNTAX      SEQUENCE OF StarFNGEntry
    MAX-ACCESS  not-accessible
    STATUS      current
    DESCRIPTION
        "A table of per-service FNG information"
    ::= { starentFNGService 1 }

starFNGEntry OBJECT-TYPE
    SYNTAX      StarFNGEntry
    MAX-ACCESS  not-accessible
    STATUS      current
    DESCRIPTION
        "The information for a FNG service"
    INDEX { IMPLIED starFNGSvcID }
    ::= { starFNGTable 1 }

StarFNGEntry ::=
    SEQUENCE {
        starFNGSvcID                   StarShortID,
        starFNGVpnID                   Gauge32,
        starFNGVpnName                 DisplayString,
        starFNGServName                DisplayString,
        starFNGStatus                  INTEGER,
        starFNGSessCurrent             Gauge32,
        starFNGSessRemain              Gauge32,
        starFNGSessCurrentActive       Gauge32,
        starFNGSessCurrentDormant      Gauge32,
        starFNGSessCurrentIpv6Active   Gauge32,
        starFNGSessCurrentIpv6Dormant  Gauge32,
        starFNGSessCurrentIpv4Active   Gauge32,
        starFNGSessCurrentIpv4Dormant  Gauge32,
        starFNGBindIpAddress           IpAddress,
        starFNGBindIpPort              Integer32,
        starFNGBindSlot                Integer32,
        starFNGBindPort                Integer32
        }

starFNGSvcID OBJECT-TYPE
    SYNTAX      StarShortID
    MAX-ACCESS not-accessible
    STATUS     current
    DESCRIPTION
        "The service identification is made up from first 8 chars of context name
         and first 8 chars of service name separated by (:)"
    ::= { starFNGEntry 1 }

starFNGVpnID OBJECT-TYPE
    SYNTAX     Gauge32
    MAX-ACCESS read-only
    STATUS     current
    DESCRIPTION
        "The internal identification of the VPN (context).  Note that this identifier can change due to
         configuration changes and/or the restart of the FNG device; in general starFNGVpnName should
         be used to identify the VPN (context)"
    ::= { starFNGEntry 2 }

starFNGVpnName OBJECT-TYPE
    SYNTAX     DisplayString
    MAX-ACCESS read-only
    STATUS     current
    DESCRIPTION
        "The VPN (context) name"
    ::= { starFNGEntry 3 }

starFNGServName OBJECT-TYPE
    SYNTAX     DisplayString
    MAX-ACCESS read-only
    STATUS     current
    DESCRIPTION
        "The name of this service"
    ::= { starFNGEntry 4 }

starFNGStatus OBJECT-TYPE
    SYNTAX     INTEGER {
                 unknown(0),
                 inservice(1),
                 outofservice(2)
                }
    MAX-ACCESS read-only
    STATUS     current
    DESCRIPTION
        "The state of this FNG service.  The value unknown(0) indicates that the
         system is unable to determine the status; inservice(1) indicates that the
         service is available for processing sessions; outofservice(2) indicates that
         the service is configured, but unavailable, either due to operator action
         or due to a fault."
    ::= { starFNGEntry 5 }

starFNGSessCurrent OBJECT-TYPE
    SYNTAX      Gauge32
    MAX-ACCESS  read-only
    STATUS      current
    DESCRIPTION
        "The number of current sessions for this FNG service."
    ::= { starFNGEntry 6 }

starFNGSessRemain OBJECT-TYPE
    SYNTAX      Gauge32
    MAX-ACCESS  read-only
    STATUS      current
    DESCRIPTION
        "A count of the remaining capacity for this FNG service, in terms
         of sessions.  If a session limit is configured for this FNG service,
         starFNGSessRemain will identify the difference between this limit
         and starFNGSessCurrent.  If no individual limit has been configured
         for this service, starFNGSessRemain will identify the remaining
         capacity for the entire chassis.  Note that in this latter case,
         the value for starFNGSessRemain cannot be summed across multiple
         services."
    ::= { starFNGEntry 7 }

starFNGSessCurrentActive OBJECT-TYPE
    SYNTAX      Gauge32
    MAX-ACCESS  read-only
    STATUS      current
    DESCRIPTION
        "The number of currently active sessions for this FNG service"
    ::= { starFNGEntry 8 }

starFNGSessCurrentDormant OBJECT-TYPE
    SYNTAX      Gauge32
    MAX-ACCESS  read-only
    STATUS      current
    DESCRIPTION
        "The number of currently dormant sessions for this FNG service"
    ::= { starFNGEntry 9 }

starFNGSessCurrentIpv6Active OBJECT-TYPE
    SYNTAX      Gauge32
    MAX-ACCESS  read-only
    STATUS      current
    DESCRIPTION
        "The number of currently active IPv6 sessions for this FNG service.  Note that this value
         will always be 0, as the current system does not support IPv6 sessions."
    ::= { starFNGEntry 10 }

starFNGSessCurrentIpv6Dormant OBJECT-TYPE
    SYNTAX      Gauge32
    MAX-ACCESS  read-only
    STATUS      current
    DESCRIPTION
        "The number of currently dormant IPv6 sessions for this FNG service.  Note that this value
         will always be 0, as the current system does not support IPv6 sessions."
    ::= { starFNGEntry 11 }

starFNGSessCurrentIpv4Active OBJECT-TYPE
    SYNTAX      Gauge32
    MAX-ACCESS  read-only
    STATUS      current
    DESCRIPTION
        "The number of currently active IPv4 sessions for this FNG service.  Note that all FNG
         sessions are currently identified as 'active', and the value for starFNGSessCurrentIPv4Dormant
         will always be zero."
    ::= { starFNGEntry 12 }

starFNGSessCurrentIpv4Dormant OBJECT-TYPE
    SYNTAX      Gauge32
    MAX-ACCESS  read-only
    STATUS      current
    DESCRIPTION
        "The number of currently dormant IPv4 sessions for this FNG service.  Note that all FNG
         sessions are currently identified as 'active', so the value for starFNGSessCurrentIPv4Dormant
         will always be zero."
    ::= { starFNGEntry 13 }

starFNGBindIpAddress OBJECT-TYPE
    SYNTAX      IpAddress
    MAX-ACCESS  read-only
    STATUS      current
    DESCRIPTION
        "The bind IP address for this FNG service"
    ::= { starFNGEntry 14 }

starFNGBindIpPort OBJECT-TYPE
    SYNTAX      Integer32
    MAX-ACCESS  read-only
    STATUS      current
    DESCRIPTION
        "The bind IP port for this FNG service"
    ::= { starFNGEntry 15 }

starFNGBindSlot OBJECT-TYPE
    SYNTAX      Integer32
    MAX-ACCESS  read-only
    STATUS      current
    DESCRIPTION
        "The physical slot number for the physical port which holds the interface
         bound to the starFNGBindIpAddress address."
    ::= { starFNGEntry 16 }

starFNGBindPort OBJECT-TYPE
    SYNTAX      Integer32
    MAX-ACCESS  read-only
    STATUS      current
    DESCRIPTION
        "The physical port number for the physical port which holds the interface
         bound to the starFNGBindIpAddress address."
    ::= { starFNGEntry 17 }



  -- FNG End


    -- SGSN
starentSGSNService OBJECT IDENTIFIER ::= { starentMIBObjects 45 }

starSGSNSerTable OBJECT-TYPE
    SYNTAX     SEQUENCE OF StarSGSNSerEntry
    MAX-ACCESS not-accessible
    STATUS     current
    DESCRIPTION
    "A table containing SGSN related information"
    ::= { starentSGSNService 1 }

starSGSNSerEntry OBJECT-TYPE
    SYNTAX     StarSGSNSerEntry
    MAX-ACCESS not-accessible
    STATUS     current
    DESCRIPTION
    "The statistics for a specific SGSN service"
    INDEX { starSGSNSerVpnID, starSGSNSerSvcID }
    ::= { starSGSNSerTable 1 }

StarSGSNSerEntry ::=
    SEQUENCE {
        starSGSNSerVpnID             Gauge32,
        starSGSNSerSvcID             Gauge32,
        starSessSGSNVpnName          DisplayString,
        starSessSGSNServName         DisplayString,
        starSessSGSNMcc              OCTET STRING,
        starSessSGSNMnc              OCTET STRING,
        starSessSGSNRncId            Gauge32,
        starSessSGSNHlrNum           OCTET STRING
    }

starSGSNSerVpnID OBJECT-TYPE
    SYNTAX     Gauge32
    MAX-ACCESS not-accessible
    STATUS     current
    DESCRIPTION
    "The internal identification of the VPN (context)"
    ::= { starSGSNSerEntry 1 }

starSGSNSerSvcID OBJECT-TYPE
    SYNTAX     Gauge32
    MAX-ACCESS not-accessible
    STATUS     current
    DESCRIPTION
    "The internal identification of this service; unique within a specific context"
    ::= { starSGSNSerEntry 2 }

starSessSGSNVpnName OBJECT-TYPE
    SYNTAX     DisplayString
    MAX-ACCESS read-only
    STATUS     current
    DESCRIPTION
    "The name of this VPN (context)"
    ::= { starSGSNSerEntry 3 }

starSessSGSNServName OBJECT-TYPE
    SYNTAX     DisplayString
    MAX-ACCESS read-only
    STATUS     current
    DESCRIPTION
    "The name of this service"
    ::= { starSGSNSerEntry 4 }

starSessSGSNMcc OBJECT-TYPE
    SYNTAX     OCTET STRING (SIZE (1..3))
    MAX-ACCESS read-only
    STATUS     current
    DESCRIPTION
    "Mobile Country Code"
    ::= { starSGSNSerEntry 5 }

starSessSGSNMnc OBJECT-TYPE
    SYNTAX     OCTET STRING (SIZE (1..3))
    MAX-ACCESS read-only
    STATUS     current
    DESCRIPTION
    "Mobile Network Code"
    ::= { starSGSNSerEntry 6 }

starSessSGSNRncId OBJECT-TYPE
    SYNTAX    Gauge32
    MAX-ACCESS read-only
    STATUS     current
    DESCRIPTION
    "The Id of the RNC "
    ::= { starSGSNSerEntry 7 }

starSessSGSNHlrNum OBJECT-TYPE
    SYNTAX     OCTET STRING (SIZE (1..16))
    MAX-ACCESS read-only
    STATUS     current
    DESCRIPTION
    "The Id of the HLR "
    ::= { starSGSNSerEntry 8 }


--SS7Rd

starentSS7Rd OBJECT IDENTIFIER ::= { starentMIBObjects 46 }

starSS7RdTable OBJECT-TYPE
    SYNTAX     SEQUENCE OF StarSS7RdEntry
    MAX-ACCESS not-accessible
    STATUS     current
    DESCRIPTION
    "A table containing SS7Rd related information"
    ::= { starentSS7Rd 1 }

starSS7RdEntry OBJECT-TYPE
    SYNTAX     StarSS7RdEntry
    MAX-ACCESS not-accessible
    STATUS     current
    DESCRIPTION
	"The statistics for a specific ss7rd "
    INDEX { starSS7rdId }
    ::= { starSS7RdTable 1 }

StarSS7RdEntry ::=
    SEQUENCE {
        starSS7rdId                     Gauge32,
        starSS7Pc                       Gauge32,
        starSS7M3UAPsId                 Gauge32,
        starSS7M3UAPspId                Gauge32,
        starSS7MTP3LinkSetId            Gauge32,
        starSS7MTP3LinkId               Gauge32,
        starSS7SCTPSelfAddr             IpAddress,
        starSS7SCTPPeerAddr             IpAddress,
        starSS7SCTPSelfPort             Gauge32,
        starSS7SCTPPeerPort             Gauge32,
        starSS7CongLevel                Gauge32,
        starSS7LocalCong                Gauge32,
	starSS7CauseString	        DisplayString
    }


starSS7rdId   OBJECT-TYPE
    SYNTAX     Gauge32
    MAX-ACCESS accessible-for-notify
    STATUS     current
    DESCRIPTION
    "SS7 Routing Domain identification"
    ::= { starSS7RdEntry 1 }

starSS7Pc OBJECT-TYPE
    SYNTAX     Gauge32
    MAX-ACCESS read-only
    STATUS     current
    DESCRIPTION
    "Point Code"
    ::= { starSS7RdEntry 2 }

starSS7M3UAPsId OBJECT-TYPE
    SYNTAX     Gauge32
    MAX-ACCESS read-only
    STATUS     current
    DESCRIPTION
    "Peer Server identification"
    ::= { starSS7RdEntry 3 }

starSS7M3UAPspId OBJECT-TYPE
    SYNTAX     Gauge32
    MAX-ACCESS read-only
    STATUS     current
    DESCRIPTION
    "Peer Server process identification"
    ::= { starSS7RdEntry 4 }

starSS7MTP3LinkSetId OBJECT-TYPE
    SYNTAX     Gauge32
    MAX-ACCESS read-only
    STATUS     current
    DESCRIPTION
    "MTP3 LinkSet Identifier"
    ::= { starSS7RdEntry 5 }

starSS7MTP3LinkId OBJECT-TYPE
    SYNTAX     Gauge32
    MAX-ACCESS read-only
    STATUS     current
    DESCRIPTION
    "MTP3 Link Identifier"
    ::= { starSS7RdEntry 6 }

starSS7SCTPSelfAddr OBJECT-TYPE
    SYNTAX     IpAddress
    MAX-ACCESS read-only
    STATUS     current
    DESCRIPTION
    "The self end point IP Address"
    ::= { starSS7RdEntry 7 }

starSS7SCTPPeerAddr OBJECT-TYPE
    SYNTAX     IpAddress
    MAX-ACCESS read-only
    STATUS     current
    DESCRIPTION
    "The IP Address of the PeerNode"
    ::= { starSS7RdEntry 8 }

starSS7SCTPSelfPort OBJECT-TYPE
    SYNTAX     Gauge32
    MAX-ACCESS read-only
    STATUS     current
    DESCRIPTION
    "The self end point sctp port"
    ::= { starSS7RdEntry 9 }

starSS7SCTPPeerPort OBJECT-TYPE
    SYNTAX     Gauge32
    MAX-ACCESS read-only
    STATUS     current
    DESCRIPTION
    "The peer end point sctp port"
    ::= { starSS7RdEntry 10 }

 starSS7CongLevel OBJECT-TYPE
    SYNTAX     Gauge32
    MAX-ACCESS read-only
    STATUS     current
    DESCRIPTION
    "Congestion Level Value"
    ::= { starSS7RdEntry 11 }

 starSS7LocalCong OBJECT-TYPE
    SYNTAX     Gauge32
    MAX-ACCESS read-only
    STATUS     current
    DESCRIPTION
    "Local Congestion Value"
    ::= { starSS7RdEntry 12 }

 starSS7CauseString OBJECT-TYPE
    SYNTAX     DisplayString
    MAX-ACCESS read-only
    STATUS     current
    DESCRIPTION
    "Cause string for failure"
    ::= { starSS7RdEntry 13 }


--SCCP Network

starentSccpNw OBJECT IDENTIFIER ::= { starentMIBObjects 47 }

starSccpNwTable OBJECT-TYPE
SYNTAX     SEQUENCE OF StarSccpNwEntry
MAX-ACCESS not-accessible
STATUS     current
DESCRIPTION
"A table containing Sccp Network related information"
::= { starentSccpNw 1 }

starSccpNwEntry OBJECT-TYPE
SYNTAX     StarSccpNwEntry
MAX-ACCESS not-accessible
STATUS     current
DESCRIPTION
"The statistics for a specific Sccp Network"
INDEX { starSccpNwId }
::= { starSccpNwTable 1 }

StarSccpNwEntry ::=
SEQUENCE {
  starSccpNwId                 Gauge32,
  starSccpSsn                  Gauge32
}

starSccpNwId OBJECT-TYPE
    SYNTAX     Gauge32
    MAX-ACCESS accessible-for-notify
    STATUS     current
    DESCRIPTION
    "SCCP Network Id"
    ::= { starSccpNwEntry 1 }

starSccpSsn OBJECT-TYPE
    SYNTAX     Gauge32
    MAX-ACCESS read-only
    STATUS     current
    DESCRIPTION
    "Sub System Number"
    ::= { starSccpNwEntry 2 }


-- SGTP Service
starentSGTPService OBJECT IDENTIFIER ::= { starentMIBObjects 48 }

starSGTPSerTable OBJECT-TYPE
SYNTAX     SEQUENCE OF StarSGTPSerEntry
MAX-ACCESS not-accessible
STATUS     current
DESCRIPTION
"A table containing SGTP Service  related information"
::= { starentSGTPService 1 }

starSGTPSerEntry OBJECT-TYPE
SYNTAX     StarSGTPSerEntry
MAX-ACCESS not-accessible
STATUS     current
DESCRIPTION
"The statistics for a specific SGTP service"
INDEX { starSGTPSerVpnID, starSGTPSerSvcID }
::= { starSGTPSerTable 1 }

StarSGTPSerEntry ::=
SEQUENCE {
    starSGTPSerVpnID             Gauge32,
    starSGTPSerSvcID             Gauge32,
    starSGTPVpnName          DisplayString,
    starSGTPServName         DisplayString,
    starSGTPSelfAddr         IpAddress,
    starSGTPPeerAddr         IpAddress,
    starSGTPSelfPort         Gauge32,
    starSGTPPeerPort         Gauge32
}

starSGTPSerVpnID OBJECT-TYPE
    SYNTAX     Gauge32
    MAX-ACCESS not-accessible
    STATUS     current
    DESCRIPTION
    "The internal identification of the VPN (context)"
    ::= { starSGTPSerEntry 1 }

starSGTPSerSvcID OBJECT-TYPE
    SYNTAX     Gauge32
    MAX-ACCESS not-accessible
    STATUS     current
    DESCRIPTION
    "The internal identification of this service; unique within a specific context"
    ::= { starSGTPSerEntry 2 }

starSGTPVpnName OBJECT-TYPE
    SYNTAX     DisplayString
    MAX-ACCESS read-only
    STATUS     current
    DESCRIPTION
    "The name of this VPN (context)"
    ::= { starSGTPSerEntry 3 }

starSGTPServName OBJECT-TYPE
    SYNTAX     DisplayString
    MAX-ACCESS read-only
    STATUS     current
    DESCRIPTION
    "The name of this service"
    ::= { starSGTPSerEntry 4 }

starSGTPSelfAddr OBJECT-TYPE
    SYNTAX     IpAddress
    MAX-ACCESS read-only
    STATUS     current
    DESCRIPTION
    "The IP Address of the SGSN"
    ::= { starSGTPSerEntry 5 }

starSGTPPeerAddr OBJECT-TYPE
    SYNTAX     IpAddress
    MAX-ACCESS read-only
    STATUS     current
    DESCRIPTION
    "The IP Address of the PeerNode"
    ::= { starSGTPSerEntry  6 }

starSGTPSelfPort OBJECT-TYPE
    SYNTAX     Gauge32
    MAX-ACCESS read-only
    STATUS     current
    DESCRIPTION
    "The self end point sgtp port"
    ::= { starSGTPSerEntry 7 }

starSGTPPeerPort OBJECT-TYPE
    SYNTAX     Gauge32
    MAX-ACCESS read-only
    STATUS     current
    DESCRIPTION
    "The peer end point sgtp port"
    ::= { starSGTPSerEntry 8 }

-- IPMS

starentIPMSServer OBJECT IDENTIFIER ::= { starentMIBObjects 49 }

starIPMSServerTable OBJECT-TYPE
    SYNTAX     SEQUENCE OF StarIPMSServerEntry
    MAX-ACCESS not-accessible
    STATUS     current
    DESCRIPTION
	"A table containing information on IPMS Servers"
    ::= { starentIPMSServer 1 }

starIPMSServerEntry OBJECT-TYPE
    SYNTAX     StarIPMSServerEntry
    MAX-ACCESS not-accessible
    STATUS     current
    DESCRIPTION
	"Information about a particular IPMS Server"
    INDEX { starIPMSServerVpnID, starIPMSServerAddr }
    ::= { starIPMSServerTable 1 }

StarIPMSServerEntry ::=
    SEQUENCE {
	starIPMSServerVpnID		Gauge32,
	starIPMSServerAddr		IpAddress,
	starIPMSServerVpnName		DisplayString
    }

starIPMSServerVpnID OBJECT-TYPE
    SYNTAX     Gauge32
    MAX-ACCESS not-accessible
    STATUS     current
    DESCRIPTION
        "The internal identification of the VPN (context)"
    ::= { starIPMSServerEntry 1 }

starIPMSServerAddr OBJECT-TYPE
    SYNTAX     IpAddress
    MAX-ACCESS accessible-for-notify
    STATUS     current
    DESCRIPTION
        "The IP address of the IPMS server within this VPN (context)"
    ::= { starIPMSServerEntry 2 }

starIPMSServerVpnName OBJECT-TYPE
    SYNTAX     DisplayString
    MAX-ACCESS read-only
    STATUS     current
    DESCRIPTION
        "The name of this VPN (context)"
    ::= { starIPMSServerEntry 3 }

-- Certificates

starentCert OBJECT IDENTIFIER ::= { starentMIBObjects 50 }

starCertTable OBJECT-TYPE
    SYNTAX     SEQUENCE OF StarCertEntry
    MAX-ACCESS not-accessible
    STATUS     current
    DESCRIPTION
	"A table containing information on X.509 Certificates"
    ::= { starentCert 1 }

starCertEntry OBJECT-TYPE
    SYNTAX     StarCertEntry
    MAX-ACCESS not-accessible
    STATUS     current
    DESCRIPTION
	"Information about a particular X.509 Certificate"
    INDEX { IMPLIED starCertSerialNumber }
    ::= { starCertTable 1 }

StarCertEntry ::=
    SEQUENCE {
	starCertSerialNumber		DisplayString,
	starCertExpiryTime		DateAndTime,
	starCertIssuer			DisplayString
    }

starCertSerialNumber OBJECT-TYPE
    SYNTAX     DisplayString
    MAX-ACCESS accessible-for-notify
    STATUS     current
    DESCRIPTION
	"The serial number for the certificate"
    ::= { starCertEntry 1 }

starCertExpiryTime OBJECT-TYPE
    SYNTAX     DateAndTime
    MAX-ACCESS read-only
    STATUS     current
    DESCRIPTION
	"The Certificate expiration date/time"
    ::= { starCertEntry 2 }

starCertIssuer OBJECT-TYPE
    SYNTAX     DisplayString
    MAX-ACCESS read-only
    STATUS     current
    DESCRIPTION
	"The Certificate issuer"
    ::= { starCertEntry 3 }

-- Files; defined for traps only

starentFile OBJECT IDENTIFIER ::= { starentMIBObjects 51 }

starFileTable OBJECT-TYPE
    SYNTAX     SEQUENCE OF StarFileEntry
    MAX-ACCESS not-accessible
    STATUS     current
    DESCRIPTION
	"A table of files stored on a mass storage device"
    ::= { starentFile 1 }

starFileEntry OBJECT-TYPE
    SYNTAX     StarFileEntry
    MAX-ACCESS not-accessible
    STATUS     current
    DESCRIPTION
	"Information about a particular file on a mass storage device"
    INDEX { IMPLIED starFileName }
    ::= { starFileTable 1 }

StarFileEntry ::=
    SEQUENCE {
	starFileName		DisplayString,
	starFileApplication	INTEGER
    }

starFileName OBJECT-TYPE
    SYNTAX     DisplayString
    MAX-ACCESS accessible-for-notify
    STATUS     current
    DESCRIPTION
	"The name (full path) of the file"
    ::= { starFileEntry 1 }

starFileApplication OBJECT-TYPE
    SYNTAX     INTEGER {
		unknown(0),
		systemfile(1),
		cdrmod(2)
               }
    MAX-ACCESS read-only
    STATUS     current
    DESCRIPTION
	"The application that owns this file"
    ::= { starFileEntry 2 }

-- FTP Servers, defined for use in traps only

starentFTPServ OBJECT IDENTIFIER ::= { starentMIBObjects 52 }

starFTPServTable OBJECT-TYPE
    SYNTAX     SEQUENCE OF StarFTPServEntry
    MAX-ACCESS not-accessible
    STATUS     current
    DESCRIPTION
	"A table of FTP servers configured"
    ::= { starentFTPServ 1 }

starFTPServEntry OBJECT-TYPE
    SYNTAX         StarFTPServEntry
    MAX-ACCESS     not-accessible
    STATUS         current
    DESCRIPTION
	"Information about a particular FTP Server"
    INDEX { starFTPServVpnID, starFTPServIpAddr }
    ::= { starFTPServTable 1 }

StarFTPServEntry ::=
    SEQUENCE {
	starFTPServVpnID	Unsigned32,
	starFTPServIpAddr	IpAddress,
	starFTPServVpnName	DisplayString
    }

starFTPServVpnID OBJECT-TYPE
    SYNTAX     Unsigned32
    MAX-ACCESS not-accessible
    STATUS     current
    DESCRIPTION
	"The internal identification of the VPN (context) used to reach this FTP server"
    ::= { starFTPServEntry 1 }

starFTPServIpAddr OBJECT-TYPE
    SYNTAX     IpAddress
    MAX-ACCESS accessible-for-notify
    STATUS     current
    DESCRIPTION
	"The IP address of the FTP server"
    ::= { starFTPServEntry 2 }

starFTPServVpnName OBJECT-TYPE
    SYNTAX     DisplayString
    MAX-ACCESS read-only
    STATUS     current
    DESCRIPTION
	"The name of the VPN (context)"
    ::= { starFTPServEntry 3 }

---for cscf peer server
starentCSCFPeerServer OBJECT IDENTIFIER ::= { starentMIBObjects 53 }

starCSCFPeerServerTable OBJECT-TYPE
  SYNTAX     SEQUENCE OF StarCSCFPeerServerEntry
  MAX-ACCESS not-accessible
  STATUS     current
  DESCRIPTION
    "A table containing PeerServer related information"
  ::= { starentCSCFPeerServer 1 }

starCSCFPeerServerEntry OBJECT-TYPE
  SYNTAX     StarCSCFPeerServerEntry
  MAX-ACCESS not-accessible
  STATUS     current
  DESCRIPTION
    "The statistics for a specific CSCF service"
  INDEX { starCSCFPeerServerVpnID, starCSCFPeerServerSvcID}
  ::= { starCSCFPeerServerTable 1 }

StarCSCFPeerServerEntry ::=
   SEQUENCE {
     starCSCFPeerServerVpnID Gauge32,
     starCSCFPeerServerSvcID Gauge32,
     starCSCFPeerServerVpnName    DisplayString,
     starCSCFPeerServerSvcName   DisplayString,
     starCSCFPeerServerListName   DisplayString,
     starCSCFPeerServerName      DisplayString,
     starCSCFPeerServerState      DisplayString
     }

starCSCFPeerServerVpnID OBJECT-TYPE
  SYNTAX     Gauge32
  MAX-ACCESS not-accessible
  STATUS     current
  DESCRIPTION
    "The internal identification of the VPN (context)"
  ::= { starCSCFPeerServerEntry 1 }
 
starCSCFPeerServerSvcID OBJECT-TYPE
  SYNTAX     Gauge32
  MAX-ACCESS not-accessible
  STATUS     current
  DESCRIPTION
    "The internal identification of this  CSCF service; unique within a specific context"
  ::= { starCSCFPeerServerEntry 2 }

starCSCFPeerServerVpnName OBJECT-TYPE
  SYNTAX     DisplayString
  MAX-ACCESS read-only
  STATUS     current
  DESCRIPTION
   "The name of this VPN (context)"
  ::= { starCSCFPeerServerEntry 3 }

starCSCFPeerServerSvcName OBJECT-TYPE
  SYNTAX     DisplayString
  MAX-ACCESS read-only
  STATUS     current
  DESCRIPTION
    "The name of this CSCF-service"
  ::= { starCSCFPeerServerEntry 4 }

starCSCFPeerServerListName OBJECT-TYPE
  SYNTAX     DisplayString
  MAX-ACCESS read-only
  STATUS     current
  DESCRIPTION
  "The name of the cscf-peer-server"
  ::= { starCSCFPeerServerEntry 5 }

starCSCFPeerServerName OBJECT-TYPE
  SYNTAX     DisplayString
  MAX-ACCESS read-only
  STATUS     current
  DESCRIPTION
  "The name of the cscf-peer-server"
  ::= { starCSCFPeerServerEntry 6 }

starCSCFPeerServerState OBJECT-TYPE
  SYNTAX     DisplayString
  MAX-ACCESS read-only
  STATUS     current
  DESCRIPTION
  "The state of the cscf-peer-server"
  ::= { starCSCFPeerServerEntry 7 }



---end for cscf peer server

--

starentSDH OBJECT IDENTIFIER ::= { starentMIBObjects 54 }

starSDHTable OBJECT-TYPE
    SYNTAX     SEQUENCE OF StarSDHEntry
    MAX-ACCESS not-accessible
    STATUS     current
    DESCRIPTION
	"A table ..."
    ::= { starentSDH 1 }

starSDHEntry OBJECT-TYPE
    SYNTAX     StarSDHEntry
    MAX-ACCESS not-accessible
    STATUS     current
    DESCRIPTION
	"Information about a specific ..."
    INDEX { starSDHSlot, starSDHPort }
    ::= { starSDHTable 1 }

StarSDHEntry ::=
    SEQUENCE {
	starSDHSlot		Integer32,
	starSDHPort		Integer32,
	starSDHOperState	Integer32
    }

starSDHSlot OBJECT-TYPE
    SYNTAX	Integer32(17..48)
    MAX-ACCESS  accessible-for-notify
    STATUS      current
    DESCRIPTION
	"The slot number for this port"
    ::= { starSDHEntry 1 }

starSDHPort OBJECT-TYPE
    SYNTAX      Integer32(1..8)
    MAX-ACCESS  accessible-for-notify
    STATUS      current
    DESCRIPTION
	"The port number within this slot"
    ::= { starSDHEntry 2 }

starSDHOperState OBJECT-TYPE
    SYNTAX	Integer32
    MAX-ACCESS  read-only
    STATUS      current
    DESCRIPTION
	"A bitmask indicating the state of SDH layer SCT.
		0x0000		Good
		0x0001		lais
		0x0002		linesd
		0x0004		linesf
		0x0010		lof
		0x0020		los
		0x0040		msrdi"
    ::= { starSDHEntry 3 }

---

starentSDHPath OBJECT IDENTIFIER ::= { starentMIBObjects 55 }

starSDHPathTable OBJECT-TYPE
    SYNTAX     SEQUENCE OF StarSDHPathEntry
    MAX-ACCESS not-accessible
    STATUS     current
    DESCRIPTION
	"A table ..."
    ::= { starentSDHPath 1 }

starSDHPathEntry OBJECT-TYPE
    SYNTAX     StarSDHPathEntry
    MAX-ACCESS not-accessible
    STATUS     current
    DESCRIPTION
	"Information about a specific ..."
    INDEX { starSDHPathSlot, starSDHPathPort, starSDHPathNum }
    ::= { starSDHPathTable 1 }

StarSDHPathEntry ::=
    SEQUENCE {
	starSDHPathSlot		Integer32,
	starSDHPathPort		Integer32,
	starSDHPathNum		Integer32,
	starSDHPathOperState	Integer32
    }

starSDHPathSlot OBJECT-TYPE
    SYNTAX	Integer32(17..48)
    MAX-ACCESS  accessible-for-notify
    STATUS      current
    DESCRIPTION
	"The slot number for this port"
    ::= { starSDHPathEntry 1 }

starSDHPathPort OBJECT-TYPE
    SYNTAX      Integer32(1..8)
    MAX-ACCESS  accessible-for-notify
    STATUS      current
    DESCRIPTION
	"The port number within this slot"
    ::= { starSDHPathEntry 2 }

starSDHPathNum OBJECT-TYPE
    SYNTAX      Integer32(1..3)
    MAX-ACCESS  accessible-for-notify
    STATUS      current
    DESCRIPTION
	"The path number"
    ::= { starSDHPathEntry 3 }

starSDHPathOperState OBJECT-TYPE
    SYNTAX	Integer32
    MAX-ACCESS  read-only
    STATUS      current
    DESCRIPTION
	"A bitmask indicating the state of SDH Path HOP.
		0x0000		Good
		0x0001		hopathsd
		0x0002		hopathsf
		0x0020		ppdi
		0x0040		prdi
		0x0080		perdi
		0x0100		perdival
		0x0200		perdivaloff"
    ::= { starSDHPathEntry 4 }


---

starentE1Trib OBJECT IDENTIFIER ::= { starentMIBObjects 56 }

starE1TribTable OBJECT-TYPE
    SYNTAX     SEQUENCE OF StarE1TribEntry
    MAX-ACCESS not-accessible
    STATUS     current
    DESCRIPTION
	"A table ..."
    ::= { starentE1Trib 1 }

starE1TribEntry OBJECT-TYPE
    SYNTAX     StarE1TribEntry
    MAX-ACCESS not-accessible
    STATUS     current
    DESCRIPTION
	"Information about a specific ..."
    INDEX { starE1TribSlot, starE1TribPort, starE1TribPath, starE1TribTug2, starE1TribTu12 }
    ::= { starE1TribTable 1 }

StarE1TribEntry ::=
    SEQUENCE {
	starE1TribSlot		Integer32,
	starE1TribPort		Integer32,
	starE1TribPath		Integer32,
	starE1TribTug2		Integer32,
	starE1TribTu12		Integer32,
	starE1TribOperStateLOP  Integer32,
	starE1TribOperState     Integer32
    }

starE1TribSlot OBJECT-TYPE
    SYNTAX	Integer32(17..48)
    MAX-ACCESS  accessible-for-notify
    STATUS      current
    DESCRIPTION
	"The slot number for this port"
    ::= { starE1TribEntry 1 }

starE1TribPort OBJECT-TYPE
    SYNTAX      Integer32(1..8)
    MAX-ACCESS  accessible-for-notify
    STATUS      current
    DESCRIPTION
	"The port number within this slot"
    ::= { starE1TribEntry 2 }

starE1TribPath OBJECT-TYPE
    SYNTAX      Integer32(1..3)
    MAX-ACCESS  accessible-for-notify
    STATUS      current
    DESCRIPTION
	" "
    ::= { starE1TribEntry 3 }

starE1TribTug2 OBJECT-TYPE
    SYNTAX	Integer32(1..7)
    MAX-ACCESS  accessible-for-notify
    STATUS      current
    DESCRIPTION
	" "
    ::= { starE1TribEntry 4 }

starE1TribTu12 OBJECT-TYPE
    SYNTAX	Integer32(1..3)
    MAX-ACCESS  accessible-for-notify
    STATUS      current
    DESCRIPTION
	" "
    ::= { starE1TribEntry 5 }

starE1TribOperStateLOP OBJECT-TYPE
    SYNTAX	Integer32
    MAX-ACCESS  read-only
    STATUS      current
    DESCRIPTION
	"A bitmask indicating the state of SDH layer LOP.
		0x0000		Good
		0x0001		lopathsd
		0x0002		lopathsf
		0x0100		erdi
		0x0200		rdi
		0x0400		lop
		0x0800		ais
		0x1000		lom"
    ::= { starE1TribEntry 6 }

starE1TribOperState OBJECT-TYPE
    SYNTAX	Integer32
    MAX-ACCESS  read-only
    STATUS      current
    DESCRIPTION
	"A bitmask
		0x0000	Good
		0x0001	inf
		0x0002	insmf
		0x0004	incmf
		0x0008	ooof
		0x0010	raiccrc
		0x0020	cfebe
		0x0040	rai
		0x0080	rmai
                0x0100  aisd
		0x0200	red
		0x0400	ais
		0x0800	ts16aisd"
    ::= { starE1TribEntry 7 }

---

starentFractE1Trib OBJECT IDENTIFIER ::= { starentMIBObjects 58 }

starFractE1TribTable OBJECT-TYPE
    SYNTAX     SEQUENCE OF StarFractE1TribEntry
    MAX-ACCESS not-accessible
    STATUS     current
    DESCRIPTION
	"A table ..."
    ::= { starentFractE1Trib 1 }

starFractE1TribEntry OBJECT-TYPE
    SYNTAX     StarFractE1TribEntry
    MAX-ACCESS not-accessible
    STATUS     current
    DESCRIPTION
	"Information about a specific ..."
    INDEX { starFractE1TribSlot, starFractE1TribPort, starFractE1TribPath, starFractE1TribTug2, starFractE1TribTu12, starFractE1TribBundNum }
    ::= { starFractE1TribTable 1 }

StarFractE1TribEntry ::=
    SEQUENCE {
	starFractE1TribSlot		Integer32,
	starFractE1TribPort		Integer32,
	starFractE1TribPath		Integer32,
	starFractE1TribTug2		Integer32,
	starFractE1TribTu12		Integer32,
	starFractE1TribBundNum		Integer32,
	starFractE1TribTimeslots	DisplayString
    }

starFractE1TribSlot OBJECT-TYPE
    SYNTAX	Integer32(17..48)
    MAX-ACCESS  accessible-for-notify
    STATUS      current
    DESCRIPTION
	"The slot number for this port"
    ::= { starFractE1TribEntry 1 }

starFractE1TribPort OBJECT-TYPE
    SYNTAX      Integer32(1..8)
    MAX-ACCESS  accessible-for-notify
    STATUS      current
    DESCRIPTION
	"The port number within this slot"
    ::= { starFractE1TribEntry 2 }

starFractE1TribPath OBJECT-TYPE
    SYNTAX      Integer32(1..3)
    MAX-ACCESS  accessible-for-notify
    STATUS      current
    DESCRIPTION
	" "
    ::= { starFractE1TribEntry 3 }

starFractE1TribTug2 OBJECT-TYPE
    SYNTAX	Integer32(1..7)
    MAX-ACCESS  accessible-for-notify
    STATUS      current
    DESCRIPTION
	" "
    ::= { starFractE1TribEntry 4 }

starFractE1TribTu12 OBJECT-TYPE
    SYNTAX	Integer32(1..3)
    MAX-ACCESS  accessible-for-notify
    STATUS      current
    DESCRIPTION
	" "
    ::= { starFractE1TribEntry 5 }

starFractE1TribBundNum OBJECT-TYPE
    SYNTAX	Integer32(0..31)
    MAX-ACCESS  not-accessible
    STATUS      obsolete
    DESCRIPTION
	" "
    ::= { starFractE1TribEntry 6 }

starFractE1TribTimeslots OBJECT-TYPE
    SYNTAX	DisplayString
    MAX-ACCESS  read-only
    STATUS      current
    DESCRIPTION
	" "
    ::= { starFractE1TribEntry 7 }

--GPRSLink
starentGPRSLink OBJECT IDENTIFIER ::= { starentMIBObjects 57 }

starGPRSLinkTable OBJECT-TYPE
    SYNTAX     SEQUENCE OF StarGPRSLinkEntry
    MAX-ACCESS not-accessible
    STATUS     current
    DESCRIPTION
    "A table containing GPRSService Link related information"
    ::= { starentGPRSLink 1 }

starGPRSLinkEntry OBJECT-TYPE
    SYNTAX     StarGPRSLinkEntry
    MAX-ACCESS not-accessible
    STATUS     current
    DESCRIPTION
    "The link statistics for a specific GPRS service"
    INDEX { starGPRSNsei }
    ::= { starGPRSLinkTable 1 }

StarGPRSLinkEntry ::=
    SEQUENCE {
        starGPRSNsei                 Gauge32,
        starGPRSNsvci                Gauge32,
        starGPRSBvci                 Gauge32
    }

starGPRSNsei OBJECT-TYPE
    SYNTAX     Gauge32
    MAX-ACCESS accessible-for-notify
    STATUS     current
    DESCRIPTION
    "Network Service Entity Indentifier"
    ::= { starGPRSLinkEntry 1 }

starGPRSNsvci OBJECT-TYPE
    SYNTAX     Gauge32
    MAX-ACCESS read-only
    STATUS     current
    DESCRIPTION
    "Network Service Virtual Circuit Identifier"
    ::= { starGPRSLinkEntry 2}

starGPRSBvci OBJECT-TYPE
    SYNTAX     Gauge32
    MAX-ACCESS read-only
    STATUS     current
    DESCRIPTION
    "Base Station System GPRS(General Packet Radio Service) Protocl Virtual Circuit Identifier"
    ::= { starGPRSLinkEntry 3}

-- end of GPRSLink

-- Files; defined for traps only

starentStorage OBJECT IDENTIFIER ::= { starentMIBObjects 59 }

starStorageTable OBJECT-TYPE
    SYNTAX     SEQUENCE OF StarStorageEntry
    MAX-ACCESS not-accessible
    STATUS     current
    DESCRIPTION
	"A table of mass storage devices"
    ::= { starentStorage 1 }

starStorageEntry OBJECT-TYPE
    SYNTAX     StarStorageEntry
    MAX-ACCESS not-accessible
    STATUS     current
    DESCRIPTION
	"Information about a particular file on a mass storage device"
    INDEX { starStorageSlot, IMPLIED starStorageName }
    ::= { starStorageTable 1 }

StarStorageEntry ::=
    SEQUENCE {
	starStorageSlot		Integer32,
	starStorageName		DisplayString,
	starStorageDeviceType	INTEGER
    }

starStorageSlot OBJECT-TYPE
    SYNTAX     Integer32(1..16)
    MAX-ACCESS accessible-for-notify
    STATUS     current
    DESCRIPTION
	"The slot number of the card holding this storage device"
    ::= { starStorageEntry 1 }

starStorageName OBJECT-TYPE
    SYNTAX     DisplayString
    MAX-ACCESS accessible-for-notify
    STATUS     current
    DESCRIPTION
	"The name of the storage device"
    ::= { starStorageEntry 2 }

starStorageDeviceType OBJECT-TYPE
    SYNTAX     INTEGER {
		unknown(0),
		independent(1),
		raid(2),
		raidmember(3)
	       }
    MAX-ACCESS read-only
    STATUS     current
    DESCRIPTION
	"The storage device type.  A value of independent(1) means that the device can be
	 accessed as a standalone device, and is not part of a raid array.  A value of
	 raid(2) means that this device is a raid array.  A value of raidmember(3) means
	 the device is part of a raid array, and thus cannot be read/written to
	 outside of the raid array"
    ::= { starStorageEntry 3 }
    
-- MME S1 Associations; defined for traps only

starentMMES1Assoc OBJECT IDENTIFIER ::= { starentMIBObjects 67 }

starMMES1AssocTable OBJECT-TYPE
    SYNTAX     SEQUENCE OF StarMMES1AssocEntry
    MAX-ACCESS not-accessible
    STATUS     current
    DESCRIPTION
	"A table of MME S1 Associations"
    ::= { starentMMES1Assoc 1 }

starMMES1AssocEntry OBJECT-TYPE
    SYNTAX     StarMMES1AssocEntry
    MAX-ACCESS not-accessible
    STATUS     current
    DESCRIPTION
	"Information about a particular MME S1 Association"
    INDEX { starMMES1AssocSvcID, starMMES1AssocENBID }
    ::= { starMMES1AssocTable 1 }

StarMMES1AssocEntry ::=
    SEQUENCE {
	starMMES1AssocSvcID     StarMediumID,
	starMMES1AssocENBID     StarENBID,
	starMMES1AssocVpnName   DisplayString,
	starMMES1AssocServName  DisplayString
    }

starMMES1AssocSvcID OBJECT-TYPE
    SYNTAX     StarMediumID
    MAX-ACCESS not-accessible
    STATUS     current
    DESCRIPTION
	"The service identification is made up from the first 8 characters of the
	 VPN name and the first 16 characters of the service name seperated by (:)"
    ::= { starMMES1AssocEntry 1 }

starMMES1AssocENBID OBJECT-TYPE
    SYNTAX     StarENBID
    MAX-ACCESS accessible-for-notify
    STATUS     current
    DESCRIPTION
	"The identification of the eNodeB"
    ::= { starMMES1AssocEntry 2 }

starMMES1AssocVpnName OBJECT-TYPE
    SYNTAX     DisplayString
    MAX-ACCESS read-only
    STATUS     current
    DESCRIPTION
        "The name of this VPN (context)"
    ::= { starMMES1AssocEntry 3 }

starMMES1AssocServName OBJECT-TYPE
    SYNTAX     DisplayString
    MAX-ACCESS read-only
    STATUS     current
    DESCRIPTION
        "The name of this MME Service"
    ::= { starMMES1AssocEntry 4 }

-- MME S1 path; defined for traps only

starentMMES1Path OBJECT IDENTIFIER ::= { starentMIBObjects 70 }

starMMES1PathTable OBJECT-TYPE
    SYNTAX     SEQUENCE OF StarMMES1PathEntry
    MAX-ACCESS not-accessible
    STATUS     current
    DESCRIPTION
	"A table of MME S1 Path"
    ::= { starentMMES1Path 1 }

starMMES1PathEntry OBJECT-TYPE
    SYNTAX     StarMMES1PathEntry
    MAX-ACCESS not-accessible
    STATUS     current
    DESCRIPTION
	"Information about a particular MME S1 Pathiation"
    INDEX { starMMES1PathSvcID, starMMES1PathENBID }
    ::= { starMMES1PathTable 1 }

StarMMES1PathEntry ::=
    SEQUENCE {
	starMMES1PathSvcID     StarMediumID,
	starMMES1PathENBID     StarENBID,
	starMMES1PathVpnName   DisplayString,
	starMMES1PathServName  DisplayString,
	starMMES1PathSelfAddr  IpAddress,
	starMMES1PathSelfPort  Gauge32,
	starMMES1PathPeerAddr  IpAddress,
	starMMES1PathPeerPort  Gauge32
    }

starMMES1PathSvcID OBJECT-TYPE
    SYNTAX     StarMediumID
    MAX-ACCESS not-accessible
    STATUS     current
    DESCRIPTION
	"The service identification is made up from the first 8 characters of the
	 VPN name and the first 16 characters of the service name seperated by (:)"
    ::= { starMMES1PathEntry 1 }

starMMES1PathENBID OBJECT-TYPE
    SYNTAX     StarENBID
    MAX-ACCESS accessible-for-notify
    STATUS     current
    DESCRIPTION
	"The identification of the eNodeB"
    ::= { starMMES1PathEntry 2 }

starMMES1PathVpnName OBJECT-TYPE
    SYNTAX     DisplayString
    MAX-ACCESS read-only
    STATUS     current
    DESCRIPTION
        "The name of this VPN (context)"
    ::= { starMMES1PathEntry 3 }

starMMES1PathServName OBJECT-TYPE
    SYNTAX     DisplayString
    MAX-ACCESS read-only
    STATUS     current
    DESCRIPTION
        "The name of this MME Service"
    ::= { starMMES1PathEntry 4 }

starMMES1PathSelfAddr OBJECT-TYPE
    SYNTAX      IpAddress
    MAX-ACCESS  read-only
    STATUS      current
    DESCRIPTION
        "Interface IP Address"
    ::= { starMMES1PathEntry 5 }

starMMES1PathSelfPort OBJECT-TYPE
    SYNTAX     Gauge32
    MAX-ACCESS read-only
    STATUS     current
    DESCRIPTION
        "Self port number"
    ::= { starMMES1PathEntry 6 }

starMMES1PathPeerAddr OBJECT-TYPE
    SYNTAX      IpAddress
    MAX-ACCESS  read-only
    STATUS      current
    DESCRIPTION
        "Interface IP Address"
    ::= { starMMES1PathEntry 7 }

starMMES1PathPeerPort OBJECT-TYPE
    SYNTAX     Gauge32
    MAX-ACCESS read-only
    STATUS     current
    DESCRIPTION
        "Peer port number"
    ::= { starMMES1PathEntry 8 }

-- traps

starentTraps OBJECT IDENTIFIER ::= { starentMIB 2 }

-- Card Trap

starCardTempOverheat NOTIFICATION-TYPE
    OBJECTS { starSlotNum,
	      starCardTemperature }
    STATUS  current
    DESCRIPTION
        "The card has reached a temperature beyond its safe operating range.

	 Probable Cause: External temperature is too high; One or more fan
         failures; blockages the prevent fan air inflow/outflow.

	 Action to be Taken: Inspect chassis for any item that may be blocking chassis
	 air flow.  Verify adjacent equipment is not obstructing air flow.
	 Verify that the fans are running via the CLI/EMS.  Check air filters.
	 Check chassis maintenance schedule to see if chassis needs routine
	 air filter replacement.  Verify room temperature is within acceptable
	 operating conditions.

	 Clear Condition: This condition is cleared when the card reaches its
	 operating temperature range or is removed from the system.

	 Condition Clear Alarm: This condition is cleared by a starCardTempOK notification.
	 This is not applicable to QVPC-SI and QVPC-DI"
    --#SUMMARY "[Card %d] Card has overheated; measured temperature %d C"
    --#ARGUMENTS {0,1}
    --#STATE NONOPERATIONAL
    --#SEVERITY CRITICAL
    ::= { starentTraps 1 }

starCardTempOK NOTIFICATION-TYPE
    OBJECTS { starSlotNum,
              starCardTemperature }
    STATUS  current
    DESCRIPTION
        "The temperature of the card is now within its safe operating range.
         This notification is only generated if the card has previosly
         generated a starCardTempOverheat notification.

	 Action to be Taken: No action required.  The cause for the card overheat
	 condition should be investigated.This is not applicable to QVPC-SI and QVPC-DI."
    --#SUMMARY "[Slot %d] Temperature OK (%d C)"
    --#ARGUMENTS {0,1}
    --#STATE OPERATIONAL
    --#SEVERITY INFORMATIONAL
    ::= { starentTraps 2 }

starCardReset NOTIFICATION-TYPE
    OBJECTS { starSlotNum,
	      starCardType,
        starSlotSerialNumber}
    STATUS  obsolete
    DESCRIPTION
        "A reset operation has been invoked on the card.  This trap is obsolete.
	 This is not applicable to QVPC-SI."
    --#SUMMARY "[Card %s-%d] Card has been reset UUID %s"
    --#ARGUMENTS {1,0,2}
    --#STATE DEGRADED
    --#SEVERITY MAJOR
    ::= { starentTraps 3 }

starCardRebootRequest NOTIFICATION-TYPE
    OBJECTS { starSlotNum,
	      starCardType,
        starSlotSerialNumber}
    STATUS  current
    DESCRIPTION
        "A Reboot operation has been invoked on this card by an administrator.  If successful,
	 a subsequent CardDown trap is typically generated.

	 Action to be Taken: No action required.  If the reboot was not scheduled the admin
	 logs can be examined to determine who invoked the reboot operation. This is not applicable to QVPC-SI."
    --#SUMMARY "[Card %s-%d] Reboot operation invoked on card UUID %s"
    --#ARGUMENTS {1,0,2}
    --#STATE DEGRADED
    --#SEVERITY MAJOR
    ::= { starentTraps 4 }

starCardUp NOTIFICATION-TYPE
    OBJECTS { starSlotNum, starCardType, starSlotSerialNumber }
    STATUS  current
    DESCRIPTION
        "The card is up (operational). This is not applicable to QVPC-SI."
    --#SUMMARY "[Card %s-%d] Card is up UUID %s"
    --#ARGUMENTS {1,0, 2}
    --#STATE OPERATIONAL
    --#SEVERITY INFORMATIONAL
    ::= { starentTraps 5 }

starCardVoltageFailure NOTIFICATION-TYPE
    OBJECTS { starSlotNum, starCardType, starSlotSerialNumber }
    STATUS  current
    DESCRIPTION
        "A voltage regulation failure has been detected this card.

         Probable Cause: Problem with incoming power; failure of power filters;
         hardware issue with card.  Note that this is an extremely abnormal
	 condition.

	 Action To Be Taken: Verify that the power supplied to the chassis is
	 operating correctly; use the CLI/EMS to check the state of the chassis
	 power filters; replace the card

	 Clear Condition: This is not a recoverable error except via restarting the card,
	 so the condition is only cleared via a starCardUp or starCardActive notification.
         This is not applicable to QVPC-SI and QVPC-DI."
    --#SUMMARY "[Card %s-%d] Voltage Failure UUID %s"
    --#ARGUMENTS {1,0,2}
    --#STATE NONOPERATIONAL
    --#SEVERITY CRITICAL
    ::= { starentTraps 6 }

starCardRemoved NOTIFICATION-TYPE
    OBJECTS { starSlotNum,
	      starCardType,
        starSlotSerialNumber}
    STATUS  current
    DESCRIPTION
        "A card has been removed from the chassis.

	 Probable Cause: An operator has physically unlocked and removed a card from
	 the chassis

	 Action to be Taken: No action is required.  If the card removal was unplanned,
	 the admin logs can identify the time when the card was initially unlocked.
         This is not applicable to QVPC-SI."
    --#SUMMARY "[Card %s-%d] Card removed UUID %s"
    --#ARGUMENTS {1,0,2}
    --#STATE NONOPERATIONAL
    --#SEVERITY MAJOR
    ::= { starentTraps 7 }

starCardInserted NOTIFICATION-TYPE
    OBJECTS { starSlotNum,
	      starCardType,
        starSlotSerialNumber}
    STATUS  current
    DESCRIPTION
        "A card has been inserted into the chassis.This is not applicable to QVPC-SI."
    --#SUMMARY "[Card %s-%d] Card inserted UUID $s"
    --#ARGUMENTS {1,0,2}
    --#STATE OPERATIONAL
    --#SEVERITY INFORMATIONAL
    ::= { starentTraps 8 }

starCardBootFailed NOTIFICATION-TYPE
    OBJECTS { starSlotNum,
	      starCardType,
        starSlotSerialNumber}
    STATUS  current
    DESCRIPTION
	"A card has failed to startup properly.  The card is not operational

	 Probable Cause: The system logs should contain additional information
	 about the cause of the boot failure. This is not applicable to QVPC-SI."
    --#SUMMARY "[Card %s-%d] Card boot failure UUID %s"
    --#ARGUMENTS {1,0,2}
    --#STATE NONOPERATIONAL
    --#SEVERITY MAJOR
    ::= { starentTraps 9 }

starCardFailed NOTIFICATION-TYPE
    OBJECTS { starSlotNum, starCardType, starSlotSerialNumber }
    STATUS  obsolete
    DESCRIPTION
	"The card has failed and is no longer operational.  This trap is obsolete
         and has been replaced with more specific traps to identify specific
         failures.This is not applicable to QVPC-SI."
    ::= { starentTraps 10 }

starCardSWFailed NOTIFICATION-TYPE
    OBJECTS { starSlotNum }
    STATUS  obsolete
    DESCRIPTION
        "A unrecoverable software error has occured on the card.  This trap is obsolete
         and has been replaced with more specific traps to identify specific
         failures.This is not applicable to QVPC-SI."
    ::= { starentTraps 11 }

starCardRCCFailed NOTIFICATION-TYPE
    OBJECTS { starSlotNum }
    STATUS  obsolete
    DESCRIPTION
        "The RCC has failed.

	 Probable Cause: A hardware failure on the RCC card.  This trap is obsolete.
	 This is not applicable to QVPC-SI and QVPC-DI."
    --#SUMMARY "[Card RCC-%d] Card failure"
    --#ARGUMENTS {0}
    --#STATE NONOPERATIONAL
    --#SEVERITY MAJOR
    ::= { starentTraps 12 }

starCardMismatch NOTIFICATION-TYPE
    OBJECTS { starSlotNum, starCardType, starSlotSerialNumber }
    STATUS  current
    DESCRIPTION
	"The card does not match its configuration, or the card does not
         match the slot it was inserted into, or the card is of an
         unsupported type.

	 Probable Cause: A card was inserted into a slot which was configured
	 for a different type of card.  For example, a Gigabit Ethernet card
	 was inserted into a slot configured for a Fast Ethernet card.

	 A starCardUp or starCardActive notification would indicate that this
	 condition has been cleared.This is not applicable to QVPC-SI."
    --#SUMMARY "[Card %s-%d] Card does not match system configuration UUID %s"
    --#ARGUMENTS {1,0,2}
    --#STATE NONOPERATIONAL
    --#SEVERITY MAJOR
    ::= { starentTraps 13 }

starCardFailureLEDOn NOTIFICATION-TYPE
    OBJECTS { starSlotNum,
	      starCardType,
        starSlotSerialNumber}
    STATUS  obsolete
    DESCRIPTION
        "The failure LED is illuminated on the card.  This trap is obsolete and
	 has been replaced with more specific traps for specific failures.
         This is not applicable to QVPC-SI and QVPC-DI."
    ::= { starentTraps 14 }

starCardFailureLEDOff NOTIFICATION-TYPE
    OBJECTS { starSlotNum,
              starCardType,
              starSlotSerialNumber}
    STATUS  obsolete
    DESCRIPTION
        "The failure LED is no longer illuminated on the card.  This notification
         is only generated if the card has previously generated a
         starCardFailureLEDOn notification.  This trap is obsolete and has been
	 replaced with more specific traps for specific failures.This is not 
         applicable to QVPC-SI and QVPC-DI."
    ::= { starentTraps 15 }

starCardPACMigrateStart NOTIFICATION-TYPE
    OBJECTS { starSlotNum, starSlotNum }
    STATUS  deprecated
    DESCRIPTION
	"A PAC/PSC Migration operation has begun.  The first varbind identifies the PAC/PSC
         being migrated away from; the second varbind identifies the PAC/PSC being
         migrated to.

	 Probable Cause: This is typically caused by an operator action; it can also
	 represent the system recovering from a software or hardware fault.

	 A starCardPACMigrateComplete is generated when the migration is completed"
    --#SUMMARY "[Card PAC-%d] Migration start to card PAC-%d"
    --#ARGUMENTS {0,1}
    --#STATE DEGRADED
    --#SEVERITY MAJOR
    ::= { starentTraps 16 }

starCardPACMigrateComplete NOTIFICATION-TYPE
    OBJECTS { starSlotNum, starSlotNum }
    STATUS  deprecated
    DESCRIPTION
	"A PAC/PSC Migration operation has successfully completed.  The first varbind identifies the PAC/PSC
         that was migrated away from; the second varbind identifies the PAC/PSC that was
         migrated to."
    --#SUMMARY "[Card PAC-%d] Migration completed from card PAC-%d"
    --#ARGUMENTS {1,0}
    --#STATE OPERATIONAL
    --#SEVERITY INFORMATIONAL
    ::= { starentTraps 17 }

starCardPACMigrateFailed NOTIFICATION-TYPE
    OBJECTS { starSlotNum, starSlotNum }
    STATUS  deprecated
    DESCRIPTION
	"A PAC/PSC Migration operation has failed.  The first varbind identifies the PAC/PSC
         that was attemped to be migrated away from; the second varbind identifies the PAC/PSC that was
         attempted to be migrated to.

	 Probable Cause: The PAC/PSC being migrated to was removed or reset before
	 the migration completed; the migration operation was terminated by an
	 operator; or a software or hardware failure on either PAC/PSC involved
	 in the migration operation.

	 The PAC/PSC in question will be reset; a starCardUp notification will be generated
	 when the card is operational again."
    --#SUMMARY "[Card PAC-%d] Migration failed to card PAC-%d"
    --#ARGUMENTS {0,1}
    --#STATE DEGRADED
    --#SEVERITY MAJOR
    ::= { starentTraps 18 }

starCardSPCSwitchoverStart NOTIFICATION-TYPE
    OBJECTS { starSlotNum, starSlotNum }
    STATUS  deprecated
    DESCRIPTION
	"An SPC switchover operation has begun.  The first varbind identifies the SPC
         being switched away from; the second varbind identifies the SPC being
         switched to.  Note that since an SPC switchover can cause a momentary loss
	 of communication through the management (SPIO) interface, it is possible
	 that this trap will not be successfully delivered.

	 Probable Cause: This is typically caused by an operator action; it can also
	 represent the system recovering from a software or hardware fault.

	 Action to be Taken: If the SPC switchover was unplanned, the admin logs should
	 be examined for the cause of the switchover.  If the cause was a software failure,
	 the system crash logs should be examined.

	 Clear Condition: Verify the SPC switchover completes successfully.

	 Clear Condition Alarm: A starCardSPCSwitchoverComplete is generated when the
	 switchover operation has completed."
    --#SUMMARY "[Card SPC-%d] Switchover started to card SPC-%d"
    --#ARGUMENTS {0,1}
    --#STATE DEGRADED
    --#SEVERITY MAJOR
    ::= { starentTraps 19 }

starCardSPCSwitchoverComplete NOTIFICATION-TYPE
    OBJECTS { starSlotNum }
    STATUS  deprecated
    DESCRIPTION
	"An SPC Switchover has completed successfully.  The starSlotNum varbind identifies the
         new primary SPC

	 Action to be Taken: If the SPC switchover was unplanned, the admin logs should
	 be examined for the cause of the switchover.  If the cause was a software failure,
	 the system crash logs should be examined."
    --#SUMMARY "[Card SPC-%d] Switchover complete to card SPC-%d"
    --#ARGUMENTS {0,0}
    --#STATE OPERATIONAL
    --#SEVERITY INFORMATIONAL
    ::= { starentTraps 20 }

starCardSPCSwitchoverFailed NOTIFICATION-TYPE
    OBJECTS { starSlotNum, starSlotNum }
    STATUS  deprecated
    DESCRIPTION
	"An SPC switchover operation has failed.  The first varbind identifies the SPC
         that was attempted to be switched away from; the second varbind identifies the SPC
         that was attempted to be switched to.

	 Probable Cause: The SPC being migrated to was removed or reset before
	 the migration completed; the migration operation was terminated by an
 	 operator; or a software or hardware failure on either SPC.

	 Action to be Taken: Verify that both SPCs have the card locks in the locked
	 position; examine the admin logs for the cause of the failure.  If the cause was
	 a software failure, the system crash logs should be examined.

	 Clear Condition: The SPC in question will be reset; a starCardUp notification will be
	 generated when the card is operational again."
    --#SUMMARY "[Card SPC-%d] Switchover failed to card SPC-%d"
    --#ARGUMENTS {0,1}
    --#STATE NONOPERATIONAL
    --#SEVERITY CRITICAL
    ::= { starentTraps 21 }

-- Fan Notifications

starFanFailed NOTIFICATION-TYPE
    OBJECTS { starFanNum,
	      starFanStatus }
    STATUS  current
    DESCRIPTION
        "One of more fans have failed on the indicated fan controller.

	 Probable Cause: A hardware failure on the fan tray.  The fan tray should
	 be replaced.

	 Action to be Taken: Verify there is no physical obstruction to the fans;
	 Replace the fan tray.

	 Clear Condition: Verify the fans are running

	 Condition Clear Alarm: A starFanInserted notification will be generated when the
	 fan tray is replaced.
     This is not applicable to QVPC-SI and QVPC-DI."
    --#SUMMARY "[FTC] Fan failure fan number %d fan status %s"
    --#ARGUMENTS {0,1}
    --#STATE DEGRADED
    --#SEVERITY MAJOR
    ::= { starentTraps 22 }

starFanRemoved NOTIFICATION-TYPE
    OBJECTS { starFanNum }
    STATUS  current
    DESCRIPTION
        "A fan tray has been removed

	 Action to be Taken: Replace the fan tray

	 Clear Condition: Verify both fan trays are present and operational.

	 Condition Clear Alarm: A starFanInserted notification will be generated when the
	 fan tray is replaced.
     This is not applicable to QVPC-SI and QVPC-DI."
    --#SUMMARY "[FTC] Fan tray removed fan number %d"
    --#ARGUMENTS {0}
    --#STATE DEGRADED
    --#SEVERITY MAJOR
    ::= { starentTraps 23 }

starFanInserted NOTIFICATION-TYPE
    OBJECTS { starFanNum }
    STATUS  current
    DESCRIPTION
        "A fan tray has been inserted
         This is not applicable to QVPC-SI and QVPC-DI."
    --#SUMMARY "[FTC] Fan tray inserted fan number %d"
    --#ARGUMENTS {0}
    --#STATE OPERATIONAL
    --#SEVERITY INFORMATIONAL
    ::= { starentTraps 24 }

-- Log Notifications.

starLogThreshold NOTIFICATION-TYPE
    OBJECTS { starLogName,
	      starLogCurSize,
              starLogMaxSize }
    STATUS  obsolete
    DESCRIPTION
        "A system log has reached its maximum size.  This trap is obsolete."
    ::= { starentTraps 25 }

-- CPU Notifications

starCPUBusy NOTIFICATION-TYPE
    OBJECTS { starCPUSlot, starCPUNumber }
    STATUS  current
    DESCRIPTION
        "The CPU is experiencing very high usage.

	 Probable Cause: For SPC/SMC CPUs this typically represents an abnormal amount
	 of management (CLI, SNMP, CORBA) requests.  For PAC/PSC cards this indicates
	 that the system is reaching its capacity.

	 Action to be Taken: For SPC/SMC cards, this may be a transient condition because
	 of a burst of management activity.  Monitor the CPU usage and if it is persistently
	 high, examine the CPU table to determine which management activity is causing the
	 excessive usage.  For PAC/PSC cards, this indicates the system is nearing its overall
	 capacity.  Monitor CPU usage and if it is persistently high, the system may need
	 additional PACs/PSCs to keep up with the system load.

	 Clear Condition: Verify that CPU usage returned to a normal load.
	 This can represent a transient condition; the trap will be periodically
	 repeated if the condition persists."
    --#SUMMARY "[Card %d] CPU %d is experiencing very high usage"
    --#ARGUMENTS {0,1}
    --#STATE DEGRADED
    --#SEVERITY MAJOR
    ::= { starentTraps 26 }

starCPUMemoryLow NOTIFICATION-TYPE
    OBJECTS { starCPUSlot, starCPUNumber }
    STATUS  current
    DESCRIPTION
        "The CPU is experiencing a low memory condition.

	 Probable Cause: For SPC CPUs this typically represents an abnormal number
	 of management sessions, in particular CLI sessions.  For PAC/PCS cards this
	 indicates that the system is reaching its capacity.

	 Action to be Taken: For SPC cards, this may be a transient condition because
	 of a burst of management activity.  Monitor memory usage and if it is persistently
	 high, examine the CPU table to determine which management activity is causing the
	 excessive usage.  Verify that large numbers of CLI sessions are not being generated
	 and, if needed, terminate extra sessions.  For PAC/PCS cards, this indicated the system
	 is nearing its overall capacity.  Monitor memory usage and if it is persistently high,
	 the system may need additional PACs/PCSs or additional PAC/PCS memory to keep up with the
	 system load.

	 Clear Condition: Verify that memory usage returned to a normal load.
	 This can represent a transient condition; the trap will be periodically
	 repeated if the condition persists."
    --#SUMMARY "[Card %d] CPU %d is low on available memory"
    --#ARGUMENTS {0,1}
    --#STATE DEGRADED
    --#SEVERITY MAJOR
    ::= { starentTraps 27 }

starCPUMemoryFailed NOTIFICATION-TYPE
    OBJECTS { starCPUSlot, starCPUNumber }
    STATUS  current
    DESCRIPTION
        "The memory on this CPU has failed.

	 Probable Cause: This indicates a hardware problem.

	 Action to be Taken: Replace the failing card.

	 The card will be reset; a starCardUp will be generated if the card
	 is restored to an operational state."
    --#SUMMARY "[Card %d] CPU %d memory failure"
    --#ARGUMENTS {0,1}
    --#STATE NONOPERATIONAL
    --#SEVERITY CRITICAL
    ::= { starentTraps 28 }

starCPUFailed NOTIFICATION-TYPE
    OBJECTS { starCPUSlot, starCPUNumber }
    STATUS  current
    DESCRIPTION
        "The CPU has failed.

	 Probable Cause: This indicates a hardware problem.

	 Action to be Taken: Replace the failing card.

	 The card will be reset; a starCardUp will be generated if the card
 	 is restored to an operational state."
    --#SUMMARY "[Card %d] CPU %d failure"
    --#ARGUMENTS {0,1}
    --#STATE NONOPERATIONAL
    --#SEVERITY CRITICAL
    ::= { starentTraps 29 }

starCPUWatchDogExpired NOTIFICATION-TYPE
    OBJECTS { starCPUSlot, starCPUNumber }
    STATUS  current
    DESCRIPTION
        "The watch dog timer has failed on this CPU.

	 Probable Cause; This could indicate an extremely busy CPU, a
	 software problem, or a hardware issue.

	 Action to be Taken: Check the admin logs for an indication of the
	 problem.  Check the system crash logs for an indication of software
	 problems.  If the problem persists, replace the card.

	 Clear Condition: Verify that an SPC/SMC switchover or PAC/PSC migration completes
	 successfully to recover from the failure condition.

	 Condition Clear Alarm: A starCardUp will be generated if the card
 	 is restored to an operational state."
    --#SUMMARY "[Card %d] CPU %d watchdog expiry"
    --#ARGUMENTS {0,1}
    --#STATE NONOPERATIONAL
    --#SEVERITY CRITICAL
    ::= { starentTraps 30 }

-- NPU Manager Notifications

starNPUARPPoolExhausted NOTIFICATION-TYPE
    OBJECTS { starNPUMgrNumber }
    STATUS  current
    DESCRIPTION
        "The ARP pool on this NPU manager is exhausted.  When this occurs, the ARP
	 entry isn't added and traffic to the local device is fowarded through
	 a slower path.

	 Action To Be Taken: Reduce the total number of directly connected devices
	 or clear ARP entries."
    --#SUMMARY "[System] NPU ARP pool exhausted for NPU Manager %d"
    --#ARGUMENTS {0}
    --#STATE DEGRADED
    --#SEVERITY MAJOR
    ::= { starentTraps 31 }

-- Power Notifications

starPowerFilterUnitFailed NOTIFICATION-TYPE
    OBJECTS { starPowerNumber }
    STATUS  deprecated
    DESCRIPTION
        "A Power Filter Unit (PFU) failed.

	 Probable Cause:  The external power source has failed or has been
	 disconnected, or a hardware failure on the PFU.

	 Action to be Taken: Verify that the input power to the power filter
	 is operational and repair if needed.  Verify that the connections to
	 the power filter are intact and that the power filter is properly
	 inserted into the chassis.  Replace the power filter if required.

	 Clear Condition: Verify that both power filters are operating.

	 Condition Clear Alarm: A starPowerFilterAvail will be generated
	 when the power filter is replaced."
    --#SUMMARY "[Power %d] Power filter has failed."
    --#ARGUMENTS {0}
    --#STATE DEGRADED
    --#SEVERITY MAJOR
    ::= { starentTraps 32 }

starPowerFilterUnitUnavail NOTIFICATION-TYPE
    OBJECTS { starPowerNumber }
    STATUS  current
    DESCRIPTION
        "A Power Filter Unit (PFU) is unavailable.

	 Probable Cause: The power filter has been removed from the chassis,
	 or no power is being provided to the PFU.

	 Action to be Taken: If the power filter removal wasn't planned,
	 Verify that the input power to the power filter
	 is operational and repair if needed.  Verify that the connections to
	 the power filter are intact and that the power filter is properly
	 inserted into the chassis.  Replace the power filter if required.

	 Clear Condition: Verify that both power filters are operating.

	 Condition Clear Alarm: A starPowerFilterUnitAvail will be generated
	 when the power filter is replaced.
     This is not applicable to QVPC-SI and QVPC-DI."
    --#SUMMARY "[Power %d] Power filter has been removed"
    --#ARGUMENTS {0}
    --#STATE DEGRADED
    --#SEVERITY MAJOR
    ::= { starentTraps 33 }

starPowerFilterUnitAvail NOTIFICATION-TYPE
    OBJECTS { starPowerNumber }
    STATUS  current
    DESCRIPTION
        "A Power Filter Unit (PFU) is available.  This typically means that a PFU has been inserted
         into the chassis or has has its power source restored.

	 Action to be Taken: No action required
     This is not applicable to QVPC-SI and QVPC-DI."
    --#SUMMARY "[Power %d] Power filter is available"
    --#ARGUMENTS {0}
    --#STATE OPERATIONAL
    --#SEVERITY INFORMATIONAL
    ::= { starentTraps 34 }

starAlertsDisabled NOTIFICATION-TYPE
    OBJECTS { starMaxAlertsPerTime,
              starWindowTime }
    STATUS  current
    DESCRIPTION
        "The sending of SNMP Traps has been disabled because too many alerts were generated
         within the defined window type

	 Probable Cause: Either a large number of SNMP notifications are being generated,
	 or the configured threshold which limits the number of notifications is set too
	 aggressively.

	 Actions to be Taken: Examine the admin logs and the SNMP trap logs to determine
	 the source of the large number of traps and take appropriate actions; verify that
	 the configured limit for the rate at which traps will be sent is appropriate for
	 your environment.

	 Clear Condition Alarm: When the rate of SNMP notifications goes down a
	 starAlertsEnabled notification is generated"
    --#SUMMARY "[System] SNMP alarts disabled; %d alerts generated in %d seconds"
    --#ARGUMENTS {0,1}
    --#STATE OPERATIONAL
    --#SEVERITY MINOR
    ::= { starentTraps 37 }

starAlertsEnabled NOTIFICATION-TYPE
    STATUS  current
    DESCRIPTION
        "The sending of SNMP Traps has been reenabled"
    --#SUMMARY "[System] SNMP alert re-enabled"
    --#STATE OPERATIONAL
    --#SEVERITY INFORMATIONAL
    ::= { starentTraps 38 }

-- AAA Failures

starAAAAuthServerUnreachable NOTIFICATION-TYPE
    OBJECTS { radiusAuthServerIndex, radiusAuthServerAddress }
    STATUS  current
    DESCRIPTION
        "The Authentication, Authorization and Accouting (AAA) server cannot be
         reached.

	 Probable Cause: The AAA server is down, or there is a network issue
	 preventing communication with the AAA server.

	 Actions to be Taken: Restore the AAA server to an operational status;
	 Verify that the AAA server is reachable by performing a 'ping' operation
	 from the CLI in the appropriate context.  Check the admin logs for
	 notification of communication problems.

	 Clear Condition: Verify that communication to the AAA authentication
	 server has been restored.

	 Condition Clear Alarm: When this condition clears a starAAAAuthServerReachable
	 notification will be generated."
    --#SUMMARY "[System] AAA Authentication Server %d (%s) is unreachable"
    --#ARGUMENTS {0,1}
    --#STATE DEGRADED
    --#SEVERITY MAJOR
    ::= { starentTraps 39 }

starAAAAuthServerReachable NOTIFICATION-TYPE
    OBJECTS { radiusAuthServerIndex, radiusAuthServerAddress }
    STATUS  current
    DESCRIPTION
        "The Authentication, Authorization and Accouting (AAA) server is now
         reachable.  This can be the result of a system startup, the configuration
	 of a new server, or a previously unreachable server becoming reachable.

	 Action to be Taken: No Action Required."
    --#SUMMARY "[System] AAA Authentication Server %d (%s) is reachable"
    --#ARGUMENTS {0,1}
    --#STATE OPERATIONAL
    --#SEVERITY INFORMATIONAL
    ::= { starentTraps 40 }

starAAAAuthServerMisconfigured NOTIFICATION-TYPE
    OBJECTS { radiusAuthServerIndex, radiusAuthServerAddress }
    STATUS  current
    DESCRIPTION
	"The Authentication, Authorization and Accounting (AAA) server has been
 	 misconfigured.  This server is not usable until this condition is repaired.

	 Action to be Taken: Examine the system configuration and correct the
	 misconfiguration.  See the user documentation for details on AAA
	 configuration.

	 Clear Condition: Verify that communication to the AAA authentication
	 server has been restored.

	 Condition Clear Alarm: When this condition clears a starAAAAuthServerReachable
	 notification will be generated."
    --#SUMMARY "[System] AAA Authentication Server %d (%s) is misconfigured"
    --#ARGUMENTS {0,1}
    --#STATE DEGRADED
    --#SEVERITY MAJOR
    ::= { starentTraps 41 }

starAAAAccServerUnreachable NOTIFICATION-TYPE
    OBJECTS { radiusAccServerIndex, radiusAccServerAddress }
    STATUS  current
    DESCRIPTION
        "The Authentication, Authorization and Accouting (AAA) server cannot be
         reached.

	 Probable Cause: The AAA server is down, or there is a network issue
	 preventing communication with the AAA server.

	 Actions to be Taken: Restore the AAA server to an operational status;
	 Verify that the AAA server is reachable by performing a 'ping' operation
	 from the CLI in the appropriate context.  Check the admin logs for
	 notification of communication problems.

	 Clear Condition: Verify that communication to the AAA accounting
	 server has been restored.

	 Condition Clear Alarm: When this condition clears a starAAAAccServerReachable
	 notification will be generated."
    --#SUMMARY "[System] AAA Accounting Server %d (%s) is unreachable"
    --#ARGUMENTS {0,1}
    --#STATE DEGRADED
    --#SEVERITY MAJOR
    ::= { starentTraps 42 }

starAAAAccServerReachable NOTIFICATION-TYPE
    OBJECTS { radiusAccServerIndex, radiusAccServerAddress }
    STATUS  current
    DESCRIPTION
        "The Authentication, Authorization and Accouting (AAA) server is now
         reachable.  This can be the result of a system startup, the configuration
	 of a new server, or a previously unreachable server becoming reachable.

	 Note that since Accounting servers are not responding to 'hello'-type
	 messages, it is not always possible to accurately determine when an accounting
	 server is reachable.  A server may be declared 'reachable' when the ST16
	 is ready to start using the server, but before any acknowledgement is actually
	 received from the server.  Once accounting information actually is sent to the
	 server a starAAAAccServerUnreachable will be generated if the server does
	 not properly respond.

	 Action to be Taken: No Action Required."
    --#SUMMARY "[System] AAA Authentication Server %d (%s) is reachable"
    --#ARGUMENTS {0,1}
    --#STATE OPERATIONAL
    --#SEVERITY INFORMATIONAL
    ::= { starentTraps 43 }

starAAAAccServerMisconfigured NOTIFICATION-TYPE
    OBJECTS { radiusAccServerIndex, radiusAccServerAddress }
    STATUS  current
    DESCRIPTION
	"The Authentication, Authorization and Accounting (AAA) server has been
	 misconfigured.  This server is not usable until this condition is repaired.

	 Action to be Taken: Examine the system configuration and correct the
	 misconfiguration.  See the user documentation for details on AAA
	 configuration.

	 Clear Condition: Verify that communication to the AAA authentication
	 server has been restored.

	 Condition Clear Alarm: When this condition clears a starAAAAccServerReachable
	 notification will be generated."
    --#SUMMARY "[System] AAA Accounting Server %d (%s) is misconfigured"
    --#ARGUMENTS {0,1}
    --#STATE DEGRADED
    --#SEVERITY MAJOR
    ::= { starentTraps 44 }

--- Log Message, debugging use only

starLogMsg NOTIFICATION-TYPE
    OBJECTS { starLogText }
    STATUS  current
    DESCRIPTION
        "A log message.  This trap is used only for debugging.This is not applicable to QVPC-SI and QVPC-DI."
    --#SUMMARY "[System] Log message: %s"
    --#ARGUMENTS {0}
    --#STATE OPERATIONAL
    --#SEVERITY INFORMATIONAL
    ::= { starentTraps 45 }

--- Service Traps

starPDSNServiceStart NOTIFICATION-TYPE
    OBJECTS { starServiceVpnName, starServiceServName }
    STATUS  current
    DESCRIPTION
        "A PDSN Service has started

	 Action to be Taken: No action required"
    --#SUMMARY "[Service PDSN-%s-%s] PDSN service has started"
    --#ARGUMENTS {0,1}
    --#STATE OPERATIONAL
    --#SEVERITY INFORMATIONAL
    ::= { starentTraps 46 }

starPDSNServiceStop NOTIFICATION-TYPE
    OBJECTS { starServiceVpnName, starServiceServName }
    STATUS  current
    DESCRIPTION
        "A PDSN Service has stopped.

	 Probable Cause: This is typically caused by operator invention.  In
         unusual cases it can be caused by the loss of resources (PACs/PSCs) to
	 support the running configuration.

	 Action to be Taken: If the PDSN service shutdown was not planned,
	 examine the admin logs for an indication of the failure.  Verify that
	 all configured PACs/PSCs are present and running in the system.  Check the
	 crash logs for an indication of a software failure.

	 Clear Condition: Verify that the PDSN service is operational.

	 Condition Clear Alarm:  A starPDSNServiceStart notification will be generated when
	 the service is restarted"
    --#SUMMARY "[Service PDSN-%s-%s] PDSN service has stopped"
    --#ARGUMENTS {0,1}
    --#STATE DEGRADED
    --#SEVERITY MAJOR
    ::= { starentTraps 47 }

starHAServiceStart NOTIFICATION-TYPE
    OBJECTS { starServiceVpnName, starServiceServName }
    STATUS  current
    DESCRIPTION
        "An HA Service has started

	 Action to be Taken: No action required"
    --#SUMMARY "[Service HA-%s-%s] HA service has started"
    --#ARGUMENTS {0,1}
    --#STATE OPERATIONAL
    --#SEVERITY INFORMATIONAL
    ::= { starentTraps 48 }

starHAServiceStop NOTIFICATION-TYPE
    OBJECTS { starServiceVpnName, starServiceServName }
    STATUS  current
    DESCRIPTION
        "An HA Service has stopped

	 Probable Cause: This is typically caused by operator invention.  In
         unusual cases it can be caused by the loss of resources (PACs/PSCs) to
	 support the running configuration.

	 Action to be Taken: If the PDSN service shutdown was not planned,
	 examine the admin logs for an indication of the failure.  Verify that
	 all configured PACs/PSCs are present and running in the system.  Check the
	 crash logs for an indication of a software failure.

	 Clear Condition: Verify that the PDSN service is operational.

	 Condition Clear Alarm:  A starHAServiceStart notification will be generated when
	 the service is restarted"
    --#SUMMARY "[Service HA-%s-%s] HA service has stopped"
    --#ARGUMENTS {0,1}
    --#STATE DEGRADED
    --#SEVERITY MAJOR
    ::= { starentTraps 49 }

starFAServiceStart NOTIFICATION-TYPE
    OBJECTS { starServiceVpnName, starServiceServName }
    STATUS  current
    DESCRIPTION
        "An FA Service has started

	 Action to be Taken: No action required"
    --#SUMMARY "[Service FA-%s-%s] FA service has started"
    --#ARGUMENTS {0,1}
    --#STATE OPERATIONAL
    --#SEVERITY INFORMATIONAL
    ::= { starentTraps 50 }

starFAServiceStop NOTIFICATION-TYPE
    OBJECTS { starServiceVpnName, starServiceServName }
    STATUS  current
    DESCRIPTION
        "An FA Service has stopped

	 Probable Cause: This is typically caused by operator invention.  In
         unusual cases it can be caused by the loss of resources (PACs/PSCs) to
	 support the running configuration.

	 Action to be Taken: If the FA service shutdown was not planned,
	 examine the admin logs for an indication of the failure.  Verify that
	 all configured PACs/PSCs are present and running in the system.  Check the
	 crash logs for an indication of a software failure.

	 Clear Condition: Verify that the FA service is operational.

	 Condition Clear Alarm:  A starFAServiceStart notification will be generated when
	 the service is restarted"
    --#SUMMARY "[FA %s-%s] FA service has stopped"
    --#ARGUMENTS {0,1}
    --#STATE DEGRADED
    --#SEVERITY MAJOR
    ::= { starentTraps 51 }

starCLISessionStart NOTIFICATION-TYPE
    OBJECTS { starCLIUsername, starCLIPrivs, starCLITtyname }
    STATUS  current
    DESCRIPTION
        "An interactive CLI session has started

	 A starCLISessionEnd notification will be sent when the CLI
	 session is terminated."
    --#SUMMARY "[System] CLI session for %s %s started on %s"
    --#ARGUMENTS {1,0,2}
    --#STATE OPERATIONAL
    --#SEVERITY INFORMATIONAL
    ::= { starentTraps 52 }

starCLISessionEnd NOTIFICATION-TYPE
    OBJECTS { starCLIUsername, starCLIPrivs, starCLITtyname }
    STATUS  current
    DESCRIPTION
        "An interactive CLI session has ended.

	 The CLI session may have been terminated by the CLI user; the session
	 may have expired due to an idle timeout, or a session timeout; or the
	 session may have been terminated by operator intervention."
    --#SUMMARY "[System] CLI session for %s %s ended on %s"
    --#ARGUMENTS {1,0,2}
    --#STATE OPERATIONAL
    --#SEVERITY INFORMATIONAL
    ::= { starentTraps 53 }

starCritTaskFailed NOTIFICATION-TYPE
    OBJECTS { starTaskFacilityName, starTaskInstance, starTaskCard, starTaskCPU }
    STATUS  current
    DESCRIPTION
        "A critical task has failed and the appropriate recovery steps begun.
	 The card containing the failed task will be restarted; migration/recovery
	 operations will proceed.

	 Probable Cause: Software error

	 Actions to be Taken: Examine the admin logs for an indication of the source
	 of the failure.

	 Clear Condition: Verify that an SPC switchover or PAC/PSC migration completes
	 to recover from this condition.

	 Condition Clear Alarm:  A starCardUp will be generated when the card
	 has successfully restarted."
    --#SUMMARY "[Card %d] Task %s/%d on CPU %d has failed"
    --#ARGUMENTS {2,0,1,3}
    --#STATE NONOPERATIONAL
    --#SEVERITY CRITICAL
    ::= { starentTraps 54 }

starCardActive NOTIFICATION-TYPE
    OBJECTS { starSlotNum,
              starCardType,
              starSlotSerialNumber}
    STATUS  current
    DESCRIPTION
        "The card is now active.This is not applicable to QVPC-SI."
    --#SUMMARY "[%s-%d] Card is active UUID %s"
    --#ARGUMENTS {1,0,2}
    --#STATE OPERATIONAL
    --#SEVERITY INFORMATIONAL
    ::= { starentTraps 55 }

starLACServiceStart NOTIFICATION-TYPE
    OBJECTS { starServiceVpnName, starServiceServName }
    STATUS  current
    DESCRIPTION
        "A LAC Service has started

	 Action to be Taken: No action required"
    --#SUMMARY "[Service LAC-%s-%s] LAC service has started"
    --#ARGUMENTS {0,1}
    --#STATE OPERATIONAL
    --#SEVERITY INFORMATIONAL
    ::= { starentTraps 56 }

starLACServiceStop NOTIFICATION-TYPE
    OBJECTS { starServiceVpnName, starServiceServName }
    STATUS  current
    DESCRIPTION
        "A LAC Service has stopped

	 Probable Cause: This is typically caused by operator invention.  In
         unusual cases it can be caused by the loss of resources (PACs/PSCs) to
	 support the running configuration.

	 Action to be Taken: If the LAC service shutdown was not planned,
	 examine the admin logs for an indication of the failure.  Verify that
	 all configured PACs/PSCs are present and running in the system.  Check the
	 crash logs for an indication of a software failure.

	 Clear Condition: Verify that the LAC service is operational.

	 Condition Clear Alarm:  A starLACServiceStart notification will be generated when
	 the service is restarted"
    --#SUMMARY "[Service LAC-%s-%s] LAC service has stopped"
    --#ARGUMENTS {0,1}
    --#STATE DEGRADED
    --#SEVERITY MAJOR
    ::= { starentTraps 57 }

starLNSServiceStart NOTIFICATION-TYPE
    OBJECTS { starServiceVpnName, starServiceServName }
    STATUS  current
    DESCRIPTION
        "A LNS Service has started

	 Action to be Taken: No Action Required"
    --#SUMMARY "[Service LNS-%s-%s] LNS service has started"
    --#ARGUMENTS {0,1}
    --#STATE OPERATIONAL
    --#SEVERITY INFORMATIONAL
    ::= { starentTraps 58 }

starLNSServiceStop NOTIFICATION-TYPE
    OBJECTS { starServiceVpnName, starServiceServName }
    STATUS  current
    DESCRIPTION
        "A LNS Service has stopped

	 Probable Cause: This is typically caused by operator invention.  In
         unusual cases it can be caused by the loss of resources (PACs/PSCs) to
	 support the running configuration.

	 Action to be Taken: If the LNS service shutdown was not planned,
	 examine the admin logs for an indication of the failure.  Verify that
	 all configured PACs/PSCs are present and running in the system.  Check the
	 crash logs for an indication of a software failure.

	 Clear Condition: Verify that the LNS service is operational.

	 Condition Clear Alarm:  A starLNSServiceStart notification will be generated when
	 the service is restarted"
    --#SUMMARY "[Service LNS-%s-%s] LNS service has stopped"
    --#ARGUMENTS {0,1}
    --#STATE DEGRADED
    --#SEVERITY MAJOR
    ::= { starentTraps 59 }

starCardDown NOTIFICATION-TYPE
    OBJECTS { starSlotNum,
              starCardType,
              starSlotSerialNumber}
    STATUS  current
    DESCRIPTION
        "The card is now down.

	 Probable Cause: The card was shut down by an operator; the card was
	 removed by an operator; or a hardware or software fault caused the
         card to shut down.  In the latter case an additional notification is
	 generated with the specific failure.

	 Action to be Taken: If the card shutdown was not planned, verify that
	 the card is present in the system and its card lock is in the locked
	 position.  Check the admin logs for the cause of the card shutdown.

	 Clear Condition: Verify that an SPC switchover/card migration completes
	 to recover from the card shutdown.

	 Condition Clear Alarm: A starCardUp notification is generated when the card is restarted.
         This is not applicable to QVPC-SI."
    --#SUMMARY "[Card %s-%d] Card down UUID %s"
    --#ARGUMENTS {1,0,2}
    --#STATE NONOPERATIONAL
    --#SEVERITY CRITICAL
    ::= { starentTraps 60 }


-- The Following two traps are using the Standard MIB
-- See rfc2495 and rfc2496
-- ds3Traps OBJECT IDENTIFIER ::= {ds3 15}
-- starDsx3LineStatusChange NOTIFICATION-TYPE
-- ::= { starentTraps 61 }
-- severity INFORMATIONAL
-- This is not applicable to QVPC-SI and QVPC-DI.

-- ds1Traps OBJECT IDENTIFIER ::= {ds1 15}
-- starDsx1LineStatusChange NOTIFICATION-TYPE
-- ::= { starentTraps 62 }
-- severity INFORMATIONAL
-- This is not applicable to QVPC-SI and QVPC-DI.

starGGSNServiceStart NOTIFICATION-TYPE
    OBJECTS { starServiceVpnName, starServiceServName }
    STATUS  current
    DESCRIPTION
        "A GGSN Service has started

	 Action to be Taken: No action required"
    --#SUMMARY "[Service GGSN-%s-%s] GGSN service has started"
    --#ARGUMENTS {0,1}
    --#STATE OPERATIONAL
    --#SEVERITY INFORMATIONAL
    ::= { starentTraps 63 }

starGGSNServiceStop NOTIFICATION-TYPE
    OBJECTS { starServiceVpnName, starServiceServName }
    STATUS  current
    DESCRIPTION
        "A GGSN Service has stopped

	 Probable Cause: This is typically caused by operator invention.  In
         unusual cases it can be caused by the loss of resources (PACs/PSCs) to
	 support the running configuration.

	 Action to be Taken: If the GGSN service shutdown was not planned,
	 examine the admin logs for an indication of the failure.  Verify that
	 all configured PACs/PSCs are present and running in the system.  Check the
	 crash logs for an indication of a software failure.

	 Clear Condition: Verify that the GGSN service is operational.

	 Condition Clear Alarm:  A starGGSNServiceStart notification will be generated when
	 the service is restarted"
    --#SUMMARY "[Service GGSN-%s-%s] GGSN service has stopped"
    --#ARGUMENTS {0,1}
    --#STATE DEGRADED
    --#SEVERITY MAJOR
    ::= { starentTraps 64 }

starLicenseExceeded NOTIFICATION-TYPE
    OBJECTS { starLicensedSessions, starCurrentSessions, starServiceType }
    STATUS current
    DESCRIPTION
	"The licenses session limit has been exceeded; note that a small number of
	 sessions are permitted beyond the licensed limit.

	 Probable Cause: The usage of the system has exceeded the capacity of the
         license installed; The license installed does not match the identification
         of the system; No license is installed

	 Action to be Taken: Verify that the proper license is installed on the
	 system; verify that the SPCs present in the system match those identified
	 in the software license.  If required, install an additional higher-capacity
	 license.

	 Clear Condition: This condition is cleared when usage goes under the licensed
	 limit.

	 Condition Clear Alarm: This condition is cleared by a starLicenseUnderLimit
	 notification."
    --#SUMMARY "[System] License Exceeded for %s service; current sessions %d exceeds license %d"
    --#ARGUMENTS {2,0,1}
    --#STATE DEGRADED
    --#SEVERITY MAJOR
    ::= { starentTraps 65 }

starSubscriberLimit NOTIFICATION-TYPE
    OBJECTS { starServiceVpnName, starServiceServName, starServiceSubLimit, starServiceSubCurrent, starServiceType }
    STATUS current
    DESCRIPTION
	"The specified service has reached its configured limit for number of subscribers

	 Action to be Taken: Verify that the configured subscriber limit is correct.
	 Configure additional services, or configure the existing service to permit
	 a larger number of subscribers"
    --#SUMMARY "[System] License Exceeded for %s service %s-%s; current sessions %d exceeds license %d"
    --#ARGUMENTS {4,0,1,3,2}
    --#STATE DEGRADED
    --#SEVERITY MAJOR
    ::= { starentTraps 66 }

starSessionRejectNoResource NOTIFICATION-TYPE
    OBJECTS { starServiceVpnName, starServiceType }
    STATUS current
    DESCRIPTION
	"A session setup was rejected because of a lack of available resources

	 Probable Cause: The system has reached its maximum capacity based on the
	 number of available PACs/PSCs/CPUs/memory.

	 Actions to be Taken: Examine the system CPU table to determine if there
	 is abnormal system usage or if the system is reaching its capacity.
	 If this condition persists, additional PACs/PSCs or PAC/PSC memory may be required.
	 Note that there is a configuration threshold which can be setup to monitor
	 the number of NORESOURCE rejects."
    --#SUMMARY "[System] Session rejected NORESOURCE for %s service of type %d"
    --#ARGUMENTS {0,1}
    --#STATE DEGRADED
    --#SEVERITY MAJOR
    ::= { starentTraps 67 }

starLongDurTimerExpiry NOTIFICATION-TYPE
    OBJECTS { starSubContext, starSubMSID, starSubName, starSubTimerDuration, starSubLongDurTimeoutAction, starSubSetupTime, starSubHomeAddr, starSubHomeAddrv6 }
    STATUS current
    DESCRIPTION
	"The long duration timer has expired for the identified subscriber.

	 Note that either starSubHomeAddr or starSubHomeAddrv6 is typically filled in,
	 as appropriate.  The other attribute will be all zero octets.

	 Action to be Taken: No action is typically required.  If an abnormal
	 number of expiries occur, verify that the configuration expiry time
	 is correct"
    --#SUMMARY "[System] context %s subscriber name %s MSID %s timer duration %d timeout action %d setup time %s home address(ipv4/ipv6) %s"
    --#ARGUMENTS {0,2,1,3,4,5,6}
    --#STATE OPERATIONAL
    --#SEVERITY INFORMATIONAL
    ::= { starentTraps 68 }

starClosedRPServiceStart NOTIFICATION-TYPE
    OBJECTS { starServiceVpnName, starServiceServName }
    STATUS  current
    DESCRIPTION
        "Closed RP Service has started

	 Action to be Taken: No action required"
    --#SUMMARY "[Service CLOSEDRP-%s-%s] Closed RP service has started"
    --#ARGUMENTS {0,1}
    --#STATE OPERATIONAL
    --#SEVERITY INFORMATIONAL
    ::= { starentTraps 69 }

starClosedRPServiceStop NOTIFICATION-TYPE
    OBJECTS { starServiceVpnName, starServiceServName }
    STATUS  current
    DESCRIPTION
        "Closed RP Service has stopped

	 Probable Cause: This is typically caused by operator invention.  In
         unusual cases it can be caused by the loss of resources (PACs/PSCs) to
	 support the running configuration.

	 Action to be Taken: If the Closed RP service shutdown was not planned,
	 examine the admin logs for an indication of the failure.  Verify that
	 all configured PACs/PSCs are present and running in the system.  Check the
	 crash logs for an indication of a software failure.

	 Clear Condition: Verify that the Closed RP service is operational.

	 Condition Clear Alarm:  A starClosedRPServiceStart notification will be generated when
	 the service is restarted"
    --#SUMMARY "[Service CLOSEDRP-%s-%s] Closed RP service has stopped"
    --#ARGUMENTS {0,1}
    --#STATE DEGRADED
    --#SEVERITY MAJOR
    ::= { starentTraps 70 }

starGtpcPathFailure NOTIFICATION-TYPE
    OBJECTS {starSessGGSNVpnName, starSessGGSNServName, starSessGGSNPeerAddr }
    STATUS  current
    DESCRIPTION
        "GTP Control Path Failure."
    --#SUMMARY "[Service GGSN-%s-%s] GTP control path failure to %s"
    --#ARGUMENTS {0,1,2}
    --#STATE DEGRADED
    --#SEVERITY MAJOR
    ::= { starentTraps 71 }

starGtpuPathFailure NOTIFICATION-TYPE
    OBJECTS {starSessGGSNVpnName, starSessGGSNServName, starSessGGSNPeerAddr }
    STATUS  current
    DESCRIPTION
        "GTP Data Path Failure."
    --#SUMMARY "[Service GGSN-%s-%s] GTP data path failure to %s"
    --#ARGUMENTS {0,1,2}
    --#STATE DEGRADED
    --#SEVERITY MAJOR
    ::= { starentTraps 72 }

starManagerFailure NOTIFICATION-TYPE
    OBJECTS { starTaskFacilityName, starTaskInstance, starTaskCard, starTaskCPU}
    STATUS  current
    DESCRIPTION
        "Software manager Failure.

	 Probable Cause: A software failure.  The failing manager will be restarted.

	 Action to be Taken: Examine the admin and crash logs for more information
	 about the failure"
    --#SUMMARY "[System] Manager %s/%d failure on card %d cpu %d"
    --#ARGUMENTS {0,1,2,3}
    --#STATE DEGRADED
    --#SEVERITY MAJOR
    ::= { starentTraps 73 }

starEISServerAlive NOTIFICATION-TYPE
    OBJECTS { starEISServerVPNName, starEISServerAddr }
    STATUS  current
    DESCRIPTION
        "EIS Server alive"
    --#SUMMARY "[System] EIS server alive, VPN %d Server Address %s"
    --#ARGUMENTS {0,1}
    --#STATE OPERATIONAL
    --#SEVERITY INFORMATIONAL
    ::= { starentTraps 74 }

starEISServerDead NOTIFICATION-TYPE
    OBJECTS { starEISServerVPNName, starEISServerAddr }
    STATUS  current
    DESCRIPTION
        "EIS Server down.

	 Probable Cause: The remote EIS server is down or there is a network
	 error making it unreachable.

	 Condition Clear Alarm:  A starEISServerAlive notification will be generated
	 when this condition is cleared"
    --#SUMMARY "[System] EIS server dead, VPN %d Server Address %s"
    --#ARGUMENTS {0,1}
    --#STATE DEGRADED
    --#SEVERITY MAJOR
    ::= { starentTraps 75 }

starCgfAlive NOTIFICATION-TYPE
    OBJECTS { starSessGGSNVpnName, starSessGGSNPeerPort, starSessGGSNPeerAddr }
    STATUS  current
    DESCRIPTION
        "GTPP CGF Server Alive."
    --#SUMMARY "[System] GTPP CGF server alive, VPN %s Server Address %s/%d"
    --#ARGUMENTS {0,2,1}
    --#STATE OPERATIONAL
    --#SEVERITY INFORMATIONAL
    ::= { starentTraps 76 }

starCgfDead NOTIFICATION-TYPE
    OBJECTS { starSessGGSNVpnName, starSessGGSNPeerPort, starSessGGSNPeerAddr }
    STATUS  current
    DESCRIPTION
        "GTPP CGF Server Dead.

	 Probable Cause: The remote CGF server is down or there is a network
	 error making it unreachable.

	 Action to be Taken: Verify that the CGF server is functioning properly;
	 verify network connectivity to the CGF server.

	 Clear Condition: This condition is cleared when the CGF server becomes
	 reachable.

	 Condition Clear Alarm: A starCgfServerAlive notification will be generated
	 when this condition is cleared"
    --#SUMMARY "[System] GTPP CGF server dead, VPN %s Server Address %s/%d"
    --#ARGUMENTS {0,2,1}
    --#STATE DEGRADED
    --#SEVERITY MAJOR
    ::= { starentTraps 77 }

starStorageServerAlive NOTIFICATION-TYPE
    OBJECTS { starSessGGSNVpnName, starSessGGSNPeerAddr }
    STATUS  current
    DESCRIPTION
        "GTPP Storage Server is Alive."
    --#SUMMARY "[System] GTPP Storage Server alive, VPN %s Server Address %s"
    --#ARGUMENTS {0,1}
    --#STATE OPERATIONAL
    --#SEVERITY INFORMATIONAL
    ::= { starentTraps 78 }

starStorageServerDead NOTIFICATION-TYPE
    OBJECTS { starSessGGSNVpnName, starSessGGSNPeerAddr}
    STATUS  current
    DESCRIPTION
        "GTPP Storage Server is Dead.

	 Probable Cause: The remote Storage server is down or there is a network
	 error making it unreachable.

	 Action to be Taken: Verify that the Storage server is functioning properly;
	 verify network connectivity to the Storage server.

	 Clear Condition: This condition is cleared when the Storage server becomes
	 reachable.

	 Condition Clear Alarm: A starStorageServerAlive notification will be generated
	 when this condition is cleared"
    --#SUMMARY "[System] GTPP Storage Server dead, VPN %s Server Address %s"
    --#ARGUMENTS {0,1}
    --#STATE DEGRADED
    --#SEVERITY CRITICAL
    ::= { starentTraps 79 }

starGgsnInitiatedUpdtFailed NOTIFICATION-TYPE
    OBJECTS { starSessGGSNVpnName, starSessGGSNServName, starSessGGSNSubsName,
              starSessGGSNAPNName, starSessGGSNImsi, starSessGGSNPeerAddr}
    STATUS  current
    DESCRIPTION
        "GGSN Initiated Update PDP Context Response Failed.

	 Probable Cause: This can happen if there is an inter-SGSN handoff and
	 the new SGSN is not listed in GGSN service and its PLMN policy is
	 set to reject unknown SGSNs.

	 Action to be Taken: List the SGSN address in the GGSN service.

	 Condition Clear Alarm: NA"
    --#SUMMARY "[System] SGSN Initiated Update PDP context response failed for APN %s Imsi %d, VPN %s Server Address %s"
    --#ARGUMENTS {3,4,0,1}
    --#STATE OPERATIONAL
    --#SEVERITY INFORMATIONAL
    ::= { starentTraps 80 }

starCongestion NOTIFICATION-TYPE
    OBJECTS { starServiceType, starCongestionPolicy, starCongestionResourceType }
    STATUS current
    DESCRIPTION
        "A congestion condition has occurred.

	 Probable Cause:  This is the result of an operator-configured congestion
	 threshold being reached.  This can be due to high usage of the resource
	 being monitored which indicates that the IMG is reaching its peak
	 capacity, or could be caused by the incorrect configuration of the
	 congestion thresholds.

	 Actions to be Taken:  Verify that the congestion thresholds are correct;
	 if the congested state is seem repeatedly, or for sustained periods of
	 time, additional system capacity may need to be brought online.

	 This system is cleared when the use of the specific resource falls below
	 the configured limit.

	 Condition Clear Alarm: A starCongestionClear notification is sent when there
	 are no congestion conditions for a service type"
    --#SUMMARY "[System] Congestion seen for %s service; resource %s, policy %s applied"
    --#ARGUMENTS {0,2,1}
    --#STATE DEGRADED
    --#SEVERITY MAJOR
    ::= { starentTraps 81 }

starCongestionClear NOTIFICATION-TYPE
    OBJECTS { starServiceType }
    STATUS current
    DESCRIPTION
        "A congestion condition has cleared"
    --#SUMMARY "[System] Congestion clear for %s service"
    --#ARGUMENTS {0}
    --#STATE OPERATIONAL
    --#SEVERITY INFORMATIONAL
    ::= { starentTraps 82 }

starServiceLossPTACs NOTIFICATION-TYPE
    OBJECTS { starCardMode, starPTACConfig, starPTACActive }
    STATUS current
    DESCRIPTION
        "A service loss condition has occurred due to PAC/PSC/TAC failure or removal.

	 Probable cause: Multiple PAC/PSC/TAC cards are no longer available, due to failure,
	 removal, or operator action -- or configuration changes have been made which
	 eliminated the availability of redundant cards.

	 Action to be Taken: Bring additional PAC/PSC/TAC cards online to match the
	 number of configured cards, or update the configuration to require fewer
	 active PAC/PSC/TAC cards.

	 Clear Condition: This condition is cleared when the number of active
	 PAC/PSC/TAC cards reaches or exceeds the configured number."
    --#SUMMARY "[System] Service Loss - Not enough PAC/PSC/TACs, %d configured, %d active"
    --#ARGUMENTS {1,2}
    --#STATE NONOPERATIONAL
    --#SEVERITY CRITICAL
    ::= { starentTraps 83 }

starServiceLossLC NOTIFICATION-TYPE
    OBJECTS { starCardType, starSlotNum, starSlotNum }
    STATUS current
    DESCRIPTION
      "A service loss condition has occurred due to LC failure or removal.

       Probable cause: The upper and lower Line Cards (LCs) are both no longer 
       available, due to failure, removal, or operator action.

       Action to be Taken: Fix or replace the line cards.

       Clear Condition: This condition is cleared when one of the two card
       becomes active."
    --#SUMMARY "[System] Service Loss - (%s) Line Cards %d and %d are both unavailable"
    --#ARGUMENTS {0,1,2}
    --#STATE NONOPERATIONAL
    --#SEVERITY CRITICAL
    ::= { starentTraps 84 }

starServiceLossSPIO NOTIFICATION-TYPE
    STATUS current
    DESCRIPTION
        "A service loss condition has occurred due to SPIO failure or removal.

	 NOTE: Since the SPIO contains the ports used for SNMP access, this
	 notification cannot normally be delivered as an SNMP trap.  The notification
	 will be logged and stored in the historical trap list, and if the system
	 is configured to send INFORM PDUs the notification might be delivered
	 at a later time.

	 Probable cause: Both SPIOs are no longer available, due to failure,
	 removal, or operator action.

	 Action to be Taken: Bring at least one SPIO online.

	 Clear Condition: This condition is cleared when a SPIO is made active"
    --#SUMMARY "[System] Service Loss - No SPIO is available"
    --#STATE OPERATIONAL
    --#SEVERITY WARNING
    --NB: Lower severity than other 'service loss' traps as the SPIO does not carry
    --    end-user traffic.
    ::= { starentTraps 85 }

-- IPSP trap

starIPSPAllAddrsFree NOTIFICATION-TYPE
    OBJECTS { starContextName, starInterfaceName }
    STATUS obsolete
    DESCRIPTION
        "All IP addresses are now free on the IP Pool Sharing Protocol (IPSP) primary HA.

	 Probable Cause:  IP Pool Sharing Protocol (IPSP) is running between two HAs
	 (a primary and a secondary).  The primary HA has now released the last address
         that was in use.  This presumably is done in preparation for taking the
	 primary HA out of server.

	 User Action:  Perform the desired maintenance on the primary HA that required
         taking the device out of service."
    --#SUMMARY "[System] IPSP - all IP addresses are now free, context %s interface %s"
    --#ARGUMENTS {0,1}
    --#STATE OPERATIONAL
    --#SEVERITY INFORMATIONAL
    ::= { starentTraps 86 }

-- PCF trap

starPCFUnreachable NOTIFICATION-TYPE
    OBJECTS { starContextName, starPCFAddress }
    STATUS current
    DESCRIPTION
        "A PCF that the IMG communicates which is no longer reachable.

     Probable Cause: The PCF has failed or is otherwise unavailable, or
     a network connectivity problem makes it unreachable.

     Action to be Taken: If the PCF outage was unplanned, restart/reset the
     PCF; verify network connectivity

     Clear Condition: The condition is cleared when the PCF address becomes
     reachable, or if the configuration is changes to not use this server.

     Condition Clear Alarm: A starPCFReachable notification is generated when
     the pcf address becomes reachable."
    --#SUMMARY "[System] PCF Unreachable, VPN %s PCF address %s"
    --#ARGUMENTS {0,1}
    --#STATE DEGRADED
    --#SEVERITY MAJOR
    ::= { starentTraps 87 }


starDhcpAlive NOTIFICATION-TYPE
    OBJECTS { starSessGGSNVpnName, starSessGGSNPeerPort, starSessGGSNPeerAddr }
    STATUS  current
    DESCRIPTION
        "DHCP Server Alive."
    --#SUMMARY "[System] DHCP server alive, VPN %s Server Address %s/%d"
    --#ARGUMENTS {0,2,1}
    --#STATE OPERATIONAL
    --#SEVERITY INFORMATIONAL
    ::= { starentTraps 88 }

starDhcpDead NOTIFICATION-TYPE
    OBJECTS { starSessGGSNVpnName, starSessGGSNPeerPort, starSessGGSNPeerAddr }
    STATUS  current
    DESCRIPTION
        "DHCP Server Dead.

	Probable Cause: The remote DHCP server is down or there is a network
	error making it unreachable.

	Action to be Taken: Verify that the DHCP server is functioning properly;
	verify network connectivity to the DHCP server.

	Clear Condition: The condition is cleared when the DHCP server becomes
	reachable, or if the configuration is changes to not use this server.

	Condition Clear Alarm: A starDhcpAlive notification is generated when
	the server becomes reachable."
    --#SUMMARY "[System] DHCP server dead, VPN %s Server Address %s/%d"
    --#ARGUMENTS {0,2,1}
    --#STATE DEGRADED
    --#SEVERITY MAJOR
    ::= { starentTraps 89 }

-- NTP traps
starNTPPeerUnreachable NOTIFICATION-TYPE
    OBJECTS { starPeerAddress }
    STATUS current
    DESCRIPTION
        "NTP Peer Unreachable.

	 Probable Cause: The NTP server is down or unavailable, or there is a network
	 connectivity issue that prevents access to the NTP server.

	 Action to be Taken: Verify that the NTP server is running properly; verify
	 that the connection to the NTP server is functioning.

	 Clear Condition: This condition is cleared when the NTP server
	 becomes reachable.

	 Condition Clear Alarm: This condition is cleared by a starNTPPeerReachable notification."

    --#SUMMARY "[System] NTP Peer Unreachable; peer address %s"
    --#ARGUMENTS {0}
    --#STATE OPERATIONAL
    --#SEVERITY WARNING
    ::= { starentTraps 90 }

starNTPSyncLost NOTIFICATION-TYPE
    STATUS  current
    DESCRIPTION
        "NTP Synchronization Lost.

	 Probable Cause: All configured NTP server are no longer available, or
	 some/all NTP servers have been unconfigured by an operator.

	 Action to be Taken: Verify that the NTP server(s) are running properly and
	 that the network connections to the NTP servers are available.  Check the
	 configured of the NTP servers for correctness.  If needed, configure
	 additional NTP servers.

	 Clear Condition: This condition is cleared when any (one) NTP server
	 becomes reachable.

	 Condition Clear Alarm: This condition is cleared by a starNTPSyncEstablished notification."

    --#SUMMARY "[System] NTP Sync Lost"
    --#STATE OPERATIONAL
    --#SEVERITY MAJOR
    ::= { starentTraps 91 }


--- L2TP traps
starL2TPTunnelDownPeerUnreachable NOTIFICATION-TYPE
    OBJECTS { 	starL2TPLocalTunnelID,
	        starL2TPPeerTunnelID,
                starL2TPContextName,
	        starL2TPServiceName,
	        starL2TPServiceTypeName,
	        starL2TPLocalAddress,
	        starL2TPPeerAddress }
    STATUS current
    DESCRIPTION
        "L2TP tunnel down due to peer unreachable.

	 Probable Cause: Misconfiguration of the peer router address or
	 inability to route to the peer.

	 Action to be Taken: Verify the peer address is correct; verify that the
	 peer is operational; verify network connectivity to the peer."
    --#SUMMARY "[System] L2TP tunnel down due to peer unreachable, context %s service type %s service name %s local tun id %d peer tun id %d local address %s peer address %s"
    --#ARGUMENTS {2,4,3,0,1,5,6}
    --#STATE OPERATIONAL
    --#SEVERITY WARNING
    ::= { starentTraps 92 }

-- Card traps  again
starCardStandby NOTIFICATION-TYPE
    OBJECTS { starSlotNum,
              starCardType,
              starSlotSerialNumber}
    STATUS  current
    DESCRIPTION
        "The card is now standby.This is not applicable to QVPC-SI."
    --#SUMMARY "[%s-%d] Card is standby UUID %s"
    --#ARGUMENTS {1,0,2}
    --#STATE OPERATIONAL
    --#SEVERITY INFORMATIONAL
    ::= { starentTraps 93 }

starLicenseUnderLimit NOTIFICATION-TYPE
    OBJECTS { starLicensedSessions, starCurrentSessions, starServiceType }
    STATUS current
    DESCRIPTION
	"Usage is now under the licensed session limit."
    --#SUMMARY "[System] System under license limit for %s service; current sessions %d license %d"
    --#ARGUMENTS {2,0,1}
    --#STATE OPERATIONAL
    --#SEVERITY INFORMATIONAL
    ::= { starentTraps 94 }


-- IPSEC

starIPSECPriTunDown NOTIFICATION-TYPE
    OBJECTS { starIPSECContextName, starIPSECGroupName, starIPSECTunLocalIpAddr, starIPSECTunRemoteIpAddr }
    STATUS current
    DESCRIPTION "IPSEC Primary Tunnel Down"
    --#SUMMARY "[System] IPSEC primary tunnel down, context %s, group %s, local ip address %s, remote ip address %s"
    --#ARGUMENTS {0,1,2,3}
    --#STATE DEGRADED
    --#SEVERITY MAJOR
    ::= { starentTraps 95 }

starIPSECPriTunUp NOTIFICATION-TYPE
    OBJECTS { starIPSECContextName, starIPSECGroupName, starIPSECTunLocalIpAddr, starIPSECTunRemoteIpAddr }
    STATUS current
    DESCRIPTION "IPSEC Primary Tunnel Up"
    --#SUMMARY "[System] IPSEC primary tunnel up, context %s, group %s, local ip address %s, remote ip address %s"
    --#ARGUMENTS {0,1,2,3}
    --#STATE OPERATIONAL
    --#SEVERITY INFORMATIONAL
    ::= { starentTraps 96 }

starIPSECSecTunDown NOTIFICATION-TYPE
    OBJECTS { starIPSECContextName, starIPSECGroupName, starIPSECTunLocalIpAddr, starIPSECTunRemoteIpAddr }
    STATUS current
    DESCRIPTION "IPSEC Secondary Tunnel Down"
    --#SUMMARY "[System] IPSEC secondary tunnel down, context %s, group %s, local ip address %s, remote ip address %s"
    --#ARGUMENTS {0,1,2,3}
    --#STATE DEGRADED
    --#SEVERITY MAJOR
    ::= { starentTraps 97 }

starIPSECSecTunUp NOTIFICATION-TYPE
    OBJECTS { starIPSECContextName, starIPSECGroupName, starIPSECTunLocalIpAddr, starIPSECTunRemoteIpAddr }
    STATUS current
    DESCRIPTION "IPSEC Secondary Tunnel Up"
    --#SUMMARY "[System] IPSEC secondary tunnel up, context %s, group %s, local ip address %s, remote ip address %s"
    --#ARGUMENTS {0,1,2,3}
    --#STATE DEGRADED
    --#SEVERITY INFORMATIONAL
    ::= { starentTraps 98 }

starIPSECTunSwitchFail NOTIFICATION-TYPE
    OBJECTS { starIPSECContextName, starIPSECGroupName }
    STATUS current
    DESCRIPTION "IPSEC Tunnel Switchover failed or unable to be attempted"
    --#SUMMARY "[System] IPSEC tunnel switchover failed, context %s, group %s"
    --#ARGUMENTS {0,1}
    --#STATE NONOPERATIONAL
    --#SEVERITY CRITICAL
    ::= { starentTraps 99 }

starIPSECTunSwitchComplete NOTIFICATION-TYPE
    OBJECTS { starIPSECContextName, starIPSECGroupName, starIPSECTunLocalIpAddr, starIPSECTunRemoteIpAddr }
    STATUS current
    DESCRIPTION "IPSEC Tunnel Switchover complete"
    --#SUMMARY "[System] IPSEC tunnel switchover complete, context %s, group %s, active tunnel: local ip address %s, remote ip address %s"
    --#ARGUMENTS {0,1,2,3}
    --#STATE OPERATIONAL
    --#SEVERITY INFORMATIONAL
    ::= { starentTraps 100 }

starNwReachServerAlive NOTIFICATION-TYPE
    OBJECTS { starNwReachName, starNwReachSrvrAddr}
    STATUS  current
    DESCRIPTION
        "Nw Reacheable Server alive"
    --#SUMMARY "[System] Network Reachability server alive, Name %s Server Address %s"
    --#ARGUMENTS {0,1}
    --#STATE OPERATIONAL
    --#SEVERITY INFORMATIONAL
    ::= { starentTraps 101 }

starNwReachServerDead NOTIFICATION-TYPE
    OBJECTS { starNwReachName, starNwReachSrvrAddr}
    STATUS  current
    DESCRIPTION
        "Nw Reacheable Server Dead.

	 Probable Cause: The remote server is down or there is a network
	 error making it unreachable.

	 A starNwReachServerAlive notification will be generated when this condition is cleared"
    --#SUMMARY "[System] Network Reachability server dead, Name %s Server Address %s"
    --#ARGUMENTS {0,1}
    --#STATE OPERATIONAL
    --#SEVERITY MAJOR
    ::= { starentTraps 102 }

starStorageServerUnackedGcdrVolPurge NOTIFICATION-TYPE
    OBJECTS { starSessGGSNVpnName, starSessGGSNPeerAddr }
    STATUS  current
    DESCRIPTION
        "GTPP storage server has performed unacked GCDRs volume purge.

	 Probable Cause: GTPP storage server has purged unacked GCDRs after hitting the
         max allowed configured limit on unacked GCDR in the backup database.

	 Action to be Taken: Check for the unacked file generated for these GCDRs.

	 Clear Condition: There is no clear condition for this notification.

	 Condition Clear Alarm: There is no clear alarm for this notification."

    --#SUMMARY "[System] GTPP Storage Server has performed unacked GCDRs volume purge. VPN %s Server Address %s"
    --#ARGUMENTS {0,1}
    --#STATE OPERATIONAL
    --#SEVERITY CRITICAL
    ::= { starentTraps 103 }

starStorageServerUnackedGcdrFileGen NOTIFICATION-TYPE
    OBJECTS { starSessGGSNVpnName, starSessGGSNPeerAddr }
    STATUS  current
    DESCRIPTION
        "GTPP storage server has exported the unacked GCDRs to file from backup db.

	 Probable Cause: GTPP storage server has generated and saved all the unacked GCDRs to file.

	 Action to be Taken: Operator needs to ftp the generated file.

	 Clear Condition: There is no clear condition for this notification.

	 Condition Clear Alarm: There is no clear alarm for this notification."

    --#SUMMARY "[System] GTPP storage server has exported the unacked GCDRs to file from backup db. VPN %s Server Address %s"
    --#ARGUMENTS {0,1}
    --#STATE OPERATIONAL
    --#SEVERITY INFORMATIONAL
    ::= { starentTraps 104 }

starNTPPeerReachable NOTIFICATION-TYPE
    OBJECTS { starPeerAddress }
    STATUS current
    DESCRIPTION
        "NTP Peer Reachable.

	 Probable Cause: The NTP server is reachable.  This could indicate a newly
	 configured NTP server (including an initial configuration on system startup) or
	 could indicate a previously unreachable server has become reachable.

	 Action to be Taken: No action required."
    --#SUMMARY "[System] NTP Peer Reachable; peer address %s"
    --#ARGUMENTS {0}
    --#STATE OPERATIONAL
    --#SEVERITY INFORMATIONAL
    ::= { starentTraps 105 }

starNTPSyncEstablished NOTIFICATION-TYPE
    STATUS  current
    DESCRIPTION
        "NTP Synchronization Established.

	 Probable Cause: An NTP server is available when previously no server was available.
	 This could indicuate a newly configured NTP server (including an initial configuration
	 on system startup) or could indicate that one or more previously unreachable server(s)
	 has become reachable.

	 Action to be Taken: No action required."
    --#SUMMARY "[System] NTP Sync Established"
    --#STATE OPERATIONAL
    --#SEVERITY INFORMATIONAL
    ::= { starentTraps 106 }

starSIPServiceStart NOTIFICATION-TYPE
    OBJECTS { starServiceVpnName, starServiceServName }
    STATUS  current
    DESCRIPTION
        "A SIP service has started

	 Action to be Taken: No action required"
    --#SUMMARY "[Service SIP-%s-%s] SIP service has started"
    --#ARGUMENTS {0,1}
    --#STATE OPERATIONAL
    --#SEVERITY INFORMATIONAL
    ::= { starentTraps 107 }

starSIPServiceStop NOTIFICATION-TYPE
    OBJECTS { starServiceVpnName, starServiceServName  }
    STATUS  current
    DESCRIPTION
         "A SIP service has stopped

	 Action to be Taken:  No action required"
    --#SUMMARY "[Service SIP-%s-%s] SIP service has stopped"
    --#ARGUMENTS {0,1}
    --#STATE OPERATIONAL
    --#SEVERITY MAJOR
    ::= { starentTraps 108 }

starVIMServiceStart NOTIFICATION-TYPE
    OBJECTS { starServiceVpnName, starServiceServName }
    STATUS current
    DESCRIPTION
          "A VIM service has started

          Action to be taken: No action required"
    --#SUMMARY "[Service VIM-%s-%s] VIM service has started"
    --#ARGUMENTS {0,1}
    --#STATE OPERATIONAL
    --#SEVERITY INFORMATIONAL
    ::= { starentTraps 109 }

starVIMServiceStop NOTIFICATION-TYPE
    OBJECTS { starServiceVpnName, starServiceServName }
    STATUS current
    DESCRIPTION
          "A VIM service has stopped. This is because of application out-of-service
          or if vim is down or no app. server

          Action to be taken: No action required"
    --#SUMMARY "[Service VIM-%s-%s] VIM service has stopped"
    --#ARGUMENTS {0,1}
    --#STATE OPERATIONAL
    --#SEVERITY MAJOR
    ::= { starentTraps 110 }

starCHATCONFServiceStart NOTIFICATION-TYPE
    OBJECTS { starServiceVpnName, starServiceServName }
    STATUS current
    DESCRIPTION
          "A CHAT/CONF service has started

           Action to be taken: No action required"
    --#SUMMARY "[Service CHAT/CONF-%s-%s] CHAT/CONF service has started"
    --#ARGUMENTS {0,1}
    --#STATE OPERATIONAL
    --#SEVERITY INFORMATIONAL
    ::= { starentTraps 111 }

starCHATCONFServiceStop NOTIFICATION-TYPE
    OBJECTS { starServiceVpnName, starServiceServName }
    STATUS current
    DESCRIPTION
          "A CHAT/CONF service has stopped. This is because of application out-of-service
          or if chatconf is down or no app. server

          Action to be taken: No action required"
    --#SUMMARY "[Service CHAT/CONF-%s-%s] CHAT/CONF service has stopped"
    --#ARGUMENTS {0,1}
    --#STATE OPERATIONAL
    --#SEVERITY MAJOR
    ::= { starentTraps 112 }

starSIPRouteNomatch NOTIFICATION-TYPE
    OBJECTS { starSIPRouteVpnName, starSIPRouteVmgName, starSIPRouteAsName, starSIPRouteDestPartyNum, starSIPRouteReqNum }
    STATUS current
    DESCRIPTION
    "SIP session has failed since there is no match in the routing table with matching prefix

    Action to be taken: Operator has to configure with matching prefix if required"
    --#SUMMARY "[Service SIPROUTENOMATCH-%s-%s-%s-%s-%s] SIP Session failed: nomatch in routing table"
    --#ARGUMENTS {0,1,2,3,4}
    --#STATE OPERATIONAL
    --#SEVERITY INFORMATIONAL
    ::= { starentTraps 113 }

starL3AddrUnreachable NOTIFICATION-TYPE
    OBJECTS { starL3Address, starPortSlot, starPortNum }
    STATUS current
    DESCRIPTION
	"A L3 Address is unreachable through the specific slot and port.

         Action to be taken: No action required"
    --#SUMMARY "[System] L3 Address %s unreachable through Slot %d/Port %d"
    --#ARGUMENTS {0,1,2}
    --#STATE OPERATIONAL
    --#SEVERITY INFORMATIONAL
    ::= { starentTraps 114 }

starSWUpgradeStart NOTIFICATION-TYPE
    STATUS current
    DESCRIPTION
	"An operator has begun to upgrade the software on the chassis."
    --#SUMMARY "[System] Software Upgrade started"
    --#STATE DEGRADED
    --#SEVERITY INFORMATIONAL
    ::= { starentTraps 115 }

starSWUpgradeComplete NOTIFICATION-TYPE
    STATUS current
    DESCRIPTION
	"An operator-initiated software upgrade has been completed."
    --#SUMMARY "[System] Software Upgrade complete"
    --#STATE DEGRADED
    --#SEVERITY INFORMATIONAL
    ::= { starentTraps 116 }

starSWUpgradeAborted NOTIFICATION-TYPE
    STATUS current
    DESCRIPTION
	"An operator-initiated software upgrade has been aborted."
    --#SUMMARY "[System] Software Upgrade started"
    --#STATE DEGRADED
    --#SEVERITY INFORMATIONAL
    ::= { starentTraps 117 }

--- BGP

starBGPPeerSessionUp NOTIFICATION-TYPE
    OBJECTS { starContextName, starBGPPeerIpAddress }
    STATUS  current
    DESCRIPTION
        "The BGP peer session to the specified IP address is operational.
         This may indicate the initial configuration of a new peer, the initial
         connectivity after a system restart, or the restoration of connectivity
         after a starBGNPeerSessionDown event.

         Action to be Taken: No action required."
    --#SUMMARY "[System] BGP peer session, vpn %s, address %s, is operational"
    --#ARGUMENTS {0,1}
    --#STATE OPERATIONAL
    --#SEVERITY INFORMATIONAL
    ::= { starentTraps 118 }

starBGPPeerSessionDown NOTIFICATION-TYPE
    OBJECTS { starContextName, starBGPPeerIpAddress }
    STATUS  current
    DESCRIPTION
        "The BGP peer session to the specified IP address is no longer operational.

	 Probable Cause: The BGP peer is not-operational; the network between the
	 ST16 and the BGP peer is experiencing an outage; LC failure(s) on the ST16.

	 Action to be Taken:  Verify the BGP peer is operational; verify network
	 connectivity to the BGP peer.

	 Clear Condition Alarm: A starBGPPeerSessionUp is generated when connectivity is reestablished"
    --#SUMMARY "[System] BGP peer session, vpn %s, address %s, is non-operational"
    --#ARGUMENTS {0,1}
    --#STATE DEGRADED
    --#SEVERITY MAJOR
    ::= { starentTraps 119 }

-- ICSR

starSRPActive NOTIFICATION-TYPE
    OBJECTS { starContextName, starSRPIpAddress }
    STATUS  current
    DESCRIPTION
        "The SRP Chassis Status is now Active.

	 Action to be Taken: No action is required."
    --#SUMMARY "[System] vpn %s SRP %s is now active"
    --#ARGUMENTS {0,1}
    --#STATE OPERATIONAL
    --#SEVERITY INFORMATIONAL
    ::= { starentTraps 120 }

starSRPStandby NOTIFICATION-TYPE
    OBJECTS { starContextName, starSRPIpAddress }
    STATUS  current
    DESCRIPTION
        "The SRP Chassis Status is now Standby.

	 Action to be Taken: No action is required."
    --#SUMMARY "[System] vpn %s SRP %s is now standby"
    --#ARGUMENTS {0,1}
    --#STATE OPERATIONAL
    --#SEVERITY INFORMATIONAL
    ::= { starentTraps 121 }

starBGPPeerReachable NOTIFICATION-TYPE
    OBJECTS { starContextName,
	      starSRPIpAddress,
	      starUDPPortNum,
	      starBGPPeerIpAddress }
    STATUS  obsolete 
    DESCRIPTION
        "The monitored BGP peer is now Reachable.  This notification can represent the
	 initial detection of the peer's state, or the reconnection to a peer
	 after a starBGPPeerDown notification.  This attribute is obsolete.

	 Action to be Taken: No action is required."
    --#SUMMARY "[System] vpn %s SRP %s port %d BGP Peer %s is up"
    --#ARGUMENTS {0,1,2,3}
    --#STATE OPERATIONAL
    --#SEVERITY INFORMATIONAL
    ::= { starentTraps 122 }

starBGPPeerUnreachable NOTIFICATION-TYPE
    OBJECTS { starContextName,
	      starSRPIpAddress,
	      starUDPPortNum,
	      starBGPPeerIpAddress }
    STATUS  obsolete 
    DESCRIPTION
        "The monitored BGP peer is now Unreachable.

	 Action to be Taken: Verify that the BGP Peer is running and is properly
	 configured.  Verify the network link to the BGP Peer. This attribute is obsolete.

	 Clear Condition: This condition is cleared when communication with the
	 BGP peer is reestablished.

	 Condition Clear Alarm: This condition is cleared by a starBGPPeerReachable
	 notification."
    --#SUMMARY "[System] vpn %s SRP %s port %d BGP Peer %s is unreachable"
    --#ARGUMENTS {0,1,2,3}
    --#STATE OPERATIONAL
    --#SEVERITY WARNING
    ::= { starentTraps 123 }

starSRPAAAReachable NOTIFICATION-TYPE
    OBJECTS { starContextName,
	      starSRPIpAddress,
	      starUDPPortNum }
    STATUS  current
    DESCRIPTION
	"The SRP AAA monitor has found a reachable AAA server.  This notification
         can represent the initial detection of an AAA server, or the restoration
	 of reachability after a starSRPAAAUnreachable notification.  This
	 notification is only generated if there was previously no reachable AAA server.

	 Action to be Taken: No action required."
    --#SUMMARY "[System] vpn %s SRP %s port %d reports AAA Reachable"
    --#ARGUMENTS {0,1,2}
    --#STATE OPERATIONAL
    --#SEVERITY INFORMATIONAL
    ::= { starentTraps 124 }

starSRPAAAUnreachable NOTIFICATION-TYPE
    OBJECTS { starContextName,
	      starSRPIpAddress,
	      starUDPPortNum }
    STATUS  current
    DESCRIPTION
       "The SRP AAA monitor has determined that all AAA servers are unreachable.

	Action to be Taken: Verify the state of the configured AAA Server(s) and
	restart them if required.  Verify the network link to the AAA Server(s).
	Configure additional AAA Servers if required.

	Clear Condition: This condition is cleared when communication with any single
	AAA service is (re)established.

	Condition Clear Alarm: This condition is cleared by a starSRPAAAReachable
	notification."
    --#SUMMARY "[System] vpn %s SRP %s port %d reports AAA Unreachable"
    --#ARGUMENTS {0,1,2}
    --#STATE DEGRADED
    --#SEVERITY MAJOR
    ::= { starentTraps 125 }

starSRPSwitchoverInitiated NOTIFICATION-TYPE
    OBJECTS { starContextName,
	      starSRPIpAddress }
    STATUS  current
    DESCRIPTION
        "An SRP (ICSR) Switchover operation has been initiated by an operator.

	 Action to be Taken: Verify that the switchover was a planned
	 operator action."
    --#SUMMARY "[System] SRP Switchover Initiated, vpn %s SRP %s"
    --#ARGUMENTS {0,1}
    --#STATE OPERATIONAL
    --#SEVERITY INFORMATIONAL
    ::= { starentTraps 126 }

starSRPCheckpointFailure NOTIFICATION-TYPE
    OBJECTS { starContextName,
	      starSRPIpAddress }
    STATUS  current
    DESCRIPTION
	"The system has detected that a checkpoint messaged failed to be sent
	 successfully to the standby HA.  If the active HA were to fail, this
	 information will be lost.

         Action to be Taken: Verify the communication path to the Standby HA."
    --#SUMMARY "[System] vpn %s SRP %s session checkpoint failure"
    --#ARGUMENTS {0,1}
    --#STATE OPERATIONAL
    --#SEVERITY WARNING
    ::= { starentTraps 127 }

starSRPConfigOutOfSync NOTIFICATION-TYPE
    OBJECTS { starContextName,
	      starSRPIpAddress }
    STATUS  current
    DESCRIPTION
	"The system has detected that the standby HA has a different configuration
	 than the active HA.  In the event of a failure of the active HA, it is
	 possible that the standby HA is not configured properly to be able to take over.

	 Action to be Taken: Update the configuration of the standby HA to match the active HA.

	 Clear Condition: This condition is cleared when the active HA confirms that the
         standby HA has an identify configuration.

         Condition Clear Alarm: This condition is cleared by a starSRPConfigInSync
	 notification."
    --#SUMMARY "[System] vpn %s SRP %s configuration not synchronized"
    --#ARGUMENTS {0,1}
    --#STATE OPERATIONAL
    --#SEVERITY WARNING
    ::= { starentTraps 128 }

starSRPConfigInSync NOTIFICATION-TYPE
    OBJECTS { starContextName,
	      starSRPIpAddress }
    STATUS  current
    DESCRIPTION
	"The system has detected that the standby HA has a matching configuration as the
	 active HA. This notification is generated only after a starSRPConfigOutOfSync
	 notification.

	 Action to be Taken: No action required."
    --#SUMMARY "[System] vpn %s SRP %s configuration synchronized"
    --#ARGUMENTS {0,1}
    --#STATE OPERATIONAL
    --#SEVERITY INFORMATIONAL
    ::= { starentTraps 129 }

starGESwitchFailure NOTIFICATION-TYPE
    OBJECTS { starSlotNum }
    STATUS  current
    DESCRIPTION
	"A failure of an internal Gigabit Ethernet switch has been detected.  If
	 it is possible to determine the slot containing the failed switch it is
	 identified in starSlotNum, otherwise starSlotNum is 0.

	 Action to be Taken: If this condition persists, the identified card
	 needs to be replaced. This is not applicable to QVPC-SI and QVPC-DI."
    --#SUMMARY "[Card %d] GE Switch Failure"
    --#ARGUMENTS {0}
    --#STATE NONOPERATIONAL
    --#SEVERITY MAJOR
    ::= { starentTraps 130 }

starSIPRouteServerAvailable NOTIFICATION-TYPE
    OBJECTS { starSIPRouteServerVpnName, starSIPRouteServerVmgName, starSIPRouteServerAsName, starSIPRouteServerIpAddr }
    STATUS current
    DESCRIPTION
        "SIP route server is available

        Action to be taken: None"
    --#SUMMARY "[Service SIPROUTESERVER-%s-%s-%s-%s] SIP Route Server Available"
    --#ARGUMENTS {0,1,2,3}
    --#STATE OPERATIONAL
    --#SEVERITY INFORMATIONAL
    ::= { starentTraps 131 }

 starSIPRouteServerUnavailable NOTIFICATION-TYPE
    OBJECTS { starSIPRouteServerVpnName, starSIPRouteServerVmgName, starSIPRouteServerAsName, starSIPRouteServerIpAddr }
    STATUS current
    DESCRIPTION
        "SIP session has failed since the server is unavailable

         Action to be taken: Operator has to check the reasons for the unavailability of the server and act accordingly"
    --#SUMMARY "[Service SIPROUTESERVER-%s-%s-%s-%s] SIP Route Server Unavailable"
    --#ARGUMENTS {0,1,2,3}
    --#STATE DEGRADED
    --#SEVERITY WARNING
    ::= { starentTraps 132 }

starFMDMaxCallRateReached NOTIFICATION-TYPE
    OBJECTS { starVIMServiceVpnName, starVIMServiceInstanceId, starVIMServiceFMDMaxCallRate, starVIMServiceFMDContinuousLoadCount }
    STATUS current
    DESCRIPTION
        "FMD max call rate reached

	Action to be taken: Increase the value of fmd-max-call-rate or set no fmd-max-call-rate

	Condition Clear Alarm: This condition is cleared by a starFMDCallRateUnderControl
	notification"
    --#SUMMARY "[Service VIM-%s-%d] Number of FMD messages processed per minute reached its limit (%d) continuously for %d measurement periods."
    --#ARGUMENTS {0,1,2,3}
    --#STATE DEGRADED
    --#SEVERITY MAJOR
    ::= { starentTraps 133 }

starFMDCallRateUnderControl NOTIFICATION-TYPE
    OBJECTS { starVIMServiceVpnName, starVIMServiceInstanceId, starVIMServiceFMDMaxCallRate, starVIMServiceFMDContinuousLoadCount }
    STATUS current
    DESCRIPTION
    "FMD call rate under control

    Action to be taken: None"
    --#SUMMARY "[Service VIM-%s-%d] Number of FMD messages processed per minute, under limit (%d) for %d measurement periods."
    --#ARGUMENTS {0,1,2,3}
    --#STATE OPERATIONAL
    --#SEVERITY INFORMATIONAL
    ::= { starentTraps 134 }

starStorageServerCPUBusy NOTIFICATION-TYPE
    OBJECTS { starSessGGSNVpnName, starSessGGSNPeerAddr, starThreshPct, starThreshMeasuredPct,
	      starGSSClusterName, starGSSClusterNodeName }
    STATUS  current
    DESCRIPTION
        "GTPP Storage Server is experiencing high CPU usage.  The usage has exceeded
	 an operator-configure value.

	 Note that this is an external server, not part of the ST16.

	 Probable Cause: The amount of information being sent to the Storage Server
	 is approaching the server's capacity; the Storage Server has other tasks
	 running on it which are taking CPU time; a problem with the Storage Server
	 is causing the CPU to be abnormally busy;

	 Condition Clear Alarm: This condition is cleared by a starStorageServerCPUNormal
	 notification"
    --#SUMMARY "[System] GTPP Storage Server CPU busy, VPN %s Server Address %s, GTPP Storage Server Cluster %s node %s, CPU usage %d percent (alarm at %d percent)"
    --#ARGUMENTS {0,1,4,5,3,2}
    --#STATE OPERATIONAL
    --#SEVERITY MAJOR
    ::= { starentTraps 135 }

starStorageServerCPUNormal NOTIFICATION-TYPE
    OBJECTS { starSessGGSNVpnName, starSessGGSNPeerAddr, starThreshPct, starThreshMeasuredPct,
	      starGSSClusterName, starGSSClusterNodeName }
    STATUS  current
    DESCRIPTION
        "GTPP Storage Server CPU usage has returned to a normal range.

	 Note that this is an external server, not part of the ST16."
    --#SUMMARY "[System] GTPP Storage Server CPU usage normal, VPN %s Server Address %s, GTPP Storage Server Cluster %s node %s, CPU usage %d percent (alarm at %d percent)"
    --#ARGUMENTS {0,1,4,5,3,2}
    --#STATE OPERATIONAL
    --#SEVERITY INFORMATIONAL
    ::= { starentTraps 136 }

starStorageServerDiskSpaceLow NOTIFICATION-TYPE
    OBJECTS { starSessGGSNVpnName, starSessGGSNPeerAddr, starThreshGB, starThreshMeasuredGB,
	      starGSSClusterName, starGSSClusterNodeName }
    STATUS  current
    DESCRIPTION
        "GTPP Storage Server is experiencing low available disk space.  The available
	 disk space has gone below an operator-configure value.

	 Note that this is an external server, not part of the ST16.

	 Probable Cause: The amount of information being sent to the Storage Server
	 is approaching the server's capacity; the Storage Server has other information
	 consuming disk space; a problem with the Storage Server is causing less disk
	 space to be available then normal.

	 Condition Clear Alarm: If the GTPP Storage Server is configured to run in an 'alarm'
	 model, this condition is cleared by a starStorageServerDiskSpaceOK notification.
	 Otherwise the starStorageServerDiskSpaceLow notification will be generated periodically
	 until the condition is cleared."
    --#SUMMARY "[System] GTPP Storage Server Disk space low, VPN %s Server Address %s, GTPP Storage Server Cluster %s node %s, disk available %d GB (alarm at %d GB)"
    --#ARGUMENTS {0,1,4,5,3,2}
    --#STATE OPERATIONAL
    --#SEVERITY MAJOR
    ::= { starentTraps 137 }

starStorageServerDiskSpaceOK NOTIFICATION-TYPE
    OBJECTS { starSessGGSNVpnName, starSessGGSNPeerAddr, starThreshPct, starThreshMeasuredPct,
	      starGSSClusterName, starGSSClusterNodeName }
    STATUS  current
    DESCRIPTION
        "GTPP Storage Server available disk space to a normal range.

	 Note that this is an external server, not part of the ST16."
    --#SUMMARY "[System] GTPP Storage Server Disk space OK, VPN %s Server Address %s, GTPP Storage Server Cluster %s node %s, disk available %d GB (alarm at %d GB)"
    --#ARGUMENTS {0,1,4,5,3,2}
    --#STATE OPERATIONAL
    --#SEVERITY INFORMATIONAL
    ::= { starentTraps 138 }

starCardSPOFAlarm NOTIFICATION-TYPE
    OBJECTS { starSlotNum, starCardType, starSlotSerialNumber }
    STATUS  current
    DESCRIPTION
	"The identified card is a Single Point of Failure (SPOF).  There is no redundant card
	 available to take over in the event of a failure.

	 Probable Cause: This can be caused by an improper
	 configuration, or by the failure or removal of other cards in the system.

	 Action to be Taken: Install or configure additional redundant cards.

	 Clear Condition: A starCardSPOFClear notification will be generated is a redundant
	 card becomes available.  Notifications like starCardDown could also obsolete this
	 notification"
    --#SUMMARY "[Card %s-%d] Card is Single Point of Failure (SPOF) UUID %s. This is not applicable to QVPC-SI."
    --#ARGUMENTS {1,0,2}
    --#STATE DEGRADED
    --#SEVERITY MAJOR
    ::= { starentTraps 139 }

starCardSPOFClear NOTIFICATION-TYPE
    OBJECTS { starSlotNum, starCardType, starSlotSerialNumber }
    STATUS  current
    DESCRIPTION
	"The identified card is no longer a Single Point of Failure (SPOF)"
    --#SUMMARY "[Card %s-%d] Card is no longer a Single Point of Failure (SPOF) UUID %s. This is not applicable to QVPC-SI."
    --#ARGUMENTS {1,0,2}
    --#STATE OPERATIONAL
    --#SEVERITY INFORMATIONAL
    ::= { starentTraps 140 }

starStorageServerOldGcdrPending NOTIFICATION-TYPE
    OBJECTS { starSessGGSNVpnName, starSessGGSNPeerAddr, starThreshInt, starThreshMeasuredInt,
	      starGSSClusterName, starGSSClusterNodeName }
    STATUS  current
    DESCRIPTION
        "GTPP Storage Server reports that GCDR files have been unprocessed for too long.

	 Note that this is an external server, not part of the ST16.

	 Probable Cause: No action has been taken long for the GCDR files generated by Storage Server.

	 Condition Clear Alarm: If the GTPP Storage Server is configured to run in an 'alarm'
	 model, this condition is cleared by a starStorageServerOldGcdrCleared notification.
	 Otherwise the starStorageServerOldGCDRPending notification will be generated
	 periodically"
    --#SUMMARY "[System] GTPP Storage Server has many unprocessed GCDR files, VPN %s Server Address %s, GTPP Storage Server Cluster %s node %s, Oldest unprocessed GCDR file %d mins. Configured period %d mins"
    --#ARGUMENTS {0,1,4,5,3,2}
    --#STATE OPERATIONAL
    --#SEVERITY WARNING
    ::= { starentTraps 141 }

starStorageServerOldGcdrCleared NOTIFICATION-TYPE
    OBJECTS { starSessGGSNVpnName, starSessGGSNPeerAddr, starThreshInt,
	      starGSSClusterName, starGSSClusterNodeName }
    STATUS  current
    DESCRIPTION
        "GCDR files on the Storage Server have been processed on the Storage Server.
         The threshold condition is now clear.

	 Note that this is an external server, not part of the ST16."
    --#SUMMARY "[System] All old GCDR files on Storage Server over the configured period of %lu min have been processed. VPN %s Storage Server Address %s, GTPP Storage Server Cluster %s node %s, "
    --#ARGUMENTS {2,0,1,3,4}
    --#STATE OPERATIONAL
    --#SEVERITY INFORMATIONAL
    ::= { starentTraps 142 }

starLoginFailure NOTIFICATION-TYPE
    OBJECTS { starCLITtyname, starCLIRemoteIpAddrType,
              starCLIRemoteIpAddr, starCLIType }
    STATUS  current
    DESCRIPTION
        "A login failure occurred attempting to establish a CLI or FTP session."
    --#SUMMARY "[System] CLI/FTP login failure from %s/%s, failure starting %s"
    --#ARGUMENTS {1,0,2}
    --#STATE OPERATIONAL
    --#SEVERITY INFORMATIONAL
    ::= { starentTraps 143 }

starIPSGServiceStart NOTIFICATION-TYPE
    OBJECTS { starServiceVpnName, starServiceServName }
    STATUS  current
    DESCRIPTION
        "A IP Services Gateway (IPSG) Service has started

	 Action to be Taken: No action required"
    --#SUMMARY "[Service IPSG-%s-%s] IPSG service has started"
    --#ARGUMENTS {0,1}
    --#STATE OPERATIONAL
    --#SEVERITY INFORMATIONAL
    ::= { starentTraps 144 }

starIPSGServiceStop NOTIFICATION-TYPE
    OBJECTS { starServiceVpnName, starServiceServName }
    STATUS  current
    DESCRIPTION
        "A IP Services Gateway (IPSG) Service has stopped.

	 Probable Cause: This is typically caused by operator invention.  In
         unusual cases it can be caused by the loss of resources (PACs/PSCs) to
	 support the running configuration.

	 Action to be Taken: If the IPSG service shutdown was not planned,
	 examine the admin logs for an indication of the failure.  Verify that
	 all configured PACs/PSCs are present and running in the system.  Check the
	 crash logs for an indication of a software failure.

	 Clear Condition: Verify that the IPSG service is operational.

	 Condition Clear Alarm:  A starIPSGServiceStart notification will be generated when
	 the service is restarted"
    --#SUMMARY "[Service IPSG-%s-%s] IPSG service has stopped"
    --#ARGUMENTS {0,1}
    --#STATE DEGRADED
    --#SEVERITY MAJOR
    ::= { starentTraps 145 }

starHAUnreachable NOTIFICATION-TYPE
    OBJECTS { starServiceVpnName, starServiceServName, starServiceFAIpAddr, starServiceHAIpAddr }
    STATUS  current
    DESCRIPTION
	"A monitored HA is unreachable from the identified FA Service.

	 Condition Clear Alarm: A starHAReachable notification will be generated when the
	 HA becomes reachable"
    --#SUMMARY "[FA %s-%s] HA Unreachable; HA address %s"
    --#ARGUMENTS {0,1,3}
    --#STATE DEGRADED
    --#SEVERITY MAJOR
    ::= { starentTraps 146 }

starHAReachable NOTIFICATION-TYPE
    OBJECTS { starServiceVpnName, starServiceServName, starServiceFAIpAddr, starServiceHAIpAddr }
    STATUS  current
    DESCRIPTION
	"A monitored HA is now reachable.  A starHAReachable notification is only
	 generated for monitored HA's which previously were marked unreachable."
    --#SUMMARY "[FA %s-%s] HA Reachable; HA address %s"
    --#ARGUMENTS {0,1,3}
    --#STATE OPERATIONAL
    --#SEVERITY INFORMATIONAL
    ::= { starentTraps 147 }

starASNGWServiceStart NOTIFICATION-TYPE
    OBJECTS { starServiceVpnName, starServiceServName }
    STATUS  obsolete
    DESCRIPTION
        "A WiMAX ASN Gateway (ASNGW) Service has started

	 Action to be Taken: No action required"
    --#SUMMARY "[Service ASNGW-%s-%s] ASNGW service has started"
    --#ARGUMENTS {0,1}
    --#STATE OPERATIONAL
    --#SEVERITY INFORMATIONAL
    ::= { starentTraps 148 }

starASNGWServiceStop NOTIFICATION-TYPE
    OBJECTS { starServiceVpnName, starServiceServName }
    STATUS  obsolete
    DESCRIPTION
        "A WiMAX ASN Gateway (ASNGW) Service has stopped.

	 Probable Cause: This is typically caused by operator invention.  In
         unusual cases it can be caused by the loss of resources (PACs/PSCs) to
	 support the running configuration.

	 Action to be Taken: If the ASNGW service shutdown was not planned,
	 examine the admin logs for an indication of the failure.  Verify that
	 all configured PACs/PSCs are present and running in the system.  Check the
	 crash logs for an indication of a software failure.

	 Clear Condition: Verify that the ASNGW service is operational.

	 Condition Clear Alarm:  A starASNGWServiceStart notification will be generated when
	 the service is restarted"
    --#SUMMARY "[Service ASNGW-%s-%s] ASNGW service has stopped"
    --#ARGUMENTS {0,1}
    --#STATE DEGRADED
    --#SEVERITY MAJOR
    ::= { starentTraps 149 }

starTaskFailed NOTIFICATION-TYPE
    OBJECTS { starTaskFacilityName, starTaskInstance, starTaskCard, starTaskCPU }
    STATUS  current
    DESCRIPTION
        "A non-critical task has failed and the appropriate recovery steps begun.
	 The failing task will be restarted.

	 Probable Cause: Software error

	 Actions to be Taken: Examine the admin logs for an indication of the source
	 of the failure.

	 Clear Condition: Verify that the task has been restarted.

	 Condition Clear Alarm:  A starTaskRestart notification will be generated when
	 task has successfully restarted."
    --#SUMMARY "[Card %d] Task %s/%d on CPU %d has failed"
    --#ARGUMENTS {2,0,1,3}
    --#STATE DEGRADED
    --#SEVERITY MAJOR
    ::= { starentTraps 150 }

starTaskRestart NOTIFICATION-TYPE
    OBJECTS { starTaskFacilityName, starTaskInstance, starTaskCard, starTaskCPU }
    STATUS  current
    DESCRIPTION
        "A non-critical task has restarted after an earlier failure.

	 Actions to be Taken: None"
    --#SUMMARY "[Card %d] Task %s/%d on CPU %d has been restarted"
    --#ARGUMENTS {2,0,1,3}
    --#STATE OPERATIONAL
    --#SEVERITY INFORMATIONAL
    ::= { starentTraps 151 }

starCSCFServiceStart NOTIFICATION-TYPE
    OBJECTS { starServiceVpnName, starServiceServName }
    STATUS  current
    DESCRIPTION
        "An CSCF Service has started

	 Action to be Taken: No action required"
    --#SUMMARY "[Service CSCF-%s-%s] CSCF service has started"
    --#ARGUMENTS {0,1}
    --#STATE OPERATIONAL
    --#SEVERITY INFORMATIONAL
    ::= { starentTraps 152 }

starCSCFServiceStop NOTIFICATION-TYPE
    OBJECTS { starServiceVpnName, starServiceServName }
    STATUS  current
    DESCRIPTION
        "An CSCF Service has stopped

	 Probable Cause: This is typically caused by operator invention.  In
         unusual cases it can be caused by the loss of resources (PACs/PSCs) to
	 support the running configuration.

	 Action to be Taken: If the CSCF service shutdown was not planned,
	 examine the admin logs for an indication of the failure.  Verify that
	 all configured PACs/PSCs are present and running in the system.  Check the
	 crash logs for an indication of a software failure.

	 Clear Condition: Verify that the CSCF service is operational.

	 Condition Clear Alarm:  A starCSCFServiceStart notification will be generated when
	 the service is restarted"
    --#SUMMARY "[CSCF %s-%s] CSCF service has stopped"
    --#ARGUMENTS {0,1}
    --#STATE DEGRADED
    --#SEVERITY MAJOR
    ::= { starentTraps 153 }

starDhcpServiceStarted NOTIFICATION-TYPE
    OBJECTS { starServiceVpnName, starServiceServName  }
    STATUS  current
    DESCRIPTION
 	"A DHCP Service has started

	 Action to be Taken: No action required"
    --#SUMMARY "[System] DHCP service started, VPN %s Service Name %s"
    --#ARGUMENTS {0,1}
    --#STATE OPERATIONAL
    --#SEVERITY INFORMATIONAL
    ::= { starentTraps 154 }

starDhcpServiceStopped NOTIFICATION-TYPE
    OBJECTS { starServiceVpnName, starServiceServName  }
    STATUS  current
    DESCRIPTION
        "A DHCP Service has stopped

	 Probable Cause: This is typically caused by operator invention.  In
         unusual cases it can be caused by the loss of resources (PACs/PSCs) to
	 support the running configuration.

	 Action to be Taken: If the DHCP service shutdown was not planned,
	 examine the admin logs for an indication of the failure.  Verify that
	 all configured PACs/PSCs are present and running in the system.  Check the
	 crash logs for an indication of a software failure.

	 Clear Condition: Verify that the DHCP service is operational.

	 Condition Clear Alarm:  A starDHCPServiceStart notification will be generated when
	 the service is restarted"

    --#SUMMARY "[System] DHCP service stopped, VPN %s Service Name %s"
    --#ARGUMENTS {0,1}
    --#STATE DEGRADED
    --#SEVERITY MAJOR
    ::= { starentTraps 155 }

starContFiltDBError NOTIFICATION-TYPE
    OBJECTS { starContFiltCFFilename, starContFiltCFErrorCode }
    STATUS  current
    DESCRIPTION
    "The Content Filtering OPTCMDB file error displayed with an error code.

    Action to be Taken: If no OPTCMDB file is there in the specified directory then
    Place a OPTCMDB-FULL file in the directory and give an upgrade command or place
    an OPTCMDB file and load the SRDBs by killing them all.

    Condition Clear Alarm: This condition is cleared by a starContFiltDBErrorClear
    notification"
    --#SUMMARY "[System] Content Filtering file %s error code: %s"
    --#ARGUMENTS {0,1}
    --#STATE DEGRADED
    --#SEVERITY MAJOR
    ::= { starentTraps 156 }

starContFiltDBErrorClear NOTIFICATION-TYPE
    OBJECTS { starContFiltCFFilename, starContFiltCFErrorCode }
    STATUS  current
    DESCRIPTION
    "The Content Filtering OPTCMDB file error removed.

    Action to be Taken: No action required"
    --#SUMMARY "[System] Content Filtering file %s error code: %s cleared"
    --#ARGUMENTS {0,1}
    --#STATE OPERATIONAL
    --#SEVERITY INFORMATIONAL
    ::= { starentTraps 157 }

starBLDBError NOTIFICATION-TYPE
    OBJECTS { starBLFilename, starBLErrorCode }
    STATUS  current
    DESCRIPTION
    "The Blacklisting OPTBLDB file error displayed with an error code.

    Action to be Taken: If no or invalid OPTBLDB file is there in the specified directory then
    Place a OPTBLDB_FULL file in the directory and give an upgrade command.

    Condition Clear Alarm: This condition is cleared by a starBLDBErrorClear
    notification"
    --#SUMMARY "[System] Blacklisting file %s error code: %s"
    --#ARGUMENTS {0,1}
    --#STATE DEGRADED
    --#SEVERITY MAJOR
    ::= { starentTraps 158 }

starBLDBErrorClear NOTIFICATION-TYPE
    OBJECTS { starBLFilename, starBLErrorCode }
    STATUS  current
    DESCRIPTION
    "The Blacklisting OPTBLDB file error removed.

    Action to be Taken: No action required"
    --#SUMMARY "[System] Blacklisting file %s error code: %s cleared"
    --#ARGUMENTS {0,1}
    --#STATE OPERATIONAL
    --#SEVERITY INFORMATIONAL
    ::= { starentTraps 159 }

starContFiltDBUpgradeError NOTIFICATION-TYPE
    OBJECTS { starContFiltCFUpgradeFilename, starContFiltCFUpgradeErrorCode }
    STATUS  current
    DESCRIPTION
    "The Content Filtering OPTCMDB file error displayed with an error code.

    Action to be Taken: Place a valid OPTCMDB-FULL file or OPTCMDB_INCR file in the
    directory and give an upgrade command.

    Condition Clear Alarm: This condition is cleared by a starContFiltDBUpgradeErrorClear
    notification"
    --#SUMMARY "[System] Content Filtering file %s error code: %s"
    --#ARGUMENTS {0,1}
    --#STATE DEGRADED
    --#SEVERITY INFORMATIONAL
    ::= { starentTraps 160 }

starContFiltDBUpgradeErrorClear NOTIFICATION-TYPE
    OBJECTS { starContFiltCFUpgradeFilename, starContFiltCFUpgradeErrorCode }
    STATUS  current
    DESCRIPTION
    "The Content Filtering OPTCMDB file error removed.

    Action to be Taken: No action required"
    --#SUMMARY "[System] Content Filtering file %s error code: %s cleared"
    --#ARGUMENTS {0,1}
    --#STATE OPERATIONAL
    --#SEVERITY INFORMATIONAL
    ::= { starentTraps 161 }

starBLDBUpgradeError NOTIFICATION-TYPE
    OBJECTS { starBLUpgradeFilename, starBLUpgradeErrorCode }
    STATUS  current
    DESCRIPTION
    "The Blacklisting OPTBLDB file error displayed with an error code.

    Action to be Taken: Place a valid OPTBLDB-FULL file file in the
    directory and give an upgrade command.

    Condition Clear Alarm: This condition is cleared by a starBLDBUpgradeErrorClear
    notification"
    --#SUMMARY "[System] Blacklisitng file %s error code: %s"
    --#ARGUMENTS {0,1}
    --#STATE DEGRADED
    --#SEVERITY INFORMATIONAL
    ::= { starentTraps 162 }

starBLDBUpgradeErrorClear NOTIFICATION-TYPE
    OBJECTS { starBLUpgradeFilename, starBLUpgradeErrorCode }
    STATUS  current
    DESCRIPTION
    "The Blacklisting OPTBLDB file error removed.

    Action to be Taken: No action required"
    --#SUMMARY "[System] Blacklisting file %s error code: %s cleared"
    --#ARGUMENTS {0,1}
    --#STATE OPERATIONAL
    --#SEVERITY INFORMATIONAL
    ::= { starentTraps 163 }

starIPSECDynTunUp NOTIFICATION-TYPE
    OBJECTS { starIPSECContextName, starIPSECPolicyName, starIPSECDynPolicyType, starIPSECDynPolicyPayloadType, starIPSECLocalGateway, starIPSECRemoteGateway }
    STATUS current
    DESCRIPTION
	"IPSEC Dynamic Tunnel Up.

         Action to be Taken: No action required"
    --#SUMMARY "[System] IPSEC Dynamic Tunnel Up; context %s, policy name %s, policy type %d, payload type %d, local gateway %s, remote gateway %s"
    --#ARGUMENTS {0,1,2,3,4,5}
    --#STATE OPERATIONAL
    --#SEVERITY INFORMATIONAL
    ::= { starentTraps 164 }

starIPSECDynTunDown NOTIFICATION-TYPE
    OBJECTS { starIPSECContextName, starIPSECPolicyName, starIPSECDynPolicyType, starIPSECDynPolicyPayloadType, starIPSECLocalGateway, starIPSECRemoteGateway }
    STATUS current
    DESCRIPTION
	"IPSEC Dynamic Tunnel Down.

	 Condition Clear Alarm: a starIPSECDynTunUp notification will be sent when the
	 tunnel is operational again.  Note however that a tunnel may go down due to administrative
	 action, or the tunnel may not longer be required, thus a starIPSECDynTunUp may not
	 follow."
    --#SUMMARY "[System] IPSEC Dynamic Tunnel Down; context %s, policy name %s, policy type %d, payload type %d, local gateway %s, remote gateway %s"
    --#ARGUMENTS {0,1,2,3,4,5}
    --#STATE DEGRADED
    --#SEVERITY MINOR
    ::= { starentTraps 165 }

starHeartbeat NOTIFICATION-TYPE
    STATUS  current
    DESCRIPTION
	"Periodic SNMP heartbeat.  A starHeartbeat notification can be generated
	 periodically if the system is configured to do so.  These notifications
	 serve only to validate that there is communication to external entities
	 which sink SNMP notifications"
    --#SUMMARY "[System] SNMP Heartbeat"
    --#STATE OPERATIONAL
    --#SEVERITY INFORMATIONAL
    ::= { starentTraps 166 }

starOverloadSystem NOTIFICATION-TYPE
    OBJECTS { starCongestionResourceType }
    STATUS current
    DESCRIPTION
        "A system-wide congestion overload condition has occurred.

	 Probable Cause:  This is the result of an operator-configured congestion
	 overload value reached.  This notification indicated a chassis-wide
	 overload condition, typically overall system usage reaching some fraction
	 of capacity.

	 Once this limit is reached, the configured behavior is taken.  This will
	 cause certain older and/or dormant calls to be dropped in favor of newer calls.

	 Note that this is similar to, but different than, the starCongestion
	 notification.  Typically the 'overload' condition will be configured to
	 trigger at an earlier point.

	 Actions to be Taken:  Verify that the congestion overload thresholds are correct;
	 if the congested state is seem repeatedly, or for sustained periods of
	 time, additional system capacity may need to be brought online.

	 This system is cleared when the use of the specific resource falls below
	 the configured limit.

	 Condition Clear Alarm: A starOverloadSystemClear notification is sent when the
	 system overload condition is clear"
    --#SUMMARY "[System] System Congestion Overload; resource type %s"
    --#ARGUMENTS {0}
    --#STATE DEGRADED
    --#SEVERITY MAJOR
    ::= { starentTraps 167 }

starOverloadSystemClear NOTIFICATION-TYPE
    STATUS current
    DESCRIPTION
        "A system-wide congestion overload condition has cleared"
    --#SUMMARY "[System] Congestion overload clear"
    --#STATE OPERATIONAL
    --#SEVERITY INFORMATIONAL
    ::= { starentTraps 168 }

starOverloadService NOTIFICATION-TYPE
    OBJECTS { starCongestionResourceType, starServiceVpnName, starServiceServName }
    STATUS current
    DESCRIPTION
        "A service-specific congestion overload condition has occurred.

	 Probable Cause:  This is the result of an operator-configured congestion
	 overload value reached.  This notification indicated a service-specific
	 overload condition, typically the use of the service reaching some fraction
	 of capacity.

	 Once this limit is reached, the configured behavior is taken.  This will
	 cause certain older and/or dormant calls to be dropped in favor of newer calls.

	 Note that this is similar to, but different than, the starCongestion
	 notification.  Typically the 'overload' condition will be configured to
	 trigger at an earlier point.

	 Since this is a service-specific notification, it is possible to receive
	 multipe notifications for different services.  Each

	 Actions to be Taken:  Verify that the congestion overload thresholds are correct;
	 if the congested state is seem repeatedly, or for sustained periods of
	 time, additional system capacity may need to be brought online.

	 This system is cleared when the use of the specific resource falls below
	 the configured limit.

	 Condition Clear Alarm: A starOverloadServiceClear notification is sent when the
	 service-specific overload condition is clear."
    --#SUMMARY "[Service %s-%s] System Congestion Overload; resource type %s"
    --#ARGUMENTS {1,2,0}
    --#STATE DEGRADED
    --#SEVERITY MAJOR
    ::= { starentTraps 169 }

starOverloadServiceClear NOTIFICATION-TYPE
    OBJECTS { starServiceVpnName, starServiceServName }
    STATUS current
    DESCRIPTION
        "A service-specific congestion overload condition has cleared"
    --#SUMMARY "[Service %s-%s] Congestion overload clear"
    --#ARGUMENTS {1,2}
    --#STATE OPERATIONAL
    --#SEVERITY INFORMATIONAL
    ::= { starentTraps 170 }

starStorageServerClusterStateChange NOTIFICATION-TYPE
    OBJECTS { starSessGGSNVpnName, starSessGGSNPeerAddr, starGSSClusterName,
    	      starGSSClusterRgName, starGSSClusterRsName, starGSSClusterNodeState,
              starGSSClusterPrevOnlineNode }
    STATUS  current
    DESCRIPTION
       	"GTPP Storage Server cluster state has been changed.

        GTPP Storage Server may have gone offline from all the nodes or switchover has been occured.

        Note that this is an external server, not part of the ST16.

        Probable Cause: GTPP Storage Server cluster hardware/software component
	failure or maintenance of GTPP Storage Server is in progress"
    --#SUMMARY "[System] GTPP Storage Server cluster state changed, VPN %s Server Address %s, GTPP Storage Server Cluster name %s, Associated resource group name %s and Associated resource name %s, Cluster node state %s, Previous online node name %s"
    --#ARGUMENTS {0,1,2,3,4,5,6}
    --#STATE OPERATIONAL
    --#SEVERITY INFORMATIONAL
    ::= { starentTraps 171 }

starStorageServerClusSwitchOver NOTIFICATION-TYPE
    OBJECTS { starSessGGSNVpnName, starSessGGSNPeerAddr, starGSSClusterName,
              starGSSClusterRgName, starGSSClusterFromNode, starGSSClusterToNode }
    STATUS  current
    DESCRIPTION
	"GTPP Storage Server switchover from current online node to next available node in cluster.

         Note that this is an external server, not part of the ST16.

         Probable Cause: GTPP Storage Server cluster Hardware/Software component failure
         or maintenance of GTPP Storage Server is in progress"
    --#SUMMARY "[System] GTPP Storage Server swicthover, VPN %s Server Address %s, GTPP Storage Server Cluster name %s, Associated resource group name %s , Switched-over from node %s to node %s"
    --#ARGUMENTS {0,1,2,3,4,5}
    --#STATE OPERATIONAL
    --#SEVERITY CRITICAL
    ::= { starentTraps 172 }

starStorageServerClusPathFail NOTIFICATION-TYPE
    OBJECTS { starSessGGSNVpnName, starSessGGSNPeerAddr, starGSSDiskPath, starGSSClusterName,
              starGSSClusterNodeName }
    STATUS  current
    DESCRIPTION
	"GTPP Storage Server cluster disk path failure has been occured.

         Note that this is an external server, not part of the ST16.

         Probable Cause: Fibre cable may have been damaged, fibre cable may have been pulled out or disk fault may have been occured.

         Condition Clear Alarm: This condition is cleared by a starStorageServerClusPathOK notification"
    --#SUMMARY "[System] GTPP Storage Server cluster disk path failure, VPN %s Server Address %s, Cluster Disk Path %s, GTPP Storage Server Cluster %s node %s"
    --#ARGUMENTS {0,1,2,3,4}
    --#STATE OPERATIONAL
    --#SEVERITY CRITICAL
    ::= { starentTraps 173 }

starStorageServerClusPathOK NOTIFICATION-TYPE
    OBJECTS { starSessGGSNVpnName, starSessGGSNPeerAddr, starGSSDiskPath, starGSSClusterName,
              starGSSClusterNodeName }
    STATUS  current
    DESCRIPTION
       	"GTPP Storage Server cluster disk path failure has been restored to ok state.

         Note that this is an external server, not part of the ST16"
    --#SUMMARY "[System] GTPP Storage Server cluster disk path OK, VPN %s Server Address %s, Cluster Disk Path %s, GTPP Storage Server Cluster %s node %s"
    --#ARGUMENTS {0,1,2,3,4}
    --#STATE OPERATIONAL
    --#SEVERITY INFORMATIONAL
    ::= { starentTraps 174 }

starStorageServerClusInterCFail NOTIFICATION-TYPE
    OBJECTS { starSessGGSNVpnName, starSessGGSNPeerAddr, starGSSTransportPath,
              starGSSClusterName, starGSSClusterNodeName }
    STATUS  current
    DESCRIPTION
        "GTPP Storage Server cluster transport path (Interconnect) failure has been occured.

         Note that this is an external server, not part of the ST16.

         Probable Cause: Interconnect interface may have been failed, Interconnect interface cable may have been pulled out.

         Condition Clear Alarm: This condition is cleared by a starStorageServerClusInterCOK notification"
    --#SUMMARY "[System] GTPP Storage Server cluster transport path (Interconnect) failure, VPN %s Server Address %s, Cluster Transport Path %s, GTPP Storage Server Cluster %s node %s"
    --#ARGUMENTS {0,1,2,3,4}
    --#STATE OPERATIONAL
    --#SEVERITY CRITICAL
    ::= { starentTraps 175 }

starStorageServerClusInterCOK NOTIFICATION-TYPE
    OBJECTS { starSessGGSNVpnName, starSessGGSNPeerAddr, starGSSTransportPath,
              starGSSClusterName, starGSSClusterNodeName }
    STATUS  current
    DESCRIPTION
        "GTPP Storage Server cluster transport path (Interconnect) failure has been restored to
	 an operational state.

         Note that this is an external server, not part of the ST16"
    --#SUMMARY "[System] GTPP Storage Server cluster transport path (Interconnect) ok, VPN %s Server Address %s, Cluster Transport Path %s, GTPP Storage Server Cluster %s node %s"
    --#ARGUMENTS {0,1,2,3,4}
    --#STATE OPERATIONAL
    --#SEVERITY INFORMATIONAL
    ::= { starentTraps 176 }


starStorageServerClusIntfFail NOTIFICATION-TYPE
    OBJECTS { starSessGGSNVpnName, starSessGGSNPeerAddr, starGSSIPMPGroupName,
              starGSSInterfaceName, starGSSClusterName, starGSSClusterNodeName }
    STATUS  current
    DESCRIPTION
        "GTPP Storage Server cluster GE Interface failure has been occured.

         Note that this is an external server, not part of the ST16.

         Probable Cause: Interface may have been failed, interface cable may have been pulled out.

         Condition Clear Alarm: This condition is cleared by a starStorageServerClusIntfOK notification"
    --#SUMMARY "[System] GTPP Storage Server cluster interface failure, VPN %s Server Address %s, Cluster IPMP Group name %s and associated interface name %s, GTPP Storage Server Cluster %s node %s"
    --#ARGUMENTS {0,1,2,3,4,5}
    --#STATE OPERATIONAL
    --#SEVERITY MAJOR
    ::= { starentTraps 177 }


starStorageServerClusIntfOK NOTIFICATION-TYPE
    OBJECTS { starSessGGSNVpnName, starSessGGSNPeerAddr, starGSSIPMPGroupName,
              starGSSInterfaceName, starGSSClusterName, starGSSClusterNodeName }
    STATUS  current
    DESCRIPTION
        "GTPP Storage Server cluster GE Interface failure failure has been restored to ok state.

         Note that this is an external server, not part of the ST16"
    --#SUMMARY "[System] GTPP Storage Server cluster GE interface ok, VPN %s Server Address %s, Cluster IPMP Group name  %s and associated GE interface name %s, GTPP Storage Server Cluster %s node %s"
    --#ARGUMENTS {0,1,2,3,4,5}
    --#STATE OPERATIONAL
    --#SEVERITY INFORMATIONAL
    ::= { starentTraps 178 }


starStorageServerMemLow NOTIFICATION-TYPE
    OBJECTS { starSessGGSNVpnName, starSessGGSNPeerAddr, starThreshMB,
              starThreshMeasuredMB, starGSSClusterName, starGSSClusterNodeName }
    STATUS  current
    DESCRIPTION
        "GTPP Storage Server is experiencing a low memory condition.

	 Note that this is an external server, not part of the ST16.

         Probable Cause: The amount of free memory used by Storage Server
         is approaching the server's capacity;

         Condition Clear Alarm: This condition is cleared by a starStorageServerMemNormal
         notification"
    --#SUMMARY "[System] GTPP Storage Server memory low, VPN %s Server Address %s, Available free memory %d MB (notification at %d MB), GTPP Storage Server Cluster %s node %s"
    --#ARGUMENTS {0,1,3,2,4,5}
    --#STATE OPERATIONAL
    --#SEVERITY MAJOR
    ::= { starentTraps 179 }

starStorageServerMemNormal NOTIFICATION-TYPE
    OBJECTS { starSessGGSNVpnName, starSessGGSNPeerAddr, starThreshMB,
              starThreshMeasuredMB, starGSSClusterName, starGSSClusterNodeName }
    STATUS  current
    DESCRIPTION
        "GTPP Storage Server Memory usage has returned to a normal range.

	 Note that this is an external server, not part of the ST16."
    --#SUMMARY "[System] GTPP Storage Server memory normal, VPN %s Server Address %s, Available free memory %d MB (notification at %d MB), GTPP Storage Server Cluster %s node %s"
    --#ARGUMENTS {0,1,3,2,4,5}
    --#STATE OPERATIONAL
    --#SEVERITY INFORMATIONAL
    ::= { starentTraps 180 }

starPDIFServiceStart NOTIFICATION-TYPE
    OBJECTS { starServiceVpnName, starServiceServName }
    STATUS  current
    DESCRIPTION
         "A PDIF Service has started

 	 Action to be Taken: No action required"
    --#SUMMARY "[Service PDIF-%s-%s] PDIF service has started"
    --#ARGUMENTS {0,1}
    --#STATE OPERATIONAL
    --#SEVERITY INFORMATIONAL
    ::= { starentTraps 181 }

starPDIFServiceStop NOTIFICATION-TYPE
    OBJECTS { starServiceVpnName, starServiceServName }
    STATUS  current
    DESCRIPTION
         "A PDIF Service has stopped.

 	 Probable Cause: This is typically caused by operator invention.  In
          rare cases it can be caused by the loss of resources (PACs) to
 	 support the running configuration.

 	 Action to be Taken: If the PDIF service shutdown was not planned,
 	 examine the admin logs for an indication of the failure.  Verify that
 	 all configured PACs are present and running in the system.  Check the
 	 crash logs for an indication of a software failure.

 	 Clear Condition: Verify that the PDIF service is operational.

 	 Condition Clear Alarm:  A starPDIFServiceStart notification will be generated when
 	 the service is restarted"
    --#SUMMARY "[Service PDIF-%s-%s] PDIF service has stopped"
    --#ARGUMENTS {0,1}
    --#STATE DEGRADED
    --#SEVERITY MAJOR
    ::= { starentTraps 182 }

starSessMgrRecoveryComplete NOTIFICATION-TYPE
    OBJECTS { starCPUSlot, starCPUNumber, starFecthedFromAAAMgr, starPriorToAudit, starPassedAudits, starCallsRecovered, starAllCallLines, starElapsedMs }
    STATUS  current
    DESCRIPTION
    "A Sess Mgr Recovery Complete

	 Probable Cause: This is typically caused by session manager task fails
	 and successfully completed recovery.

	 Action to be Taken: None"
    --#SUMMARY "[System] Session Manager task recovery completed, in %d (ms) fetched from aaamgr %d calls recovered %d passed audit %d prior to audit %d all call lines %d on Slot Number %d Cpu Number %d"
    --#ARGUMENTS {7,2,3,4,5,6,0,1}
    --#STATE DEGRADED
    --#SEVERITY MAJOR
    ::= { starentTraps 183 }

starDiameterPeerDown NOTIFICATION-TYPE
    OBJECTS { starDiameterVpnName, starDiameterPeerAddr, starDiameterEndpointName }
    STATUS  current
    DESCRIPTION
 	"A diameter peer is down.

 	 Problem Cause: The diameter peer has failed, or a network connectivity
 	 prevents reaching the peer.

 	 Condition Clear Alarm:  A starDiameterPeerUp notification will be generated when
 	 the peer is up"
    --#SUMMARY "[VPN %s] Diameter Peer %s endpoint %s is down"
    --#ARGUMENTS {0,1,2}
    --#STATE DEGRADED
    --#SEVERITY MAJOR
    ::= { starentTraps 184 }

starDiameterPeerUp NOTIFICATION-TYPE
    OBJECTS { starDiameterVpnName, starDiameterPeerAddr, starDiameterEndpointName }
    STATUS  current
    DESCRIPTION
 	"A diameter peer is up.  This notification is only generated for peers which
 	 have previously been declared down."
    --#SUMMARY "[VPN %s] Diameter Peer %s endpoint %s is up"
    --#ARGUMENTS {0,1,2}
    --#STATE OPERATIONAL
    --#SEVERITY INFORMATIONAL
    ::= { starentTraps 185 }

starDiameterServerUnreachable NOTIFICATION-TYPE
    OBJECTS { starServiceVpnName, starDiameterPeerAddr, starDiameterEndpointName }
    STATUS  current
    DESCRIPTION
 	"A diameter server is down.

 	 Problem Cause: The diameter server has failed, or a network connectivity
 	 prevents reaching the server.

 	 Condition Clear Alarm:  A starDiameterServerReachable notification will be generated when
	 the server is reachable"
    --#SUMMARY "[VPN %s] Diameter Server %s endpoint %s is unreachable"
    --#ARGUMENTS {0,1,2}
    --#STATE DEGRADED
    --#SEVERITY MAJOR
    ::= { starentTraps 186 }

starDiameterServerReachable NOTIFICATION-TYPE
    OBJECTS { starServiceVpnName, starDiameterPeerAddr, starDiameterEndpointName }
    STATUS  current
    DESCRIPTION
 	"A diameter server is up.  This notification is only generated for servers which
 	 have previously been declared unreachable."
    --#SUMMARY "[VPN %s] Diameter Server %s endpoint %s is reachable"
    --#ARGUMENTS {0,1,2}
    --#STATE OPERATIONAL
    --#SEVERITY INFORMATIONAL
    ::= { starentTraps 187 }

starCDRFileRemoved NOTIFICATION-TYPE
    OBJECTS { starCDRFilename }
    STATUS  current
    DESCRIPTION
	"A Charging Data Record (CDR) file has been deleted from the system due to a
	 lack of available storage space.  When required, the system deletes old files
	 to make space for new files.  This notification is only generated when
	 specifically enabled on the system.

	 Probable Cause: CDR files are not being moved off the system, or these files
	 are not being deleted after they have been transferred."
    --#SUMMARY "[System] CDR file %s removed"
    --#ARGUMENTS {0}
    --#STATE OPERATIONAL
    --#SEVERITY MAJOR
    ::= { starentTraps 188 }

starCSCFPeerServerReachable NOTIFICATION-TYPE
    OBJECTS { starCSCFPeerServerVpnName, starCSCFPeerServerSvcName, starCSCFPeerServerListName }
    STATUS  current
    DESCRIPTION
        "A peer server is reachable"
    --#SUMMARY "[CSCF %s-%s] CSCF Peer Server %s Reachable"
    --#ARGUMENTS {0,1,2}
    --#STATE OPERATIONAL
    --#SEVERITY INFORMATIONAL
    ::= { starentTraps 189 }

starCSCFPeerServerUnreachable NOTIFICATION-TYPE
    OBJECTS { starCSCFPeerServerVpnName, starCSCFPeerServerSvcName, starCSCFPeerServerListName }
    STATUS  current
    DESCRIPTION
        "A peer server is unreachable"
    --#SUMMARY "[CSCF %s-%s] CSCF Peer Server %s UnReachable"
    --#ARGUMENTS {0,1,2}
    --#STATE DEGRADED
    --#SEVERITY MINOR
    ::= { starentTraps 190 }

starDHCPV6ServiceStart NOTIFICATION-TYPE
    OBJECTS { starServiceVpnName, starServiceServName }
    STATUS  current
    DESCRIPTION
    "A SGSN Service has started
    Action to be Taken: No action required"
    --#SUMMARY "[Service DHCP V6 %s-%s] DHCP V6 service has started"
    --#ARGUMENTS {0,1}
    --#STATE OPERATIONAL
    --#SEVERITY INFORMATIONAL
    ::= { starentTraps 191 }

starCLIConfigMode NOTIFICATION-TYPE
    OBJECTS { starCLIUsername, starCLIContext }
    STATUS  current
    DESCRIPTION
        "An interactive CLI session has enter 'configuration' mode for the specified
	 context.  This CLI user can thus potentially start issuing configuration
	 commands which will impact the overall system configuration.

	 Note that this notification is not enabled by default; it is only generated
	 if the system is specifically configured to enable it."
    --#SUMMARY "[System] CLI session entered configuration mode for context %s, CLI user %s"
    --#ARGUMENTS {1,0}
    --#STATE OPERATIONAL
    --#SEVERITY INFORMATIONAL
    ::= { starentTraps 192 }

starDHCPV6ServiceStop NOTIFICATION-TYPE
    OBJECTS { starServiceVpnName, starServiceServName }
    STATUS  current
    DESCRIPTION
    "A DHCPV6 Service has stopped.
    Clear Condition: Verify that the DHCPV6 service is operational.

    Condition Clear Alarm:  A starDHCPV6ServiceStart notification will be generated when
    the service is restarted"
    --#SUMMARY "[Service DHCPV6 %s-%s] DHCPV6 service has stopped"
    --#ARGUMENTS {0,1}
    --#STATE DEGRADED
    --#SEVERITY MAJOR
    ::= { starentTraps 193 }

starSGSNServiceStart NOTIFICATION-TYPE
    OBJECTS { starServiceVpnName, starServiceServName }
    STATUS  current
    DESCRIPTION
    "A SGSN Service has started
    Action to be Taken: No action required"
    --#SUMMARY "[Service SGSN %s-%s] SGSN service has started"
    --#ARGUMENTS {0,1}
    --#STATE OPERATIONAL
    --#SEVERITY INFORMATIONAL
    ::= { starentTraps 194 }

starSGSNServiceStop NOTIFICATION-TYPE
    OBJECTS { starServiceVpnName, starServiceServName }
    STATUS  current
    DESCRIPTION
    "A SGSN Service has stopped.
    Probable Cause: This is typically caused by operator invention.  In
    unusual cases it can be caused by the loss of resources (PACs/PSCs) to
    support the running configuration.

    Action to be Taken: If the SGSN service shutdown was not planned,
    examine the admin logs for an indication of the failure.  Verify that
    all configured PACs/PSCs are present and running in the system.  Check the
    crash logs for an indication of a software failure.

    Clear Condition: Verify that the SGSN service is operational.

    Condition Clear Alarm:  A starSGSNServiceStart notification will be generated when
    the service is restarted"
    --#SUMMARY "[Service SGSN %s-%s] SGSN service has stopped"
    --#ARGUMENTS {0,1}
    --#STATE DEGRADED
    --#SEVERITY MAJOR
    ::= { starentTraps 195 }

starM3UAPCUnavailable NOTIFICATION-TYPE
    OBJECTS {
                starSS7rdId,
                starSS7Pc,
                starSS7M3UAPsId,
                starSS7CauseString
            }
    STATUS  current
    DESCRIPTION
    "M3UA Route to the Point code becomes unavailable.

    Possibe reason:
    1. Received destination unavailable (DUNA) message or
    2. SCTP association is down or
    3. Remote peer server is down

    Condition Clear Alarm:  A starM3UAPCAvailable notification will be generated when
    the reemore peer identified by the point code becomes reachable"

    --#SUMMARY "[ss7-routing-domain %d] m3ua point-code %d through peer-server %d unavailable cause %s"
    --#ARGUMENTS {0,1,2,3}
    --#STATE DEGRADED
    --#SEVERITY MINOR
    ::= { starentTraps 196 }

starM3UAPCAvailable NOTIFICATION-TYPE
    OBJECTS {
                starSS7rdId,
                starSS7Pc,
                starSS7M3UAPsId,
                starSS7CauseString
            }
    STATUS  current
    DESCRIPTION
    "M3UA Route to the Point code becomes available.

    Possible reason:
    1. Received destination available (DAVA) message.
    2. SCTP association is up
    3. Remote peer server is up

    starM3UAPCAvailable is generated only when a previous starM3UAPCUnavailable is generated.
    "
    --#SUMMARY "[ss7-routing-domain %d] m3ua point-code %d through peer-server %d available cause %s"
    --#ARGUMENTS {0,1,2,3}
    --#STATE OPERATIONAL
    --#SEVERITY INFORMATIONAL
    ::= { starentTraps 197 }



 -- Thresholds

starThreshCPUUtilization NOTIFICATION-TYPE
    OBJECTS { starCPUSlot, starCPUNumber, starThreshPct, starThreshMeasuredPct }
    STATUS current
    DESCRIPTION
	"The overall CPU utilization for the identified processor has exceeded for configured
	 threshold value for the current monitoring period.

         Probable Cause: This is a user configurable threshold.

         If the thresholding subsystem is configured to run in an 'alarm' model,
         a starThreshClearCPUUtilization notification will be generated when the measured
	 value falls below the threshold."
    --#SUMMARY "[Card] Threshold: CPU utilization threshold for card %d CPU %d threshold %d%% measured %d%%"
    --#ARGUMENTS {0,1,2,3}
    --#STATE OPERATIONAL
    --#SEVERITY WARNING
    ::= { starentTraps 200 }

starThreshClearCPUUtilization NOTIFICATION-TYPE
    OBJECTS { starCPUSlot, starCPUNumber, starThreshPct, starThreshMeasuredPct }
    STATUS current
    DESCRIPTION
	"The threshold condition is now clear."
    --#SUMMARY "[Card] Threshold: CPU utilization threshold clear card %d for CPU %d threshold %d%% measured %d%%"
    --#ARGUMENTS {0,1,2,3}
    --#STATE OPERATIONAL
    --#SEVERITY INFORMATIONAL
    ::= { starentTraps 201 }

starThreshCPUMemory NOTIFICATION-TYPE
    OBJECTS { starCPUSlot, starCPUNumber, starThreshInt, starThreshMeasuredInt }
    STATUS current
    DESCRIPTION
	"The amount of available memory for the identified processor has fallen below the
	 configured threshold value.

         Probable Cause: This is a user configurable threshold.

         If the thresholding subsystem is configured to run in an 'alarm' model,
         a starThreshClearCPUMemory notification will be generated when the measured
	 value falls below the threshold."
    --#SUMMARY "[Card %d] Threshold: CPU memory threshold for CPU %d; measured %d threshold %d"
    --#ARGUMENTS {0,1,3,2}
    --#STATE OPERATIONAL
    --#SEVERITY WARNING
    ::= { starentTraps 202 }

starThreshClearCPUMemory NOTIFICATION-TYPE
    OBJECTS { starCPUSlot, starCPUNumber, starThreshInt, starThreshMeasuredInt }
    STATUS current
    DESCRIPTION
	"The threshold condition is now clear."
    --#SUMMARY "[Card %d] Threshold: CPU memory threshold CLEAR for CPU %d; measured %d threshold %d"
    --#ARGUMENTS {0,1,3,2}
    --#STATE OPERATIONAL
    --#SEVERITY INFORMATIONAL
    ::= { starentTraps 203 }

starThreshLicense NOTIFICATION-TYPE
    OBJECTS { starThreshPct, starThreshMeasuredPct, starServiceType }
    STATUS current
    DESCRIPTION
	"The percentage available, licensed subscribers has fallen below the configured
	 threshold value.

         Probable Cause: This is a user configurable threshold.

         If the thresholding subsystem is configured to run in an 'alarm' model,
         a starThreshClearLicense notification will be generated when the measured
	 value falls below the threshold."
    --#SUMMARY "[System] Threshold: license threshold for service %s threshold %d%% measured %d%%"
    --#ARGUMENTS {2,0,1}
    --#STATE OPERATIONAL
    --#SEVERITY WARNING
    ::= { starentTraps 204 }

starThreshClearLicense NOTIFICATION-TYPE
    OBJECTS { starThreshPct, starThreshMeasuredPct, starServiceType }
    STATUS current
    DESCRIPTION
	"The threshold condition is now clear."
    --#SUMMARY "[System] Threshold: license threshold for service %s threshold %d%% measured %d%%"
    --#ARGUMENTS {2,0,1}
    --#STATE OPERATIONAL
    --#SEVERITY INFORMATIONAL
    ::= { starentTraps 205 }

starThreshSubscriberTotal NOTIFICATION-TYPE
    OBJECTS { starThreshInt, starThreshMeasuredInt }
    STATUS current
    DESCRIPTION
	"The total number of subscribers is above the configured threshold value.

         Probable Cause: This is a user configurable threshold.

         If the thresholding subsystem is configured to run in an 'alarm' model,
         a starThreshClearSubscriberTotal notification will be generated when the measured
	 value falls below the threshold."
    --#SUMMARY "[System] Threshold: subscriber total threshold; measured %d threshold %d"
    --#ARGUMENTS {1,0}
    --#STATE OPERATIONAL
    --#SEVERITY WARNING
    ::= { starentTraps 206 }

starThreshClearSubscriberTotal NOTIFICATION-TYPE
    OBJECTS { starThreshInt, starThreshMeasuredInt }
    STATUS current
    DESCRIPTION
	"The threshold condition is now clear."
    --#SUMMARY "[System] Threshold: subscriber total threshold CLEAR; measured %d threshold %d"
    --#ARGUMENTS {1,0}
    --#STATE OPERATIONAL
    --#SEVERITY INFORMATIONAL
    ::= { starentTraps 207 }

starThreshSubscriberActive NOTIFICATION-TYPE
    OBJECTS { starThreshInt, starThreshMeasuredInt }
    STATUS current
    DESCRIPTION
	"The total number of active subscribers is above the configured threshold value.

         Probable Cause: This is a user configurable threshold.

         If the thresholding subsystem is configured to run in an 'alarm' model,
         a starThreshClearSubscriberActive notification will be generated when the measured
	 value falls below the threshold."
    --#SUMMARY "[System] Threshold: active subscribers threshold; measured %d threshold %d"
    --#ARGUMENTS {1,0}
    --#STATE OPERATIONAL
    --#SEVERITY WARNING
    ::= { starentTraps 208 }

starThreshClearSubscriberActive NOTIFICATION-TYPE
    OBJECTS { starThreshInt, starThreshMeasuredInt }
    STATUS current
    DESCRIPTION
	"The threshold condition is now clear."
    --#SUMMARY "[System] Threshold: active subscribers threshold CLEAR; measured %d threshold %d"
    --#ARGUMENTS {1,0}
    --#STATE OPERATIONAL
    --#SEVERITY INFORMATIONAL
    ::= { starentTraps 209 }

starThreshPortRxUtil NOTIFICATION-TYPE
    OBJECTS { starPortSlot, starPortNum, starThreshPct, starThreshMeasuredPct,starSlotSerialNumber }
    STATUS current
    DESCRIPTION
	"The Rx utilization of the port has exceeded the configured threshold value during
	 the current monitoring period.

         Probable Cause: This is a user configurable threshold.

         If the thresholding subsystem is configured to run in an 'alarm' model,
         a starThreshClearPortRxUtil notification will be generated when the measured
	 value falls below the threshold."
    --#SUMMARY "[System] Threshold: port rx utilization threshold on slot %d port %d threshold %d%% measured %d%% UUID %s"
    --#ARGUMENTS {0,1,2,3}
    --#STATE OPERATIONAL
    --#SEVERITY WARNING
    ::= { starentTraps 210 }

starThreshClearPortRxUtil NOTIFICATION-TYPE
    OBJECTS { starPortSlot, starPortNum, starThreshPct, starThreshMeasuredPct, starSlotSerialNumber }
    STATUS current
    DESCRIPTION
	"The threshold condition is now clear."
    --#SUMMARY "[System] Threshold: port rx utilization threshold clear on slot %d port %d threshold %d%% measured %d%% UUID %s"
    --#ARGUMENTS {0,1,2,3,4}
    --#STATE OPERATIONAL
    --#SEVERITY INFORMATIONAL
    ::= { starentTraps 211 }

starThreshPortTxUtil NOTIFICATION-TYPE
    OBJECTS { starPortSlot, starPortNum, starThreshPct, starThreshMeasuredPct, starSlotSerialNumber }
    STATUS current
    DESCRIPTION
	"The Tx utilization of the port has exceeded the configured threshold value during
	 the current monitoring period.

         Probable Cause: This is a user configurable threshold.

         If the thresholding subsystem is configured to run in an 'alarm' model,
         a starThreshClearPortTxUtil notification will be generated when the measured
	 value falls below the threshold."
    --#SUMMARY "[System] Threshold: port tx utilization threshold on slot %d port %d threshold %d%% measured %d%% UUID %s"
    --#ARGUMENTS {0,1,2,3,4}
    --#STATE OPERATIONAL
    --#SEVERITY WARNING
    ::= { starentTraps 212 }

starThreshClearPortTxUtil NOTIFICATION-TYPE
    OBJECTS { starPortSlot, starPortNum, starThreshPct, starThreshMeasuredPct, starSlotSerialNumber }
    STATUS current
    DESCRIPTION
	"The threshold condition is now clear."
    --#SUMMARY "[System] Threshold: port tx utilization threshold clear on slot %d port %d threshold %d%% measured %d%% UUID %s"
    --#ARGUMENTS {0,1,2,3,4}
    --#STATE OPERATIONAL
    --#SEVERITY INFORMATIONAL
    ::= { starentTraps 213 }

starThreshPortHighActivity NOTIFICATION-TYPE
    OBJECTS { starPortSlot, starPortNum, starThreshPct, starThreshMeasuredPct, starSlotSerialNumber }
    STATUS current
    DESCRIPTION
	    "High activity on the port has exceeded the configured
         threshold value during the current monitoring period.

         Probable Cause: This is a user configurable threshold.

         If the thresholding subsystem is configured to run in an 'alarm' model,
         a starThreshClearPortHighActivity notification will be generated when the measured
	 value falls below the threshold."
    --#SUMMARY "[System] Threshold: port high activity threshold on slot %d port %d threshold %d%% measured %d%% UUID %s"
    --#ARGUMENTS {0,1,2,3,4}
    --#STATE OPERATIONAL
    --#SEVERITY WARNING
    ::= { starentTraps 214 }

starThreshClearPortHighActivity NOTIFICATION-TYPE
    OBJECTS { starPortSlot, starPortNum, starThreshPct, starThreshMeasuredPct, starSlotSerialNumber }
    STATUS current
    DESCRIPTION
	"The threshold condition is now clear."
    --#SUMMARY "[System] Threshold: port high activity threshold clear on slot %d port %d threshold %d%% measured %d%% UUID %s"
    --#ARGUMENTS {0,1,2,3,4}
    --#STATE OPERATIONAL
    --#SEVERITY INFORMATIONAL
    ::= { starentTraps 215 }

starThreshAAAAuthFail NOTIFICATION-TYPE
    OBJECTS { starThreshInt, starThreshMeasuredInt }
    STATUS current
    DESCRIPTION
	"The number of AAA authentication failures has exceeded the configured threshold
	 during the current monitoring period.

         Probable Cause: This is a user configurable threshold.

         If the thresholding subsystem is configured to run in an 'alarm' model,
         a starThreshClearAAAAuthFail notification will be generated when the measured
	 value falls below the threshold."
    --#SUMMARY "[System] Threshold: AAA authentication failures threshold; measured %d threshold %d"
    --#ARGUMENTS {1,0}
    --#STATE OPERATIONAL
    --#SEVERITY WARNING
    ::= { starentTraps 216 }

starThreshClearAAAAuthFail NOTIFICATION-TYPE
    OBJECTS { starThreshInt, starThreshMeasuredInt }
    STATUS current
    DESCRIPTION
	"The threshold condition is now clear."
    --#SUMMARY "[System] Threshold: AAA authentication failures threshold CLEAR; measured %d threshold %d"
    --#ARGUMENTS {1,0}
    --#STATE OPERATIONAL
    --#SEVERITY INFORMATIONAL
    ::= { starentTraps 217 }

starThreshAAAAuthFailRate NOTIFICATION-TYPE
    OBJECTS { starThreshPct, starThreshMeasuredPct }
    STATUS current
    DESCRIPTION
	"The percentage of AAA authentication requests which failed has exceeded the configured threshold
	 during the current monitoring period.

         Probable Cause: This is a user configurable threshold.

         If the thresholding subsystem is configured to run in an 'alarm' model,
         a starThreshClearAAAAuthFailRate notification will be generated when the measured
	 value falls below the threshold."
    --#SUMMARY "[System] Threshold: AAA authentication failure rate threshold for threshold %d%% measured %d%%"
    --#ARGUMENTS {0,1}
    --#STATE OPERATIONAL
    --#SEVERITY WARNING
    ::= { starentTraps 218 }

starThreshClearAAAAuthFailRate NOTIFICATION-TYPE
    OBJECTS { starThreshPct, starThreshMeasuredPct }
    STATUS current
    DESCRIPTION
	"The threshold condition is now clear."
    --#SUMMARY "[System] Threshold: AAA authentication failure rate threshold clear for threshold %d%% measured %d%%"
    --#ARGUMENTS {0,1}
    --#STATE OPERATIONAL
    --#SEVERITY INFORMATIONAL
    ::= { starentTraps 219 }

starThreshAAAAcctFail NOTIFICATION-TYPE
    OBJECTS { starThreshInt, starThreshMeasuredInt }
    STATUS current
    DESCRIPTION
	"The number of AAA accounting failures has exceeded the configured threshold
	 during the current monitoring period.

         Probable Cause: This is a user configurable threshold.

         If the thresholding subsystem is configured to run in an 'alarm' model,
         a starThreshClearAAAAcctFail notification will be generated when the measured
	 value falls below the threshold."
    --#SUMMARY "[System] Threshold: AAA accounting failures threshold; measured %d threshold %d"
    --#ARGUMENTS {1,0}
    --#STATE OPERATIONAL
    --#SEVERITY WARNING
    ::= { starentTraps 220 }

starThreshClearAAAAcctFail NOTIFICATION-TYPE
    OBJECTS { starThreshInt, starThreshMeasuredInt }
    STATUS current
    DESCRIPTION
	"The threshold condition is now clear."
    --#SUMMARY "[System] Threshold: AAA accounting failures threshold CLEAR; measured %d threshold %d"
    --#ARGUMENTS {1,0}
    --#STATE OPERATIONAL
    --#SEVERITY INFORMATIONAL
    ::= { starentTraps 221 }

starThreshAAAAcctFailRate NOTIFICATION-TYPE
    OBJECTS { starThreshPct, starThreshMeasuredPct }
    STATUS current
    DESCRIPTION
	"The percentage of AAA accounting requests which failed has exceeded the configured threshold
	 during the current monitoring period.

         Probable Cause: This is a user configurable threshold.

         If the thresholding subsystem is configured to run in an 'alarm' model,
         a starThreshClearAAAAcctFailRate notification will be generated when the measured
	 value falls below the threshold."
    --#SUMMARY "[System] Threshold: AAA accounting failure rate threshold for threshold %d%% measured %d%%"
    --#ARGUMENTS {0,1}
    --#STATE OPERATIONAL
    --#SEVERITY WARNING
    ::= { starentTraps 222 }

starThreshClearAAAAcctFailRate NOTIFICATION-TYPE
    OBJECTS { starThreshPct, starThreshMeasuredPct }
    STATUS current
    DESCRIPTION
	"The threshold condition is now clear."
    --#SUMMARY "[System] Threshold: AAA accounting failure rate threshold clear for threshold %d%% measured %d%%"
    --#ARGUMENTS {0,1}
    --#STATE OPERATIONAL
    --#SEVERITY INFORMATIONAL
    ::= { starentTraps 223 }

starThreshAAARetryRate NOTIFICATION-TYPE
    OBJECTS { starThreshPct, starThreshMeasuredPct }
    STATUS current
    DESCRIPTION
	"The percentage of AAA requests which has to be retried has exceeded the configured threshold
	 during the current monitoring period.

         Probable Cause: This is a user configurable threshold.

         If the thresholding subsystem is configured to run in an 'alarm' model,
         a starThreshClearAAARetryRate notification will be generated when the measured
	 value falls below the threshold."
    --#SUMMARY "[System] Threshold: AAA retry rate threshold for threshold %d%% measured %d%%"
    --#ARGUMENTS {0,1}
    --#STATE OPERATIONAL
    --#SEVERITY WARNING
    ::= { starentTraps 224 }

starThreshClearAAARetryRate NOTIFICATION-TYPE
    OBJECTS { starThreshPct, starThreshMeasuredPct }
    STATUS current
    DESCRIPTION
	"The threshold condition is now clear."
    --#SUMMARY "[System] Threshold: AAA retry rate threshold clear for threshold %d%% measured %d%%"
    --#ARGUMENTS {0,1}
    --#STATE OPERATIONAL
    --#SEVERITY INFORMATIONAL
    ::= { starentTraps 225 }

starThreshCallSetup NOTIFICATION-TYPE
    OBJECTS { starThreshInt, starThreshMeasuredInt }
    STATUS current
    DESCRIPTION
	"The number of call setup operations has exceeded the configured threshold during the
	 current monitoring period.

         Probable Cause: This is a user configurable threshold.

         If the thresholding subsystem is configured to run in an 'alarm' model,
         a starThreshClearCallSetup notification will be generated when the measured
	 value falls below the threshold."
    --#SUMMARY "[System] Threshold: call setups threshold; measured %d threshold %d"
    --#ARGUMENTS {1,0}
    --#STATE OPERATIONAL
    --#SEVERITY WARNING
    ::= { starentTraps 226 }

starThreshClearCallSetup NOTIFICATION-TYPE
    OBJECTS { starThreshInt, starThreshMeasuredInt }
    STATUS current
    DESCRIPTION
	"The threshold condition is now clear."
    --#SUMMARY "[System] Threshold: call setups threshold CLEAR; measured %d threshold %d"
    --#ARGUMENTS {1,0}
    --#STATE OPERATIONAL
    --#SEVERITY INFORMATIONAL
    ::= { starentTraps 227 }

starThreshCallSetupFailure NOTIFICATION-TYPE
    OBJECTS { starThreshInt, starThreshMeasuredInt }
    STATUS current
    DESCRIPTION
	"The number of call setup operations which failed has exceeded the configured threshold during the
	 current monitoring period.

         Probable Cause: This is a user configurable threshold.

         If the thresholding subsystem is configured to run in an 'alarm' model,
         a starThreshClearCallSetupFailure notification will be generated when the measured
	 value falls below the threshold."
    --#SUMMARY "[System] Threshold: call setup failures threshold; measured %d threshold %d"
    --#ARGUMENTS {1,0}
    --#STATE OPERATIONAL
    --#SEVERITY WARNING
    ::= { starentTraps 228 }

starThreshClearCallSetupFailure NOTIFICATION-TYPE
    OBJECTS { starThreshInt, starThreshMeasuredInt }
    STATUS current
    DESCRIPTION
	"The threshold condition is now clear."
    --#SUMMARY "[System] Threshold: call setup failures threshold CLEAR; measured %d threshold %d"
    --#ARGUMENTS {1,0}
    --#STATE OPERATIONAL
    --#SEVERITY INFORMATIONAL
    ::= { starentTraps 229 }

starThreshCallRejectNoResource NOTIFICATION-TYPE
    OBJECTS { starThreshInt, starThreshMeasuredInt }
    STATUS current
    DESCRIPTION
	"The number of call setup operations which were rejected due to a no resource condition
         has exceeded the configured threshold during the current monitoring period.

         Probable Cause: This is a user configurable threshold.

         If the thresholding subsystem is configured to run in an 'alarm' model,
         a starThreshClearCallRejectNoResource notification will be generated when the measured
	 value falls below the threshold."
    --#SUMMARY "[System] Threshold: calls rejects for no resource condition threshold; measured %d threshold %d"
    --#ARGUMENTS {1,0}
    --#STATE OPERATIONAL
    --#SEVERITY WARNING
    ::= { starentTraps 230 }

starThreshClearCallRejectNoResource NOTIFICATION-TYPE
    OBJECTS { starThreshInt, starThreshMeasuredInt }
    STATUS current
    DESCRIPTION
	"The threshold condition is now clear."
    --#SUMMARY "[System] Threshold: calls rejects for no resource condition threshold CLEAR; measured %d threshold %d"
    --#ARGUMENTS {1,0}
    --#STATE OPERATIONAL
    --#SEVERITY INFORMATIONAL
    ::= { starentTraps 231 }

starThreshPacketsFilteredDropped NOTIFICATION-TYPE
    OBJECTS { starThreshInt, starThreshMeasuredInt }
    STATUS current
    DESCRIPTION
	"The number of user data packets filtered has exceeded the configured threshold
	 for the current monitoring period.

         Probable Cause: This is a user configurable threshold.

         If the thresholding subsystem is configured to run in an 'alarm' model,
         a starThreshClearPacketsFilteredDropped notification will be generated when the measured
	 value falls below the threshold."
    --#SUMMARY "[System] Threshold: user packets filtered threshold; measured %d threshold %d"
    --#ARGUMENTS {1,0}
    --#STATE OPERATIONAL
    --#SEVERITY WARNING
    ::= { starentTraps 232 }

starThreshClearPacketsFilteredDropped NOTIFICATION-TYPE
    OBJECTS { starThreshInt, starThreshMeasuredInt }
    STATUS current
    DESCRIPTION
	"The threshold condition is now clear."
    --#SUMMARY "[System] Threshold: user packets filtered threshold CLEAR; measured %d threshold %d"
    --#ARGUMENTS {1,0}
    --#STATE OPERATIONAL
    --#SEVERITY INFORMATIONAL
    ::= { starentTraps 233 }

starThreshPacketsForwarded NOTIFICATION-TYPE
    OBJECTS { starThreshInt, starThreshMeasuredInt }
    STATUS current
    DESCRIPTION
	"The number of user data packets forwarded has exceeded the configured threshold
	 for the current monitoring period.

         Probable Cause: This is a user configurable threshold.

         If the thresholding subsystem is configured to run in an 'alarm' model,
         a starThreshClearPacketsForwarded notification will be generated when the measured
	 value falls below the threshold."
    --#SUMMARY "[System] Threshold: user packets forwarded threshold; measured %d threshold %d"
    --#ARGUMENTS {1,0}
    --#STATE OPERATIONAL
    --#SEVERITY WARNING
    ::= { starentTraps 234 }

starThreshClearPacketsForwarded NOTIFICATION-TYPE
    OBJECTS { starThreshInt, starThreshMeasuredInt }
    STATUS current
    DESCRIPTION
	"The threshold condition is now clear."
    --#SUMMARY "[System] Threshold: user packets forwarded threshold CLEAR; measured %d threshold %d"
    --#ARGUMENTS {1,0}
    --#STATE OPERATIONAL
    --#SEVERITY INFORMATIONAL
    ::= { starentTraps 235 }

starThreshSessCPUThroughput NOTIFICATION-TYPE
    OBJECTS { starCPUSlot, starCPUNumber, starThreshMB, starThreshMeasuredMB }
    STATUS current
    DESCRIPTION
	"The total session throughout for the specified processor has exceeded the configured
	 threshold for the current monitoring period.

         Probable Cause: This is a user configurable threshold.

         If the thresholding subsystem is configured to run in an 'alarm' model,
         a starThreshClearSessCPUThroughput notification will be generated when the measured
	 value falls below the threshold."
    --#SUMMARY "[Card %d] Threshold: CPU throughput threshold on CPU %d; measured %d threshold %d"
    --#ARGUMENTS {0,1,3,2}
    --#STATE OPERATIONAL
    --#SEVERITY WARNING
    ::= { starentTraps 236 }

starThreshClearSessCPUThroughput NOTIFICATION-TYPE
    OBJECTS { starCPUSlot, starCPUNumber, starThreshMB, starThreshMeasuredMB }
    STATUS current
    DESCRIPTION
	"The threshold condition is now clear."
    --#SUMMARY "[Card %d] Threshold: CPU throughput threshold CLEAR on CPU %d; measured %d threshold %d"
    --#ARGUMENTS {0,1,3,2}
    --#STATE OPERATIONAL
    --#SEVERITY INFORMATIONAL
    ::= { starentTraps 237 }

starThreshIPPoolAvail NOTIFICATION-TYPE
    OBJECTS { starIPPoolContext, starIPPoolGroup, starThreshPct, starThreshMeasuredPct }
    STATUS current
    DESCRIPTION
	"The available IP pool addresses in a context has fallen below the configured
	 threshold

         Probable Cause: This is a user configurable threshold.

         If the thresholding subsystem is configured to run in an 'alarm' model,
         a starThreshClearIPPoolAvail notification will be generated when the measured
	 value falls below the threshold."
    --#SUMMARY "[System] Threshold: IP Pool availability threshold for context %s pool group %s threshold %d%% measured %d%%"
    --#ARGUMENTS {0,1,2,3}
    --#STATE OPERATIONAL
    --#SEVERITY WARNING
    ::= { starentTraps 238 }

starThreshClearIPPoolAvail NOTIFICATION-TYPE
    OBJECTS { starIPPoolContext, starIPPoolGroup, starThreshPct, starThreshMeasuredPct }
    STATUS current
    DESCRIPTION
	"The threshold condition is now clear."
    --#SUMMARY "[System] Threshold: IP Pool availability threshold clear for context %s pool group %s threshold %d%% measured %d%%"
    --#ARGUMENTS {0,1,2,3}
    --#STATE OPERATIONAL
    --#SEVERITY INFORMATIONAL
    ::= { starentTraps 239 }

starThreshCPUUtilization10Sec NOTIFICATION-TYPE
    OBJECTS { starCPUSlot, starCPUNumber, starThreshPct, starThreshMeasuredPct }
    STATUS current
    DESCRIPTION
	"The CPU utilization of 10 second measurement for the identified processor has exceeded for configured
	 threshold value for the current monitoring period."
    --#SUMMARY "[Card] Threshold: 10 Second Average utilization for card %d CPU %d threshold %d%% measured %d%%"
    --#ARGUMENTS {0,1,2,3}
    --#STATE OPERATIONAL
    --#SEVERITY WARNING
    ::= { starentTraps 240 }

starThreshClearCPUUtilization10Sec NOTIFICATION-TYPE
    OBJECTS { starCPUSlot, starCPUNumber, starThreshPct, starThreshMeasuredPct }
    STATUS current
    DESCRIPTION
	"The threshold condition is now clear."
    --#SUMMARY "[Card] Threshold: 10 Second Average utilization clear for card %dCPU %d threshold %d%% measured %d%%"
    --#ARGUMENTS {0,1,2,3}
    --#STATE OPERATIONAL
    --#SEVERITY INFORMATIONAL
    ::= { starentTraps 241 }

starThreshCPULoad NOTIFICATION-TYPE
OBJECTS { starCPUSlot, starCPUNumber, starThreshInt, starThreshMeasuredInt }
    STATUS current
    DESCRIPTION
	"The CPU load for the identified processor has exceeded for configured
	 threshold value for the current monitoring period."
    --#SUMMARY "[Card %d] Threshold: CPU Load for CPU %d; measured %d threshold %d"
    --#ARGUMENTS {0,1,3,2}
    --#STATE OPERATIONAL
    --#SEVERITY WARNING
    ::= { starentTraps 242 }

starThreshClearCPULoad NOTIFICATION-TYPE
    OBJECTS { starCPUSlot, starCPUNumber, starThreshInt, starThreshMeasuredInt }
    STATUS current
    DESCRIPTION
	"The threshold condition is now clear."
    --#SUMMARY "[Card %d] Threshold: CPU Load CLEAR for CPU %d; measured %d threshold %d"
    --#ARGUMENTS {0,1,3,2}
    --#STATE OPERATIONAL
    --#SEVERITY INFORMATIONAL
    ::= { starentTraps 243 }

starThreshCPUMemUsage NOTIFICATION-TYPE
    OBJECTS { starCPUSlot, starCPUNumber, starThreshPct, starThreshMeasuredPct }
    STATUS current
    DESCRIPTION
	"The CPU mem usage for the identified processor has exceeded for configured
	 threshold value for the current monitoring period."
    --#SUMMARY "[Card] Threshold: CPU Memory Usage for card %d CPU %d threshold %d%% measured %d%%"
    --#ARGUMENTS {0,1,2,3}
    --#STATE OPERATIONAL
    --#SEVERITY WARNING
    ::= { starentTraps 244 }

starThreshClearCPUMemUsage NOTIFICATION-TYPE
    OBJECTS { starCPUSlot, starCPUNumber, starThreshPct, starThreshMeasuredPct }
    STATUS current
    DESCRIPTION
	"The threshold condition is now clear."
    --#SUMMARY "[Card] Threshold: Memory Usage clear for card %d CPU %d threshold %d%% measured %d%%"
    --#ARGUMENTS {0,1,2,3}
    --#STATE OPERATIONAL
    --#SEVERITY INFORMATIONAL
    ::= { starentTraps 245 }

starThreshPDSNSessions NOTIFICATION-TYPE
    OBJECTS { starThreshInt, starThreshMeasuredInt }
    STATUS current
    DESCRIPTION
	"The total number of PDSN sessions is above the configured threshold value."
    --#SUMMARY "[System] Threshold: Total PDSN Sessions; measured %d threshold %d"
    --#ARGUMENTS {1,0}
    --#STATE OPERATIONAL
    --#SEVERITY WARNING
    ::= { starentTraps 246 }

starThreshClearPDSNSessions NOTIFICATION-TYPE
    OBJECTS { starThreshInt, starThreshMeasuredInt }
    STATUS current
    DESCRIPTION
	"The threshold condition is now clear."
    --#SUMMARY "[System] Threshold: Total PDSN Sessions CLEAR; measured %d threshold %d"
    --#ARGUMENTS {1,0}
    --#STATE OPERATIONAL
    --#SEVERITY INFORMATIONAL
    ::= { starentTraps 247 }
    
starThreshGGSNSessions NOTIFICATION-TYPE
    OBJECTS { starThreshInt, starThreshMeasuredInt }
    STATUS current
    DESCRIPTION
	"The total number of GGSN sessions is above the configured threshold value."
    --#SUMMARY "[System] Threshold: Total GGSN Sessions; measured %d threshold %d"
    --#ARGUMENTS {1,0}
    --#STATE OPERATIONAL
    --#SEVERITY WARNING
    ::= { starentTraps 248 }

starThreshClearGGSNSessions NOTIFICATION-TYPE
    OBJECTS { starThreshInt, starThreshMeasuredInt }
    STATUS current
    DESCRIPTION
	"The threshold condition is now clear."
    --#SUMMARY "[System] Threshold: Total GGSN Sessions CLEAR; measured %d threshold %d"
    --#ARGUMENTS {1,0}
    --#STATE OPERATIONAL
    --#SEVERITY INFORMATIONAL
    ::= { starentTraps 249 }

starThreshHASessions NOTIFICATION-TYPE
    OBJECTS { starThreshInt, starThreshMeasuredInt }
    STATUS current
    DESCRIPTION
	"The total number of HA sessions is above the configured threshold value."
    --#SUMMARY "[System] Threshold: Total HA Sessions; measured %d threshold %d"
    --#ARGUMENTS {1,0}
    --#STATE OPERATIONAL
    --#SEVERITY WARNING
    ::= { starentTraps 250 }

starThreshClearHASessions NOTIFICATION-TYPE
    OBJECTS { starThreshInt, starThreshMeasuredInt }
    STATUS current
    DESCRIPTION
	"The threshold condition is now clear."
    --#SUMMARY "[System] Threshold: Total HA Sessions CLEAR; measured %d threshold %d"
    --#ARGUMENTS {1,0}
    --#STATE OPERATIONAL
    --#SEVERITY INFORMATIONAL
    ::= { starentTraps 251 }

starThreshLNSSessions NOTIFICATION-TYPE
    OBJECTS { starThreshInt, starThreshMeasuredInt }
    STATUS current
    DESCRIPTION
	"The total number of L2TP LNS sessions is above the configured threshold value."
    --#SUMMARY "[System] Threshold: Total L2TP LNS Sessions; measured %d threshold %d"
    --#ARGUMENTS {1,0}
    --#STATE OPERATIONAL
    --#SEVERITY WARNING
    ::= { starentTraps 252 }

starThreshClearLNSSessions NOTIFICATION-TYPE
    OBJECTS { starThreshInt, starThreshMeasuredInt }
    STATUS current
    DESCRIPTION
	"The threshold condition is now clear."
    --#SUMMARY "[System] Threshold: Total L2TP LNS Sessions CLEAR; measured %d threshold %d"
    --#ARGUMENTS {1,0}
    --#STATE OPERATIONAL
    --#SEVERITY INFORMATIONAL
    ::= { starentTraps 253 }

starThreshPerServicePDSNSessions NOTIFICATION-TYPE
    OBJECTS { starServiceVpnName, starServiceServName, starThreshInt, starThreshMeasuredInt }
    STATUS current
    DESCRIPTION
	"The total number of PDSN sessions in a service is above the configured threshold value."
    --#SUMMARY "[System] Threshold: Per Sevice PDSN Sessions, context %s service name %s; measured %d threshold %d"
    --#ARGUMENTS {0,1,3,2}
    --#STATE OPERATIONAL
    --#SEVERITY WARNING
    ::= { starentTraps 254 }

starThreshClearPerServicePDSNSessions NOTIFICATION-TYPE
    OBJECTS { starServiceVpnName, starServiceServName, starThreshInt, starThreshMeasuredInt }
    STATUS current
    DESCRIPTION
	"The threshold condition is now clear."
    --#SUMMARY "[System] Threshold: Per Sevice PDSN Sessions CLEAR, context %s service name %s; measured %d threshold %d"
    --#ARGUMENTS {0,1,3,2}
    --#STATE OPERATIONAL
    --#SEVERITY INFORMATIONAL
    ::= { starentTraps 255 }

starThreshPerServiceGGSNSessions NOTIFICATION-TYPE
    OBJECTS { starServiceVpnName, starServiceServName, starThreshInt, starThreshMeasuredInt }
    STATUS current
    DESCRIPTION
	"The total number of GGSN sessions in a service is above the configured threshold value."
    --#SUMMARY "[System] Threshold: Per Sevice GGSN Sessions, context %s service name %s; measured %d threshold %d"
    --#ARGUMENTS {0,1,3,2}
    --#STATE OPERATIONAL
    --#SEVERITY WARNING
    ::= { starentTraps 256 }

starThreshClearPerServiceGGSNSessions NOTIFICATION-TYPE
    OBJECTS { starServiceVpnName, starServiceServName, starThreshInt, starThreshMeasuredInt }
    STATUS current
    DESCRIPTION
	"The threshold condition is now clear."
    --#SUMMARY "[System] Threshold: Per Sevice GGSN Sessions CLEAR, context %s service name %s; measured %d threshold %d"
    --#ARGUMENTS {0,1,3,2}
    --#STATE OPERATIONAL
    --#SEVERITY INFORMATIONAL
    ::= { starentTraps 257 }

starThreshPerServiceHASessions NOTIFICATION-TYPE
    OBJECTS { starServiceVpnName, starServiceServName, starThreshInt, starThreshMeasuredInt }
    STATUS current
    DESCRIPTION
	"The total number of HA sessions in a service is above the configured threshold value."
    --#SUMMARY "[System] Threshold: Per Sevice HA Sessions, context %s service name %s; measured %d threshold %d"
    --#ARGUMENTS {0,1,3,2}
    --#STATE OPERATIONAL
    --#SEVERITY WARNING
    ::= { starentTraps 258 }

starThreshClearPerServiceHASessions NOTIFICATION-TYPE
    OBJECTS { starServiceVpnName, starServiceServName, starThreshInt, starThreshMeasuredInt }
    STATUS current
    DESCRIPTION
	"The threshold condition is now clear."
    --#SUMMARY "[System] Threshold: Per Sevice HA Sessions CLEAR, context %s service name %s; measured %d threshold %d"
    --#ARGUMENTS {0,1,3,2}
    --#STATE OPERATIONAL
    --#SEVERITY INFORMATIONAL
    ::= { starentTraps 259 }

starThreshPerServiceLNSSessions NOTIFICATION-TYPE
    OBJECTS { starServiceVpnName, starServiceServName, starThreshInt, starThreshMeasuredInt }
    STATUS current
    DESCRIPTION
	"The total number of L2TP LNS sessions in a service is above the configured threshold value."
    --#SUMMARY "[System] Threshold: Per Sevice L2TP LNS Sessions, context %s service name %s; measured %d threshold %d"
    --#ARGUMENTS {0,1,3,2}
    --#STATE OPERATIONAL
    --#SEVERITY WARNING
    ::= { starentTraps 260 }

starThreshClearPerServiceLNSSessions NOTIFICATION-TYPE
    OBJECTS { starServiceVpnName, starServiceServName, starThreshInt, starThreshMeasuredInt }
    STATUS current
    DESCRIPTION
	"The threshold condition is now clear."
    --#SUMMARY "[System] Threshold: Per Sevice L2TP LNS Sessions CLEAR, context %s service name %s; measured %d threshold %d"
    --#ARGUMENTS {0,1,3,2}
    --#STATE OPERATIONAL
    --#SEVERITY INFORMATIONAL
    ::= { starentTraps 261 }

starThreshIPPoolHold NOTIFICATION-TYPE
    OBJECTS { starIPPoolContext, starIPPoolName, starThreshPct, starThreshMeasuredPct }
    STATUS current
    DESCRIPTION
	"The percentage IP pool addresses in HOLD state in a context has gone above the configured
	 threshold"
    --#SUMMARY "[System] Threshold: IP Pool Address in Hold State for context %s pool %s threshold %d%% measured %d%%"
    --#ARGUMENTS {0,1,2,3}
    --#STATE OPERATIONAL
    --#SEVERITY WARNING
    ::= { starentTraps 262 }

starThreshClearIPPoolHold NOTIFICATION-TYPE
    OBJECTS { starIPPoolContext, starIPPoolName, starThreshPct, starThreshMeasuredPct }
    STATUS current
    DESCRIPTION
	"The threshold condition is now clear."
    --#SUMMARY "[System] Threshold: IP Pool Address in Hold State clear for context %s pool %s threshold %d%% measured %d%%"
    --#ARGUMENTS {0,1,2,3}
    --#STATE OPERATIONAL
    --#SEVERITY INFORMATIONAL
    ::= { starentTraps 263 }

starThreshIPPoolUsed NOTIFICATION-TYPE
    OBJECTS { starIPPoolContext, starIPPoolName, starThreshPct, starThreshMeasuredPct }
    STATUS current
    DESCRIPTION
	"The percentage IP pool addresses in USED state in a context has gone above the configured
	 threshold"
    --#SUMMARY "[System] Threshold: IP Pool Address in Used State for context %s pool %s threshold %d%% measured %d%%"
    --#ARGUMENTS {0,1,2,3}
    --#STATE OPERATIONAL
    --#SEVERITY WARNING
    ::= { starentTraps 264 }

starThreshClearIPPoolUsed NOTIFICATION-TYPE
    OBJECTS { starIPPoolContext, starIPPoolName, starThreshPct, starThreshMeasuredPct }
    STATUS current
    DESCRIPTION
	"The threshold condition is now clear."
    --#SUMMARY "[System] Threshold: IP Pool Address in Used State clear for context %s pool %s threshold %d%% measured %d%%"
    --#ARGUMENTS {0,1,2,3}
    --#STATE OPERATIONAL
    --#SEVERITY INFORMATIONAL
    ::= { starentTraps 265 }

starThreshIPPoolRelease NOTIFICATION-TYPE
    OBJECTS { starIPPoolContext, starIPPoolName, starThreshPct, starThreshMeasuredPct }
    STATUS current
    DESCRIPTION
	"The percentage IP pool addresses in RELEASE state in a context has gone above the configured
	 threshold"
    --#SUMMARY "[System] Threshold: IP Pool Address in Release State for context %s pool %s threshold %d%% measured %d%%"
    --#ARGUMENTS {0,1,2,3}
    --#STATE OPERATIONAL
    --#SEVERITY WARNING
    ::= { starentTraps 266 }

starThreshClearIPPoolRelease NOTIFICATION-TYPE
    OBJECTS { starIPPoolContext, starIPPoolName, starThreshPct, starThreshMeasuredPct }
    STATUS current
    DESCRIPTION
	"The threshold condition is now clear."
    --#SUMMARY "[System] Threshold: IP Pool Address in Release State clear for context %s pool %s threshold %d%% measured %d%%"
    --#ARGUMENTS {0,1,2,3}
    --#STATE OPERATIONAL
    --#SEVERITY INFORMATIONAL
    ::= { starentTraps 267 }

starThreshIPPoolFree NOTIFICATION-TYPE
    OBJECTS { starIPPoolContext, starIPPoolName, starThreshPct, starThreshMeasuredPct }
    STATUS current
    DESCRIPTION
	"The percentage IP pool addresses in HOLD state in a context has gone below the configured
	 threshold"
    --#SUMMARY "[System] Threshold: IP Pool Address in Free State for context %s pool %s threshold %d%% measured %d%%"
    --#ARGUMENTS {0,1,2,3}
    --#STATE OPERATIONAL
    --#SEVERITY WARNING
    ::= { starentTraps 268 }

starThreshClearIPPoolFree NOTIFICATION-TYPE
    OBJECTS { starIPPoolContext, starIPPoolName, starThreshPct, starThreshMeasuredPct }
    STATUS current
    DESCRIPTION
	"The threshold condition is now clear."
    --#SUMMARY "[System] Threshold: IP Pool Address in Free State clear for context %s pool %s threshold %d%% measured %d%%"
    --#ARGUMENTS {0,1,2,3}
    --#STATE OPERATIONAL
    --#SEVERITY INFORMATIONAL
    ::= { starentTraps 269 }

starThreshAAAAcctArchive NOTIFICATION-TYPE
    OBJECTS { starThreshInt, starThreshMeasuredInt }
    STATUS current
    DESCRIPTION
	"The AAA accounting archive size has gone above the configured
	 threshold"
    --#SUMMARY "[System] Threshold: AAA Accounting Archive Size; measured %d threshold %d"
    --#ARGUMENTS {1,0}
    --#STATE OPERATIONAL
    --#SEVERITY WARNING
    ::= { starentTraps 270 }

starThreshClearAAAAcctArchive NOTIFICATION-TYPE
    OBJECTS { starThreshInt, starThreshMeasuredInt }
    STATUS current
    DESCRIPTION
	"The threshold condition is now clear."
    --#SUMMARY "[System] Threshold: AAA Accounting Archive Size CLEAR; measured %d threshold %d"
    --#ARGUMENTS {1,0}
    --#STATE OPERATIONAL
    --#SEVERITY INFORMATIONAL
    ::= { starentTraps 271 }

starThreshPortSpecRxUtil NOTIFICATION-TYPE
    OBJECTS { starPortSlot, starPortNum, starThreshPct, starThreshMeasuredPct }
    STATUS deprecated
    DESCRIPTION
	"The Rx utilization of the port has exceeded the configured threshold value during
	 the current monitoring period.

         Probable Cause: This is a user configurable threshold.

         If the thresholding subsystem is configured to run in an 'alarm' model,
         a starThreshClearPortSpecRxUtil notification will be generated when the measured
	 value falls below the threshold."
    --#SUMMARY "[System] Threshold: port rx utilization threshold on card %d port %d; measured %d threshold %d"
    --#ARGUMENTS {0,1,3,2}
    --#STATE OPERATIONAL
    --#SEVERITY WARNING
    ::= { starentTraps 272 }

starThreshClearPortSpecRxUtil NOTIFICATION-TYPE
    OBJECTS { starPortSlot, starPortNum, starThreshPct, starThreshMeasuredPct }
    STATUS deprecated
    DESCRIPTION
	"The threshold condition is now clear."
    --#SUMMARY "[System] Threshold: port rx utilization threshold CLEAR on card %d port %d; measured %d threshold %d"
    --#ARGUMENTS {0,1,3,2}
    --#STATE OPERATIONAL
    --#SEVERITY INFORMATIONAL
    ::= { starentTraps 273 }

starThreshPortSpecTxUtil NOTIFICATION-TYPE
    OBJECTS { starPortSlot, starPortNum, starThreshPct, starThreshMeasuredPct }
    STATUS deprecated
    DESCRIPTION
	"The Tx utilization of the port has exceeded the configured threshold value during
	 the current monitoring period.

         Probable Cause: This is a user configurable threshold.

         If the thresholding subsystem is configured to run in an 'alarm' model,
         a starThreshClearPortSpecTxUtil notification will be generated when the measured
	 value falls below the threshold."
    --#SUMMARY "[System] Threshold: port tx utilization threshold on card %d port %d; measured %d threshold %d"
    --#ARGUMENTS {0,1,3,2}
    --#STATE OPERATIONAL
    --#SEVERITY WARNING
    ::= { starentTraps 274 }

starThreshClearPortSpecTxUtil NOTIFICATION-TYPE
    OBJECTS { starPortSlot, starPortNum, starThreshPct, starThreshMeasuredPct }
    STATUS deprecated
    DESCRIPTION
	"The threshold condition is now clear."
    --#SUMMARY "[System] Threshold: port tx utilization threshold CLEAR on card %d port %d; measured %d threshold %d"
    --#ARGUMENTS {0,1,3,2}
    --#STATE OPERATIONAL
    --#SEVERITY INFORMATIONAL
    ::= { starentTraps 275 }

starThreshHACallSetupRate NOTIFICATION-TYPE
    OBJECTS { starServiceVpnName, starThreshInt, starThreshMeasuredInt }
    STATUS current
    DESCRIPTION
        "The per-context HA call setup rate (calls per second) has gone above the configured threshold

         Probable Cause: This is a user configurable threshold.

         If the thresholding subsystem is configured to run in an 'alarm' model,
	 a starThreshClearHACallSetupRate notification will be generated when the measured
	 value falls below the threshold."
    --#SUMMARY "[VPN %s] Threshold: HA Per-Context Call Setup Rate; measured %d (cps) threshold %d (cps)"
    --#ARGUMENTS {0,2,1}
    --#STATE OPERATIONAL
    --#SEVERITY WARNING
    ::= { starentTraps 276 }

starThreshClearHACallSetupRate NOTIFICATION-TYPE
    OBJECTS { starServiceVpnName, starThreshInt, starThreshMeasuredInt }
    STATUS current
    DESCRIPTION
        "The threshold condition is now clear."
    --#SUMMARY "[VPN %s] Threshold: HA Per-Context Call Setup Rate CLEAR; measured %d (cps) threshold %d (cps)"
    --#ARGUMENTS {0,2,1}
    --#STATE OPERATIONAL
    --#SEVERITY INFORMATIONAL
    ::= { starentTraps 277 }

starThreshHASvcCallSetupRate NOTIFICATION-TYPE
    OBJECTS { starServiceVpnName, starServiceServName, starThreshInt, starThreshMeasuredInt }
    STATUS current
    DESCRIPTION
        "The per-service HA Call setup rate (calls per second) has gone above the configured threshold

         Probable Cause: This is a user configurable threshold.

         If the thresholding subsystem is configured to run in an 'alarm' model,
	 a starThreshClearHASvcCallSetupRate notification will be generated when the measured
	 value falls below the threshold."
    --#SUMMARY "[Service HA-%s-%s] Threshold: HA Per-Service Call Setup Rate; measured %d (cps) threshold %d (cps)"
    --#ARGUMENTS {0,1,3,2}
    --#STATE OPERATIONAL
    --#SEVERITY WARNING
    ::= { starentTraps 278 }

starThreshClearHASvcCallSetupRate NOTIFICATION-TYPE
    OBJECTS { starServiceVpnName, starServiceServName, starThreshInt, starThreshMeasuredInt }
    STATUS current
    DESCRIPTION
	"The threshold condition is now clear."
    --#SUMMARY "[Service HA-%s-%s] Threshold: HA Per-Service Call Setup Rate CLEAR; measured %d (cps) threshold %d (cps)"
    --#ARGUMENTS {0,1,3,2}
    --#STATE OPERATIONAL
    --#SEVERITY INFORMATIONAL
    ::= { starentTraps 279 }

starThreshHASvcRegReplyError NOTIFICATION-TYPE
    OBJECTS { starServiceVpnName, starServiceServName, starThreshInt, starThreshMeasuredInt }
    STATUS current
    DESCRIPTION
        "The per-service HA Reg Reply Error count has gone above the configured threshold

         Probable Cause: This is a user configurable threshold.

         If the thresholding subsystem is configured to run in an 'alarm' model,
	 a starThreshClearHASvcRegReplyError notification will be generated when the measured
	 value falls below the threshold."
    --#SUMMARY "[Service HA-%s-%s] Threshold: HA Per-Service Reg Reply Error; measured %d threshold %d"
    --#ARGUMENTS {0,1,3,2}
    --#STATE OPERATIONAL
    --#SEVERITY WARNING
    ::= { starentTraps 280 }

starThreshClearHASvcRegReplyError NOTIFICATION-TYPE
    OBJECTS { starServiceVpnName, starServiceServName, starThreshInt, starThreshMeasuredInt }
    STATUS current
    DESCRIPTION
	"The threshold condition is now clear."
    --#SUMMARY "[Service HA-%s-%s] Threshold: HA Per-Service Reg Reply Error CLEAR; measured %d threshold %d"
    --#ARGUMENTS {0,1,3,2}
    --#STATE OPERATIONAL
    --#SEVERITY INFORMATIONAL
    ::= { starentTraps 281 }

starThreshHASvcReregReplyError NOTIFICATION-TYPE
    OBJECTS { starServiceVpnName, starServiceServName, starThreshInt, starThreshMeasuredInt }
    STATUS current
    DESCRIPTION
        "The per-service HA Rereg Reply Error count has gone above the configured threshold

         Probable Cause: This is a user configurable threshold.

         If the thresholding subsystem is configured to run in an 'alarm' model,
	 a starThreshClearHASvcReregReplyError notification will be generated when the measured
	 value falls below the threshold."
    --#SUMMARY "[Service HA-%s-%s] Threshold: HA Per-Service Rereg Reply Error; measured %d threshold %d"
    --#ARGUMENTS {0,1,3,2}
    --#STATE OPERATIONAL
    --#SEVERITY WARNING
    ::= { starentTraps 282 }

starThreshClearHASvcReregReplyError NOTIFICATION-TYPE
    OBJECTS { starServiceVpnName, starServiceServName, starThreshInt, starThreshMeasuredInt }
    STATUS current
    DESCRIPTION
	"The threshold condition is now clear."
    --#SUMMARY "[Service HA-%s-%s] Threshold: HA Per-Service Rereg Reply Error CLEAR; measured %d threshold %d"
    --#ARGUMENTS {0,1,3,2}
    --#STATE OPERATIONAL
    --#SEVERITY INFORMATIONAL
    ::= { starentTraps 283 }

starThreshHASvcDeregReplyError NOTIFICATION-TYPE
    OBJECTS { starServiceVpnName, starServiceServName, starThreshInt, starThreshMeasuredInt }
    STATUS current
    DESCRIPTION
        "The per-service HA Dereg Reply Error count has gone above the configured threshold

         Probable Cause: This is a user configurable threshold.

         If the thresholding subsystem is configured to run in an 'alarm' model,
	 a starThreshClearHASvcDeregReplyError notification will be generated when the measured
	 value falls below the threshold."
    --#SUMMARY "[Service HA-%s-%s] Threshold: HA Per-Service Dereg Reply Error; measured %d threshold %d"
    --#ARGUMENTS {0,1,3,2}
    --#STATE OPERATIONAL
    --#SEVERITY WARNING
    ::= { starentTraps 284 }

starThreshClearHASvcDeregReplyError NOTIFICATION-TYPE
    OBJECTS { starServiceVpnName, starServiceServName, starThreshInt, starThreshMeasuredInt }
    STATUS current
    DESCRIPTION
	"The threshold condition is now clear."
    --#SUMMARY "[Service HA-%s-%s] Threshold: HA Per-Service Dereg Reply Error CLEAR; measured %d threshold %d"
    --#ARGUMENTS {0,1,3,2}
    --#STATE OPERATIONAL
    --#SEVERITY INFORMATIONAL
    ::= { starentTraps 285 }

starThreshFASvcRegReplyError NOTIFICATION-TYPE
    OBJECTS { starServiceVpnName, starServiceServName, starThreshInt, starThreshMeasuredInt }
    STATUS current
    DESCRIPTION
        "The Per-Service FA Reg Reply Error count has gone above the configured threshold

         Probable Cause: This is a user configurable threshold.

         If the thresholding subsystem is configured to run in an 'alarm' model,
	 a starThreshClearFASvcRegReplyError notification will be generated when the measured
	 value falls below the threshold."
    --#SUMMARY "[Service FA-%s-%s] Threshold: FA Per-Service Reg Reply Error; measured %d threshold %d"
    --#ARGUMENTS {0,1,3,2}
    --#STATE OPERATIONAL
    --#SEVERITY WARNING
    ::= { starentTraps 286 }

starThreshClearFASvcRegReplyError NOTIFICATION-TYPE
    OBJECTS { starServiceVpnName, starServiceServName, starThreshInt, starThreshMeasuredInt }
    STATUS current
    DESCRIPTION
	"The threshold condition is now clear."
    --#SUMMARY "[Service FA-%s-%s] Threshold: FA Per-Service Reg Reply Error CLEAR; measured %d threshold %d"
    --#ARGUMENTS {0,1,3,2}
    --#STATE OPERATIONAL
    --#SEVERITY INFORMATIONAL
    ::= { starentTraps 287 }

starThreshPDSNCallSetupRate NOTIFICATION-TYPE
    OBJECTS { starServiceVpnName, starThreshInt, starThreshMeasuredInt }
    STATUS current
    DESCRIPTION
        "The Per-Context PDSN Call Setup Rate (calls per second) has gone above the
	 configured threshold

         Probable Cause: This is a user configurable threshold.

         If the thresholding subsystem is configured to run in an 'alarm' model,
	 a starThreshClearPDSNCallSetupRate notification will be generated when the measured
	 value falls below the threshold."
    --#SUMMARY "[VPN %s] Threshold: PDSN Per-Context Call Setup Rate; measured %d (cps) threshold %d (cps)"
    --#ARGUMENTS {0,2,1}
    --#STATE OPERATIONAL
    --#SEVERITY WARNING
    ::= { starentTraps 288 }

starThreshClearPDSNCallSetupRate NOTIFICATION-TYPE
    OBJECTS { starServiceVpnName, starThreshInt, starThreshMeasuredInt }
    STATUS current
    DESCRIPTION
	"The threshold condition is now clear."
    --#SUMMARY "[VPN %s] Threshold: PDSN Per-Context Call Setup Rate CLEAR; measured %d (cps) threshold %d (cps)"
    --#ARGUMENTS {0,2,1}
    --#STATE OPERATIONAL
    --#SEVERITY INFORMATIONAL
    ::= { starentTraps 289 }

starThreshPDSNSvcCallSetupRate NOTIFICATION-TYPE
    OBJECTS { starServiceVpnName, starServiceServName, starThreshInt, starThreshMeasuredInt }
    STATUS current
    DESCRIPTION
        "The Per-Service PDSN Call Setup Rate (calls per second) has gone above the
	 configured threshold

         Probable Cause: This is a user configurable threshold.

         If the thresholding subsystem is configured to run in an 'alarm' model,
	 a starThreshClearPDSNSvcCallSetupRate notification will be generated when the measured
	 value falls below the threshold."

    --#SUMMARY "[Service PDSN-%s-%s] Threshold: PDSN Per-Service Call Setup Rate; measured %d (cps) threshold %d (cps)"
    --#ARGUMENTS {0,1,3,2}
    --#STATE OPERATIONAL
    --#SEVERITY WARNING
    ::= { starentTraps 290 }

starThreshClearPDSNSvcCallSetupRate NOTIFICATION-TYPE
    OBJECTS { starServiceVpnName, starServiceServName, starThreshInt, starThreshMeasuredInt }
    STATUS current
    DESCRIPTION
	"The threshold condition is now clear."
    --#SUMMARY "[Service PDSN-%s-%s] Threshold: PDSN Per-Service Call Setup Rate CLEAR; measured %d (cps) threshold %d (cps)"
    --#ARGUMENTS {0,1,3,2}
    --#STATE OPERATIONAL
    --#SEVERITY INFORMATIONAL
    ::= { starentTraps 291 }

starThreshPDSNSvcA11RRPFailure NOTIFICATION-TYPE
    OBJECTS { starServiceVpnName, starServiceServName, starThreshInt, starThreshMeasuredInt }
    STATUS current
    DESCRIPTION
        "The Per-Service PDSN A11 RRP Failure count has gone above the configured threshold

         Probable Cause: This is a user configurable threshold.

         If the thresholding subsystem is configured to run in an 'alarm' model,
	 a starThreshClearPDSNSvcA11RRPFailure notification will be generated when the measured
	 value falls below the threshold."
    --#SUMMARY "[Service PDSN-%s-%s] Threshold: PDSN Per-Service A11 RRP Failure; measured %d threshold %d"
    --#ARGUMENTS {0,1,3,2}
    --#STATE OPERATIONAL
    --#SEVERITY WARNING
    ::= { starentTraps 292 }

starThreshClearPDSNSvcA11RRPFailure NOTIFICATION-TYPE
    OBJECTS { starServiceVpnName, starServiceServName, starThreshInt, starThreshMeasuredInt }
    STATUS current
    DESCRIPTION
	"The threshold condition is now clear."
    --#SUMMARY "[Service PDSN-%s-%s] Threshold: PDSN Per-Service A11 RRP Failure CLEAR; measured %d threshold %d"
    --#ARGUMENTS {0,1,3,2}
    --#STATE OPERATIONAL
    --#SEVERITY INFORMATIONAL
    ::= { starentTraps 293 }

starThreshPDSNSvcA11RRQMsgDiscard NOTIFICATION-TYPE
    OBJECTS { starServiceVpnName, starServiceServName, starThreshInt, starThreshMeasuredInt }
    STATUS current
    DESCRIPTION
        "The Per-Service PDSN A11 RRQ Msg Discard count has gone above the configured threshold

         Probable Cause: This is a user configurable threshold.

         If the thresholding subsystem is configured to run in an 'alarm' model,
	 a starThreshClearPDSNSvcA11RRQMsgDiscard notification will be generated when the measured
	 value falls below the threshold."
    --#SUMMARY "[Service PDSN-%s-%s] Threshold: PDSN Per-Service A11 RRQ Msg Discard; measured %d threshold %d"
    --#ARGUMENTS {0,1,3,2}
    --#STATE OPERATIONAL
    --#SEVERITY WARNING
    ::= { starentTraps 294 }

starThreshClearPDSNSvcA11RRQMsgDiscard NOTIFICATION-TYPE
    OBJECTS { starServiceVpnName, starServiceServName, starThreshInt, starThreshMeasuredInt }
    STATUS current
    DESCRIPTION
	"The threshold condition is now clear."
    --#SUMMARY "[Service PDSN-%s-%s] Threshold: PDSN Per-Service A11 RRQ Msg Discard CLEAR; measured %d threshold %d"
    --#ARGUMENTS {0,1,3,2}
    --#STATE OPERATIONAL
    --#SEVERITY INFORMATIONAL
    ::= { starentTraps 295 }

starThreshPDSNSvcA11RACMsgDiscard NOTIFICATION-TYPE
    OBJECTS { starServiceVpnName, starServiceServName, starThreshInt, starThreshMeasuredInt }
    STATUS current
    DESCRIPTION
        "The Per-Service PDSN A11 RAC Msg Discard count has gone above the configured threshold

         Probable Cause: This is a user configurable threshold.

         If the thresholding subsystem is configured to run in an 'alarm' model,
	 a starThreshClearPDSNSvcA11RACMsgDiscard notification will be generated when the measured
	 value falls below the threshold."
    --#SUMMARY "[Service PDSN-%s-%s] Threshold: PDSN Per-Service A11 RAC Msg Discard; measured %d threshold %d"
    --#ARGUMENTS {0,1,3,2}
    --#STATE OPERATIONAL
    --#SEVERITY WARNING
    ::= { starentTraps 296 }

starThreshClearPDSNSvcA11RACMsgDiscard NOTIFICATION-TYPE
    OBJECTS { starServiceVpnName, starServiceServName, starThreshInt, starThreshMeasuredInt }
    STATUS current
    DESCRIPTION
	"The threshold condition is now clear."
    --#SUMMARY "[Service PDSN-%s-%s] Threshold: PDSN Per-Service A11 RAC Msg Discard CLEAR; measured %d threshold %d"
    --#ARGUMENTS {0,1,3,2}
    --#STATE OPERATIONAL
    --#SEVERITY INFORMATIONAL
    ::= { starentTraps 297 }

starThreshPDSNSvcA11PPPSendDiscard NOTIFICATION-TYPE
    OBJECTS { starServiceVpnName, starServiceServName, starThreshInt, starThreshMeasuredInt }
    STATUS current
    DESCRIPTION
        "The Per-Service PDSN A11 PPP Send Discard count has gone above the configured threshold

         Probable Cause: This is a user configurable threshold.

         If the thresholding subsystem is configured to run in an 'alarm' model,
	 a starThreshClearPDSNSvcA11PPPSendDiscard notification will be generated when the measured
	 value falls below the threshold."
    --#SUMMARY "[Service PDSN-%s-%s] Threshold: PDSN Per-Service All PPP Send Discard; measured %d threshold %d"
    --#ARGUMENTS {0,1,3,2}
    --#STATE OPERATIONAL
    --#SEVERITY WARNING
    ::= { starentTraps 298 }

starThreshClearPDSNSvcA11PPPSendDiscard NOTIFICATION-TYPE
    OBJECTS { starServiceVpnName, starServiceServName, starThreshInt, starThreshMeasuredInt }
    STATUS current
    DESCRIPTION
	"The threshold condition is now clear."
    --#SUMMARY "[Service PDSN-%s-%s] Threshold: PDSN Per-Service A11 PPP Send Discard CLEAR; measured %d threshold %d"
    --#ARGUMENTS {0,1,3,2}
    --#STATE OPERATIONAL
    --#SEVERITY INFORMATIONAL
    ::= { starentTraps 299 }

starThreshAAAMgrQueue NOTIFICATION-TYPE
    OBJECTS { starTaskInstance, starThreshPct, starThreshMeasuredPct }
    STATUS current
    DESCRIPTION
        "The Per-AAA Manager internal request queue usage has gone above the configured threshold

         Probable Cause: This is a user configurable threshold.

         If the thresholding subsystem is configured to run in an 'alarm' model,
	 a starThreshClearAAAMgrQueue will be generated when the measured
	 value falls below the threshold."
    --#SUMMARY "[System] Threshold: AAA Mgr internal request queue for AAA Manager %d threshold %d%% measured %d%%"
    --#ARGUMENTS {0,1,2}
    --#STATE OPERATIONAL
    --#SEVERITY WARNING
    ::= { starentTraps 300 }

starThreshClearAAAMgrQueue NOTIFICATION-TYPE
    OBJECTS { starTaskInstance, starThreshPct, starThreshMeasuredPct }
    STATUS current
    DESCRIPTION
	"The threshold condition is now clear."
    --#SUMMARY "[System] Threshold: AAA Mgr internal request queue clear for AAA Manager %d threshold %d%% measured %d%%"
    --#ARGUMENTS {0,1,2}
    --#STATE OPERATIONAL
    --#SEVERITY INFORMATIONAL
    ::= { starentTraps 301 }

starThreshAAAAcctArchiveQueue1 NOTIFICATION-TYPE
    OBJECTS { starTaskInstance, starThreshPct, starThreshMeasuredPct }
    STATUS current
    DESCRIPTION
        "The Per-Sessmgr Archive queue  usage is above the configured threshold percentage

         Probable Cause: This is a user configurable threshold.

         If the thresholding subsystem is configured to run in an 'alarm' model,
         a starThreshClearAAAAcctArchiveQueue-1 notification will be generated when the measured
         value falls below the threshold."
    --#SUMMARY "{System] Threshold: Sessmgr Archive Queue for SessMgr instance %d threshold %d%% measured %d%%"
    --#ARGUMENTS {0,1,2}
    --#STATE OPERATIONAL
    --#SEVERITY WARNING
    ::= { starentTraps 505 }

starThreshClearAAAAcctArchiveQueue1 NOTIFICATION-TYPE
    OBJECTS { starTaskInstance, starThreshPct, starThreshMeasuredPct }
    STATUS current
    DESCRIPTION
        "The threshold condition is now clear."
    --#SUMMARY "[System] Threshold:Sessmgr Archive Queue clear for SessMgr instance %d threshold %d%% measured %d%%"
    --#ARGUMENTS {0,1,2}
    --#STATE OPERATIONAL
    --#SEVERITY INFORMATIONAL
    ::= { starentTraps 506 }

starThreshAAAAcctArchiveQueue2 NOTIFICATION-TYPE
    OBJECTS { starTaskInstance, starThreshPct, starThreshMeasuredPct }
    STATUS current
    DESCRIPTION
        "The Sessmgr  Archive queue  usage is above the configured threshold percentage

         Probable Cause: This is a user configurable threshold.

         If the thresholding subsystem is configured to run in an 'alarm' model,
         a starThreshClearAAAAcctArchiveQueue-2 notification will be generated when the measured
         value falls below the threshold."
    --#SUMMARY "[System] Threshold: Sessmgr Archive Queue for Sessmgr instance %d threshold %d%% measured %d%%"
    --#ARGUMENTS {0,1,2}
    --#STATE OPERATIONAL
    --#SEVERITY WARNING
    ::= { starentTraps 507 }

starThreshClearAAAAcctArchiveQueue2 NOTIFICATION-TYPE
    OBJECTS { starTaskInstance, starThreshPct, starThreshMeasuredPct }
    STATUS current
    DESCRIPTION
        "The threshold condition is now clear."
    --#SUMMARY "[System] Threshold: Sessmgr Archive Queue clear for Sessmgr instance %d threshold %d%% measured %d%%"
    --#ARGUMENTS {0,1,2}
    --#STATE OPERATIONAL
    --#SEVERITY INFORMATIONAL
    ::= { starentTraps 508 }

starThreshAAAAcctArchiveQueue3 NOTIFICATION-TYPE
    OBJECTS { starTaskInstance, starThreshPct, starThreshMeasuredPct }
    STATUS current
    DESCRIPTION
        "The Sessmgr Archive queue  usage is above the configured threshold percentage

         Probable Cause: This is a user configurable threshold.

         If the thresholding subsystem is configured to run in an 'alarm' model,
         a starThreshClearAAAAcctArchiveQueue-3 notification will be generated when the measured
         value falls below the threshold."
    --#SUMMARY "[System] Threshold: Sessmgr Archive Queue for Sessmgr instance %d threshold %d%% measured %d%%"
    --#ARGUMENTS {0,1,2}
    --#STATE OPERATIONAL
    --#SEVERITY WARNING
    ::= { starentTraps 509 }

starThreshClearAAAAcctArchiveQueue3 NOTIFICATION-TYPE
    OBJECTS { starTaskInstance, starThreshPct, starThreshMeasuredPct }
    STATUS current
    DESCRIPTION
        "The threshold condition is now clear."
    --#SUMMARY "[System] Threshold: Sessmgr Archive Queue Clear for Sessmgr instance %d threshold %d%% measured %d%%"
    --#ARGUMENTS {0,1,2}
    --#STATE OPERATIONAL
    --#SEVERITY INFORMATIONAL
    ::= { starentTraps 510 }

starThreshDnsLookupSrvFailure NOTIFICATION-TYPE
    OBJECTS { starContextName, starThreshInt, starThreshMeasuredInt }
    STATUS current
    DESCRIPTION
        "The Total number of DNS SRV lookup failures  is above the configured threshold value.

          Probable Cause: This is a user configurable threshold.

          If the thresholding subsystem is configured to run in an 'alarm' model,
          a starThreshClearSrvLookupSrvFailure notification will be generated when the measured
          value falls below the threshold."
    --#SUMMARY "[System] Threshold: DNS SRV lookup failure; context %s measured %d threshold %d"
    --#ARGUMENTS {0,2,1}
    --#STATE OPERATIONAL
    --#SEVERITY WARNING
    ::= { starentTraps 511 }
   
starThreshClearDnsLookupSrvFailure NOTIFICATION-TYPE
    OBJECTS { starContextName, starThreshInt, starThreshMeasuredInt }
    STATUS current
    DESCRIPTION
        "The threshold condition is now clear."
    --#SUMMARY "[System] Threshold: DNS SRV lookup failure CLEAR; context %s measured %d threshold %d"
    --#ARGUMENTS {0,2,1}
    --#STATE OPERATIONAL
    --#SEVERITY INFORMATIONAL
    ::= { starentTraps 512 }


starThreshCPUOrbsWarn NOTIFICATION-TYPE
    OBJECTS { starCPUSlot, starCPUNumber, starThreshPct, starThreshMeasuredPct }
    STATUS current
    DESCRIPTION
	"The ORBs task has exceeding the CPU usage configured as a warning"
    --#SUMMARY "[System] Threshold: ORBs process CPU warning on card %d CPU %d threshold %d%% measured %d%%"
    --#ARGUMENTS {0,1,2,3}
    --#STATE OPERATIONAL
    --#SEVERITY WARNING
    ::= { starentTraps 302 }

starThreshClearCPUOrbsWarn NOTIFICATION-TYPE
    OBJECTS { starCPUSlot, starCPUNumber, starThreshPct, starThreshMeasuredPct }
    STATUS current
    DESCRIPTION
	"The threshold condition is now clear"
    --#SUMMARY "[System] Threshold: ORBs process CPU warning clear on card %d CPU %d threshold %d%% measured %d%%"
    --#ARGUMENTS {0,1,2,3}
    --#STATE OPERATIONAL
    --#SEVERITY INFORMATIONAL
    ::= { starentTraps 303 }

starThreshCPUOrbsCritical NOTIFICATION-TYPE
    OBJECTS { starCPUSlot, starCPUNumber, starThreshPct, starThreshMeasuredPct }
    STATUS current
    DESCRIPTION
	"The ORBs task has exceeded the CPU usage configured as a critical error"
    --#SUMMARY "[System] Threshold: ORBs process CPU critical on card %d CPU %d threshold %d%% measured %d%%"
    --#ARGUMENTS {0,1,2,3}
    --#STATE OPERATIONAL
    --#SEVERITY CRITICAL
    ::= { starentTraps 304 }

starThreshClearCPUOrbsCritical NOTIFICATION-TYPE
    OBJECTS { starCPUSlot, starCPUNumber, starThreshPct, starThreshMeasuredPct }
    STATUS current
    DESCRIPTION
	"The threshold condition is now clear"
    --#SUMMARY "[System] Threshold: ORBs process CPU critical clear on card %d CPU %d threshold %d%% measured %d%%"
    --#ARGUMENTS {0,1,2,3}
    --#STATE OPERATIONAL
    --#SEVERITY INFORMATIONAL
    ::= { starentTraps 305 }

starThreshRPSetupFailRate NOTIFICATION-TYPE
    OBJECTS { starThreshPct, starThreshMeasuredPct }
    STATUS current
    DESCRIPTION
	"The RP call setup failure rate has exceeded the configured threshold"
    --#SUMMARY "[System] Threshold: RP Setup failure rate for threshold %d%% measured %d%%"
    --#ARGUMENTS {0,1}
    --#STATE OPERATIONAL
    --#SEVERITY WARNING
    ::= { starentTraps 306 }

starThreshClearRPSetupFailRate NOTIFICATION-TYPE
    OBJECTS { starThreshPct, starThreshMeasuredPct }
    STATUS current
    DESCRIPTION
	"The threshold condition is now clear"
    --#SUMMARY "[System] Threshold: RP Setup failure rate clear for threshold %d%% measured %d%%"
    --#ARGUMENTS {0,1}
    --#STATE OPERATIONAL
    --#SEVERITY INFORMATIONAL
    ::= { starentTraps 307 }

starThreshPPPSetupFailRate NOTIFICATION-TYPE
    OBJECTS { starThreshPct, starThreshMeasuredPct }
    STATUS current
    DESCRIPTION
	"The PPP call setup failure rate has exceeded the configured threshold"
    --#SUMMARY "[System] Threshold: PPP Setup failure rate for threshold %d%% measured %d%%"
    --#ARGUMENTS {0,1}
    --#STATE OPERATIONAL
    --#SEVERITY WARNING
    ::= { starentTraps 308 }

starThreshClearPPPSetupFailRate NOTIFICATION-TYPE
    OBJECTS { starThreshPct, starThreshMeasuredPct }
    STATUS current
    DESCRIPTION
	"The threshold condition is now clear"
    --#SUMMARY "[System] Threshold: PPP Setup failure rate clear for threshold %d%% measured %d%%"
    --#ARGUMENTS {0,1}
    --#STATE OPERATIONAL
    --#SEVERITY INFORMATIONAL
    ::= { starentTraps 309 }

starThreshStorageUtilization NOTIFICATION-TYPE
    OBJECTS { starStorageSlot, starStorageName, starThreshPct, starThreshMeasuredPct }
    STATUS current
    DESCRIPTION
	"The utilization of a mass storage device has exeeded the configured threshold"
    --#SUMMARY "[System] Threshold: Mass storage device usage on card %d storage device %s threshold %d%% measured %d%%"
    --#ARGUMENTS {0,1,2,3}
    --#STATE OPERATIONAL
    --#SEVERITY WARNING
    ::= { starentTraps 310 }

starThreshClearStorageUtilization NOTIFICATION-TYPE
    OBJECTS { starStorageSlot, starStorageName, starThreshPct, starThreshMeasuredPct }
    STATUS current
    DESCRIPTION
	"The threshold condition is now clear"
    --#SUMMARY "[System] Threshold: Mass storage device usage clear on card %d storage device %s threshold %d%% measured %d%%"
    --#ARGUMENTS {0,1,2,3}
    --#STATE OPERATIONAL
    --#SEVERITY INFORMATIONAL
    ::= { starentTraps 311 }

starThreshDCCAProtocolErrors NOTIFICATION-TYPE
    OBJECTS { starThreshInt, starThreshMeasuredInt }
    STATUS current
    DESCRIPTION
	"The number of DCCA Protocol Errors has exceeded the configured threshold"
    --#SUMMARY "[System] Threshold: DCCAProtocol Errors; %d measured threshold %d"
    --#ARGUMENTS {1,0}
    --#STATE OPERATIONAL
    --#SEVERITY WARNING
    ::= { starentTraps 312 }

starThreshClearDCCAProtocolErrors NOTIFICATION-TYPE
    OBJECTS { starThreshInt, starThreshMeasuredInt }
    STATUS current
    DESCRIPTION
	"The threshold condition is now clear"
    --#SUMMARY "[System] Threshold: DCCA Protocol Errors CLEAR; %d measured threshold %d"
    --#ARGUMENTS {1,0}
    --#STATE OPERATIONAL
    --#SEVERITY INFORMATIONAL
    ::= { starentTraps 313 }

starThreshDCCABadAnswers NOTIFICATION-TYPE
    OBJECTS { starThreshInt, starThreshMeasuredInt }
    STATUS current
    DESCRIPTION
	"The number of DCCA BadAnswers has exceeded the configured threshold"
    --#SUMMARY "[System] Threshold: DCCA BadAnswers; %d measured threshold %d"
    --#ARGUMENTS {1,0}
    --#STATE OPERATIONAL
    --#SEVERITY WARNING
    ::= { starentTraps 314 }

starThreshClearDCCABadAnswers NOTIFICATION-TYPE
    OBJECTS { starThreshInt, starThreshMeasuredInt }
    STATUS current
    DESCRIPTION
	"The threshold condition is now clear"
    --#SUMMARY "[System] Threshold: DCCA BadAnswers CLEAR; %d measured threshold %d"
    --#ARGUMENTS {1,0}
    --#STATE OPERATIONAL
    --#SEVERITY INFORMATIONAL
    ::= { starentTraps 315 }

starThreshDCCAUnknownRatingGroup NOTIFICATION-TYPE
    OBJECTS { starThreshInt, starThreshMeasuredInt }
    STATUS current
    DESCRIPTION
	"The number of DCCA UnknownRatingGroup has exceeded the configured threshold"
    --#SUMMARY "[System] Threshold: DCCA UnknownRatingGroup; %d measured threshold %d"
    --#ARGUMENTS {1,0}
    --#STATE OPERATIONAL
    --#SEVERITY WARNING
    ::= { starentTraps 316 }

starThreshClearDCCAUnknownRatingGroup NOTIFICATION-TYPE
    OBJECTS { starThreshInt, starThreshMeasuredInt }
    STATUS current
    DESCRIPTION
	"The threshold condition is now clear"
    --#SUMMARY "[System] Threshold: DCCA UnknownRatingGroup CLEAR; %d measured threshold %d"
    --#ARGUMENTS {1,0}
    --#STATE OPERATIONAL
    --#SEVERITY INFORMATIONAL
    ::= { starentTraps 317 }

starThreshDCCARatingFailed NOTIFICATION-TYPE
    OBJECTS { starThreshInt, starThreshMeasuredInt }
    STATUS current
    DESCRIPTION
	"The number of DCCA RatingFailed has exceeded the configured threshold"
    --#SUMMARY "[System] Threshold: DCCA RatingFailed; %d measured threshold %d"
    --#ARGUMENTS {1,0}
    --#STATE OPERATIONAL
    --#SEVERITY WARNING
    ::= { starentTraps 318 }

starThreshClearDCCARatingFailed NOTIFICATION-TYPE
    OBJECTS { starThreshInt, starThreshMeasuredInt }
    STATUS current
    DESCRIPTION
	"The threshold condition is now clear"
    --#SUMMARY "[System] Threshold: DCCA RatingFailed CLEAR; %d measured threshold %d"
    --#ARGUMENTS {1,0}
    --#STATE OPERATIONAL
    --#SEVERITY INFORMATIONAL
    ::= { starentTraps 319 }

starThreshIPSECIKERequests NOTIFICATION-TYPE
    OBJECTS { starServiceVpnName, starServiceServName, starThreshInt, starThreshMeasuredInt }
    STATUS current
    DESCRIPTION
	"The number of IPSEC IKE requests seen for this HA service has exceeded the configured
	 threshold.

	 Probable Cause: This is a user configurable threshold.

         If the thresholding subsystem is configured to run in an 'alarm' model,
	 a starThreshClearIPSECIKERequests notification will be generated when the measured
	 value falls below the threshold."
    --#SUMMARY "[Service HA-%s-%s] Threshold: HA Per-Service IPSEC IKE Requests; measured %d threshold %d"
    --#ARGUMENTS {0,1,3,2}
    --#STATE OPERATIONAL
    --#SEVERITY WARNING
    ::= { starentTraps 320 }

starThreshClearIPSECIKERequests NOTIFICATION-TYPE
    OBJECTS { starServiceVpnName, starServiceServName, starThreshInt, starThreshMeasuredInt }
    STATUS current
    DESCRIPTION
	"The threshold condition is now clear"
    --#SUMMARY "Service HA-%s-%s] Threshold: HA Per-Service IPSEC IKE Requests CLEAR; measured %d threshold %d"
    --#ARGUMENTS {0,1,3,2}
    --#STATE OPERATIONAL
    --#SEVERITY INFORMATIONAL
    ::= { starentTraps 321 }

starThreshIPSECIKEFailures NOTIFICATION-TYPE
    OBJECTS { starServiceVpnName, starServiceServName, starThreshInt, starThreshMeasuredInt }
    STATUS current
    DESCRIPTION
	"The number of IPSEC IKE failures seen for this HA service has exceeded the configured
	 threshold.

	 Probable Cause: This is a user configurable threshold.

         If the thresholding subsystem is configured to run in an 'alarm' model,
	 a starThreshClearIPSECIKEFailures notification will be generated when the measured
	 value falls below the threshold."
    --#SUMMARY "[Service HA-%s-%s] Threshold: HA Per-Service IPSEC IKE Failured; measured %d threshold %d"
    --#ARGUMENTS {0,1,3,2}
    --#STATE OPERATIONAL
    --#SEVERITY WARNING
    ::= { starentTraps 322 }

starThreshClearIPSECIKEFailures NOTIFICATION-TYPE
    OBJECTS { starServiceVpnName, starServiceServName, starThreshInt, starThreshMeasuredInt }
    STATUS current
    DESCRIPTION
	"The threshold condition is now clear"
    --#SUMMARY "[Service HA-%s-%s] Threshold: HA Per-Service IPSEC IKE Failures CLEAR; measured %d threshold %d"
    --#ARGUMENTS {0,1,3,2}
    --#STATE OPERATIONAL
    --#SEVERITY INFORMATIONAL
    ::= { starentTraps 323 }

starThreshIPSECIKEFailRate NOTIFICATION-TYPE
    OBJECTS { starServiceVpnName, starServiceServName, starThreshPct, starThreshMeasuredPct }
    STATUS current
    DESCRIPTION
	"The rate of IPSEC IKE failures (as a percentage of total requests) seen for this HA service
	 has exceeded the configured threshold.

	 Probable Cause: This is a user configurable threshold.

         If the thresholding subsystem is configured to run in an 'alarm' model,
	 a starThreshClearIPSECIKEFailRate notification will be generated when the measured
	 value falls below the threshold."
    --#SUMMARY "[Service] Threshold: HA Per-Service IPSEC IKE Failure Rate for context %s service %s threshold %d%% measured %d%%"
    --#ARGUMENTS {0,1,2,3}
    --#STATE OPERATIONAL
    --#SEVERITY WARNING
    ::= { starentTraps 324 }

starThreshClearIPSECIKEFailRate NOTIFICATION-TYPE
    OBJECTS { starServiceVpnName, starServiceServName, starThreshPct, starThreshMeasuredPct }
    STATUS current
    DESCRIPTION
	"The threshold condition is now clear"
    --#SUMMARY "[Service] Threshold: HA Per-Service IPSEC IKE Failure Rate clear for context %s service %s threshold %d%% measured %d%%"
    --#ARGUMENTS {0,1,2,3}
    --#STATE OPERATIONAL
    --#SEVERITY INFORMATIONAL
    ::= { starentTraps 325 }

starThreshIPSECTunSetup NOTIFICATION-TYPE
    OBJECTS { starServiceVpnName, starServiceServName, starThreshInt, starThreshMeasuredInt }
    STATUS current
    DESCRIPTION
	"The number of IPSEC tunnels setup over the last measurement period for this HA service
	 has exceeded the configured threshold.

	 Probable Cause: This is a user configurable threshold.

         If the thresholding subsystem is configured to run in an 'alarm' model,
	 a starThreshClearIPSECTunSetup notification will be generated when the measured
	 value falls below the threshold."
    --#SUMMARY "[Service HA-%s-%s] Threshold: HA Per-Service IPSEC Tunnels Setup; measured %d threshold %d"
    --#ARGUMENTS {0,1,3,2}
    --#STATE OPERATIONAL
    --#SEVERITY WARNING
    ::= { starentTraps 326 }

starThreshClearIPSECTunSetup NOTIFICATION-TYPE
    OBJECTS { starServiceVpnName, starServiceServName, starThreshInt, starThreshMeasuredInt }
    STATUS current
    DESCRIPTION
	"The threshold condition is now clear"
    --#SUMMARY "[Service HA-%s-%s] Threshold: HA Per-Service IPSEC Tunnels Setup CLEAR; measured %d threshold %d"
    --#ARGUMENTS {0,1,3,2}
    --#STATE OPERATIONAL
    --#SEVERITY INFORMATIONAL
    ::= { starentTraps 327 }

starThreshIPSECTunEstabl NOTIFICATION-TYPE
    OBJECTS { starServiceVpnName, starServiceServName, starThreshInt, starThreshMeasuredInt }
    STATUS current
    DESCRIPTION
	"The current number of IPSEC tunnels established for this HA service
	 has exceeded the configured threshold.

	 Probable Cause: This is a user configurable threshold.

         If the thresholding subsystem is configured to run in an 'alarm' model,
	 a starThreshClearIPSECTunEstabl notification will be generated when the measured
	 value falls below the threshold."
    --#SUMMARY "[Service HA-%s-%s] Threshold: HA Per-Service IPSEC Tunnels Established; measured %d threshold %d"
    --#ARGUMENTS {0,1,3,2}
    --#STATE OPERATIONAL
    --#SEVERITY WARNING
    ::= { starentTraps 328 }

starThreshClearIPSECTunEstabl NOTIFICATION-TYPE
    OBJECTS { starServiceVpnName, starServiceServName, starThreshInt, starThreshMeasuredInt }
    STATUS current
    DESCRIPTION
	"The threshold condition is now clear"
    --#SUMMARY "[Service HA-%s-%s] Threshold: HA Per-Service IPSEC Tunnels Established CLEAR; measured %d threshold %d"
    --#ARGUMENTS {0,1,3,2}
    --#STATE OPERATIONAL
    --#SEVERITY INFORMATIONAL
    ::= { starentTraps 329 }

starThreshIPSECCallReqRej NOTIFICATION-TYPE
    OBJECTS { starServiceVpnName, starServiceServName, starThreshInt, starThreshMeasuredInt }
    STATUS current
    DESCRIPTION
	"The number of IPSEC Rejected Call Requests
	 has exceeded the configured threshold.

	 Probable Cause: This is a user configurable threshold.  Reject Call Requests indicate
	 that an IPSEC Manager has reached its maximum allowable number of IPSEC tunnels.

         If the thresholding subsystem is configured to run in an 'alarm' model,
	 a starThreshClearIPSECTunnelsTotal notification will be generated when the measured
	 value falls below the threshold."
    --#SUMMARY "[Service HA-%s-%s] Threshold: HA Per-Service IPSEC Reject Call Requests CLEAR; measured %d threshold %d"
    --#ARGUMENTS {0,1,3,2}
    --#STATE OPERATIONAL
    --#SEVERITY WARNING
    ::= { starentTraps 330 }

starThreshClearIPSECCallReqRej NOTIFICATION-TYPE
    OBJECTS { starServiceVpnName, starServiceServName, starThreshInt, starThreshMeasuredInt }
    STATUS current
    DESCRIPTION
	"The threshold condition is now clear"
    --#SUMMARY "[Service HA-%s-%s] Threshold: HA Per-Service IPSEC Rejected Call Requests CLEAR; measured %d threshold %d"
    --#ARGUMENTS {0,1,3,2}
    --#STATE OPERATIONAL
    --#SEVERITY INFORMATIONAL
    ::= { starentTraps 331 }

starThreshCSCFSvcRouteFailure NOTIFICATION-TYPE
    OBJECTS { starServiceVpnName, starServiceServName, starThreshInt, starThreshMeasuredInt }
    STATUS current
    DESCRIPTION
        "The Per-Service CSCF Route failure count has gone above the configured threshold

         Probable Cause: This is a user configurable threshold.

         If the thresholding subsystem is configured to run in an 'alarm' model,
	 a starThreshClearCSCFSvcRouteFailure notification will be generated when the measured
	 value falls below the threshold."
    --#SUMMARY "[Service CSCF-%s-%s] Threshold: CSCF Per-Service Route failure; measured %d threshold %d"
    --#ARGUMENTS {0,1,3,2}
    --#STATE OPERATIONAL
    --#SEVERITY WARNING
    ::= { starentTraps 332 }

starThreshClearCSCFSvcRouteFailure NOTIFICATION-TYPE
    OBJECTS { starServiceVpnName, starServiceServName, starThreshInt, starThreshMeasuredInt }
    STATUS current
    DESCRIPTION
	"The threshold condition is now clear."
    --#SUMMARY "[Service CSCF-%s-%s] Threshold: CSCF Per-Service Route failure CLEAR; measured %d threshold %d"
    --#ARGUMENTS {0,1,3,2}
    --#STATE OPERATIONAL
    --#SEVERITY INFORMATIONAL
    ::= { starentTraps 333 }

starThreshContFiltRating NOTIFICATION-TYPE
    OBJECTS { starThreshInt, starThreshMeasuredInt }
    STATUS  current
    DESCRIPTION
	"The number of Content Filtering Rating operations performed has gone above
	 the configured threshold.

         Probable Cause: This is a user configurable threshold.

         If the thresholding subsystem is configured to run in an 'alarm' model,
	 a starThreshClearContFiltRating notification will be generated when the measured
	 value falls below the threshold."
    --#SUMMARY "[System] Threshold: Content Filtering 'ratings'; measured %d threshold %d"
    --#ARGUMENTS {1,0}
    --#STATE OPERATIONAL
    --#SEVERITY WARNING
    ::= { starentTraps 334 }

starThreshClearContFiltRating NOTIFICATION-TYPE
    OBJECTS { starThreshInt, starThreshMeasuredInt }
    STATUS current
    DESCRIPTION
	"The threshold condition is now clear."
    --#SUMMARY "[System] Threshold: Content Filtering 'ratings' CLEAR; measured %d threshold %d"
    --#ARGUMENTS {1,0}
    --#STATE OPERATIONAL
    --#SEVERITY INFORMATIONAL
    ::= { starentTraps 335 }

starThreshContFiltBlock NOTIFICATION-TYPE
    OBJECTS { starThreshInt, starThreshMeasuredInt }
    STATUS  current
    DESCRIPTION
	"The number of Content Filtering Block operations performed has gone above
	 the configured threshold.

         Probable Cause: This is a user configurable threshold.

         If the thresholding subsystem is configured to run in an 'alarm' model,
	 a starThreshClearContFiltBlock notification will be generated when the measured
	 value falls below the threshold."
    --#SUMMARY "[System] Threshold: Content Filtering 'blocks'; measured %d threshold %d"
    --#ARGUMENTS {1,0}
    --#STATE OPERATIONAL
    --#SEVERITY WARNING
    ::= { starentTraps 336 }

starThreshClearContFiltBlock NOTIFICATION-TYPE
    OBJECTS { starThreshInt, starThreshMeasuredInt }
    STATUS current
    DESCRIPTION
	"The threshold condition is now clear."
    --#SUMMARY "[System] Threshold: Content Filtering 'blocks' CLEAR; measured %d threshold %d"
    --#ARGUMENTS {1,0}
    --#STATE OPERATIONAL
    --#SEVERITY INFORMATIONAL
    ::= { starentTraps 337 }

starThreshCDRFileSpace NOTIFICATION-TYPE
    OBJECTS { starThreshPct, starThreshMeasuredPct }
    STATUS current
    DESCRIPTION
        "The CDR file space usage is above the configured threshold percentage

         Probable Cause: This is a user configurable threshold.

         If the thresholding subsystem is configured to run in an 'alarm' model,
         a starThreshClearCDRFileSpaceOverLimit notification will be generated when the measured
         value falls below the threshold."
    --#SUMMARY "Threshold: CDR File space for threshold %d%% measured %d%%"
    --#ARGUMENTS {0,1}
    --#STATE OPERATIONAL
    --#SEVERITY WARNING
    ::= { starentTraps 338 }

starThreshClearCDRFileSpace NOTIFICATION-TYPE
    OBJECTS { starThreshPct, starThreshMeasuredPct }
    STATUS current
    DESCRIPTION
        "The threshold condition is now clear."
    --#SUMMARY "Threshold: CDR File space clear for threshold %d%% measured %d%%"
    --#ARGUMENTS {0,1}
    --#STATE OPERATIONAL
    --#SEVERITY INFORMATIONAL
    ::= { starentTraps 339 }

starThreshEDRFileSpace NOTIFICATION-TYPE
    OBJECTS { starThreshPct, starThreshMeasuredPct }
    STATUS current
    DESCRIPTION
        "The EDR file space usage is above the configured threshold percentage

         Probable Cause: This is a user configurable threshold.

         If the thresholding subsystem is configured to run in an 'alarm' model,
         a starThreshClearEDRFileSpaceOverLimit notification will be generated when the measured
         value falls below the threshold."
    --#SUMMARY "Threshold: EDR File space for threshold %d%% measured %d%%"
    --#ARGUMENTS {0,1}
    --#STATE OPERATIONAL
    --#SEVERITY WARNING
    ::= { starentTraps 340 }

starThreshClearEDRFileSpace NOTIFICATION-TYPE
    OBJECTS { starThreshPct, starThreshMeasuredPct }
    STATUS current
    DESCRIPTION
        "The threshold condition is now clear."
    --#SUMMARY "Threshold: EDR File space clear for threshold %d%% measured %d%%"
    --#ARGUMENTS {0,1}
    --#STATE OPERATIONAL
    --#SEVERITY INFORMATIONAL
    ::= { starentTraps 341 }

starThreshPDIFCurrSess NOTIFICATION-TYPE
    OBJECTS { starThreshInt, starThreshMeasuredInt }
    STATUS current
    DESCRIPTION
         "The chassis-wide count of current PDIF sessions has gone above the configured threshold

          Probable Cause: This is a user configurable threshold.

          If the thresholding subsystem is configured to run in an 'alarm' model,
 	 a starThreshClearPDIFCurrSess notification will be generated when the measured
 	 value falls below the threshold."
    --#SUMMARY "[System] Threshold: PDIF Current Sessions; measured %d threshold %d"
    --#ARGUMENTS {1,0}
    --#STATE OPERATIONAL
    --#SEVERITY WARNING
    ::= { starentTraps 342 }

starThreshClearPDIFCurrSess NOTIFICATION-TYPE
    OBJECTS { starThreshInt, starThreshMeasuredInt }
    STATUS current
    DESCRIPTION
 	"The threshold condition is now clear."
    --#SUMMARY "[System] Threshold: PDIF Current Sessions CLEAR; measured %d threshold %d"
    --#ARGUMENTS {1,0}
    --#STATE OPERATIONAL
    --#SEVERITY INFORMATIONAL
    ::= { starentTraps 343 }

starThreshPDIFCurrActSess NOTIFICATION-TYPE
    OBJECTS { starThreshInt, starThreshMeasuredInt }
    STATUS current
    DESCRIPTION
         "The chassis-wide count of current PDIF active sessions has gone above the configured threshold

          Probable Cause: This is a user configurable threshold.

          If the thresholding subsystem is configured to run in an 'alarm' model,
 	 a starThreshClearPDIFCurrActiveSess notification will be generated when the measured
 	 value falls below the threshold."
    --#SUMMARY "[System] Threshold: PDIF Current Active Sessions; measured %d threshold %d"
    --#ARGUMENTS {1,0}
    --#STATE OPERATIONAL
    --#SEVERITY WARNING
    ::= { starentTraps 344 }

starThreshClearPDIFCurrActSess NOTIFICATION-TYPE
    OBJECTS { starThreshInt, starThreshMeasuredInt }
    STATUS current
    DESCRIPTION
 	"The threshold condition is now clear."
    --#SUMMARY "[System] Threshold: PDIF Current Active Sessions CLEAR; measured %d threshold %d"
    --#ARGUMENTS {1,0}
    --#STATE OPERATIONAL
    --#SEVERITY INFORMATIONAL
    ::= { starentTraps 345 }

starThreshCDRFlowControl NOTIFICATION-TYPE
    OBJECTS { starThreshInt, starThreshMeasuredInt }
    STATUS  current
    DESCRIPTION
	"The number of Charging Data Record (CDR) records which have been discarded at an ACSMGR
	 due to flow control has gone above the configured threshold.

	 Probable Cause: This is a user configurable threshold.  This threshold potentially
         indicates an overload condition due which prevents processes CDR messages at the same rate as
	 the incoming packets."

    --#SUMMARY "[System] Threshold: Total num of CDR records discarded by due to flow control; measured %d threshold %d"
    --#ARGUMENTS {1,0}
    --#STATE OPERATIONAL
    --#SEVERITY INFORMATIONAL
    ::= { starentTraps 346 }

starThreshClearCDRFlowControl NOTIFICATION-TYPE
    OBJECTS { starThreshInt, starThreshMeasuredInt }
    STATUS  current
    DESCRIPTION
	"The threshold condition is now clear."
    --#SUMMARY "[System] Threshold: Total number of CDR records discarded due to clow control CLEAR; measured %d threshold %d"
    --#ARGUMENTS {1,0}
    --#STATE OPERATIONAL
    --#SEVERITY MAJOR
    ::= { starentTraps 347 }

starThreshASNGWSessTimeout NOTIFICATION-TYPE
    OBJECTS { starThreshInt, starThreshMeasuredInt }
    STATUS obsolete
    DESCRIPTION
         "The ASNGW session timeout has gone above the configured threshold

          Probable Cause: This is a user configurable threshold.

         If the thresholding subsystem is configured to run in an 'alarm' model,
 	 a starThreshASNGWSessTimeout notification will be generated when the measured
 	 value falls below the threshold."
    --#SUMMARY "[System] Threshold: ASNGW Session Timeout; measured %d threshold %d"
    --#ARGUMENTS {1,0}
    --#STATE OPERATIONAL
    --#SEVERITY WARNING
    ::= { starentTraps 348 }

starThreshClearASNGWSessTimeout NOTIFICATION-TYPE
    OBJECTS { starThreshInt, starThreshMeasuredInt }
    STATUS obsolete
    DESCRIPTION
	"The threshold condition is now clear."
    --#SUMMARY "[System] Threshold: ASNGW Session Timeout CLEAR; measured %d threshold %d"
    --#ARGUMENTS {1,0}
    --#STATE OPERATIONAL
    --#SEVERITY WARNING
    ::= { starentTraps 349 }

starThreshASNGWSessSetupTimeout NOTIFICATION-TYPE
    OBJECTS { starThreshInt, starThreshMeasuredInt }
    STATUS obsolete
    DESCRIPTION
         "The ASNGW session setup timeout has gone above the configured threshold

          Probable Cause: This is a user configurable threshold.

         If the thresholding subsystem is configured to run in an 'alarm' model,
 	 a starThreshASNGWSessSetupTimeout notification will be generated when the measured
 	 value falls below the threshold."
    --#SUMMARY "[System] Threshold: ASNGW Session Setup Timeout; measured %d threshold %d"
    --#ARGUMENTS {1,0}
    --#STATE OPERATIONAL
    --#SEVERITY WARNING
    ::= { starentTraps 350 }

starThreshClearASNGWSessSetupTimeout NOTIFICATION-TYPE
    OBJECTS { starThreshInt, starThreshMeasuredInt }
    STATUS obsolete
    DESCRIPTION
	"The threshold condition is now clear."
    --#SUMMARY "[System] Threshold: ASNGW Session Setup Timeout CLEAR; measured %d threshold %d"
    --#ARGUMENTS {1,0}
    --#STATE OPERATIONAL
    --#SEVERITY WARNING
    ::= { starentTraps 351 }

starThreshASNGWAuthFail NOTIFICATION-TYPE
    OBJECTS { starThreshInt, starThreshMeasuredInt }
    STATUS obsolete
    DESCRIPTION
	"The number of ASNGW authentication failures has exceeded the configured threshold
	 during the current monitoring period.

         Probable Cause: This is a user configurable threshold.

         If the thresholding subsystem is configured to run in an 'alarm' model,
         a starThreshASNGWAuthFail notification will be generated when the measured
	 value falls below the threshold."
    --#SUMMARY "[System] Threshold: ASNGW authentication failures threshold; measured %d threshold %d"
    --#ARGUMENTS {1,0}
    --#STATE OPERATIONAL
    --#SEVERITY WARNING
    ::= { starentTraps 352}

starThreshClearASNGWAuthFail NOTIFICATION-TYPE
    OBJECTS { starThreshInt, starThreshMeasuredInt }
    STATUS obsolete
    DESCRIPTION
	"The threshold condition is now clear."
    --#SUMMARY "[System] Threshold: ASNGW authentication failures threshold CLEAR; measured %d threshold %d"
    --#ARGUMENTS {1,0}
    --#STATE OPERATIONAL
    --#SEVERITY WARNING
    ::= { starentTraps 353 }

starThreshASNGWR6InvNai NOTIFICATION-TYPE
    OBJECTS { starThreshInt, starThreshMeasuredInt }
    STATUS obsolete
    DESCRIPTION
	"The number of ASNGW R6 Invalid Nai has exceeded the configured threshold
	 during the current monitoring period.

         Probable Cause: This is a user configurable threshold.

         If the thresholding subsystem is configured to run in an 'alarm' model,
         a starThreshASNGWR6InvNai notification will be generated when the measured
	 value falls below the threshold. This trap is obsolete."
    --#SUMMARY "[System] Threshold: ASNGW R6 Invalid NAI threshold; measured %d threshold %d"
    --#ARGUMENTS {1,0}
    --#STATE OPERATIONAL
    --#SEVERITY WARNING
    ::= { starentTraps 354 }

starThreshClearASNGWR6InvNai NOTIFICATION-TYPE
    OBJECTS { starThreshInt, starThreshMeasuredInt }
    STATUS obsolete
    DESCRIPTION
	"The threshold condition is now clear. This trap is obsolete."
    --#SUMMARY "[System] Threshold: ASNGW R6 Invalid NAI threshold CLEAR; measured %d threshold %d"
    --#ARGUMENTS {1,0}
    --#STATE OPERATIONAL
    --#SEVERITY WARNING
    ::= { starentTraps 355 }

starThreshASNGWMaxEAPRetry NOTIFICATION-TYPE
    OBJECTS { starThreshInt, starThreshMeasuredInt }
    STATUS obsolete
    DESCRIPTION
	"The number of ASNGW Maximum EAP Retry has exceeded the configured threshold
	 during the current monitoring period.

         Probable Cause: This is a user configurable threshold.

         If the thresholding subsystem is configured to run in an 'alarm' model,
         a starThreshASNGWMaxEAPRetry notification will be generated when the measured
	 value falls below the threshold."
    --#SUMMARY "[System] Threshold: ASNGW Maximum EAP Retry threshold; measured %d threshold %d"
    --#ARGUMENTS {1,0}
    --#STATE OPERATIONAL
    --#SEVERITY WARNING
    ::= { starentTraps 356 }

starThreshClearASNGWMaxEAPRetry NOTIFICATION-TYPE
    OBJECTS { starThreshInt, starThreshMeasuredInt }
    STATUS obsolete
    DESCRIPTION
	"The threshold condition is now clear."
    --#SUMMARY "[System] Threshold: ASNGW Maximum EAP Retry threshold CLEAR; measured %d threshold %d"
    --#ARGUMENTS {1,0}
    --#STATE OPERATIONAL
    --#SEVERITY WARNING
    ::= { starentTraps 357 }

starThreshASNGWNWEntryDenial NOTIFICATION-TYPE
    OBJECTS { starThreshInt, starThreshMeasuredInt }
    STATUS obsolete
    DESCRIPTION
	"The number of ASNGW Network Entry Denial has exceeded the configured threshold
	 during the current monitoring period.

         Probable Cause: This is a user configurable threshold.

         If the thresholding subsystem is configured to run in an 'alarm' model,
         a starThreshASNGWNWEntryDenial notification will be generated when the measured
	 value falls below the threshold."
    --#SUMMARY "[System] Threshold: ASNGW Network Entry Denial threshold; measured %d threshold %d"
    --#ARGUMENTS {1,0}
    --#STATE OPERATIONAL
    --#SEVERITY WARNING
    ::= { starentTraps 358 }

starThreshClearASNGWNWEntryDenial NOTIFICATION-TYPE
    OBJECTS { starThreshInt, starThreshMeasuredInt }
    STATUS obsolete
    DESCRIPTION
	"The threshold condition is now clear."
    --#SUMMARY "[System] Threshold: ASNGW Network Entry Denial threshold CLEAR; measured %d threshold %d"
    --#ARGUMENTS {1,0}
    --#STATE OPERATIONAL
    --#SEVERITY WARNING
    ::= { starentTraps 359 }

starThreshASNGWHandoffDenial NOTIFICATION-TYPE
    OBJECTS { starThreshInt, starThreshMeasuredInt }
    STATUS obsolete
    DESCRIPTION
	"The number of ASNGW Handoff Denial has exceeded the configured threshold
	 during the current monitoring period.

         Probable Cause: This is a user configurable threshold.

         If the thresholding subsystem is configured to run in an 'alarm' model,
         a starThreshASNGWHandoffDenial notification will be generated when the measured
	 value falls below the threshold."
    --#SUMMARY "[System] Threshold: ASNGW Handoff Denial threshold; measured %d threshold %d"
    --#ARGUMENTS {1,0}
    --#STATE OPERATIONAL
    --#SEVERITY WARNING
    ::= { starentTraps 360 }

starThreshClearASNGWHandoffDenial NOTIFICATION-TYPE
    OBJECTS { starThreshInt, starThreshMeasuredInt }
    STATUS obsolete
    DESCRIPTION
	"The threshold condition is now clear."
    --#SUMMARY "[System] Threshold: ASNGW Handoff Denial threshold CLEAR; measured %d threshold %d"
    --#ARGUMENTS {1,0}
    --#STATE OPERATIONAL
    --#SEVERITY WARNING
    ::= { starentTraps 361 }

starThreshSGSNSessions NOTIFICATION-TYPE
    OBJECTS { starThreshInt, starThreshMeasuredInt }
    STATUS current
    DESCRIPTION
        "The total number of SGSN sessions is above the configured threshold value."
    --#SUMMARY "[System] Threshold: Total SGSN Sessions; measured %d threshold %d"
    --#ARGUMENTS {1,0}
    --#STATE OPERATIONAL
    --#SEVERITY WARNING
    ::= { starentTraps 362 }

starThreshClearSGSNSessions NOTIFICATION-TYPE
    OBJECTS { starThreshInt, starThreshMeasuredInt }
    STATUS current
    DESCRIPTION
        "The threshold condition is now clear."
    --#SUMMARY "[System] Threshold: Total SGSN Sessions CLEAR; measured %d threshold %d"
    --#ARGUMENTS {1,0}
    --#STATE OPERATIONAL
    --#SEVERITY INFORMATIONAL
    ::= { starentTraps 363 }

starThreshPerServiceSGSNSessions NOTIFICATION-TYPE
    OBJECTS { starServiceVpnName, starServiceServName, starThreshInt, starThreshMeasuredInt }
    STATUS current
    DESCRIPTION
        "The total number of SGSN sessions in a service is above the configured threshold value."
    --#SUMMARY "[System] Threshold: Per Sevice SGSN Sessions, context %s service name %s; measured %d threshold %d"
    --#ARGUMENTS {0,1,3,2}
    --#STATE OPERATIONAL
    --#SEVERITY WARNING
    ::= { starentTraps 364 }

starThreshClearPerServiceSGSNSessions NOTIFICATION-TYPE
    OBJECTS { starServiceVpnName, starServiceServName, starThreshInt, starThreshMeasuredInt }
    STATUS current
    DESCRIPTION
        "The threshold condition is now clear."
    --#SUMMARY "[System] Threshold: Per Sevice SGSN Sessions CLEAR, context %s service name %s; measured %d threshold %d"
    --#ARGUMENTS {0,1,3,2}
    --#STATE OPERATIONAL
    --#SEVERITY INFORMATIONAL
    ::= { starentTraps 365 }

starThreshSGSNPdpSessions NOTIFICATION-TYPE
    OBJECTS { starThreshInt, starThreshMeasuredInt }
    STATUS current
    DESCRIPTION
        "The total number of SGSN PDP sessions is above the configured threshold value."
    --#SUMMARY "[System] Threshold: Total SGSN PDP Sessions; measured %d threshold %d"
    --#ARGUMENTS {1,0}
    --#STATE OPERATIONAL
    --#SEVERITY WARNING
    ::= { starentTraps 366 }

starThreshClearSGSNPdpSessions NOTIFICATION-TYPE
    OBJECTS { starThreshInt, starThreshMeasuredInt }
    STATUS current
    DESCRIPTION
        "The threshold condition is now clear."
    --#SUMMARY "[System] Threshold: Total SGSN PDP Sessions CLEAR; measured %d threshold %d"
    --#ARGUMENTS {1,0}
    --#STATE OPERATIONAL
    --#SEVERITY INFORMATIONAL
    ::= { starentTraps 367 }

starThreshPerServiceSGSNPdpSessions NOTIFICATION-TYPE
    OBJECTS { starServiceVpnName, starServiceServName, starThreshInt, starThreshMeasuredInt }
    STATUS current
    DESCRIPTION
        "The total number of SGSN PDP sessions in a service is above the configured threshold value."
    --#SUMMARY "[System] Threshold: Per Sevice SGSN PDP Sessions, context %s service name %s; measured %d threshold %d"
    --#ARGUMENTS {0,1,3,2}
    --#STATE OPERATIONAL
    --#SEVERITY WARNING
    ::= { starentTraps 368 }

starThreshClearPerServiceSGSNPdpSessions NOTIFICATION-TYPE
    OBJECTS { starServiceVpnName, starServiceServName, starThreshInt, starThreshMeasuredInt }
    STATUS current
    DESCRIPTION
        "The threshold condition is now clear."
    --#SUMMARY "[System] Threshold: Per Sevice SGSN PDP Sessions CLEAR, context %s service name %s; measured %d threshold %d"
    --#ARGUMENTS {0,1,3,2}
    --#STATE OPERATIONAL
    --#SEVERITY INFORMATIONAL
    ::= { starentTraps 369 }

starThreshFWDosAttack NOTIFICATION-TYPE
    OBJECTS { starThreshInt, starThreshMeasuredInt }
    STATUS  current
    DESCRIPTION
	"The cumulative number of FW Dos-Attacks has exceeded the configured
	 threshold during the current monitoring period.

         Probable Cause: This is a user configurable threshold.

         If the thresholding subsystem is configured to run in an 'alarm' model,
	 a starThreshClearFWDosAttack notification will be generated when the
	 measured value falls below the threshold."
    --#SUMMARY "[System] Threshold: Firewall 'Dos-Attack'; measured %d threshold %d"
    --#ARGUMENTS {1,0}
    --#STATE OPERATIONAL
    --#SEVERITY WARNING
    ::= { starentTraps 370 }

starThreshClearFWDosAttack NOTIFICATION-TYPE
    OBJECTS { starThreshInt, starThreshMeasuredInt }
    STATUS current
    DESCRIPTION
	"The threshold condition is now clear."
    --#SUMMARY "[System] Threshold: Firewall 'Dos-Attack' CLEAR; measured %d threshold %d"
    --#ARGUMENTS {1,0}
    --#STATE OPERATIONAL
    --#SEVERITY INFORMATIONAL
    ::= { starentTraps 371 }

starThreshFWDropPacket NOTIFICATION-TYPE
    OBJECTS { starThreshInt, starThreshMeasuredInt }
    STATUS  current
    DESCRIPTION
	"The cumulative number of FW Dropped Packets has exceeded the configured
	 threshold during the current monitoring period.

         Probable Cause: This is a user configurable threshold.

         If the thresholding subsystem is configured to run in an 'alarm' model,
	 a starThreshClearFWDropPacket notification will be generated when the
	 measured value falls below the threshold."
    --#SUMMARY "[System] Threshold: Firewall 'Drop-Packet'; measured %d threshold %d"
    --#ARGUMENTS {1,0}
    --#STATE OPERATIONAL
    --#SEVERITY WARNING
    ::= { starentTraps 372 }

starThreshClearFWDropPacket NOTIFICATION-TYPE
    OBJECTS { starThreshInt, starThreshMeasuredInt }
    STATUS current
    DESCRIPTION
	"The threshold condition is now clear."
    --#SUMMARY "[System] Threshold: Firewall 'Drop-Packet' CLEAR; measured %d threshold %d"
    --#ARGUMENTS {1,0}
    --#STATE OPERATIONAL
    --#SEVERITY INFORMATIONAL
    ::= { starentTraps 373 }

starThreshFWDenyRule NOTIFICATION-TYPE
    OBJECTS { starThreshInt, starThreshMeasuredInt }
    STATUS  current
    DESCRIPTION
	"The cumulative number of FW Deny-Rules has exceeded the configured
	 threshold during the current monitoring period.

         Probable Cause: This is a user configurable threshold.

         If the thresholding subsystem is configured to run in an 'alarm' model,
	 a starThreshClearFWDenyRule notification will be generated when the
	 measured value falls below the threshold."
    --#SUMMARY "[System] Threshold: Firewall 'Deny-Rule'; measured %d threshold %d"
    --#ARGUMENTS {1,0}
    --#STATE OPERATIONAL
    --#SEVERITY WARNING
    ::= { starentTraps 374 }

starThreshClearFWDenyRule NOTIFICATION-TYPE
    OBJECTS { starThreshInt, starThreshMeasuredInt }
    STATUS current
    DESCRIPTION
	"The threshold condition is now clear."
    --#SUMMARY "[System] Threshold: Firewall 'Deny-Rule' CLEAR; measured %d threshold %d"
    --#ARGUMENTS {1,0}
    --#STATE OPERATIONAL
    --#SEVERITY INFORMATIONAL
    ::= { starentTraps 375 }

starThreshFWNoRule NOTIFICATION-TYPE
    OBJECTS { starThreshInt, starThreshMeasuredInt }
    STATUS  current
    DESCRIPTION
	"The cumulative number of FW No Rules has exceeded the configured
	 threshold during the current monitoring period.

         Probable Cause: This is a user configurable threshold.

         If the thresholding subsystem is configured to run in an 'alarm' model,
	 a starThreshClearFWNoRule notification will be generated when the
	 measured value falls below the threshold."
    --#SUMMARY "[System] Threshold: Firewall 'No-Rule'; measured %d threshold %d"
    --#ARGUMENTS {1,0}
    --#STATE OPERATIONAL
    --#SEVERITY WARNING
    ::= { starentTraps 376 }

starThreshClearFWNoRule NOTIFICATION-TYPE
    OBJECTS { starThreshInt, starThreshMeasuredInt }
    STATUS current
    DESCRIPTION
	"The threshold condition is now clear."
    --#SUMMARY "[System] Threshold: Firewall 'No-Rule' CLEAR; measured %d threshold %d"
    --#ARGUMENTS {1,0}
    --#STATE OPERATIONAL
    --#SEVERITY INFORMATIONAL
    ::= { starentTraps 377 }

starThreshPHSGWSessTimeout NOTIFICATION-TYPE
    OBJECTS { starThreshInt, starThreshMeasuredInt }
    STATUS current
    DESCRIPTION
         "The PHSGW session timeout has gone above the configured threshold
 
          Probable Cause: This is a user configurable threshold.
 
         If the thresholding subsystem is configured to run in an 'alarm' model,
 	 a starThreshPHSGWSessTimeout notification will be generated when the measured
 	 value falls below the threshold."
    --#SUMMARY "[System] Threshold: PHSGW Session Timeout; measured %d threshold %d"
    --#ARGUMENTS {1,0}
    --#STATE OPERATIONAL
    --#SEVERITY WARNING
    ::= { starentTraps 378 }

starThreshClearPHSGWSessTimeout NOTIFICATION-TYPE
    OBJECTS { starThreshInt, starThreshMeasuredInt }
    STATUS current
    DESCRIPTION
	"The threshold condition is now clear."
    --#SUMMARY "[System] Threshold: PHSGW Session Timeout CLEAR; measured %d threshold %d"
    --#ARGUMENTS {1,0}
    --#STATE OPERATIONAL
    --#SEVERITY INFORMATIONAL 
    ::= { starentTraps 379 }

starThreshPHSGWSessSetupTimeout NOTIFICATION-TYPE
    OBJECTS { starThreshInt, starThreshMeasuredInt }
    STATUS current
    DESCRIPTION
         "The PHSGW session setup timeout has gone above the configured threshold
 
          Probable Cause: This is a user configurable threshold.
 
         If the thresholding subsystem is configured to run in an 'alarm' model,
 	 a starThreshPHSGWSessSetupTimeout notification will be generated when the measured
 	 value falls below the threshold."
    --#SUMMARY "[System] Threshold: PHSGW Session Setup Timeout; measured %d threshold %d"
    --#ARGUMENTS {1,0}
    --#STATE OPERATIONAL
    --#SEVERITY WARNING
    ::= { starentTraps 380 }

starThreshClearPHSGWSessSetupTimeout NOTIFICATION-TYPE
    OBJECTS { starThreshInt, starThreshMeasuredInt }
    STATUS obsolete
    DESCRIPTION
	"The threshold condition is now clear."
    --#SUMMARY "[System] Threshold: PHSGW Session Setup Timeout CLEAR; measured %d threshold %d"
    --#ARGUMENTS {1,0}
    --#STATE OPERATIONAL
    --#SEVERITY INFORMATIONAL 
    ::= { starentTraps 381 }

starThreshPHSGWAuthFail NOTIFICATION-TYPE
    OBJECTS { starThreshInt, starThreshMeasuredInt }
    STATUS obsolete
    DESCRIPTION
	"The number of PHSGW authentication failures has exceeded the configured threshold
	 during the current monitoring period.

         Probable Cause: This is a user configurable threshold.

         If the thresholding subsystem is configured to run in an 'alarm' model,
         a starThreshPHSGWAuthFail notification will be generated when the measured
	 value falls below the threshold."
    --#SUMMARY "[System] Threshold: PHSGW authentication failures threshold; measured %d threshold %d"
    --#ARGUMENTS {1,0}
    --#STATE OPERATIONAL
    --#SEVERITY WARNING
    ::= { starentTraps 382}

starThreshClearPHSGWAuthFail NOTIFICATION-TYPE
    OBJECTS { starThreshInt, starThreshMeasuredInt }
    STATUS obsolete
    DESCRIPTION
	"The threshold condition is now clear."
    --#SUMMARY "[System] Threshold: PHSGW authentication failures threshold CLEAR; measured %d threshold %d"
    --#ARGUMENTS {1,0}
    --#STATE OPERATIONAL
    --#SEVERITY INFORMATIONAL 
    ::= { starentTraps 383 }

starThreshPHSGWMaxEAPRetry NOTIFICATION-TYPE
    OBJECTS { starThreshInt, starThreshMeasuredInt }
    STATUS obsolete
    DESCRIPTION
	"The number of PHSGW Maximum EAP Retry has exceeded the configured threshold
	 during the current monitoring period.

         Probable Cause: This is a user configurable threshold.

         If the thresholding subsystem is configured to run in an 'alarm' model,
         a starThreshPHSGWMaxEAPRetry notification will be generated when the measured
	 value falls below the threshold."
    --#SUMMARY "[System] Threshold: PHSGW Maximum EAP Retry threshold; measured %d threshold %d"
    --#ARGUMENTS {1,0}
    --#STATE OPERATIONAL
    --#SEVERITY WARNING
    ::= { starentTraps 384 }

starThreshClearPHSGWMaxEAPRetry NOTIFICATION-TYPE
    OBJECTS { starThreshInt, starThreshMeasuredInt }
    STATUS obsolete
    DESCRIPTION
	"The threshold condition is now clear."
    --#SUMMARY "[System] Threshold: PHSGW Maximum EAP Retry threshold CLEAR; measured %d threshold %d"
    --#ARGUMENTS {1,0}
    --#STATE OPERATIONAL
    --#SEVERITY INFORMATIONAL 
    ::= { starentTraps 385 }

starThreshPHSGWNWEntryDenial NOTIFICATION-TYPE
    OBJECTS { starThreshInt, starThreshMeasuredInt }
    STATUS obsolete
    DESCRIPTION
	"The number of PHSGW Network Entry Denial has exceeded the configured threshold
	 during the current monitoring period.

         Probable Cause: This is a user configurable threshold.

         If the thresholding subsystem is configured to run in an 'alarm' model,
         a starThreshPHSGWNWEntryDenial notification will be generated when the measured
	 value falls below the threshold."
    --#SUMMARY "[System] Threshold: PHSGW Network Entry Denial threshold; measured %d threshold %d"
    --#ARGUMENTS {1,0}
    --#STATE OPERATIONAL
    --#SEVERITY WARNING
    ::= { starentTraps 386 }

starThreshClearPHSGWNWEntryDenial NOTIFICATION-TYPE
    OBJECTS { starThreshInt, starThreshMeasuredInt }
    STATUS obsolete
    DESCRIPTION
	"The threshold condition is now clear."
    --#SUMMARY "[System] Threshold: PHSGW Network Entry Denial threshold CLEAR; measured %d threshold %d"
    --#ARGUMENTS {1,0}
    --#STATE OPERATIONAL
    --#SEVERITY INFORMATIONAL 
    ::= { starentTraps 387 }

starThreshPHSGWHandoffDenial NOTIFICATION-TYPE
    OBJECTS { starThreshInt, starThreshMeasuredInt }
    STATUS obsolete
    DESCRIPTION
	"The number of PHSGW Handoff Denial has exceeded the configured threshold
	 during the current monitoring period.

         Probable Cause: This is a user configurable threshold.

         If the thresholding subsystem is configured to run in an 'alarm' model,
         a starThreshPHSGWHandoffDenial notification will be generated when the measured
	 value falls below the threshold."
    --#SUMMARY "[System] Threshold: PHSGW Handoff Denial threshold; measured %d threshold %d"
    --#ARGUMENTS {1,0}
    --#STATE OPERATIONAL
    --#SEVERITY WARNING
    ::= { starentTraps 388 }

starThreshClearPHSGWHandoffDenial NOTIFICATION-TYPE
    OBJECTS { starThreshInt, starThreshMeasuredInt }
    STATUS obsolete
    DESCRIPTION
	"The threshold condition is now clear."
    --#SUMMARY "[System] Threshold: PHSGW Handoff Denial threshold CLEAR; measured %d threshold %d"
    --#ARGUMENTS {1,0}
    --#STATE OPERATIONAL
    --#SEVERITY INFORMATIONAL 
    ::= { starentTraps 389 }

starThreshASNGWSessions NOTIFICATION-TYPE
    OBJECTS { starThreshInt, starThreshMeasuredInt }
    STATUS obsolete
    DESCRIPTION
	"The total number of ASNGW sessions is above the configured threshold value."
    --#SUMMARY "[System] Threshold: Total ASNGW Sessions; measured %d threshold %d"
    --#ARGUMENTS {1,0}
    --#STATE OPERATIONAL
    --#SEVERITY WARNING
    ::= { starentTraps 390 }

starThreshClearASNGWSessions NOTIFICATION-TYPE
    OBJECTS { starThreshInt, starThreshMeasuredInt }
    STATUS obsolete
    DESCRIPTION
	"The threshold condition is now clear."
    --#SUMMARY "[System] Threshold: Total ASNGW Sessions CLEAR; measured %d threshold %d"
    --#ARGUMENTS {1,0}
    --#STATE OPERATIONAL
    --#SEVERITY INFORMATIONAL
    ::= { starentTraps 391 }

starThreshPerServiceASNGWSessions NOTIFICATION-TYPE
    OBJECTS { starServiceVpnName, starServiceServName, starThreshInt, starThreshMeasuredInt }
    STATUS obsolete
    DESCRIPTION
	"The total number of ASNGW sessions in a service is above the configured threshold value."
    --#SUMMARY "[System] Threshold: Per Sevice ASNGW Sessions, context %s service name %s; measured %d threshold %d"
    --#ARGUMENTS {0,1,3,2}
    --#STATE OPERATIONAL
    --#SEVERITY WARNING
    ::= { starentTraps 392 }

starThreshClearPerServiceASNGWSessions NOTIFICATION-TYPE
    OBJECTS { starServiceVpnName, starServiceServName, starThreshInt, starThreshMeasuredInt }
    STATUS obsolete
    DESCRIPTION
	"The threshold condition is now clear."
    --#SUMMARY "[System] Threshold: Per Sevice ASNGW Sessions CLEAR, context %s service name %s; measured %d threshold %d"
    --#ARGUMENTS {0,1,3,2}
    --#STATE OPERATIONAL
    --#SEVERITY INFORMATIONAL
    ::= { starentTraps 393 }

starThreshPHSPCSessSetupTimeout NOTIFICATION-TYPE
    OBJECTS { starThreshInt, starThreshMeasuredInt }
    STATUS obsolete
    DESCRIPTION
         "The PHSPC session setup timeout has gone above the configured threshold
 
          Probable Cause: This is a user configurable threshold.
 
         If the thresholding subsystem is configured to run in an 'alarm' model,
 	 a starThreshPHSPCSessSetupTimeout notification will be generated when the measured
 	 value falls below the threshold."
    --#SUMMARY "[System] Threshold: PHSPC Session Setup Timeout; measured %d threshold %d"
    --#ARGUMENTS {1,0}
    --#STATE OPERATIONAL
    --#SEVERITY WARNING
    ::= { starentTraps 394 }

starThreshClearPHSPCSessSetupTimeout NOTIFICATION-TYPE
    OBJECTS { starThreshInt, starThreshMeasuredInt }
    STATUS obsolete
    DESCRIPTION
	"The threshold condition is now clear."
    --#SUMMARY "[System] Threshold: PHSPC Session Setup Timeout CLEAR; measured %d threshold %d"
    --#ARGUMENTS {1,0}
    --#STATE OPERATIONAL
    --#SEVERITY INFORMATIONAL 
    ::= { starentTraps 395 }

starThreshPHSPCSleepModeTimeout NOTIFICATION-TYPE
    OBJECTS { starThreshInt, starThreshMeasuredInt }
    STATUS obsolete
    DESCRIPTION
         "The PHSPC idle mode timeout has gone above the configured threshold
 
          Probable Cause: This is a user configurable threshold.
 
         If the thresholding subsystem is configured to run in an 'alarm' model,
 	 a starThreshPHSPCSleepModeTimeout notification will be generated when the measured
 	 value falls below the threshold."
    --#SUMMARY "[System] Threshold: PHSPC Idle Mode Timeout; measured %d threshold %d"
    --#ARGUMENTS {1,0}
    --#STATE OPERATIONAL
    --#SEVERITY WARNING
    ::= { starentTraps 396 }

starThreshClearPHSPCSleepModeTimeout NOTIFICATION-TYPE
    OBJECTS { starThreshInt, starThreshMeasuredInt }
    STATUS obsolete
    DESCRIPTION
	"The threshold condition is now clear."
    --#SUMMARY "[System] Threshold:  PHSPC Idle Mode Timeout CLEAR; measured %d threshold %d"
    --#ARGUMENTS {1,0}
    --#STATE OPERATIONAL
    --#SEVERITY INFORMATIONAL 
    ::= { starentTraps 397 }

starThreshPHSPCSmEntryDenial NOTIFICATION-TYPE
    OBJECTS { starThreshInt, starThreshMeasuredInt }
    STATUS obsolete
    DESCRIPTION
	"The number of PHSPC sm entry denial has exceeded the configured threshold
	 during the current monitoring period.

         Probable Cause: This is a user configurable threshold.

         If the thresholding subsystem is configured to run in an 'alarm' model,
         a starThreshPHSPCSmEntryDenial notification will be generated when the measured
	 value falls below the threshold."
    --#SUMMARY "[System] Threshold: PHSPC Sm Entry Denial threshold; measured %d threshold %d"
    --#ARGUMENTS {1,0}
    --#STATE OPERATIONAL
    --#SEVERITY WARNING
    ::= { starentTraps 398}

starThreshClearPHSPCSmEntryDenial NOTIFICATION-TYPE
    OBJECTS { starThreshInt, starThreshMeasuredInt }
    STATUS obsolete
    DESCRIPTION
	"The threshold condition is now clear."
    --#SUMMARY "[System] Threshold: PHSPC Sm Entry Denial threshold CLEAR; measured %d threshold %d"
    --#ARGUMENTS {1,0}
    --#STATE OPERATIONAL
    --#SEVERITY INFORMATIONAL 
    ::= { starentTraps 399 }

starThreshSGWSessions NOTIFICATION-TYPE
    OBJECTS { starThreshInt, starThreshMeasuredInt }
    STATUS current
    DESCRIPTION
        "The total number of SGW sessions is above the configured threshold value.

         Probable Cause: This is a user configurable threshold.

         If the thresholding subsystem is configured to run in an 'alarm' model,
         a starThreshClearSGWSessions notification will be generated when the measured
         value falls below the threshold."
    --#SUMMARY "[System] Threshold: Total SGW Sessions; measured %d threshold %d"
    --#ARGUMENTS {1,0}
    --#STATE OPERATIONAL
    --#SEVERITY WARNING
    ::= { starentTraps 408 }

starThreshClearSGWSessions NOTIFICATION-TYPE
    OBJECTS { starThreshInt, starThreshMeasuredInt }
    STATUS current
    DESCRIPTION
        "The threshold condition is now clear."
    --#SUMMARY "[System] Threshold: Total SGW Sessions CLEAR; measured %d threshold %d"
    --#ARGUMENTS {1,0}
    --#STATE OPERATIONAL
    --#SEVERITY INFORMATIONAL
    ::= { starentTraps 409 }

starThreshPGWSessions NOTIFICATION-TYPE
    OBJECTS { starThreshInt, starThreshMeasuredInt }
    STATUS current
    DESCRIPTION
        "The total number of PGW sessions is above the configured threshold value.

         Probable Cause: This is a user configurable threshold.

         If the thresholding subsystem is configured to run in an 'alarm' model,
         a starThreshClearSGWSessions notification will be generated when the measured
         value falls below the threshold."
    --#SUMMARY "[System] Threshold: Total PGW Sessions; measured %d threshold %d"
    --#ARGUMENTS {1,0}
    --#STATE OPERATIONAL
    --#SEVERITY WARNING
    ::= { starentTraps 410 }

starThreshClearPGWSessions NOTIFICATION-TYPE
    OBJECTS { starThreshInt, starThreshMeasuredInt }
    STATUS current
    DESCRIPTION
        "The threshold condition is now clear."
    --#SUMMARY "[System] Threshold: Total PGW Sessions CLEAR; measured %d threshold %d"
    --#ARGUMENTS {1,0}
    --#STATE OPERATIONAL
    --#SEVERITY INFORMATIONAL
    ::= { starentTraps 411 }

starThreshLMASessions NOTIFICATION-TYPE
    OBJECTS { starThreshInt, starThreshMeasuredInt }
    STATUS current
    DESCRIPTION
        "The total number of LMA sessions is above the configured threshold value.

         Probable Cause: This is a user configurable threshold.

         If the thresholding subsystem is configured to run in an 'alarm' model,
         a starThreshClearLMASessions notification will be generated when the measured
         value falls below the threshold."
    --#SUMMARY "[System] Threshold: Total LMA Sessions; measured %d threshold %d"
    --#ARGUMENTS {1,0}
    --#STATE OPERATIONAL
    --#SEVERITY WARNING
    ::= { starentTraps 412 }

starThreshClearLMASessions NOTIFICATION-TYPE
    OBJECTS { starThreshInt, starThreshMeasuredInt }
    STATUS current
    DESCRIPTION
        "The threshold condition is now clear."
    --#SUMMARY "[System] Threshold: Total LMA Sessions CLEAR; measured %d threshold %d"
    --#ARGUMENTS {1,0}
    --#STATE OPERATIONAL
    --#SEVERITY INFORMATIONAL
    ::= { starentTraps 413 }

starThreshMAGSessions NOTIFICATION-TYPE
    OBJECTS { starThreshInt, starThreshMeasuredInt }
    STATUS current
    DESCRIPTION
        "The total number of MAG sessions is above the configured threshold value.

         Probable Cause: This is a user configurable threshold.

         If the thresholding subsystem is configured to run in an 'alarm' model,
         a starThreshClearMAGSessions notification will be generated when the measured
         value falls below the threshold."
    --#SUMMARY "[System] Threshold: Total MAG Sessions; measured %d threshold %d"
    --#ARGUMENTS {1,0}
    --#STATE OPERATIONAL
    --#SEVERITY WARNING
    ::= { starentTraps 414 }

starThreshClearMAGSessions NOTIFICATION-TYPE
    OBJECTS { starThreshInt, starThreshMeasuredInt }
    STATUS current
    DESCRIPTION
        "The threshold condition is now clear."
    --#SUMMARY "[System] Threshold: Total MAG Sessions CLEAR; measured %d threshold %d"
    --#ARGUMENTS {1,0}
    --#STATE OPERATIONAL
    --#SEVERITY INFORMATIONAL
    ::= { starentTraps 415 }

  starThreshFNGCurrSess NOTIFICATION-TYPE
    OBJECTS { starThreshInt, starThreshMeasuredInt }
    STATUS current
    DESCRIPTION
         "The chassis-wide count of current FNG sessions has gone above the configured threshold

         Probable Cause: This is a user configurable threshold.

         If the thresholding subsystem is configured to run in an 'alarm' model,
         a starThreshClearFNGCurrSess notification will be generated when the measured
         value falls below the threshold."
    --#SUMMARY "[System] Threshold: FNG Current Sessions; measured %d threshold %d"
    --#ARGUMENTS {1,0}
    --#STATE OPERATIONAL
    --#SEVERITY WARNING
    ::= { starentTraps 416 }

  starThreshClearFNGCurrSess NOTIFICATION-TYPE
    OBJECTS { starThreshInt, starThreshMeasuredInt }
    STATUS current
    DESCRIPTION 
        "The threshold condition is now clear."
    --#SUMMARY "[System] Threshold: FNG Current Sessions CLEAR; measured %d threshold %d"
    --#ARGUMENTS {1,0}
    --#STATE OPERATIONAL
    --#SEVERITY INFORMATIONAL
    ::= { starentTraps 417 }


starThreshFNGCurrActSess NOTIFICATION-TYPE
    OBJECTS { starThreshInt, starThreshMeasuredInt }
    STATUS current
    DESCRIPTION
         "The chassis-wide count of current FNG active sessions has gone above the configured threshold
 
          Probable Cause: This is a user configurable threshold.
 
          If the thresholding subsystem is configured to run in an 'alarm' model,
 	 a starThreshClearFNGCurrActiveSess notification will be generated when the measured
 	 value falls below the threshold."
    --#SUMMARY "[System] Threshold: FNG Current Active Sessions; measured %d threshold %d"
    --#ARGUMENTS {1,0}
    --#STATE OPERATIONAL
    --#SEVERITY WARNING
    ::= { starentTraps 418 }
 
starThreshClearFNGCurrActSess NOTIFICATION-TYPE
    OBJECTS { starThreshInt, starThreshMeasuredInt }
    STATUS current
    DESCRIPTION 
 	"The threshold condition is now clear."
    --#SUMMARY "[System] Threshold: FNG Current Active Sessions CLEAR; measured %d threshold %d"
    --#ARGUMENTS {1,0}
    --#STATE OPERATIONAL
    --#SEVERITY INFORMATIONAL
    ::= { starentTraps 419 }

starThreshPHSGWEAPOLAuthFailure NOTIFICATION-TYPE
    OBJECTS { starThreshInt, starThreshMeasuredInt }
    STATUS current
    DESCRIPTION
	"The number of PHSGW EAPOL Auth Failure has exceeded the configured threshold
	 during the current monitoring period.

         Probable Cause: This is a user configurable threshold.

         If the thresholding subsystem is configured to run in an 'alarm' model,
         a starThreshPHSGWEAPOLAuthFailure notification will be generated when the measured
	 value falls below the threshold."
    --#SUMMARY "[System] Threshold: PHSGW EAPOL Auth Failure threshold; measured %d threshold %d"
    --#ARGUMENTS {1,0}
    --#STATE OPERATIONAL
    --#SEVERITY WARNING
    ::= { starentTraps 420 }

starThreshClearPHSGWEAPOLAuthFailure NOTIFICATION-TYPE
    OBJECTS { starThreshInt, starThreshMeasuredInt }
    STATUS current
    DESCRIPTION
	"The threshold condition is now clear."
    --#SUMMARY "[System] Threshold: PHSGW EAPOL Auth Failure threshold CLEAR; measured %d threshold %d"
    --#ARGUMENTS {1,0}
    --#STATE OPERATIONAL
    --#SEVERITY WARNING
    ::= { starentTraps 421 }

starThreshPHSGWMaxEAPOLRetry NOTIFICATION-TYPE
    OBJECTS { starThreshInt, starThreshMeasuredInt }
    STATUS current
    DESCRIPTION
	"The number of PHSGW max EAPOL retry has exceeded the configured threshold
	 during the current monitoring period.

         Probable Cause: This is a user configurable threshold.

         If the thresholding subsystem is configured to run in an 'alarm' model,
         a starThreshPHSGWMaxEAPOLRetry notification will be generated when the measured
	 value falls below the threshold."
    --#SUMMARY "[System] Threshold: PHSGW max EAPOL retry threshold; measured %d threshold %d"
    --#ARGUMENTS {1,0}
    --#STATE OPERATIONAL
    --#SEVERITY WARNING
    ::= { starentTraps 422 }

starThreshClearPHSGWMaxEAPOLRetry NOTIFICATION-TYPE
    OBJECTS { starThreshInt, starThreshMeasuredInt }
    STATUS obsolete
    DESCRIPTION
	"The threshold condition is now clear."
    --#SUMMARY "[System] Threshold: PHSGW max EAPOL retry threshold CLEAR; measured %d threshold %d"
    --#ARGUMENTS {1,0}
    --#STATE OPERATIONAL
    --#SEVERITY WARNING
    ::= { starentTraps 423 }

starThreshHSGWSessions NOTIFICATION-TYPE
    OBJECTS { starThreshInt, starThreshMeasuredInt }
    STATUS current
    DESCRIPTION
        "The total number of HSGW sessions is above the configured threshold value.

         Probable Cause: This is a user configurable threshold.

         If the thresholding subsystem is configured to run in an 'alarm' model,
         a starThreshClearHSGWSessions notification will be generated when the measured
         value falls below the threshold."
    --#SUMMARY "[System] Threshold: Total HSGW Sessions; measured %d threshold %d"
    --#ARGUMENTS {1,0}
    --#STATE OPERATIONAL
    --#SEVERITY WARNING
    ::= { starentTraps 424 }

starThreshClearHSGWSessions NOTIFICATION-TYPE
    OBJECTS { starThreshInt, starThreshMeasuredInt }
    STATUS current
    DESCRIPTION
        "The threshold condition is now clear."
    --#SUMMARY "[System] Threshold: Total HSGW Sessions CLEAR; measured %d threshold %d"
    --#ARGUMENTS {1,0}
    --#STATE OPERATIONAL
    --#SEVERITY INFORMATIONAL
    ::= { starentTraps 425 }

starThreshPDGCurrSess NOTIFICATION-TYPE
    OBJECTS { starThreshInt, starThreshMeasuredInt }
    STATUS current
    DESCRIPTION
        "The chassis-wide count of current PDG sessions has gone above the configured threshold

        Probable Cause: This is a user configurable threshold.

        If the thresholding subsystem is configured to run in an 'alarm' model,
        a starThreshClearPDGCurrSess notification will be generated when the measured
        value falls below the threshold."
    --#SUMMARY "[System] Threshold: PDG Current Sessions; measured %d threshold %d"
    --#ARGUMENTS {1,0}
    --#STATE OPERATIONAL
    --#SEVERITY WARNING
    ::= { starentTraps 426 }

starThreshClearPDGCurrSess NOTIFICATION-TYPE
    OBJECTS { starThreshInt, starThreshMeasuredInt }
    STATUS current
    DESCRIPTION 
        "The threshold condition is now clear."
    --#SUMMARY "[System] Threshold: PDG Current Sessions CLEAR; measured %d threshold %d"
    --#ARGUMENTS {1,0}
    --#STATE OPERATIONAL
    --#SEVERITY INFORMATIONAL
    ::= { starentTraps 427 }

starThreshPDGCurrActSess NOTIFICATION-TYPE
    OBJECTS { starThreshInt, starThreshMeasuredInt }
    STATUS current
    DESCRIPTION
         "The chassis-wide count of current PDG active sessions has gone above the configured threshold
 
          Probable Cause: This is a user configurable threshold.
 
          If the thresholding subsystem is configured to run in an 'alarm' model,
 	 a starThreshClearPDGCurrActiveSess notification will be generated when the measured
 	 value falls below the threshold."
    --#SUMMARY "[System] Threshold: PDG Current Active Sessions; measured %d threshold %d"
    --#ARGUMENTS {1,0}
    --#STATE OPERATIONAL
    --#SEVERITY WARNING
    ::= { starentTraps 428 }
 
starThreshClearPDGCurrActSess NOTIFICATION-TYPE
    OBJECTS { starThreshInt, starThreshMeasuredInt }
    STATUS current
    DESCRIPTION 
 	"The threshold condition is now clear."
    --#SUMMARY "[System] Threshold: PDG Current Active Sessions CLEAR; measured %d threshold %d"
    --#ARGUMENTS {1,0}
    --#STATE OPERATIONAL
    --#SEVERITY INFORMATIONAL
    ::= { starentTraps 429 }

starThreshNATPortChunks NOTIFICATION-TYPE
    OBJECTS { starIPPoolContext,starIPPoolName, starThreshPct, starThreshMeasuredPct }
    STATUS  current
    DESCRIPTION
	"The NAT port chunks utilization of NAT pool is above the configured 
         threshold value.

         Probable Cause: This is a user configurable threshold.
         
         If the thresholding subsystem is configured to run in an 'alarm' model,
         a starThreshClearNATPortChunks notification will be generated when the measured
	 value exceeds the threshold."
    --#SUMMARY "[System] Threshold: NAT port chunk utilization in context %s for pool %s threshold %d%% measured %d%%"
    --#ARGUMENTS {0,1,2,3}
    --#STATE OPERATIONAL
    --#SEVERITY WARNING
    ::= { starentTraps 430 }

starThreshClearNATPortChunks NOTIFICATION-TYPE
    OBJECTS { starIPPoolContext,starIPPoolName, starThreshPct, starThreshMeasuredPct }
    STATUS current
    DESCRIPTION 
	"The threshold condition is now clear."
    --#SUMMARY "[System] Threshold: NAT port chunk utilization threshold clear in context %s pool %s threshold %d%% measured %d%%"
    --#ARGUMENTS {0,1,2,3}
    --#STATE OPERATIONAL
    --#SEVERITY INFORMATIONAL
    ::= { starentTraps 431 }

  starThreshGPRSSessions NOTIFICATION-TYPE
    OBJECTS { starThreshInt, starThreshMeasuredInt }
    STATUS current
    DESCRIPTION
    "The total number of GPRS sessions is above the configured threshold value."
    --#SUMMARY "[System] Threshold: Total GPRS Sessions; measured %d threshold %d"
    --#ARGUMENTS {1,0}
    --#STATE OPERATIONAL
    --#SEVERITY WARNING
    ::= { starentTraps 432 }

  starThreshClearGPRSSessions NOTIFICATION-TYPE
    OBJECTS { starThreshInt, starThreshMeasuredInt }
    STATUS current
    DESCRIPTION
    "The threshold condition is now clear."
    --#SUMMARY "[System] Threshold: Total GPRS Sessions CLEAR; measured %d threshold %d"
    --#ARGUMENTS {1,0}
    --#STATE OPERATIONAL
    --#SEVERITY INFORMATIONAL
    ::= { starentTraps 433 }

 starThreshPerServiceGPRSSessions NOTIFICATION-TYPE
    OBJECTS { starServiceVpnName, starServiceServName, starThreshInt, starThreshMeasuredInt }
    STATUS current
    DESCRIPTION
    "The total number of GPRS sessions in a service is above the configured threshold value."
    --#SUMMARY "[System] Threshold: Per Sevice SGSN Sessions, context %s service name %s; measured %d threshold %d"
    --#ARGUMENTS {0,1,3,2}
    --#STATE OPERATIONAL
    --#SEVERITY WARNING
    ::= { starentTraps 434 }

 starThreshClearPerServiceGPRSSessions NOTIFICATION-TYPE
    OBJECTS { starServiceVpnName, starServiceServName, starThreshInt, starThreshMeasuredInt }
    STATUS current
    DESCRIPTION
    "The threshold condition is now clear."
    --#SUMMARY "[System] Threshold: Per Sevice GPRS Sessions CLEAR, context %s service name %s; measured %d threshold %d"
    --#ARGUMENTS {0,1,3,2}
    --#STATE OPERATIONAL
    --#SEVERITY INFORMATIONAL
    ::= { starentTraps 435 }

  starThreshGPRSPdpSessions NOTIFICATION-TYPE
    OBJECTS { starThreshInt, starThreshMeasuredInt }
    STATUS current
    DESCRIPTION
    "The total number of GPRS PDP sessions is above the configured threshold value."
    --#SUMMARY "[System] Threshold: Total GPRS PDP Sessions; measured %d threshold %d"
    --#ARGUMENTS {1,0}
    --#STATE OPERATIONAL
    --#SEVERITY WARNING
    ::= { starentTraps 436 }

  starThreshClearGPRSPdpSessions NOTIFICATION-TYPE
    OBJECTS { starThreshInt, starThreshMeasuredInt }
    STATUS current
    DESCRIPTION
    "The threshold condition is now clear."
    --#SUMMARY "[System] Threshold: Total GPRS PDP Sessions CLEAR; measured %d threshold %d"
    --#ARGUMENTS {1,0}
    --#STATE OPERATIONAL
    --#SEVERITY INFORMATIONAL
    ::= { starentTraps 437 }


  starThreshPerServiceGPRSPdpSessions NOTIFICATION-TYPE
    OBJECTS { starServiceVpnName, starServiceServName, starThreshInt, starThreshMeasuredInt }
    STATUS current
    DESCRIPTION
    "The total number of GPRS PDP sessions in a service is above the configured threshold value."
    --#SUMMARY "[System] Threshold: Per Sevice GPRS PDP Sessions, context %s service name %s; measured %d threshold %d"
    --#ARGUMENTS {0,1,3,2}
    --#STATE OPERATIONAL
    --#SEVERITY WARNING
    ::= { starentTraps 438 }

  starThreshClearPerServiceGPRSPdpSessions NOTIFICATION-TYPE
    OBJECTS { starServiceVpnName, starServiceServName, starThreshInt, starThreshMeasuredInt }
    STATUS current
    DESCRIPTION
    "The threshold condition is now clear."
    --#SUMMARY "[System] Threshold: Per Sevice GPRS PDP Sessions CLEAR, context %s service name %s; measured %d threshold %d"
    --#ARGUMENTS {0,1,3,2}
    --#STATE OPERATIONAL
    --#SEVERITY INFORMATIONAL
    ::= { starentTraps 439 }

starThreshMMESessions NOTIFICATION-TYPE

    OBJECTS { starThreshInt, starThreshMeasuredInt }
    STATUS current
    DESCRIPTION
        "The total number of subscribers is above the configured threshold value.

         Probable Cause: This is a user configurable threshold.

         If the thresholding subsystem is configured to run in an 'alarm' model,
         a starThreshClearMMESessions notification will be generated when the measured
         value falls below the threshold."
    --#SUMMARY "[System] Threshold: Session total threshold  measured %d threshold %d"
    --#ARGUMENTS {0,1}
    --#STATE OPERATIONAL
    --#SEVERITY WARNING
    ::= { starentTraps 440 }

starThreshClearMMESessions NOTIFICATION-TYPE
    OBJECTS { starThreshInt, starThreshMeasuredInt }
    STATUS current
    DESCRIPTION
    "The threshold condition is now clear."
    --#SUMMARY "[System] Threshold: Total MME Sessions CLEAR; measured %d threshold %d"
    --#ARGUMENTS {0,1}
    --#STATE OPERATIONAL
    --#SEVERITY INFORMATIONAL
    ::= { starentTraps 441 }

starThreshMMEAuthFail NOTIFICATION-TYPE
    OBJECTS { starThreshInt, starThreshMeasuredInt }
    STATUS current
    DESCRIPTION
        "The total number of subscribers is above the configured threshold value.

         Probable Cause: This is a user configurable threshold.

         If the thresholding subsystem is configured to run in an 'alarm' model,
         a starThreshClearMMEAuthFail notification will be generated when the measured
         value falls below the threshold."
    --#SUMMARY "[System] Threshold: MME Auth Fail measured %d threshold %d"
    --#ARGUMENTS {0,1}
    --#STATE OPERATIONAL
    --#SEVERITY WARNING
    ::= { starentTraps 442 }

starThreshClearMMEAuthFail NOTIFICATION-TYPE
    OBJECTS { starThreshInt, starThreshMeasuredInt }
    STATUS current
    DESCRIPTION
    "The threshold condition is now clear."
    --#SUMMARY "[System] Threshold: Total MME Auth Fail CLEAR; measured %d threshold %d"
    --#ARGUMENTS {0,1}
    --#STATE OPERATIONAL
    --#SEVERITY INFORMATIONAL
    ::= { starentTraps 443 }

starThreshMMEAttachFail NOTIFICATION-TYPE
    OBJECTS { starThreshInt, starThreshMeasuredInt }
    STATUS current
    DESCRIPTION
        "The total number of subscribers is above the configured threshold value.

         Probable Cause: This is a user configurable threshold.

         If the thresholding subsystem is configured to run in an 'alarm' model,
         a starThreshClearMMEAttachFail notification will be generated when the measured
         value falls below the threshold."
    --#SUMMARY "[System] Threshold: MME AttachFail measured %d threshold %d"
    --#ARGUMENTS {0,1}
    --#STATE OPERATIONAL
    --#SEVERITY WARNING
    ::= { starentTraps 444 }

starThreshClearMMEAttachFail NOTIFICATION-TYPE
    OBJECTS { starThreshInt, starThreshMeasuredInt }
    STATUS current
    DESCRIPTION
    "The threshold condition is now clear."
    --#SUMMARY "[System] Threshold: Total MME Attach Fail CLEAR; measured %d threshold %d"
    --#ARGUMENTS {0,1}
    --#STATE OPERATIONAL
    --#SEVERITY INFORMATIONAL
    ::= { starentTraps 445 }

starThreshCSCFSvcRegRcvdRate NOTIFICATION-TYPE
    OBJECTS { starServiceVpnName, starServiceServName, starThreshInt, starThreshMeasuredInt }
    STATUS current
    DESCRIPTION
        "The Per-Service CSCF Registration Per Interval  count has gone above the configured threshold

         Probable Cause: This is a user configurable threshold.

         If the thresholding subsystem is configured to run in an 'alarm' model,
	 a starThreshClearCSCFSvcRegRcvdRate notification will be generated when the measured
	 value falls below the threshold."
    --#SUMMARY "[Service CSCF-%s-%s] Threshold: CSCF Per-Service Registrations Per Interval; measured %d threshold %d"
    --#ARGUMENTS {0,1,3,2}
    --#STATE OPERATIONAL
    --#SEVERITY WARNING
    ::= { starentTraps 446 }

starThreshClearCSCFSvcRegRcvdRate NOTIFICATION-TYPE
    OBJECTS { starServiceVpnName, starServiceServName, starThreshInt, starThreshMeasuredInt }
    STATUS current
    DESCRIPTION 
	"The threshold condition is now clear."
    --#SUMMARY "[Service CSCF-%s-%s] Threshold: CSCF Per-Service Registrations Per Interval CLEAR; measured %d threshold %d"
    --#ARGUMENTS {0,1,3,2}
    --#STATE OPERATIONAL
    --#SEVERITY INFORMATIONAL
    ::= { starentTraps 447 }


starThreshCSCFSvcTotalActiveReg NOTIFICATION-TYPE
    OBJECTS { starServiceVpnName, starServiceServName, starThreshInt, starThreshMeasuredInt }
    STATUS current
    DESCRIPTION
        "The Per-Service CSCF Total Active Registrations count has gone above the configured threshold

         Probable Cause: This is a user configurable threshold.

         If the thresholding subsystem is configured to run in an 'alarm' model,
	 a starThreshClearCSCFSvcTotalActiveReg notification will be generated when the measured
	 value falls below the threshold."
    --#SUMMARY "[Service CSCF-%s-%s] Threshold: CSCF Per-Service Total Active Registrations; measured %d threshold %d"
    --#ARGUMENTS {0,1,3,2}
    --#STATE OPERATIONAL
    --#SEVERITY WARNING
    ::= { starentTraps 448 }

starThreshClearCSCFSvcTotalActiveReg NOTIFICATION-TYPE
    OBJECTS { starServiceVpnName, starServiceServName, starThreshInt, starThreshMeasuredInt }
    STATUS current
    DESCRIPTION 
	"The threshold condition is now clear."
    --#SUMMARY "[Service CSCF-%s-%s] Threshold: CSCF Per-Service Total Active Registrations CLEAR; measured %d threshold %d"
    --#ARGUMENTS {0,1,3,2}
    --#STATE OPERATIONAL
    --#SEVERITY INFORMATIONAL
    ::= { starentTraps 449 }


starThreshCSCFSvcInviteRcvdRate NOTIFICATION-TYPE
    OBJECTS { starServiceVpnName, starServiceServName, starThreshInt, starThreshMeasuredInt }
    STATUS current
    DESCRIPTION
        "The Per-Service CSCF Calls Per Interval count has gone above the configured threshold

        Probable Cause: This is a user configurable threshold.

         If the thresholding subsystem is configured to run in an 'alarm' model,
	 a starThreshClearCSCFSvcInviteRcvdRate notification will be generated when the measured
	 value falls below the threshold."
    --#SUMMARY "[Service CSCF-%s-%s] Threshold: CSCF Per-Service Calls Per Interval ; measured %d threshold %d"
    --#ARGUMENTS {0,1,3,2}
    --#STATE OPERATIONAL
    --#SEVERITY WARNING
    ::= { starentTraps 450 }

starThreshClearCSCFSvcInviteRcvdRate NOTIFICATION-TYPE
    OBJECTS { starServiceVpnName, starServiceServName, starThreshInt, starThreshMeasuredInt }
    STATUS current
    DESCRIPTION 
	"The threshold condition is now clear."
    --#SUMMARY "[Service CSCF-%s-%s] Threshold: CSCF Per-Service Calls Per Interval CLEAR; measured %d threshold %d"
    --#ARGUMENTS {0,1,3,2}
    --#STATE OPERATIONAL
    --#SEVERITY INFORMATIONAL
    ::= { starentTraps 451 }


starThreshCSCFSvcTotalActiveCalls NOTIFICATION-TYPE
    OBJECTS { starServiceVpnName, starServiceServName, starThreshInt, starThreshMeasuredInt }
    STATUS current
    DESCRIPTION
        "The Per-Service CSCF Total Active Calls count has gone above the configured threshold

         Probable Cause: This is a user configurable threshold.

         If the thresholding subsystem is configured to run in an 'alarm' model,
	 a starThreshClearCSCFSvcTotalActiveCalls notification will be generated when the measured
	 value falls below the threshold."
    --#SUMMARY "[Service CSCF-%s-%s] Threshold: CSCF Per-Service Total Active Calls; measured %d threshold %d"
    --#ARGUMENTS {0,1,3,2}
    --#STATE OPERATIONAL
    --#SEVERITY WARNING
    ::= { starentTraps 452 }

starThreshClearCSCFSvcTotalActiveCalls NOTIFICATION-TYPE
    OBJECTS { starServiceVpnName, starServiceServName, starThreshInt, starThreshMeasuredInt }
    STATUS current
    DESCRIPTION 
	"The threshold condition is now clear."
    --#SUMMARY "[Service CSCF-%s-%s] Threshold: CSCF Per-Service Total Active Calls CLEAR; measured %d threshold %d"
    --#ARGUMENTS {0,1,3,2}
    --#STATE OPERATIONAL
    --#SEVERITY INFORMATIONAL
    ::= { starentTraps 453 }

starThreshCSCFSvcTotalCallFailure NOTIFICATION-TYPE
    OBJECTS { starServiceVpnName, starServiceServName, starThreshInt, starThreshMeasuredInt }
    STATUS current
    DESCRIPTION
        "The Per-Service CSCF Total Call Failure count has gone above the configured threshold

         Probable Cause: This is a user configurable threshold.

         If the thresholding subsystem is configured to run in an 'alarm' model,
	 a starThreshClearCSCFSvcTotalCallFailure notification will be generated when the measured
	 value falls below the threshold."
    --#SUMMARY "[Service CSCF-%s-%s] Threshold: CSCF Per-Service Total Call Failure; measured %d threshold %d"
    --#ARGUMENTS {0,1,3,2}
    --#STATE OPERATIONAL
    --#SEVERITY WARNING
    ::= { starentTraps 454 }

starThreshClearCSCFSvcTotalCallFailure NOTIFICATION-TYPE
    OBJECTS { starServiceVpnName, starServiceServName, starThreshInt, starThreshMeasuredInt }
    STATUS current
    DESCRIPTION 
	"The threshold condition is now clear."
    --#SUMMARY "[Service CSCF-%s-%s] Threshold: CSCF Per-Service Total Call Failure CLEAR; measured %d threshold %d"
    --#ARGUMENTS {0,1,3,2}
    --#STATE OPERATIONAL
    --#SEVERITY INFORMATIONAL
    ::= { starentTraps 455 }


starThreshCSCFSvcErrorNoResource NOTIFICATION-TYPE
    OBJECTS { starServiceVpnName, starServiceServName, starThreshInt, starThreshMeasuredInt }
    STATUS current
    DESCRIPTION
        "The Per-Service CSCF No resource failure count has gone above the configured threshold

         Probable Cause: This is a user configurable threshold.

         If the thresholding subsystem is configured to run in an 'alarm' model,
	 a starThreshClearCSCFSvcErrorNoResource notification will be generated when the measured
	 value falls below the threshold."
    --#SUMMARY "[Service CSCF-%s-%s] Threshold: CSCF Per-Service No resourse failure; measured %d threshold %d"
    --#ARGUMENTS {0,1,3,2}
    --#STATE OPERATIONAL
    --#SEVERITY WARNING
    ::= { starentTraps 456 }

starThreshClearCSCFSvcErrorNoResource NOTIFICATION-TYPE
    OBJECTS { starServiceVpnName, starServiceServName, starThreshInt, starThreshMeasuredInt }
    STATUS current
    DESCRIPTION 
	"The threshold condition is now clear."
    --#SUMMARY "[Service CSCF-%s-%s] Threshold: CSCF Per-Service No resource failure CLEAR; measured %d threshold %d"
    --#ARGUMENTS {0,1,3,2}
    --#STATE OPERATIONAL
    --#SEVERITY INFORMATIONAL
    ::= { starentTraps 457 }


starThreshCSCFSvcErrorTcp NOTIFICATION-TYPE
    OBJECTS { starServiceVpnName, starServiceServName, starThreshInt, starThreshMeasuredInt }
    STATUS current
    DESCRIPTION
        "The Per-Service CSCF Tcp failure count has gone above the configured threshold
        
        Probable Cause: This is a user configurable threshold.

         If the thresholding subsystem is configured to run in an 'alarm' model,
	 a starThreshClearCSCFSvcErrorTcp notification will be generated when the measured
	 value falls below the threshold."
    --#SUMMARY "[Service CSCF-%s-%s] Threshold: CSCF Per-Service Tcp failure; measured %d threshold %d"
    --#ARGUMENTS {0,1,3,2}
    --#STATE OPERATIONAL
    --#SEVERITY WARNING
    ::= { starentTraps 458 }

starThreshClearCSCFSvcErrorTcp NOTIFICATION-TYPE
    OBJECTS { starServiceVpnName, starServiceServName, starThreshInt, starThreshMeasuredInt }
    STATUS current
    DESCRIPTION 
	"The threshold condition is now clear."
    --#SUMMARY "[Service CSCF-%s-%s] Threshold: CSCF Per-Service Tcp failure CLEAR; measured %d threshold %d"
    --#ARGUMENTS {0,1,3,2}
    --#STATE OPERATIONAL
    --#SEVERITY INFORMATIONAL
    ::= { starentTraps 459 }


starThreshCSCFSvcErrorPresence NOTIFICATION-TYPE
    OBJECTS { starServiceVpnName, starServiceServName, starThreshInt, starThreshMeasuredInt }
    STATUS current
    DESCRIPTION
        "The Per-Service CSCF Presence failure count has gone above the configured threshold

         Probable Cause: This is a user configurable threshold.

         If the thresholding subsystem is configured to run in an 'alarm' model,
	 a starThreshClearCSCFSvcErrorPresence notification will be generated when the measured
	 value falls below the threshold."
    --#SUMMARY "[Service CSCF-%s-%s] Threshold: CSCF Per-Service Presence failure; measured %d threshold %d"
    --#ARGUMENTS {0,1,3,2}
    --#STATE OPERATIONAL
    --#SEVERITY WARNING
    ::= { starentTraps 460 }

starThreshClearCSCFSvcErrorPresence NOTIFICATION-TYPE
    OBJECTS { starServiceVpnName, starServiceServName, starThreshInt, starThreshMeasuredInt }
    STATUS current
    DESCRIPTION 
	"The threshold condition is now clear."
    --#SUMMARY "[Service CSCF-%s-%s] Threshold: CSCF Per-Service Presence failure CLEAR; measured %d threshold %d"
    --#ARGUMENTS {0,1,3,2}
    --#STATE OPERATIONAL
    --#SEVERITY INFORMATIONAL
    ::= { starentTraps 461 }


starThreshCSCFSvcErrorRegAuth NOTIFICATION-TYPE
    OBJECTS { starServiceVpnName, starServiceServName, starThreshInt, starThreshMeasuredInt }
    STATUS current
    DESCRIPTION
        "The Per-Service CSCF Reg-Auth failure count has gone above the configured threshold

         Probable Cause: This is a user configurable threshold.

         If the thresholding subsystem is configured to run in an 'alarm' model,
	 a starThreshClearCSCFSvcErrorRegAuth notification will be generated when the measured
	 value falls below the threshold."
    --#SUMMARY "[Service CSCF-%s-%s] Threshold: CSCF Per-Service Reg-Auth failure; measured %d threshold %d"
    --#ARGUMENTS {0,1,3,2}
    --#STATE OPERATIONAL
    --#SEVERITY WARNING
    ::= { starentTraps 462 }

starThreshClearCSCFSvcErrorRegAuth NOTIFICATION-TYPE
    OBJECTS { starServiceVpnName, starServiceServName, starThreshInt, starThreshMeasuredInt }
    STATUS current
    DESCRIPTION 
	"The threshold condition is now clear."
    --#SUMMARY "[Service CSCF-%s-%s] Threshold: CSCF Per-Service Reg-Auth failure CLEAR; measured %d threshold %d"
    --#ARGUMENTS {0,1,3,2}
    --#STATE OPERATIONAL
    --#SEVERITY INFORMATIONAL
    ::= { starentTraps 463 }

starThreshBGPRoutes NOTIFICATION-TYPE
    OBJECTS { starServiceVpnName, starThreshPct, starThreshMeasuredPct }
    STATUS current
    DESCRIPTION
        "The Total number of BGP routes  is above the configured threshold value.

         Probable Cause: This is a user configurable threshold.

         If the thresholding subsystem is configured to run in an 'alarm' model,
         a starThreshClearBGPRoutes notification will be generated when the measured
         value falls below the threshold."
    --#SUMMARY "[System] Threshold: maximum routes for context %s threshold %d%% measured %d%%"
    --#ARGUMENTS {0,1,2}
    --#STATE OPERATIONAL
    --#SEVERITY WARNING
    ::= { starentTraps 464 }

starThreshClearBGPRoutes NOTIFICATION-TYPE
    OBJECTS { starServiceVpnName, starThreshPct, starThreshMeasuredPct }
    STATUS current
    DESCRIPTION
        "The threshold condition is now clear."
    --#SUMMARY "[System] Threshold: maximum routes clear for context %s threshold %d%% measured %d%%"
    --#ARGUMENTS {0,1,2}
    --#STATE OPERATIONAL
    --#SEVERITY INFORMATIONAL
    ::= { starentTraps 465 }

starThreshPCCPolicySessions NOTIFICATION-TYPE
    OBJECTS { starThreshInt, starThreshMeasuredInt }
    STATUS current
    DESCRIPTION
  "The total number of PCC-Policy sessions is above the configured threshold value."
    --#SUMMARY "[System] Threshold: Total PCC-Policy Sessions; measured %d threshold %d"
    --#ARGUMENTS {1,0}
    --#STATE OPERATIONAL
    --#SEVERITY WARNING
    ::= { starentTraps 466 }

starThreshClearPCCPolicySessions NOTIFICATION-TYPE
    OBJECTS { starThreshInt, starThreshMeasuredInt }
    STATUS current
    DESCRIPTION
  "The threshold condition is now clear."
    --#SUMMARY "[System] Threshold: Total PCC-Policy Sessions CLEAR; measured %d threshold %d"
    --#ARGUMENTS {1,0}
    --#STATE OPERATIONAL
    --#SEVERITY INFORMATIONAL
    ::= { starentTraps 467 }

starThreshPerServicePCCPolicySessions NOTIFICATION-TYPE
    OBJECTS { starServiceVpnName, starServiceServName, starThreshInt, starThreshMeasuredInt }
    STATUS current
    DESCRIPTION
  "The total number of PCC-Policy sessions in a service is above the configured threshold value."
    --#SUMMARY "[System] Threshold: Per Sevice PCC-Policy Sessions, context %s service name %s; measured %d threshold %d"
    --#ARGUMENTS {0,1,3,2}
    --#STATE OPERATIONAL
    --#SEVERITY WARNING
    ::= { starentTraps 468 }

starThreshClearPerServicePCCPolicySessions NOTIFICATION-TYPE
    OBJECTS { starServiceVpnName, starServiceServName, starThreshInt, starThreshMeasuredInt }
    STATUS current
    DESCRIPTION
  "The threshold condition is now clear."
    --#SUMMARY "[System] Threshold: Per Sevice PCC-Policy Sessions CLEAR, context %s service name %s; measured %d threshold %d"
    --#ARGUMENTS {0,1,3,2}
    --#STATE OPERATIONAL
    --#SEVERITY INFORMATIONAL
    ::= { starentTraps 469 }

starThreshPCCQuotaSessions NOTIFICATION-TYPE
    OBJECTS { starThreshInt, starThreshMeasuredInt }
    STATUS current
    DESCRIPTION
  "The total number of PCC-Quota sessions is above the configured threshold value."
    --#SUMMARY "[System] Threshold: Total PCC-Quota Sessions; measured %d threshold %d"
    --#ARGUMENTS {1,0}
    --#STATE OPERATIONAL
    --#SEVERITY WARNING
    ::= { starentTraps 470 }

starThreshClearPCCQuotaSessions NOTIFICATION-TYPE
    OBJECTS { starThreshInt, starThreshMeasuredInt }
    STATUS current
    DESCRIPTION
  "The threshold condition is now clear."
    --#SUMMARY "[System] Threshold: Total PCC-Quota Sessions CLEAR; measured %d threshold %d"
    --#ARGUMENTS {1,0}
    --#STATE OPERATIONAL
    --#SEVERITY INFORMATIONAL
    ::= { starentTraps 471 }

starThreshPerServicePCCQuotaSessions NOTIFICATION-TYPE
    OBJECTS { starServiceVpnName, starServiceServName, starThreshInt, starThreshMeasuredInt }
    STATUS current
    DESCRIPTION
  "The total number of PCC-Quota sessions in a service is above the configured threshold value."
    --#SUMMARY "[System] Threshold: Per Sevice PCC-Quota Sessions, context %s service name %s; measured %d threshold %d"
    --#ARGUMENTS {0,1,3,2}
    --#STATE OPERATIONAL
    --#SEVERITY WARNING
    ::= { starentTraps 472 }

starThreshClearPerServicePCCQuotaSessions NOTIFICATION-TYPE
    OBJECTS { starServiceVpnName, starServiceServName, starThreshInt, starThreshMeasuredInt }
    STATUS current
    DESCRIPTION
  "The threshold condition is now clear."
    --#SUMMARY "[System] Threshold: Per Sevice PCC-Quota Sessions CLEAR, context %s service name %s; measured %d threshold %d"
    --#ARGUMENTS {0,1,3,2}
    --#STATE OPERATIONAL
    --#SEVERITY INFORMATIONAL
    ::= { starentTraps 473 }

starThreshPCCAFSessions NOTIFICATION-TYPE
    OBJECTS { starThreshInt, starThreshMeasuredInt }
    STATUS current
    DESCRIPTION
  "The total number of PCC-AF sessions is above the configured threshold value."
    --#SUMMARY "[System] Threshold: Total PCC-AF Sessions; measured %d threshold %d"
    --#ARGUMENTS {1,0}
    --#STATE OPERATIONAL
    --#SEVERITY WARNING
    ::= { starentTraps 474 }

starThreshClearPCCAFSessions NOTIFICATION-TYPE
    OBJECTS { starThreshInt, starThreshMeasuredInt }
    STATUS current
    DESCRIPTION
  "The threshold condition is now clear."
    --#SUMMARY "[System] Threshold: Total PCC-AF Sessions CLEAR; measured %d threshold %d"
    --#ARGUMENTS {1,0}
    --#STATE OPERATIONAL
    --#SEVERITY INFORMATIONAL
    ::= { starentTraps 475 }

starThreshPerServicePCCAFSessions NOTIFICATION-TYPE
    OBJECTS { starServiceVpnName, starServiceServName, starThreshInt, starThreshMeasuredInt }
    STATUS current
    DESCRIPTION
  "The total number of PCC-AF sessions in a service is above the configured threshold value."
    --#SUMMARY "[System] Threshold: Per Sevice PCC-AF Sessions, context %s service name %s; measured %d threshold %d"
    --#ARGUMENTS {0,1,3,2}
    --#STATE OPERATIONAL
    --#SEVERITY WARNING
    ::= { starentTraps 476 }

starThreshClearPerServicePCCAFSessions NOTIFICATION-TYPE
    OBJECTS { starServiceVpnName, starServiceServName, starThreshInt, starThreshMeasuredInt }
    STATUS current
    DESCRIPTION
  "The threshold condition is now clear."
    --#SUMMARY "[System] Threshold: Per Sevice PCC-AF Sessions CLEAR, context %s service name %s; measured %d threshold %d"
    --#ARGUMENTS {0,1,3,2}
    --#STATE OPERATIONAL
    --#SEVERITY INFORMATIONAL
    ::= { starentTraps 477 }

starThreshNPUUtilization NOTIFICATION-TYPE
    OBJECTS { starNPUSlot, starThreshPct, starThreshMeasuredPct }
    STATUS current
    DESCRIPTION
        "The overall NPU utilization for the identified processor has exceeded for 
         configured threshold value for the current monitoring period.

         Probable Cause: This is a user configurable threshold.

         If the thresholding subsystem is configured to run in an 'alarm' model,
         a starThreshClearNPUUtilization notification will be generated when the measured
         value falls below the threshold.This is not applicable to QVPC-SI and QVPC-DI."
    --#SUMMARY "[Card] Threshold: NPU utilization threshold for card %d threshold %d%% measured %d%%"
    --#ARGUMENTS {0,1,2}
    --#STATE OPERATIONAL
    --#SEVERITY WARNING
    ::= { starentTraps 478 }

starThreshClearNPUUtilization NOTIFICATION-TYPE
    OBJECTS { starNPUSlot, starThreshPct, starThreshMeasuredPct }
    STATUS current
    DESCRIPTION
        "The threshold condition is now clear.This is not applicable to QVPC-SI and QVPC-DI."
    --#SUMMARY "[Card] Threshold: NPU utilization threshold clear for card %d threshold %d%% measured %d%%"
    --#ARGUMENTS {0,1,2}
    --#STATE OPERATIONAL
    --#SEVERITY INFORMATIONAL
    ::= { starentTraps 479 }
 
starThreshDnsLookupFailure NOTIFICATION-TYPE
    OBJECTS { starServiceVpnName, starThreshPct, starThreshMeasuredPct }
    STATUS current
    DESCRIPTION
	"The Total number of DNS lookup failures  is above the configured threshold value.
	
	  Probable Cause: This is a user configurable threshold.
	  
	  If the thresholding subsystem is configured to run in an 'alarm' model,
	  a starThreshClearDnsLookupFailure notification will be generated when the measured
	  value falls below the threshold."
    --#SUMMARY "[System] Threshold: DNS lookup failure for context %s threshold %d%% measured %d%%"
    --#ARGUMENTS {0,1,2}
    --#STATE OPERATIONAL
    --#SEVERITY WARNING
    ::= { starentTraps 480 }
    
starThreshClearDnsLookupFailure NOTIFICATION-TYPE
    OBJECTS { starServiceVpnName, starThreshPct, starThreshMeasuredPct }
    STATUS current
    DESCRIPTION
	"The threshold condition is now clear."
    --#SUMMARY "[System] Threshold: DNS lookup failure clear for context %s threshold %d%% measured %d%%"
    --#ARGUMENTS {0,1,2}
    --#STATE OPERATIONAL
    --#SEVERITY INFORMATIONAL
    ::= { starentTraps 481 }
				
starThreshDiameterRetryRate NOTIFICATION-TYPE
    OBJECTS { starThreshPct, starThreshMeasuredPct }
    STATUS current
    DESCRIPTION
	"The percentage of Diameter requests which has to be retried has exceeded the configured threshold
	 during the current monitoring period.

         Probable Cause: This is a user configurable threshold.

         If the thresholding subsystem is configured to run in an 'alarm' model,
         a starThreshClearDiameterRetryRate notification will be generated when the measured
	 value falls below the threshold."
    --#SUMMARY "[System] Threshold: Diameter retry rate threshold for threshold %d%% measured %d%%"
    --#ARGUMENTS {0,1}
    --#STATE OPERATIONAL
    --#SEVERITY WARNING
    ::= { starentTraps 482 }

starThreshClearDiameterRetryRate NOTIFICATION-TYPE
    OBJECTS { starThreshPct, starThreshMeasuredPct }
    STATUS current
    DESCRIPTION
	"The threshold condition is now clear."
    --#SUMMARY "[System] Threshold: Diameter retry rate threshold clear for threshold %d%% measured %d%%"
    --#ARGUMENTS {0,1}
    --#STATE OPERATIONAL
    --#SEVERITY INFORMATIONAL
    ::= { starentTraps 483 }


starThreshHNBGWHnbSess NOTIFICATION-TYPE
    OBJECTS { starThreshInt, starThreshMeasuredInt }
    STATUS current
    DESCRIPTION
    "The chassis-wide count of current HNBGW HNB sessions has gone above the configured threshold"
    --#SUMMARY "[System] Threshold: HNBGW HNB Sessions; measured %d threshold %d"
    --#ARGUMENTS {1,0}
    --#STATE OPERATIONAL
    --#SEVERITY WARNING
    ::= { starentTraps 484 }


starThreshClearHNBGWHnbSess NOTIFICATION-TYPE
    OBJECTS { starThreshInt, starThreshMeasuredInt }
    STATUS current
    DESCRIPTION 
    "The threshold condition is now clear."
    --#SUMMARY "[System] Threshold: HNBGW HNB Sessions CLEAR; measured %d threshold %d"
    --#ARGUMENTS {1,0}
    --#STATE OPERATIONAL
    --#SEVERITY INFORMATIONAL
    ::= { starentTraps 485 }


starThreshHNBGWUeSess NOTIFICATION-TYPE
    OBJECTS { starThreshInt, starThreshMeasuredInt }
    STATUS current
    DESCRIPTION
    "The chassis-wide count of current HNBGW UE sessions has gone above the configured threshold "
    --#SUMMARY "[System] Threshold: HNBGW UE Sessions; measured %d threshold %d"
    --#ARGUMENTS {1,0}
    --#STATE OPERATIONAL
    --#SEVERITY WARNING
    ::= { starentTraps 486 }


starThreshClearHNBGWUeSess NOTIFICATION-TYPE
    OBJECTS { starThreshInt, starThreshMeasuredInt }
    STATUS current
    DESCRIPTION 
        "The threshold condition is now clear."
    --#SUMMARY "[System] Threshold: HNBGW UE Sessions CLEAR; measured %d threshold %d"
    --#ARGUMENTS {1,0}
    --#STATE OPERATIONAL
    --#SEVERITY INFORMATIONAL
    ::= { starentTraps 487 }


starThreshHNBGWIuSess NOTIFICATION-TYPE
    OBJECTS { starThreshInt, starThreshMeasuredInt }
    STATUS current
    DESCRIPTION
        "The chassis-wide count of current HNBGW IU sessions has gone above the configured threshold"
    --#SUMMARY "[System] Threshold: HNBGW IU Sessions; measured %d threshold %d"
    --#ARGUMENTS {1,0}
    --#STATE OPERATIONAL
    --#SEVERITY WARNING
    ::= { starentTraps 488 }


starThreshClearHNBGWIuSess NOTIFICATION-TYPE
    OBJECTS { starThreshInt, starThreshMeasuredInt }
    STATUS current
    DESCRIPTION 
    "The threshold condition is now clear."
    --#SUMMARY "[System] Threshold: HNBGW IU Sessions CLEAR; measured %d threshold %d"
    --#ARGUMENTS {1,0}
    --#STATE OPERATIONAL
    --#SEVERITY INFORMATIONAL
    ::= { starentTraps 489 }

starThreshPerServicePDGSessions NOTIFICATION-TYPE
    OBJECTS { starThreshInt, starThreshMeasuredInt }
    STATUS current
    DESCRIPTION
	"The total number of PDG sessions in a service is above the configured threshold value."
    --#SUMMARY "[System] Threshold: Per Service PDG Sessions; measured %d threshold %d"
    --#ARGUMENTS {1,0}
    --#STATE OPERATIONAL
    --#SEVERITY WARNING
    ::= { starentTraps 491 }

starThreshClearPerServicePDGSessions NOTIFICATION-TYPE
    OBJECTS { starThreshInt, starThreshMeasuredInt }
    STATUS current
    DESCRIPTION
	"The threshold condition is now clear."
    --#SUMMARY "[System] Threshold: Per Sevice PDG Sessions CLEAR,measured %d threshold %d"
    --#ARGUMENTS {1,0}
    --#STATE OPERATIONAL
    --#SEVERITY INFORMATIONAL
    ::= { starentTraps 492 }

starThreshSystemCapacity NOTIFICATION-TYPE
    OBJECTS { starThreshPct, starThreshMeasuredPct }
    STATUS current
    DESCRIPTION
        "The System resource capacity has exceeded the configured threshold"
    --#SUMMARY "[System] Threshold: System Resource Capacity for threshold %d%% measured %d%%"
    --#ARGUMENTS {0,1}
    --#STATE OPERATIONAL
    --#SEVERITY WARNING
    ::= { starentTraps 493 }

starThreshClearSystemCapacity NOTIFICATION-TYPE
    OBJECTS { starThreshPct, starThreshMeasuredPct }
    STATUS  current
    DESCRIPTION
         " The threshold condition is now clear for system capacity."
    --#SUMMARY "[System] Threshold: System Resource Capacity clear for threshold %d%% measured %d%%"
    --#ARGUMENTS {0,1}
    --#STATE OPERATIONAL
    --#SEVERITY INFORMATIONAL
    ::= { starentTraps 494 }

starThreshTpoRtoTimeout NOTIFICATION-TYPE
    OBJECTS { starThreshInt, starThreshMeasuredInt }
    STATUS current
    DESCRIPTION
        "The total number of TPO RTO timeouts is above the configured 
         threshold value.
         Probable Cause: This is a user configurable threshold.
         If the thresholding subsystem is configured to run in an 'alarm' model, 
         a starThreshClearTpoRtoTimeout notification will be generated when the 
         measured value falls below the threshold."
    --#SUMMARY "[System] Threshold: TPO RTO timeouts; measured %d threshold %d"
    --#ARGUMENTS {1,0}
    --#STATE OPERATIONAL
    --#SEVERITY WARNING
    ::= { starentTraps 495 }

starThreshClearTpoRtoTimeout NOTIFICATION-TYPE
    OBJECTS { starThreshInt, starThreshMeasuredInt }
    STATUS current
    DESCRIPTION
        "The threshold condition is now clear."
    --#SUMMARY "[System] Threshold: TPO RTO timeouts CLEAR; measured %d threshold %d"
    --#ARGUMENTS {1,0}
    --#STATE OPERATIONAL
    --#SEVERITY INFORMATIONAL
    ::= { starentTraps 496 }

starThreshTpoDnsFailure NOTIFICATION-TYPE
    OBJECTS { starThreshPct, starThreshMeasuredPct }
    STATUS current
    DESCRIPTION
        "The total number of TPO DNS query failure is above the configured threshold value.
         Probable Cause: This is a user configurable threshold.
         If the thresholding subsystem is configured to run in an 'alarm' model, 
         a starThreshClearTpoDnsFailure notification will be generated when the 
         measured value falls below the threshold. "
    --#SUMMARY "[System] Threshold: TPO DNS query failure for threshold %d%% measured %d%%"
    --#ARGUMENTS {0,1}
    --#STATE OPERATIONAL
    --#SEVERITY WARNING
    ::= { starentTraps 497 }

starThreshClearTpoDnsFailure NOTIFICATION-TYPE
    OBJECTS { starThreshPct, starThreshMeasuredPct }
    STATUS current
    DESCRIPTION
        "The threshold condition is now clear."
    --#SUMMARY "[System] Threshold: TPO DNS query failure clear for threshold %d%% measured %d%%"
    --#ARGUMENTS {0,1}
    --#STATE OPERATIONAL
    --#SEVERITY INFORMATIONAL
    ::= { starentTraps 498 }

starThreshTpoLowCompressionGain NOTIFICATION-TYPE
    OBJECTS { starThreshInt, starThreshMeasuredInt }
    STATUS current
    DESCRIPTION
        "The total number of TPO low compression gain is above the configured 
         threshold value.
         Probable Cause: This is a user configurable threshold.
         If the thresholding subsystem is configured to run in an 'alarm' model, 
         a starThreshClearTpoLowCompressionGain notification will be generated 
         when the measured value falls below the threshold."
    --#SUMMARY "[System] Threshold: TPO TPO low compression gain; measured %d threshold %d"
    --#ARGUMENTS {1,0}
    --#STATE OPERATIONAL
    --#SEVERITY WARNING
    ::= { starentTraps 499 }

starThreshClearTpoLowCompressionGain NOTIFICATION-TYPE
    OBJECTS { starThreshInt, starThreshMeasuredInt }
    STATUS current
    DESCRIPTION
        "The threshold condition is now clear."
    --#SUMMARY "[System] Threshold: TPO low compression gain CLEAR; measured %d threshold %d"
    --#ARGUMENTS {1,0}
    --#STATE OPERATIONAL
    --#SEVERITY INFORMATIONAL
    ::= { starentTraps 500 }

starThreshEPDGCurrSess NOTIFICATION-TYPE
    OBJECTS { starThreshInt, starThreshMeasuredInt }
    STATUS current
    DESCRIPTION
        "The chassis-wide count of current EPDG sessions has gone above the configured threshold

         Probable Cause: This is a user configurable threshold.

         If the thresholding subsystem is configured to run in an 'alarm' model, a 
	 starThreshClearEPDGCurrSess notification will be generated when the measured
         value falls below the threshold."
    --#SUMMARY "[System] Threshold: EPDG Current Sessions; measured %d threshold %d"
    --#ARGUMENTS {1,0}
    --#STATE OPERATIONAL
    --#SEVERITY WARNING
    ::= { starentTraps 501 }

starThreshClearEPDGCurrSess NOTIFICATION-TYPE
    OBJECTS { starThreshInt, starThreshMeasuredInt }
    STATUS current
    DESCRIPTION
        "The threshold condition is now clear."
    --#SUMMARY "[System] Threshold: EPDG Current Sessions CLEAR; measured %d threshold %d"
    --#ARGUMENTS {1,0}
    --#STATE OPERATIONAL
    --#SEVERITY INFORMATIONAL
    ::= { starentTraps 502 }


starThreshCardTemperatureNearPowerOffLimit  NOTIFICATION-TYPE
    OBJECTS { starSlotNum, starThreshInt, starThreshMeasuredInt}
    STATUS current
    DESCRIPTION
    "On the certain card, the distance between the poweroff/reset point and 
     current temperature on card is smaller than the setted threshold, during 
     the current monitoring period.

     Probable Cause: This is a user configurable threshold. 
       Possible reason to cause this alarm: 
       1) External temperature is too high; 
       2) One or more fan failures; 
       3) Blockages the prevent fan air inflow/outflow.

     If the thresholding subsystem is configured to run in an 'alarm' model, a 
     starThreshClearCardTemperaturePowerOffLimit notification will be generated 
     when the measured temperature falls, making the distance between the 
     poweroff/reset point and current temperature larger than the setted 
     threshold."
    --#SUMMARY "[Card] Threshold: Card temperature near power off limit alarm for slot number %d threshold %d measured %d"
    --#ARGUMENTS {0,1,2}
    --#STATE OPERATIONAL
    --#SEVERITY MAJOR
    ::= { starentTraps 503 }

starThreshClearCardTemperaturePowerOffLimit NOTIFICATION-TYPE
    OBJECTS {starSlotNum, starThreshInt, starThreshMeasuredInt}
    STATUS current
    DESCRIPTION
    "On the certain card, the distance between the poweroff/reset point and 
     current temperature on card is larger than the setted clear point."
    --#SUMMARY "[Card] Threshold: Card temperature near power off limit clear for slot number %d threshold %d measured %d"
    --#ARGUMENTS {0,1,2}
    --#STATE OPERATIONAL
    --#SEVERITY INFORMATIONAL
    ::= { starentTraps 504 }

starThreshHENBGWHenbSessions NOTIFICATION-TYPE
    OBJECTS {starThreshInt, starThreshMeasuredInt}
    STATUS current
    DESCRIPTION
        "The total number of HENBGW Henb sessions is above the configured threshold value.

          Probable Cause: This is a user configurable threshold.

          If the thresholding subsystem is configured to run in an 'alarm' model, a starThreshClearHENBGWHenbSessions
          notification will be generated when the measure  value falls below the threshold."
    --#SUMMARY "[System] Threshold: Total HENBGW Henb Sessions; measured %d threshold %d"
    --#ARGUMENTS {1,0}
    --#STATE OPERATIONAL
    --#SEVERITY WARNING
    ::= { starentTraps 513 }

starThreshClearHENBGWHenbSessions NOTIFICATION-TYPE
    OBJECTS { starThreshInt, starThreshMeasuredInt }
    STATUS current
    DESCRIPTION
        "The threshold condition is now clear."
    --#SUMMARY "[System] Threshold: Total HENBGW Henb Sessions CLEAR; measured %d threshold %d"
    --#ARGUMENTS {1,0}
    --#STATE OPERATIONAL
    --#SEVERITY INFORMATIONAL
    ::= { starentTraps 514 }

starThreshHENBGWUeSessions NOTIFICATION-TYPE
    OBJECTS {starThreshInt, starThreshMeasuredInt}
    STATUS current
    DESCRIPTION
        "The total number of HENBGW UE sessions is above the configured threshold value.

          Probable Cause: This is a user configurable threshold.

          If the thresholding subsystem is configured to run in an 'alarm' model, a starThreshClearHENBGWUeSessions
          notification will be generated when the measure  value falls below the threshold."
    --#SUMMARY "[System] Threshold: Total HENBGW Sessions; measured %d threshold %d"
    --#ARGUMENTS {1,0}
    --#STATE OPERATIONAL
    --#SEVERITY WARNING
    ::= { starentTraps 515 }

starThreshClearHENBGWUeSessions NOTIFICATION-TYPE
    OBJECTS { starThreshInt, starThreshMeasuredInt }
    STATUS current
    DESCRIPTION
        "The threshold condition is now clear."
    --#SUMMARY "[System] Threshold: Total HENBGW UE Sessions CLEAR; measured %d threshold %d"
    --#ARGUMENTS {1,0}
    --#STATE OPERATIONAL
    --#SEVERITY INFORMATIONAL
    ::= { starentTraps 516 }

starThreshHENBGWPagingMessages NOTIFICATION-TYPE
    OBJECTS { starThreshInt, starThreshMeasuredInt }
    STATUS current
    DESCRIPTION
        "The total number of HENBGW Paging Messages received is above the configured threshold value.

         Probable Cause: This is a user configurable threshold.

         If the thresholding subsystem is configured to run in an 'alarm' model, a starThreshClearHENBGWPagingMessages
         notification will be generated when the measured value falls below the threshold."
    --#SUMMARY "[System] Threshold: Total HENBGW Paging Messages; measured %d threshold %d"
    --#ARGUMENTS {1,0}
    --#STATE OPERATIONAL
    --#SEVERITY WARNING
    ::= { starentTraps 517 }

starThreshClearHENBGWPagingMessages NOTIFICATION-TYPE
    OBJECTS { starThreshInt, starThreshMeasuredInt }
    STATUS current
    DESCRIPTION
        "The threshold condition is now clear."
    --#SUMMARY "[System] Threshold: Total HENBGW Paging Messages CLEAR; measured %d threshold %d"
    --#ARGUMENTS {1,0}
    --#STATE OPERATIONAL
    --#SEVERITY INFORMATIONAL
   ::= { starentTraps 518} 

starThreshPerServiceSAMOGSessions NOTIFICATION-TYPE
    OBJECTS { starThreshInt, starThreshMeasuredInt }
    STATUS current
    DESCRIPTION
	"The total number of SAMOG sessions in a service is above the configured threshold value."
    --#SUMMARY "[System] Threshold: Per Sevice SAMOG Sessions, measured %d threshold %d"
    --#ARGUMENTS {1,0}
    --#STATE OPERATIONAL
    --#SEVERITY WARNING
    ::= { starentTraps 519 }

starThreshClearPerServiceSAMOGSessions NOTIFICATION-TYPE
    OBJECTS { starThreshInt, starThreshMeasuredInt }
    STATUS current
    DESCRIPTION
	"The threshold condition is now clear."
    --#SUMMARY "[System] Threshold: Per Sevice SAMOG Sessions CLEAR, measured %d threshold %d"
    --#ARGUMENTS {1,0}
    --#STATE OPERATIONAL
    --#SEVERITY INFORMATIONAL
    ::= { starentTraps 520 }

starThreshNATPktDrop NOTIFICATION-TYPE
    OBJECTS { starIPPoolContext,starIPPoolName, starThreshPct, starThreshMeasuredPct }
    STATUS  current
    DESCRIPTION
	"The NAT packet drops from a NAT pool is above the configured threshold value.

         Probable Cause: This is a user configurable threshold.
         
         If the thresholding subsystem is configured to run in an 'alarm' model,
         a starThreshNATPktDrop notification will be generated when the measured
	 value exceeds the threshold."
    --#SUMMARY "[System] Threshold: NAT Pkt Drop in context %s for pool %s threshold %d%% measured %d%%"
    --#ARGUMENTS {0,1,2,3}
    --#STATE OPERATIONAL
    --#SEVERITY WARNING
    ::= { starentTraps 521 }

starThreshClearNATPktDrop NOTIFICATION-TYPE
    OBJECTS { starIPPoolContext,starIPPoolName, starThreshPct, starThreshMeasuredPct }
    STATUS current
    DESCRIPTION 
	"The threshold condition is now clear."
    --#SUMMARY "[System] Threshold: NAT Pkt Drop threshold clear in context %s pool %s threshold %d%% measured %d%%"
    --#ARGUMENTS {0,1,2,3}
    --#STATE OPERATIONAL
    --#SEVERITY INFORMATIONAL
    ::= { starentTraps 522 }

starThreshFabricEGQDiscards NOTIFICATION-TYPE
    OBJECTS { starSlotNum, starThreshDeviceNum, starThreshMeasuredInt, starThreshInt, starThreshPeriodInt }
    STATUS current
    DESCRIPTION
	"The number of EGQDiscards observed during configured threshold and interval exceeded.
   Probable Cause:  Possible FAP or FE issue.  Collect more data by running .show fabric health. command."
    --#SUMMARY "Threshold EGQDiscards slot %d device %d measured %d threshold %d per %d sec"
    --#ARGUMENTS {0,1,2,3,4}
    --#STATE OPERATIONAL
    --#SEVERITY CRITICAL 
    ::= { starentTraps 523 }

starThreshClearFabricEGQDiscards NOTIFICATION-TYPE
    OBJECTS { starSlotNum, starThreshDeviceNum, starThreshMeasuredInt, starThreshInt }
    STATUS current
    DESCRIPTION
	"The threshold condition is now clear."
    --#SUMMARY "Threshold EGQDiscards  slot %d device %d  threshold CLEAR measured %d threshold %d"
    --#ARGUMENTS {0,1,2,3}
    --#STATE OPERATIONAL
    --#SEVERITY CRITICAL 
    ::= { starentTraps 524 }

starGILANServiceStart NOTIFICATION-TYPE
    OBJECTS { starServiceVpnName, starServiceServName }
    STATUS  current
    DESCRIPTION
        "A GILAN Service has started

	 Action to be Taken: No action required"
    --#SUMMARY "[Service GILAN-%s-%s] GILAN service has started"
    --#ARGUMENTS {0,1}
    --#STATE OPERATIONAL
    --#SEVERITY INFORMATIONAL
    ::= { starentTraps 525 }

starGILANServiceStop NOTIFICATION-TYPE
    OBJECTS { starServiceVpnName, starServiceServName }
    STATUS  current
    DESCRIPTION
        "A GILAN Service has stopped

	 Probable Cause: This is typically caused by operator invention.  In
         unusual cases it can be caused by the loss of resources (PACs/PSCs) to
	 support the running configuration.

	 Action to be Taken: If the GILAN service shutdown was not planned,
	 examine the admin logs for an indication of the failure.  Check the
	 crash logs for an indication of a software failure.

	 Clear Condition: Verify that the GILAN service is operational.

	 Condition Clear Alarm:  A starGILANServiceStart notification will be generated when
	 the service is restarted"
    --#SUMMARY "[Service GILAN-%s-%s] GILAN service has stopped"
    --#ARGUMENTS {0,1}
    --#STATE DEGRADED
    --#SEVERITY MAJOR
    ::= { starentTraps 526 }

starThreshEPDGIKEV2SetupAttempts NOTIFICATION-TYPE
    OBJECTS { starServiceVpnName, starServiceServName, starThreshInt, starThreshMeasuredInt }
    STATUS current
    DESCRIPTION
        "The number of IKEv2 Setup attepmts requests seen for this ePDG service has exceeded the configured
         threshold.

         Probable Cause: This is a user configurable threshold.

         If the thresholding subsystem is configured to run in an 'alarm' model,
         a starThreshEPDGIKEV2SetupAttempts notification will be generated when the measured
         value falls below the threshold."
    --#SUMMARY "[Service ePDG-%s-%s] Threshold: ePDG Per-Service IKEv2 Setup Attempts; measured %d threshold %d"
    --#ARGUMENTS {0,1,3,2}
    --#STATE OPERATIONAL
    --#SEVERITY WARNING
    ::= { starentTraps 527 }

starThreshClearEPDGIKEV2SetupAttempts NOTIFICATION-TYPE
    OBJECTS { starServiceVpnName, starServiceServName, starThreshInt, starThreshMeasuredInt }
    STATUS current
    DESCRIPTION
        "The threshold condition is now clear"
    --#SUMMARY "[Service ePDG-%s-%s] Threshold: ePDG Per-Service IKEv2 Setup Attempts CLEAR; measured %d threshold %d"
    --#ARGUMENTS {0,1,3,2}
    --#STATE OPERATIONAL
    --#SEVERITY INFORMATIONAL
    ::= { starentTraps 528 }

starThreshEPDGIKEV2AuthFailures NOTIFICATION-TYPE
    OBJECTS { starServiceVpnName, starServiceServName, starThreshInt, starThreshMeasuredInt }
    STATUS current
    DESCRIPTION
        "The number of IKEv2 Authentication Failures seen for this ePDG service has exceeded the configured
         threshold.

         Probable Cause: This is a user configurable threshold.

         If the thresholding subsystem is configured to run in an 'alarm' model,
         a starThreshEPDGIKEV2AuthFailures notification will be generated when the measured
         value falls below the threshold."
    --#SUMMARY "[Service ePDG-%s-%s] Threshold: ePDG Per-Service IKEv2 Authentication Failures; measured %d threshold %d"
    --#ARGUMENTS {0,1,3,2}
    --#STATE OPERATIONAL
    --#SEVERITY WARNING
    ::= { starentTraps 529 }

starThreshClearEPDGIKEV2AuthFailures NOTIFICATION-TYPE
    OBJECTS { starServiceVpnName, starServiceServName, starThreshInt, starThreshMeasuredInt }
    STATUS current
    DESCRIPTION
        "The threshold condition is now clear"
    --#SUMMARY "[Service ePDG-%s-%s] Threshold: ePDG Per-Service IKEv2 Authentication Failures CLEAR; measured %d threshold %d"
    --#ARGUMENTS {0,1,3,2}
    --#STATE OPERATIONAL
    --#SEVERITY INFORMATIONAL
    ::= { starentTraps 530 }

starThreshEPDGIKEV2SetupSuccess NOTIFICATION-TYPE
    OBJECTS { starServiceVpnName, starServiceServName, starThreshInt, starThreshMeasuredInt }
    STATUS current
    DESCRIPTION
        "The number of IKEv2 Setup Success seen for this ePDG service has exceeded the configured
         threshold.

         Probable Cause: This is a user configurable threshold.

         If the thresholding subsystem is configured to run in an 'alarm' model,
         a starThreshEPDGIKEV2SetupSuccess notification will be generated when the measured
         value falls below the threshold."
    --#SUMMARY "[Service ePDG-%s-%s] Threshold: ePDG Per-Service IKEv2 Setup Success; measured %d threshold %d"
    --#ARGUMENTS {0,1,3,2}
    --#STATE OPERATIONAL
    --#SEVERITY WARNING
    ::= { starentTraps 531 }

starThreshClearEPDGIKEV2SetupSuccess NOTIFICATION-TYPE
    OBJECTS { starServiceVpnName, starServiceServName, starThreshInt, starThreshMeasuredInt }
    STATUS current
    DESCRIPTION
        "The threshold condition is now clear"
    --#SUMMARY "[Service ePDG-%s-%s] Threshold: ePDG Per-Service IKEv2 Setup Success CLEAR; measured %d threshold %d"
    --#ARGUMENTS {0,1,3,2}
    --#STATE OPERATIONAL
    --#SEVERITY INFORMATIONAL
    ::= { starentTraps 532 }

starThreshEPDGIKEV2SetupFailure NOTIFICATION-TYPE
    OBJECTS { starServiceVpnName, starServiceServName, starThreshInt, starThreshMeasuredInt }
    STATUS current
    DESCRIPTION
        "The number of IKEv2 Setup Failure seen for this ePDG service has exceeded the configured
         threshold.

         Probable Cause: This is a user configurable threshold.

         If the thresholding subsystem is configured to run in an 'alarm' model,
         a starThreshEPDGIKEV2SetupFailure notification will be generated when the measured
         value falls below the threshold."
    --#SUMMARY "[Service ePDG-%s-%s] Threshold: ePDG Per-Service IKEv2 Setup Failure; measured %d threshold %d"
    --#ARGUMENTS {0,1,3,2}
    --#STATE OPERATIONAL
    --#SEVERITY WARNING
    ::= { starentTraps 533 }

starThreshClearEPDGIKEV2SetupFailure NOTIFICATION-TYPE
    OBJECTS { starServiceVpnName, starServiceServName, starThreshInt, starThreshMeasuredInt }
    STATUS current
    DESCRIPTION
        "The threshold condition is now clear"
    --#SUMMARY "[Service ePDG-%s-%s] Threshold: ePDG Per-Service IKEv2 Setup Failure CLEAR; measured %d threshold %d"
    --#ARGUMENTS {0,1,3,2}
    --#STATE OPERATIONAL
    --#SEVERITY INFORMATIONAL
    ::= { starentTraps 534 }

starThreshEPDGIKEV2SetupFailureRate NOTIFICATION-TYPE
    OBJECTS { starServiceVpnName, starServiceServName, starThreshPct, starThreshMeasuredPct }
    STATUS current
    DESCRIPTION
        "The rate of IKEv2 Setup failures (as a percentage of total requests) seen for this ePDG service
         has exceeded the configured threshold.

         Probable Cause: This is a user configurable threshold.

         If the thresholding subsystem is configured to run in an 'alarm' model,
         a starThreshEPDGIKEV2SetupFailureRate notification will be generated when the measured
         value falls below the threshold."
    --#SUMMARY "[Service ePDG-%s-%s] Threshold: ePDG Per-Service IKEv2 Setup Failure Rate; measured %d%% threshold %d%%"
    --#ARGUMENTS {0,1,2,3}
    --#STATE OPERATIONAL
    --#SEVERITY WARNING
    ::= { starentTraps 535 }

starThreshClearEPDGIKEV2SetupFailureRate NOTIFICATION-TYPE
    OBJECTS { starServiceVpnName, starServiceServName, starThreshPct, starThreshMeasuredPct }
    STATUS current
    DESCRIPTION
        "The threshold condition is now clear"
    --#SUMMARY "[Service ePDG-%s-%s] Threshold: ePDG Per-Service IKEv2 Setup Failure Rate CLEAR; measured %d%% threshold %d%%"
    --#ARGUMENTS {0,1,2,3}
    --#STATE OPERATIONAL
    --#SEVERITY INFORMATIONAL
    ::= { starentTraps 536 }

starThreshLagRxUtil NOTIFICATION-TYPE
    OBJECTS { starLAGGroup, starThreshPct, starThreshMeasuredPct }
    STATUS current
    DESCRIPTION
	"The Rx utilization of port on a lag group has exceeded the configured threshold value during
	 the current monitoring period.

         Probable Cause: This is a user configurable threshold.

         If the thresholding subsystem is configured to run in an 'alarm' model,
         a starThreshClearLagRxUtil notification will be generated when the measured
	 value falls below the threshold."
    --#SUMMARY "[System] Threshold: lag ports rx utilization threshold for lag group id %d threshold %d%% measured %d%%"
    --#ARGUMENTS {0,1,2}
    --#STATE OPERATIONAL
    --#SEVERITY WARNING
    ::= { starentTraps 537 }

starThreshClearLagRxUtil NOTIFICATION-TYPE
    OBJECTS { starLAGGroup, starThreshPct, starThreshMeasuredPct }
    STATUS current
    DESCRIPTION
	"The threshold condition is now clear."
    --#SUMMARY "[System] Threshold: lag ports rx utilization threshold clear for lag group id %d threshold %d%% measured %d%%"
    --#ARGUMENTS {0,1,2}
    --#STATE OPERATIONAL
    --#SEVERITY INFORMATIONAL
    ::= { starentTraps 538 }

starThreshLagTxUtil NOTIFICATION-TYPE
    OBJECTS { starLAGGroup, starThreshPct, starThreshMeasuredPct }
    STATUS current
    DESCRIPTION
	"The Tx utilization of port on a lag group has exceeded the configured threshold value during
	 the current monitoring period.

         Probable Cause: This is a user configurable threshold.

         If the thresholding subsystem is configured to run in an 'alarm' model,
         a starThreshClearLagTxUtil notification will be generated when the measured
	 value falls below the threshold."
    --#SUMMARY "[System] Threshold: lag ports tx utilization threshold for lag group id %d threshold %d%% measured %d%%"
    --#ARGUMENTS {0,1,2}
    --#STATE OPERATIONAL
    --#SEVERITY WARNING
    ::= { starentTraps 539 }

starThreshClearLagTxUtil NOTIFICATION-TYPE
    OBJECTS { starLAGGroup, starThreshPct, starThreshMeasuredPct }
    STATUS current
    DESCRIPTION
	"The threshold condition is now clear."
    --#SUMMARY "[System] Threshold: lag ports tx utilization threshold clear for lag group id %d threshold %d%% measured %d%%"
    --#ARGUMENTS {0,1,2}
    --#STATE OPERATIONAL
    --#SEVERITY INFORMATIONAL
    ::= { starentTraps 540 }


starThreshCPUCryptoCoresUtilization NOTIFICATION-TYPE
    OBJECTS { starCPUSlot, starCPUNumber, starCPUCoreNumber, starThreshPct, starThreshMeasuredPct }
    STATUS current
    DESCRIPTION
	"The CPU Crypto Core utilization has exceeded for configured
	 threshold value for the current monitoring period.

         Probable Cause: This is a user configurable threshold.

         If the thresholding subsystem is configured to run in an 'alarm' model,
         a starThreshClearCPUCryptoCoresUtilization notification will be generated when the measured
	 value falls below the threshold."
    --#SUMMARY "[Card] Threshold: CPU utilization threshold for card %d CPU %d CORE %d threshold %d%% measured %d%%"
    --#ARGUMENTS {0,1,2,3,4}
    --#STATE OPERATIONAL
    --#SEVERITY WARNING
    ::= { starentTraps 541 }


starThreshClearCPUCryptoCoresUtilization NOTIFICATION-TYPE
    OBJECTS { starCPUSlot, starCPUNumber, starCPUCoreNumber, starThreshPct, starThreshMeasuredPct }
    STATUS current
    DESCRIPTION
	"The threshold condition is now clear."
    --#SUMMARY "[Card] Threshold: CPU utilization threshold clear card %d for CPU %d CORE %d threshold %d%% measured %d%%"
    --#ARGUMENTS {0,1,2,3,4}
    --#STATE OPERATIONAL
    --#SEVERITY INFORMATIONAL
    ::= { starentTraps 542}

-- Non Thresholds Range 2

starOSPFNeighborDown NOTIFICATION-TYPE
    OBJECTS { starContextName, starInterfaceName, starInterfaceIPAddress, starOSPFNeighborRouterID, starOSPFFromState, starOSPFToState }
    STATUS  current
    DESCRIPTION
	"An OSPF neighbor is down.

	 Condition Clear Alarm: A starOSPFNeighborFull notification will be generated when the neighbor
	 is restored."
    --#SUMMARY "[VPN %s] OSPF Neighbor down, interface %s/%s, OSPF Neighbor %s, transitioned from state %s to %s"
    --#ARGUMENTS {0,1,2,3,4,5}
    --#STATE DEGRADED
    --#SEVERITY MINOR
    ::= { starentTraps 1001 }

starOSPFNeighborFull NOTIFICATION-TYPE
    OBJECTS { starContextName, starInterfaceName, starInterfaceIPAddress, starOSPFNeighborRouterID }
    STATUS  current
    DESCRIPTION
	"An OSPF neighbor is full.  A starOSPFNeighborFull notification is only sent for neighbors
	 which had previous been declared down via a starOSPFNeighborDown notification."
    --#SUMMARY "[VPN %s] OSPF Neighbor full, interface %s/%s, OSPF Neighbor %s"
    --#ARGUMENTS {0,1,2,3}
    --#STATE OPERATIONAL
    --#SEVERITY INFORMATIONAL
    ::= { starentTraps 1002 }

starM3UAPSDown NOTIFICATION-TYPE
    OBJECTS { starSS7rdId, starSS7M3UAPsId }
    STATUS  current
    DESCRIPTION
    "The M3UA Peer Server is unavailable.

    Possibe reason: All related Peer Server Processes(PSPs) are in the ASP-DOWN state for this Peer Server.

    Condition Clear Alarm:  A starM3UAPSActive notification will be generated when
    the Peer Server becomes reachable as at least one PSP is in ASP-ACTIVE state"
    --#SUMMARY "[ss7-routing-domain %d] peer-server-%d is down"
    --#ARGUMENTS {0,1}
    --#STATE DEGRADED
    --#SEVERITY MAJOR
    ::= { starentTraps 1004 }

starM3UAPSActive NOTIFICATION-TYPE
    OBJECTS { starSS7rdId, starSS7M3UAPsId }
    STATUS  current
    DESCRIPTION
    "Peer Server is available and application traffic is active.This state implies that at
    least one PSP is in the ASP-ACTIVE state.
    starM3UAPSActive is only generated for Application Services which were previously declared down via a starM3UAPSDown notification"

    --#SUMMARY "[ss7-routing-domain %d] peer-server-%d is active"
    --#ARGUMENTS {0,1}
    --#STATE OPERATIONAL
    --#SEVERITY INFORMATIONAL
    ::= { starentTraps 1005 }

starM3UAPSPDown NOTIFICATION-TYPE
    OBJECTS {
                starSS7rdId,
                starSS7M3UAPsId,
                starSS7M3UAPspId,
                starSS7CauseString
            }
    STATUS  current
    DESCRIPTION
    "An ASP Down message received from the remote M3UA peer indicates the adaptation layer at the remote M3UA peer
    is NOT ready to receive DATA, SSNM, RKM or ASPTM messages

    Possibe reason:
    1. SCTP association is down or
    2. Remote peer server process is down

    Condition Clear Alarm:  A starM3UAPSPUp notification will be generated when
    the reemote ASP becomes available"
    --#SUMMARY "[ss7-routing-domain %d] peer-server %d peer-server-process %d is down cause %s"
    --#ARGUMENTS {0,1,2,3}
    --#STATE DEGRADED
    --#SEVERITY MINOR
    ::= { starentTraps 1006 }

starM3UAPSPUp NOTIFICATION-TYPE
    OBJECTS {
                starSS7rdId,
                starSS7M3UAPsId,
                starSS7M3UAPspId,
                starSS7CauseString
            }
    STATUS  current
    DESCRIPTION
    "An ASP Up message received from the remote M3UA peer indicates that that the
    adaptation layer at the remote peer is ready to receive any ASPSM/ASPTM messages for all
    Routing Keys that the ASP is configured to serve
    starM3UAPSPUp is generated only when previous starM3UAPSPDown was generated"
    --#SUMMARY "[ss7-routing-domain %d] peer-server %d peer-server-process %d is active cause %s"
    --#ARGUMENTS {0,1,2,3}
    --#STATE OPERATIONAL
    --#SEVERITY INFORMATIONAL
    ::= { starentTraps 1007 }


starSCCPSspRcvd NOTIFICATION-TYPE
    OBJECTS { starSccpNwId, starSS7Pc, starSccpSsn }
    STATUS  current
    DESCRIPTION
    "Subsystem prohibitted received from a peer. The receiving node needs to update the  translation tables so that traffic could be re routed to a
    backup system if available
    Condition Clear: A starSCCPSspClear notification will be generated when this condition is cleared."
    --#SUMMARY "[sccp-network %d] dpc-%d ssn-%d prohibited"
    --#ARGUMENTS {0,1,2}
    --#STATE DEGRADED
    --#SEVERITY MAJOR
    ::= { starentTraps 1008 }

starSCCPSspClear NOTIFICATION-TYPE
    OBJECTS { starSccpNwId, starSS7Pc, starSccpSsn }
    STATUS  current
    DESCRIPTION
    "Susbsystem available received from a peer. This indicates a previously prohibited
    node is now available. Receiving node needs to update its translation tables
    A starSCCPSspClear notification is only generated for peers which had previously generated a starSCCPSspRcvd noficiation"
    --#SUMMARY "[sccp-network %d] dpc-%d ssn-%d allowed"
    --#ARGUMENTS {0,1,2}
    --#STATE OPERATIONAL
    --#SEVERITY INFORMATIONAL
    ::= { starentTraps 1009 }


starSGSNRNCReset NOTIFICATION-TYPE
    OBJECTS { starSessSGSNVpnName, starSessSGSNServName,starSessSGSNMcc,starSessSGSNMnc,starSessSGSNRncId}
    STATUS  current
    DESCRIPTION
    "SGSN has received an Radio Network Controller(RNC) reset event.SGSN will clean up all the Iu connections with the RNC.
    This event is not generated when we get RNC Reset the firt time system boots up. This trap is generated only on subsequent reset events"

    --#SUMMARY "[Service SGSN %s-%s] RNC Reset event received ; MCC %s MNC %s RncId %d"
    --#ARGUMENTS {0,1,2,3,4}
    --#STATE OPERATIONAL
    --#SEVERITY INFORMATIONAL
    ::= { starentTraps 1010 }

starSGSNHLRReset NOTIFICATION-TYPE
    OBJECTS { starSessSGSNVpnName, starSessSGSNServName, starSessSGSNHlrNum}
    STATUS  current
    DESCRIPTION
    "Home Location register(HLR) reset event received. SGSN will mark all the subscribers served by this HLR so that the
    subscription record can be fetched again on subsequent user activity"

    --#SUMMARY "[Service SGSN %s-%s] HLR Reset event received ; HLR Number %s"
    --#ARGUMENTS {0,1,2}
    --#STATE OPERATIONAL
    --#SEVERITY INFORMATIONAL
    ::= { starentTraps 1011 }

starSGSNGtpcPathFailure NOTIFICATION-TYPE
    OBJECTS {starSGTPVpnName, starSGTPServName, starSGTPPeerAddr , starSGTPPeerPort , starSGTPSelfAddr, starSGTPSelfPort}
    STATUS  current
    DESCRIPTION
    "No response received from peer GPRS Serving Node(GSN) as several messages have timed out. The control path towards the peer GSN is down.
    Check that the peer GGSN or SGSN is UP

    Possibe reason: Remote GSN is down

    Condition Clear Alarm:  A starSGSNGtpcPathFailureClear notification will be generated when
    the control path towards the peer GSN is available"
    --#SUMMARY "[Service SGTP %s-%s] GTP control path failure. peer-end-point %s:%d , self-end-point %s:%d"
    --#ARGUMENTS {0,1,2,3,4,5}
    --#STATE DEGRADED
    --#SEVERITY MAJOR
    ::= { starentTraps 1012 }


starSGSNGtpcPathFailureClear NOTIFICATION-TYPE
    OBJECTS {starSGTPVpnName, starSGTPServName, starSGTPPeerAddr , starSGTPPeerPort , starSGTPSelfAddr, starSGTPSelfPort}
    STATUS  current
    DESCRIPTION
    "The path to the peer GSN which was down is now available
    A starSGSNGtpcPathFailureClear notification is only generated for GSNs which had previously generated a starSGSNGtpcPathFailure notification"
    --#SUMMARY "[Service SGTP %s-%s] GTP control path active  peer-end-point %s:%d , self-end-point %s:%d"
    --#ARGUMENTS {0,1,2,3,4,5}
    --#STATE  OPERATIONAL
    --#SEVERITY INFORMATIONAL
    ::= { starentTraps 1013 }

starSGSNGtpuPathFailure NOTIFICATION-TYPE
    OBJECTS {starSGTPVpnName, starSGTPServName, starSGTPPeerAddr , starSGTPPeerPort , starSGTPSelfAddr, starSGTPSelfPort}
    STATUS  current
    DESCRIPTION
    "No response received for ECHO request sent from SGSN. Data path failure detected towards peer GPRS Serving Node(GSN) or Radio Network Controller(RNC).
    Check if the peer RNC or GSN is up

    Possibe reason: Remote GSN is down

    Condition Clear Alarm:  A starSGSNGtpuPathFailureClear notification will be generated when
    the data path to the remote GSN becomes available"
    --#SUMMARY "[Service SGTP %s-%s] GTP data path failure. peer-end-point %s:%d , self-end-point %s:%d"
    --#ARGUMENTS {0,1,2,3,4,5}
    --#STATE DEGRADED
    --#SEVERITY MAJOR
    ::= { starentTraps 1014 }

starSGSNGtpuPathFailureClear NOTIFICATION-TYPE
    OBJECTS {starSGTPVpnName, starSGTPServName, starSGTPPeerAddr , starSGTPPeerPort , starSGTPSelfAddr, starSGTPSelfPort}
    STATUS  current
    DESCRIPTION
    "The data path toward peer GSN or RNC is now available
    A starSGSNGtpuPathFailureClear notification is only sent for peers which had previously generated a starSGSNGtpuPathFailure notification."
    --#SUMMARY "[Service SGTP %s-%s] GTP data path is available peer-end-point %s:%d , self-end-point %s:%d"
    --#ARGUMENTS {0,1,2,3,4,5}
    --#STATE OPERATIONAL
    --#SEVERITY INFORMATIONAL
    ::= { starentTraps 1015 }

starMTP3LinkOutOfService NOTIFICATION-TYPE
    OBJECTS {starSS7rdId,starSS7MTP3LinkSetId, starSS7MTP3LinkId}
    STATUS  current
    DESCRIPTION
    "Message Transfer Part(MTP3) link out of service.

    Possibe reason:
    1. Physical link is down or
    2. Layer 2 (SSCOP/MTP2) is down
    3. Operator action - link deactivated.

    Condition Clear Alarm:  A starMTP3LinkInService notification will be generated when
    the link comes back in service"
    --#SUMMARY "[ss7-routing-domain %d] linkset-%d link-%d out of service"
    --#ARGUMENTS {0,1,2}
    --#STATE DEGRADED
    --#SEVERITY MINOR
    ::= { starentTraps 1016 }

starMTP3LinkInService NOTIFICATION-TYPE
    OBJECTS {starSS7rdId,starSS7MTP3LinkSetId, starSS7MTP3LinkId}
    STATUS  current
    DESCRIPTION
    "Message Transfer Part(MTP3) link is in service."
    --#SUMMARY "[ss7-routing-domain %d] linkset-%d link-%d in service"
    --#ARGUMENTS {0,1,2}
    --#STATE OPERATIONAL
    --#SEVERITY INFORMATIONAL
    ::= { starentTraps 1017 }

starMTP3LinkSetUnAvailable NOTIFICATION-TYPE
    OBJECTS {starSS7rdId,starSS7MTP3LinkSetId}
    STATUS  current
    DESCRIPTION
    "Message Transfer Part(MTP3) linkset Unavailable

    Possibe reason:
    1. All the links in the linkset is down.
    2. Operator action - linkset deactivated.

    Condition Clear Alarm:  A starMTP3LinkSetAvailable notification will be generated when
    the previously down linkset is available"
    --#SUMMARY "[ss7-routing-domain%d] linkset-%d unavailable"
    --#ARGUMENTS {0,1}
    --#STATE DEGRADED
    --#SEVERITY MAJOR
    ::= { starentTraps 1018 }

    starMTP3LinkSetAvailable NOTIFICATION-TYPE
    OBJECTS {starSS7rdId, starSS7MTP3LinkSetId}
    STATUS  current
    DESCRIPTION
    "Message Transfer Part(MTP3) linkset Available.
    A starMTP3LinkSetAvailable notification is only generated for linksets which previously generated a starMTP3LinkSetUnavailable notification"
    --#SUMMARY "[ss7-routing-domain%d] linkset-%d available"
    --#ARGUMENTS {0,1}
    --#STATE OPERATIONAL
    --#SEVERITY INFORMATIONAL
    ::= { starentTraps 1019 }


starSCTPAssociationFail NOTIFICATION-TYPE
    OBJECTS {starSS7rdId, starSS7M3UAPsId, starSS7M3UAPspId }
    STATUS  current
    DESCRIPTION
    "M3UA Stream Control Transmission Protocol(SCTP) association establishment failure.
    Possibe reason: The peer is down. or network reachability to the remote server is down or the end point configuration is not correct at our end.
    Condition Clear Alarm:  A starSCTPAssociationEstablished notification will be generated when
    the previously failed association is successfully established again"
    --#SUMMARY "[ss7-routing-domain %d] peer-server-%d peer-server-process-%d association down"
    --#ARGUMENTS {0,1,2}
    --#STATE DEGRADED
    --#SEVERITY MAJOR
    ::= { starentTraps 1020 }

starSCTPAssociationEstablished NOTIFICATION-TYPE
    OBJECTS {starSS7rdId, starSS7M3UAPsId, starSS7M3UAPspId }
    STATUS  current
    DESCRIPTION
    "M3UA Stream Control Transmission Protocol (SCTP) association establishment ok. Previoulsy there was a failure to establish the same association
    A starM3UASCTPAssociationEstabalish notification is only generated for peers which previously generated a starM3UASCRPAssociationFail notification"
    --#SUMMARY "[ss7-routing-domain %d] peer-server-%d peer-server-process-%d association up"
    --#ARGUMENTS {0,1,2}
    --#STATE OPERATIONAL
    --#SEVERITY INFORMATIONAL
    ::= { starentTraps 1021 }

starSCTPPathDown NOTIFICATION-TYPE

    OBJECTS {
                starSS7rdId,
                starSS7M3UAPsId,
                starSS7M3UAPspId,
                starSS7SCTPSelfAddr,
                starSS7SCTPSelfPort,
                starSS7SCTPPeerAddr,
                starSS7SCTPPeerPort,
                starSS7CauseString
            }
    STATUS  current
    DESCRIPTION
    "Stream Control Transmission Protoco(SCTP) path down.
    Possible reason: The peer is down. or network reachability to the remote server is down or the end point configuration is not correct at our end.
    Condition Clear Alarm:  A starSCTPPathUp notification will be generated when the previously down path becomes usable"
    --#SUMMARY "[ss7-routing-domain %d] peer-server %d peer-server-process %d self-end-point %s:%d peer-end-point %s:%d sctp path down cause %s"
    --#ARGUMENTS {0,1,2,3,4,5,6,7}
    --#STATE DEGRADED
    --#SEVERITY MINOR
    ::= { starentTraps 1022 }

starSCTPPathUp NOTIFICATION-TYPE
    OBJECTS {
                starSS7rdId,
                starSS7M3UAPsId,
                starSS7M3UAPspId,
                starSS7SCTPSelfAddr,
                starSS7SCTPSelfPort,
                starSS7SCTPPeerAddr,
                starSS7SCTPPeerPort,
                starSS7CauseString
            }
    STATUS  current
    DESCRIPTION
    "Stream Control Transmission Protocol(SCTP) path up.
    A starSCTPPathUp notification is only generated for peers which had previously generated a starSCTPPathDown notification"
    --#SUMMARY "[ss7-routing-domain %d] peer-server %d peer-server-process %d self-end-point %s:%d peer-end-point %s:%d sctp path up cause %s"
    --#ARGUMENTS {0,1,2,3,4,5,6,7}
    --#STATE OPERATIONAL
    --#SEVERITY INFORMATIONAL
    ::= { starentTraps 1023 }

starPortDown NOTIFICATION-TYPE
    OBJECTS { starPortSlot, starPortNum, starPortType,starSlotSerialNumber }
    STATUS  current
    DESCRIPTION
    "Port status is Down. This notification is only generated for physical port.

     Action to be Taken: No action required. The cause for the port down should be investigated."
    --#SUMMARY "[Card] Port status is down Slot %d Port %d port type %s UUID %s"
    --#ARGUMENTS {0,1,2,3}
    --#STATE DEGRADED
    --#SEVERITY MAJOR
    ::= { starentTraps 1024 }

starPortUp NOTIFICATION-TYPE
    OBJECTS { starPortSlot, starPortNum, starPortType, starSlotSerialNumber }
    STATUS  current
    DESCRIPTION
    "Port status is up. This notification is only generated for physical port and a
     'starPortDown' notification was previously generated.

    Action to be Taken: No action required"
    --#SUMMARY "[Card] Port status is up Slot %d Port %d port type %s UUID %s"
    --#ARGUMENTS {0,1,2,3}
    --#STATE OPERATIONAL
    --#SEVERITY INFORMATIONAL
    ::= { starentTraps 1025 }

-- BS trap

starBSReachable NOTIFICATION-TYPE
    OBJECTS { starServiceVpnName, starServiceServName, starPeerAddress }
    STATUS current
    DESCRIPTION
        "The Base Station is reachable now. This can be result of Base Station Startup, etc.

	 Action to be Taken: No Action Required"
    --#SUMMARY "[ASNGW Service %s-%s] Base Station Reachable, Base Station address %s"
    --#ARGUMENTS {0,1,2}
    --#STATE OPERATIONAL
    --#SEVERITY INFORMATIONAL
    ::= { starentTraps 1026 }

starBSUnreachable NOTIFICATION-TYPE
    OBJECTS { starServiceVpnName, starServiceServName, starPeerAddress }
    STATUS current
    DESCRIPTION
        "A Base Station that the IMG communicates with is no longer reachable.

	 Probable Cause: The Base Station has failed or is otherwise unavailable, or
	 a network connectivity problem makes it unreachable.

	 Action to be Taken: If the Base Station outage was unplanned, restart/reset the
	 Base Station; verify network connectivity.

	 Condition Clear Alarm: This condition is cleared by a starBSReachable notification."

    --#SUMMARY "[ASNGW Service %s-%s] Base Station Unreachable, Base Station address %s"
    --#ARGUMENTS {0,1,2}
    --#STATE DEGRADED
    --#SEVERITY MAJOR
    ::= { starentTraps 1027 }

starSystemStartup NOTIFICATION-TYPE
    OBJECTS { starChassisType, starChassisDescription, starChassisSWRevision }
    STATUS current
    DESCRIPTION
        "The system has completed a reboot/startup"
    --#SUMMARY "[Chassis] System Startup, Cisco %s chassis, '%s', SW Revision %s"
    --#ARGUMENTS {0,1,2}
    --#STATE OPERATIONAL
    --#SEVERITY INFORMATIONAL
    ::= { starentTraps 1028 }

 starMTP3PCUnavailable NOTIFICATION-TYPE
    OBJECTS { starSS7rdId, starSS7Pc, starSS7MTP3LinkSetId}
    STATUS  current
    DESCRIPTION
    "Message Transfer Part(MTP3) Route to the Point code becomes unavailable.

    Possibe reason:
    1. Associated linkset (all links within this linkset) becomes unavailable,
    hence route to the point code also becomes unvailable throught this linkset.
    2. Remote peer is down

    Condition Clear Alarm:  A starMTP3PCAvailable notification will be generated when
    the reemore peer identified by the point code becomes reachable"

    --#SUMMARY "[ss7-routing-domain %d] mtp3 point code-%d through linkset-%d unavailable"
    --#ARGUMENTS {0,1,2}
    --#STATE DEGRADED
    --#SEVERITY MINOR
    ::= { starentTraps 1029 }

 starMTP3PCAvailable NOTIFICATION-TYPE
    OBJECTS { starSS7rdId, starSS7Pc, starSS7MTP3LinkSetId}
    STATUS  current
    DESCRIPTION
    "Message Transfer Part(MTP3) Route to the Point code becomes available.

    Possible reason:
    1. Associated linkset (one of the links in the linkset) becomes available.
    2. Remote peer is up

    starMTP3PCAvailable is generated only when a previous starMTP3PCUnavailable is generated.
    "
    --#SUMMARY "[ss7-routing-domain %d] mtp3 point code-%d through linkset-%d available"
    --#ARGUMENTS {0,1,2}
    --#STATE OPERATIONAL
    --#SEVERITY INFORMATIONAL
    ::= { starentTraps 1030 }

 starSS7PCUnavailable NOTIFICATION-TYPE
    OBJECTS { starSS7rdId, starSS7Pc}
    STATUS  current
    DESCRIPTION
    "SS7 Point code is unavailable, all the routes to this point code is unavailable.

    Possibe reason:
    1. All the routes (both M3UA and MTP3) to this point code becomes unavailable.

    Condition Clear Alarm:  A starSS7PCAvailable notification will be generated when
    the reemore peer identified by the point code becomes reachable"

    --#SUMMARY "[ss7-routing-domain %d] point code-%d unavailable"
    --#ARGUMENTS {0,1}
    --#STATE DEGRADED
    --#SEVERITY MINOR
    ::= { starentTraps 1031 }

 starSS7PCAvailable NOTIFICATION-TYPE
    OBJECTS { starSS7rdId, starSS7Pc}
    STATUS  current
    DESCRIPTION
    "SS7 Point code is available, one of the routes to this point code is available.

    Possible reason:
    1. One of the routes (either M3UA or MTP3) to this point code becomes available.

    starSS7PCAvailable is generated only when a previous starSS7PCUnavailable is generated.
    "
    --#SUMMARY "[ss7-routing-domain %d] point code-%d available"
    --#ARGUMENTS {0,1}
    --#STATE OPERATIONAL
    --#SEVERITY INFORMATIONAL
    ::= { starentTraps 1032 }

starASNPCServiceStart NOTIFICATION-TYPE
    OBJECTS { starServiceVpnName, starServiceServName }
    STATUS  obsolete
    DESCRIPTION
        "A WiMAX ASN Paging Controller (ASNPC) Service has started

	 Action to be Taken: No action required"
    --#SUMMARY "[Service ASNPC-%s-%s] ASNPC service has started"
    --#ARGUMENTS {0,1}
    --#STATE OPERATIONAL
    --#SEVERITY INFORMATIONAL
    ::= { starentTraps 1033 }

starASNPCServiceStop NOTIFICATION-TYPE
    OBJECTS { starServiceVpnName, starServiceServName }
    STATUS  obsolete
    DESCRIPTION
        "A WiMAX ASN Paging Controller (ASNPC) Service has stopped.

	 Probable Cause: This is typically caused by operator invention.  In
         unusual cases it can be caused by the loss of resources (PACs/PSCs) to
	 support the running configuration.

	 Action to be Taken: If the ASNPC service shutdown was not planned,
	 examine the admin logs for an indication of the failure.  Verify that
	 all configured PACs/PSCs are present and running in the system.  Check the
	 crash logs for an indication of a software failure.

	 Clear Condition: Verify that the ASNPC service is operational.

	 Condition Clear Alarm:  A starASNPCServiceStart notification will be generated when
	 the service is restarted"
    --#SUMMARY "[Service ASNPC-%s-%s] ASNPC service has stopped"
    --#ARGUMENTS {0,1}
    --#STATE DEGRADED
    --#SEVERITY MAJOR
    ::= { starentTraps 1034 }

starDiameterCapabilitiesExchangeFailure NOTIFICATION-TYPE
    OBJECTS { starDiameterVpnName, starDiameterPeerAddr, starDiameterEndpointName , starDiameterECode}
    STATUS  current
    DESCRIPTION
 	"Capability negotiations has failed and connections are down.

	 Problem Cause: Due to an error in Capability Exchange Answer received from the peer
	 the connections have been torn down.
	 "
    --#SUMMARY "[VPN %s]  Capability exchange for %s endpoint %s failed. Cause Code: %d"
    --#ARGUMENTS {0,1,2,3}
    --#STATE DEGRADED
    --#SEVERITY MAJOR
    ::= { starentTraps 1035 }

starDiameterCapabilitiesExchangeSuccess NOTIFICATION-TYPE
    OBJECTS { starDiameterVpnName, starDiameterPeerAddr, starDiameterEndpointName}
    STATUS  current
    DESCRIPTION
 	"A diameter server is up.  This notification is only generated for servers which
 	 have previously been declared unreachable."

    --#SUMMARY "[VPN %s]  Capability exchange for %s endpoint %s is a success"
    --#ARGUMENTS {0,1,2}
    --#STATE OPERATIONAL
    --#SEVERITY INFORMATIONAL
    ::= { starentTraps 1036 }

starSRPConnDown NOTIFICATION-TYPE
    OBJECTS { starContextName, starSRPIpAddress }
    STATUS  current
    DESCRIPTION
	"The connection to the standby SRP system is down.  While this connection is down, the
	 active system is operating without a standby and would be unable to perform an SRP
	 switchover.

	 Action to be Taken: Verify that the standby system is operational; verify the network
	 between systems is operational.

	 Clear Condition: This condition is cleared when the active system is reconnected to the
	 standby SRP system.

	 Condition Clear Alarm: A starSRPConnUp notification is generated when this condition is clear"
    --#SUMMARY "[System] SRP Connection Down, SRP standby vpn %s address %s"
    --#ARGUMENTS {0,1}
    --#STATE DEGRADED
    --#SEVERITY MAJOR
    ::= { starentTraps 1037 }

starSRPConnUp NOTIFICATION-TYPE
    OBJECTS { starContextName, starSRPIpAddress }
    STATUS  current
    DESCRIPTION
	"The connection to the standby SRP system is now up.  This notification is only generated
	 if a starSRPConnDown had previously been generated."
    --#SUMMARY "[System] SRP Connection Up, SRP standby vpn %s address %s"
    --#ARGUMENTS {0,1}
    --#STATE OPERATIONAL
    --#SEVERITY INFORMATIONAL
    ::= { starentTraps 1038 }

starDiameterIpv6PeerDown NOTIFICATION-TYPE
    OBJECTS { starDiameterVpnName, starDiameterPeerAddrIpv6, starDiameterEndpointName }
    STATUS  current
    DESCRIPTION
        "A diameter peer is down.  This diameter peer is reached using an IPv6 address.

         For IPv4-connected diameter peers, a starDiameterPeerDown notification
         would be generated.

         Problem Cause: The diameter peer has failed, or a network connectivity
         prevents reaching the peer.

         Condition Clear Alarm:  A starDiameterPeerUp notification will be generated when
         the peer is up"
    --#SUMMARY "[VPN %s] Diameter Peer %s endpoint %s is down"
    --#ARGUMENTS {0,1,2}
    --#STATE DEGRADED
    --#SEVERITY MAJOR
    ::= { starentTraps 1039 }

starDiameterIpv6PeerUp NOTIFICATION-TYPE
    OBJECTS { starDiameterVpnName, starDiameterPeerAddrIpv6, starDiameterEndpointName }
    STATUS  current
    DESCRIPTION
        "A diameter peer is up.  This diameter peer is reached using an IPv6 address.
         This notification is only generated for peers which have previously been declared down.

         For IPv4-connected diameter peers, a starDiameterPeerUp notification
         would be generated."
    --#SUMMARY "[VPN %s] Diameter Peer %s endpoint %s is up"
    --#ARGUMENTS {0,1,2}
    --#STATE OPERATIONAL
    --#SEVERITY INFORMATIONAL
    ::= { starentTraps 1040 }

starIPMSServerUnreachable NOTIFICATION-TYPE
    OBJECTS { starIPMSServerVpnName, starIPMSServerAddr }
    STATUS  current
    DESCRIPTION
        "An IPMS server is unreachable.

         Probable Cause: The IPMS server has failed, or a network connectivity
         issue prevents reaching the server.

         Condition Clear Alarm:  A starIPMSServerReachable notification will be generated
         when the server becomes reachable."
    --#SUMMARY "[VPN %s] IPMS Server %s is unreachable"
    --#ARGUMENTS {0,1}
    --#STATE DEGRADED
    --#SEVERITY MINOR
    ::= { starentTraps 1041 }

starIPMSServerReachable NOTIFICATION-TYPE
    OBJECTS { starIPMSServerVpnName, starIPMSServerAddr }
    STATUS  current
    DESCRIPTION
        "An IPMS server is reachable.  A starIPMSServerReachable notification is only
         generated for servers which had previously been declared unreachable."
    --#SUMMARY "[VPN %s] IPMS Server %s is reachable"
    --#ARGUMENTS {0,1}
    --#STATE OPERATIONAL
    --#SEVERITY INFORMATIONAL
    ::= { starentTraps 1042 }

starCertShortLifetime NOTIFICATION-TYPE
    OBJECTS { starCertSerialNumber, starCertIssuer, starCertExpiryTime }
    STATUS  current
    DESCRIPTION
        "A certificate is approaching its expiration.  The certificate is still valid,
         but should be updated with a new certificate.

         Action to be Taken: A new certificate should be created and configured on the system."
    --#SUMMARY "[System] Certificate short lifetime, certificate serial number %s, expiration date %s"
    --#ARGUMENTS {0,2}
    --#STATE OPERATIONAL
    --#SEVERITY INFORMATIONAL
    ::= { starentTraps 1043 }

starCertExpired NOTIFICATION-TYPE
    OBJECTS { starCertSerialNumber, starCertIssuer, starCertExpiryTime }
    STATUS  current
    DESCRIPTION
        "A certificate has expired.  The certificate is no longer valid.

         Action to be Taken: A new certificate should be created and configured on the system.

         Condition Clear Alarm: A starCertValid notification is sent when a new, valid, certificate
         is configured."
    --#SUMMARY "[System] Certificate expired, certificate serial number %s, expiration date %s"
    --#ARGUMENTS {0,2}
    --#STATE NONOPERATIONAL
    --#SEVERITY CRITICAL
    ::= { starentTraps 1044 }

starCertValid NOTIFICATION-TYPE
    OBJECTS { starCertSerialNumber, starCertIssuer, starCertExpiryTime }
    STATUS  current
    DESCRIPTION
        "A valid certificate has been configured.  This notification is only generated if a
         starCertExpired had been previously generated."
    --#SUMMARY "[System] Certificate valid, certificate serial number %s, expiration date %s"
    --#ARGUMENTS {0,2}
    --#STATE OPERATIONAL
    --#SEVERITY INFORMATIONAL
    ::= { starentTraps 1045 }

starFTPPushFail NOTIFICATION-TYPE
    OBJECTS { starFTPServVpnName, starFTPServIpAddr, starFileName, starFileApplication }
    STATUS  current
    DESCRIPTION
	"An FTP push operation has failed for the specified file to the specified server."
    --#SUMMARY "[System] FTP file push failure; server %s/%s, file %s (application %s)"
    --#ARGUMENTS { 0,1,2,3 }
    --#STATE OPERATIONAL
    --#SEVERITY INFORMATIONAL
    ::= { starentTraps 1046 }

starFTPServSwitch NOTIFICATION-TYPE
    OBJECTS { starFTPServVpnName, starFTPServIpAddr, starFTPServIpAddr, starFileApplication }
    STATUS  current
    DESCRIPTION
	"An FTP server switchover has been performed; that is, the system has determined
	 that an external FTP server is unreachable, and is not using an alternate FTP
	 server"
    --#SUMMARY "[System] FTP Server switchover; from server %s/%s to %s/%s (application %s)"
    --#ARGUMENTS { 0,1,0,2,3 }
    --#STATE OPERATIONAL
    --#SEVERITY INFORMATIONAL
    ::= { starentTraps 1047 }

starSDHSectionDown NOTIFICATION-TYPE
    OBJECTS { starSDHSlot, starSDHPort, starSDHOperState }
    STATUS current
    DESCRIPTION
	"The SDH interface on this port is down.  The starSDHOperState identifies the specific
	 issue.

	 Probable Cause:

	 Action to be Taken:

	 Condition Clear Alarm: This condition is cleared by a starSDHSectionUp notification,"
    --#SUMMARY "[Port %d-%d] SDH Down, operstate %x"
    --#ARGUMENTS {0,1,2}
    --#STATE NONOPERATIONAL
    --#SEVERITY MAJOR
    ::= { starentTraps 1048 }

starSDHSectionUp NOTIFICATION-TYPE
    OBJECTS { starSDHSlot, starSDHPort }
    STATUS current
    DESCRIPTION
	"The SDH interface on this port is now up.  A starSDHSectionUp notification is only generated
	 if a starSDHSectionDown was previously generated for this port."
    --#SUMMARY "[Port %d-%d] SDH Up"
    --#ARGUMENTS {0,1}
    --#STATE OPERATIONAL
    --#SEVERITY INFORMATIONAL
    ::= { starentTraps 1049 }

starSDHPathHopDown NOTIFICATION-TYPE
    OBJECTS { starSDHPathSlot, starSDHPathPort, starSDHPathNum, starSDHPathOperState }
    STATUS current
    DESCRIPTION
	"The identified SDH Path is down.  The value of starSDHPathOperState identifies the
	 specific failure bits."
    --#SUMMARY "[Port %d-%d] SDH Path down, path %d, operstate %x"
    --#ARGUMENTS {0,1,2,3}
    --#STATE DEGRADED
    --#SEVERITY MAJOR
    ::= { starentTraps 1050 }

starSDHPathHopUp NOTIFICATION-TYPE
    OBJECTS { starSDHPathSlot, starSDHPathPort, starSDHPathNum }
    STATUS current
    DESCRIPTION
	"The identified SDH Path is up."
    --#SUMMARY "[Port %d-%d] SDH Path up, path %d"
    --#ARGUMENTS {0,1,2}
    --#STATE OPERATIONAL
    --#SEVERITY INFORMATIONAL
    ::= { starentTraps 1051 }

starSDHLopDown NOTIFICATION-TYPE
    OBJECTS { starE1TribSlot, starE1TribPort, starE1TribPath, starE1TribTug2, starE1TribTu12, starE1TribOperStateLOP }
    STATUS current
    DESCRIPTION
	"The identified E1 Tributary on this port is down.  The value of starE1TribOperStateLOP identifies
	 the specific failure bits.

	 Probable Cause:

	 Action to be Taken:

	 Condition Clear Alarm: This condition is cleared by a starSDHLopDown notification,"
    --#SUMMARY "[Port %d-%d] E1 Tributary down, path %d, E1 tributary %d/%d, LOP operstate %x"
    --#ARGUMENTS {0,1,2,3,4,5}
    --#STATE DEGRADED
    --#SEVERITY MAJOR
    ::= { starentTraps 1052 }

starSDHLopUp NOTIFICATION-TYPE
    OBJECTS { starE1TribSlot, starE1TribPort, starE1TribPath, starE1TribTug2, starE1TribTu12 }
    STATUS current
    DESCRIPTION
	"The identified E1 Tributary on this port is now up.  A starE1TributaryUp notification is
	 only generated if a starSDHLopDown was previously generated for this E1 tributary."
    --#SUMMARY "[Port %d-%d] E1 Tributary up, path %d, E1 tributary %d/%d"
    --#ARGUMENTS {0,1,2,3,4}
    --#STATE OPERATIONAL
    --#SEVERITY INFORMATIONAL
    ::= { starentTraps 1053 }

starIMSUEServiceStart NOTIFICATION-TYPE
    OBJECTS { starServiceVpnName, starServiceServName }
    STATUS  current
    DESCRIPTION
        "A IMSUE Service has started

         Action to be Taken: No action required"
    --#SUMMARY "[Service IMSUE-%s-%s] IMSUE service has started"
    --#ARGUMENTS {0,1}
    --#STATE OPERATIONAL
    --#SEVERITY INFORMATIONAL
    ::= { starentTraps 1054 }

starIMSUEServiceStop NOTIFICATION-TYPE
    OBJECTS { starServiceVpnName, starServiceServName }
    STATUS  current
    DESCRIPTION
        "A IMSUE Service has stopped.

         Probable Cause: This is typically caused by operator invention.  In
         rare cases it can be caused by the loss of resources (PACs/PSCs) to
         support the running configuration.

         Action to be Taken: If the IMSUE service shutdown was not planned,
         examine the admin logs for an indication of the failure.  Verify that
         all configured PACs are present and running in the system.  Check the
         crash logs for an indication of a software failure.

         Clear Condition: Verify that the IMSUE service is operational.

         Condition Clear Alarm:  A starIMSUEServiceStart notification will be
         generated when the service is restarted"
    --#SUMMARY "[Service IMSUE-%s-%s] IMSUE service has stopped"
    --#ARGUMENTS {0,1}
    --#STATE DEGRADED
    --#SEVERITY MAJOR
    ::= { starentTraps 1055 }

 starSS7PCCongested NOTIFICATION-TYPE
    OBJECTS { starSS7rdId, starSS7Pc, starSS7CongLevel, starSS7LocalCong}
    STATUS  current
    DESCRIPTION
    "SS7 Point code is congested, all the routes to this point-code is congested.

    Possible reason:
    1. All the routes (both M3UA and MTP3) to this Point Code have become congested.

    Condition Clear Alarm:  A starSS7PCCongestionCleared notification will be generated when the congestion gets cleared for any one of the routes
    "
    --#SUMMARY "[ss7-routing-domain %d] point code-%d %d congested level-%d"
    --#ARGUMENTS {0,1,2,3}
    --#STATE DEGRADED
    --#SEVERITY MAJOR
    ::= { starentTraps 1056 }

 starSS7PCCongestionCleared NOTIFICATION-TYPE
    OBJECTS { starSS7rdId, starSS7Pc, starSS7CongLevel, starSS7LocalCong}
    STATUS  current
    DESCRIPTION
    "SS7 Point code Congestion gets cleared, one of the routes to this point-code is cleared from congestion.

    Possible reason:
    1. One of the routes (either M3UA or MTP3) to this Point Code has resumed from congestion.

    starSS7PCCongestionCleared is generated only when a previous starSS7PCCongested is generated.
    "
    --#SUMMARY "[ss7-routing-domain %d] point code-%d %d congestion cleared level-%d"
    --#ARGUMENTS {0,1,2,3}
    --#STATE OPERATIONAL
    --#SEVERITY INFORMATIONAL
    ::= { starentTraps 1057 }

starPHSGWServiceStart NOTIFICATION-TYPE
    OBJECTS { starServiceVpnName, starServiceServName }
    STATUS  obsolete
    DESCRIPTION
        "A PHS-GW Service has started

         Action to be Taken: No action required"
    --#SUMMARY "[Service PHW-GW-%s-%s] PHS-GW service has started"
    --#ARGUMENTS {0,1}
    --#STATE OPERATIONAL
    --#SEVERITY INFORMATIONAL
    ::= { starentTraps 1058 }

starPHSGWServiceStop NOTIFICATION-TYPE
    OBJECTS { starServiceVpnName, starServiceServName }
    STATUS  obsolete
    DESCRIPTION
        "A PHS-GW Service has stopped.

         Probable Cause: This is typically caused by operator invention.  In
         rare cases it can be caused by the loss of resources (PACs/PSCs) to
         support the running configuration.

         Action to be Taken: If the PHS-GW service shutdown was not planned,
         examine the admin logs for an indication of the failure.  Verify that
         all configured PACs are present and running in the system.  Check the
         crash logs for an indication of a software failure.

         Clear Condition: Verify that the PHS-GW service is operational.

         Condition Clear Alarm:  A starPHSGWServiceStart notification will be
	 generated when the service is restarted"
    --#SUMMARY "[Service PHS-GW-%s-%s] PHS-GW service has stopped"
    --#ARGUMENTS {0,1}
    --#STATE DEGRADED
    --#SEVERITY MAJOR
    ::= { starentTraps 1059 }

starGPRSServiceStart NOTIFICATION-TYPE
    OBJECTS { starServiceVpnName, starServiceServName}
    STATUS  current
    DESCRIPTION
    "A GPRS Service has started
    Action to be Taken: No action required"
    --#SUMMARY "[Service GPRS %s-%s] GPRS service has started"
    --#ARGUMENTS {0,1}
    --#STATE OPERATIONAL
    --#SEVERITY INFORMATIONAL
    ::= { starentTraps 1060 }

starGPRSServiceStop NOTIFICATION-TYPE
    OBJECTS { starServiceVpnName , starServiceServName}
    STATUS  current
    DESCRIPTION
    "A GPRS Service has stopped.
    Probable Cause:
    In unusual cases it can be caused by the loss of resources (PACs/PSCs) to
    support the running configuration.This can also happen due to some misconfiguration of the
    service parameters.

    Action to be Taken: If the GPRS service shutdown was not planned,
    examine the admin logs for an indication of the failure.  Verify that
    all configured PACs/PSCs are present and running in the system.  Check the
    crash logs for an indication of a software failure.

    Clear Condition: Verify that the GPRS service is operational.

    Condition Clear Alarm:  A starGPRSServiceStart notification will be generated when
    the service is restarted"
    --#SUMMARY "[Service GPRS %s-%s] GPRS service has stopped"
    --#ARGUMENTS {0,1}
    --#STATE DEGRADED
    --#SEVERITY MAJOR
    ::= { starentTraps 1061 }

starGPRSNseDown NOTIFICATION-TYPE
    OBJECTS { starGPRSNsei }
    STATUS  current
    DESCRIPTION
    "Network Service Entity (NSE) is down.

    Possible reason:
    The Last NSVC(Network Service virtual circuit in the NSE is down.

    Condition Clear Alarm: A starGPRSNseUp will be generated when at least one NSVC in the NSE comes up"

    --#SUMMARY "[nsei %d] NSE down "
    --#ARGUMENTS {0}
    --#STATE DEGRADED
    --#SEVERITY MAJOR
    ::= { starentTraps 1062 }

starGPRSNseUp NOTIFICATION-TYPE
    OBJECTS { starGPRSNsei }
    STATUS  current
    DESCRIPTION
    "Network Service Entity (NSE) is up.

    Possible reason:
    The First NSVC(Network Service virtual circuit in the NSE is up.

    starGPRSNseUp is generated only when a previous starGPRSNseDown has been generated"

    --#SUMMARY "[nsei %d] NSE Up"
    --#ARGUMENTS {0}
    --#STATE OPERATIONAL
    --#SEVERITY INFORMATIONAL
    ::= { starentTraps 1063 }

starGPRSNsvcDown NOTIFICATION-TYPE
    OBJECTS { starGPRSNsei, starGPRSNsvci }
    STATUS  current
    DESCRIPTION
    "Network Service Entity Virtual Circuit (NSVC) is down.

    Possible reasons:
    1) NS_ALIVE heartbeat messages sent from the Serving GPRS support Node (SGSN) were not acknowledged by the Base Station Subsystem(BSS)
       for a configured number of maximum retries.

    This trap is generated only when an NSVC goes down due to reasons other than physical port failure. A separate trap
    is generated for a physical port failure event.

    Condition Clear Alarm: A starGPRSNsvcUp will be generated when the NSVC comes up"

    --#SUMMARY "[nsei %d] nsvci %d NSVC is down "
    --#ARGUMENTS {0,1}
    --#STATE DEGRADED
    --#SEVERITY MAJOR
    ::= { starentTraps 1064 }

starGPRSNsvcUp NOTIFICATION-TYPE
    OBJECTS { starGPRSNsei, starGPRSNsvci }
    STATUS  current
    DESCRIPTION
    "An Network Service Entity Virtual Circuit (NSVC) comes up
    An starGPRSNsvcUp trap is generated only when a previous starGPRSNsvcDown was generated"
    --#SUMMARY "[nsei %d] nsvci %d NSVC is up"
    --#ARGUMENTS {0,1}
    --#STATE OPERATIONAL
    --#SEVERITY INFORMATIONAL
    ::= { starentTraps 1065 }

starGPRSBvcDown NOTIFICATION-TYPE
    OBJECTS { starGPRSNsei, starGPRSBvci }
    STATUS  current
    DESCRIPTION
    "Base Station Subsystem (BSS) GPRS (General Packet Radio Service) Protocol (BSSGP) Virtual Circuit (BVC) is Down.

    Possible reason:
    1) ALL Network Service Entity Virtual Circuit (NSVC) associated with this BVC are down

    Condition Clear Alarm: A starGPRSBvcUp will be generated when the BVC is available"

    --#SUMMARY "[nsei %d] bvci %d BVC is down"
    --#ARGUMENTS {0,1}
    --#STATE DEGRADED
    --#SEVERITY MAJOR
    ::= { starentTraps 1066 }

starGPRSBvcUp NOTIFICATION-TYPE
    OBJECTS { starGPRSNsei, starGPRSBvci }
    STATUS  current
    DESCRIPTION
    "Base Station Subsystem (BSS) GPRS ((General Packet Radio Service) Protocol (BSSGP) Virtual Circuit (BVC) is Up

    Possible reasons:

    1) Atleast one NSVC associated with the BVC becomes available.

    starGPRSBvcUp is generated only when a previous starGPRSBvcDown has been generated.
    "
    --#SUMMARY "[nsei %d] bvci %d BVC Up"
    --#ARGUMENTS {0,1}
    --#STATE OPERATIONAL
    --#SEVERITY INFORMATIONAL
    ::= { starentTraps 1067 }

starSDHE1TribDown NOTIFICATION-TYPE
    OBJECTS { starE1TribSlot, starE1TribPort, starE1TribPath, starE1TribTug2, starE1TribTu12, starE1TribOperState }
    STATUS current
    DESCRIPTION
	"The identified E1 Tributary on this port is down.

	 Probable Cause:

	 Action to be Taken:

	 Condition Clear Alarm: This condition is cleared by a starSDHTugUp notification,"
    --#SUMMARY "[Port %d-%d] E1 Tributary down, path %d, E1 tributary %d/%d, operstate %x"
    --#ARGUMENTS {0,1,2,3,4,5}
    --#STATE DEGRADED
    --#SEVERITY MAJOR
    ::= { starentTraps 1068 }

starSDHE1TribUp NOTIFICATION-TYPE
    OBJECTS { starE1TribSlot, starE1TribPort, starE1TribPath, starE1TribTug2, starE1TribTu12 }
    STATUS current
    DESCRIPTION
	"The identified E1 Tributary on this port is up."
    --#SUMMARY "[Port %d-%d] E1 Tributary up, path %d, E1 tributary %d/%d"
    --#ARGUMENTS {0,1,2,3,4}
    --#STATE OPERATIONAL
    --#SEVERITY INFORMATIONAL
    ::= { starentTraps 1069 }

starSDHFractE1LMIDown NOTIFICATION-TYPE
    OBJECTS { starFractE1TribSlot, starFractE1TribPort, starFractE1TribPath, starFractE1TribTug2, starFractE1TribTu12, starFractE1TribTimeslots }
    STATUS current
    DESCRIPTION
	"The identified fractional E1 Tributary on this port is down."
    --#SUMMARY "[Port %d-%d] Fractional E1 LMI down, path %d, E1 tributary %d/%d, timeslots %s"
    --#ARGUMENTS {0,1,2,3,4,5}
    --#STATE DEGRADED
    --#SEVERITY MAJOR
    ::= { starentTraps 1070 }

starSDHFractE1LMIUp NOTIFICATION-TYPE
    OBJECTS { 
                starFractE1TribSlot, 
                starFractE1TribPort, 
                starFractE1TribPath, 
                starFractE1TribTug2, 
                starFractE1TribTu12, 
                starFractE1TribTimeslots 
            }
    STATUS current
    DESCRIPTION
	"The identified fractional E1 Tributary on this port is up."
    --#SUMMARY "[Port %d-%d] Fractional E1 up, path %d, E1 tributary %d/%d, timeslots %s"
    --#ARGUMENTS {0,1,2,3,4,5}
    --#STATE OPERATIONAL
    --#SEVERITY INFORMATIONAL
    ::= { starentTraps 1071 }

starPHSPCServiceStart NOTIFICATION-TYPE
    OBJECTS { starServiceVpnName, starServiceServName }
    STATUS  obsolete
    DESCRIPTION
        "A PHS-PC Service has started

         Action to be Taken: No action required"
    --#SUMMARY "[Service PHS-PC-%s-%s] PHS-PC service has started"
    --#ARGUMENTS {0,1}
    --#STATE OPERATIONAL
    --#SEVERITY INFORMATIONAL
    ::= { starentTraps 1072 }

starPHSPCServiceStop NOTIFICATION-TYPE
    OBJECTS { starServiceVpnName, starServiceServName }
    STATUS  obsolete
    DESCRIPTION
        "A PHS-PC Service has stopped.

         Probable Cause: This is typically caused by operator invention.  In
         rare cases it can be caused by the loss of resources (PACs/PSCs) to
         support the running configuration.

         Action to be Taken: If the PHS-PC service shutdown was not planned,
         examine the admin logs for an indication of the failure.  Verify that
         all configured PACs are present and running in the system.  Check the
         crash logs for an indication of a software failure.

         Clear Condition: Verify that the PHS-PC service is operational.

         Condition Clear Alarm:  A starPHSPCServiceStart notification will be
	 generated when the service is restarted"
    --#SUMMARY "[Service PHS-PC-%s-%s] PHS-PC service has stopped"
    --#ARGUMENTS {0,1}
    --#STATE DEGRADED
    --#SEVERITY MAJOR
    ::= { starentTraps 1073 }

 starM3UAPSPCongested NOTIFICATION-TYPE
    OBJECTS { starSS7rdId, starSS7M3UAPsId, starSS7M3UAPspId, starSS7Pc, starSS7CongLevel}
    STATUS  current
    DESCRIPTION
    "Peer Server Process (PSP) link is congested, when the congestion queue size rises above the threshold limit.

    Possible reason:
    1. No Stream Control Transmission Protocol (SCTP) Acknowledgement from peer end due to packet loss
    2. Acknowledgement with zero window size

    Condition Clear Alarm:  A starM3UAPSPCongestionCleared notification will be generated when the congestion queue size goes below the threshold limit
    "
    --#SUMMARY "[ss7-routing-domain %d] peer-server-%d peer-server-porcess-%d (point-code-%d) congested"
    --#ARGUMENTS {0,1,2,3}
    --#STATE DEGRADED
    --#SEVERITY MAJOR
    ::= { starentTraps 1074 }

 starM3UAPSPCongestionCleared NOTIFICATION-TYPE
    OBJECTS { starSS7rdId, starSS7M3UAPsId, starSS7M3UAPspId, starSS7Pc, starSS7CongLevel}
    STATUS  current
    DESCRIPTION
    "Peer Server Process (PSP) link Congestion gets cleared, when the congestion queue size goes below the threshold limit.
    starM3UAPSPCongestionCleared is generated only when a previous starM3UAPSPCongested is generated.
    "
    --#SUMMARY "[ss7-routing-domain %d] peer-server-%d peer-server-porcess-%d (point-code-%d) congestion cleared"
    --#ARGUMENTS {0,1,2,3}
    --#STATE OPERATIONAL
    --#SEVERITY INFORMATIONAL
    ::= { starentTraps 1075 }

starStorageFailed NOTIFICATION-TYPE
    OBJECTS { starStorageSlot, starStorageName }
    STATUS  current
    DESCRIPTION
	"The specified storage device has failed.  This storage device is now out of service
	 and cannot be used to store additional data.

	 This notification is currently only generated for failures on the hard drive attached
	 to the SMC card.

	 Probable Cause: A hardware failure on the device; a hardware failure on the card
	 to which the device is attached.

	 Action to be Taken: Replace the card

	 Condition Clear Alarm: A starCardRemoved notification will be generated when the
	 card is removed from the chassis."
    --#SUMMARY "[Slot-%d] Storage device %s failed"
    --#ARGUMENTS {0,1}
    --#STATE DEGRADED
    --#SEVERITY MAJOR
    ::= { starentTraps 1076 }

starRaidFailed NOTIFICATION-TYPE
    OBJECTS { starStorageName }
    STATUS  current
    DESCRIPTION
	"The specified raid array has failed.  The raid array can no longer be used to
	 store data.

	 Probable Cause: Hardware failure(s) on the devices within the raid array;
	 Hardware failure(s) on the card(s) to which the devices are attached;
	 the removal of the cards containing devices in the array; operator action
	 which disabled the raid array.

	 Condition Clear Alarm: a starRaidStarted notification will be generated when the
	 raid array is online."
    --#SUMMARY "[System] Raid array %s failed"
    --#ARGUMENTS {0}
    --#STATE DEGRADED
    --#SEVERITY MAJOR
    ::= { starentTraps 1077 }

starRaidStarted NOTIFICATION-TYPE
    OBJECTS { starStorageName }
    STATUS  current
    DESCRIPTION
	"The specific raid array has resumed operation.  This notification is only generated
	 if a starRaidFailed notification was previously generated for this array."
    --#SUMMARY "[System] Raid array %s started"
    --#ARGUMENTS {0}
    --#STATE OPERATIONAL
    --#SEVERITY INFORMATIONAL
    ::= { starentTraps 1078 }

starRaidDegraded NOTIFICATION-TYPE
    OBJECTS { starStorageName, starStorageSlot, starStorageName }
    STATUS  current
    DESCRIPTION
	"The specified raid array is running in a degraded state.  This typically means
	 one of the member devices has failed or become unavailable.  The raid array
	 continues to function and can read/store data, but may not be operating in
	 a redundant manner.

	 Probable Cause: Hardware failure(s) on the devices within the raid array;
	 Hardware failure(s) on the card(s) to which the devices are attached;
	 the removal of the cards containing devices in the array; operator action
	 which disabled the raid array.

	 The first variable binding, starStorageName is indicating the raid array 
	 name; The second variable binding, starStorageSlot is the disk card number,
	 in which the fail happens; The third varbind, which is also the second
	 starStorageName, is the name of the disk that the fail happens.	 
	 
	 Condition Clear Alarm: a starRaidRecovered notification will be generated when the
	 raid array is fully recovered."
    --#SUMMARY "[System] Raid array %s degraded; slot/device %d/%s unavailable"
    --#ARGUMENTS {0,1,2}
    --#STATE DEGRADED
    --#SEVERITY MAJOR
    ::= { starentTraps 1079 }

starRaidRecovered NOTIFICATION-TYPE
    OBJECTS { starStorageName, starStorageSlot, starStorageName }
    STATUS  current
    DESCRIPTION
	"The specific raid array has been recovered and is running in its normal,
	 redundant state.  This notification is only generated if a starRaidDegraded
	 notification was previously generated for this array. As to the variable
	 bindings, please refer to the trap starRaidDegraded.
	 "
    --#SUMMARY "[System] Raid array %s recovered; slot/device %d/%s added to array"
    --#ARGUMENTS {0,1,2}
    --#STATE OPERATIONAL
    --#SEVERITY INFORMATIONAL
    ::= { starentTraps 1080 }

starPGWServiceStart NOTIFICATION-TYPE
    OBJECTS { starServiceVpnName, starServiceServName }
    STATUS  current
    DESCRIPTION
        "A Packet Data Network Gateway (PGW) Service has started.

         Action to be Taken: No action required"
    --#SUMMARY "[Service PGW-%s-%s] PGW service has started"
    --#ARGUMENTS {0,1}
    --#STATE OPERATIONAL
    --#SEVERITY INFORMATION
    ::= { starentTraps 1081 }

starPGWServiceStop NOTIFICATION-TYPE
    OBJECTS { starServiceVpnName, starServiceServName }
    STATUS  current
    DESCRIPTION
        "A Packet Data Network Gateway (PGN) Service has stopped.

         Probable Cause: This is typically caused by operator intervention.  In
         rare cases it can be caused by the loss of resources (PSCs) to support
         the running configuration.

         Action to be Taken: If the PGW service shutdown was not planned,
         examine the admin logs for an indication of the failure.  Verify that
         all configured PSCs are present and running in the system.  Check the
         crash logs for an indication of a software failure.

         Clear Condition: Verify that the PGW service is operational.

         Condition Clear Alarm:  A starPGWServiceStart notification will be
         generated when the service is restarted"
    --#SUMMARY "[Service PGW-%s-%s] PGW service has stopped"
    --#ARGUMENTS {0,1}
    --#STATE DEGRADED
    --#SEVERITY MAJOR
    ::= { starentTraps 1082 }

starSGWServiceStart NOTIFICATION-TYPE
    OBJECTS { starServiceVpnName, starServiceServName }
    STATUS  current
    DESCRIPTION
        "A Serving Gateway (SGW) Service has started.

         Action to be Taken: No action required"
    --#SUMMARY "[Service SGW-%s-%s] SGW service has started"
    --#ARGUMENTS {0,1}
    --#STATE OPERATIONAL
    --#SEVERITY INFORMATION
    ::= { starentTraps 1083 }

starSGWServiceStop NOTIFICATION-TYPE
    OBJECTS { starServiceVpnName, starServiceServName }
    STATUS  current
    DESCRIPTION
        "A Serving Gateway (SGW) Service has stopped.

         Probable Cause: This is typically caused by operator intervention.  In
         rare cases it can be caused by the loss of resources (PSCs) to support
         the running configuration.

         Action to be Taken: If the SGW service shutdown was not planned,
         examine the admin logs for an indication of the failure.  Verify that
         all configured PSCs are present and running in the system.  Check the
         crash logs for an indication of a software failure.

         Clear Condition: Verify that the SGW service is operational.

         Condition Clear Alarm:  A starSGWServiceStart notification will be
         generated when the service is restarted"
    --#SUMMARY "[Service SGW-%s-%s] SGW service has stopped"
    --#ARGUMENTS {0,1}
    --#STATE DEGRADED
    --#SEVERITY MAJOR
    ::= { starentTraps 1084 }

starEGTPServiceStart NOTIFICATION-TYPE
    OBJECTS { starServiceVpnName, starServiceServName }
    STATUS  current
    DESCRIPTION
        "An Evolved GPRS Tunneling Protocol (EGTP) Service has started.

         Action to be Taken: No action required"
    --#SUMMARY "[Service EGTP-%s-%s] EGTP service has started"
    --#ARGUMENTS {0,1}
    --#STATE OPERATIONAL
    --#SEVERITY INFORMATION
    ::= { starentTraps 1085 }

starEGTPServiceStop NOTIFICATION-TYPE
    OBJECTS { starServiceVpnName, starServiceServName }
    STATUS  current
    DESCRIPTION
        "An Evolved GPRS Tunneling Protocol (EGTP) Service has stopped.

         Probable Cause: This is typically caused by operator intervention.  In
         rare cases it can be caused by the loss of resources (PSCs) to support
         the running configuration.

         Action to be Taken: If the EGTP service shutdown was not planned,
         examine the admin logs for an indication of the failure.  Verify that
         all configured PSCs are present and running in the system.  Check the
         crash logs for an indication of a software failure.

         Clear Condition: Verify that the EGTP service is operational.

         Condition Clear Alarm:  A starEGTPServiceStart notification will be
         generated when the service is restarted"
    --#SUMMARY "[Service EGTP-%s-%s] EGTP service has stopped"
    --#ARGUMENTS {0,1}
    --#STATE DEGRADED
    --#SEVERITY MAJOR
    ::= { starentTraps 1086 }

starLMAServiceStart NOTIFICATION-TYPE
    OBJECTS { starServiceVpnName, starServiceServName }
    STATUS  current
    DESCRIPTION
        "A Local Mobility Anchor (LMA) Service has started.

         Action to be Taken: No action required"
    --#SUMMARY "[Service LMA-%s-%s] LMA service has started"
    --#ARGUMENTS {0,1}
    --#STATE OPERATIONAL
    --#SEVERITY INFORMATION
    ::= { starentTraps 1087 }

starLMAServiceStop NOTIFICATION-TYPE
    OBJECTS { starServiceVpnName, starServiceServName }
    STATUS  current
    DESCRIPTION
        "A Local Mobility Anchor (LMA) Service has stopped.

         Probable Cause: This is typically caused by operator intervention.  In
         rare cases it can be caused by the loss of resources (PSCs) to support
         the running configuration.

         Action to be Taken: If the LMA service shutdown was not planned,
         examine the admin logs for an indication of the failure.  Verify that
         all configured PSCs are present and running in the system.  Check the
         crash logs for an indication of a software failure.

         Clear Condition: Verify that the LMA service is operational.

         Condition Clear Alarm:  A starLMAServiceStart notification will be
         generated when the service is restarted"
    --#SUMMARY "[Service LMA-%s-%s] LMA service has stopped"
    --#ARGUMENTS {0,1}
    --#STATE DEGRADED
    --#SEVERITY MAJOR
    ::= { starentTraps 1088 }

starMAGServiceStart NOTIFICATION-TYPE
    OBJECTS { starServiceVpnName, starServiceServName }
    STATUS  current
    DESCRIPTION
        "A Mobile Access Gateway (MAG) Service has started.

         Action to be Taken: No action required"
    --#SUMMARY "[Service MAG-%s-%s] MAG service has started"
    --#ARGUMENTS {0,1}
    --#STATE OPERATIONAL
    --#SEVERITY INFORMATION
    ::= { starentTraps 1089 }

starMAGServiceStop NOTIFICATION-TYPE
    OBJECTS { starServiceVpnName, starServiceServName }
    STATUS  current
    DESCRIPTION
        "A MAG Service has stopped.

         Probable Cause: This is typically caused by operator intervention.  In
         rare cases it can be caused by the loss of resources (PSCs) to support
         the running configuration.

         Action to be Taken: If the MAG service shutdown was not planned,
         examine the admin logs for an indication of the failure.  Verify that
         all configured PSCs are present and running in the system.  Check the
         crash logs for an indication of a software failure.

         Clear Condition: Verify that the MAG service is operational.

         Condition Clear Alarm:  A starMAGServiceStart notification will be
         generated when the service is restarted"
    --#SUMMARY "[Service MAG-%s-%s] MAG service has stopped"
    --#ARGUMENTS {0,1}
    --#STATE DEGRADED
    --#SEVERITY MAJOR
    ::= { starentTraps 1090 }

starMMEServiceStart NOTIFICATION-TYPE
    OBJECTS { starServiceVpnName, starServiceServName }
    STATUS  current
    DESCRIPTION
        "A Mobility Management Entity (MME) Service has started.

         Action to be Taken: No action required"
    --#SUMMARY "[Service MME-%s-%s] MME service has started"
    --#ARGUMENTS {0,1}
    --#STATE OPERATIONAL
    --#SEVERITY INFORMATION
    ::= { starentTraps 1091 }

starMMEServiceStop NOTIFICATION-TYPE
    OBJECTS { starServiceVpnName, starServiceServName }
    STATUS  current
    DESCRIPTION
        "A Mobility Management Entity (MME) Service has stopped.

         Probable Cause: This is typically caused by operator intervention.  In
         rare cases it can be caused by the loss of resources (PSCs) to support
         the running configuration.

         Action to be Taken: If the MME service shutdown was not planned,
         examine the admin logs for an indication of the failure.  Verify that
         all configured PSCs are present and running in the system.  Check the
         crash logs for an indication of a software failure.

         Clear Condition: Verify that the MME service is operational.

         Condition Clear Alarm:  A starMMEServiceStart notification will be
         generated when the service is restarted"
    --#SUMMARY "[Service MME-%s-%s] MME service has stopped"
    --#ARGUMENTS {0,1}
    --#STATE DEGRADED
    --#SEVERITY MAJOR
    ::= { starentTraps 1092 }

starHSGWServiceStart NOTIFICATION-TYPE
    OBJECTS { starServiceVpnName, starServiceServName }
    STATUS  current
    DESCRIPTION
        "A HRPD Serving Gateway (HSGW) Service has started.

         Action to be Taken: No action required"
    --#SUMMARY "[Service HSGW-%s-%s] HSGW service has started"
    --#ARGUMENTS {0,1}
    --#STATE OPERATIONAL
    --#SEVERITY INFORMATION
    ::= { starentTraps 1093 }

starHSGWServiceStop NOTIFICATION-TYPE
    OBJECTS { starServiceVpnName, starServiceServName }
    STATUS  current
    DESCRIPTION
        "A HRPD Serving Gateway (HSGW) Service has stopped.

         Probable Cause: This is typically caused by operator intervention.  In
         rare cases it can be caused by the loss of resources (PSCs) to support
         the running configuration.

         Action to be Taken: If the HSGW service shutdown was not planned,
         examine the admin logs for an indication of the failure.  Verify that
         all configured PSCs are present and running in the system.  Check the
         crash logs for an indication of a software failure.

         Clear Condition: Verify that the HSGW service is operational.

         Condition Clear Alarm:  A starHSGWServiceStart notification will be
         generated when the service is restarted"
    --#SUMMARY "[Service HSGW-%s-%s] HSGW service has stopped"
    --#ARGUMENTS {0,1}
    --#STATE DEGRADED
    --#SEVERITY MAJOR
    ::= { starentTraps 1094 }

starCPUBusyClear NOTIFICATION-TYPE
    OBJECTS { starCPUSlot, starCPUNumber }
    STATUS  current
    DESCRIPTION
        "The CPU is no longer busy."
    --#SUMMARY "[Card %d] CPU %d is no longer experiencing very high usage"
    --#ARGUMENTS {0,1}
    --#STATE OPERATIONAL
    --#SEVERITY INFORMATIONAL
    ::= { starentTraps 1095 }

starCPUMemoryLowClear NOTIFICATION-TYPE
    OBJECTS { starCPUSlot, starCPUNumber }
    STATUS  current
    DESCRIPTION
        "The CPU is no longer experiencing a low memory condition."
    --#SUMMARY "[Card %d] CPU %d is no longer low on available memory"
    --#ARGUMENTS {0,1}
    --#STATE OPERATIONAL
    --#SEVERITY INFORMATIONAL
    ::= { starentTraps 1096 }

-- FNG Service

  starFNGServiceStart NOTIFICATION-TYPE
    OBJECTS { starServiceVpnName, starServiceServName }
    STATUS  current
    DESCRIPTION
        "A FNG Service has started
        Action to be Taken: No action required"
        --#SUMMARY "[Service FNG-%s-%s] FNG service has started"
        --#ARGUMENTS {0,1}
        --#STATE OPERATIONAL
        --#SEVERITY INFORMATIONAL
    ::= { starentTraps 1097 }

  starFNGServiceStop NOTIFICATION-TYPE
    OBJECTS { starServiceVpnName, starServiceServName }
    STATUS  current
    DESCRIPTION
        "A FNG Service has stopped.
        Probable Cause: This is typically caused by operator invention.  In
        rare cases it can be caused by the loss of resources (PACs) to
        support the running configuration.

        Action to be Taken: If the FNG service shutdown was not planned,
        examine the admin logs for an indication of the failure.  Verify that
        all configured PACs are present and running in the system.  Check the
        crash logs for an indication of a software failure.

        Clear Condition: Verify that the FNG service is operational.

        Condition Clear Alarm:  A starFNGServiceStart notification will be generated when
        the service is restarted"

        --#SUMMARY "[Service FNG-%s-%s] FNG service has stopped"
        --#ARGUMENTS {0,1}
        --#STATE DEGRADED
        --#SEVERITY MAJOR
    ::= { starentTraps 1098 }

starManagerRestart NOTIFICATION-TYPE
    OBJECTS { starTaskFacilityName, starTaskInstance, starTaskCard, starTaskCPU }
    STATUS  current
    DESCRIPTION
        "The identified manager task has been restarted."
    --#SUMMARY "[System] Manager %s/%d restarted on %d/%d"
    --#ARGUMENTS {0,1,2,3}
    --#STATE OPERATIONAL
    --#SEVERITY INFORMATIONAL
    ::= { starentTraps 1099 }

starConfigurationUpdate NOTIFICATION-TYPE
    STATUS  current
    DESCRIPTION
	"The configuration of the chassis has been changed.  This notification is
	 generated based on a periodic polling of the chassis, it is not real-time
         generated based on individual changes.  The configuration change could
         have been made via CLI sessions, CORBA management operations, or other
         methods.

         This notification is not generated by default; it is only generated if the
         configuration polling mechanism is specifically enabled."
    --#SUMMARY "[System] System configuration updated"
    --#STATE OPERATIONAL
    --#SEVERITY INFORMATIONAL
    ::= { starentTraps 1100 }

-- PDG Service

starPDGServiceStart NOTIFICATION-TYPE
    OBJECTS { starServiceVpnName, starServiceServName }
    STATUS  current
    DESCRIPTION
        "A PDG Service has started
        Action to be Taken: No action required"
        --#SUMMARY "[Service PDG-%s-%s] PDG service has started"
        --#ARGUMENTS {0,1}
        --#STATE OPERATIONAL
        --#SEVERITY INFORMATIONAL
    ::= { starentTraps 1101 }

  starPDGServiceStop NOTIFICATION-TYPE
    OBJECTS { starServiceVpnName, starServiceServName }
    STATUS  current
    DESCRIPTION
        "A PDG Service has stopped.
        Probable Cause: This is typically caused by operator invention.  In
        rare cases it can be caused by the loss of resources (PACs) to
        support the running configuration.

        Action to be Taken: If the PDG service shutdown was not planned,
        examine the admin logs for an indication of the failure.  Verify that
        all configured PACs are present and running in the system.  Check the
        crash logs for an indication of a software failure.

        Clear Condition: Verify that the PDG service is operational.

        Condition Clear Alarm:  A starPDGServiceStart notification will be generated when
        the service is restarted"

        --#SUMMARY "[Service PDG-%s-%s] PDG service has stopped"
        --#ARGUMENTS {0,1}
        --#STATE DEGRADED
        --#SEVERITY MAJOR
    ::= { starentTraps 1102 }

starDynPkgLoadError NOTIFICATION-TYPE
    OBJECTS { starDynPkgFilename, starDynCFErrorCode }
    STATUS  current
    DESCRIPTION
    "The Dynamic rater package error displayed with an error code.

    Action to be Taken: If no or invalid rater.pkg file is there in the specified directory then 
    Place a rater_f.pkg file in the directory and give an upgrade command or place a valid 
    Rater.pkg file and load the SRDBs by killing them all.

    Condition Clear Alarm: This condition is cleared by a starDynPkgLoadErrorClear
    notification"

    --#SUMMARY "[System] Dynamic Rater package %s error code: %s"
    --#ARGUMENTS {0,1}
    --#STATE DEGRADED
    --#SEVERITY MAJOR
    ::= { starentTraps 1103 }

starDynPkgLoadErrorClear NOTIFICATION-TYPE
    OBJECTS { starDynPkgFilename, starDynCFErrorCode }
    STATUS  current
    DESCRIPTION
    "The Dynamic rater package error removed.

    Action to be Taken: No action required"
    --#SUMMARY "[System] Dynamic Rater package %s error code: %s cleared"
    --#ARGUMENTS {0,1}
    --#STATE OPERATIONAL
    --#SEVERITY INFORMATIONAL
    ::= { starentTraps 1104 }

starDynPkgUpgradeError NOTIFICATION-TYPE
    OBJECTS { starDynPkgUpgradeFilename, starDynCFUpgradeErrorCode }
    STATUS  current
    DESCRIPTION
    "The Dynamic rater package error displayed with an error code.

    Action to be Taken: Place a valid rater_f.pkg file in the 
    directory and give an upgrade command.

    Condition Clear Alarm: This condition is cleared by a starDynPkgUpgradeErrorClear  
    notification"
    --#SUMMARY "[System] Dynamic Rater package %s error code: %s"
    --#ARGUMENTS {0,1}
    --#STATE DEGRADED
    --#SEVERITY INFORMATIONAL
    ::= { starentTraps 1105 }

starDynPkgUpgradeErrorClear  NOTIFICATION-TYPE
    OBJECTS { starDynPkgUpgradeFilename, starDynCFUpgradeErrorCode }
    STATUS  current
    DESCRIPTION
    "The Dynamic Rater package error removed.

    Action to be Taken: No action required"
    --#SUMMARY "[System] Dynamic Rater package %s error code: %s cleared"
    --#ARGUMENTS {0,1}
    --#STATE OPERATIONAL
    --#SEVERITY INFORMATIONAL
    ::= { starentTraps 1106 }

starCSCFPeerServerUnavailable NOTIFICATION-TYPE
    OBJECTS { starCSCFPeerServerVpnName, starCSCFPeerServerSvcName, starCSCFPeerServerName }
    STATUS  current
    DESCRIPTION
         "Peer server is unavailable"
    --#SUMMARY "[CSCF %s-%s] CSCF Peer Server %s Unavailable"
    --#ARGUMENTS {0,1,2}
    --#STATE DEGRADED
    --#SEVERITY MAJOR
    ::= { starentTraps 1107 }

starCSCFPeerServerOutofService NOTIFICATION-TYPE
    OBJECTS { starCSCFPeerServerVpnName, starCSCFPeerServerSvcName, starCSCFPeerServerName }
    STATUS  current
    DESCRIPTION
         "Peer server is out-of-service"
    --#SUMMARY "[CSCF %s-%s] CSCF Peer Server %s Out-of-service"
    --#ARGUMENTS {0,1,2}
    --#STATE DEGRADED
    --#SEVERITY CRITICAL
    ::= { starentTraps 1108 }

starCSCFPeerServerInService NOTIFICATION-TYPE
    OBJECTS { starCSCFPeerServerVpnName, starCSCFPeerServerSvcName, starCSCFPeerServerName }
    STATUS  current
    DESCRIPTION
         "Peer server unavailable and/or out of service condition cleared"
    --#SUMMARY "[CSCF %s-%s] CSCF Peer Server %s Available and In Service"
    --#ARGUMENTS {0,1,2}
    --#STATE OPERATIONAL
    --#SEVERITY INFORMATIONAL
    ::= { starentTraps 1109 }

  starServiceLossPTACsClear NOTIFICATION-TYPE
    OBJECTS {starCardMode}
    STATUS  current
    DESCRIPTION
        "Service Loss condition is no longer valid for PAC/PSC/TACs."
    --#SUMMARY "[System] Service Loss condition clear for cardmode %s"
    --#ARGUMENTS {0}
    --#STATE OPERATIONAL
    --#SEVERITY INFORMATIONAL
    ::= { starentTraps 1110 }

  starServiceLossLCClear NOTIFICATION-TYPE
    OBJECTS { starCardType, starSlotNum, starSlotNum }
    STATUS  current
    DESCRIPTION
        "Service Loss condition is no longer valid for LC."
    --#SUMMARY "[System] Service Loss condition clear because one of the two %s cards (%d, %d) is active now"
    --#ARGUMENTS {0,1,2}
    --#STATE OPERATIONAL
    --#SEVERITY INFORMATIONAL
    ::= { starentTraps 1111 }

starEgtpcPathFailure NOTIFICATION-TYPE
    OBJECTS { starEGTPVpnName, starEGTPServName, starEGTPInterfaceType, starEGTPSelfAddr,starEGTPPeerAddr, starEGTPPeerOldRstCnt, starEGTPPeerNewRstCnt, starEGTPPeerSessCnt, starEGTPFailureReason }
    STATUS  current
    DESCRIPTION
        "EGTP Control Path Failure. No response received for GTPV2 request sent from MME or SGW or PGW.

         Possibe reason: Remote peer MME or SGW or PGW is down

         Condition Clear Alarm:  A StarEgtpcPathFailureClear notification will be generated when
         the control path to the remote peer MME or SGW or PGW becomes available"
    --#SUMMARY "[Service GTPV2-%s-%s] EGTP control path failure  interface type %s, self address %s,  peer address %s, peer old restart counter %d,  peer new restart counter %d,  peer session count  %d, failure reason %s"
    --#ARGUMENTS {0,1,2,3,4,5,6,7,8}
    --#STATE DEGRADED
    --#SEVERITY MAJOR
    ::= { starentTraps 1112 }

starEgtpcPathFailureClear NOTIFICATION-TYPE
    OBJECTS { starEGTPVpnName, starEGTPServName, starEGTPInterfaceType, starEGTPSelfAddr, starEGTPPeerAddr, starEGTPPeerOldRstCnt, starEGTPPeerSessCnt}
    STATUS  current
    DESCRIPTION
        "EGTP Control Path Failure condition is no longer valid."
    --#SUMMARY "[Service GTPV2-%s-%s] EGTP control path failure condition clear for interface type %s, self address %s,  peer address %s, peer restart counter %d,  peer session count  %d"
    --#ARGUMENTS {0,1,2,3,4,5,6}
    --#STATE OPERATIONAL
    --#SEVERITY INFORMATIONAL
    ::= { starentTraps 1113 }

starCscfSessResourceCongestion NOTIFICATION-TYPE
    OBJECTS { starSmgrId, starCongestionPolicy, starCscfSessCongestionResourceType }
    STATUS current
    DESCRIPTION
        "A congestion condition has occurred at Session Manager for Cscf Service. 

	 Probable Cause:  This is the result of an operator-configured congestion
	 threshold being reached for Cscf Service at Session Manager. This can be due to high 
     usage of the resource being monitored which indicates that the 
     IMG is reaching its peak capacity, or could be caused by the 
     incorrect configuration of the congestion thresholds.

	 Actions to be Taken:  Verify that the congestion thresholds are correct;
	 if the congested state is seem repeatedly, or for sustained periods of
	 time, additional system capacity may need to be brought online.

	 This system is cleared when the use of the specific resource falls below
	 the configured limit.

	 Condition Clear Alarm: A starCscfSessResourceCongestionClear notification is sent when there
	 are no congestion conditions for cscf service in that Session Manager Instance"
    --#SUMMARY "[System] Cscf Congestion seen for sessmgr-%d; resource %s, policy %s applied"
    --#ARGUMENTS {0,2,1}
    --#STATE DEGRADED
    --#SEVERITY MAJOR
    ::= { starentTraps 1114 }

starCscfSessResourceCongestionClear NOTIFICATION-TYPE
    OBJECTS { starSmgrId }
    STATUS current
    DESCRIPTION
        "A congestion condition has cleared at Session Manager for Cscf service"
    --#SUMMARY "[System] Cscf Congestion clear for sessmgr-%d"
    --#ARGUMENTS {0}
    --#STATE OPERATIONAL
    --#SEVERITY INFORMATIONAL
    ::= { starentTraps 1115 }

starOSPFv3NeighborDown NOTIFICATION-TYPE
   OBJECTS { starContextName, starInterfaceName, starInterfaceIPAddress, starOSPFNeighborRouterID, starOSPFFromState, starOSPFToState }
   STATUS  current
   DESCRIPTION
        "An OSPFv3 neighbor is down.

   	Condition Clear Alarm: A starOSPFv3NeighborFull notification will be generated when the neighbor is restored."
    --#SUMMARY "[VPN %s] OSPFv3 Neighbor down, interface %s/%s, OSPFv3 Neighbor %s, transitioned from state %s to %s"
    --#ARGUMENTS {0,1,2,3,4,5}
    --#STATE DEGRADED
    --#SEVERITY MINOR
    ::= { starentTraps 1116 }

  starOSPFv3NeighborFull NOTIFICATION-TYPE
    OBJECTS { starContextName, starInterfaceName, starInterfaceIPAddress, starOSPFNeighborRouterID }
    STATUS  current
    DESCRIPTION
        "An OSPFv3 neighbor is full.  A starOSPFv3NeighborFull notification is only sent for neighbors which had previous been declared down via a starOSPFv3NeighborDown notification."
    --#SUMMARY "[VPN %s] OSPFv3 Neighbor full, interface %s/%s, OSPFv3 Neighbor %s"
    --#ARGUMENTS {0,1,2,3}
    --#STATE OPERATIONAL
    --#SEVERITY INFORMATIONAL
    ::= { starentTraps 1117 }

starServiceLossSPIOClear NOTIFICATION-TYPE 
    STATUS  current
    DESCRIPTION
        "Service Loss condition is no longer valid for SPIO."
    --#SUMMARY "[System] Service Loss condition clear for SPIO"    
    --#STATE OPERATIONAL
    --#SEVERITY INFORMATIONAL
    ::= { starentTraps 1118 }

starEgtpuPathFailure NOTIFICATION-TYPE
     OBJECTS { starEGTPVpnName, starEGTPServName, starEGTPSelfAddr, starEGTPPeerAddr, starEGTPSelfPort, starEGTPPeerPort, starEGTPPeerSessCnt }
     STATUS  current
     DESCRIPTION
         "No response received for GTP-U ECHO requests. Data path failure detected towards peer EPC Node. 
 
          Check if the peer RNC or GSN is up
 
          Possible reason: Remote EPC node is down
 
          Condition Clear Alarm:  A starEgtpuPathFailureClear notification will be generated when the data 
 	  path towards the peer node is available"
    --#SUMMARY "[Service GTPU-%s-%s] EGTPU path failure self address %s, peer address %s, self port %d, peer port %d, peer session count %d"
    --#ARGUMENTS {0,1,2,3,4,5,6}
    --#STATE DEGRADED
    --#SEVERITY MAJOR
    ::= { starentTraps 1119 }
 
starEgtpuPathFailureClear NOTIFICATION-TYPE
    OBJECTS { starEGTPVpnName, starEGTPServName, starEGTPSelfAddr, starEGTPPeerAddr, starEGTPSelfPort, starEGTPPeerPort }
    STATUS current
    DESCRIPTION
         "The data path to the peer EPC node which was down is now available
          A starEgtpuPathFailureClear notification is only generated for nodes which had previously generated a
 	  starEgtpuPathFailure notification"
    --#SUMMARY "[Service GTPU-%s-%s] EGTPU path failure condition clear for self address %s, peer address %s self port %d, peer port %d"
    --#ARGUMENTS {0,1,2,3,4,5}
    --#STATE OPERATIONAL
    --#SEVERITY INFORMATIONAL
    ::= { starentTraps 1120 }

starStorageServerCDRLoss NOTIFICATION-TYPE
    OBJECTS { starSessGGSNVpnName, starSessGGSNPeerAddr, starGSSCDRLossConfigured, starGSSCDRLossMeasured, starGSSClusterName, starGSSClusterNodeName }
    STATUS  current
    DESCRIPTION
        "GTPP Storage Server is experiencing CDR Loss greater than the configured threshold value at the GSS.
	 Note that this is an external server, not part of the ST16."
    --#SUMMARY "[System] GTPP Storage Server CDR Loss, VPN %s Server Address %s, GTPP Storage Server Cluster %s node %s, CDR Lost %d (alarm at %d )"
    --#ARGUMENTS {0,1,4,5,3,2}
    --#STATE OPERATIONAL
    --#SEVERITY MAJOR
    ::= { starentTraps 1121 }

starHNBGWServiceStart NOTIFICATION-TYPE
    OBJECTS { starServiceVpnName, starServiceServName }
    STATUS  current
    DESCRIPTION
        "A Home Node B Gateway (HNB GW) Service has started.

         Action to be Taken: No action required"
    --#SUMMARY "[Service HNBGW-%s-%s] HNB GW service has started"
    --#ARGUMENTS {0,1}
    --#STATE OPERATIONAL
    --#SEVERITY INFORMATION
    ::= { starentTraps 1122 }

starHNBGWServiceStop NOTIFICATION-TYPE
    OBJECTS { starServiceVpnName, starServiceServName }
    STATUS  current
    DESCRIPTION
        "A Home Node B Gateway (PGN) Service has stopped.

         Probable Cause: This is typically caused by operator intervention.  In
         rare cases it can be caused by the loss of resources (PSCs) to support
         the running configuration.

         Action to be Taken: If the HNB GW service shutdown was not planned,
         examine the admin logs for an indication of the failure.  Verify that
         all configured PSCs are present and running in the system.  Check the
         crash logs for an indication of a software failure.

         Clear Condition: Verify that the HNB GW service is operational.

         Condition Clear Alarm:  A starHNBGWServiceStart notification will be
         generated when the service is restarted"
    --#SUMMARY "[Service HNBGW-%s-%s] HNB GW service has stopped"
    --#ARGUMENTS {0,1}
    --#STATE DEGRADED
    --#SEVERITY MAJOR
    ::= { starentTraps 1123 }

starSystemReboot NOTIFICATION-TYPE
    OBJECTS { starChassisType, starChassisDescription, starChassisSWRevision }
    STATUS current
    DESCRIPTION
        "The system has rebooted by the operator. If successful, a subsequent 
         starSystemStartup trap is typically generated.

         Action to be Taken: No action required. If the reboot was not scheduled the 
         admin logs can be examined to determine who invoked the reboot operation."
    --#SUMMARY "[Chassis] System Reboot, Starent %s chassis, '%s', SW Revision %s"
    --#ARGUMENTS {0,1,2}
    --#STATE DEGRADED
    --#SEVERITY MAJOR
    ::= { starentTraps 1124 }

starLicenseAboutToExpire NOTIFICATION-TYPE
    OBJECTS { starLicenseKey, starLicenseExpiryDate, starLicenseDaysRemaining }
    STATUS current
    DESCRIPTION
        "A license is about to expire.

         Action to be Taken: A new license should be created and configured on the system
         before the grace period is over."
    --#SUMMARY "[System] License is about to expire for license with key %d, expiration date %s with %d day to expire."
    --#ARGUMENTS {0,1,2}
    --#STATE OPERATIONAL
    --#SEVERITY CRITICAL
    ::= { starentTraps 1125 }

starLicenseExpired NOTIFICATION-TYPE
    OBJECTS { starLicenseKey, starLicenseExpiryDate, starLicenseDaysAfterExpiry }
    STATUS current
    DESCRIPTION
        "A license is in the grace period and should be updated with a new license.

         Action to be Taken: A new license should be created and configured on the system."
    --#SUMMARY "[System] License expired for license with key %d, expiration date %s and it has been %d day the license has expired."
    --#ARGUMENTS {0,1,2}
    --#STATE NONOPERATIONAL
    --#SEVERITY CRITICAL
    ::= { starentTraps 1126 }
    
-- PCC-Policy Service

starPCCPolicyServiceStart NOTIFICATION-TYPE
    OBJECTS { starServiceVpnName, starServiceServName }
    STATUS  current
    DESCRIPTION
        "A PCC-Policy Service has started
        Action to be Taken: No action required"
        --#SUMMARY "[Service PCC-Policy-%s-%s] PCC-Policy service has started"
        --#ARGUMENTS {0,1}
        --#STATE OPERATIONAL
        --#SEVERITY INFORMATIONAL
    ::= { starentTraps 1127 }

starPCCPolicyServiceStop NOTIFICATION-TYPE
    OBJECTS { starServiceVpnName, starServiceServName }
    STATUS  current
    DESCRIPTION
        "A PCC-Policy Service has stopped.
        Probable Cause: This is typically caused by operator invention. In
        rare cases it can be caused by the loss of resources (PACs/PSCs) to
        support the running configuration.

        Action to be Taken: If the PCC-Policy service shutdown was not planned,
        examine the admin logs for an indication of the failure.  Verify that
        all configured PACs/PSCs are present and running in the system.  Check 
        the crash logs for an indication of a software failure.

        Clear Condition: Verify that the PCC-Policy service is operational.

        Condition Clear Alarm:  A starPCCPolicyServiceStart notification will 
        be generated when the service is restarted"

        --#SUMMARY "[Service PCC-Policy-%s-%s] PCC-Policy service has stopped"
        --#ARGUMENTS {0,1}
        --#STATE DEGRADED
    ::= { starentTraps 1128 }

-- PCC-Quota Service

starPCCQuotaServiceStart NOTIFICATION-TYPE
    OBJECTS { starServiceVpnName, starServiceServName }
    STATUS  current
    DESCRIPTION
        "A PCC-Quota Service has started
        Action to be Taken: No action required"
        --#SUMMARY "[Service PCC-Quota-%s-%s] PCC-Quota service has started"
        --#ARGUMENTS {0,1}
        --#STATE OPERATIONAL
        --#SEVERITY INFORMATIONAL
    ::= { starentTraps 1129 }

starPCCQuotaServiceStop NOTIFICATION-TYPE
    OBJECTS { starServiceVpnName, starServiceServName }
    STATUS  current
    DESCRIPTION
        "A PCC-Quota Service has stopped.
        Probable Cause: This is typically caused by operator invention. In
        rare cases it can be caused by the loss of resources (PACs/PSCs) to
        support the running configuration.

        Action to be Taken: If the PCC-Quota service shutdown was not planned,
        examine the admin logs for an indication of the failure.  Verify that
        all configured PACs/PSCs are present and running in the system.  Check 
        the crash logs for an indication of a software failure.

        Clear Condition: Verify that the PCC-Quota service is operational.

        Condition Clear Alarm:  A starPCCQuotaServiceStart notification will 
        be generated when the service is restarted"

        --#SUMMARY "[Service PCC-Quota-%s-%s] PCC-Quota service has stopped"
        --#ARGUMENTS {0,1}
        --#STATE DEGRADED
        --#SEVERITY MAJOR
    ::= { starentTraps 1130 }

-- PCC-AF Service

starPCCAFServiceStart NOTIFICATION-TYPE
  OBJECTS { starServiceVpnName, starServiceServName }
  STATUS  current
  DESCRIPTION
      "A PCC-AF Service has started
      Action to be Taken: No action required"
      --#SUMMARY "[Service PCC-AF-%s-%s] PCC-AF service has started"
      --#ARGUMENTS {0,1}
      --#STATE OPERATIONAL
      --#SEVERITY INFORMATIONAL
  ::= { starentTraps 1131 }

starPCCAFServiceStop NOTIFICATION-TYPE
  OBJECTS { starServiceVpnName, starServiceServName }
  STATUS  current
  DESCRIPTION
      "A PCC-AF Service has stopped.
      Probable Cause: This is typically caused by operator invention. In
      rare cases it can be caused by the loss of resources (PACs/PSCs) to
      support the running configuration.

      Action to be Taken: If the PCC-AF service shutdown was not planned,
      examine the admin logs for an indication of the failure.  Verify that
      all configured PACs/PSCs are present and running in the system.  Check 
      the crash logs for an indication of a software failure.

      Clear Condition: Verify that the PCC-AF service is operational.

      Condition Clear Alarm:  A starPCCAFServiceStart notification will 
      be generated when the service is restarted"

      --#SUMMARY "[Service PCC-AF-%s-%s] PCC-AF service has stopped"
      --#ARGUMENTS {0,1}
      --#STATE DEGRADED
      --#SEVERITY MAJOR
  ::= { starentTraps 1132 }

--SPR Failures

starSPRServerUnreachable NOTIFICATION-TYPE
    OBJECTS { starSPRServerIpAddr }
    STATUS  current
    DESCRIPTION
        "The Subscriber Profile Repository (SPR) server cannot be reached.

	 Probable Cause: The SPR server is down, or there is a network issue
         preventing communication with the SPR server.

         Actions to be Taken: Restore the SPR server to an operational status;
         Verify that the SPR server is reachable by performing a 'ping' operation
         from the CLI in the appropriate context. Check the admin logs for
         notification of communication problems.

         Clear Condition: Verify that communication to the SPR authentication
         server has been restored.

         Condition Clear Alarm: When this condition clears a starSPRServerReachable
         notification will be generated."
    --#SUMMARY "[System] SPR Server %s is unreachable"
    --#ARGUMENTS {0}
    --#STATE DEGRADED
    --#SEVERITY MAJOR
    ::= { starentTraps 1133 }

starSPRServerReachable NOTIFICATION-TYPE
    OBJECTS { starSPRServerIpAddr }
    STATUS  current
    DESCRIPTION
        "The Subscriber Profile Repository (SPR) server is now reachable.  
        This can be the result of a system startup, the configuration
        of a new server, or a previously unreachable server becoming reachable.

	Action to be Taken: No Action Required."
    --#SUMMARY "[System] SPR Server %s is reachable"
    --#ARGUMENTS {0}
    --#STATE OPERATIONAL
    --#SEVERITY INFORMATIONAL
    ::= { starentTraps 1134 }

starGSServiceStart NOTIFICATION-TYPE
    OBJECTS { starServiceVpnName, starServiceServName }
    STATUS  current 
    DESCRIPTION     
    "A GS Service has started

    Action to be Taken: No action required"
    --#SUMMARY "[Service GS %s-%s] GS service has started"
    --#ARGUMENTS {0,1}
    --#STATE OPERATIONAL
    --#SEVERITY INFORMATIONAL
    ::= { starentTraps 1135 }
                    
starGSServiceStop NOTIFICATION-TYPE
    OBJECTS { starServiceVpnName, starServiceServName }
    STATUS  current 
    DESCRIPTION     
    "A GS Service has stopped.
    Probable Cause: This is typically caused by operator invention.  In
    unusual cases it can be caused by the loss of resources (PACs/PSCs) to
    support the running configuration.
                    
    Action to be Taken: If the GS service shutdown was not planned,
    examine the admin logs for an indication of the failure.  Verify that
    all configured PACs/PSCs are present and running in the system.  Check the
    crash logs for an indication of a software failure.

    Clear Condition: Verify that the GS service is operational.

    Condition Clear Alarm:  A starGSServiceStart notification will be generated when
    the service is restarted"
    --#SUMMARY "[Service GS %s-%s] GS service has stopped"
    --#ARGUMENTS {0,1}
    --#STATE DEGRADED
    --#SEVERITY MAJOR
    ::= { starentTraps 1136 }

starMAPServiceStart NOTIFICATION-TYPE
    OBJECTS { starServiceVpnName, starServiceServName }
    STATUS  current 
    DESCRIPTION     
    "A MAP Service has started
    Action to be Taken: No action required"
    --#SUMMARY "[Service MAP %s-%s] MAP service has started"
    --#ARGUMENTS {0,1}
    --#STATE OPERATIONAL
    --#SEVERITY INFORMATIONAL
    ::= { starentTraps 1137 }
                    
starMAPServiceStop NOTIFICATION-TYPE
    OBJECTS { starServiceVpnName, starServiceServName }
    STATUS  current 
    DESCRIPTION     
    "A MAP Service has stopped.
    Probable Cause: This is typically caused by operator invention.  In
    unusual cases it can be caused by the loss of resources (PACs/PSCs) to
    support the running configuration.
                    
    Action to be Taken: If the MAP service shutdown was not planned,
    examine the admin logs for an indication of the failure.  Verify that
    all configured PACs/PSCs are present and running in the system.  Check the
    crash logs for an indication of a software failure.

    Clear Condition: Verify that the MAP service is operational.

    Condition Clear Alarm:  A starMAPServiceStart notification will be generated when
    the service is restarted"
    --#SUMMARY "[Service MAP %s-%s] MAP service has stopped"
    --#ARGUMENTS {0,1}
    --#STATE DEGRADED
    --#SEVERITY MAJOR
    ::= { starentTraps 1138 }

starIUPSServiceStart NOTIFICATION-TYPE
    OBJECTS { starServiceVpnName, starServiceServName }
    STATUS  current 
    DESCRIPTION     
    "An IUPS Service has started
    Action to be Taken: No action required"
    --#SUMMARY "[Service IUPS %s-%s] IUPS service has started"
    --#ARGUMENTS {0,1}
    --#STATE OPERATIONAL
    --#SEVERITY INFORMATIONAL
    ::= { starentTraps 1139 }
                    
starIUPSServiceStop NOTIFICATION-TYPE
    OBJECTS { starServiceVpnName, starServiceServName }
    STATUS  current 
    DESCRIPTION     
    "An IUPS Service has stopped.
    Probable Cause: This is typically caused by operator invention.  In
    unusual cases it can be caused by the loss of resources (PACs/PSCs) to
    support the running configuration.
                    
    Action to be Taken: If the IUPS service shutdown was not planned,
    examine the admin logs for an indication of the failure.  Verify that
    all configured PACs/PSCs are present and running in the system.  Check the
    crash logs for an indication of a software failure.

    Clear Condition: Verify that the IUPS service is operational.

    Condition Clear Alarm:  A starIUPSServiceStart notification will be generated when
    the service is restarted"
    --#SUMMARY "[Service IUPS %s-%s] IUPS service has stopped"
    --#ARGUMENTS {0,1}
    --#STATE DEGRADED
    --#SEVERITY MAJOR
    ::= { starentTraps 1140 }

starSGTPServiceStart NOTIFICATION-TYPE
    OBJECTS { starServiceVpnName, starServiceServName }
    STATUS  current 
    DESCRIPTION     
    "A SGTP Service has started
    Action to be Taken: No action required"
    --#SUMMARY "[Service SGTP %s-%s] SGTP service has started"
    --#ARGUMENTS {0,1}
    --#STATE OPERATIONAL
    --#SEVERITY INFORMATIONAL
    ::= { starentTraps 1141 }
                    
starSGTPServiceStop NOTIFICATION-TYPE
    OBJECTS { starServiceVpnName, starServiceServName }
    STATUS  current 
    DESCRIPTION     
    "A SGTP Service has stopped.
    Probable Cause: This is typically caused by operator invention.  In
    unusual cases it can be caused by the loss of resources (PACs/PSCs) to
    support the running configuration.
                    
    Action to be Taken: If the SGTP service shutdown was not planned,
    examine the admin logs for an indication of the failure.  Verify that
    all configured PACs/PSCs are present and running in the system.  Check the
    crash logs for an indication of a software failure.

    Clear Condition: Verify that the SGTP service is operational.

    Condition Clear Alarm:  A starSGTPServiceStart notification will be generated when
    the service is restarted"
    --#SUMMARY "[Service SGTP %s-%s] SGTP service has stopped"
    --#ARGUMENTS {0,1}
    --#STATE DEGRADED
    --#SEVERITY MAJOR
    ::= { starentTraps 1142 }

starEPDGServiceStart NOTIFICATION-TYPE
    OBJECTS { starServiceVpnName, starServiceServName }
    STATUS  current
    DESCRIPTION
        "A EPDG Service has started

         Action to be Taken: No action required"
    --#SUMMARY "[Service EPDG-%s-%s] EPDG service has started"
    --#ARGUMENTS {0,1}
    --#STATE OPERATIONAL
    --#SEVERITY INFORMATIONAL
    ::= { starentTraps 1143 }

starEPDGServiceStop NOTIFICATION-TYPE
    OBJECTS { starServiceVpnName, starServiceServName }
    STATUS  current
    DESCRIPTION
        "A EPDG Service has stopped.

	 Probable Cause: This is typically caused by operator invention.  In
	 unusual cases it can be caused by the loss of resources (PACs/PSCs) to
	 support the running configuration.

	 Action to be Taken: If the EPDG service shutdown was not planned,
	 examine the admin logs for an indication of the failure.  Verify that
	 all configured PACs/PSCs are present and running in the system.  Check the
	 crash logs for an indication of a software failure.

	 Clear Condition: Verify that the EPDG service is operational.

	 Condition Clear Alarm: A starEPDGServiceStart notification will be generated when
			        the service is restarted"
    --#SUMMARY "[Service EPDG-%s-%s] EPDG service has stopped"
    --#ARGUMENTS {0,1}
    --#STATE DEGRADED
    --#SEVERITY MAJOR
    ::= { starentTraps 1144 }

starApsCommandSuccess NOTIFICATION-TYPE
    OBJECTS { starSlotNum, starCardType, starPortNum, starPortType }
    STATUS current
    DESCRIPTION
        "APS Command Success Status."
    --#SUMMARY "APS Command Success for card %d card type %d port %d port type %s"
    --#ARGUMENTS {0,1,2,3}
    --#STATE DEGRADED
    --#SEVERITY MAJOR
    ::= { starentTraps 1145 }

starApsCommandFailure NOTIFICATION-TYPE
    OBJECTS { starSlotNum, starCardType, starPortNum, starPortType }
    STATUS current
    DESCRIPTION
        "APS Command Failure Status."
    --#SUMMARY "APS Command Failure for card %d card type %d port %d port type %d"
    --#ARGUMENTS {0,1,2,3}
    --#STATE DEGRADED
    --#SEVERITY MAJOR
    ::= { starentTraps 1146 }

starApsSwitchSuccess NOTIFICATION-TYPE
    OBJECTS { starSlotNum, starCardType, starPortNum, starPortType }
    STATUS current
    DESCRIPTION
        "APS Switch Success Status."
    --#SUMMARY "APS Switch Command Status for card %d card type %d port %d port type %d"
    --#ARGUMENTS {0,1,2,3}
    --#STATE DEGRADED
    --#SEVERITY MAJOR
    ::= { starentTraps 1147 }

starApsSwitchFailure NOTIFICATION-TYPE
    OBJECTS { starSlotNum, starCardType, starPortNum, starPortType }
    STATUS current
    DESCRIPTION
        "APS Switch Failure Status."
    --#SUMMARY "APS Switch Command Failure Status for card %d card type %d port %d port type %s"
    --#ARGUMENTS {0,1,2,3}
    --#STATE DEGRADED
    --#SEVERITY MAJOR
    ::= { starentTraps 1148 }

starApsModeMismatch NOTIFICATION-TYPE
    OBJECTS { starSlotNum, starCardType, starPortNum }
    STATUS current
    DESCRIPTION
        "APS Mode Mismatch Status."
    --#SUMMARY "APS Mode Mismatch for card %d card type %s port %d"
    --#ARGUMENTS {0,1,2}
    --#STATE DEGRADED
    --#SEVERITY MAJOR
    ::= { starentTraps 1149 }

starApsChannelMismatch NOTIFICATION-TYPE
    OBJECTS { starSlotNum, starCardType, starSlotNum }
    STATUS current
    DESCRIPTION
        "APS Channel Mismatch Status."
    --#SUMMARY "APS Channel Mismatch for card %d card type %s port %d"
    --#ARGUMENTS {0,1,2}
    --#STATE DEGRADED
    --#SEVERITY MAJOR
    ::= { starentTraps 1150 }

starApsByteMismatch NOTIFICATION-TYPE
    OBJECTS { starSlotNum, starCardType, starSlotNum }
    STATUS current
    DESCRIPTION
        "APS Byte Mismatch Status."
    --#SUMMARY "APS Byte Mismatch for card %d card type %s for card  %d"
    --#ARGUMENTS {0,1,2}
    --#STATE DEGRADED
    --#SEVERITY MAJOR
    ::= { starentTraps 1151 }

starApsFeProtLineFailure NOTIFICATION-TYPE
    OBJECTS {  starSlotNum, starCardType, starSlotNum, starSlotNum }
    STATUS current
    DESCRIPTION
        "APS FE Protocol Line Failure Status."
    --#SUMMARY "APS FE Port Line Failure Status for card %d card type %s from card  %d to card %d"
    --#ARGUMENTS {0,1,2,3}
    --#STATE DEGRADED
    --#SEVERITY MAJOR
    ::= { starentTraps 1152 }

starApsLossOfRedundancy NOTIFICATION-TYPE
    OBJECTS { starSlotNum, starCardType, starSlotNum, starSlotNum }
    STATUS current
    DESCRIPTION
        "APS Loss of Redundancy Status."
    --#SUMMARY "APS Loss of Redundancy for card %d card type %s from card  %d to card %d"
    --#ARGUMENTS {0,1,2,3}
    --#STATE DEGRADED
    --#SEVERITY MAJOR
    ::= { starentTraps 1153}

starApsLossOfRedundancyClear NOTIFICATION-TYPE
    OBJECTS { starSlotNum, starCardType, starSlotNum, starSlotNum }
    STATUS current
    DESCRIPTION
        "APS Loss of Redundancy Clear Status."
    --#SUMMARY "APS Redundancy Restored for card %d card type %s from card  %d to card %d"
    --#ARGUMENTS {0,1,2,3}
    --#STATE DEGRADED
    --#SEVERITY MAJOR
    ::= { starentTraps 1154 }

starHNBGWSGSNRanapReset NOTIFICATION-TYPE
    OBJECTS { starSessHNBGWVpnName, starSessHNBGWServName, starSessHNBGWPsNwName, starSessHNBGWSgsnPtCd }
    STATUS  current 
    DESCRIPTION     
    "RANAP Reset Received from SGSN"
    
    --#SUMMARY "[Service HNBGW %s-%s PS Network %s] Received RANAP Reset from SGSN %d"
    --#ARGUMENTS {0,1,2,3}
    --#STATE OPERATIONAL
    --#SEVERITY INFORMATIONAL
    ::= { starentTraps 1155 }

starHNBGWMSCRanapReset NOTIFICATION-TYPE
    OBJECTS { starSessHNBGWVpnName, starSessHNBGWServName, starSessHNBGWCsNwName, starSessHNBGWMscPtCd }
    STATUS  current 
    DESCRIPTION     
    "RANAP Reset Received from MSC"
    
    --#SUMMARY "[Service HNBGW %s-%s CS Network %s] Received RANAP Reset from MSC %d"
    --#ARGUMENTS {0,1,2,3}
    --#STATE OPERATIONAL
    --#SEVERITY INFORMATIONAL
    ::= { starentTraps 1156 }

starALCAPNodeReset NOTIFICATION-TYPE
    OBJECTS { starSessALCAPVpnName, starSessALCAPServName, starSessALCAPAAL2NodeName }
    STATUS  current 
    DESCRIPTION     
    "ALCAP Node Reset Received from MGW"

    --#SUMMARY "[Service ALCAP %s-%s] AAL2 Node %s  Received ALCAP Node Reset"
    --#ARGUMENTS {0,1,2}
    --#STATE OPERATIONAL
    --#SEVERITY INFORMATIONAL
    ::= { starentTraps 1157 }

starALCAPPathReset NOTIFICATION-TYPE
    OBJECTS { starSessALCAPVpnName, starSessALCAPServName, starSessALCAPAAL2NodeName, starSessALCAPPathId }
    STATUS  current 
    DESCRIPTION     
    "ALCAP Path Reset Received from MGW"

    --#SUMMARY "[Service ALCAP %s-%s] AAL2 Node %s Path %d Received ALCAP Path Reset"
    --#ARGUMENTS {0,1,2,3}
    --#STATE OPERATIONAL
    --#SEVERITY INFORMATIONAL
    ::= { starentTraps 1158 }

starALCAPPathBlock NOTIFICATION-TYPE
    OBJECTS { starSessALCAPVpnName, starSessALCAPServName, starSessALCAPPathId }
    STATUS  current 
    DESCRIPTION     
    "ALCAP Block Received from MGW"
    
    --#SUMMARY "[Service ALCAP %s-%s] Path %d  Received ALCAP Block"
    --#ARGUMENTS {0,1,2}
    --#STATE OPERATIONAL
    --#SEVERITY INFORMATIONAL
    ::= { starentTraps 1159 }

starALCAPPathUnBlock NOTIFICATION-TYPE
    OBJECTS { starSessALCAPVpnName, starSessALCAPServName, starSessALCAPPathId }
    STATUS  current 
    DESCRIPTION     
    "ALCAP Un Block Received from MGW"

    --#SUMMARY "[Service ALCAP %s-%s] Path %d  Received ALCAP Un Block"
    --#ARGUMENTS {0,1,2}
    --#STATE OPERATIONAL
    --#SEVERITY INFORMATIONAL
    ::= { starentTraps 1160 }

starSGSServiceStart NOTIFICATION-TYPE
    OBJECTS { starServiceVpnName, starServiceServName }
    STATUS  current
    DESCRIPTION
        "A SGS Service has started

         Action to be Taken: No action required"
    --#SUMMARY "[Service SGS-%s-%s] SGS service has started"
    --#ARGUMENTS {0,1}
    --#STATE OPERATIONAL
    --#SEVERITY INFORMATIONAL
    ::= { starentTraps 1161 }

starSGSServiceStop NOTIFICATION-TYPE
    OBJECTS { starServiceVpnName, starServiceServName }
    STATUS  current
    DESCRIPTION
        "A SGS Service has stopped.

	 Probable Cause: This is typically caused by operator invention.  In
	 unusual cases it can be caused by the loss of resources (PACs/PSCs) to
	 support the running configuration.

	 Action to be Taken: If the SGS service shutdown was not planned,
	 examine the admin logs for an indication of the failure.  Verify that
	 all configured PACs/PSCs are present and running in the system.  Check the
	 crash logs for an indication of a software failure.

	 Clear Condition: Verify that the SGS service is operational.

	 Condition Clear Alarm: A starSGSServiceStart notification will be generated when
			        the service is restarted"
    --#SUMMARY "[Service SGS-%s-%s] SGS service has stopped"
    --#ARGUMENTS {0,1}
    --#STATE DEGRADED
    --#SEVERITY MAJOR
    ::= { starentTraps 1162 }

starSgsnGnMsgDelay NOTIFICATION-TYPE
    OBJECTS { starSGTPVpnName, starSGTPServName, starSGTPPeerAddr }
    STATUS current
    DESCRIPTION
        "Messaging Dealy seen towards GGSN as many messages sent to that GGSN did 
        not receive response within a certain time"

    --#SUMMARY "[Service SGTP %s-%s] SGSN Gn Message delay towards GGSN %s"
    --#ARGUMENTS {0,1,2}
    --#STATE OPERATIONAL
    --#SEVERITY WARNING
    ::= { starentTraps 1163 }

starSgsnGnMsgDelayClear NOTIFICATION-TYPE
    OBJECTS { starSGTPVpnName, starSGTPServName, starSGTPPeerAddr}
    STATUS current
    DESCRIPTION
    "The delay seen towards GGSN is no longer seen as message responses are received in time as expected"

    --#SUMMARY "[Service SGTP %s-%s] Clear SGSN Gn Message delay towards GGSN %s"
    --#ARGUMENTS {0,1,2}
    --#STATE OPERATIONAL
    --#SEVERITY INFORMATIONAL
    ::= { starentTraps 1164 }

starBNGServiceStart NOTIFICATION-TYPE
    OBJECTS { starServiceVpnName, starServiceServName }
    STATUS  current
    DESCRIPTION
        "A BNG Service has started

         Action to be Taken: No action required"
    --#SUMMARY "[Service BNG-%s-%s] BNG service has started"
    --#ARGUMENTS {0,1}
    --#STATE OPERATIONAL
    --#SEVERITY INFORMATIONAL
    ::= { starentTraps 1165 }

starBNGServiceStop NOTIFICATION-TYPE
    OBJECTS { starServiceVpnName, starServiceServName }
    STATUS  current
    DESCRIPTION
        "A BNG Service has stopped.

	 Probable Cause: This is typically caused by operator invention.  In
	 unusual cases it can be caused by the loss of resources (PACs/PSCs) to
	 support the running configuration.

	 Action to be Taken: If the BNG service shutdown was not planned,
	 examine the admin logs for an indication of the failure.  Verify that
	 all configured PACs/PSCs are present and running in the system.  Check the
	 crash logs for an indication of a software failure.

	 Clear Condition: Verify that the BNG service is operational.

	 Condition Clear Alarm: A starBNGServiceStart notification will be generated when
			        the service is restarted"
    --#SUMMARY "[Service BNG-%s-%s] BNG service has stopped"
    --#ARGUMENTS {0,1}
    --#STATE DEGRADED
    --#SEVERITY MAJOR
    ::= { starentTraps 1166 }

starMMES1AssocFail NOTIFICATION-TYPE
    OBJECTS { starMMES1AssocVpnName, starMMES1AssocServName, starMMES1AssocENBID }
    STATUS  current
    DESCRIPTION
	"An S1 Association between an MME service and an eNodeB has failed.

	 Action to be Taken: If the shutdown of the eNodeB was not planned,
	 determine the health/status of the eNodeB.  If available, verify the 
	 health of the network between the two elements.

	 Clear Condition: The condition is cleared with the S1 Association
	 is reestablished.

	 Condition Clear Alarm:  A starMMES1AssocEstab notification will be generated
	 when the S1 association is re-established"
    --#SUMMARY "[S1 Association %s-%s-%s] Association Failed"
    --#ARGUMENTS {0,1,2}
    --#STATE DEGRADED
    --#SEVERITY MAJOR
    ::= { starentTraps 1167 }

starMMES1AssocSetup NOTIFICATION-TYPE
    OBJECTS { starMMES1AssocVpnName, starMMES1AssocServName, starMMES1AssocENBID }
    STATUS  current
    DESCRIPTION
	"An S1 Association between an MME service and an eNodeB has been 
	 established.  Normally a starMMES1AssocSetup notification would be 
	 generated only for an associated which had previously failed, but
	 optionally this notification can be generated for any association
	 setup."
    --#SUMMARY "[S1 Association %s-%s-%s] Association Setup"
    --#ARGUMENTS {0,1,2}
    --#STATE DEGRADED
    --#SEVERITY INFORMATIONAL
    ::= { starentTraps 1168 }
 

--MVG Traps

starMVGPeerDown NOTIFICATION-TYPE
    OBJECTS { starServiceVpnName, starPeerAddress, starMVGEndpointName,
    starMVGCauseCode, starMVGProtocolType }
    STATUS  current
    DESCRIPTION
 	"A MVG peer is down.

 	 Problem Cause: The MVG peer has failed, or a network connectivity
 	 prevents reaching the peer.

 	 Condition Clear Alarm:  A starMVGPeerUp notification will be generated when
 	 the peer is up"
    --#SUMMARY "[VPN %s] MVG Peer %s endpoint %s is down"
    --#ARGUMENTS {0,1,2}
    --#STATE DEGRADED
    --#SEVERITY MAJOR
    ::= { starentTraps 1169 }

starMVGPeerUp NOTIFICATION-TYPE
    OBJECTS { starServiceVpnName, starPeerAddress, starMVGEndpointName, 
    starMVGCauseCode, starMVGProtocolType }
    STATUS  current
    DESCRIPTION
 	"A MVG peer is up.  This notification is only generated for peers which
 	 have previously been declared down."
    --#SUMMARY "[VPN %s] MVG Peer %s endpoint %s is up"
    --#ARGUMENTS {0,1,2}
    --#STATE OPERATIONAL
    --#SEVERITY INFORMATIONAL
    ::= { starentTraps 1170 }

starPCCNtfyIntfPeerUnreachable NOTIFICATION-TYPE
     OBJECTS { starPCCNtfyIntfPeerName }
     STATUS  current
     DESCRIPTION
     "The IPCF Event Notification Interface peer cannot be reached. ?
     
     Probable Cause: The Event Notification server on SPR is down Or the IP-address/port configuration does not match with the server
     
     Actions to be Taken: Check the Event notification server on SPR and ensure it is running. Ensure that IP-address port combination on IPCF match the server side configurations. 
     
     Clear Condition: Verify that the Event notification interface status on boxer is up.
     
     Condition Clear Alarm: When this condition clears a starNtfyIntfPeerReachable notification will be generated."
     --#SUMMARY "[System] Event Notification Peer (%s) is unreachable"
     --#ARGUMENTS {0}
     --#STATE DEGRADED
     --#SEVERITY MAJOR
     ::= { starentTraps 1173 }
     
starPCCNtfyIntfPeerReachable NOTIFICATION-TYPE
     OBJECTS { starPCCNtfyIntfPeerName }
     STATUS  current
     DESCRIPTION
     " The Notification Interface peer can be reached.?
     
     Action to be Taken: No Action Required."
     --#SUMMARY "[System] Event Notification Peer (%s) is reachable"
     --#ARGUMENTS {0}
     --#STATE OPERATIONAL
     --#SEVERITY INFORMATIONAL
     ::= { starentTraps 1174 }
     
starIPSecNodePeerDown NOTIFICATION-TYPE
    OBJECTS { starServiceVpnName, starServiceServName, starPeerAddress }
    STATUS  current
    DESCRIPTION
        "A Node Service peer has stopped responding.

         Problem Cause: The IPSec Node peer has failed, or a network connectivity
         prevents reaching the peer.

         Condition Clear Alarm:  A starIPSecNodePeerUp notification will be generated when
         the peer is up"
    --#SUMMARY "[Service %s-%s] IPSec Node peer %s is down"
    --#ARGUMENTS {0,1,2}
    --#STATE DEGRADED
    --#SEVERITY MAJOR
   ::= { starentTraps 1175 }

starIPSecNodePeerUp NOTIFICATION-TYPE
    OBJECTS { starServiceVpnName, starServiceServName, starPeerAddress }
    STATUS  current
    DESCRIPTION
        "A Node Service peer is back online
        Action to be Taken: No action required"
    --#SUMMARY "[Service %s-%s] IPSec Node peer %s is up"
    --#ARGUMENTS {0,1,2}
    --#STATE OPERATIONAL
    --#SEVERITY INFORMATIONAL
    ::= { starentTraps 1176 }

starApsRemoteResponseFail NOTIFICATION-TYPE
    OBJECTS { starSlotNum, starCardType, starPortSlot }
    STATUS current
    DESCRIPTION
        "APS Remote Response Fail."
    --#SUMMARY "APS Remote Response Fail for card %d type %s port %d"
    --#ARGUMENTS {0,1,2}
    --#STATE OPERATIONAL
    --#SEVERITY INFORMATIONAL
    ::= { starentTraps 1177}

starCdrPurged NOTIFICATION-TYPE
    OBJECTS {starSessGGSNVpnName,starSessGGSNAPNName,starSessGTPPGroupName }
    STATUS  current
    DESCRIPTION
         "CDRs purged"
    --#SUMMARY "[System] CDRs pugrd for context %s in apn %s for gtpp group%d"
    --#ARGUMENTS {0,1,2}
    --#STATE OPERATIONAL
    --#SEVERITY INFORMATIONAL
    ::= { starentTraps 1178 }

starLocalUserAdded NOTIFICATION-TYPE
    OBJECTS {
                starCLIContext,
                starCLIUsername,
                starCLITtyname,
                starCLIRemoteIpAddrType,
                starCLIRemoteIpAddr,
                starCLIDatabaseUsername,
                starCLIPrivs
            }
    STATUS  current
    DESCRIPTION
	"A local user was added to the system.
	 Probable Cause: A command was issued which resulted in a new user
	 being added to the local user database.  If this was not a planned
	 action then further investigation is advised."
    --#SUMMARY "[System] Security: Context %s User %s %s from IP %s added user %s with %s privileges to the local database"
    --#ARGUMENTS {0,1,2,3,4,5}
    --#STATE OPERATIONAL
    --#SEVERITY WARNING
    ::= { starentTraps 1180 }

starLocalUserRemoved NOTIFICATION-TYPE
    OBJECTS {
                starCLIContext,
                starCLIUsername,
                starCLITtyname,
                starCLIRemoteIpAddrType,
                starCLIRemoteIpAddr,
                starCLIDatabaseUsername
            }
    STATUS  current
    DESCRIPTION
	"A local user was removed from the system.
	 Probable Cause: A command was issued which resulted in an existing
	 user being removed from the local user database.  If this was not
	 a planned action then further investigation is advised."
    --#SUMMARY "[System] Security: Context %s User %s %s from IP %s removed user %s from the local database"
    --#ARGUMENTS {0,1,2,3,4}
    --#STATE OPERATIONAL
    --#SEVERITY WARNING
    ::= { starentTraps 1181 }

starLocalUserPrivilegeChanged NOTIFICATION-TYPE
    OBJECTS {
                starCLIUsername,
                starCLITtyname,
                starCLIRemoteIpAddrType,
                starCLIRemoteIpAddr,
                starCLIDatabaseUsername,
                starCLIPrivs
            }
    STATUS  current
    DESCRIPTION
	"A local user's privileges were modified.
	 Probable Cause: A command was issued which resulted in an existing
	 user's privileges being modified.  If this was not a planned action
	 then further investigation is advised."
    --#SUMMARY "[System] Security: User %s %s from IP %s changed user %s privilege to %s in the local database"
    --#ARGUMENTS {0,1,2,3,4}
    --#STATE OPERATIONAL
    --#SEVERITY WARNING
    ::= { starentTraps 1182 }

starOsShellAccessed NOTIFICATION-TYPE
    OBJECTS {
                starCLIContext,
                starCLIUsername,
                starCLITtyname,
                starCLIRemoteIpAddrType,
                starCLIRemoteIpAddr
            }
    STATUS  current
    DESCRIPTION
	"A user has accessed the OS shell.
	 Probable Cause: A command was issued which resulted in a user's
	 access to the operating system shell.  If this activity was not
	 anticipated, then further investigation should be performed."
    --#SUMMARY "[System] Security: Context %s User %s %s from IP %s has gained access to the OS shell"
    --#ARGUMENTS {0,1,2,3}
    --#STATE OPERATIONAL
    --#SEVERITY WARNING
    ::= { starentTraps 1183 }

starTestModeEntered NOTIFICATION-TYPE
    OBJECTS {
                starCLIContext,
                starCLIUsername,
                starCLITtyname,
                starCLIRemoteIpAddrType,
                starCLIRemoteIpAddr
            }
    STATUS  current
    DESCRIPTION
	"A user has entered the StarOS Test Mode.
	 Probable Cause: A command was issued which resulted in a user
	 entering the CLI test command mode.  The test command mode is
	 only intended for maintenance and diagnostic activity and could
	 result in major service disruptions.  If this action was not
	 intentional, the user should exit from test mode."
    --#SUMMARY "[System] Security: Context %s User %s %s from IP %s has entered test mode"
    --#ARGUMENTS {0,1,2,3}
    --#STATE OPERATIONAL
    --#SEVERITY WARNING
    ::= { starentTraps 1184 }

starLicenseFeaturesModified NOTIFICATION-TYPE
    OBJECTS {
                starCLIContext,
                starCLIUsername,
                starCLITtyname,
                starCLIRemoteIpAddrType,
                starCLIRemoteIpAddr
            }
    STATUS  current
    DESCRIPTION
	"A user has manually modified the StarOS license feature set through the CLI.
	 Probable Cause: A command was issued which resulted in a user
	 modifying the set of license features available to the user.  This
	 capability was only intended for maintenance and diagnostic activity
	 and could result in major service disruptions.  If this action was not
	 intentional, the user should restore the original license feature set."
    --#SUMMARY "[System] Security: Context %s User %s %s from IP %s has modified the license feature set"
    --#ARGUMENTS {0,1,2,3}
    --#STATE OPERATIONAL
    --#SEVERITY WARNING
    ::= { starentTraps 1185 }

starHiddenAccessEnabled NOTIFICATION-TYPE
    OBJECTS {
                starCLIContext,
                starCLIUsername,
                starCLITtyname,
                starCLIRemoteIpAddrType,
                starCLIRemoteIpAddr
            }
    STATUS  current
    DESCRIPTION
	"An administrator has explicitly enabled the use of hidden test commands.
	 Probable Cause: A command was configured which resulted in users
	 having access to the specific test commands which may have been previously
	 unavailable.  If this action was not intentional, the user should disable
	 access to the hidden test commands."
    --#SUMMARY "[System] Security: Context %s User %s %s from IP %s has enabled access to hidden test commands"
    --#ARGUMENTS {0,1,2,3}
    --#STATE OPERATIONAL
    --#SEVERITY WARNING
    ::= { starentTraps 1186 }

starHiddenAccessDisabled NOTIFICATION-TYPE
    OBJECTS {
                starCLIContext,
                starCLIUsername,
                starCLITtyname,
                starCLIRemoteIpAddrType,
                starCLIRemoteIpAddr
            }
    STATUS  current
    DESCRIPTION
	"An administrator has explicitly disabled the use of hidden test commands.
	 Probable Cause: A command was configured which resulted in users no longer
	 having access to specific test commands which may have been previously
	 available.  If this action was not intentional, the user should re-enable
	 access to the hidden test commands."
    --#SUMMARY "[System] Security: Context %s User %s %s from IP %s has disabled access to hidden test commands"
    --#ARGUMENTS {0,1,2,3}
    --#STATE OPERATIONAL
    --#SEVERITY WARNING
    ::= { starentTraps 1187 }

 starLawfulInterceptChanged NOTIFICATION-TYPE
     OBJECTS { starCLIUsername, starCLIUsername }
     STATUS current
     DESCRIPTION
         "Original Lawful Intercept configured by Admin: %s is changed by Admin: %s"
     --#SUMMARY "Original Lawful Intercept configured by Admin: %s is changed by Admin: %s"
     --#ARGUMENTS {0,1}
     --#STATE OPERATIONAL
     --#SEVERITY INFORMATIONAL
     ::= { starentTraps 1188 }

starMMES1PathFail NOTIFICATION-TYPE
    OBJECTS { starMMES1PathVpnName, starMMES1PathServName, starMMES1PathENBID, starMMES1PathSelfAddr,
              starMMES1PathSelfPort, starMMES1PathPeerAddr, starMMES1PathPeerPort }
    STATUS  current
    DESCRIPTION
	"An S1 Path between an MME service and an eNodeB has failed.

	 Action to be Taken: If the shutdown of the eNodeB was not planned,
	 determine the health/status of the eNodeB.  If available, verify the 
	 health of the network between the two elements.

	 Clear Condition: The condition is cleared with the S1 Path is
	 reestablished.

	 Condition Clear Alarm:  A starMMES1PathEstab notification will be generated
	 when the S1 path is re-established"
    --#SUMMARY "[S1 Path %s-%s-%s] Path Failed for self endpoint %s:%d peer endpoint %s:%d"
    --#ARGUMENTS {0,1,2,3,4,5,6}
    --#STATE DEGRADED
    --#SEVERITY MAJOR
    ::= { starentTraps 1189 }

starMMES1PathSetup NOTIFICATION-TYPE
    OBJECTS { starMMES1PathVpnName, starMMES1PathServName, starMMES1PathENBID, starMMES1PathSelfAddr,
              starMMES1PathSelfPort, starMMES1PathPeerAddr, starMMES1PathPeerPort }
    STATUS  current
    DESCRIPTION
	"An S1 Path between an MME service and an eNodeB has been 
	 established.  Normally a starMMES1PathSetup notification would be 
	 generated only for a path which had previously failed, but
	 optionally this notification can be generated for any path
	 setup."
    --#SUMMARY "[S1 Path %s-%s-%s] Path Setup for self endpoint %s:%d peer endpoint %s:%d"
    --#ARGUMENTS {0,1,2,3,4,5,6}
    --#STATE OPERATIONAL
    --#SEVERITY INFORMATIONAL
    ::= { starentTraps 1190 }

starSAEGWServiceStart NOTIFICATION-TYPE
    OBJECTS { starServiceVpnName, starServiceServName }
    STATUS  current
    DESCRIPTION
        "A SAEGW Service has started

         Action to be Taken: No action required"
    --#SUMMARY "[Service SAEGW -%s-%s] SAEGW service has started"
    --#ARGUMENTS {0,1}
    --#STATE OPERATIONAL
    --#SEVERITY INFORMATIONAL
    ::= { starentTraps 1191 }

starSAEGWServiceStop NOTIFICATION-TYPE
    OBJECTS { starServiceVpnName, starServiceServName }
    STATUS  current
    DESCRIPTION
        "A SEAGW Service has stopped.

       Probable Cause: This is typically caused by operator invention.  In
       unusual cases it can be caused by the loss of resources (PACs/PSCs) to
       support the running configuration.

       Action to be Taken: If the SAEGW service shutdown was not planned,
       examine the admin logs for an indication of the failure.  Verify that
       all configured PACs/PSCs are present and running in the system.  Check the
       crash logs for an indication of a software failure.

       Clear Condition: Verify that the SEAGW service is operational.

       Condition Clear Alarm: A starSAEGWServiceStart notification will be
                              generated when the service is restarted"
    --#SUMMARY "[Service SAEGW-%s-%s] SAEGW service has stopped"
    --#ARGUMENTS {0,1}
    --#STATE DEGRADED
    --#SEVERITY MAJOR
    ::= { starentTraps 1192 }


starHenbgwAccessServiceStart NOTIFICATION-TYPE
    OBJECTS { starServiceVpnName, starServiceServName }
    STATUS  current
    DESCRIPTION
        "A HENBGW Access Service has started

         Action to be Taken: No action required"
    --#SUMMARY "[Service HenbgwAccess-%s-%s] HENBGW Access service has started"
    --#ARGUMENTS {0,1}
    --#STATE OPERATIONAL
    --#SEVERITY INFORMATIONAL
    ::= { starentTraps 1193 }

starHenbgwAccessServiceStop NOTIFICATION-TYPE
    OBJECTS { starServiceVpnName, starServiceServName }
    STATUS  current
    DESCRIPTION
        "A HENBGW Access Service has stopped.

       Probable Cause: This is typically caused by operator invention.  In
       unusual cases it can be caused by the loss of resources (PACs/PSCs) to
       support the running configuration.

       Action to be Taken: If the HENBGW Access service shutdown was not planned,
       examine the admin logs for an indication of the failure.  Verify that
       all configured PACs/PSCs are present and running in the system.  Check the
       crash logs for an indication of a software failure.

       Clear Condition: Verify that the HENBGW Access service is operational.

       Condition Clear Alarm: A starHenbgwAccessServiceStart notification will be
                              generated when the service is restarted"
    --#SUMMARY "[Service HenbgwAccess-%s-%s] HENBGW Access service has stopped"
    --#ARGUMENTS {0,1}
    --#STATE DEGRADED
    --#SEVERITY MAJOR
    ::= { starentTraps 1194 }

starHenbgwNetworkServiceStart NOTIFICATION-TYPE
    OBJECTS { starServiceVpnName, starServiceServName }
    STATUS  current
    DESCRIPTION
        "A HENBGW Network Service has started

         Action to be Taken: No action required"
    --#SUMMARY "[Service HenbgwNetwork-%s-%s] HENBGW Network service has started"
    --#ARGUMENTS {0,1}
    --#STATE OPERATIONAL
    --#SEVERITY INFORMATIONAL
    ::= { starentTraps 1195 }

starHenbgwNetworkServiceStop NOTIFICATION-TYPE
    OBJECTS { starServiceVpnName, starServiceServName }
    STATUS  current
    DESCRIPTION
        "A HENBGW Network Service has stopped.

       Probable Cause: This is typically caused by operator invention.  In
       unusual cases it can be caused by the loss of resources (PACs/PSCs) to
       support the running configuration.

       Action to be Taken: If the HENBGW Network service shutdown was not planned,
       examine the admin logs for an indication of the failure.  Verify that
       all configured PACs/PSCs are present and running in the system.  Check the
       crash logs for an indication of a software failure.

       Clear Condition: Verify that the HENBGW Network service is operational.

       Condition Clear Alarm: A starHenbgwNetworkServiceStart notification will be
                              generated when the service is restarted"
    --#SUMMARY "[Service HenbgwNetwork-%s-%s] HENBGW Network service has stopped"
    --#ARGUMENTS {0,1}
    --#STATE DEGRADED
    --#SEVERITY MAJOR
    ::= { starentTraps 1196 }

starAAAArchiveStarted NOTIFICATION-TYPE
    OBJECTS {starTaskInstance}
    STATUS  current
    DESCRIPTION
         "Archive started"
    --#SUMMARY "[System] AAA Archive started for sessmgr instance %d"
    --#ARGUMENTS {1}
    --#STATE OPERATIONAL
    --#SEVERITY INFORMATIONAL
    ::= { starentTraps 1197 }

starECSTotalDNSLearntIPv4Threshold NOTIFICATION-TYPE
    OBJECTS {starECSTotalDNSLearntIPThresholdInstance, starECSTotalDNSLearntIPThresholdconfigured, starECSTotalDNSLearntIPThresholdmeasured}
    STATUS  current
    DESCRIPTION
    " DNS Learnt IPv4 entries exceed the threshold limit (high water mark) configured.
    For IPv4 Max IP entries = 512,00
    Alarm Cleared when the IPv4 entries go below the Lower Water Mark configured"
    --#SUMMARY "[ACSMgr Instance %d] Threshold-%d Measured value-%d"
    --#ARGUMENTS {0,1,2}
    --#STATE OPERATIONAL
    --#SEVERITY INFORMATIONAL
    ::= { starentTraps 1198 }

starECSTotalDNSLearntIPv4ThresholdClear NOTIFICATION-TYPE
    OBJECTS {starECSTotalDNSLearntIPThresholdInstance, starECSTotalDNSLearntIPThresholdconfigured, starECSTotalDNSLearntIPThresholdmeasured}
    STATUS current
    DESCRIPTION
    "DNS Learnt IPv4 entries reach below  the threshold limit (lower water mark) configured."
    --#SUMMARY "[ACSMgr Instance %d] Threshold-%d Measured value-%d"
    --#ARGUMENTS {0,1,2}
    --#STATE OPERATIONAL
    --#SEVERITY INFORMATIONAL
    ::= { starentTraps 1199 }

starECSTotalDNSLearntIPv6Threshold NOTIFICATION-TYPE
    OBJECTS {starECSTotalDNSLearntIPThresholdInstance, starECSTotalDNSLearntIPThresholdconfigured, starECSTotalDNSLearntIPThresholdmeasured}
    STATUS current
    DESCRIPTION
    "DNS Learnt IPv6 entries exceed the threshold limit (high water mark) configured.
    For IPv6 Max IP entries = 256,00
    Alarm Cleared when the IPv6 entries go below the Lower Water Mark configured"
     --#SUMMARY "[ACSMgr Instance %d] Threshold-%d Measured value-%d"
     --#ARGUMENTS {0,1,2}
     --#STATE OPERATIONAL
     --#SEVERITY INFORMATIONAL
     ::= { starentTraps 1200 }

starECSTotalDNSLearntIPv6ThresholdClear NOTIFICATION-TYPE
    OBJECTS {starECSTotalDNSLearntIPThresholdInstance, starECSTotalDNSLearntIPThresholdconfigured, starECSTotalDNSLearntIPThresholdmeasured}
    STATUS current
    DESCRIPTION
    "DNS Learnt IPv6 entries reach below the threshold limit (lower water mark) configured."
     --#SUMMARY "[ACSMgr Instance %d] Threshold-%d Measured value-%d"
     --#ARGUMENTS {0,1,2}
     --#STATE OPERATIONAL
     --#SEVERITY INFORMATIONAL
    ::= { starentTraps 1201 }


starIPSecNodeIpv6PeerDown NOTIFICATION-TYPE
    OBJECTS { starServiceVpnName, starServiceServName, starPeerAddressIpv6 }
    STATUS  current
    DESCRIPTION
        "A Node Service peer has stopped responding. This peer is reached using an IPv6 address.

         For IPv4-connected peers, a starIPSecNodePeerDown notification would be generated.

         Problem Cause: The IPSec Node peer has failed, or a network connectivity
         prevents reaching the peer.

         Condition Clear Alarm:  A starIPSecNodeIpv6PeerUp notification will be generated when
         the peer is up"
    --#SUMMARY "[Service %s-%s] IPSec Node peer %s is down"
    --#ARGUMENTS {0,1,2}
    --#STATE DEGRADED
    --#SEVERITY MAJOR
   ::= { starentTraps 1202 }

starIPSecNodeIpv6PeerUp NOTIFICATION-TYPE
    OBJECTS { starServiceVpnName, starServiceServName, starPeerAddressIpv6 }
    STATUS  current
    DESCRIPTION
        "A Node Service peer is back online. This peer is reached using an IPv6 address.

         For IPv4-connected peers, a starIPSecNodePeerUp notification would be generated.

        Action to be Taken: No action required"
    --#SUMMARY "[Service %s-%s] IPSec Node peer %s is up"
    --#ARGUMENTS {0,1,2}
    --#STATE OPERATIONAL
    --#SEVERITY INFORMATIONAL
    ::= { starentTraps 1203 }

starLAGGroupDown NOTIFICATION-TYPE
    OBJECTS { starPortSlot, starPortNum, starLAGPartner }
    STATUS  current
    DESCRIPTION
    "LAG group status is Down. This notification is only generated for master physical port and
     a previous 'starLAGGroupUp' notification was previously generated.

     Action to be Taken: No action required. The cause for the LAG down should be investigated."
    --#SUMMARY "[Port] LAG group status is down Slot %d Port %d Partner %s"
    --#ARGUMENTS {0,1,2}
    --#STATE DEGRADED
    --#SEVERITY MAJOR
    ::= { starentTraps 1204 }

starLAGGroupUp NOTIFICATION-TYPE
    OBJECTS { starPortSlot, starPortNum, starLAGPartner }
    STATUS  current
    DESCRIPTION
    "LAG group status is up. This notification is only generated for master physical port.

     Action to be Taken: No action required"
    --#SUMMARY "[Port] LAG group status is up Slot %d Port %d Partner %s"
    --#ARGUMENTS {0,1,2}
    --#STATE OPERATIONAL
    --#SEVERITY INFORMATIONAL
    ::= { starentTraps 1205 }

starVLRAssocDown NOTIFICATION-TYPE
    OBJECTS { starSGSServiceVpnName, starSGSServiceServName, starVLRName,  starVLRIpAddr1,
              starVLRIpAddr2, starVLRPortNum }
    STATUS  current
    DESCRIPTION
        "A VLR Association is down.

         Problem Cause: The VLR Association has failed, or a network connectivity prevents reaching the VLR.  
         
         Condition Clear Alarm:  A starVLRAssocUp notification will be generated when the VLR association is up"
    --#SUMMARY "[ VLR Association %s-%s-%s] is down; End point Addr1: %s Addr2: %s Port: %d"
    --#ARGUMENTS {0,1,2,3,4,5}
    --#STATE DEGRADED
    --#SEVERITY MAJOR
    ::= { starentTraps 1206}

starVLRAssocUp  NOTIFICATION-TYPE
    OBJECTS { starSGSServiceVpnName, starSGSServiceServName, starVLRName, starVLRIpAddr1,   
              starVLRIpAddr2,  starVLRPortNum }
    STATUS  current
    DESCRIPTION
        "A VLR Association is up.  This notification is only generated for Association 
         which have previously been declared down."
    --#SUMMARY "[ VLR Association %s-%s-%s] is up; End pointAddr1: %s Addr2: %s Port %d"
    --#ARGUMENTS {0,1,2,3,4,5}
    --#STATE OPERATIONAL
    --#SEVERITY INFORMATIONAL
    ::= { starentTraps 1207}

starVLRAllAssocDown NOTIFICATION-TYPE
    OBJECTS { starSGSServiceVpnName,  starSGSServiceServName }
    STATUS  current
    DESCRIPTION
        "All the VLR Associations are down.

         Problem Cause: All the VLR Associations has failed, or  network connectivity
         prevents reaching the VLRs.

         Condition Clear Alarm:  A starVLRAllAssocUp notification will be generated when
         all the VLR associations are  up"
    --#SUMMARY "All VLR Associations are down %s-%s"
    --#ARGUMENTS {0,1}
    --#STATE DEGRADED
    --#SEVERITY MAJOR
    ::= { starentTraps 1208}

starVLRAllAssocDownClear  NOTIFICATION-TYPE
    OBJECTS { starSGSServiceVpnName,  starSGSServiceServName }
    STATUS  current
    DESCRIPTION
        "VLR at least one association is up.  This notification is only generated for all the Association which
         have previously been declared down."
    --#SUMMARY "VLR at least one association is up %s-%s"
    --#ARGUMENTS {0,1}
    --#STATE OPERATIONAL
    --#SEVERITY INFORMATIONAL
    ::= { starentTraps 1209 }

starEnhancedCongestion NOTIFICATION-TYPE
    OBJECTS { starServiceType, starCongestionPolicy, starCongestionResourceType, starCongestionType, starCongestionActionProfileName}
    STATUS current
    DESCRIPTION
        "A congestion condition has occurred.

         Probable Cause:  This is the result of an operator-configured congestion
         threshold being reached.  This can be due to high usage of the resource
         being monitored which indicates that the IMG is reaching its peak
         capacity, or could be caused by the incorrect configuration of the
         congestion thresholds.

         Actions to be Taken:  Verify that the congestion thresholds are correct;
         if the congested state is seem repeatedly, or for sustained periods of
         time, additional system capacity may need to be brought online.

         This system is cleared when the use of the specific resource falls below
         the configured limit.

         Condition Clear Alarm: A starCongestionClear notification is sent when there
         are no congestion conditions for a service type"
    --#SUMMARY "[System] Congestion seen for %s service; resource %s, policy %s applied, %s threshold exceeded, action profile %s"
    --#ARGUMENTS {0,2,1,3,4}
    --#STATE DEGRADED
    --#SEVERITY MAJOR
    ::= { starentTraps 1210 }

starEnhancedCongestionClear NOTIFICATION-TYPE
    OBJECTS { starServiceType, starCongestionType }
    STATUS current
    DESCRIPTION
        "A congestion condition has cleared."
    --#SUMMARY "[System] Congestion cleared for service %s threshold %s"
    --#ARGUMENTS {0,1}
    --#STATE OPERATIONAL
    --#SEVERITY INFORMATIONAL
    ::= { starentTraps 1211 }

starSGSNRNCNoResetAck NOTIFICATION-TYPE
    OBJECTS { starSessSGSNVpnName, starSessSGSNServName,starSessSGSNMcc,starSessSGSNMnc,starSessSGSNRncId}
    STATUS  current
    DESCRIPTION
    "SGSN has not received an Radio Network Controller(RNC) reset-ack event. 
    This event is generated on expiry of all retransmission for RNC Reset and non-receipt of Reset-Ack."

    --#SUMMARY "[Service SGSN %s-%s] RNC Reset Ack event not received ; MCC %s MNC %s RncId %d"
    --#ARGUMENTS {0,1,2,3,4}
    --#STATE OPERATIONAL
    --#SEVERITY INFORMATIONAL
    ::= { starentTraps 1212 }

starThreshSAEGWSessions NOTIFICATION-TYPE
    OBJECTS { starThreshInt, starThreshMeasuredInt }
    STATUS  current
    DESCRIPTION
        "The total number of SAEGW sessions is above the configured threshold 
        value. 
        
        Probable Cause: This is a user configurable threshold.
        
        If the thresholding subsystem is configured to run in an 'alarm' 
        model,a starThreshClearSAEGWSessions notification will be generated 
        when the measured value falls below the threshold"
    --#SUMMARY "ThreshSAEGWSessions threshold %d measured value %d"
    --#ARGUMENTS {0,1}
    --#STATE OPERATIONAL
    --#SEVERITY WARNING
    ::= { starentTraps 1213 }

starThreshClearSAEGWSessions NOTIFICATION-TYPE
    OBJECTS { starThreshInt, starThreshMeasuredInt }
    STATUS  current
    DESCRIPTION
        "The threshold condition is now clear."
    --#SUMMARY "ThreshClearSAEGWSessions threshold %d measured value %d"
    --#ARGUMENTS {0,1}
    --#STATE OPERATIONAL
    --#SEVERITY INFORMATION
    ::= { starentTraps 1214 }

starSGSNRMCPUWarn NOTIFICATION-TYPE
    OBJECTS { starTaskFacilityName, starTaskInstance, starTaskCard,
              starTaskCPU, starThreshInt, starThreshMeasuredInt }
    STATUS  current
    DESCRIPTION
    "The CPU usage is goin in Warning level.
    This event is generated when current CPU usage reaches 90% of allocated limit.

    Condition Clear Alarm: A starSGSNRMCPUWarnClear notification is sent when there
    CPU usage reaches 50% of allocated limit after warning"

    --#SUMMARY "[SGSN Facility %s-%d] Card %d CPU %d allocated %d used %d"
    --#ARGUMENTS {0,1,2,3,4,5}
    --#STATE OPERATIONAL
    --#SEVERITY WARNING 
    ::= { starentTraps 1215 }

starSGSNRMCPUWarnClear NOTIFICATION-TYPE
    OBJECTS { starTaskFacilityName, starTaskInstance, starTaskCard,
              starTaskCPU, starThreshInt, starThreshMeasuredInt }
    STATUS  current
    DESCRIPTION
    "The CPU usage is coming back to normal once warned.
    This event is generated when current CPU usage reaches 50% of allocated limit after warning."

    --#SUMMARY "[SGSN Facility %s-%d] Card %d CPU %d allocated %d used %d"
    --#ARGUMENTS {0,1,2,3,4,5}
    --#STATE OPERATIONAL
    --#SEVERITY INFORMATIONAL
    ::= { starentTraps 1216 }

starSGSNRMMemWarn NOTIFICATION-TYPE
    OBJECTS { starTaskFacilityName, starTaskInstance, starTaskCard,
              starTaskCPU, starThreshInt, starThreshMeasuredInt }
    STATUS  current
    DESCRIPTION
    "The Memory usage for the proclet is going in Warning level.
    This event is generated when current Memory usage exceeds allocated limit.

    Condition Clear Alarm: A starSGSNRMMemWarnClear notification is sent when  
    current Memory usage reaches below 95% of allocated limit once warned."

    --#SUMMARY "[SGSN Facility %s-%d] Card %d CPU %d allocated %d used %d"
    --#ARGUMENTS {0,1,2,3,4,5}
    --#STATE OPERATIONAL
    --#SEVERITY WARNING
    ::= { starentTraps 1217 }

starSGSNRMMemWarnClear NOTIFICATION-TYPE
    OBJECTS { starTaskFacilityName, starTaskInstance, starTaskCard,
              starTaskCPU, starThreshInt, starThreshMeasuredInt }
    STATUS  current
    DESCRIPTION
    "The Memory usage for the proclet is coming back to normal once warned.
    This event is generated when current Memory usage reaches below 95% of allocated limit once warned."

    --#SUMMARY "[SGSN Facility %s-%d] Card %d CPU %d allocated %d used %d"
    --#ARGUMENTS {0,1,2,3,4,5}
    --#STATE OPERATIONAL
    --#SEVERITY INFORMATIONAL
    ::= { starentTraps 1218 }

starRMCPUOver NOTIFICATION-TYPE
    OBJECTS { starTaskFacilityName, starTaskInstance, starTaskCard,
              starTaskCPU, starThreshInt, starThreshMeasuredInt }
    STATUS  current
    DESCRIPTION
    "The CPU usage is goin in Overlaod level.
    This event is generated when current CPU usage reaches 50% more of allocated limit.

    Condition Clear Alarm: A starRMCPUOverClear notification is sent when  
    urrent CPU usage reaches 50% of allocated limit after over"

    --#SUMMARY "[SGSN Facility %s-%d] Card %d CPU %d allocated %d used %d"
    --#ARGUMENTS {0,1,2,3,4,5}
    --#STATE OPERATIONAL
    --#SEVERITY WARNING
    ::= { starentTraps 1219 }

starRMCPUOverClear NOTIFICATION-TYPE
    OBJECTS { starTaskFacilityName, starTaskInstance, starTaskCard,
              starTaskCPU, starThreshInt, starThreshMeasuredInt }
    STATUS  current
    DESCRIPTION
    "The CPU usage is going back to normal level.
    This event is generated when current CPU usage reaches 50% of allocated limit after over."

    --#SUMMARY "[SGSN Facility %s-%d] Card %d CPU %d allocated %d used %d"
    --#ARGUMENTS {0,1,2,3,4,5}
    --#STATE OPERATIONAL
    --#SEVERITY INFORMATIONAL
    ::= { starentTraps 1220 }

starSGSNRMMemOver NOTIFICATION-TYPE
    OBJECTS { starTaskFacilityName, starTaskInstance, starTaskCard,
              starTaskCPU, starThreshInt, starThreshMeasuredInt }
    STATUS  current
    DESCRIPTION
    "The Memory usage of the task is going in Overload level.
    This event is generated when current Memory usage reached twice allocated limit."

    --#SUMMARY "[SGSN Facility %s-%d] Card %d CPU %d allocated %d used %d"
    --#ARGUMENTS {0,1,2,3,4,5}
    --#STATE OPERATIONAL
    --#SEVERITY WARNING 
    ::= { starentTraps 1221 }

starSGSNRMMemOverClear NOTIFICATION-TYPE
    OBJECTS { starTaskFacilityName, starTaskInstance, starTaskCard,
              starTaskCPU, starThreshInt, starThreshMeasuredInt }
    STATUS  current
    DESCRIPTION
    "The Memory usage for a proclet reached normal after overload.
    This event is generated when current Memory usage reaches 95% of allocated limit once overloaded."

    --#SUMMARY "[SGSN Facility %s-%d] Card %d CPU %d allocated %d used %d"
    --#ARGUMENTS {0,1,2,3,4,5}
    --#STATE OPERATIONAL
    --#SEVERITY INFORMATIONAL
    ::= { starentTraps 1222 }

starSessMgrFlowCount NOTIFICATION-TYPE
    OBJECTS {
                starSessMgrFlowInstId,
                starSessMgrFlowPDNNo,
                starSessMgrFlowMemUsage,
                starSessMgrFlowCounter,
                starSessMgrTotalFlowCount
            }
    STATUS  current
    DESCRIPTION
    "Session Manager Flows counting, This event is genereted when number of flows in a session manager instance
    goes beyond configured threshold,it will also print number of PDN, Memeory usage and sess manager instance number."

    --#SUMMARY "[Session Manager Instance %d] is Having Total number of PDNs %d with Memory Usage %d and Max Flows per Session %d, Total used Flows %d"
    --#ARGUMENTS {0,1,2,3,4}
    --#STATE OPERATIONAL
    --#SEVERITY INFORMATIONAL
    ::= { starentTraps 1223 }

starSessMgrFlowCountClear NOTIFICATION-TYPE
    OBJECTS {
                starSessMgrFlowInstId,
                starSessMgrFlowPDNNo,
                starSessMgrFlowMemUsage,
                starSessMgrFlowCounter,
                starSessMgrTotalFlowCount
            }
    STATUS  current
    DESCRIPTION
    "Clear Session Manager Flows Counting Trap, This event is genereted when number of flows in a session manager instance
    goes below configured threshold,it will also print number of PDN, Memeory usage and sess manager instance number."

    --#SUMMARY "[Session Manager Instance %d] is Having Total number of PDNs %d with Memory Usage %d and Max Flows per Session %d, Total used Flows %d"
    --#ARGUMENTS {0,1,2,3,4}
    --#STATE OPERATIONAL
    --#SEVERITY INFORMATIONAL
    ::= { starentTraps 1224 }

starStorageFound NOTIFICATION-TYPE
     OBJECTS { starStorageSlot, starStorageName }
     STATUS  current
     DESCRIPTION
     "The specified storage device is found and mounted successfully
     on the card. This notification only generated to the storage device for
     which 'starStorageNotFound' notification was generated"
 
     --#SUMMARY "[Slot-%d] Storage device is found and mounted on %s"
     --#ARGUMENTS {0,1}
     --#STATE OPERATIONAL
     --#SEVERITY INFORMATIONAL
     ::= { starentTraps 1225 } 
 
starStorageNotFound NOTIFICATION-TYPE
     OBJECTS { starStorageSlot, starStorageName }
     STATUS  current
     DESCRIPTION
     "The specified storage device not found on the card.  
     This notification is currently only generated for failures to access
     the specified storage device on the card.
     Probable Cause: The storage device is not accessible on the card.
   
     Action to be Taken: Verify the storage device on the card is attached
     correctly.
 
     Condition Clear Alarm: A starStorageFound notification will be generated
     when the storage device is mounted on the card."
     --#SUMMARY "[Slot-%d] Storage device %s is not mounted or present"
     --#ARGUMENTS {0,1}
     --#STATE DEGRADED
     --#SEVERITY MAJOR
     ::= { starentTraps 1226 }

starHENBGWMMESCTPAssocDown NOTIFICATION-TYPE
     OBJECTS { starHENBGWServiceVpnName, starHENBGWServiceServName, starHENBGWServiceLogicalENBId,   
               starHENBGWServiceMMEServName, starHENBGWServicePeerAddr, starHENBGWServicePeerPort }
     STATUS  current
     DESCRIPTION
         "A HENBGW MME SCTP Association is down.
          Problem Cause: The HENBGW MME SCTP Association has failed, or a network 
          connectivity prevents reaching the MME.

          Condition Clear Alarm:  A starHENBGWMMESCTPAssocUp notification will be generated when 
          the HENBGW MME SCTP association is up."
     --#SUMMARY "[ HENBGW MME Association %s-%s-%s-%s] is down; End pointAddr: %s Port %d"
     --#ARGUMENTS {0,1,2,3,4,5}
     --#STATE DEGRADED
     --#SEVERITY MAJOR
     ::= { starentTraps 1227 }

starHENBGWMMESCTPAssocUp  NOTIFICATION-TYPE
     OBJECTS { starHENBGWServiceVpnName, starHENBGWServiceServName, starHENBGWServiceLogicalENBId,   
               starHENBGWServiceMMEServName, starHENBGWServicePeerAddr, starHENBGWServicePeerPort }
     STATUS  current
     DESCRIPTION
         "A HENBGW MME SCTP Association is up.  This notification is only generated for   
          Association which have previously been declared down, optionally this notification 
	  can be generated for any association up."
     --#SUMMARY "[HENBGW MME Association %s-%s-%s-%s] is up; End pointAddr: %s Port %d"
     --#ARGUMENTS {0,1,2,3,4,5}
     --#STATE OPERATIONAL
     --#SEVERITY INFORMATIONAL
     ::= { starentTraps 1228 }

starHENBGWMMESCTPAllAssocDown NOTIFICATION-TYPE
     OBJECTS { starHENBGWServiceVpnName, starHENBGWServiceServName }
     STATUS  current
     DESCRIPTION
         "All the HENBGW MME SCTP Associations are down.
          Problem Cause: All the HENBGW MME SCTP Associations has failed, or network connectivity
          prevents reaching the MMEs.

          Condition Clear Alarm:  A starHENBGWMMESCTPAllAssocDownClear notification will be  
          generated when at least one HENBGW MME SCTP association is up."
     --#SUMMARY "All HENBGW MME SCTP Associations are down %s-%s"
     --#ARGUMENTS {0,1}
     --#STATE NONOPERATIONAL
     --#SEVERITY CRITICAL
     ::= { starentTraps 1229 }

starHENBGWMMESCTPAllAssocDownClear  NOTIFICATION-TYPE
     OBJECTS { starHENBGWServiceVpnName, starHENBGWServiceServName }
     STATUS  current
     DESCRIPTION
         "HENBGW MME SCTP at least one association is up.  This notification is only generated for 
          all the Association which have previously been declared down."
     --#SUMMARY "HENBGW MME SCTP at least one association is up %s-%s"
     --#ARGUMENTS {0,1}
     --#STATE OPERATIONAL
     --#SEVERITY INFORMATIONAL
     ::= { starentTraps 1230 }

starNPDBConnectionDown NOTIFICATION-TYPE
     OBJECTS { starTaskFacilityName, starTaskInstance, starNwReachSrvrAddr}
     STATUS  current
     DESCRIPTION
         " A NPDB connection is down.

         Probable Cause: This is typically caused when NPDB server resets the socket.

         Action to be Taken: Check if the NDPB Server is running.

         Clear Condition: Verify that PING PONG messages are exchanged with the NPDB Server.

         Condition Clear Alarm:   A startNPDBConnectionUp notification will be generated when
         the service is restarted"
     --#SUMMARY "[CSCF Task %s/%d] Connection  to NPDB server %s is down"
     --#ARGUMENTS {0,1,2}
     --#STATE DEGRADED
     --#SEVERITY MAJOR
     ::= { starentTraps 1231 }

starNPDBConnectionUp NOTIFICATION-TYPE
     OBJECTS { starTaskFacilityName, starTaskInstance, starNwReachSrvrAddr}
     STATUS  current
     DESCRIPTION
         " A NPDB connection is up.

            Action to be Taken: No action required"
     --#SUMMARY "[CSCF Task %s/%d] Connection  to NPDB server %s is up"
     --#ARGUMENTS {0,1,2}
     --#STATE OPERATIONAL
     --#SEVERITY MAJOR
     ::= { starentTraps 1232 }

starNPUMissedARPFrames NOTIFICATION-TYPE
     OBJECTS { starNPUSlotNumber, starNPUCPUNumber, starNPUNPUNumber }
     STATUS  current
     DESCRIPTION
     "This trap will be raised when NPU misses the ARP and packets route 
     to kernel. This will print the slot number CPU number and NPU number"
 
     --#SUMMARY "[Slot-%d] CPU %d NPU %d are routed through the kernel"
     --#ARGUMENTS {0,1,2}
     --#STATE DEGRADED
     --#SEVERITY MAJOR
     ::= { starentTraps 1233 } 

starNPUMissedARPFramesClear NOTIFICATION-TYPE
     OBJECTS { starNPUSlotNumber, starNPUCPUNumber, starNPUNPUNumber }
     STATUS  current
     DESCRIPTION
     "This clear trap will be raised when NPU misses the ARP and packets route 
     to kernel recovers. This will print the slot number CPU number and NPU number"
 
     --#SUMMARY "[Slot-%d] CPU %d NPU %d are routed through the kernel"
     --#ARGUMENTS {0,1,2}
     --#STATE DEGRADED
     --#SEVERITY MAJOR
     ::= { starentTraps 1234 } 

starChassisCrashListFull  NOTIFICATION-TYPE
     OBJECTS { starChassisCrashList }
     STATUS  current
     DESCRIPTION
         "Chassis crash list is reached full. This notification is generated 
          when no more space is left to store the crash list and reached 
          to disk limit."
     --#SUMMARY "[System] Chassis Crash List is %s"
     --#ARGUMENTS {0}
     --#STATE OPERATIONAL
     --#SEVERITY INFORMATIONAL
     ::= { starentTraps 1235 } 

starSessMgrCSCFServiceRecoveryComplete NOTIFICATION-TYPE
     OBJECTS {starServiceVpnName, starServiceServName, starTaskInstance, starCPUSlot, starCPUNumber}
     STATUS  current
     DESCRIPTION
     "Indicates that the CSCF Service had completed recovery.
      This trap is generated when all the calls are recovered and the listen socket becomes active to accept packets"
 
     --#SUMMARY "[Service CSCF %s-%s] CSCF Service Recovery Complete For Sessmgr Instance %d on %d/%d"
      --#ARGUMENTS {0,1,2,3,4}
      --#STATE OPERATIONAL
      --#SEVERITY INFORMATIONAL
     ::= { starentTraps 1236 }


starECSreaddressServerDown  NOTIFICATION-TYPE
    OBJECTS { starPeerAddress, starUDPPortNum}
     STATUS  current
     DESCRIPTION
        "Server from readdress server list is detected down
         This notification is generated when there are consecutive failures for server."
     --#SUMMARY "ECS Readdress server-list server %s:%d going down"
     --#ARGUMENTS {0,1}
     --#STATE OPERATIONAL
     --#SEVERITY INFORMATIONAL
     ::= { starentTraps 1237 }

starECSreaddressServerUp NOTIFICATION-TYPE
    OBJECTS { starPeerAddress, starUDPPortNum}
     STATUS  current
     DESCRIPTION
        "Server from readdress server list is detected up
         This notification is generated when after deadtime server is detected up."
     --#SUMMARY "ECS Readdress server-list server %s:%d is up"
     --#ARGUMENTS {0,1}
     --#STATE OPERATIONAL
     --#SEVERITY INFORMATIONAL
     ::= { starentTraps 1238 }

starCdrHDDStart NOTIFICATION-TYPE
    OBJECTS {starServiceVpnName,starSessGTPPGroupName}
    STATUS  current
    DESCRIPTION
         "CDRs are being written to the HDD"
    --#SUMMARY "[System] CDRs are being written to the HDD for context %s for gtpp group%s"
    --#ARGUMENTS {0,1}
    --#STATE OPERATIONAL
    --#SEVERITY INFORMATIONAL
    ::= { starentTraps 1239 }

starCdrStreamingStart NOTIFICATION-TYPE
    OBJECTS {starServiceVpnName,starSessGTPPGroupName}
    STATUS  current
    DESCRIPTION
         "CDR streaming is started"
    --#SUMMARY "[System] CDR streaming is started for context %s for gtpp group%s"
    --#ARGUMENTS {0,1}
    --#STATE OPERATIONAL
    --#SEVERITY INFORMATIONAL
    ::= { starentTraps 1240 }

starCdrStreamingComplete NOTIFICATION-TYPE
    OBJECTS {starServiceVpnName,starSessGTPPGroupName}
    STATUS  current
    DESCRIPTION
         "CDR streaming is Completed"
    --#SUMMARY "[System] CDR streaming is completed for context %s for gtpp group%s"
    --#ARGUMENTS {0,1}
    --#STATE OPERATIONAL
    --#SEVERITY INFORMATIONAL
    ::= { starentTraps 1241 }

starVLRDown NOTIFICATION-TYPE
    OBJECTS { starSGSServiceVpnName, starSGSServiceServName, starVLRName }
    STATUS  current
    DESCRIPTION
        "A VLR is down.

         Problem Cause: The VLR has failed, or a network connectivity prevents reaching the VLR.  
         
         Condition Clear Alarm:  A starVLRUp notification will be generated when the VLR is up"
    --#SUMMARY "[ VLR %s-%s-%s] is down"
    --#ARGUMENTS {0,1,2}
    --#STATE DEGRADED
    --#SEVERITY MAJOR
    ::= { starentTraps 1242}

starVLRUp  NOTIFICATION-TYPE
    OBJECTS { starSGSServiceVpnName, starSGSServiceServName, starVLRName }  
    STATUS  current
    DESCRIPTION
        "A VLR is up.  This notification is only generated for VLRs 
         which have previously been declared down."
    --#SUMMARY "[ VLR %s-%s-%s] is up"
    --#ARGUMENTS {0,1,2}
    --#STATE OPERATIONAL
    --#SEVERITY INFORMATIONAL
    ::= { starentTraps 1243}

starPCFReachable NOTIFICATION-TYPE
    OBJECTS { starContextName, starPCFAddress }
    STATUS current
    DESCRIPTION
        "A PCF that the IMG communication is reachable."

    --#SUMMARY "[System] PCF Reachable, VPN %s PCF address %s"
    --#ARGUMENTS {0,1}
    --#STATE OPERATIONAL
    --#SEVERITY INFORMATIONAL
    ::= { starentTraps 1244 }

starLIRcvryError NOTIFICATION-TYPE
     OBJECTS { starLIRcvryErrType, starLIRcvryErrString }
     STATUS  current
     DESCRIPTION
     "This trap will be raised when Lawful Intercepts cannot be saved or recovered
     to/from backup. This will print the type of error and error string"

     --#SUMMARY "Lawful Intercept Recovery Error %d: %s"
     --#ARGUMENTS {0,1}
     --#STATE DEGRADED
     --#SEVERITY MAJOR
     ::= { starentTraps 1245 }

starLIRcvryComplete NOTIFICATION-TYPE
     STATUS  current
     DESCRIPTION
     "This trap will be raised when Lawful Intercepts are successfully recovered"

     --#SUMMARY "Lawful Intercepts are recovered successfully"
     --#STATE DEGRADED
     --#SEVERITY INFORMATIONAL
     ::= { starentTraps 1246 }

starCGWServiceStart NOTIFICATION-TYPE
    OBJECTS { starServiceVpnName, starServiceServName }
    STATUS  current
    DESCRIPTION
        "A Serving Gateway (CGW) Service has started.

         Action to be Taken: No action required"
    --#SUMMARY "[Service CGW-%s-%s] CGW service has started"
    --#ARGUMENTS {0,1}
    --#STATE OPERATIONAL
    --#SEVERITY INFORMATION
    ::= { starentTraps 1247 }

starCGWServiceStop NOTIFICATION-TYPE
    OBJECTS { starServiceVpnName, starServiceServName }
    STATUS  current
    DESCRIPTION
        "A Serving Gateway (CGW) Service has stopped.

         Probable Cause: This is typically caused by operator intervention.  In
         rare cases it can be caused by the loss of resources (PSCs) to support
         the running configuration.

         Action to be Taken: If the CGW service shutdown was not planned,
         examine the admin logs for an indication of the failure.  Verify that
         all configured PSCs are present and running in the system.  Check the
         crash logs for an indication of a software failure.

         Clear Condition: Verify that the CGW service is operational.

         Condition Clear Alarm:  A starCGWServiceStart notification will be
         generated when the service is restarted"
    --#SUMMARY "[Service CGW-%s-%s] CGW service has stopped"
    --#ARGUMENTS {0,1}
    --#STATE DEGRADED
    --#SEVERITY MAJOR
    ::= { starentTraps 1248 }

starMMENewConnectionsDisallowed NOTIFICATION-TYPE
    OBJECTS { starMMEInitialDisallowReason, starImsimgrInstId  }
    STATUS  current
    DESCRIPTION
        "The demultiplexer on the MME chassis has reached a condition where new connections are being dropped/rejected on MME services due to the specified reason.Please note that this is the initial trigger for this condition. More reasons/triggers may be activated later i.e. after the trap has been sent. These are not indicated via a new trap.
         Action to be Taken: If this is not intentional (i.e not driven by policy/configuration), cross-check IMSImgr counters using the reason provided.
         Clear Condition: The condition is cleared when new connections at the MME are re-allowed.
         Condition Clear Alarm:  A starMMENewConnectionsAllowed notification will be generated
         when the condition is cleared."
    --#SUMMARY "New connections being dropped/rejected at MME chassis %s due to reason %s"
    --#ARGUMENTS {0,1}
    --#STATE DEGRADED
    --#SEVERITY MAJOR
    ::= { starentTraps 1249}

starMMENewConnectionsAllowed NOTIFICATION-TYPE
    STATUS  current
    DESCRIPTION
        "The MME chassis is now accepting new connections again. All conditions causing MME to disallow new connections have cleared."
    --#SUMMARY "New connections now being allowed at MME chassis %s "
    --#ARGUMENTS {0,1}
    --#STATE OPERATIONAL
    --#SEVERITY INFORMATIONAL
    ::= { starentTraps 1250 }

starSAMOGServiceStart NOTIFICATION-TYPE
    OBJECTS { starServiceVpnName, starServiceServName }
    STATUS  current
    DESCRIPTION
        "A SAMOG Service has started

         Action to be Taken: No action required"
    --#SUMMARY "[Service SAMOG-%s-%s] SAMOG service has started"
    --#ARGUMENTS {0,1}
    --#STATE OPERATIONAL
    --#SEVERITY INFORMATIONAL
    ::= { starentTraps 1251 }

starSAMOGServiceStop NOTIFICATION-TYPE
    OBJECTS { starServiceVpnName, starServiceServName }
    STATUS  current
    DESCRIPTION
        "A SAMOG Service has stopped.

         Probable Cause: This is typically caused by operator invention.  In
         unusual cases it can be caused by the loss of resources (PACs/PSCs) to
         support the running configuration.

         Action to be Taken: If the SAMOG service shutdown was not planned,
         examine the admin logs for an indication of the failure.  Verify that
         all configured PACs/PSCs are present and running in the system.  Check the
         crash logs for an indication of a software failure.

         Clear Condition: Verify that the SAMOG service is operational.

         Condition Clear Alarm:  A starSAMOGServiceStart notification will be generated when
         the service is restarted"
    --#SUMMARY "[Service SAMOG-%s-%s] SAMOG service has stopped"
    --#ARGUMENTS {0,1}
    --#STATE DEGRADED
    --#SEVERITY MAJOR
    ::= { starentTraps 1252 }

starCardSwitchoverStart NOTIFICATION-TYPE
    OBJECTS { starSlotNum, starSlotNum }
    STATUS  current
    DESCRIPTION
    "A management card (SPC/MMIO) switchover operation has begun.
    The first varbind identifies from which management card switchover
    started.
    The second varbind identifies to which management card switchover is
    planned to switch.
    Switchover can cause a momentary loss of communication through the
    management interface (SPIO incase of ASR5000) , it is possible
    that this trap will not be successfully delivered.

    Probable Cause: This is typically caused by an operator action; it can also
    represent the system recovering from a software or hardware fault.

    Action to be Taken: If the management card switchover was unplanned,
    the admin logs should be examined for the cause of the switchover.
    If the cause was a software failure, the system crash logs should be
    examined.

    Clear Condition: Verify the management card  switchover completed 
    successfully.

    Clear Condition Alarm: A starCardSPCSwitchoverComplete is generated when
    the switchover operation has completed.This is not applicable to QVPC-SI."
    --#SUMMARY "Card Switchover start from card %d to card %d"
    --#ARGUMENTS {0,1}
    --#STATE DEGRADED
    --#SEVERITY MAJOR
    ::= { starentTraps 1253 }

starCardSwitchoverComplete NOTIFICATION-TYPE
    OBJECTS { starSlotNum, starSlotNum }
    STATUS  current
    DESCRIPTION
    "A management card (SPC/MMIO) Switchover has completed successfully. 
    The first varbind identifies from which management card switchover
    started.
    The second varbind identifies to which management card switchover is
    completed.

    Action to be Taken: If the management card switchover was unplanned,
    the admin logs should be examined for the cause of the switchover.
    If the cause was a software failure, the system crash logs
    should be examined.This is not applicable to QVPC-SI."
    --#SUMMARY "Card Switchover completed from card %d to card %d"
    --#ARGUMENTS {0,1}
    --#STATE OPERATIONAL
    --#SEVERITY INFORMATIONAL
    ::= { starentTraps 1254 }

starCardSwitchoverFailed NOTIFICATION-TYPE
    OBJECTS { starSlotNum, starSlotNum }
    STATUS  current
    DESCRIPTION
    "A management card (SPC/MMIO) switchover operation has failed. 
    The first varbind identifies from which management card switchover
    started.
    The second varbind identifies to which management card switchover is
    failed.
    
    Probable Cause: The management card being switched to was removed or 
    reset before the switchover completed; the switchover operation was
    terminated by an operator; or a software or hardware failure on another
    management card.

    Action to be Taken: Verify that both management cards have the card
    locks in the locked position; examine the admin logs for the cause of
    the failure.  If the cause was a software failure, the system crash logs
    should be examined.

    Clear Condition: The management card in question will be reset;
    a starCardUp notification will be generated when the card is operational
    again.This is not applicable to QVPC-SI."
    --#SUMMARY "Card Switchover failed from card %d to card %d"
    --#ARGUMENTS {0,1}
    --#STATE NONOPERATIONAL
    --#SEVERITY CRITICAL
    ::= { starentTraps 1255 }


starCardMigrateStart NOTIFICATION-TYPE
    OBJECTS { starSlotNum, starSlotNum }
    STATUS  current
    DESCRIPTION
    "A data processing card (PAC/PSC/DPC) Migration operation has begun.
    The first varbind identifies from which data processing card migration
    has started.
    The second varbind identifies to which data processing card migration is
    planned to migrate.

    Probable Cause: This is typically caused by an operator action; it can also
    represent the system recovering from a software or hardware fault.

    A starCardMigrateComplete is generated when the migration is completed. 
    This is not applicable to QVPC-SI."

    --#SUMMARY "Card Migration started from card %d to card %d"
    --#ARGUMENTS {0,1}
    --#STATE DEGRADED
    --#SEVERITY MAJOR
    ::= { starentTraps 1256 }

starCardMigrateComplete NOTIFICATION-TYPE
    OBJECTS { starSlotNum, starSlotNum }
    STATUS  current
    DESCRIPTION
    "A data processing card (PAC/PSC/DPC) Migration operation has
    successfully completed.
    The first varbind identifies from which data processing card migration has
    started.
    The second varbind identifies to which data processing card migration has
    completed.This is not applicable to QVPC-SI."
    --#SUMMARY "Card Migration completed from card %d to card %d"
    --#ARGUMENTS {0,1}
    --#STATE OPERATIONAL
    --#SEVERITY INFORMATIONAL
    ::= { starentTraps 1257 }

starCardMigrateFailed NOTIFICATION-TYPE
    OBJECTS { starSlotNum, starSlotNum }
    STATUS  current
    DESCRIPTION
    "A data processing card (PAC/PSC/DPC) Migration operation has failed.
    The first varbind identifies from which data processing card migration has
    started.
    The second varbind identifies to which data processing card migration has
    failed to migrate.

    Probable Cause: The data processing card being migrated to was removed or 
    reset before the migration completed; the migration operation was 
    terminated by an operator; or a software or hardware failure on another 
    data processing card involved
    in the migration operation.

    The data processing card in question will be reset; a starCardUp
    notification will be generated when the card is operational again.This is not 
    applicable to QVPC-SI."
    --#SUMMARY "Card Migration failed from card %d to card %d"
    --#ARGUMENTS {0,1}
    --#STATE DEGRADED
    --#SEVERITY MAJOR
    ::= { starentTraps 1258 }

starTechSuppPasswdChanged NOTIFICATION-TYPE
    OBJECTS {  
                starCLIContext,
                starCLIUsername,
                starCLITtyname,
                starCLIRemoteIpAddrType,
                starCLIRemoteIpAddr
            }
    STATUS  current
    DESCRIPTION
        "A user has changed the StarOS tech-support password.
         Probable Cause: A command was issued which resulted in a user
         changing the tech-support password value.  The tech-support
         password is used to gain access to the CLI test-commands.
         These CLI test commands are only intended for maintenance
         and diagnostic activity and could result in major service
         disruptions.  If this action was unintended, the user should
         notify the Cisco TAC group to reset the tech-support password."
    --#SUMMARY "[System] Security: context %s user %s ttyname %s address type %s remote ip address %s"
    --#ARGUMENTS {0,1,2,3,4}
    --#STATE OPERATIONAL
    --#SEVERITY WARNING 
    ::= { starentTraps 1259 }

starPMIPPathFailure NOTIFICATION-TYPE
     OBJECTS { starPMIPVpnName, 
               starPMIPServName, 
               starPMIPSelfAddrType,
               starPMIPSelfAddr,
               starPMIPPeerAddrType, 
               starPMIPPeerAddr, 
               starPMIPPeerOldRstCnt, 
               starPMIPPeerNewRstCnt, 
               starPMIPPeerSessCnt, 
               starPMIPFailureReason 
             }
     STATUS  current
     DESCRIPTION
         "PMIP Path Failure.
          
          Possibe reason: This trap will be triggered by MAGMGR/HAMGR when path failure or node restart is detected."
     --#SUMMARY "[Service PMIP-%s-%s]  path failure, self address %s, peer address %s, peer old restart counter %d,  peer new restart counter %d, peer session count  %d, failure reason %s"
     --#ARGUMENTS {0,1,3,5,6,7,8,9}
     --#STATE DEGRADED
     --#SEVERITY MAJOR
     ::= { starentTraps 1260 } 

starPMIPPathFailureClear NOTIFICATION-TYPE
     OBJECTS { starPMIPVpnName, 
               starPMIPServName, 
               starPMIPSelfAddrType,
               starPMIPSelfAddr,
               starPMIPPeerAddrType,
               starPMIPPeerAddr
             }
     STATUS  current
     DESCRIPTION
         "PMIP Control Path Failure condition is no longer valid."
     --#SUMMARY "[Service PMIP-%s-%s]  path failure condition clear for self address %s, peer address %s"
     --#ARGUMENTS {0,1,3,5}
     --#STATE DEGRADED
     --#SEVERITY MAJOR
     ::= { starentTraps 1261 }

starHENBGWMMESCTPAssocDestAddrDown NOTIFICATION-TYPE
     OBJECTS { starHENBGWServiceVpnName, starHENBGWServiceServName, starHENBGWServiceLogicalENBId,   
               starHENBGWServiceMMEServName, starHENBGWServicePeerAddr, starHENBGWServicePeerPort }
     STATUS  current
     DESCRIPTION
         "A HENBGW MME SCTP Association Destination Address is down.
          Problem Cause: One of destination MME SCTP address is not reachable or removed.

          Condition Clear Alarm:  A starHENBGWMMESCTPAssocDestAddrUp notification will be generated when 
          the HENBGW MME SCTP association destination address is reachable again"
     --#SUMMARY "[ HENBGW MME Association %s-%s-%s-%s] destination address:%s is down; Port %d"
     --#ARGUMENTS {0,1,2,3,4,5}
     --#STATE DEGRADED
     --#SEVERITY MAJOR
     ::= { starentTraps 1262 }

starHENBGWMMESCTPAssocDestAddrUp  NOTIFICATION-TYPE
     OBJECTS { starHENBGWServiceVpnName, starHENBGWServiceServName, starHENBGWServiceLogicalENBId,   
               starHENBGWServiceMMEServName, starHENBGWServicePeerAddr, starHENBGWServicePeerPort }
     STATUS  current
     DESCRIPTION
         "A HENBGW MME SCTP Association Destination Address is up.
          This notification is only generated for   
          Association Destination Address which have previously been declared down." 
     --#SUMMARY "[HENBGW MME Association %s-%s-%s-%s] destination address:%s is up; Port %d"
     --#ARGUMENTS {0,1,2,3,4,5}
     --#STATE OPERATIONAL
     --#SEVERITY INFORMATIONAL
     ::= { starentTraps 1263 }

starMRMEServiceStart NOTIFICATION-TYPE 
     OBJECTS { starServiceVpnName, starServiceServName }
     STATUS  current
     DESCRIPTION
         "A Multi Radio Management (MRME) Service has started.

          Action to be Taken: No action required"
     --#SUMMARY "[Service MRME-%s-%s] MRME service has started"
     --#ARGUMENTS {0,1}
     --#STATE OPERATIONAL
     --#SEVERITY INFORMATIONAL
     ::= { starentTraps 1264 }

starMRMEServiceStop NOTIFICATION-TYPE
     OBJECTS { starServiceVpnName, starServiceServName }
     STATUS  current
     DESCRIPTION
         "A Multi Radio Management (MRME) Service has stopped.
 
          Probable Cause: This is typically caused by operator invention.  In
          unusual cases it can be caused by the loss of resources (PACs/PSCs) to
          support the running configuration.
 
          Action to be Taken: If the MRME service shutdown was not planned,
          examine the admin logs for an indication of the failure.  Verify that
          all configured PACs/PSCs are present and running in the system.  Check    \
the
          crash logs for an indication of a software failure.
 
          Clear Condition: Verify that the MRME service is operational.
 
          Condition Clear Alarm:  A starMRMEServiceStart notification will be       \
generated when
          the service is restarted"
     --#SUMMARY "[Service MRME-%s-%s] MRME service has stopped"
     --#ARGUMENTS {0,1}
     --#STATE DEGRADED
     --#SEVERITY MAJOR
     ::= { starentTraps 1265 }

starSLSServiceStart NOTIFICATION-TYPE
    OBJECTS { starServiceVpnName, starServiceServName }
    STATUS  current
    DESCRIPTION
        "An SLS Service has started

         Action to be Taken: No action required"
    --#SUMMARY "[Service SLS-%s-%s] SLS service has started"
    --#ARGUMENTS {0,1}
    --#STATE OPERATIONAL
    --#SEVERITY INFORMATIONAL
    ::= { starentTraps 1266 }

starSLSServiceStop NOTIFICATION-TYPE
    OBJECTS { starServiceVpnName, starServiceServName }
    STATUS  current
    DESCRIPTION
        "An SLS Service has stopped.

	 Probable Cause: This is typically caused by operator invention.  In
	 unusual cases it can be caused by the loss of resources (PACs/PSCs) to
	 support the running configuration.

	 Action to be Taken: If the SLS service shutdown was not planned,
	 examine the admin logs for an indication of the failure.  Verify that
	 all configured PACs/PSCs are present and running in the system.  Check the
	 crash logs for an indication of a software failure.

	 Clear Condition: Verify that the SLS service is operational.

	 Condition Clear Alarm: A starSLSServiceStart notification will be generated when
			        the service is restarted"
    --#SUMMARY "[Service SLS-%s-%s] SLS service has stopped"
    --#ARGUMENTS {0,1}
    --#STATE DEGRADED
    --#SEVERITY MAJOR
    ::= { starentTraps 1267 }

starESMLCAssocDown NOTIFICATION-TYPE
    OBJECTS { starSLSServiceVpnName, starSLSServiceServName, starESMLCId,  starESMLCIpAddr1,
              starESMLCIpAddr2, starESMLCPortNum }
    STATUS  current
    DESCRIPTION
        "An ESMLC Association is down.

         Problem Cause: The ESMLC Association has failed, or a network connectivity prevents reaching the ESMLC.  
         
         Condition Clear Alarm:  A starESMLCAssocUp notification will be generated when the ESMLC association is up"
    --#SUMMARY "[ ESMLC Association %s-%s-%d] is down; End point Addr1: %s Addr2: %s Port: %d"
    --#ARGUMENTS {0,1,2,3,4,5}
    --#STATE DEGRADED
    --#SEVERITY MAJOR
    ::= { starentTraps 1268}

starESMLCAssocUp  NOTIFICATION-TYPE
    OBJECTS { starSLSServiceVpnName, starSLSServiceServName, starESMLCId,  starESMLCIpAddr1,
              starESMLCIpAddr2, starESMLCPortNum }
    STATUS  current
    DESCRIPTION
        "An ESMLC Association is up.  This notification is only generated for Association 
         which have previously been declared down."
    --#SUMMARY "[ ESMLC Association %s-%s-%d] is up; End pointAddr1: %s Addr2: %s Port %d"
    --#ARGUMENTS {0,1,2,3,4,5}
    --#STATE OPERATIONAL
    --#SEVERITY INFORMATIONAL
    ::= { starentTraps 1269}

starESMLCAllAssocDown NOTIFICATION-TYPE
    OBJECTS { starSLSServiceVpnName,  starSLSServiceServName }
    STATUS  current
    DESCRIPTION
        "All the ESMLC Associations are down.

         Problem Cause: All the ESMLC Associations has failed, or  network connectivity
         prevents reaching the ESMLCs.

         Condition Clear Alarm:  An starESMLCAllAssocUp notification will be generated when
         all the ESMLC associations are  up"
    --#SUMMARY "All ESMLC Associations are down %s-%s"
    --#ARGUMENTS {0,1}
    --#STATE DEGRADED
    --#SEVERITY MAJOR
    ::= { starentTraps 1270}

starESMLCAllAssocDownClear  NOTIFICATION-TYPE
    OBJECTS { starSLSServiceVpnName,  starSLSServiceServName }
    STATUS  current
    DESCRIPTION
        "At least one ESMLC associations is up.  This notification is only generated for all the Association which
         have previously been declared down."
    --#SUMMARY "All ESMLCs associations are up %s-%s"
    --#ARGUMENTS {0,1}
    --#STATE OPERATIONAL
    --#SEVERITY INFORMATIONAL
    ::= { starentTraps 1271 }

starSBCServiceStart NOTIFICATION-TYPE
    OBJECTS { starServiceVpnName, starServiceServName }
    STATUS  current
    DESCRIPTION
        "An SBc Service has started

         Action to be Taken: No action required"
    --#SUMMARY "[Service SBc-%s-%s] SBc service has started"
    --#ARGUMENTS {0,1}
    --#STATE OPERATIONAL
    --#SEVERITY INFORMATIONAL
    ::= { starentTraps 1272 }

starSBCServiceStop NOTIFICATION-TYPE
    OBJECTS { starServiceVpnName, starServiceServName }
    STATUS  current
    DESCRIPTION
        "An SBc Service has stopped.
         Probable Cause: This is typically caused by operator intervention, when a     
         critical parameter associated with sbc-service is changed/removed.  In
         unusual cases it can be caused by the loss of resources (PACs/PSCs) to
         support the running configuration.

         Action to be Taken: If the SBc service shutdown was not planned,
         examine the admin logs for any indication of the failure.  Verify that 
         all configured PACs/PSCs are present and running in the system. Check for  
         any sbc-service related configuration errors by running show configuration errors    
         section sbc-service. Note that sbc-service should be associated to an    
         mme-service to be operationally up. In case the associated mme-service is down,    
         sbc-service is also stopped. Also check the
         crash logs for any indication of a software failure."

    --#SUMMARY "[Service SBc-%s-%s] SBc service has stopped"
    --#ARGUMENTS {0,1}
    --#STATE DEGRADED
    --#SEVERITY MAJOR
    ::= { starentTraps 1273 }

starCBCAssocDown NOTIFICATION-TYPE
    OBJECTS { starSBCServiceVpnName, starSBCServiceServName, starPeerId, starPeerIpAddr, starPeerPortNum }
    STATUS  current
    DESCRIPTION
        "A CBC Association is down.
         Problem Cause: SCTP connection between MME and CBC has been brought down - could be for any of the 
         following reasons -
           i) network connectivity between MME and CBC is broken.
          ii) CBC has gracefully terminated the SCTP association with MME.
         iii) MME has gracefully terminated the SCTP association with CBC, typically due to   
              operation intervention that would have effected sbc-service.

         Action to be taken - In case the SCTP association between MME and CBC is abnormally  
         closed, check for network connectivity between MME and CBC.

         Condition Clear Alarm: In case the association termination was abnormal, A           
         starPeerAssocUp notification will be generated when the CBC association is up"

    --#SUMMARY "[ CBC Association %s-%d] is down; End point Addr: %s Port: %d"
    --#ARGUMENTS {0,1,2,3,4}
    --#STATE DEGRADED
    --#SEVERITY MAJOR
    ::= { starentTraps 1274}

starCBCAssocUp  NOTIFICATION-TYPE
    OBJECTS { starSBCServiceVpnName, starSBCServiceServName, starPeerId,  starPeerIpAddr, starPeerPortNum }
    STATUS  current
    DESCRIPTION
        "A CBC Association is up."
    --#SUMMARY "[ CBC Association %s-%d] is up; End point Addr: %s Port %d"
    --#ARGUMENTS {0,1,2,3,4}
    --#STATE OPERATIONAL
    --#SEVERITY INFORMATIONAL
    ::= { starentTraps 1275}

starCBCBufSizeExceeded  NOTIFICATION-TYPE
    OBJECTS { starSBCServiceVpnName, starSBCServiceServName, starPeerId,  starPeerIpAddr, starPeerPortNum }
    STATUS  current
    DESCRIPTION
        "A received CBC message exceeded our buffer size limit"
    --#SUMMARY "[ CBC Association %s-%d] message size exceeded"
    --#ARGUMENTS {0,1,2,3,4}
    --#STATE OPERATIONAL
    --#SEVERITY INFORMATIONAL
    ::= { starentTraps 1403}

starBFDSessUp NOTIFICATION-TYPE 
    OBJECTS { starContextName,
              starBfdSrcAddressType,
              starBfdSrcAddress,
              starBfdDstAddressType, 
              starBfdDstAddress, 
              starBfdLocalDisc, 
              starBfdRemDisc,
              starPhyPortId }
     STATUS  current
     DESCRIPTION
         "The BFD Session to the specified IP address is operational.   
          This may indicate the initial configuration of a new neighbor,
          the initial connectivity after a system restart, or the 
          restoration of connectivity after a starBFDSessDown event.
 
          Action to be Taken: No action required."
     --#SUMMARY "[System] BFD Session, vpn %s SrcAddr %s DstAddr %s, PhyPortId %d is operational"
     --#ARGUMENTS {0,2,4}
     --#STATE OPERATIONAL
     --#SEVERITY INFORMATIONAL
     ::= { starentTraps 1276 }

starBFDSessDown NOTIFICATION-TYPE 
    OBJECTS { starContextName,
              starBfdSrcAddressType,
              starBfdSrcAddress,
              starBfdDstAddressType, 
              starBfdDstAddress, 
              starBfdLocalDisc, 
              starBfdRemDisc,
              starBfdSessDiagCode,
              starPhyPortId }
     STATUS  current
     DESCRIPTION
         "The BFD Session to the specified IP address is no longer
          operational.
 
          Probable Cause: The BFD Session is not-operational;
          the network between the ASR5x00 and the BFD Neighbor is
          experiencing an outage; Look into the Diagnostic Code for
          further details.
         
          Action to be Taken:  Verify the BFD Session is operational;
          verify network connectivity to the BFD Neighbor.
          
          Clear Condition Alarm: A starBFDSessUp is generated when 
          connectivity is reestablished"

     --#SUMMARY "[System] BFD Session, vpn %s SrcAddr %s DstAddr %s, PhyPortId %d is not operational and Diagnostic Code is %d"
     --#ARGUMENTS {0,2,4,7}
     --#STATE DEGRADED
     --#SEVERITY MAJOR
     ::= { starentTraps 1277 }

starSRPSwitchoverOccured NOTIFICATION-TYPE
    OBJECTS { starContextName,
              starSRPIpAddress,
              starSRPSwitchReason }
    STATUS  current
    DESCRIPTION
        "An SRP (ICSR) Switchover Occurred.
         Chassis has transitioned from Active to Standby State or 
         Chassis has transitioned from Standby to PendingActive State.

         Action to be Taken: Verify Active and Standby Chassis States of ICSR pair."

    --#SUMMARY "[System] SRP Switchover Occurred, vpn %s SRP %s Switchover Reason: %d"
    --#ARGUMENTS {0,1,2}
    --#STATE OPERATIONAL
    --#SEVERITY INFORMATIONAL
    ::= { starentTraps 1278 }
    
starHENBGWMMEOverloadStart NOTIFICATION-TYPE
    OBJECTS {starHENBGWServiceVpnName, starHENBGWServiceServName,   
             starHENBGWServiceLogicalENBId, starHENBGWServiceMMEServName,
             starHENBGWServicePeerAddr, starHENBGWServicePeerPort,
             starHENBGWServiceTLRI}
   STATUS  current
   DESCRIPTION
       "A HENBGW MME Overload Start message received.
        Condition Clear Alarm:  A starHENBGWMMEOverloadStop notification will be generated
        when the HENBGW MME overload stop message received."
   --#SUMMARY "[HENBGW MME  %s-%s-%s-%s] received overload start message with traffic load reduction indication percentage %d. End pointAddr: %s Port %d"
   --#ARGUMENTS {0,1,2,3,6,4,5}
   --#STATE DEGRADED
   --#SEVERITY MAJOR
   ::= {starentTraps 1279}

starHENBGWMMEOverloadStop  NOTIFICATION-TYPE
    OBJECTS {starHENBGWServiceVpnName, starHENBGWServiceServName, 
             starHENBGWServiceLogicalENBId, starHENBGWServiceMMEServName,
             starHENBGWServicePeerAddr, starHENBGWServicePeerPort}
    STATUS  current
    DESCRIPTION
         "A HENBGW MME Overload Stop message received.  This notification is only generated for the
          MME which have previously been generated overload start message, optionally this notification
          can be generated for any overload stop message received from MME."
    --#SUMMARY "[HENBGW MME %s-%s-%s-%s] received overload stop message.  End pointAddr: %s Port %d"
    --#ARGUMENTS {0,1,2,3,4,5}
    --#STATE OPERATIONAL
    --#SEVERITY INFORMATIONAL
    ::= { starentTraps 1280 }

starNpudriverECCError  NOTIFICATION-TYPE
    OBJECTS { starSlotNum }
    STATUS current
    DESCRIPTION
        " A double bit ECC error occured.
        Action to be taken - RMA this card."
    --#SUMMARY "A double bit ECC error occured on slot %d"
    --#ARGUMENTS {0}
    --#STATE DEGRADED
    --#SEVERITY MAJOR
    ::= { starentTraps 1281 }

starGTPCRLFOverThreshold NOTIFICATION-TYPE
    OBJECTS {   starGTPCRLFSessMgrInst,
                starGTPCRLFVPNName,
                starGTPCRLFVPNId,
                starGTPCRLFContextName,
                starGTPCRLFCurrAppTPS }
    STATUS current
    DESCRIPTION
    " GTP RLF Status update - GTP RLF Over Threshold. "
    --#SUMMARY "GTP RLF Status update - GTP RLF Over Threshold - Sessmgr Instance: %d Context: %s Context ID: %d RLF template name: %s Current Applied TPS: %d"
    --#ARGUMENTS {0,1,2,3,4}
    --#STATE DEGRADED
    --#SEVERITY MAJOR
    ::= { starentTraps 1282 }

starGTPCRLFOverLimit NOTIFICATION-TYPE
    OBJECTS {   starGTPCRLFSessMgrInst,
                starGTPCRLFVPNName,
                starGTPCRLFVPNId,
                starGTPCRLFContextName,
                starGTPCRLFCurrAppDelayTol }
    STATUS current
    DESCRIPTION
      " GTP RLF Status update - GTP RLF Over Limit."
      --#SUMMARY "GTP RLF Status update - GTP RLF Over Limit - Sessmgr Instance: %d Context: %s Context ID: %d RLF template name: %s Current Applied Delay Tolerance: %d"
      --#ARGUMENTS {0,1,2,3,4}
      --#STATE DEGRADED
      --#SEVERITY MAJOR
      ::= { starentTraps 1283 }

starGTPCRLFOverThresholdClear NOTIFICATION-TYPE
    OBJECTS {   starGTPCRLFSessMgrInst,
                starGTPCRLFVPNName,
                starGTPCRLFVPNId,
                starGTPCRLFContextName }
    STATUS current
    DESCRIPTION
    " GTP RLF Status update - GTP RLF Over Threshold Cleared."
    --#SUMMARY "GTP RLF Status update - GTP RLF Over Threshold Cleared - Sessmgr Instance: %d Context: %s Context ID: %d RLF template name: %s"
    --#ARGUMENTS {0,1,2,3}
    --#STATE DEGRADED
    --#SEVERITY MAJOR
    ::= { starentTraps 1284 }

starGTPCRLFOverLimitClear NOTIFICATION-TYPE
    OBJECTS {   starGTPCRLFSessMgrInst,
                starGTPCRLFVPNName,
                starGTPCRLFVPNId,
                starGTPCRLFContextName }
    STATUS current
    DESCRIPTION
      " GTP RLF Status update - GTP RLF Over Limit Cleared."
      --#SUMMARY "GTP RLF Status update - GTP RLF Over Limit Cleared - Sessmgr Instance: %d Context: %s Context ID: %d RLF template name: %s"
      --#ARGUMENTS {0,1,2,3}
      --#STATE DEGRADED
      --#SEVERITY MAJOR
      ::= { starentTraps 1285 }

starS102ServiceStart NOTIFICATION-TYPE
    OBJECTS { starServiceVpnName, starServiceServName }
    STATUS  current
    DESCRIPTION
        "An S102 Service has started

         Action to be Taken: No action required"
    --#SUMMARY "[Service S102-%s-%s] CSCF service has started"
    --#ARGUMENTS {0,1}
    --#STATE OPERATIONAL
    --#SEVERITY INFORMATIONAL
    ::= { starentTraps 1286 }

starS102ServiceStop NOTIFICATION-TYPE
    OBJECTS { starServiceVpnName, starServiceServName }
    STATUS  current
    DESCRIPTION
        "An S102 Service has stopped

         Probable Cause: This is typically caused by operator invention.  In
         unusual cases it can be caused by the loss of resources (PACs/PSCs) to
         support the running configuration.

         Action to be Taken: If the S102 service shutdown was not planned,
         examine the admin logs for an indication of the failure.  Verify that
         all configured PACs/PSCs are present and running in the system.  Check the
         crash logs for an indication of a software failure.

         Clear Condition: Verify that the S102 service is operational.

         Condition Clear Alarm:  A starS102ServiceStart notification will be generated when
         the service is restarted"
    --#SUMMARY "[S102 %s-%s] S102 service has stopped"
    --#ARGUMENTS {0,1}
    --#STATE DEGRADED
    --#SEVERITY MAJOR
    ::= { starentTraps 1287 }

starBGPPeerSessionIPv6Up NOTIFICATION-TYPE
    OBJECTS { starContextName, starBGPPeerIpv6Address }
    STATUS  current
    DESCRIPTION
        "The BGP peer session to the specified IP v6 address is operational.
         This may indicate the initial configuration of a new peer, the initial
         connectivity after a system restart, or the restoration of connectivity
         after a starBGNPeerSessionDown event.

         Action to be Taken: No action required."
    --#SUMMARY "[System] BGP peer session, vpn %s, address %s, is operational"
    --#ARGUMENTS {0,1}
    --#STATE OPERATIONAL
    --#SEVERITY INFORMATIONAL
    ::= { starentTraps 1288 }

starBGPPeerSessionIPv6Down NOTIFICATION-TYPE
    OBJECTS { starContextName, starBGPPeerIpv6Address }
    STATUS  current
    DESCRIPTION
        "The BGP peer session to the specified IP v6 address is no longer operational.

         Probable Cause: The BGP peer is not-operational; the network between the
         ST16 and the BGP peer is experiencing an outage; LC failure(s) on the ST16.

         Action to be Taken:  Verify the BGP peer is operational; verify network
         connectivity to the BGP peer.

         Clear Condition Alarm: A starBGPPeerSessionUp is generated when connectivity is reestablished"
    --#SUMMARY "[System] BGP peer session, vpn %s, address %s, is non-operational"
    --#ARGUMENTS {0,1}
    --#STATE DEGRADED
    --#SEVERITY MAJOR
    ::= { starentTraps 1289 }

starMMEEMBMSServiceStart NOTIFICATION-TYPE
    OBJECTS { starServiceVpnName, starServiceServName }
    STATUS  current
    DESCRIPTION
        "An MME-EMBM Service has started

         Action to be Taken: No action required"
    --#SUMMARY "[Service MME-EMBMS-%s-%s] MME-EMBMS service has started"
    --#ARGUMENTS {0,1}
    --#STATE OPERATIONAL
    --#SEVERITY INFORMATIONAL
    ::= { starentTraps 1290 }

starMMEEMBMSServiceStop NOTIFICATION-TYPE
    OBJECTS { starServiceVpnName, starServiceServName }
    STATUS  current
    DESCRIPTION
        "An MME-EMBMS Service has stopped.
         Probable Cause: This is typically caused by operator intervention, when a
         critical parameter associated with mme-embms-service is changed/removed. In
         unusual cases it can be caused by the loss of resources (PACs/PSCs) to
         support the running configuration.

         Action to be Taken: If the MME-EMBMS service shutdown was not planned,
         examine the admin logs for any indication of the failure.  Verify that
         all configured PACs/PSCs are present and running in the system. Check for
         any mme-embms-service related configuration errors by running show configuration errors
         section mme-embms-service. Also check the crash logs for any indication of a software failure."

    --#SUMMARY "[Service MME-EMBMS-%s-%s] MME-EMBMS service has stopped"
    --#ARGUMENTS {0,1}
    --#STATE DEGRADED
    --#SEVERITY MAJOR
    ::= { starentTraps 1291 }

starMCEAssocDown NOTIFICATION-TYPE
    OBJECTS { starMMEEMBMSServiceVpnName, starMMEEMBMSServiceServName , starMMEEMBMSPeerId, starMMEEMBMSPeerIpAddr, starMMEEMBMSPeerPortNum }
    STATUS  current
    DESCRIPTION
        "An MCE Association is down.
         Problem Cause: SCTP connection between MME and MCE has been brought down - could be for any of the
         following reasons -
           i) network connectivity between MME and MCE is broken.
          ii) MCE has gracefully terminated the SCTP association with MME.
         iii) MME has gracefully terminated the SCTP association with MCE, typically due to
              operation intervention that would have effected mme-embms-service.

         Action to be taken - In case the SCTP association between MME and MCE is abnormally
         closed, check for network connectivity between MME and MCE.

         Condition Clear Alarm: In case the association termination was abnormal, A
         starPeerAssocUp notification will be generated when the MCE association is up"

    --#SUMMARY "[ MCE Association %s-%d] is down; End point Addr: %s Port: %d"
    --#ARGUMENTS {0,1,2,3,4}
    --#STATE DEGRADED
    --#SEVERITY MAJOR
    ::= { starentTraps 1292}

starMCEAssocUp  NOTIFICATION-TYPE
    OBJECTS {starMMEEMBMSServiceVpnName, starMMEEMBMSServiceServName , starMMEEMBMSPeerId,  starMMEEMBMSPeerIpAddr, starMMEEMBMSPeerPortNum }
    STATUS  current
    DESCRIPTION
        "A MCE Association is up."
    --#SUMMARY "[ MCE Association %s-%d] is up; End point Addr: %s Port %d"
    --#ARGUMENTS {0,1,2,3,4}
    --#STATE OPERATIONAL
    --#SEVERITY INFORMATIONAL
    ::= { starentTraps 1293}


starIuBcTcpConnDown NOTIFICATION-TYPE
    OBJECTS { starCBSServiceVpnName, starIuBcSelfIpAddr, starIuBcSelfPortNum , starIuBcPeerIpAddr, starIuBcPeerPortNum,  starIuBcTcpConnCauseStr}
    STATUS  current
    DESCRIPTION
        "A TCP connection at IuBc interface is down.
         Problem Cause: TCP connection between HNBGW and CBC server has been brought down - could be for any of the 
         following reasons -
           i) network connectivity between HNBGW and CBC server is broken.
          ii) CBC Server has gracefully terminated the TCP connection with HNBGW.
         iii) HNBGW has gracefully terminated the TCP connection with CBC server, typically due to   
              operation intervention that would have effected cbs-service.

         Action to be taken - In case the TCP connection between HNBGW and CBC server is abnormally  
         closed, check for network connectivity between HNBGW and CBC server.

         Condition Clear Alarm: In case the connection termination was abnormal, A           
         IuBcTCPConnUp notification will be generated when the TCP connection is up"

    --#SUMMARY "[ TCP Connection %s-%s-%d] is down; Peer IP Addr: %s Port: %d with cause %s"
    --#ARGUMENTS {0,1,2,3,4,5}
    --#STATE DEGRADED
    --#SEVERITY MAJOR
    ::= { starentTraps 1294} 


starIuBcTcpConnUp NOTIFICATION-TYPE
    OBJECTS { starCBSServiceVpnName, starIuBcSelfIpAddr, starIuBcSelfPortNum , starIuBcPeerIpAddr, starIuBcPeerPortNum,  starIuBcTcpConnCauseStr}
    STATUS  current
    DESCRIPTION
        "A TCP Connection is up."
    --#SUMMARY "[ TCP Connection %s-%s-%d] is up; Peer IP Addr: %s Port: %d with cause %s"
    --#ARGUMENTS {0,1,2,3,4,5}
    --#STATE OPERATIONAL
    --#SEVERITY INFORMATIONAL
    ::= { starentTraps 1295 }

starSessCapReached NOTIFICATION-TYPE
    OBJECTS { starTaskInstance, starTaskCard, starTaskCPU }
    STATUS  current
    DESCRIPTION
        "Session manager will start rejecting new calls as the capacity reached."
    --#SUMMARY "Session manager instance %d card %d cpu %d"
    --#ARGUMENTS {0,1,2}
    --#STATE OPERATIONAL
    --#SEVERITY CRITICAL
    ::= { starentTraps 1298 }

starSerdesLanePermDown NOTIFICATION-TYPE
    OBJECTS { starSlotNum, starDeviceNum, starSerdesNum }
    STATUS  current
    DESCRIPTION
        "A serdes lanes is a high speed serial link between a FAP(chip on an MIO/DPC/DPC2/MIO2) 
        and an FE(chip on an FSC card). When a serdes lane has errors, we calibrate it to get 
        optimized Rx parameters. If we attempt to calibrate a lane more than 5 times, it is 
        taken offline. By taking it offline we no longer use it so we are eliminating 
        potential traffic loss.."
    --#SUMMARY "SERDES lane is Down on local: slot %d device %d serdes lane index %d, Remote: slot %d device %d serdes lane index %d"
    --#ARGUMENTS {0,1,2}
    --#STATE OPERATIONAL
    --#SEVERITY INFORMATIONAL
    ::= { starentTraps 1303 }



starLAGGroupDownDueToMinlink NOTIFICATION-TYPE
    OBJECTS { starPortSlot, starPortNum, starLAGGroup, starLAGMinlink }
    STATUS  current
    DESCRIPTION
    "LAG group status is Down due to links in LAG group falls below minlink . This notification is only generated 
    for master physical port and  a previous 'starLAGGroupUp' notification was previously generated.

     Action to be Taken: No action required. The cause for the LAG down should be investigated."
    --#SUMMARY "[Port] LAG group (%d) status is down due to minlink: Slot %d Port %d minlink %d"
    --#ARGUMENTS {3,0,1,4}
    --#STATE DEGRADED
    --#SEVERITY MAJOR
    ::= { starentTraps 1299 }

starNicBondChange NOTIFICATION-TYPE
    OBJECTS { starPortSlot, starPortNum }
    STATUS  current
    DESCRIPTION
   "Nic Bond change will happen whenever there is change in the leaf node connected to our ports in QvPC-DI.
    This notification is generated to inform that there is a change in the vNIC (mac-address).

     Action to be Taken: No action required. The cause for the leaf node down should be investigated."
    --#SUMMARY "Nic Bond changed: Slot %d Port %d Mac changed from %s to %s"
    --#ARGUMENTS {3,10, "02:23:4A:32:DA:32", "54:22:1B:8C:4D:1F"}
    --#STATE OPERATIONAL
    --#SEVERITY INFORMATIONAL
    ::= { starentTraps 1376 }

starThreshAllFramedRoutes NOTIFICATION-TYPE
    OBJECTS { starContextName, starVRFName, starThreshInt, starThreshMeasuredInt }
    STATUS  current
    DESCRIPTION
        "All framed routes crosses user defined threshold."
    --#SUMMARY "facility vpnmgr context %s vrfname %s framed routes threshold %d%% measured %d%%"
    --#ARGUMENTS {0,1,2,3}
    --#STATE OPERATIONAL
    --#SEVERITY INFORMATIONAL
    ::= { starentTraps 1304 }

starThreshAllFramedRoutesClear NOTIFICATION-TYPE
    OBJECTS { starContextName, starVRFName, starThreshInt, starThreshMeasuredInt }
    STATUS  current
    DESCRIPTION
        "All framed routes crosses user defined threshold cleared."
    --#SUMMARY "facility vpnmgr context %s vrfname %s framed routes threshold %d%% measured %d%%"
    --#ARGUMENTS {0,1,2,3}
    --#STATE OPERATIONAL
    --#SEVERITY INFORMATIONAL
    ::= { starentTraps 1305 }

starThreshAllTotalRoutes NOTIFICATION-TYPE
    OBJECTS { starContextName, starVRFName, starThreshInt, starThreshMeasuredInt }
    STATUS  current
    DESCRIPTION
        "All total routes crosses user defined threshold."
    --#SUMMARY "facility vpnmgr context %s vrfname %s total routes threshold %d measured %d"
    --#ARGUMENTS {0,1,2,3}
    --#STATE OPERATIONAL
    --#SEVERITY INFORMATIONAL
    ::= { starentTraps 1306 }

starThreshAllTotalRoutesClear NOTIFICATION-TYPE
    OBJECTS { starContextName, starVRFName, starThreshInt, starThreshMeasuredInt }
    STATUS  current
    DESCRIPTION
        "All total routes crosses user defined threshold cleared."
    --#SUMMARY "facility vpnmgr context %s vrfname %s total routes threshold %d measured %d"
    --#ARGUMENTS {0,1,2,3}
    --#STATE OPERATIONAL
    --#SEVERITY INFORMATIONAL
    ::= { starentTraps 1307 }

starThreshVRFFramedRoutes NOTIFICATION-TYPE
    OBJECTS { starContextName, starVRFName, starThreshInt, starThreshMeasuredInt }
    STATUS  current
    DESCRIPTION
        "Total number of VRF framed routes crosses user defined threshold."
    --#SUMMARY "facility vpnmgr context %s vrfname %s framed routes threshold %d%% measured %d%%"
    --#ARGUMENTS {0,1,2,3}
    --#STATE OPERATIONAL
    --#SEVERITY INFORMATIONAL
    ::= { starentTraps 1308 }

starThreshVRFFramedRoutesClear NOTIFICATION-TYPE
    OBJECTS { starContextName, starVRFName, starThreshInt, starThreshMeasuredInt }
    STATUS  current
    DESCRIPTION
        "Total number of VRF framed routes crosses user defined threshold cleared."
    --#SUMMARY "facility vpnmgr context %s vrfname %s framed routes threshold %d%% measured %d%%"
    --#ARGUMENTS {0,1,2}
    --#STATE OPERATIONAL
    --#SEVERITY INFORMATIONAL
    ::= { starentTraps 1309 }

starThreshVRFTotalRoutes NOTIFICATION-TYPE
    OBJECTS { starContextName, starVRFName, starThreshInt, starThreshMeasuredInt }
    STATUS  current
    DESCRIPTION
        "Total number of VRF total routes crosses user defined threshold."
    --#SUMMARY "facility vpnmgr context %s vrfname %s total routes threshold %d measured %d"
    --#ARGUMENTS {0,1,2,3}
    --#STATE OPERATIONAL
    --#SEVERITY INFORMATIONAL
    ::= { starentTraps 1310 }

starThreshVRFTotalRoutesClear NOTIFICATION-TYPE
    OBJECTS { starContextName, starVRFName, starThreshInt, starThreshMeasuredInt }
    STATUS  current
    DESCRIPTION
        "Total number of VRF total routes crosses user defined threshold cleared."
    --#SUMMARY "facility vpnmgr context %s vrfname %s total routes threshold %d measured %d"
    --#ARGUMENTS {0,1,2,3}
    --#STATE OPERATIONAL
    --#SEVERITY INFORMATIONAL
    ::= { starentTraps 1311 }

starStatFilesizeExceeded NOTIFICATION-TYPE
    OBJECTS { starStatFilesizeLimit, starStatFilesizeMeasured}
    STATUS  current
    DESCRIPTION
        "Actual Bulkstat filesize crosses 80% user defined Bulkstat filesize."
    --#SUMMARY "Filesize exeeceded for facility bulkstat: filesize limit  %d filesize measured %d"
    --#ARGUMENTS {0,1}
    --#STATE OPERATIONAL
    --#SEVERITY INFORMATIONAL
    ::= { starentTraps 1312 }

starStatFilesizeClear NOTIFICATION-TYPE
    OBJECTS { starStatFilesizeLimit, starStatFilesizeMeasured}
    STATUS  current
    DESCRIPTION
        "Actual Bulkstat filesize crosses 80% user defined Bulkstat filesize condition cleared."
    --#SUMMARY "Filesize condition for facility bulkstat cleared: filesize limit  %d filesize measured %d"
    --#ARGUMENTS {0,1}
    --#STATE OPERATIONAL
    --#SEVERITY INFORMATIONAL
    ::= { starentTraps 1313 }

starThreshLMASetupBindingUpdateDenyRate NOTIFICATION-TYPE
    OBJECTS { starThreshPct, starThreshMeasuredPct }
    STATUS current
    DESCRIPTION
	"The percentage of LMA setup binding update deny rate which failed has exceeded the configured threshold
	 during the current monitoring period.

         Probable Cause: This is a user configurable threshold.

         If the thresholding subsystem is configured to run in an 'alarm' model,
         a starThreshClearLMASetupBindingUpdateDenyRate notification will be generated when the measured
	 value falls below the threshold."
    --#SUMMARY "[System] Threshold: LMA setup binding update deny rate threshold for threshold %d%% measured %d%%"
    --#ARGUMENTS {0,1}
    --#STATE OPERATIONAL
    --#SEVERITY WARNING
    ::= { starentTraps 1314 }

starThreshClearLMASetupBindingUpdateDenyRate NOTIFICATION-TYPE
    OBJECTS { starThreshPct, starThreshMeasuredPct }
    STATUS current
    DESCRIPTION
	"The threshold condition is now clear."
    --#SUMMARY "[System] Threshold: LMA setup binding update deny rate threshold clear for threshold %d%% measured %d%%"
    --#ARGUMENTS {0,1}
    --#STATE OPERATIONAL
    --#SEVERITY INFORMATIONAL
    ::= { starentTraps 1315 }

starThreshMAGSetupBindingUpdateDenyRate NOTIFICATION-TYPE
    OBJECTS { starThreshPct, starThreshMeasuredPct }
    STATUS current
    DESCRIPTION
	"The percentage of MAG setup binding update deny rate which failed has exceeded the configured threshold
	 during the current monitoring period.

         Probable Cause: This is a user configurable threshold.

         If the thresholding subsystem is configured to run in an 'alarm' model,
         a starThreshClearMAGSetupBindingUpdateDenyRate notification will be generated when the measured
	 value falls below the threshold."
    --#SUMMARY "[System] Threshold: MAG setup binding update deny rate threshold for threshold %d%% measured %d%%"
    --#ARGUMENTS {0,1}
    --#STATE OPERATIONAL
    --#SEVERITY WARNING
    ::= { starentTraps 1316 }

starThreshClearMAGSetupBindingUpdateDenyRate NOTIFICATION-TYPE
    OBJECTS { starThreshPct, starThreshMeasuredPct }
    STATUS current
    DESCRIPTION
	"The threshold condition is now clear."
    --#SUMMARY "[System] Threshold: MAG setup binding update deny rate threshold clear for threshold %d%% measured %d%%"
    --#ARGUMENTS {0,1}
    --#STATE OPERATIONAL
    --#SEVERITY INFORMATIONAL
    ::= { starentTraps 1317 }

starThreshEGTPCS2BSetupFailRate NOTIFICATION-TYPE
    OBJECTS { starThreshPct, starThreshMeasuredPct }
    STATUS current
    DESCRIPTION
	"The percentage of EGTPC S2B setup fail rate which failed has exceeded the configured threshold
	 during the current monitoring period.

         Probable Cause: This is a user configurable threshold.

         If the thresholding subsystem is configured to run in an 'alarm' model,
         a starThreshClearEGTPC S2B SetupFailRate notification will be generated when the measured
	 value falls below the threshold."
    --#SUMMARY "[System] Threshold: EPDG setup fail rate threshold for threshold %d%% measured %d%%"
    --#ARGUMENTS {0,1}
    --#STATE OPERATIONAL
    --#SEVERITY WARNING
    ::= { starentTraps 1318 }

starThreshClearEGTPCS2BSetupFailRate NOTIFICATION-TYPE
    OBJECTS { starThreshPct, starThreshMeasuredPct }
    STATUS current
    DESCRIPTION
	"The threshold condition is now clear."
    --#SUMMARY "[System] Threshold: EGTPC S2B setup fail rate threshold clear for threshold %d%% measured %d%%"
    --#ARGUMENTS {0,1}
    --#STATE OPERATIONAL
    --#SEVERITY INFORMATIONAL
    ::= { starentTraps 1319 }

starThreshSNXDisconnectReason NOTIFICATION-TYPE
    OBJECTS { starDiscReasons, starThreshInt, starThreshMeasuredInt }
    STATUS current
    DESCRIPTION
         "The threshold when exceeded the configured values for a given disconnect-reason, trap will be raised."
    --#SUMMARY "[System] Threshold: Session Manager disconnect-reason %s threshold %d%% measured %d%%"
    --#ARGUMENTS {0,1,2}
    --#STATE OPERATIONAL
    --#SEVERITY INFORMATIONAL
    ::= { starentTraps 1320 }

starThreshClearSNXDisconnectReason NOTIFICATION-TYPE
    OBJECTS { starDiscReasons, starThreshInt, starThreshMeasuredInt }
    STATUS current
    DESCRIPTION
        "The threshold condition is now clear."
    --#SUMMARY "[System] Threshold: Session Manager threshold clear for disconnect-reason %s threshold %d%% me    asured %d%%"
    --#ARGUMENTS {0,1,2}
    --#STATE OPERATIONAL
    --#SEVERITY INFORMATIONAL
    ::= { starentTraps 1321 }


starTetheringTACDatabaseUpgradeFailureStatus NOTIFICATION-TYPE
    OBJECTS { starTetheringDatabasePreDBVersion, starTetheringDatabaseUpgradeDBVersion, starTetheringDatabaseUpgradeComment }
    STATUS  current
    DESCRIPTION
        "Tethering TAC Database Upgrade Failure Status. 
         Condition Clear Alarm: This condition is cleared by starTetheringTACDatabaseUpgradeSuccessStatus  notification."
    --#SUMMARY "Pre-DB Version %s Upgrade Version %s, Comment: %s"
    --#ARGUMENTS {0,1,2}
    --#STATE OPERATIONAL
    --#SEVERITY MAJOR
    ::= { starentTraps 1322 }

starTetheringTACDatabaseUpgradeSuccessStatus NOTIFICATION-TYPE
    OBJECTS { starTetheringDatabasePreDBVersion, starTetheringDatabaseUpgradeDBVersion, starTetheringDatabaseUpgradeComment }
    STATUS  current
    DESCRIPTION
        "Tethering TAC Database Upgrade Failure Success. 
         Action to be taken: No action required "
    --#SUMMARY "Pre-DB Version %s Upgrade Version %s, Comment: %s"
    --#ARGUMENTS {0,1,2}
    --#STATE OPERATIONAL
    --#SEVERITY INFORMATIONAL
    ::= { starentTraps 1323 }

starTetheringOSDatabaseUpgradeFailureStatus NOTIFICATION-TYPE
    OBJECTS { starTetheringDatabasePreDBVersion, starTetheringDatabaseUpgradeDBVersion, starTetheringDatabaseUpgradeComment }
    STATUS  current
    DESCRIPTION
        "Tethering OS Database Upgrade Failure Status.          
         Condition Clear Alarm: This condition is cleared by starTetheringOSDatabaseUpgradeSuccessStatus  notification."
    --#SUMMARY "Pre-DB Version %s Upgrade Version %s, Comment: %s"
    --#ARGUMENTS {0,1,2}
    --#STATE OPERATIONAL
    --#SEVERITY MAJOR
    ::= { starentTraps 1324 }

starTetheringOSDatabaseUpgradeSuccessStatus NOTIFICATION-TYPE
    OBJECTS { starTetheringDatabasePreDBVersion, starTetheringDatabaseUpgradeDBVersion, starTetheringDatabaseUpgradeComment }
    STATUS  current
    DESCRIPTION
        "Tethering OS Database Upgrade Failure Success.
         Action to be taken: No action required "
    --#SUMMARY "Pre-DB Version %s Upgrade Version %s, Comment: %s"
    --#ARGUMENTS {0,1,2}
    --#STATE OPERATIONAL
    --#SEVERITY INFORMATIONAL
    ::= { starentTraps 1325 }

starTetheringV6OSDatabaseUpgradeFailureStatus NOTIFICATION-TYPE
    OBJECTS { starTetheringDatabasePreDBVersion, starTetheringDatabaseUpgradeDBVersion, starTetheringDatabaseUpgradeComment }    
    STATUS  current
    DESCRIPTION
        "Tethering V6OS Database Upgrade Failure Status.                   
	 Condition Clear Alarm: This condition is cleared by starTetheringV6OSDatabaseUpgradeSuccessStatus  notification."
    --#SUMMARY "Pre-DB Version %s Upgrade Version %s, Comment: %s"
    --#ARGUMENTS {0,1,2}
    --#STATE OPERATIONAL
    --#SEVERITY MAJOR
    ::= { starentTraps 1326 }

starTetheringV6OSDatabaseUpgradeSuccessStatus NOTIFICATION-TYPE
    OBJECTS { starTetheringDatabasePreDBVersion, starTetheringDatabaseUpgradeDBVersion, starTetheringDatabaseUpgradeComment }
    STATUS  current
    DESCRIPTION
        "Tethering V6OS Database Upgrade Failure Success.
         Action to be taken: No action required "
    --#SUMMARY "Pre-DB Version %s Upgrade Version %s, Comment: %s"
    --#ARGUMENTS {0,1,2}
    --#STATE OPERATIONAL
    --#SEVERITY INFORMATIONAL
    ::= { starentTraps 1327 }

starTetheringUADatabaseUpgradeFailureStatus NOTIFICATION-TYPE
    OBJECTS { starTetheringDatabasePreDBVersion, starTetheringDatabaseUpgradeDBVersion, starTetheringDatabaseUpgradeComment }    
    STATUS  current
    DESCRIPTION
        "Tethering V6OS Database Upgrade Failure Status.                            
	 Condition Clear Alarm: This condition is cleared by starTetheringUADatabaseUpgradeSuccessStatus  notification."
    --#SUMMARY "Pre-DB Version %s Upgrade Version %s, Comment: %s"
    --#ARGUMENTS {0,1,2}
    --#STATE OPERATIONAL
    --#SEVERITY MAJOR
    ::= { starentTraps 1328 }

starTetheringUADatabaseUpgradeSuccessStatus NOTIFICATION-TYPE
    OBJECTS { starTetheringDatabasePreDBVersion, starTetheringDatabaseUpgradeDBVersion, starTetheringDatabaseUpgradeComment }
    STATUS  current
    DESCRIPTION
        "Tethering UA Database Upgrade Failure Success.
         Action to be taken: No action required "
    --#SUMMARY "Pre-DB Version %s Upgrade Version %s, Comment: %s"
    --#ARGUMENTS {0,1,2}
    --#STATE OPERATIONAL
    --#SEVERITY INFORMATIONAL
    ::= { starentTraps 1329 }

starThreshEGTPCS5SetupFailRate NOTIFICATION-TYPE
    OBJECTS { starThreshPct, starThreshMeasuredPct }
    STATUS current
    DESCRIPTION
        "The percentage of EGTPC S5 setup fail rate which failed has exceeded the configured threshold
         during the current monitoring period.

         Probable Cause: This is a user configurable threshold.

         If the thresholding subsystem is configured to run in an 'alarm' model,
         a starThreshClearEGTPCS5SetupFailRate notification will be generated when the measured
         value falls below the threshold."
    --#SUMMARY "[System] Threshold: EGTPC S5 setup failure rate threshold for threshold %d%% measured %d%%"
    --#ARGUMENTS {0,1}
    --#STATE OPERATIONAL
    --#SEVERITY WARNING
    ::= { starentTraps 1330 }

starThreshClearEGTPCS5SetupFailRate NOTIFICATION-TYPE
    OBJECTS { starThreshPct, starThreshMeasuredPct }
    STATUS current
    DESCRIPTION
        "The threshold condition is now clear."
    --#SUMMARY "[System] Threshold: EGTPC S5 setup failure rate threshold clear for threshold %d%% measured %d%%"
    --#ARGUMENTS {0,1}
    --#STATE OPERATIONAL
    --#SEVERITY INFORMATIONAL
    ::= { starentTraps 1331 }


starDdfReload  NOTIFICATION-TYPE
    OBJECTS { starSlotNum, starDdfDev }
    STATUS current
    DESCRIPTION
      " DDF MCDMA Engine Reloaded due to CRC Error. This is not applicable to QVPC-SI and QVPC-DI."
    --#SUMMARY "A DDF reload occured on slot %d"
    --#ARGUMENTS {0,1}
    --#STATE OPERATIONAL
    --#SEVERITY MAJOR
    ::= { starentTraps 1332 }

starHdRaidMgmtCardSwitchover  NOTIFICATION-TYPE
    OBJECTS { starSlotNum, starHdRaidMgmtCardSwitchoverCause }
    STATUS current
    DESCRIPTION
      " Management Card Switchover due to unrecoverable HDRaid error."
    --#SUMMARY "Management Card switchover happened from slot %d due to unrecoverable HDRaid error %s."
    --#ARGUMENTS {0, 1}
    --#STATE OPERATIONAL
    --#SEVERITY MAJOR
    ::= { starentTraps 1333 }

starThreshLSLogsVolume NOTIFICATION-TYPE
    OBJECTS { starTaskFacilityName, starTaskInstance, starThreshInt, starThreshMeasuredInt }
    STATUS current
    DESCRIPTION
         "When any facility and instance generate event-logs more than the configured amount of threshold for a configured amount of time, will trigger a trap."
    --#SUMMARY "[System] Threshold: facility %s instance %d is generating overwhelming logs, threshold %d%% measured %d%%"
    --#ARGUMENTS {0,1,2,3}
    --#STATE OPERATIONAL
    --#SEVERITY INFORMATIONAL
    ::= { starentTraps 1334 }

starThreshClearLSLogsVolume NOTIFICATION-TYPE
    OBJECTS { starTaskFacilityName, starTaskInstance, starThreshInt, starThreshMeasuredInt }
    STATUS current
    DESCRIPTION
         "When any facility and instance generate event-logs less than the clear threshold, will trigger clear trap."
    --#SUMMARY "[System] Threshold: facility %s instance %d overwheming logs threshold clear for threshold %d%% measured %d%%"
    --#ARGUMENTS {0,1,2,3}
    --#STATE OPERATIONAL
    --#SEVERITY INFORMATIONAL
    ::= { starentTraps 1335 }

starIKEv2DOSAttack NOTIFICATION-TYPE
    OBJECTS { starTaskInstance }
    STATUS current
    DESCRIPTION
         "Alarm will be triggered when a ipsecmgr facility is under DDOS attack."
    --#SUMMARY "[IPSEC] : ipsecmgr facility instance %d is under DDOS attack"
    --#ARGUMENTS {0}
    --#STATE OPERATIONAL
    --#SEVERITY INFORMATIONAL
    ::= { starentTraps 1336 }

starIKEv2ClearDOSAttack NOTIFICATION-TYPE
    OBJECTS { starTaskInstance }
    STATUS current
    DESCRIPTION
         "Alarm will be triggered when a ipsecmgr facility is out of DDOS attack."
    --#SUMMARY "[IPSEC] : ipsecmgr facility instance %d is under DDOS attack"
    --#ARGUMENTS {0}
    --#STATE OPERATIONAL
    --#SEVERITY INFORMATIONAL
    ::= { starentTraps 1337 }

starIKEv2DecryptionFailThreshold NOTIFICATION-TYPE
    OBJECTS { starTaskInstance, starSessSub1NAI, starSessSub1IpAddr}
    STATUS current
    DESCRIPTION
         "Alarm will be triggered when decryption fail count for subsequent IKEV2 messages from a UE increases configured value ."
    --#SUMMARY "[IPSEC] : Decryption failcount exceeded for UE %s with NAI %s and IP addr %s on IPSec Mgr instance %d"
    --#ARGUMENTS {0,1,2, 3}
    --#STATE OPERATIONAL
    --#SEVERITY INFORMATIONAL
    ::= { starentTraps 1338 }

starIKEv2ClearDecryptionFailThreshold NOTIFICATION-TYPE
    OBJECTS { starTaskInstance, starSessSub1NAI, starSessSub1IpAddr}
    STATUS current
    DESCRIPTION
         "Alarm will be triggered when UE sends a valid IKEv2 packet , for which the decryption passes"
    --#SUMMARY "[IPSEC] : Decryption fail alarm cleared [Reason: %s ]for UE with NAI %s and IP addr %s on IPSec Mgr instance %d"
    --#ARGUMENTS {0 ,1, 2, 3}
    --#STATE OPERATIONAL
    --#SEVERITY INFORMATIONAL
    ::= { starentTraps 1339 }

starDiameterRlfThresholdOver NOTIFICATION-TYPE
  OBJECTS { starDiameterDiamproxyInstance, starDiameterVpnName, starDiameterRlfContext, starDiameterPeerName, starDiameterEndpointName, starDiameterRlfECode, starDiameterRlfTps, starDiameterRlfDelayTolerance, starDiameterRlfQueuePercent}
  STATUS  current
  DESCRIPTION
  "Diameter RLF hit upper threshold"
  --#SUMMARY "[Diamproxy %d] [VPN %s]  Diameter RLF context %s hit upper threshold for peer %s endpoint %s. Cause Code: %d TPS : %d, Delay Tolerance : %d"
  --#ARGUMENTS {0,1,2,3,4,5,6,7}
  --#STATE DEGRADED
  --#SEVERITY MAJOR
  ::= { starentTraps 1340 }

starDiameterRlfOverLimit NOTIFICATION-TYPE
  OBJECTS { starDiameterDiamproxyInstance, starDiameterVpnName, starDiameterRlfContext, starDiameterPeerName, starDiameterEndpointName, starDiameterRlfECode, starDiameterRlfTps, starDiameterRlfDelayTolerance, starDiameterRlfQueuePercent}
  STATUS  current
  DESCRIPTION
  "Diameter RLF queue full"
  --#SUMMARY "[Diamproxy %d] [VPN %s]  Diameter RLF context %s hit queue limit for peer %s endpoint %s. Cause Code: %d TPS : %d, Delay Tolerance : %d"
  --#ARGUMENTS {0,1,2,3,4,5,6,7}
  --#STATE DEGRADED
  --#SEVERITY MAJOR
  ::= { starentTraps 1341 }

starDiameterRlfThresholdGood NOTIFICATION-TYPE
  OBJECTS { starDiameterDiamproxyInstance, starDiameterVpnName, starDiameterRlfContext, starDiameterPeerName, starDiameterEndpointName, starDiameterRlfECode, starDiameterRlfTps, starDiameterRlfDelayTolerance, starDiameterRlfQueuePercent}
  STATUS  current
  DESCRIPTION
  "Diameter RLF under stable condition"
  --#SUMMARY "[Diamproxy %d] [VPN %s]  Diameter RLF context %s under stable condition for peer %s endpoint %s. Cause Code: %d TPS : %d, Delay Tolerance : %d"
  --#ARGUMENTS {0,1,2,3,4,5,6,7}
  --#STATE OPERATIONAL
  --#SEVERITY INFORMATIONAL
  ::= { starentTraps 1342 }

starThreshHatHb5MinsLoss NOTIFICATION-TYPE
    OBJECTS { starSlotNum, starSlotNum, starThreshPct, starThreshMeasuredPct }
    STATUS  current
    DESCRIPTION
        "Heartbeat loss for past 5 mins on each card with respect to each peer card."
    --#SUMMARY "Results on-card %d: to-card %d health loss for 5mins, is in Bad health, threshold %d%% measured value %d%%"
    --#ARGUMENTS {0,1,2,3}
    --#STATE OPERATIONAL
    --#SEVERITY INFORMATIONAL
    ::= { starentTraps 1343 }

starThreshClearHatHb5MinsLoss NOTIFICATION-TYPE
    OBJECTS { starSlotNum, starSlotNum, starThreshPct, starThreshMeasuredPct }
    STATUS  current
    DESCRIPTION
        "Clear heartbeat loss for past 5 mins interval on each card with respect to each peer card."
    --#SUMMARY "Results on-card %d: to-card %d health loss for 5mins, is in Good health, threshold %d%% measured value %d%%"
    --#ARGUMENTS {0,1,2,3}
    --#STATE OPERATIONAL
    --#SEVERITY INFORMATIONAL
    ::= { starentTraps 1344 }

starThreshHatHb60MinsLoss NOTIFICATION-TYPE
    OBJECTS { starSlotNum, starSlotNum, starThreshPct, starThreshMeasuredPct }
    STATUS  current
    DESCRIPTION
        "Heartbeat loss for past 60 mins on each card with respect to each peer card."
    --#SUMMARY "Results on-card %d: to-card %d health loss for 60mins, is in Bad health, threshold %d%% measured value %d%%"
    --#ARGUMENTS {0,1,2,3}
    --#STATE OPERATIONAL
    --#SEVERITY INFORMATIONAL
    ::= { starentTraps 1345 }

starThreshClearHatHb60MinsLoss NOTIFICATION-TYPE
    OBJECTS { starSlotNum, starSlotNum, starThreshPct, starThreshMeasuredPct }
    STATUS  current
    DESCRIPTION
        "Clear heartbeat loss for past 60 mins interval on each card with respect to each peer card."
    --#SUMMARY "Results on-card %d: to-card %d health loss for 60mins, is in Good health, threshold %d%% measured value %d%%"
    --#ARGUMENTS {0,1,2,3}
    --#STATE OPERATIONAL
    --#SEVERITY INFORMATIONAL
    ::= { starentTraps 1346 }

starGlobalCLISessionsLimit NOTIFICATION-TYPE
    OBJECTS {
                starCLIActiveCount,
                starCLIMaxCount
            }
    STATUS  current
    DESCRIPTION
	"Glocal Concurrent CLI Sessions limit has been hit.
	 Total number of Active CLI Sessions have exceeded configured Maximum Limit.
         If possible, please cleanup idle sessions."
    --#SUMMARY "[System] Security: active CLI sessions count %d is higher than maximum CLI sessions limit %d"
    --#ARGUMENTS {0,1}
    --#STATE OPERATIONAL
    --#SEVERITY WARNING
    ::= { starentTraps 1347 }

starUserCLISessionsLimit NOTIFICATION-TYPE
    OBJECTS {
                starCLIContext,
                starCLIUsername,
                starCLITtyname,
                starCLIRemoteIpAddrType,
                starCLIRemoteIpAddr,
                starCLIDatabaseUsername,
                starCLIPrivs,
                starCLIActiveCount,
                starCLIMaxCount
            }
    STATUS  current
    DESCRIPTION
	"Concurrent CLI Sessions limit has been hit for this user.
	 Total number of Active CLI Sessions have exceeded configured Maximum Limit for this use.
         If possible, please cleanup idle sessions."
    --#SUMMARY "[System] Security: context %s user %s ttyname %s address type %s remote ip address %s privilege level %s active CLI sessions %d max CLI sessions %d"
    --#ARGUMENTS {0,1,2,3,4,5,6,7,8}
    --#STATE OPERATIONAL
    --#SEVERITY WARNING
    ::= { starentTraps 1348 }

starSmartLicenseServiceOOC NOTIFICATION-TYPE
    OBJECTS { starSmartLicenseServiceName, starSmartLicenseServiceUsage }
    STATUS current
    DESCRIPTION
        "Smart Licence Service Usage is Out-Of-Compliance, new calls are not allowed for this license.

         Action to be Taken: Please make sure surplus licenses are available to avoid service distruption"
    --#SUMMARY "[System] Smart Licensing Service %s is out-of-compliance, currently using %d licenses"
    --#ARGUMENTS {0,1}
    --#STATE OPERATIONAL
    --#SEVERITY WARNING
    ::= { starentTraps 1349 }

starSmartLicenseServiceOOCClear NOTIFICATION-TYPE
    OBJECTS { starSmartLicenseServiceName, starSmartLicenseServiceUsage }
    STATUS current
    DESCRIPTION
        "Smart Licence Service Usage is In-Compliance, new calls are allowed for this license."
    --#SUMMARY "[System] Smart Licensing Service %s is now in-compliance, currently using %d licenses"
    --#ARGUMENTS {0,1}
    --#STATE OPERATIONAL
    --#SEVERITY WARNING
    ::= { starentTraps 1350 }

starSmartLicenseEvalMode NOTIFICATION-TYPE
    OBJECTS { starSmartLicenseEvalModeRemaining }
    STATUS current
    DESCRIPTION
        "Smart Licensing device is in evaluation period, device being used without registering.

         Action to be Taken: Please register the device with idtoken."
    --#SUMMARY "[System] Smart Licensing device is in evaluation period, device has %d days of evaluation period"
    --#ARGUMENTS {0}
    --#STATE OPERATIONAL
    --#SEVERITY WARNING
    ::= { starentTraps 1351 }

starSmartLicenseEvalModeClear NOTIFICATION-TYPE
    OBJECTS { starSmartLicenseEvalModeRemaining }
    STATUS current
    DESCRIPTION
        "Smart Licensing device is now registered and authorized successfully."
    --#SUMMARY "[System] Smart Licensing device is either registered or evaluation period has been expired, device has %d days of evaluation period"
    --#ARGUMENTS {0}
    --#STATE OPERATIONAL
    --#SEVERITY WARNING
    ::= { starentTraps 1352 }

starSmartLicenseEvalModeExpire NOTIFICATION-TYPE
    STATUS current
    DESCRIPTION
        "Smart Licensing device in evaluation period has expired.

         Action to be Taken: Smart Licensing device works only with valid license, no more evaluation period allowed."
    --#SUMMARY "[System] Smart Licensing device in evaluation period has been expired, no more evaluation period allowed for the device"
    --#STATE DEGRADED
    --#SEVERITY CRITICAL
    ::= { starentTraps 1353 }

starSmartLicenseEvalModeExpireClear NOTIFICATION-TYPE
    STATUS current
    DESCRIPTION
        "Smart Licensing device evaluation period is reseted. Device can be used for 90 days in evaluation period."
    --#SUMMARY "[System] Smart Licensing device evaluation period is reseted, device now has 90 days of evaluation period"
    --#STATE OPERATIONAL
    --#SEVERITY WARNING
    ::= { starentTraps 1354 }

starSmartLicenseCSSMConntectionFail NOTIFICATION-TYPE
    STATUS current
    DESCRIPTION
        "Smart License device unable to connect CSSM License Server.

         Action to be Taken: Make sure to connect the device to the CSSM License Server to avoid service distruption."
    --#SUMMARY "[System] Smart Licensing device unable to connect CSSM license server"
    --#STATE DEGRADED
    --#SEVERITY CRITICAL
    ::= { starentTraps 1355 }

starSmartLicenseCSSMConnectionFailClear NOTIFICATION-TYPE
    STATUS current
    DESCRIPTION
        "Smart License device is now able to connect the CSSM License Server."
    --#SUMMARY "[System] Smart Licensing device is now connected to CSSM license server"
    --#STATE OPERATIONAL
    --#SEVERITY WARNING
    ::= { starentTraps 1356 }


starSxServiceStart NOTIFICATION-TYPE
    OBJECTS { starServiceVpnName, starServiceServName }
    STATUS  current
    DESCRIPTION
        "A Packet Data Network Gateway Sx-Service has started.

         Action to be Taken: No action required"
    --#SUMMARY "[Service Sx-%s-%s] Sx service has started"
    --#ARGUMENTS {0,1}
    --#STATE OPERATIONAL
    --#SEVERITY INFORMATION
    ::= { starentTraps 1357 }

starSxServiceStop NOTIFICATION-TYPE
    OBJECTS { starServiceVpnName, starServiceServName }
    STATUS  current
    DESCRIPTION
        "A Packet Data Network Gateway Sx-Service has stopped.

         Probable Cause: This is typically caused by operator intervention.  In
         rare cases it can be caused by the loss of resources (PSCs) to support
         the running configuration.

         Action to be Taken: If the Sx-service shutdown was not planned,
         examine the admin logs for an indication of the failure.  Verify that
         all configured PSCs are present and running in the system.  Check the
         crash logs for an indication of a software failure.

         Clear Condition: Verify that the Sx service is operational.

         Condition Clear Alarm:  A starSxServiceStart notification will be
         generated when the service is restarted"
    --#SUMMARY "[Service Sx-%s-%s] Sx service has stopped"
    --#ARGUMENTS {0,1}
    --#STATE DEGRADED
    --#SEVERITY MAJOR
    ::= { starentTraps 1358 }


starUplaneServiceStart NOTIFICATION-TYPE
    OBJECTS { starServiceVpnName, starServiceServName }
    STATUS  current
    DESCRIPTION
        "A User Plane (uplane) Service has started.

         Action to be Taken: No action required"
    --#SUMMARY "[Service uplane-%s-%s] User-Plane service has started"
    --#ARGUMENTS {0,1}
    --#STATE OPERATIONAL
    --#SEVERITY INFORMATION
    ::= { starentTraps 1359 }

starUplaneServiceStop NOTIFICATION-TYPE
    OBJECTS { starServiceVpnName, starServiceServName }
    STATUS  current
    DESCRIPTION
        "A User Plane (uplane) Service has stopped.

         Probable Cause: This is typically caused by operator intervention.  In
         rare cases it can be caused by the loss of resources (PSCs) to support
         the running configuration.

         Action to be Taken: If the User-Plane service shutdown was not planned,
         examine the admin logs for an indication of the failure.  Verify that
         all configured PSCs are present and running in the system.  Check the
         crash logs for an indication of a software failure.

         Clear Condition: Verify that the User-Plane service is operational.

         Condition Clear Alarm:  A starUplaneServiceStart notification will be
         generated when the service is restarted"
    --#SUMMARY "[Service Uplane-%s-%s] Uplane service has stopped"
    --#ARGUMENTS {0,1}
    --#STATE DEGRADED
    --#SEVERITY MAJOR
    ::= { starentTraps 1360 }

DisabledEventIDs NOTIFICATION-TYPE
    OBJECTS {
                starCLIEventIDStart,
                starCLIEventIDEnd,
                starCLIUsername,
                starCLIContext,
                starCLIPrivs,
                starCLITtyname,
                starCLIRemoteIpAddrType,
                starCLIRemoteIpAddr
            }
    STATUS  current
    DESCRIPTION
	"Informs about the Logging Event ID Range that has been disabled by an user."
    --#SUMMARY "[System] Security: Event IDs from %d to %d have been disabled by user %s context %s privilege level %s ttyname %s address type %s remote ip address %s"
    --#ARGUMENTS {0,1,2,3,4,5,6,7}
    --#STATE OPERATIONAL
    --#SEVERITY WARNING
    ::= { starentTraps 1361 }

LogLevelChanged NOTIFICATION-TYPE
    OBJECTS {
                starCLILogLevelChanged,
                starCLIUsername,
                starCLIContext,
                starCLIPrivs,
                starCLITtyname,
                starCLIRemoteIpAddrType,
                starCLIRemoteIpAddr
            }
    STATUS  current
    DESCRIPTION
	"Informs about the change in logging level of a facility by an user."
    --#SUMMARY "[System] Security: 'Logging level of facility <facility> is changed to <critical>' by user %s context %s privilege level %s ttyname %s address type %s remote ip address %s"
    --#ARGUMENTS {0,1,2,3,4,5,6}
    --#STATE OPERATIONAL
    --#SEVERITY WARNING
    ::= { starentTraps 1362 }


starThreshTotalVolume NOTIFICATION-TYPE
    OBJECTS { starRuleBaseName, starRuleDefName, starGroupOfRuledef, starThreshInt, starThreshMeasuredInt }
    STATUS  current
    DESCRIPTION
        "Total Volume for Specified RuleBase and RuleDef"
    --#SUMMARY "facility sessmgr RuleBase %s RuleDef %s GroupOfRuledefFlag %d threshold volume %d%% bytes measured volume %d%% Kilobytes"
    --#ARGUMENTS {0,1,2,3,4}
    --#STATE OPERATIONAL
    --#SEVERITY INFORMATIONAL
    ::= { starentTraps 1363 }

starThreshTotalVolumeClear NOTIFICATION-TYPE
    OBJECTS { starRuleBaseName, starRuleDefName, starGroupOfRuledef, starThreshInt, starThreshMeasuredInt }
    STATUS  current
    DESCRIPTION
        "Total Volume for Specified RuleBase and RuleDef"
    --#SUMMARY "facility sessmgr RuleBase %s RuleDef %s GroupOfRuledefFlag %d threshold volume  %d%% bytes  measured volume %d%% Kilobytes"
    --#ARGUMENTS {0,1,2,3,4}
    --#STATE OPERATIONAL
    --#SEVERITY INFORMATIONAL
    ::= { starentTraps 1364 }

starIKEv2DDOSAttackUDPFail NOTIFICATION-TYPE
    OBJECTS { starTaskInstance }
    STATUS current
    DESCRIPTION
         "Alarm will be triggered when a ipsecdemux encounters high UDP errors rate."
    --#SUMMARY "[IPSEC] : IPSec demux instance [%d] context [%s] UDP failure rate exceeded the configured System based threshold "
    --#ARGUMENTS {0,1}
    --#STATE OPERATIONAL
    --#SEVERITY CRITICAL 
    ::= { starentTraps 1365 }

starIKEv2DDOSAttackClearUDPFail NOTIFICATION-TYPE
    OBJECTS { starTaskInstance }
    STATUS current
    DESCRIPTION
         "Alarm will be triggered when udp error rate falls below threshold or config is disabled."
    --#SUMMARY "[IPSEC] : IPSec demux instance [%d] context [%s] UDP failure rate alarm cleared [%s] for System Based Threshold"
    --#ARGUMENTS {0,1,2}
    --#STATE OPERATIONAL
    --#SEVERITY INFORMATIONAL
    ::= { starentTraps 1366 }

starIKEv2DDOSAttackUDPFailPeer NOTIFICATION-TYPE
    OBJECTS { starTaskInstance }
    STATUS current
    DESCRIPTION
         "Alarm will be triggered when a IKEv2 UDP failure rate crosses configured upper threshold for Source-IP"
    --#SUMMARY "[IPSEC] : IPSec demux instance [%d] context [%s] UDP failure rate exceeded the configured Source-IP based threshold for  Peer IP %s "
    --#ARGUMENTS {0,1,2}
    --#STATE OPERATIONAL
    --#SEVERITY CRITICAL
    ::= { starentTraps 1367 }

starIKEv2ClearDDOSAttackUDPFailPeer NOTIFICATION-TYPE
    OBJECTS { starTaskInstance }
    STATUS current
    DESCRIPTION
         "Alarm will be triggered when IKEv2 UDP failure rate comes down below configured lower threshold for Source-IP or config is disabled."
    --#SUMMARY "[IPSEC] : IPSec demux instance [%d] context [%s] UDP failure rate alarm cleared [%s] for Source-IP based threshold for Peer IP %s "
    --#ARGUMENTS {0,1,2,3}
    --#STATE OPERATIONAL
    --#SEVERITY INFORMATIONAL
    ::= { starentTraps 1368 }


starIKEv2DDOSAttackINITFlood NOTIFICATION-TYPE
    OBJECTS { starTaskInstance }
    STATUS current
    DESCRIPTION
         "Alarm will be triggered when a ipsecdemux encounters Flood of INIT requests."
    --#SUMMARY "[IPSEC] : IPSecDemux Facility instance [%d] context [%s ]Outstanding INIT excceded the configured threshold "
    --#ARGUMENTS {0}
    --#STATE OPERATIONAL
    --#SEVERITY CRITICAL 
    ::= { starentTraps 1369 }

starIKEv2DDOSAttackClearINITFlood NOTIFICATION-TYPE
    OBJECTS { starTaskInstance }
    STATUS current
    DESCRIPTION
         "Alarm will be triggered when rate of INIT requests falls below threshold or config is disabled."
    --#SUMMARY "[IPSEC] : IPSecDemux Facility instance [%d] context [%s ]Outstanding INIT requests [below threshold]"
    --#ARGUMENTS {0}
    --#STATE OPERATIONAL
    --#SEVERITY INFORMATIONAL
    ::= { starentTraps 1370 }

starIKEv2DDOSAttackINITPeerFlood NOTIFICATION-TYPE
    OBJECTS { starTaskInstance }
    STATUS current
    DESCRIPTION
         "Alarm will be triggered when a ipsecdemux encounters Flood of INIT requests."
    --#SUMMARY "[IPSEC] : IPSecDemux Facility instance [%d] context [%s ]Outstanding INIT excceded the configured threshold "
    --#ARGUMENTS {0}
    --#STATE OPERATIONAL
    --#SEVERITY CRITICAL 
    ::= { starentTraps 1371 }

starIKEv2DDOSAttackClearINITPeerFlood NOTIFICATION-TYPE
    OBJECTS { starTaskInstance }
    STATUS current
    DESCRIPTION
         "Alarm will be triggered when rate of INIT requests falls below threshold or config is disabled."
    --#SUMMARY "[IPSEC] : IPSecDemux Facility instance [%d] context [%s ]Outstanding INIT requests [below threshold]"
    --#ARGUMENTS {0}
    --#STATE OPERATIONAL
    --#SEVERITY INFORMATIONAL
    ::= { starentTraps 1372 }

starIFTaskHealthFailure NOTIFICATION-TYPE
    OBJECTS { starSlotNum }
    STATUS  current
    DESCRIPTION
	"A failure of an IFTASK worker thread health has been detected.
         This may lead to internal control plane network slow down.

	 Action to be Taken: If this condition persists, the identified card
	 needs to be rebooted. This is applicable to QvPC DI and SI platforms."
    --#SUMMARY "[Card %d] IFTASK Health Failure"
    --#ARGUMENTS {0}
    --#STATE NONOPERATIONAL
    --#SEVERITY MAJOR
    ::= { starentTraps 1373 }

starIKEv2ReqRateThreshold NOTIFICATION-TYPE
    OBJECTS { starTaskInstance }
    STATUS current
    DESCRIPTION
         "Alarm will be triggered when IKEv2 Request messages crosses the configured threshold."
    --#SUMMARY "[IPSEC] : Max Allowed IKEv2 Request Count crossed configured threshold %s for UE with NAI %s and IP addr %s on IPSec Mgr instance %d"
    --#ARGUMENTS {0,1,2,3}
    --#STATE OPERATIONAL
    --#SEVERITY INFORMATIONAL
    ::= { starentTraps 1374 }

starIKEv2ClearReqRateThreshold NOTIFICATION-TYPE
    OBJECTS { starTaskInstance }
    STATUS current
    DESCRIPTION
         "Alarm will be triggered when either IKESA session is deleted or IKEv2 Request messages per interval reaches lower than configured threshold."
    --#SUMMARY "[IPSEC] : Alarm for Max allowed IKEv2 request alarm cleared [Reason:%s ]for UE with NAI %s and IP addr %s on IPSec Mgr instance %d "
    --#ARGUMENTS {0,1,2,3}
    --#STATE OPERATIONAL
    --#SEVERITY INFORMATIONAL
    ::= { starentTraps 1375 }

starChassisStartupTimeout NOTIFICATION-TYPE
    STATUS current
    DESCRIPTION
        "Not all cards did not comeup within chassis timeout, chassis will proceed with whatever cards are present and start applying the startup configuration"
    --#SUMMARY
    --#STATE OPERATIONAL
    --#SEVERITY WARNING
    ::= { starentTraps 1377 }

starNeedADCLicense NOTIFICATION-TYPE
    OBJECTS { starP2PPluginVersion , starADCLicenseExpiryDate }
    STATUS current
    DESCRIPTION
        "ADC license required.
        Action to be taken: Please purchase and configure ADC license"
    --#ARGUMENTS {0,1}
    --#SUMMARY "ADC Plugin Version %s needs ADC Annual license. Please purchase and configure ADC Annual license. Upgrade to ADC Plugin Versions released after %s will not be allowed" 
    --#STATE OPERATIONAL
    --#SEVERITY WARNING
    ::= { starentTraps 1378 }

starNeedADCLicenseClear NOTIFICATION-TYPE
    OBJECTS { starP2PPluginVersion }
    STATUS current
    DESCRIPTION
        "ADC license present."
    --#ARGUMENTS {0}
    --#SUMMARY "ADC Plugin Version %s either has or doesn't need ADC Annual license" 
    --#STATE OPERATIONAL
    --#SEVERITY INFORMATIONAL 
    ::= { starentTraps 1379 }

starADCLicenseAboutToExpire NOTIFICATION-TYPE
    OBJECTS {  starADCLicenseExpiryDate }
    STATUS current
    DESCRIPTION
        "ADC license is about to expire.
         
         Action to be Taken: A new ADC license should be created and configured on the system before the grace period is over."
    --#SUMMARY "ADC Annual License will expire on %s. Upgrade to ADC Plugin Versions released after %s will not be allowed. Please renew the license."
    --#ARGUMENTS {0,0}
    --#STATE OPERATIONAL
    --#SEVERITY CRITICAL
    ::= { starentTraps 1380 }

starADCLicenseExpired NOTIFICATION-TYPE
    OBJECTS {  starLicenseExpiryDate }
    STATUS current
    DESCRIPTION
        "ADC license has expired.

         Action to be Taken: A new license should be created and configured on the system."
    --#SUMMARY "ADC Annual License has expired. Upgrade to ADC Plugin Versions released after %s will not be allowed. Please renew the license"
    --#ARGUMENTS {0}
    --#STATE NONOPERATIONAL
    --#SEVERITY CRITICAL
    ::= { starentTraps 1381 }

starSxPathFailure NOTIFICATION-TYPE
    OBJECTS { starServiceVpnName, starServiceServName, starSxSelfAddr, starSxPeerAddr, starSxPeerOldRecTimeStamp, starSxPeerNewRecTimeStamp, starSxFailureCause }
    STATUS  current
    DESCRIPTION
        "Sx Path Failure. No response received for Sx request sent to Sx Peer.

         Possibe reason: Remote Sx peer is down

         Condition Clear Alarm:  A StarSxPathFailureClear notification will be generated when
         the path to the remote Sx peer becomes available"
    --#SUMMARY "[Service Sx-%s-%s] Sx path failure  self address %s,  peer address %s, peer old recovery timestamp %d,  peer new recovery timestamp %d, Failure cause %s"
    --#ARGUMENTS {0,1,2,3,4,5,6,7,8}
    --#STATE DEGRADED
    --#SEVERITY MAJOR
    ::= { starentTraps 1382 }

starSxPathFailureClear NOTIFICATION-TYPE
    OBJECTS { starServiceVpnName, starServiceServName,  starSxSelfAddr, starSxPeerAddr, starSxPeerNewRecTimeStamp, starSxFailureCause}
    STATUS  current
    DESCRIPTION
        "Sx Path Failure condition is no longer valid."
    --#SUMMARY "[Service Sx-%s-%s] Sx path failure condition clear for self address %s,  peer address %s, peer recovery timestamp %d, Clear reason %s"
    --#ARGUMENTS {0,1,2,3,4,5,6}
    --#STATE OPERATIONAL
    --#SEVERITY INFORMATIONAL
    ::= { starentTraps 1383 }

starThreshDataPlaneMonitor5MinsLoss NOTIFICATION-TYPE
    OBJECTS { starSlotNum, starSlotNum, starThreshPct, starThreshMeasuredPct }
    STATUS  current
    DESCRIPTION
        "5 minute data plane monitor packet loss between peer cards."
    --#SUMMARY "5 minute dataplane monitor loss from-card %d to-card %d, threshold %d%% measured value %d%%"
    --#ARGUMENTS {0,1,2,3}
    --#STATE OPERATIONAL
    --#SEVERITY INFORMATIONAL
    ::= { starentTraps 1384 }

starThreshClearDataPlaneMonitor5MinsLoss NOTIFICATION-TYPE
    OBJECTS { starSlotNum, starSlotNum, starThreshPct, starThreshMeasuredPct }
    STATUS  current
    DESCRIPTION
        "Clear 5 minute data plane monitor packet loss between peer cards."
    --#SUMMARY "5 minute dataplane monitor loss from-card %d to-card %d, threshold %d%% measured value %d%%"
    --#ARGUMENTS {0,1,2,3}
    --#STATE OPERATIONAL
    --#SEVERITY INFORMATIONAL
    ::= { starentTraps 1385 }

starThreshDataPlaneMonitor60MinsLoss NOTIFICATION-TYPE
    OBJECTS { starSlotNum, starSlotNum, starThreshPct, starThreshMeasuredPct }
    STATUS  current
    DESCRIPTION
        "60 minute data plane monitor packet loss between peer cards."
    --#SUMMARY "60 minute dataplane monitor loss from-card %d to-card %d, threshold %d%% measured value %d%%"
    --#ARGUMENTS {0,1,2,3}
    --#STATE OPERATIONAL
    --#SEVERITY INFORMATIONAL
    ::= { starentTraps 1386 }

starThreshClearDataPlaneMonitor60MinsLoss NOTIFICATION-TYPE
    OBJECTS { starSlotNum, starSlotNum, starThreshPct, starThreshMeasuredPct }
    STATUS  current
    DESCRIPTION
        "Clear 60 minute data plane monitor packet loss between peer cards."
    --#SUMMARY "60 minute dataplane monitor loss from-card %d to-card %d, threshold %d%% measured value %d%%"
    --#ARGUMENTS {0,1,2,3}
    --#STATE OPERATIONAL
    --#SEVERITY INFORMATIONAL
    ::= { starentTraps 1387 }

starThreshControlPlaneMonitor5MinsLoss NOTIFICATION-TYPE
    OBJECTS { starSlotNum, starSlotNum, starThreshPct, starThreshMeasuredPct }
    STATUS  current
    DESCRIPTION
        "5 minute control plane monitor packet loss between peer cards."
    --#SUMMARY "5 minute controlplane monitor loss from-card %d to-card %d, threshold %d%% measured value %d%%"
    --#ARGUMENTS {0,1,2,3}
    --#STATE OPERATIONAL
    --#SEVERITY INFORMATIONAL
    ::= { starentTraps 1388 }

starThreshClearControlPlaneMonitor5MinsLoss NOTIFICATION-TYPE
    OBJECTS { starSlotNum, starSlotNum, starThreshPct, starThreshMeasuredPct }
    STATUS  current
    DESCRIPTION
        "Clear 5 minute control plane monitor packet loss between peer cards."
    --#SUMMARY "5 minute controlplane monitor loss from-card %d to-card %d, threshold %d%% measured value %d%%"
    --#ARGUMENTS {0,1,2,3}
    --#STATE OPERATIONAL
    --#SEVERITY INFORMATIONAL
    ::= { starentTraps 1389 }

starThreshControlPlaneMonitor60MinsLoss NOTIFICATION-TYPE
    OBJECTS { starSlotNum, starSlotNum, starThreshPct, starThreshMeasuredPct }
    STATUS  current
    DESCRIPTION
        "60 minute control plane monitor packet loss between peer cards."
    --#SUMMARY "60 minute controlplane monitor loss from-card %d to-card %d, threshold %d%% measured value %d%%"
    --#ARGUMENTS {0,1,2,3}
    --#STATE OPERATIONAL
    --#SEVERITY INFORMATIONAL
    ::= { starentTraps 1390 }

starThreshClearControlPlaneMonitor60MinsLoss NOTIFICATION-TYPE
    OBJECTS { starSlotNum, starSlotNum, starThreshPct, starThreshMeasuredPct }
    STATUS  current
    DESCRIPTION
        "Clear 60 minute control plane monitor packet loss between peer cards."
    --#SUMMARY "60 minute controlplane monitor loss from-card %d to-card %d, threshold %d%% measured value %d%%"
    --#ARGUMENTS {0,1,2,3}
    --#STATE OPERATIONAL
    --#SEVERITY INFORMATIONAL
    ::= { starentTraps 1391 }

starSxPeerAssociated NOTIFICATION-TYPE
    OBJECTS {starServiceVpnName, starServiceServName, starSxInterfaceType, starSxSelfAddr, starSxPeerAddr, starSxInterfaceType, starSxCPUPGroupName}
    STATUS  current
    DESCRIPTION
        "Sx Peer Association sucessful with <Sx-Interface-Type Self-IP Peer-IP and Sx-Interface-Type>."
    --#SUMMARY "[Service Sx-%s-%s] Sx Peer Association sucessful with self node is %d , peer address %s and remote address is %s and its type is %d, Group name is %s"
    --#ARGUMENTS {0 1 2 3 4 5 6}
    --#STATE OPERATIONAL
    --#SEVERITY INFORMATIONAL
    ::= { starentTraps 1392 }

starSxPeerAssociationRelease NOTIFICATION-TYPE
    OBJECTS {starServiceVpnName, starServiceServName, starSxInterfaceType, starSxSelfAddr, starSxPeerAddr, starSxInterfaceType, starSxCPUPGroupName}
    STATUS  current
    DESCRIPTION
        "Sx Peer Association released sucessfully with <Sx-Interface-Type Sx-Self-IP Sx-Peer-IP and Sx-Interface-Type>."
    --#SUMMARY "[Service Sx-%s-%s] Sx Peer Association released sucessfully with self node is %d , peer address %s and remote address is %s and its type is %d, Group name is %s"
    --#ARGUMENTS {0 1 2 3 4 5 6}
    --#STATE OPERATIONAL
    --#SEVERITY INFORMATIONAL
    ::= { starentTraps 1393 }

starChassisThroughputOver NOTIFICATION-TYPE
    OBJECTS {starThreshInt,starThreshMeasuredInt}
    STATUS  current
    DESCRIPTION
        "Chassis Throughput exceeds over-limit."
    --#SUMMARY "Chassis Throughput limit %d , measured %d"
    --#ARGUMENTS {0 1}
    --#STATE OPERATIONAL
    --#SEVERITY INFORMATIONAL
    ::= { starentTraps 1394 }

starChassisThroughputOverClear NOTIFICATION-TYPE
    OBJECTS {starThreshInt,starThreshMeasuredInt}
    STATUS  current
    DESCRIPTION
        "Chassis Throughput Over trap cleared."
    --#SUMMARY "Chassis Throughput limit %d , measured %d"
    --#ARGUMENTS {0 1}
    --#STATE OPERATIONAL
    --#SEVERITY INFORMATIONAL
    ::= { starentTraps 1395 }

starChassisThroughputWarn NOTIFICATION-TYPE
    OBJECTS {starThreshInt,starThreshMeasuredInt}
    STATUS  current
    DESCRIPTION
        "Chassis Throughput Exceeds Warn Threshold."
    --#SUMMARY "Chassis Throughput limit %d , measured %d"
    --#ARGUMENTS {0 1}
    --#STATE OPERATIONAL
    --#SEVERITY INFORMATIONAL
    ::= { starentTraps 1396 }

starChassisThroughputWarnClear NOTIFICATION-TYPE
    OBJECTS {starThreshInt,starThreshMeasuredInt}
    STATUS  current
    DESCRIPTION
        "Chassis Throughput Warn Trap cleared."
    --#SUMMARY "Chassis Throughput limit %d , measured %d"
    --#ARGUMENTS {0 1}
    --#STATE OPERATIONAL
    --#SEVERITY INFORMATIONAL
    ::= { starentTraps 1397 }

starIFTaskBootConfigApplied NOTIFICATION-TYPE
    OBJECTS { starSlotNum,starCPUNumber}
    STATUS  current
    DESCRIPTION
	"IFTask Boot Configuration has been applied on identified card-cpu."
    --#SUMMARY "iftask boot config applied on Card %d CPU %d"
    --#ARGUMENTS {0 1}
    --#STATE OPERATIONAL
    --#SEVERITY INFORMATIONAL
    ::= { starentTraps 1398 }

starUidhURLHostDatabaseUpgradeFailureStatus NOTIFICATION-TYPE
    OBJECTS { starCommonDatabasePreDBVersion, starCommonDatabaseUpgradeDBVersion, starCommonDatabaseUpgradeComment }    
    STATUS  current
    DESCRIPTION
        "UIDH URL-HOST Database Upgrade Failure Status.                            
	     Condition Clear Alarm: This condition is cleared by starUidhURLHostDatabaseUpgradeSuccessStatus  notification."
    --#SUMMARY "Pre-DB Version %s Upgrade Version %s, Comment: %s"
    --#ARGUMENTS {0,1,2}
    --#STATE OPERATIONAL
    --#SEVERITY MAJOR
    ::= { starentTraps 1399 }

starUidhURLHostDatabaseUpgradeSuccessStatus NOTIFICATION-TYPE
    OBJECTS { starCommonDatabasePreDBVersion, starCommonDatabaseUpgradeDBVersion, starCommonDatabaseUpgradeComment }
    STATUS  current
    DESCRIPTION
        "UIDH URL-HOST Database Upgrade Success.
         Action to be taken: No action required "
    --#SUMMARY "Pre-DB Version %s Upgrade Version %s, Comment: %s"
    --#ARGUMENTS {0,1,2}
    --#STATE OPERATIONAL
    --#SEVERITY INFORMATIONAL
    ::= { starentTraps 1400 }

starSmartLicenseFeatureOOC NOTIFICATION-TYPE
    OBJECTS { starSmartLicenseFeatureName,  starSmartLicenseFeatureUsage }
    STATUS current
    DESCRIPTION
        "Smart Licence Feature Usage is Out-Of-Compliance, new calls are not allowed for services which uses this feature license.

         Action to be Taken: Please make sure surplus licenses are available to avoid service distruption"
    --#SUMMARY "[System] Smart Licensing Feature %s is out-of-compliance, currently using %d licenses"
    --#ARGUMENTS {0,1}
    --#STATE OPERATIONAL
    --#SEVERITY WARNING
    ::= { starentTraps 1401 }

starSmartLicenseFeatureOOCClear NOTIFICATION-TYPE
    OBJECTS { starSmartLicenseFeatureName,  starSmartLicenseFeatureUsage }
    STATUS current
    DESCRIPTION
        "Smart Licence Feature Usage is In-Compliance, new calls are allowed for services which uses this feature license."
    --#SUMMARY "[System] Smart Licensing Feature %s is now in-compliance, currently using %d licenses"
    --#ARGUMENTS {0,1}
    --#STATE OPERATIONAL
    --#SEVERITY WARNING
    ::= { starentTraps 1402 }

-- Conformance Information


starentMIBConformance OBJECT IDENTIFIER ::= { starentMIB 3 }

starentMIBGroups      OBJECT IDENTIFIER ::= { starentMIBConformance 1 }

starentMIBCompliances OBJECT IDENTIFIER ::= { starentMIBConformance 2 }

-- Compliance Statements

starentMIBCompliance2 MODULE-COMPLIANCE
    STATUS current
    DESCRIPTION
        "The compliance statement for ..."

    MODULE
        MANDATORY-GROUPS { starChassisGroup,
			   starAlertGroup,
			   starAlertTrapGroup,
                           starTrapGroup }
    ::= { starentMIBCompliances 2 }

starChassisGroup OBJECT-GROUP
    OBJECTS { starChassisCriticalCO,
              starChassisMajorCO,
              starChassisMinorCO,
              starChassisAudibleAlarm,
	      starChassisUTCTime,
	      starChassisLocalTime,
	      starChassisType,
              starChassisAction,
	      starTimeTicks,
              starChassisDescription,
              starChassisSWRevision,
              starChassisPeakCpuUsage,
              starChassisPeakMemoryUsage, 
              -- slot table
              starSlotType,
              starCardType,
	      starCardOperState,
	      starCardAdminState,
	      starCardRevision,
	      starCardLastStateChange,
	      starCardMode,
	      starCardPacStandbyPriority,
	      starCardLock,
	      starCardHaltIssued,
	      starCardRebootPending,
	      starCardUsable,
	      starCardSinglePOF,
	      starCardAttachment,
	      starCardTemperature,
	      starSlotNumPorts,
	      starSlotAction,
	      starSlotVoltageState,
	      starSlotNumCPU,
	      starSlotPartNumber,
	      starSlotPartRevision,
	      starSlotSerialNumber,
	      starSlotCLEICode,
	      starSlotCiscoModelName,
	      starSlotCiscoHardwareRev,
	      starSlotCiscoSerialNumber,
	      starDeviceNum,
	      starSerdesNum,
	      starSlotMappingType,
	      starSlotMappingRCCNum,
	      starSlotMappingToSlot,
              -- NPU table
	      starNPUSlot,
              -- fan table
              starFanNum,
              starFanLocation,
              starFanStatus,
              starFanSpeed,
	      -- log table
	      starLogCurSize,
	      starLogMaxSize,
	      starLogText,
	      -- power table
              starPowerState,
	      -- cpu table
	      starCPUUser,
	      starCPUSystem,
	      starCPUIdle,
	      starCPUIO,
	      starCPUIRQ,
	      starCPULoad1Min,
	      starCPULoad5Min,
	      starCPULoad15Min,
	      starCPUMemTotal,
	      starCPUMemUsed,
	      starCPUNumProcesses,
	      starCPUMemCached,
	      -- Session In Progress
	      starSessInProgCalls,
	      starSessInProgActiveCalls,
	      starSessInProgDormantCalls,
	      starSessInProgArrived,
	      starSessInProgLCPNeg,
	      starSessInProgLCPUp,
	      starSessInProgAuthenticating,
	      starSessInProgAuthenticated,
	      starSessInProgIPCPUp,
	      starSessInProgSIPConn,
	      starSessInProgMIPConn,
	      starSessInProgDisc,
	      -- Session
              starSessMgrCount,
              starSessTtlArrived,
              starSessTtlRejected,
              starSessTtlConnected,
              starSessTtlAuthSucc,
              starSessTtlAuthFail,
              starSessTtlLCPUp,
              starSessTtlIPCPUp,
              starSessTtlSrcViol,
              starSessTtlKeepFail,
	      starSessTtlOctForwarded,
	      starSessTtlRPRegAccept,
	      starSessTtlRPRegAcceptInterPDSN,
	      starSessCurrPPPSessions,
	      starSessTtlTxBytes,
	      starSessTtlRxBytes,
	      starSessTtlSIPTxBytes,
	      starSessTtlSIPRxBytes,
	      starSessTtlMIPTxBytes,
	      starSessTtlMIPRxBytes,
	      starSessTtlOctForwardedGB,
          starSessTtlOctForwardedRev1,
          starSessTtlTxBytesRev1,
          starSessTtlRxBytesRev1,
          starSessTtlSIPTxBytesRev1,
          starSessTtlSIPRxBytesRev1,
          starSessTtlMIPTxBytesRev1,
          starSessTtlMIPRxBytesRev1,
          starSessTtlOctForwardedGBRev1,
              -- AAA
              starAAAMgrCount,
              starAAATtlRequests,
              starAAATtlAuthRequests,
              starAAATtlAcctRequests,
              starAAACurRequests,
              starAAACurAuthRequests,
              starAAACurAcctRequests,
              starAAATtlAcctSess,
              starAAACurAcctSess,
              starAAATtlAuthSuccess,
              starAAATtlAuthFailure,
              -- A11
              starA11MgrCount,
              starA11TtlArrived,
              starA11TtlRejected,
              starA11TtlDemultiplexed,
              starA11TtlDereg,
              starA11CurActive,
              -- HA
              starHAMgrCount,
              starHATtlArrived,
              starHATtlRejected,
              starHATtlDemultiplexed,
              starHATtlDereg,
              starHACurActive,
              -- FA
              starFAMgrCount,
              starFATtlArrived,
              starFATtlRejected,
              starFATtlDemultiplexed,
              starFATtlDereg,
              starFACurActive,
	      -- Service Managers
              starServiceVpnName,
              starServiceServName,
	      starServiceSubLimit,
	      starServiceSubCurrent,
	      starServiceType,
	      starServiceFAIpAddr,
	      starServiceHAIpAddr,
        starSmartLicenseServiceName,
        starSmartLicenseServiceUsage,
        starSmartLicenseFeatureName,
        starSmartLicenseFeatureUsage,
        starSmartLicenseEvalModeRemaining,
        starP2PPluginVersion,
        starADCLicenseExpiryDate,
        starSxInterfaceType,
        starSxSelfAddr,
        starSxPeerAddr,
        starSxPeerNewRecTimeStamp,
        starSxPeerOldRecTimeStamp,
        starSxFailureCause,
        starSxCPUPGroupName,
	      -- CLI
              starCLITtyname,
              starCLIPrivs,
	      starCLIType,
          starCLIRemoteIpAddrType,
	      starCLIRemoteIpAddr,
	      starCLIContext,
	      -- Tasks
              starTaskFacilityName,
              starTaskCard,
              starTaskCPU,
	      -- PPP Stats
              starPPPStatVpnName,
              starPPPStatServName,
              starPPPStatInit,
              starPPPStatReneg,
              starPPPStatSuccess,
              starPPPStatFailed,
              starPPPStatReleased,
              starPPPStatReleasedLocal,
              starPPPStatReleasedRemote,
              starPPPStatLcpFailMaxRetry,
              starPPPStatLcpFailOption,
              starPPPStatIpcpFailMaxRetry,
              starPPPStatIpcpFailOption,
              starPPPStatCcpFail,
              starPPPStatAuthFail,
              starPPPStatLcpEntered,
              starPPPStatAuthEntered,
              starPPPStatIpcpEntered,
              starPPPStatRenegPdsn,
              starPPPStatRenegMobil,
              starPPPStatRenegAddrMismatch,
              starPPPStatRenegOther,
              starPPPStatChapAuthAttempt,
              starPPPStatPapAuthAttempt,
              starPPPStatMSChapAuthAttempt,
              starPPPStatChapAuthFail,
              starPPPStatPapAuthFail,
              starPPPStatMSChapAuthFail,
              starPPPStatStacComp,
              starPPPStatMppcComp,
              starPPPStatDeflComp,
              starPPPStatFscErrs,
              starPPPStatUnknProto,
              starPPPStatBadAddr,
              starPPPStatBadCtrl,
              starPPPStatVjComp,
              starPPPStatDiscLcpRemote,
              starPPPStatDiscRpRemote,
              starPPPStatDiscAdmin,
              starPPPStatDiscIdleTimeout,
              starPPPStatDiscAbsTimeout,
              starPPPStatDiscPPPKeepalive,
              starPPPStatDiscNoResource,
              starPPPStatDiscMisc,
              starPPPStatFailedReneg,
              starPPPStatLcpFailUnknown,
              starPPPStatIpcpFailUnknown,
              starPPPStatAuthAbort,
              starPPPStatLowerLayerDisc,
              starPPPStatLcpSuccess,
              starPPPStatAuthSuccess,
              starPPPStatRenegLowerLayerHandoff,
              starPPPStatRenegParamUpdate,
              starPPPStatChapAuthSuccess,
              starPPPStatPapAuthSuccess,
              starPPPStatMSChapAuthSuccess,
              starPPPStatChapAuthAbort,
              starPPPStatPapAuthAbort,
              starPPPStatMSChapAuthAbort,
              starPPPStatSessSkipAuth,
              starPPPStatNegComp,
              starPPPStatCCPNegFailComp,
              starPPPStatDiscLocalLowerLayer,
              starPPPStatDiscAddFlowFail,
              starPPPStatDiscMaxRetriesLCP,
              starPPPStatDiscMaxRetriesIPCP,
              starPPPStatDiscMaxSetupTimer,
              starPPPStatDiscInvalidDestVpn,
              starPPPStatDiscOptNegFailLCP,
              starPPPStatDiscOptNegFailIPCP,
              starPPPStatDiscNoRemoteIpAddr,
              starPPPStatDiscCallTypeDetectFail,
              starPPPStatDiscRemoteDiscUpLayer,
              starPPPStatDiscLongDuraTimeout,
              starPPPStatDiscAuthFail,
              starPPPStatLCPEchoTotalReq,
              starPPPStatLCPEchoReqResent,
              starPPPStatLCPEchoRepRecved,
              starPPPStatLCPEchoReqTimeout,
              starPPPStatRecvErrBadCtrlField,
              starPPPStatRecvErrBadPacketLen,
              starPPPStatRemoteTerm,
              starPPPStatMiscFail,
	      -- MIPHA Stats
              starMIPHAStatVpnID,
              starMIPHAStatVpnName,
              starMIPHAStatServName,
              starMIPHAStatDisconnects,
              starMIPHAStatExpiry,
              starMIPHAStatDereg,
              starMIPHAStatAdminDrop,
              starMIPHAStatRegRecvTotal,
              starMIPHAStatRegRecvInitial,
              starMIPHAStatRegRecvRenew,
              starMIPHAStatRegRecvDereg,
              starMIPHAStatRegAcceptTotal,
              starMIPHAStatRegAcceptReg,
              starMIPHAStatRegAcceptRenew,
              starMIPHAStatRegAcceptDereg,
              starMIPHAStatRegDeniedTotal,
              starMIPHAStatRegDeniedInitial,
              starMIPHAStatRegDeniedRenew,
              starMIPHAStatRegDeniedDereg,
              starMIPHAStatRegReplyTotal,
              starMIPHAStatRegReplyAcceptReg,
              starMIPHAStatRegReplyAcceptDereg,
              starMIPHAStatRegReplyDenied,
              starMIPHAStatRegReplyBadReq,
              starMIPHAStatRegReplyMismatchID,
              starMIPHAStatRegReplyAdminProhib,
              starMIPHAStatRegReplyUnspecErr,
              starMIPHAStatRegReplyNoResource,
              starMIPHAStatRegReplyMnAuthFail,
              starMIPHAStatRegReplyFAAuthFail,
              starMIPHAStatRegReplySimulBind,
              starMIPHAStatRegReplyUnknownHA,
              starMIPHAStatRegReplyRevTunUnav,
              starMIPHAStatRegReplyRevTunMand,
              starMIPHAStatRegReplyEncapUnav,
              starMIPHAStatRegReplySendError,
	      starMIPHAStatFARevocations,
	      starMIPHAStatRegAcceptHO,
	      starMIPHAStatRegDeniedHO,
	      starMIPHAStatRegDiscardTotal,
	      -- MIPFA Stats
	      starMIPFAStatVpnID,
              starMIPFAStatVpnName,
              starMIPFAStatServName,
              starMIPFAStatAdvertSend,
              starMIPFAStatDiscExpiry,
              starMIPFAStatDiscDereg,
              starMIPFAStatDiscAdmin,
              starMIPFAStatAuthAttempt,
              starMIPFAStatAuthSuccess,
              starMIPFAStatAuthFailure,
              starMIPFAStatRegRecvTotal,
              starMIPFAStatRegRecvInitial,
              starMIPFAStatRegRecvRenewal,
              starMIPFAStatRegRecvDereg,
              starMIPFAStatRegAcceptTotal,
              starMIPFAStatRegAcceptInitial,
              starMIPFAStatRegAcceptRenewal,
              starMIPFAStatRegAcceptDereg,
              starMIPFAStatRegDenTotal,
              starMIPFAStatRegDenInitial,
              starMIPFAStatRegDenRenewal,
              starMIPFAStatRegDenDereg,
              starMIPFAStatRegDiscardTotal,
              starMIPFAStatRegDiscardInitial,
              starMIPFAStatRegDiscardRenewal,
              starMIPFAStatRegDiscardDereg,
              starMIPFAStatRegRelayedTotal,
              starMIPFAStatRegRelayedInitial,
              starMIPFAStatRegRelayedRenewal,
              starMIPFAStatRegRelayedDereg,
              starMIPFAStatRegAuthFailTotal,
              starMIPFAStatRegAuthFailInitial,
              starMIPFAStatRegAuthFailRenewal,
              starMIPFAStatRegAuthFailDereg,
              starMIPFAStatRegDenPDSNTotal,
              starMIPFAStatRegDenPDSNInitial,
              starMIPFAStatRegDenPDSNRenewal,
              starMIPFAStatRegDenPDSNDereg,
              starMIPFAStatRegDenHATotal,
              starMIPFAStatRegDenHAInitial,
              starMIPFAStatRegDenHARenewal,
              starMIPFAStatRegDenHADereg,
              starMIPFAStatRegDenPDSNUnspec,
              starMIPFAStatRegDenPDSNTimeout,
              starMIPFAStatRegDenPDSNAdmin,
              starMIPFAStatRegDenPDSNResources,
              starMIPFAStatRegDenPDSNMnAuth,
              starMIPFAStatRegDenPDSNHAAuth,
              starMIPFAStatRegDenPDSNTooLong,
              starMIPFAStatRegDenPDSNBadReq,
              starMIPFAStatRegDenPDSNEncapUnav,
              starMIPFAStatRegDenPDSNRevTunUnav,
              starMIPFAStatRegDenPDSNRevTunMand,
              starMIPFAStatRegDenHAFAAuth,
              starMIPFAStatRegDenHABadReq,
              starMIPFAStatRegDenHAMismatchID,
              starMIPFAStatRegDenHASimulBind,
              starMIPFAStatRegDenHAUnknownHA,
              starMIPFAStatRegDenHARevRunUnavail,
              starMIPFAStatRegRplRcvTotal,
              starMIPFAStatRegRplRcvTotalRly,
              starMIPFAStatRegRplRcvErrors,
              starMIPFAStatRegRplRcvInitial,
              starMIPFAStatRegRplRcvInitialRly,
              starMIPFAStatRegRplRcvRenewal,
              starMIPFAStatRegRplRcvRenewalRly,
              starMIPFAStatRegRplRcvDereg,
              starMIPFAStatRegRplRcvDeregRly,
              starMIPFAStatRegRplSentTotal,
              starMIPFAStatRegRplSentAcceptReg,
              starMIPFAStatRegRplSentAcceptDereg,
              starMIPFAStatRegRplSentBadReq,
              starMIPFAStatRegRplSentTooLong,
              starMIPFAStatRegRplSentMnAuthFail,
              starMIPFAStatRegRplSentHAAuthFail,
              starMIPFAStatRegRplSentAdminProhib,
              starMIPFAStatRegRplSentNoResources,
              starMIPFAStatRegRplSentRevTunUnav,
              starMIPFAStatRegRplSentRevTunMand,
              starMIPFAStatRegRplSentSendErrors,
	      starMIPFAStatRegDenPDSNBadReply,
	      starMIPFAStatRegDenPDSNMissNAI,
	      starMIPFAStatRegDenPDSNMissHomeAgent,
	      starMIPFAStatRegDenPDSNMissHomeAddr,
	      starMIPFAStatRegDenPDSNUnknChallenge,
	      starMIPFAStatRegDenPDSNMissChallenge,
	      starMIPFAStatRegDenPDSNStaleChallenge,
	      starMIPFAStatRegDenPDSNMNTooDistant,
	      starMIPFAStatRegDenPDSNStyleUnavail,
	      starMIPFAStatRegDenPDSNHANetUnreach,
	      starMIPFAStatRegDenPDSNHAHostUnreach,
	      starMIPFAStatRegDenPDSNHAPortUnreach,
	      starMIPFAStatRegDenPDSNHAUnreach,
	      starMIPFAStatRegDenPDSNInvCOA,
	      starMIPFAStatRegReqSentInitTotal,
	      starMIPFAStatRegReqSentInitResend,
	      starMIPFAStatRegReqSentRenewTotal,
	      starMIPFAStatRegReqSentRenewResend,
	      starMIPFAStatRegReqSentDeregTotal,
	      starMIPFAStatRegReqSentDeregResend,
	      starMIPFAStatRegRplSentMNTooDistant,
	      starMIPFAStatRegRplSentInvCOA,
	      starMIPFAStatRegRplSentHANetUnreach,
	      starMIPFAStatRegRplSentHAHostUnreach,
	      starMIPFAStatRegRplSentHAPortUnreach,
	      starMIPFAStatRegRplSentHAUnreach,
	      starMIPFAStatRegRplSentRegTimeout,
	      starMIPFAStatRegRplSentMissNAI,
	      starMIPFAStatRegRplSentMissHomeAgent,
	      starMIPFAStatRegRplSentMissHomeAddr,
	      starMIPFAStatRegRplSentUnknChallenge,
	      starMIPFAStatRegRplSentMissChallenge,
	      starMIPFAStatRegRplSentStaleChallenge,
	      starMIPFAStatRegRplSentBadReply,
	      -- RP stats
	      starRPStatVpnID,
              starRPStatVpnName,
              starRPStatServName,
              starRPRegRecvTotal,
              starRPRegAcceptTotal,
              starRPRegDeniedTotal,
              starRPRegDiscardTotal,
              starRPRegAcceptInitial,
              starRPRegAcceptInterPDSN,
              starRPRegDeniedInitial,
              starRPRegAcceptRenew,
              starRPRegDeniedRenew,
              starRPRegAcceptDereg,
              starRPRegDeniedDereg,
              starRPRegSendError,
              starRPRegHashError,
              starRPRegDecodeError,
              starRPRegUnhandled,
              starRPRegAirlinkSeqError,
              starRPRegDenyUnspec,
              starRPRegDenyAdminProhib,
              starRPRegDenyNoResource,
              starRPRegDenyAuth,
              starRPRegDenyMismatchID,
              starRPRegDenyBadRequest,
              starRPRegDenyUnknownPDSN,
              starRPRegDenyRevTunUnav,
              starRPRegDenyRevTunReq,
              starRPRegDenyUnrecogVend,
              starRPRegUpdTotal,
              starRPRegUpdAccept,
              starRPRegUpdDenied,
              starRPRegUpdUnack,
              starRPRegUpdTrans,
              starRPRegUpdRetrans,
              starRPRegUpdReceived,
              starRPRegUpdDiscard,
              starRPRegUpdSendError,
              starRPRegUpdUplyrInit,
              starRPRegUpdOther,
              starRPRegUpdHandoff,
              starRPRegUpdDenyUnspec,
              starRPRegUpdDenyAdminProhib,
              starRPRegUpdDenyAuth,
              starRPRegUpdDenyMismatchID,
              starRPRegUpdDenyBadRequest,
              starRPSecViolations,
              starRPSecBadAuth,
              starRPSecBadID,
              starRPSecBadSpi,
              starRPSecMissingMnHAAuth,
              starRPSecMissingRegUpdate,
	      starRPRegRecvInitial,
	      starRPRegAcceptActvStartIntraPDSN,
	      starRPRegAcceptActvStopIntraPDSN,
	      starRPRegRecvRenew,
	      starRPRegActvStartRenew,
	      starRPRegActvStopRenew,
	      starRPRegRecvDereg,
	      starRPRegAcceptActvStopDereg,
	      starRPDiscSessAbsent,
	      starRPDiscNoMemory,
	      starRPDiscMalformed,
	      starRPDiscAuthFail,
	      starRPDiscInternalBounce,
	      starRPDiscInpuQueueExceeded,
	      starRPDiscMismatchedId,
	      starRPDiscInvPacketLen,
	      starRPDiscMisc,
              starRP1xTxBytes,
              starRP1xRxBytes,
              starRP1xTxPackets,
              starRP1xRxPackets,
              starRPDoTxBytes,
              starRPDoRxBytes,
              starRPDoTxPackets,
              starRPDoRxPackets,

	      --
	      starSubContext,
	      starSubTimerDuration,
              starSubLongDurTimeoutAction,
	      starSubSetupTime,
	      starSubHomeAddr,
	      starSubHomeAddrv6,
	      --
	      starEISServerVPNName,
              --
	      starThreshMeasuredPct,
	      starThreshPct,
              starThreshMeasuredInt,
              starThreshInt,
              starThreshMeasuredMB,
              starThreshMB,
	      starThreshMeasuredGB,
	      starThreshGB,
	      -- Port
	      starPortType,
	      starPortTypeDescr,
	      starPortAdminState,
	      starPortOperState,
              starPortOperMode,
	      starPortLinkState,
	      starRedundantPortSlot,
	      starRedundantPortNum,
	      starPortRxBytes,
	      starPortTxBytes,
	      starPortRxFrames,
	      starPortTxFrames,
	      starPortRxDiscards,
              starPortTxDiscards,
              starPortRxErrors,
              starPortTxErrors,                                                
              -- IPPool
	      starIPPoolVpnID,
	      starIPPoolContext,
	      starIPPoolGroup,
	      starIPPoolName,
	      starIPPoolType,
	      starIPPoolState,
	      starIPPoolStartAddr,
	      starIPPoolMaskorEndAddr,
	      starIPPoolPriority,
	      starIPPoolUsed,
	      starIPPoolHold,
	      starIPPoolRelease,
	      starIPPoolFree,
	      -- IP Pool group
              starIPPoolGroupName,
              starIPPoolGroupVpnName,
              starIPPoolGroupUsed, 
              starIPPoolGroupHold,
              starIPPoolGroupRelease,
              starIPPoolGroupFree,
              starIPPoolGroupPctUsed,
              starIPPoolGroupAvail,
	      starLicensedSessions,
              starCurrentSessions,
	      starDiameterVpnName,
	      starDiameterPeerAddr,
	      starDiameterEndpointName,
	      starDiameterPeerName,
        starDiameterRlfContext,
	      starDiameterPeerAddrIpv6,
	      starInterfaceIPAddress,
	      starOSPFNeighborRouterID,
	      starOSPFFromState,
	      starOSPFToState,
	      starDiameterECode,
	      starDiameterRlfECode,
        starDiameterRlfTps,
        starDiameterRlfDelayTolerance,
        starDiameterRlfQueuePercent,
        starDiameterDiamproxyInstance,
	      starGSSCDRLossConfigured,
	      starGSSCDRLossMeasured,
	      -- GGSN
              starSessGGSNVpnName,
              starSessGGSNServName,
              starSessGGSNPeerPort,
              starSessGGSNPeerAddr,
              starSessGGSNImsi,
              starSessGGSNSubsName,
              starSessGGSNAPNName,
	      starSessGTPPGroupName,
	      -- L2TP
              starL2TPContextName,
	      starL2TPServiceName,
	      starL2TPServiceTypeName,
	      starL2TPLocalAddress,
	      starL2TPPeerAddress,
	      -- SUB1
              starSessSub1Context,
              starSessSub1NAI,
              starSessSub1MSID,
              starSessSub1IpAddr,
	      starSessSub1LastResult,
              starSessSub1ServiceName,
              starSessSub1HAIpAddr,
              starSessSub1PeerIpAddr,
              starSessSub1InPackets,
              starSessSub1InPacketsDropped,
              starSessSub1InBytes,
              starSessSub1OutPackets,
              starSessSub1OutPacketsDropped,
              starSessSub1OutBytes,
              starSessSub1Activity,
              starSessSub1State,
              starSessSub1CallID,
              starSessSub1ConnectTime,
              starSessSub1CallDuration,
              starSessSub1TimeIdle,
	      starSessSub1AccessType,
	      starSessSub1AccessTech,
	      starSessSub1LinkStatus,
	      starSessSub1NetworkType,
	      starSessSub1CarrierID,
	      starSessSub1ESN,
	      starSessSub1GMTTimezoneOffset,
	      starSessSub1SessMgr,
	      starSessSub1RemoteIPAddr,
	      starSessSub1Card,
	      starSessSub1CPU,
	      starSessSub1TimeIdleLeft,
	      starSessSub1TimeLeft,
	      starSessSub1TimeLongDurLeft,
	      starSessSub1LongDurAction,
	      starSessSub1AlwaysOn,
	      starSessSub1IPPoolName,
	      starSessSub1VLANID,
	      starSessSub1LNSIPAddr,
	      starSessSub1ProxyMIP,
	      starSessSub1GGSNMIP,
	      starSessSub1HomeAgentIpAddr,
	      starSessSub1LocalIPAddr,
	      starSessSub1FAServiceName,
	      starSessSub1FAVPNName,
	      starSessSub1SourceVPN,
	      starSessSub1DestVPN,
	      starSessSub1AAAVPN,
	      starSessSub1AAADomain,
	      starSessSub1AAAStart,
	      starSessSub1AAAStop,
	      starSessSub1AAAInterim,
	      starSessSub1AcctSessionID,
	      starSessSub1AAARadiusGroup,
	      starSessSub1AAARadiusAuthServerIPAddr,
	      starSessSub1AAARadiusAcctServerIPAddr,
	      starSessSub1NASIPAddr,
	      starSessSub1NexthopIPAddr,
	      starSessSub1ActiveInACL,
	      starSessSub1ActiveOutACL,
	      starSessSub1ECSRulebase,
	      starSessSub1InPlcyGrp,
	      starSessSub1OutPlcyGrp,
	      starSessSub1DownTrafPolState,
	      starSessSub1DownCommDataRate,
	      starSessSub1DownPeakDataRate,
	      starSessSub1DownBurstSize,
	      starSessSub1DownExceedAction,
	      starSessSub1DownViolateAction,
	      starSessSub1DownExceed,
	      starSessSub1DownViolate,
	      starSessSub1UpTrafPolState,
	      starSessSub1UpCommDataRate,
	      starSessSub1UpPeakDataRate,
	      starSessSub1UpBurstSize,
	      starSessSub1UpExceedAction,
	      starSessSub1UpViolateAction,
	      starSessSub1UpExceed,
	      starSessSub1UpViolate,
	      starSessSub1L3TunnelingState,
	      starSessSub1L3TunLocalIPAddr,
	      starSessSub1L3TunRemoteIPAddr,
	      starSessSub1AddrViaDHCP,
	      starSessSub1DHCPServName,
	      starSessSub1DHCPServIPAddr,
	      starSessSub1AccessLinkIPFrag,
	      starSessSub1IgnoreDFBit,
	      starSessSub1MIPGratARPMode,
	      starSessSub1ExtInlSrvrProc,
	      starSessSub1ExtInlSrvrIngrIPAddr,
	      starSessSub1ExtInlSrvrIngrVLANTag,
	      starSessSub1ExtInlSrvrEgrIPAddr,
	      starSessSub1ExtInlSrvrEgrVLANTag,
	      starSessSub1ExtInlSrvrVPNName,
	      starSessSub1RadAcctMode,
	      starSessSub1InBytesDropped,
	      starSessSub1OutBytesDropped,
	      starSessSub1PeakBPSTx,
	      starSessSub1PeakBPSRx,
	      starSessSub1AveBPSTx,
	      starSessSub1AveBPSRx,
	      starSessSub1SustBPSTx,
	      starSessSub1SustBPSRx,
	      starSessSub1PeakPPSTx,
	      starSessSub1PeakPPSRx,
	      starSessSub1AvePPSTx,
	      starSessSub1AvePPSRx,
	      starSessSub1SustPPSTx,
	      starSessSub1SustPPSRx,
	      starSessSub1ActivePct,
	      starSessSub1IPv4BadHdr,
	      starSessSub1IPv4TtlExceeded,
	      starSessSub1IPv4FragSent,
	      starSessSub1IPv4FragFail,
	      starSessSub1IPv4InACLDrop,
	      starSessSub1IPv4OutACLDrop,
	      starSessSub1IPv4InCSSDownDrop,
	      starSessSub1IPv4OutCSSDownDrop,
	      starSessSub1IPv4OutXOFFDropPkt,
	      starSessSub1IPv4OutXOFFDropByte,
	      starSessSub1IPv4SrcViol,
	      starSessSub1IPv4ProxyDNSRedir,
	      starSessSub1IPv4SrcProxyDNSPThru,
	      starSessSub1IPv4ProxyDNSDrop,
	      starSessSub1IPv4SrcViolNoAcct,
	      starSessSub1IPv4SrcViolIgnored,
	      starSessSub1ExtInlSrvrTxPkt,
	      starSessSub1ExtInlSrvrRxPkt,
	      starSessSub1IPv4ICMPDropPkt,
	      starSessSub1TunnelType,
	      starSessSub1IPSECTunDownDropPkt,
	      starSessSub1IPSECFlowID,
	      starSessSub1DormancyTotal,
	      starSessSub1HandoffTotal,
	      starSessSub1AccessFlows,
	      starSessSub1TFT,
	      starSessSub1NASPort,
	      starSessSub1AcctSessionID,
	      starSessSub1CorrID,
	      starSessSub1L2TPPeerIPAddr,
	      starSessSub1IPv4EarlyPDURecv,
	      --
	      starIPSECContextName,
              starIPSECGroupName,
              starIPSECTunLocalIpAddr,
              starIPSECTunRemoteIpAddr,
	      starIPSECPolicyName,
	      starIPSECDynPolicyType,
	      starIPSECDynPolicyPayloadType,
	      starIPSECLocalGateway,
	      starIPSECRemoteGateway,
	      -- SIPRoute
              starSIPRouteVpnName,
              starSIPRouteVmgName,
              starSIPRouteAsName,
              starSIPRouteDestPartyNum,
              starSIPRouteReqNum,
	      -- SIPRouteServer
              starSIPRouteServerVpnName,
              starSIPRouteServerVmgName,
              starSIPRouteServerAsName,
              starSIPRouteServerIpAddr,
	      -- VIMService
              starVIMServiceVpnName,
              starVIMServiceFMDMaxCallRate,
	      starVIMServiceFMDContinuousLoadCount,
	      -- GSS
	      starGSSClusterName,
	      starGSSClusterNodeName,
	      starGSSClusterRgName,
	      starGSSClusterRsName,
	      starGSSClusterNodeState,
	      starGSSClusterPrevOnlineNode,
	      starGSSClusterFromNode,
	      starGSSClusterToNode,
	      starGSSDiskPath,
	      starGSSTransportPath,
	      starGSSIPMPGroupName,
	      starGSSInterfaceName,
              -- RP Service Option
	      starRPServiceOptionCalls,
	      -- PCF Status
	      starPCFStatVpnName,
	      starPCFStatRxPkts,
	      starPCFStatTxPkts,
	      starPCFStatRxBytes,
	      starPCFStatTxBytes,
	      starPCFStatTotalSessions,
	      starPCFStatCurrentSessions,
	      starPCFStatCurrentActiveSessions,
	      starPCFStatCurrentDormantSessions,
	      starPCFStatCurrentSIPConnected,
	      starPCFStatCurrentMIPConnected,
	      starPCFStatCurrentPMIPConnected,
	      starPCFStatCurrentL2TPLACConnected,
	      starPCFStatCurrentOtherConnected,
	      -- PCF Service Stats
	      starPCFVpnID,
              starPCFVpnName,
	      starPCFServName,
              starPCFRrqRcvd,
              starPCFRrqAccepted,
              starPCFRrqDenied,
              starPCFRrqDiscarded,
              starPCFInitialRrqRcvd,
              starPCFInitialRrqAccepted,
              starPCFIntraPDSNActiveHORrqAccepted,
              starPCFIntraPDSNDormantHORrqAccepted,
              starPCFInterPDSNHORrqAccepted,
              starPCFInitialRrqDenied,
              starPCFInitialRrqDiscarded,
              starPCFRenewRrqRcvd,
              starPCFRenewRrqAccepted,
              starPCFRenewActiveRrqAccepted,
              starPCFRenewDormantRrqAccepted,
              starPCFRenewRrqDenied,
              starPCFRenewRrqDiscarded,
              starPCFDeregRrqRcvd,
              starPCFDeregRrqAccepted,
              starPCFDeregDormantRrqAccepted,
              starPCFDeregRrqDenied,
              starPCFDeregRrqDiscarded,
              starPCFIntraPDSNActiveAnidHORrqAccepted,
              starPCFIntraPDSNDormantAnidHORrqAccepted,
	      starPCFDeniedUnSpeReason,
              starPCFDeniedAdmProh,
              starPCFDeniedInsufResource,
              starPCFDeniedMobNodeAuthFail,
              starPCFDeniedIdentMismatch,
              starPCFDeniedPoorFormedReq,
              starPCFDeniedUnknownPDSNAddr,
              starPCFDeniedRevTunnelUnavail,
              starPCFDeniedRevTunnelRequire,
              starPCFDeniedUnrecogVendorId,
              starPCFDeniedSessionClosed,
              starPCFDeniedBsnSessionInfoUnavail,
              starPCFRegUpdTransmitted,
              starPCFRegUpdAccepted,
              starPCFRegUpdateRpLifetimeExpiry,
              starPCFRegUpdateUpperLayerIntiated,
              starPCFRegUpdateOtherReason,
              starPCFRegUpdateHORelease,
              starPCFRegUpdateSessmgrDied,
              starPCFAuxA10ConnectionsSetup,
              starPCFSessionsDenied,
              starPCFSessionsInit,
              starPCFSessionsReneg,
              starPCFDiscLcpRemote,
              starPCFDiscRpRemote,
              starPCFDiscRpLocal,
              starPCFDiscMaxIpcpRetr,
              starPCFDiscMaxIpv6cpRetr,
              starPCFDiscMaxLcpRetr,
              starPCFDiscAuthFail,
              starPCFDiscSessSetupTimeout,
              starPCFDiscFlowAddFail,
              starPCFDiscInvDestContext,
              starPCFDiscLcpOptFail,
              starPCFDiscIpcpOptFail,
              starPCFDiscIpv6cpOptFail,
              starPCFDiscNoRemIpAddr,
              starPCFDiscDetectionFail,
              starPCFDiscMisc,
              starPCFCurrentSessions,
              starPCFSessionsSetup,
              starPCFSessionsRelsese,
              starPCFCurrentRevaSessions,
              starPCFRevaSessionsSetup,
              starPCFRevaSessionsRelsese, 
	      -- PDIF System
	      starPDIFSysStatus,
	      starPDIFSysNumService,
	      starPDIFSysSessCurrent,
	      starPDIFSysSessCurrActive,
	      starPDIFSysSessCurrDormant,
	      starPDIFSysSessTtlSetup,
	      starPDIFSysChildSACurrent,
	      -- PDIF Service
	      starPDIFVpnID,
	      starPDIFVpnName,
	      starPDIFServName,
	      starPDIFStatus,
	      starPDIFSessCurrent,
	      starPDIFSessRemain,
	      starPDIFSessCurrentActive ,
	      starPDIFSessCurrentDormant ,
	      starPDIFSessCurrentIpv6Active,
	      starPDIFSessCurrentIpv6Dormant,
	      starPDIFSessCurrentIpv4Active,
	      starPDIFSessCurrentIpv4Dormant,
	      starPDIFBindIpAddress,
	      starPDIFBindIpPort,
	      starPDIFBindSlot,
	      starPDIFBindPort,
              -- SGSN Service
	      starSessSGSNVpnName,
	      starSessSGSNServName,
	      starSessSGSNMcc,
	      starSessSGSNMnc,
	      starSessSGSNRncId,
	      starSessSGSNHlrNum,
              -- SS7Rd
	      starSS7Pc,
	      starSS7M3UAPsId,
	      starSS7M3UAPspId,
	      starSS7MTP3LinkSetId,
	      starSS7MTP3LinkId,
	      starSS7SCTPSelfAddr,
	      starSS7SCTPPeerAddr,
	      starSS7SCTPSelfPort,
	      starSS7SCTPPeerPort,
              --SCCPNw
	      starSccpSsn,
              --SGTPServ
	      starSGTPVpnName,
	      starSGTPServName,
	      starSGTPSelfAddr,
	      starSGTPPeerAddr,
	      starSGTPSelfPort,
	      starSGTPPeerPort,
	      --IPMS
	      starIPMSServerVpnName,
	      --Certs
	      starCertExpiryTime,
	      starCertIssuer,
	      --Files
	      starFileApplication,
	      --FTP Servers
	      starFTPServVpnName,
              ---CSCF Peer Server
              starCSCFPeerServerVpnName,
              starCSCFPeerServerSvcName,
              starCSCFPeerServerListName,
              starCSCFPeerServerName,
	      starCSCFPeerServerState,
	      -- SDH/E1
	      starSDHOperState,
	      starSDHPathOperState,
	      starE1TribOperStateLOP,
	      starE1TribOperState,
	      starFractE1TribTimeslots,
              --GPRSServ
              starGPRSNsvci,
              starGPRSBvci,
	      --Storage
	      starStorageDeviceType,
	      -- PDG System
	      starPDGSysStatus,
	      starPDGSysNumService,
	      starPDGSysSessCurrent,
	      starPDGSysSessCurrActive,
	      starPDGSysSessCurrDormant,
	      starPDGSysSessTtlSetup,
	      starPDGSysChildSACurrent,
	      -- PDG Service
	      starPDGVpnID,
	      starPDGVpnName,
	      starPDGServName,
	      starPDGStatus,
	      starPDGSessCurrent,
	      starPDGSessRemain,
	      starPDGSessCurrentActive ,
	      starPDGSessCurrentDormant ,
	      starPDGSessCurrentIpv6Active,
	      starPDGSessCurrentIpv6Dormant,
	      starPDGSessCurrentIpv4Active,
	      starPDGSessCurrentIpv4Dormant,
	      starPDGBindIpAddress,
	      starPDGBindIpPort,
	      starPDGBindSlot,
	      starPDGBindPort,
              --EGTPServ
	      -- PDG System
	      starPDGSysStatus,
	      starPDGSysNumService,
	      starPDGSysSessCurrent,
	      starPDGSysSessCurrActive,
	      starPDGSysSessCurrDormant,
	      starPDGSysSessTtlSetup,
	      starPDGSysChildSACurrent,
	      -- PDG Service
	      starPDGVpnID,
	      starPDGVpnName,
	      starPDGServName,
	      starPDGStatus,
	      starPDGSessCurrent,
	      starPDGSessRemain,
	      starPDGSessCurrentActive ,
	      starPDGSessCurrentDormant ,
	      starPDGSessCurrentIpv6Active,
	      starPDGSessCurrentIpv6Dormant,
	      starPDGSessCurrentIpv4Active,
	      starPDGSessCurrentIpv4Dormant,
	      starPDGBindIpAddress,
	      starPDGBindIpPort,
	      starPDGBindSlot,
	      starPDGBindPort,
              --EGTPServ
	      starEGTPVpnName,
	      starEGTPServName,
	      starEGTPInterfaceType,
	      starEGTPSelfPort,
	      starEGTPSelfAddr,
	      starEGTPPeerPort,
	      starEGTPPeerAddr,
	      starEGTPPeerOldRstCnt,
	      starEGTPPeerNewRstCnt,
	      starEGTPPeerSessCnt,
	      starEGTPPeerOldRstCnt,
	      starEGTPFailureReason,
              starLicenseKey,
              starLicenseExpiryDate,
              starLicenseDaysRemaining,
              starLicenseDaysAfterExpiry, 
	      -- FNG System
	      starFNGSysStatus,
	      starFNGSysNumService,
	      starFNGSysSessCurrent,
	      starFNGSysSessCurrActive,
	      starFNGSysSessCurrDormant,
	      starFNGSysSessTtlSetup,
	      starFNGSysChildSACurrent,
	      -- FNG Service
	      starFNGVpnID,
	      starFNGVpnName,
	      starFNGServName,
	      starFNGStatus,
	      starFNGSessCurrent,
	      starFNGSessRemain,
	      starFNGSessCurrentActive ,
	      starFNGSessCurrentDormant ,
	      starFNGSessCurrentIpv6Active,
	      starFNGSessCurrentIpv6Dormant,
	      starFNGSessCurrentIpv4Active,
	      starFNGSessCurrentIpv4Dormant,
	      starFNGBindIpAddress,
	      starFNGBindIpPort,
	      starFNGBindSlot,
	      starFNGBindPort,
	      -- MME S1 Assoc
	      starMMES1AssocVpnName,
	      starMMES1AssocServName,
	      -- MME S1 Path
	      starMMES1PathVpnName,
	      starMMES1PathServName,
	      starMMES1PathSelfAddr,
	      starMMES1PathSelfPort,
	      starMMES1PathPeerAddr,
	      starMMES1PathPeerPort,
        --SPR Server
        starSPRServerIpAddr,
	      -- HNBGW Service
	      starSessHNBGWVpnName,
	      starSessHNBGWServName,
	      starSessHNBGWCsNwName,
	      starSessHNBGWPsNwName,
	      starSessHNBGWSgsnPtCd,
	      starSessHNBGWMscPtCd,
	      -- HENBGW Service
	      starHENBGWServiceVpnName,
	      starHENBGWServiceServName,
	      starHENBGWServiceLogicalENBId,
	      starHENBGWServiceMMEServName,
	      starHENBGWServicePeerAddr,
	      starHENBGWServicePeerPort,
	      starHENBGWServiceTLRI,
	      -- ALCAP Service
	      starSessALCAPVpnName,
	      starSessALCAPServName,
	      starSessALCAPAAL2NodeName,
	      starSessALCAPPathId,
          -- MVG Service
	      starMVGEndpointName,
              starMVGCauseCode,
              starMVGProtocolType,
              starPCCNtfyIntfPeerName,
              -- PMIP --
              starPMIPVpnName,
              starPMIPServName,
              starPMIPSelfAddrType,
              starPMIPSelfAddr,
              starPMIPPeerAddrType,
              starPMIPPeerAddr,
              starPMIPPeerOldRstCnt,
              starPMIPPeerNewRstCnt,
              starPMIPPeerSessCnt,
              starPMIPFailureReason,
          -- CBS Service
          starCBSServiceVpnName,
          starIuBcSelfPortNum,
          starIuBcSelfIpAddr,
          starIuBcPeerPortNum,
          starIuBcPeerIpAddr,
          starIuBcTcpConnCauseStr,
          -- RLF --
          starGTPCRLFSessMgrInst,
          starGTPCRLFVPNName,
          starGTPCRLFVPNId,
          starGTPCRLFContextName,
          starGTPCRLFCurrAppTPS,
          starGTPCRLFCurrAppDelayTol
      }
    STATUS current
    DESCRIPTION
        "A collection of objects providing information about a chassis"
    ::= { starentMIBGroups 1 }

starAlertGroup OBJECT-GROUP
    OBJECTS { starMaxAlertsPerTime,
              starWindowTime,
	      starAlertSendingEnabled }
    STATUS current
    DESCRIPTION
        "A collection of objects to control the rate at which traps can be generated"
    ::= { starentMIBGroups 3 }

starAlertTrapGroup NOTIFICATION-GROUP
    NOTIFICATIONS { starAlertsDisabled,
                    starAlertsEnabled }
    STATUS current
    DESCRIPTION
        "A collection of traps related to trap thresholding"
    ::= { starentMIBGroups 4 }

starTrapGroup NOTIFICATION-GROUP
    NOTIFICATIONS { starCardTempOverheat,
	            starCardTempOK,
	            starCardRebootRequest,
	            starCardUp,
	            starCardVoltageFailure,
	            starCardRemoved,
	            starCardInserted,
	            starCardBootFailed,
	            starCardMismatch,
	            starCardPACMigrateStart,
	            starCardPACMigrateComplete,
	            starCardPACMigrateFailed,
	            starCardSPCSwitchoverStart,
	            starCardSPCSwitchoverComplete,
	            starCardSPCSwitchoverFailed,
                    starFanFailed,
	            starFanRemoved,
                    starFanInserted,
	            starCPUBusy,
	            starCPUMemoryLow,
	            starCPUMemoryFailed,
	            starCPUFailed,
	            starCPUWatchDogExpired,
	            starNPUARPPoolExhausted,
	            starPowerFilterUnitFailed,
	            starPowerFilterUnitUnavail,
	            starPowerFilterUnitAvail,
	            starAlertsDisabled,
	            starAlertsEnabled,
	            starAAAAuthServerUnreachable,
	            starAAAAuthServerReachable,
	            starAAAAuthServerMisconfigured,
	            starAAAAccServerUnreachable,
	            starAAAAccServerReachable,
	            starAAAAccServerMisconfigured,
	            starLogMsg,
	            starPDSNServiceStart,
	            starPDSNServiceStop,
	            starHAServiceStart,
	            starHAServiceStop,
	            starFAServiceStart,
	            starFAServiceStop,
	            starCLISessionStart,
	            starCLISessionEnd,
	            starCritTaskFailed,
                    starCardActive,
	            starLACServiceStart,
	            starLACServiceStop,
	            starLNSServiceStart,
	            starLNSServiceStop,
                    starCardDown,
                    starGGSNServiceStart,
                    starGGSNServiceStop,
                    starLicenseExceeded,
                    starSubscriberLimit,
                    starSessionRejectNoResource,
                    starSIPServiceStart,
                    starSIPServiceStop,
                    starVIMServiceStart,
                    starVIMServiceStop,
                    starCHATCONFServiceStart,
                    starCHATCONFServiceStop,
		    starSIPRouteNomatch,
		    starL3AddrUnreachable,
		    starSWUpgradeStart,
		    starSWUpgradeComplete,
		    starSWUpgradeAborted,
		    starBGPPeerSessionUp,
		    starBGPPeerSessionDown,
		    starSRPActive,
		    starSRPStandby,
		    starBGPPeerReachable,
		    starBGPPeerUnreachable,
		    starSRPAAAReachable,
		    starSRPAAAUnreachable,
		    starSRPSwitchoverInitiated,
		    starSRPCheckpointFailure,
		    starSRPConfigOutOfSync,
		    starSRPConfigInSync,
		    starGESwitchFailure,
		    starSIPRouteServerAvailable,
		    starSIPRouteServerUnavailable,
		    starFMDMaxCallRateReached,
		    starFMDCallRateUnderControl,
		    starStorageServerCPUBusy,
		    starStorageServerCPUNormal,
		    starStorageServerDiskSpaceLow,
		    starStorageServerDiskSpaceOK,
		    starCardSPOFAlarm,
		    starCardSPOFClear,
		    starStorageServerOldGcdrPending,
		    starStorageServerOldGcdrCleared,
		    starLoginFailure,
		    starIPSGServiceStart,
		    starIPSGServiceStop,
		    starHAUnreachable,
		    starHAReachable,
		    starASNGWServiceStart,
		    starASNGWServiceStop,
		    starTaskFailed,
		    starTaskRestart,
		    starCSCFServiceStart,
		    starCSCFServiceStop,
                    starPHSGWServiceStart,
                    starPHSGWServiceStop,
                    starPHSPCServiceStart,
                    starPHSPCServiceStop,
		    starIPSECDynTunUp,
		    starIPSECDynTunDown,
		    starHeartbeat,
		    starOverloadSystem,
		    starOverloadSystemClear,
		    starOverloadService,
		    starOverloadServiceClear,
		    starStorageServerClusterStateChange,
		    starStorageServerClusSwitchOver,
		    starStorageServerClusPathFail,
		    starStorageServerClusPathOK,
		    starStorageServerClusInterCFail,
		    starStorageServerClusInterCOK,
		    starStorageServerClusIntfFail,
		    starStorageServerClusIntfOK,
		    starStorageServerMemLow,
		    starStorageServerMemNormal,
                    starLongDurTimerExpiry,
                    starClosedRPServiceStart,
                    starClosedRPServiceStop,
                    starGtpcPathFailure,
                    starGtpuPathFailure,
                    starManagerFailure,
                    starEISServerAlive,
                    starEISServerDead,
                    starCgfAlive,
                    starCgfDead,
		    starCdrPurged,
                    starAAAArchiveStarted,
		    starIPSecNodeIpv6PeerDown,
		    starIPSecNodeIpv6PeerUp,
                    starVLRAssocDown,
                    starVLRAssocUp,
                    starVLRAllAssocDown,
                    starVLRAllAssocDownClear,
                    starVLRDown,
                    starVLRUp,
                    starStorageServerAlive,
                    starStorageServerDead,
                    starGgsnInitiatedUpdtFailed,
		    starCongestion,
		    starCongestionClear,
		    starCscfSessResourceCongestion,
		    starCscfSessResourceCongestionClear,
		    starServiceLossPTACs,
		    starServiceLossLC,
		    starServiceLossSPIO,
		    starIPSPAllAddrsFree,
		    starPCFUnreachable,
            starPCFReachable,
            starLIRcvryError,
            starLIRcvryComplete,
            starCGWServiceStart,
            starCGWServiceStop,
            starDhcpAlive,
            starDhcpDead,
		    starDhcpServiceStarted,
		    starDhcpServiceStopped,
	            starNTPPeerUnreachable,
	            starNTPSyncLost,
	            starL2TPTunnelDownPeerUnreachable,
	            starCardStandby,
	            starLicenseUnderLimit,
	            starIPSECPriTunDown,
	            starIPSECPriTunUp,
	            starIPSECSecTunDown,
	            starIPSECSecTunUp,
	            starIPSECTunSwitchFail,
	            starIPSECTunSwitchComplete,
                    starNwReachServerAlive,
                    starNwReachServerDead,
                    starStorageServerUnackedGcdrVolPurge,
                    starStorageServerUnackedGcdrFileGen,
		    starNTPPeerReachable,
		    starNTPSyncEstablished,
                    starContFiltDBError,
                    starContFiltDBErrorClear,
                    starBLDBError,
                    starBLDBErrorClear,
                    starContFiltDBUpgradeError,
                    starContFiltDBUpgradeErrorClear,
                    starBLDBUpgradeError,
                    starBLDBUpgradeErrorClear,
                    starDynPkgLoadError,
                    starDynPkgLoadErrorClear,                    
                    starDynPkgUpgradeError,
                    starDynPkgUpgradeErrorClear,
		    starPDIFServiceStart,
                    starPDIFServiceStop,
                    starSessMgrRecoveryComplete,
                    starSessMgrFlowCount,
                    starSessMgrFlowCountClear,
                    starDiameterPeerDown,
                    starDiameterPeerUp,
                    starDiameterServerUnreachable,
                    starDiameterServerReachable,
		    starDiameterCapabilitiesExchangeSuccess,
		    starDiameterCapabilitiesExchangeFailure,
        	starDiameterRlfThresholdOver,
        	starDiameterRlfThresholdGood,
			starDiameterRlfOverLimit,
                    starCDRFileRemoved,
                    starCSCFPeerServerReachable,
                    starCSCFPeerServerUnreachable,
                    starCSCFPeerServerUnavailable,
                    starCSCFPeerServerOutofService,
                    starCSCFPeerServerInService,
                    starCLIConfigMode,
                    starSGSNServiceStart,
                    starSGSNServiceStop,
                    starM3UAPCUnavailable,
                    starM3UAPCAvailable,
                    starECSTotalDNSLearntIPv4Threshold,
                    starECSTotalDNSLearntIPv4ThresholdClear,
                    starECSTotalDNSLearntIPv6Threshold,
                    starECSTotalDNSLearntIPv6ThresholdClear,
                    starM3UAPSDown,
                    starM3UAPSActive,
                    starM3UAPSPDown,
                    starM3UAPSPUp,
                    starSCCPSspRcvd,
                    starSCCPSspClear,
                    starSGSNRNCReset,
                    starSGSNHLRReset,
                    starSGSNGtpcPathFailure,
                    starSGSNGtpcPathFailureClear,
                    starSGSNGtpuPathFailure,
                    starSGSNGtpuPathFailureClear,
                    starMTP3LinkOutOfService,
                    starMTP3LinkInService,
                    starMTP3LinkSetUnAvailable,
                    starMTP3LinkSetAvailable,
                    starSCTPAssociationFail,
                    starSCTPAssociationEstablished,
                    starSCTPPathDown,
                    starSCTPPathUp,
                    starMTP3PCUnavailable,
                    starMTP3PCAvailable,
                    starSS7PCUnavailable,
                    starSS7PCAvailable,
                    starSS7PCCongested,
                    starSS7PCCongestionCleared,
                    starM3UAPSPCongested,
                    starM3UAPSPCongestionCleared,
		    starStorageFailed,
		    starRaidFailed,
		    starRaidStarted,
		    starRaidDegraded,
		    starRaidRecovered,
                    starHENBGWMMESCTPAssocDown,
		    starHENBGWMMESCTPAssocUp,
		    starHENBGWMMESCTPAllAssocDown,
		    starHENBGWMMESCTPAllAssocDownClear,
            starECSreaddressServerDown,
            starECSreaddressServerUp,
            starStorageFound,
            starStorageNotFound,
                    starThreshCPUUtilization,
                    starThreshClearCPUUtilization,
                    starThreshCPUMemory,
                    starThreshClearCPUMemory,
                    starThreshCPUCryptoCoresUtilization,
                    starThreshClearCPUCryptoCoresUtilization,
                    starThreshLicense,
                    starThreshClearLicense,
                    starThreshSubscriberTotal,
                    starThreshClearSubscriberTotal,
                    starThreshSubscriberActive,
                    starThreshClearSubscriberActive,
                    starThreshPortRxUtil,
                    starThreshClearPortRxUtil,
                    starThreshPortTxUtil,
                    starThreshClearPortTxUtil,
                    starThreshPortHighActivity,
                    starThreshClearPortHighActivity,
                    starThreshAAAAuthFail,
                    starThreshClearAAAAuthFail,
                    starThreshAAAAuthFailRate,
                    starThreshClearAAAAuthFailRate,
                    starThreshAAAAcctFail,
                    starThreshClearAAAAcctFail,
                    starThreshAAAAcctFailRate,
                    starThreshClearAAAAcctFailRate,
                    starThreshAAARetryRate,
                    starThreshClearAAARetryRate,
                    starThreshCallSetup,
                    starThreshClearCallSetup,
                    starThreshCallSetupFailure,
                    starThreshClearCallSetupFailure,
                    starThreshCallRejectNoResource,
                    starThreshClearCallRejectNoResource,
                    starThreshPacketsFilteredDropped,
                    starThreshClearPacketsFilteredDropped,
                    starThreshPacketsForwarded,
                    starThreshClearPacketsForwarded,
                    starThreshSessCPUThroughput,
                    starThreshClearSessCPUThroughput,
                    starThreshIPPoolAvail,
                    starThreshClearIPPoolAvail,
                    starThreshCPUUtilization10Sec,
                    starThreshClearCPUUtilization10Sec,
                    starThreshCPULoad,
                    starThreshClearCPULoad,
                    starThreshCPUMemUsage,
                    starThreshClearCPUMemUsage,
                    starThreshPDSNSessions,
                    starThreshClearPDSNSessions,
                    starThreshGGSNSessions,
                    starThreshClearGGSNSessions,
                    starThreshHASessions,
                    starThreshClearHASessions,
                    starThreshLNSSessions,
                    starThreshClearLNSSessions,
                    starThreshPerServicePDSNSessions,
                    starThreshClearPerServicePDSNSessions,
                    starThreshPerServicePDGSessions,
                    starThreshClearPerServicePDGSessions,
                    starThreshPerServiceGGSNSessions,
                    starThreshClearPerServiceGGSNSessions,
                    starThreshPerServiceHASessions,
                    starThreshClearPerServiceHASessions,
                    starThreshPerServiceLNSSessions,
                    starThreshClearPerServiceLNSSessions,
                    starThreshIPPoolHold,
                    starThreshClearIPPoolHold,
                    starThreshIPPoolUsed,
                    starThreshClearIPPoolUsed,
                    starThreshIPPoolRelease,
                    starThreshClearIPPoolRelease,
                    starThreshIPPoolFree,
                    starThreshClearIPPoolFree,
                    starThreshAAAAcctArchive,
                    starThreshClearAAAAcctArchive,
		    starThreshPortSpecRxUtil,
		    starThreshClearPortSpecRxUtil,
		    starThreshPortSpecTxUtil,
		    starThreshClearPortSpecTxUtil,
                    starThreshHACallSetupRate,
                    starThreshClearHACallSetupRate,
                    starThreshHASvcCallSetupRate,
                    starThreshClearHASvcCallSetupRate,
                    starThreshHASvcRegReplyError,
                    starThreshClearHASvcRegReplyError,
                    starThreshHASvcReregReplyError,
                    starThreshClearHASvcReregReplyError,
                    starThreshHASvcDeregReplyError,
                    starThreshClearHASvcDeregReplyError,
                    starThreshFASvcRegReplyError,
                    starThreshClearFASvcRegReplyError,
                    starThreshPDSNCallSetupRate,
                    starThreshClearPDSNCallSetupRate,
                    starThreshPDSNSvcCallSetupRate,
                    starThreshClearPDSNSvcCallSetupRate,
                    starThreshPDSNSvcA11RRPFailure,
                    starThreshClearPDSNSvcA11RRPFailure,
                    starThreshPDSNSvcA11RRQMsgDiscard,
                    starThreshClearPDSNSvcA11RRQMsgDiscard,
                    starThreshPDSNSvcA11RACMsgDiscard,
                    starThreshClearPDSNSvcA11RACMsgDiscard,
                    starThreshPDSNSvcA11PPPSendDiscard,
                    starThreshClearPDSNSvcA11PPPSendDiscard,
		    starThreshAAAMgrQueue,
		    starThreshClearAAAMgrQueue,
            starThreshAAAAcctArchiveQueue1,
            starThreshClearAAAAcctArchiveQueue1,
            starThreshAAAAcctArchiveQueue2,
            starThreshClearAAAAcctArchiveQueue2,
            starThreshAAAAcctArchiveQueue3,
            starThreshClearAAAAcctArchiveQueue3,
            starThreshDnsLookupSrvFailure,
            starThreshClearDnsLookupSrvFailure,
		    starThreshCPUOrbsWarn,
		    starThreshClearCPUOrbsWarn,
		    starThreshCPUOrbsCritical,
		    starThreshClearCPUOrbsCritical,
		    starThreshRPSetupFailRate,
		    starThreshClearRPSetupFailRate,
		    starThreshPPPSetupFailRate,
		    starThreshClearPPPSetupFailRate,
		    starThreshStorageUtilization,
		    starThreshClearStorageUtilization,
		    starThreshDCCAProtocolErrors,
		    starThreshClearDCCAProtocolErrors,
		    starThreshDCCABadAnswers,
		    starThreshClearDCCABadAnswers,
		    starThreshDCCAUnknownRatingGroup,
		    starThreshClearDCCAUnknownRatingGroup,
		    starThreshDCCARatingFailed,
		    starThreshClearDCCARatingFailed,
		    starThreshIPSECIKERequests,
		    starThreshClearIPSECIKERequests,
		    starThreshIPSECIKEFailures,
		    starThreshClearIPSECIKEFailures,
		    starThreshIPSECIKEFailRate,
		    starThreshClearIPSECIKEFailRate,
		    starThreshIPSECTunSetup,
		    starThreshClearIPSECTunSetup,
		    starThreshIPSECTunEstabl,
		    starThreshClearIPSECTunEstabl,
		    starThreshIPSECCallReqRej,
		    starThreshClearIPSECCallReqRej,
                    starThreshEPDGIKEV2SetupAttempts,
                    starThreshClearEPDGIKEV2SetupAttempts,
                    starThreshEPDGIKEV2AuthFailures,
                    starThreshClearEPDGIKEV2AuthFailures,
                    starThreshEPDGIKEV2SetupSuccess,
                    starThreshClearEPDGIKEV2SetupSuccess,
                    starThreshEPDGIKEV2SetupFailure,
                    starThreshClearEPDGIKEV2SetupFailure,
                    starThreshEPDGIKEV2SetupFailureRate,
                    starThreshClearEPDGIKEV2SetupFailureRate,
		    starThreshCSCFSvcRouteFailure,
		    starThreshClearCSCFSvcRouteFailure,
        starThreshCSCFSvcRegRcvdRate, 
        starThreshClearCSCFSvcRegRcvdRate,
        starThreshCSCFSvcTotalActiveReg, 
        starThreshClearCSCFSvcTotalActiveReg,
        starThreshCSCFSvcInviteRcvdRate,
        starThreshClearCSCFSvcInviteRcvdRate,
        starThreshCSCFSvcTotalActiveCalls,
        starThreshClearCSCFSvcTotalActiveCalls,
        starThreshCSCFSvcTotalCallFailure,
        starThreshClearCSCFSvcTotalCallFailure, 
        starThreshCSCFSvcErrorNoResource,
        starThreshClearCSCFSvcErrorNoResource,
        starThreshCSCFSvcErrorTcp,
        starThreshClearCSCFSvcErrorTcp,
        starThreshCSCFSvcErrorPresence,
        starThreshClearCSCFSvcErrorPresence,
        starThreshCSCFSvcErrorRegAuth,
        starThreshClearCSCFSvcErrorRegAuth,
		    starThreshContFiltRating,
		    starThreshClearContFiltRating,
		    starThreshContFiltBlock,
		    starThreshClearContFiltBlock,
                    starThreshCDRFileSpace,
                    starThreshClearCDRFileSpace,
                    starThreshEDRFileSpace,
                    starThreshClearEDRFileSpace,
		    starThreshPDIFCurrSess,
		    starThreshClearPDIFCurrSess,
		    starThreshPDIFCurrActSess,
		    starThreshClearPDIFCurrActSess,
		    starThreshCDRFlowControl,
		    starThreshSGSNSessions,
		    starThreshClearSGSNSessions,
		    starThreshPerServiceSGSNSessions,
	            starThreshClearPerServiceSGSNSessions,
	            starThreshSGSNPdpSessions,
	            starThreshClearSGSNPdpSessions,
	            starThreshPerServiceSGSNPdpSessions,
	            starThreshClearPerServiceSGSNPdpSessions,
		    starThreshClearCDRFlowControl,
                    starThreshASNGWSessTimeout,
                    starThreshClearASNGWSessTimeout,
                    starThreshASNGWSessSetupTimeout,
                    starThreshClearASNGWSessSetupTimeout,
                    starThreshASNGWAuthFail,
                    starThreshClearASNGWAuthFail,
                    starThreshASNGWMaxEAPRetry,
                    starThreshClearASNGWMaxEAPRetry,
                    starThreshASNGWNWEntryDenial,
                    starThreshClearASNGWNWEntryDenial,
                    starThreshASNGWHandoffDenial,
                    starThreshClearASNGWHandoffDenial,
                    starThreshPHSGWSessTimeout,
                    starThreshClearPHSGWSessTimeout,
                    starThreshPHSGWSessSetupTimeout,
                    starThreshClearPHSGWSessSetupTimeout,
                    starThreshPHSGWAuthFail,
                    starThreshClearPHSGWAuthFail,
                    starThreshPHSGWMaxEAPRetry,
                    starThreshClearPHSGWMaxEAPRetry,
                    starThreshPHSGWNWEntryDenial,
                    starThreshClearPHSGWNWEntryDenial,
                    starThreshPHSGWHandoffDenial,
                    starThreshClearPHSGWHandoffDenial,
                    starThreshASNGWSessions,
	            starThreshClearASNGWSessions,
	            starThreshPerServiceASNGWSessions,
	            starThreshClearPerServiceASNGWSessions,
                    starThreshPHSPCSessSetupTimeout,
                    starThreshClearPHSPCSessSetupTimeout,
                    starThreshPHSPCSleepModeTimeout,
                    starThreshClearPHSPCSleepModeTimeout,
                    starThreshPHSPCSmEntryDenial,
                    starThreshClearPHSPCSmEntryDenial,
                    starThreshSGWSessions,
		    starThreshClearSGWSessions,
                    starThreshPGWSessions,
		    starThreshClearPGWSessions,
		    starThreshLMASessions,
                    starThreshClearLMASessions,
		    starThreshMAGSessions,
		    starThreshClearMAGSessions,
		    starThreshHSGWSessions,
		    starThreshClearHSGWSessions,
                    starThreshHENBGWHenbSessions,
		    starThreshClearHENBGWHenbSessions,
                    starThreshHENBGWUeSessions,
		    starThreshClearHENBGWUeSessions,
		    starThreshHENBGWPagingMessages,
		    starThreshClearHENBGWPagingMessages,
                    starThreshPHSGWEAPOLAuthFailure,
                    starThreshClearPHSGWEAPOLAuthFailure,
                    starThreshPHSGWMaxEAPOLRetry,
                    starThreshClearPHSGWMaxEAPOLRetry,
		    starThreshFWDosAttack,
		    starThreshClearFWDosAttack,
		    starThreshFWDropPacket,
		    starThreshClearFWDropPacket,
		    starThreshFWDenyRule,
		    starThreshClearFWDenyRule,
		    starThreshFWNoRule,
		    starThreshClearFWNoRule,
		    starSRPConnDown,
		    starSRPConnUp,		    
		    starThreshNATPortChunks,
                    starThreshClearNATPortChunks,
		    starThreshClearFWDosAttack,
		    starThreshFWDropPacket,
		    starThreshClearFWDropPacket,
		    starThreshGPRSSessions,
		    starThreshClearGPRSSessions,
		    starThreshPerServiceGPRSSessions,
		    starThreshClearPerServiceGPRSSessions,
		    starThreshGPRSPdpSessions,
		    starThreshClearGPRSPdpSessions,
		    starThreshPerServiceGPRSPdpSessions,
		    starThreshClearPerServiceGPRSPdpSessions,
		    starThreshFWDenyRule,
		    starThreshClearFWDenyRule,
		    starThreshFWNoRule,
		    starThreshClearFWNoRule,
                    starThreshBGPRoutes,
                    starThreshClearBGPRoutes,
                    starThreshNPUUtilization,
                    starThreshClearNPUUtilization,
                    starThreshEPDGCurrSess,
                    starThreshClearEPDGCurrSess,
		    starSRPConnDown,
		    starSRPConnUp,
		    starPortDown,
		    starPortUp,
		    starOSPFNeighborDown,
		    starOSPFNeighborFull,
                    starBSReachable,
                    starBSUnreachable,
		    starSystemStartup,
		    starASNPCServiceStart,
		    starASNPCServiceStop,
		    starDiameterIpv6PeerDown,
		    starDiameterIpv6PeerUp,
		    starIPMSServerUnreachable,
		    starIPMSServerReachable,
		    starCertShortLifetime,
		    starCertExpired,
		    starCertValid,
		    starFTPPushFail,
		    starFTPServSwitch,
		    starSDHSectionDown,
		    starSDHSectionUp,
		    starSDHPathHopDown,
		    starSDHPathHopUp,
		    starSDHLopDown,
		    starSDHLopUp,
		    starSDHE1TribDown,
		    starSDHE1TribUp,
		    starSDHFractE1LMIDown,
		    starSDHFractE1LMIUp,
		    starGPRSServiceStart,
		    starGPRSServiceStop,
		    starGPRSNseDown,
		    starGPRSNseUp,
		    starGPRSNsvcDown,
		    starGPRSNsvcUp,
		    starGPRSBvcDown,
		    starGPRSBvcUp,
		    starPDGServiceStart,
		    starPDGServiceStop,
		    starThreshPDGCurrSess,
		    starThreshClearPDGCurrSess,
		    starThreshPDGCurrActSess,
		    starThreshClearPDGCurrActSess,
		    starPGWServiceStart,
		    starPGWServiceStop,
		    starSGWServiceStart,
		    starSGWServiceStop,
		    starEGTPServiceStart,
		    starEGTPServiceStop,
		    starLMAServiceStart,
		    starLMAServiceStop,
		    starMAGServiceStart,
		    starMAGServiceStop,
		    starMMEServiceStart,
		    starMMEServiceStop,
		    starHSGWServiceStart,
		    starHSGWServiceStop,
                    starCPUBusyClear,
                    starCPUMemoryLowClear,
                    starManagerRestart,
                    starConfigurationUpdate,
	            starFNGServiceStart,
         	    starFNGServiceStop,
	            starThreshFNGCurrSess,
        	    starThreshClearFNGCurrSess,
		    starThreshFNGCurrActSess,
		    starThreshClearFNGCurrActSess,
		    starEgtpcPathFailure,
		    starEgtpcPathFailureClear,
		    starEgtpuPathFailure,
		    starEgtpuPathFailureClear,
		    starServiceLossSPIOClear,
                    starHNBGWServiceStart,
                    starHNBGWServiceStop,
                    starSystemReboot,
                    starServiceLossPTACsClear,
                    starServiceLossLCClear,
                    starOSPFv3NeighborDown,
                    starOSPFv3NeighborFull,
                    starLicenseAboutToExpire,
                    starLicenseExpired,
                    starStorageServerCDRLoss,
                    starPCCPolicyServiceStart,
                    starPCCPolicyServiceStop,
                    starPCCQuotaServiceStart,
                    starPCCQuotaServiceStop,
                    starPCCAFServiceStart,
                    starPCCAFServiceStop,
                    starThreshPCCPolicySessions,
                    starThreshClearPCCPolicySessions,
                    starThreshPerServicePCCPolicySessions,
                    starThreshClearPerServicePCCPolicySessions,
                    starThreshPCCQuotaSessions,
                    starThreshClearPCCQuotaSessions,
                    starThreshPerServicePCCQuotaSessions,
                    starThreshClearPerServicePCCQuotaSessions,
                    starThreshPCCAFSessions,
                    starThreshClearPCCAFSessions,
                    starThreshPerServicePCCAFSessions,
                    starThreshClearPerServicePCCAFSessions,
                    starSPRServerUnreachable,
                    starSPRServerReachable,
                    starGSServiceStart,
                    starGSServiceStop,
                    starMAPServiceStart,
                    starMAPServiceStop,
                    starIUPSServiceStart,
                    starIUPSServiceStop,
                    starSGTPServiceStart,
                    starSGTPServiceStop,
		    starEPDGServiceStart,
		    starEPDGServiceStop,
		    starSxServiceStart,
		    starSxServiceStop,
		    starUplaneServiceStart,
		    starUplaneServiceStop,
                    starApsCommandSuccess,
                    starApsCommandFailure,
                    starApsSwitchSuccess,
                    starApsSwitchFailure,
                    starApsModeMismatch,
                    starApsChannelMismatch,
                    starApsByteMismatch,
                    starApsFeProtLineFailure,
                    starApsLossOfRedundancy,
                    starApsLossOfRedundancyClear,
		    starSGSServiceStart,
		    starSGSServiceStop,
	            starSgsnGnMsgDelay,
        	    starSgsnGnMsgDelayClear,
		    starBNGServiceStart,
		    starBNGServiceStop,
		    starHenbgwAccessServiceStart,
		    starHenbgwAccessServiceStop,
		    starHenbgwNetworkServiceStart,
		    starHenbgwNetworkServiceStop,
		    starThreshDnsLookupFailure,
		    starThreshClearDnsLookupFailure,
		    starThreshDiameterRetryRate,
		    starThreshClearDiameterRetryRate,
		    starMMES1AssocFail,
		    starMMES1AssocSetup,
		    starMMES1PathFail,
		    starMMES1PathSetup,
		    starHNBGWSGSNRanapReset,
		    starHNBGWMSCRanapReset,
		    starALCAPNodeReset,
		    starALCAPPathReset,
		    starALCAPPathBlock,
		    starALCAPPathUnBlock,
		    starThreshHNBGWHnbSess,
		    starThreshClearHNBGWHnbSess,
		    starThreshHNBGWUeSess,
		    starThreshClearHNBGWUeSess,
		    starThreshHNBGWIuSess,
		    starThreshClearHNBGWIuSess,
            starMVGPeerDown,
            starMVGPeerUp,
		    starThreshSystemCapacity,
		    starThreshClearSystemCapacity,
                    starThreshClearHNBGWIuSess,
                    starThreshTpoRtoTimeout,
                    starThreshClearTpoRtoTimeout,
                    starThreshTpoDnsFailure,
                    starThreshClearTpoDnsFailure,
                    starThreshTpoLowCompressionGain,
                    starThreshClearTpoLowCompressionGain,
                    starSGSNRNCNoResetAck,
                    starThreshSAEGWSessions,
                    starThreshClearSAEGWSessions,
                    starPCCNtfyIntfPeerUnreachable,
                    starPCCNtfyIntfPeerReachable,
                    starIPSecNodePeerDown,
                    starIPSecNodePeerUp,
                    starThreshCardTemperatureNearPowerOffLimit,
                    starThreshClearCardTemperaturePowerOffLimit,
                    starEnhancedCongestion,
                    starEnhancedCongestionClear,
                    starChassisCrashListFull,
                    starChassisStartupTimeout,
                    starSessMgrCSCFServiceRecoveryComplete,
                    starNPDBConnectionDown,
                    starNPDBConnectionUp,
                    starCdrHDDStart,
                    starCdrStreamingStart,
                    starCdrStreamingComplete,
                    starMMENewConnectionsDisallowed,
                    starMMENewConnectionsAllowed,
                    starSAMOGServiceStart,
                    starSAMOGServiceStop,
                    starCardSwitchoverStart,
                    starCardSwitchoverComplete,
                    starCardSwitchoverFailed,
                    starCardMigrateStart,
                    starCardMigrateComplete,
                    starCardMigrateFailed,
                    starPMIPPathFailure,
                    starPMIPPathFailureClear,
		    starHENBGWMMESCTPAssocDestAddrDown,
                    starHENBGWMMESCTPAssocDestAddrUp,
		    starMRMEServiceStart,
		    starMRMEServiceStop,
		    starThreshPerServiceSAMOGSessions,
		    starThreshClearPerServiceSAMOGSessions,	
		    starSLSServiceStart,
		    starSLSServiceStop,
                    starESMLCAssocDown,
                    starESMLCAssocUp,
                    starESMLCAllAssocDown,
		    starESMLCAllAssocDownClear,
		    starSBCServiceStart,
		    starSBCServiceStop,
                    starCBCAssocDown,
                    starCBCAssocUp,
                    starCBCBufSizeExceeded,
                    starBFDSessUp,
                    starBFDSessDown,
                    starThreshFabricEGQDiscards,
		    starThreshNATPktDrop,
		    starThreshClearNATPktDrop,
                    starThreshClearFabricEGQDiscards,
                    starHENBGWMMEOverloadStart,
		    starHENBGWMMEOverloadStop,
		    starBGPPeerSessionIPv6Up,
		    starBGPPeerSessionIPv6Down,
                    starMMEEMBMSServiceStart,
		    starMMEEMBMSServiceStop,
                    starMCEAssocDown,
		    starMCEAssocUp,
            starIuBcTcpConnDown,
            starIuBcTcpConnUp,
                    starGILANServiceStart,
                    starGILANServiceStop,
        starGTPCRLFOverThreshold,
        starGTPCRLFOverLimit,
        starGTPCRLFOverThresholdClear,
        starGTPCRLFOverLimitClear,
		    starIFTaskHealthFailure,
		    starNeedADCLicense,
		    starNeedADCLicenseClear,
		    starADCLicenseAboutToExpire,
            starADCLicenseExpired,
            starSxPathFailure,
            starSxPathFailureClear,
            starChassisThroughputOver,
            starChassisThroughputOverClear,
            starChassisThroughputWarn,
            starChassisThroughputWarnClear,
            starIFTaskBootConfigApplied
                }
    STATUS current
    DESCRIPTION
        "A collection of objects which represent required notifications."
    ::= { starentMIBGroups 5 }

starTrapObsoleteGroup NOTIFICATION-GROUP
    NOTIFICATIONS { starCardReset,
		    starCardFailed,
	            starCardRCCFailed,
	            starCardSWFailed,
	            starCardFailureLEDOn,
	            starCardFailureLEDOff,
	            starLogThreshold,
	            starThreshASNGWR6InvNai,
	            starThreshClearASNGWR6InvNai
                   }
    STATUS obsolete
    DESCRIPTION
	"A collection of objects which represent obsolete notifications."
    ::= { starentMIBGroups 6 }

starChassisObsoleteGroup OBJECT-GROUP
    OBJECTS { starRPRegAcceptIntraPDSN,
              starSlotVoltage1dot5,
              starSlotVoltage1dot5LowThresh,
              starSlotVoltage1dot5HighThresh,
              starSlotVoltage1dot8,
              starSlotVoltage1dot8LowThresh,
              starSlotVoltage1dot8HighThresh,
              starSlotVoltage2dot5,
              starSlotVoltage2dot5LowThresh,
              starSlotVoltage2dot5HighThresh,
              starSlotVoltage3dot3,
              starSlotVoltage3dot3LowThresh,
              starSlotVoltage3dot3HighThresh,
              starSlotVoltage5dot0,
              starSlotVoltage5dot0LowThresh,
              starSlotVoltage5dot0HighThresh
            }
    STATUS obsolete
    DESCRIPTION
	"A collection of objects which are obsolete."
    ::= { starentMIBGroups 7 }
END
