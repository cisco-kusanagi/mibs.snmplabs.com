--			Ascend mibipsecpolicy MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBIPSECPOLICY-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibmibProfIpsecPolicy  OBJECT IDENTIFIER ::= { configuration 167}

	-- The mibmibProfIpsecPolicy table
	--
	-- This table contains parameters for the mibmibProfIpsecPolicy profile
	--

    mibmibProfIpsecPolicyTable	OBJECT-TYPE
	SYNTAX		SEQUENCE OF MibmibProfIpsecPolicyEntry
	ACCESS		not-accessible
	STATUS		mandatory
	DESCRIPTION	"A list of mibmibProfIpsecPolicy profile entries."
	::= { mibmibProfIpsecPolicy 1 }

    mibmibProfIpsecPolicyEntry	OBJECT-TYPE
	SYNTAX		MibmibProfIpsecPolicyEntry
	ACCESS		not-accessible
	STATUS		mandatory
	DESCRIPTION	"A mibmibProfIpsecPolicy entry containing objects that
			 maps to the parameters of mibmibProfIpsecPolicy profile."
	INDEX		{ mibProfIpsecPolicy-PolicyName }
	::= { mibmibProfIpsecPolicyTable 1 }

    MibmibProfIpsecPolicyEntry ::=
	SEQUENCE {
	    mibProfIpsecPolicy-PolicyName
		DisplayString,
	    mibProfIpsecPolicy-FilterName
		DisplayString,
	    mibProfIpsecPolicy-KeyManagement
		INTEGER,
	    mibProfIpsecPolicy-IpsecProposals
		DisplayString,
	    mibProfIpsecPolicy-PrimaryTunnelAddress
		IpAddress,
	    mibProfIpsecPolicy-SecondaryTunnelAddress
		IpAddress,
	    mibProfIpsecPolicy-Action-o
		INTEGER
	}

    mibProfIpsecPolicy-PolicyName	OBJECT-TYPE
	SYNTAX	DisplayString
	ACCESS	read-only
	STATUS	mandatory
	DESCRIPTION	"The name of this IPSEC Policy."
	::= { mibmibProfIpsecPolicyEntry 1 }

    mibProfIpsecPolicy-FilterName	OBJECT-TYPE
	SYNTAX	DisplayString
	ACCESS	read-write
	STATUS	mandatory
	DESCRIPTION	"The name of the Filter containing the IPSec selectors for this Policy. Current IPSec policy will be applied only to the traffic that the filter forwards. Traffic not forwarded by the filter will not necessarily be dropped, it may have a chance to match another policy."
	::= { mibmibProfIpsecPolicyEntry 2 }

    mibProfIpsecPolicy-KeyManagement	OBJECT-TYPE
	SYNTAX	INTEGER {
		    manual (1),
		    ike (2)
		}
	ACCESS	read-write
	STATUS	mandatory
	DESCRIPTION	"This determines whether static key or dynamic key (IKE) is used for this policy."
	::= { mibmibProfIpsecPolicyEntry 3 }

    mibProfIpsecPolicy-IpsecProposals	OBJECT-TYPE
	SYNTAX	DisplayString
	ACCESS	read-write
	STATUS	mandatory
	DESCRIPTION	"The name of the IPSEC Protection Suite profile to be used for IPSec SAs negotiation for the traffic encompassed by this policy. This may be a unique proposal or the first element of a list of proposals."
	::= { mibmibProfIpsecPolicyEntry 4 }

    mibProfIpsecPolicy-PrimaryTunnelAddress	OBJECT-TYPE
	SYNTAX	IpAddress
	ACCESS	read-write
	STATUS	mandatory
	DESCRIPTION	"IP address of the primary IPSEC peer (tunnel mode only)."
	::= { mibmibProfIpsecPolicyEntry 5 }

    mibProfIpsecPolicy-SecondaryTunnelAddress	OBJECT-TYPE
	SYNTAX	IpAddress
	ACCESS	read-write
	STATUS	mandatory
	DESCRIPTION	"IP address of the secondary IPSEC peer (tunnel mode only)."
	::= { mibmibProfIpsecPolicyEntry 6 }

    mibProfIpsecPolicy-Action-o	OBJECT-TYPE
	SYNTAX	INTEGER {
		    noAction (1),
		    createProfile (2),
		    deleteProfile (3)
		}
	ACCESS	read-write
	STATUS	mandatory
	DESCRIPTION	""
	::= { mibmibProfIpsecPolicyEntry 7 }

END
