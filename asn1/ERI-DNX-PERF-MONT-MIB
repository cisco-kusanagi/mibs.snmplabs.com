ERI-DNX-PERF-MONT-MIB DEFINITIONS ::= BEGIN

IMPORTS
	MODULE-IDENTITY, OBJECT-IDENTITY, OBJECT-TYPE, 
	Integer32, Gauge32
		FROM SNMPv2-SMI
    DisplayString
        FROM SNMPv2-TC
    eriMibs
        FROM ERI-ROOT-SMI
    LinkPortAddress, dnx
        FROM ERI-DNX-SMC-MIB;

eriDNXLinkPMStatsMIB MODULE-IDENTITY 
      LAST-UPDATED    "200204110000Z"
      ORGANIZATION    "Eastern Research, Inc."
      CONTACT-INFO
                      "Customer Service
                Postal: Eastern Research, Inc.
                        225 Executive Drive
                        Moorestown, NJ 08057
                Phone:  +1-800-337-4374
                Email:  support@erinc.com"
      DESCRIPTION
              "The ERI Enterprise MIB Module for the DNX DSx1 Performance Monitoring."

  	::= { eriMibs 7 }

-- *************************************************************************
-- The enterprise OID will be { iso(1) org(3) dod(6) internet(1) private(4)
--                              enterprises(1) virent(644) eri(2) dnx (4) 
--								performanceMonitoring (4) }
-- *************************************************************************
performanceMonitoring OBJECT IDENTIFIER 	::= { dnx 4 }

dsx1Esf 	OBJECT IDENTIFIER 	::= { performanceMonitoring 1 }
dsx1G826	OBJECT IDENTIFIER 	::= { performanceMonitoring 2 }

-- *************************************************************************
-- The DNX Performance Monitoring Statistics are currently provided in three
-- tables. The ESF Current Statistics, ESF 24 Hour Statistics, and the G.826 
-- Statistics.  Each Table will provide data for all applicable DS1/E1 links 
-- in the system. 

-- *************************************************************************
-- This table is the DSx1 ESF Current Statistics table

dsx1EsfCurrTable OBJECT-TYPE
        SYNTAX SEQUENCE OF DSx1EsfCurrEntry
        MAX-ACCESS not-accessible
        STATUS current
        DESCRIPTION
            "This is the DS1/E1 ESF Current Statistics table which consists
            of an entry for each DS1 link in the system that is configured
            for T1 ESF lines. This table provides the counters for the current 
            15 minute time interval."
        ::= { dsx1Esf 1 }

dsx1EsfCurrEntry OBJECT-TYPE
        SYNTAX DSx1EsfCurrEntry
        MAX-ACCESS not-accessible
        STATUS current
        DESCRIPTION
            "The conceptual row of the DS1/E1 ESF Statistics table. 
            A row in this table cannot be added, deleted, or modified
            directly. Rows may be removed or added by configuring the
            DS1 line type via the appropriate Device Provisioning table."
        INDEX { dsx1EsfCurrLinkAddr }
        ::= { dsx1EsfCurrTable 1 }

DSx1EsfCurrEntry ::=
        SEQUENCE {
                dsx1EsfCurrLinkAddr    LinkPortAddress,
                dsx1EsfCurrResrcId     Integer32,
                dsx1EsfCurrESs		   Gauge32,
                dsx1EsfCurrUASs		   Gauge32,
                dsx1EsfCurrSESs		   Gauge32,
                dsx1EsfCurrBESs		   Gauge32,
                dsx1EsfCurrLOFs        Gauge32,
                dsx1EsfCurrSeconds     Gauge32,
                dsx1EsfCurrIntervals   Gauge32,
                dsx1EsfCurrStatus	   DisplayString
                }

dsx1EsfCurrLinkAddr OBJECT-TYPE
        SYNTAX LinkPortAddress
        MAX-ACCESS read-only
        STATUS current
        DESCRIPTION
            "This number uniquely identifies an DS1/E1 link resource. 
            This number will be used throughout the system to identify 
            a unique link. The format is represented using an IP address 
            syntax (4 byte string). Note that the maximum valid link 
            number will vary depending on the specified carrier and framing 
            options. For example, an octal T1/E1 device has 8 DS1 links
            however the DS3 has 28 DS1 links.
            
               The 1st byte is reserved for future Nest Number use
               The 2nd byte represents the Slot Number (1-11)            
               The 3rd byte represents the Link Number (1-84)
               The 4th byte is reserved for future use           
            "
        ::= { dsx1EsfCurrEntry 1 }

dsx1EsfCurrResrcId OBJECT-TYPE
        SYNTAX Integer32
        MAX-ACCESS read-only
        STATUS current
        DESCRIPTION
            "Uniquely identifies a link in the system.
            This number is provided as key to allow the manager to 
            map this entry to a corresponding Resource Table entry."
        ::= { dsx1EsfCurrEntry 2 }

dsx1EsfCurrESs OBJECT-TYPE
        SYNTAX Gauge32 (0..900)
        MAX-ACCESS read-only
        STATUS current
        DESCRIPTION
            "This is the number of errored seconds that have
            occurred on the link during the current interval.
            This is not incremented during an Unavailable Second.
            
            For ESF links an Errored Second is a second with the 
            occurrence of a Loss of Frame or a CRC6 error in a 
            one-second period."            
        ::= { dsx1EsfCurrEntry 3 }

dsx1EsfCurrUASs OBJECT-TYPE
        SYNTAX Gauge32 (0..900)
        MAX-ACCESS read-only
        STATUS current
        DESCRIPTION
            "This is the number of failed seconds (UAS) that have
            occurred on the link during the current interval.
            
            Unavailable Seconds (UAS) are calculated by counting the number
            of seconds that the interface is unavailable.  Each second period 
            during the occurrence of a Failed Signal State (ten consecutive SES)
            is known as a failed/unavailable second."
        ::= { dsx1EsfCurrEntry 4 }

dsx1EsfCurrSESs OBJECT-TYPE
        SYNTAX Gauge32 (0..900)
        MAX-ACCESS read-only
        STATUS current
        DESCRIPTION
            "This is the number of severely errored seconds that have
            occurred on the link during the current interval. Controlled 
            slips are not included in this parameter. This is not incremented 
            during an Unavailable Second.
            
            A Severely Errored Second for ESF signals is a second period with
            320 or more CRC6 errors."
        ::= { dsx1EsfCurrEntry 5 }

dsx1EsfCurrBESs OBJECT-TYPE
        SYNTAX Gauge32 (0..900)
        MAX-ACCESS read-only
        STATUS current
        DESCRIPTION
            "This is the number of bursty errored seconds that have
            occurred on the T1 link during the current interval.
            This is not incremented during an Unavailable Second and 
            applies to ESF signals only.
            
            A Bursty Errored Second is a second period with more than one 
            but less than 320 CRC6 errors."
        ::= { dsx1EsfCurrEntry 6 }
        
dsx1EsfCurrLOFs OBJECT-TYPE
        SYNTAX Gauge32 (0..900)
        MAX-ACCESS read-only
        STATUS current
        DESCRIPTION
            "This is the number of loss of frames that have
            occurred on the link during the current interval.
            
            A loss of frame occurs when either network equipment or the 
            DTE senses errors in the framing pattern. Depending upon the 
            equipment, this occurs when any 2 of 4, 2 of 5, or 3 of 5 
            consecutive terminal framing bits received contain bit errors 
            in the framing pattern."
        ::= { dsx1EsfCurrEntry 7 }

dsx1EsfCurrSeconds OBJECT-TYPE
        SYNTAX Gauge32 (0..900)
        MAX-ACCESS read-only
        STATUS current
        DESCRIPTION
            "The total number of seconds in the current interval."
        ::= { dsx1EsfCurrEntry 8 }

dsx1EsfCurrIntervals OBJECT-TYPE
        SYNTAX Gauge32 (0..96)
        MAX-ACCESS read-only
        STATUS current
        DESCRIPTION
            "The total number of valid 15 minute intervals counted since
            the link has been up and running."
        ::= { dsx1EsfCurrEntry 9 }

dsx1EsfCurrStatus OBJECT-TYPE
        SYNTAX DisplayString (SIZE(8))
        MAX-ACCESS read-only
        STATUS current
        DESCRIPTION
        	"This defines the status of the DS1/E1 link using an 8 character 
        	code which can contain numbers or letters.  The codes are 
        	interpreted as follows:
        		character #1 - 'F' or zero where 'F' indicates Failed Signal
        						Status (FSS) if 'U' or 'L' are present.
        		character #2 - 'U' or zero where 'U' indicates an 
        						unavailable signal state.
        		character #3 through #6 are always zero.
        		character #7 - 'L' or zero where 'L' indicates that the T1
        						line is in loop.
        		character #8 - always zero."
        ::= { dsx1EsfCurrEntry 10 }

-- *************************************************************************
-- This table is the DSx1 ESF 24 Hour Statistics table

dsx1Esf24HrTable OBJECT-TYPE
        SYNTAX SEQUENCE OF DSx1Esf24HrEntry
        MAX-ACCESS not-accessible
        STATUS current
        DESCRIPTION
            "This is the DS1/E1 24 Hour ESF Statistics table which consists
            of an entry for each DS1/E1 link in the system that is configured
            for T1 ESF lines.  This table provides the total counters accumulated 
            for last 24 hour period."
        ::= { dsx1Esf 2 }

dsx1Esf24HrEntry OBJECT-TYPE
        SYNTAX DSx1Esf24HrEntry
        MAX-ACCESS not-accessible
        STATUS current
        DESCRIPTION
            "The conceptual row of the DS1/E1 24 Hour ESF Statistics table. 
            A row in this table cannot be added, deleted, or modified
            directly. Rows may be removed or added by configuring the
            DS1 line type via the appropriate Device Provisioning table."
        INDEX { dsx1Esf24HrLinkAddr }
        ::= { dsx1Esf24HrTable 1 }

DSx1Esf24HrEntry ::=
        SEQUENCE {
                dsx1Esf24HrLinkAddr   LinkPortAddress,
                dsx1Esf24HrResrcId    Integer32,
                dsx1Esf24HrESs		  Gauge32,
                dsx1Esf24HrUASs		  Gauge32,
                dsx1Esf24HrSESs		  Gauge32,
                dsx1Esf24HrBESs		  Gauge32,
                dsx1Esf24HrLOFs       Gauge32
                }

dsx1Esf24HrLinkAddr OBJECT-TYPE
        SYNTAX LinkPortAddress
        MAX-ACCESS read-only
        STATUS current
        DESCRIPTION
            "This number uniquely identifies an DS1/E1 link resource. 
            This number will be used throughout the system to identify 
            a unique link. The format is represented using an IP address 
            syntax (4 byte string). Note that the maximum valid link 
            number will vary depending on the specified carrier and framing 
            options. For example, an octal T1/E1 device has 8 DS1 links but the 
            DS3 has 28 DS1 links.
            
               The 1st byte is reserved for future Nest Number use
               The 2nd byte represents the Slot Number (1-11)            
               The 3rd byte represents the Link Number (1-84)
               The 4th byte is reserved for future use           
            "
        ::= { dsx1Esf24HrEntry 1 }

dsx1Esf24HrResrcId OBJECT-TYPE
        SYNTAX Integer32
        MAX-ACCESS read-only
        STATUS current
        DESCRIPTION
            "Uniquely identifies a link in the system.
            This number is provided as key to allow the manager to 
            map this entry to a corresponding Resource Table entry."
        ::= { dsx1Esf24HrEntry 2 }

dsx1Esf24HrESs OBJECT-TYPE
        SYNTAX Gauge32 (0..65535)
        MAX-ACCESS read-only
        STATUS current
        DESCRIPTION
            "This is the number of errored seconds that have
            occurred on the link during the past 24 hours."
        ::= { dsx1Esf24HrEntry 3 }

dsx1Esf24HrUASs OBJECT-TYPE
        SYNTAX Gauge32 (0..65535)
        MAX-ACCESS read-only
        STATUS current
        DESCRIPTION
            "This is the number of Unavailable Seconds (UAS) that 
            have occurred on the T1 link during the past 24 hours."
        ::= { dsx1Esf24HrEntry 4 }

dsx1Esf24HrSESs OBJECT-TYPE
        SYNTAX Gauge32 (0..65535)
        MAX-ACCESS read-only
        STATUS current
        DESCRIPTION
            "This is the number of severely errored seconds that have
            occurred on the T1 link during the past 24 hours."
        ::= { dsx1Esf24HrEntry 5 }

dsx1Esf24HrBESs OBJECT-TYPE
        SYNTAX Gauge32 (0..65535)
        MAX-ACCESS read-only
        STATUS current
        DESCRIPTION
            "This is the number of bursty errored seconds that have
            occurred on the T1 link during the past 24 hours."
        ::= { dsx1Esf24HrEntry 6 }
        
dsx1Esf24HrLOFs OBJECT-TYPE
        SYNTAX Gauge32 (0..65535)
        MAX-ACCESS read-only
        STATUS current
        DESCRIPTION
            "This is the number of loss of frames that have
            occurred on the T1 link during the past 24 hours."
        ::= { dsx1Esf24HrEntry 7 }

-- *************************************************************************
-- This table is the ESF 96 Registers table

dsx1Esf96RegTable OBJECT-TYPE
        SYNTAX SEQUENCE OF DSx1Esf96RegEntry
        MAX-ACCESS not-accessible
        STATUS current
        DESCRIPTION
            "This table is the ESF 96 Registers Table.  It displays the 96
             15 minute performance registers for each link on a card"
        ::= { dsx1Esf 3 }

dsx1Esf96RegEntry OBJECT-TYPE
        SYNTAX DSx1Esf96RegEntry
        MAX-ACCESS not-accessible
        STATUS current
        DESCRIPTION
            "The conceptual row of the DS1/E1 ESF 96 Registers table. 
            A row in this table cannot be added, deleted, or modified
            directly. Rows may be removed or added by configuring the
            DS1 line type via the appropriate Device Provisioning table."
        INDEX { dsx1Esf96RegLinkAddr, dsx1Esf96RegInterval }
        ::= {dsx1Esf96RegTable 1}

DSx1Esf96RegEntry ::=
        SEQUENCE {
                dsx1Esf96RegLinkAddr  LinkPortAddress,
                dsx1Esf96RegInterval  Integer32,
                dsx1Esf96RegESs       Gauge32,
                dsx1Esf96RegUASs      Gauge32,
                dsx1Esf96RegSESs      Gauge32,
                dsx1Esf96RegBESs      Gauge32
                }

dsx1Esf96RegLinkAddr OBJECT-TYPE
        SYNTAX LinkPortAddress
        MAX-ACCESS read-only
        STATUS current
        DESCRIPTION
            "Uniquely identifies a link in the system.
             This number is provided as key to allow the manager to
             map this entry to a corresponding Resource Table entry."
        ::= { dsx1Esf96RegEntry 1 }

dsx1Esf96RegInterval OBJECT-TYPE
        SYNTAX Integer32 (1..96)
        MAX-ACCESS read-only
        STATUS current
        DESCRIPTION
            "Specifies the interval Number On a particular link"
        ::= {dsx1Esf96RegEntry 2}

dsx1Esf96RegESs OBJECT-TYPE
        SYNTAX Gauge32 (0..900)
        MAX-ACCESS read-only
        STATUS current
        DESCRIPTION
            "The number of Errored Seconds for a particular interval 
            on a particular link"
        ::={dsx1Esf96RegEntry 3}

dsx1Esf96RegUASs OBJECT-TYPE
        SYNTAX Gauge32 (0..900)
        MAX-ACCESS read-only
        STATUS current
        DESCRIPTION
            "The number of Unavailable Seconds for a particular interval 
            on a particular link"
        ::={dsx1Esf96RegEntry 4}

dsx1Esf96RegSESs OBJECT-TYPE
        SYNTAX Gauge32 (0..900)
        MAX-ACCESS read-only
        STATUS current
        DESCRIPTION
            "The number of Severely Errored Seconds for a particular interval 
            on a particular link"
        ::= {dsx1Esf96RegEntry 5}

dsx1Esf96RegBESs OBJECT-TYPE
        SYNTAX Gauge32 (0..900)
        MAX-ACCESS read-only
        STATUS current
        DESCRIPTION
            "The number of Bursty Errored Seconds for a particular interval 
            on a particular link"
        ::= {dsx1Esf96RegEntry 6}

-- *************************************************************************
-- This table is the DS1/E1 G.826 Statistics table

dsx1G826Table OBJECT-TYPE
        SYNTAX SEQUENCE OF DSx1G826Entry
        MAX-ACCESS not-accessible
        STATUS current
        DESCRIPTION
            "This is the DS1/E1 G.826 Statistics table which consists
            of an entry for each DS1/E1 link in the system.  This table 
            provides the total counters accumulated since the link has 
            been up or since the last time the counts were cleared. The
            counters are calculated in accordance with the ITU-T G.826 
            Error performance parameters, November 1993."
        ::= { dsx1G826 1 }

dsx1G826Entry OBJECT-TYPE
        SYNTAX DSx1G826Entry
        MAX-ACCESS not-accessible
        STATUS current
        DESCRIPTION
            "The conceptual row of the DS1/E1 G.826 Statistics table. 
            A row in this table cannot be added or deleted directly but 
            the counter time period can be reset to zero.  Rows may be 
            removed or added by configuring the DS1/E1 line type via the 
            appropriate Device Provisioning tables."
        INDEX { dsx1G826LinkAddr }
        ::= { dsx1G826Table 1 }

DSx1G826Entry ::=
        SEQUENCE {
                dsx1G826LinkAddr        LinkPortAddress,
                dsx1G826ResrcId  		Integer32,
                dsx1G826TotalTime		Integer32,         -- RW
                dsx1G826ESs  			Gauge32,
                dsx1G826ErrFSs          Gauge32,
                dsx1G826SESs            Gauge32,
                dsx1G826ConsecSESs		Gauge32,
                dsx1G826ConsecErrFSs    Gauge32,
                dsx1G826BGErrBlocks     Gauge32,
                dsx1G826ESRatio		    DisplayString,
                dsx1G826SESRatio		DisplayString,                
                dsx1G826BgBERRatio		DisplayString,
                dsx1G826UASs            Gauge32
                }

dsx1G826LinkAddr OBJECT-TYPE
        SYNTAX LinkPortAddress
        MAX-ACCESS read-only
        STATUS current
        DESCRIPTION
            "This number uniquely identifies an DS1/E1 link resource. 
            This number will be used throughout the system to identify 
            a unique link. The format is represented using an IP address 
            syntax (4 byte string). Note that the maximum valid link 
            number will vary depending on the specified carrier and framing 
            options. For example, an octal T1/E1 device has 8 DS1 links but the 
            DS3 has 28 DS1 links.
            
               The 1st byte is reserved for future Nest Number use
               The 2nd byte represents the Slot Number (1-11)            
               The 3rd byte represents the Link Number (1-84)
               The 4th byte is reserved for future use           
            "
        ::= { dsx1G826Entry 1 }

dsx1G826ResrcId OBJECT-TYPE
        SYNTAX Integer32
        MAX-ACCESS read-only
        STATUS current
        DESCRIPTION
            "Uniquely identifies a link in the system.
             This number is provided as key to allow the manager to 
             map this entry to a corresponding Resource Table entry."
        ::= { dsx1G826Entry 2 }

dsx1G826TotalTime OBJECT-TYPE
        SYNTAX Integer32
        MAX-ACCESS read-write
        STATUS current
        DESCRIPTION
            "This the total number of seconds the G.826 data has been collected.
            Resetting this to zero will clear the counters for specific link."
        ::= { dsx1G826Entry 3 }

dsx1G826ESs OBJECT-TYPE
        SYNTAX Gauge32
        MAX-ACCESS read-only
        STATUS current
        DESCRIPTION
            "This is the total number of errored seconds that have
            occurred since the link has been up or since the G.826 
            counters have been reset.
            
            An Errored Second for G.826 is a one second period with one 
            or more errored blocks or at least one defect."
        ::= { dsx1G826Entry 4 }

dsx1G826ErrFSs OBJECT-TYPE
        SYNTAX Gauge32
        MAX-ACCESS read-only
        STATUS current
        DESCRIPTION
            "This is the total number of error free seconds since the 
            link has been up or since the G.826 counters have been reset."
        ::= { dsx1G826Entry 5 }
        
dsx1G826SESs OBJECT-TYPE
        SYNTAX Gauge32
        MAX-ACCESS read-only
        STATUS current
        DESCRIPTION
            "This is the total number of severely errored seconds that have
            occurred since the link has been up or since the G.826 counters 
            have been reset.
            
            A Severely Errored Second for G.826 is a one second period that
            contains 30% or more errored blocks OR at least one defect.
            This is a subset of ES."
        ::= { dsx1G826Entry 6 }

dsx1G826ConsecSESs OBJECT-TYPE
        SYNTAX Gauge32
        MAX-ACCESS read-only
        STATUS current
        DESCRIPTION
            "This is the total number of continuous occurrences of SES,
            in a one second intervals, since the link has been up 
            or since the G.826 counters have been reset."
        ::= { dsx1G826Entry 7 }

dsx1G826ConsecErrFSs OBJECT-TYPE
        SYNTAX Gauge32
        MAX-ACCESS read-only
        STATUS current
        DESCRIPTION
            "This is the total number of consecutive seconds one second
            period intervals that did not have defects or errors since 
            the link has been up or since the G.826 counters have been reset."
        ::= { dsx1G826Entry 8 }

dsx1G826BGErrBlocks OBJECT-TYPE
        SYNTAX Gauge32
        MAX-ACCESS read-only
        STATUS current
        DESCRIPTION
            "This is the total number of background errored blocks that have 
            occurred since the link has been up or since the G.826 counters 
            have been reset.  
            
            A Background Block Error for G.826 is an errored block not 
            occurring as part of an SES."
        ::= { dsx1G826Entry 9 }

dsx1G826ESRatio OBJECT-TYPE
        SYNTAX DisplayString
        MAX-ACCESS read-only
        STATUS current
        DESCRIPTION
            "This is the ratio of ES to total seconds in available time
            during a fixed measurement interval rounded to 2 decimals."
        ::= { dsx1G826Entry 10 } 
        
dsx1G826SESRatio OBJECT-TYPE
        SYNTAX DisplayString
        MAX-ACCESS read-only
        STATUS current
        DESCRIPTION
            "This is the ratio of SES to total seconds in available time
            during a fixed measurement interval rounded to 2 decimals."
        ::= { dsx1G826Entry 11 }

dsx1G826BgBERRatio OBJECT-TYPE
        SYNTAX DisplayString
        MAX-ACCESS read-only
        STATUS current
        DESCRIPTION
            "This is the ratio of background block errors to total blocks 
            in available time during a fixed measurement interval rounded 
            to 2 decimals.  This total block count excludes all blocks 
            during SES."
        ::= { dsx1G826Entry 12 }

dsx1G826UASs OBJECT-TYPE
        SYNTAX Gauge32
        MAX-ACCESS read-only
        STATUS current
        DESCRIPTION
            "This is the total number of Unavailable Seconds (UAS) that have 
            occurred since the link has been up or since the G.826 counters 
            have been reset."
        ::= { dsx1G826Entry 13 }
END

-- *************************************************************************
--
--  MIB:    ERI-DNX-LINK-TEST-MIB
--
--	Purpose:
--          This will be the MIB for the DNX Link Test Statistics Module. 
--          This will provide for BERT and LOOP testing and statistics 
--          for each DS1 or E1 link in the system.
--
--  Contact: Eastern Research Inc. 1-800-337-4374  Email: support@erinc.com
--
-- *************************************************************************
