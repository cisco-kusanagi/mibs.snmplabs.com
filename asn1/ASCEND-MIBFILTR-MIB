--			Ascend mibfiltr MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBFILTR-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibfilterProfile  OBJECT IDENTIFIER ::= { configuration 77}

	-- The mibfilterProfile table
	--
	-- This table contains parameters for the mibfilterProfile profile
	--

    mibfilterProfileTable	OBJECT-TYPE
	SYNTAX		SEQUENCE OF MibfilterProfileEntry
	ACCESS		not-accessible
	STATUS		mandatory
	DESCRIPTION	"A list of mibfilterProfile profile entries."
	::= { mibfilterProfile 1 }

    mibfilterProfileEntry	OBJECT-TYPE
	SYNTAX		MibfilterProfileEntry
	ACCESS		not-accessible
	STATUS		mandatory
	DESCRIPTION	"A mibfilterProfile entry containing objects that
			 maps to the parameters of mibfilterProfile profile."
	INDEX		{ filterProfile-FilterName }
	::= { mibfilterProfileTable 1 }

    MibfilterProfileEntry ::=
	SEQUENCE {
	    filterProfile-FilterName
		DisplayString,
	    filterProfile-Action-o
		INTEGER
	}

    filterProfile-FilterName	OBJECT-TYPE
	SYNTAX	DisplayString
	ACCESS	read-only
	STATUS	mandatory
	DESCRIPTION	"The name of this filter. All filters are referenced by name so a name must be assigned to active filters."
	::= { mibfilterProfileEntry 1 }

    filterProfile-Action-o	OBJECT-TYPE
	SYNTAX	INTEGER {
		    noAction (1),
		    createProfile (2),
		    deleteProfile (3)
		}
	ACCESS	read-write
	STATUS	mandatory
	DESCRIPTION	""
	::= { mibfilterProfileEntry 2 }


	-- The mibfilterProfile__output_filters table
	--
	-- This table contains parameters for the mibfilterProfile__output_filters profile
	--

    mibfilterProfile-OutputFiltersTable	OBJECT-TYPE
	SYNTAX		SEQUENCE OF MibfilterProfile-OutputFiltersEntry
	ACCESS		not-accessible
	STATUS		mandatory
	DESCRIPTION	"A list of mibfilterProfile__output_filters profile entries."
	::= { mibfilterProfile 2 }

    mibfilterProfile-OutputFiltersEntry	OBJECT-TYPE
	SYNTAX		MibfilterProfile-OutputFiltersEntry
	ACCESS		not-accessible
	STATUS		mandatory
	DESCRIPTION	"A mibfilterProfile__output_filters entry containing objects that
			 maps to the parameters of mibfilterProfile__output_filters profile."
	INDEX		{ filterProfile-OutputFilters-FilterName, filterProfile-OutputFilters-Index-o }
	::= { mibfilterProfile-OutputFiltersTable 1 }

    MibfilterProfile-OutputFiltersEntry ::=
	SEQUENCE {
	    filterProfile-OutputFilters-FilterName
		DisplayString,
	    filterProfile-OutputFilters-Index-o
		INTEGER,
	    filterProfile-OutputFilters-ValidEntry
		INTEGER,
	    filterProfile-OutputFilters-Forward
		INTEGER,
	    filterProfile-OutputFilters-oType
		INTEGER,
	    filterProfile-OutputFilters-GenFilter-Offset
		INTEGER,
	    filterProfile-OutputFilters-GenFilter-Len
		INTEGER,
	    filterProfile-OutputFilters-GenFilter-More
		INTEGER,
	    filterProfile-OutputFilters-GenFilter-CompNeq
		INTEGER,
	    filterProfile-OutputFilters-GenFilter-Mask
		DisplayString,
	    filterProfile-OutputFilters-GenFilter-Value
		DisplayString,
	    filterProfile-OutputFilters-IpFilter-Protocol
		INTEGER,
	    filterProfile-OutputFilters-IpFilter-SourceAddressMask
		IpAddress,
	    filterProfile-OutputFilters-IpFilter-SourceAddress
		IpAddress,
	    filterProfile-OutputFilters-IpFilter-DestAddressMask
		IpAddress,
	    filterProfile-OutputFilters-IpFilter-DestAddress
		IpAddress,
	    filterProfile-OutputFilters-IpFilter-oSrcPortCmp
		INTEGER,
	    filterProfile-OutputFilters-IpFilter-SourcePort
		INTEGER,
	    filterProfile-OutputFilters-IpFilter-oDstPortCmp
		INTEGER,
	    filterProfile-OutputFilters-IpFilter-DestPort
		INTEGER,
	    filterProfile-OutputFilters-IpFilter-TcpEstab
		INTEGER,
	    filterProfile-OutputFilters-RouteFilter-SourceAddressMask
		IpAddress,
	    filterProfile-OutputFilters-RouteFilter-SourceAddress
		IpAddress,
	    filterProfile-OutputFilters-RouteFilter-RouteMask
		IpAddress,
	    filterProfile-OutputFilters-RouteFilter-RouteAddress
		IpAddress,
	    filterProfile-OutputFilters-RouteFilter-AddMetric
		INTEGER,
	    filterProfile-OutputFilters-RouteFilter-Action
		INTEGER,
	    filterProfile-OutputFilters-IpxFilter-SrcNetAddress
		DisplayString,
	    filterProfile-OutputFilters-IpxFilter-DestNetAddress
		DisplayString,
	    filterProfile-OutputFilters-IpxFilter-SrcNodeAddress
		DisplayString,
	    filterProfile-OutputFilters-IpxFilter-DestNodeAddress
		DisplayString,
	    filterProfile-OutputFilters-IpxFilter-SrcSocket
		DisplayString,
	    filterProfile-OutputFilters-IpxFilter-SrcSocketCmp
		INTEGER,
	    filterProfile-OutputFilters-IpxFilter-DestSocket
		INTEGER,
	    filterProfile-OutputFilters-IpxFilter-DstSocketCmp
		INTEGER,
	    filterProfile-OutputFilters-TosFilter-Protocol
		INTEGER,
	    filterProfile-OutputFilters-TosFilter-SourceAddressMask
		IpAddress,
	    filterProfile-OutputFilters-TosFilter-SourceAddress
		IpAddress,
	    filterProfile-OutputFilters-TosFilter-DestAddressMask
		IpAddress,
	    filterProfile-OutputFilters-TosFilter-DestAddress
		IpAddress,
	    filterProfile-OutputFilters-TosFilter-oSrcPortCmp
		INTEGER,
	    filterProfile-OutputFilters-TosFilter-SourcePort
		INTEGER,
	    filterProfile-OutputFilters-TosFilter-oDstPortCmp
		INTEGER,
	    filterProfile-OutputFilters-TosFilter-DestPort
		INTEGER,
	    filterProfile-OutputFilters-TosFilter-Precedence
		INTEGER,
	    filterProfile-OutputFilters-TosFilter-TypeOfService
		INTEGER,
	    filterProfile-OutputFilters-TosFilter-MarkingType
		INTEGER,
	    filterProfile-OutputFilters-TosFilter-Dscp
		DisplayString
	}

    filterProfile-OutputFilters-FilterName	OBJECT-TYPE
	SYNTAX	DisplayString
	ACCESS	read-only
	STATUS	mandatory
	DESCRIPTION	""
	::= { mibfilterProfile-OutputFiltersEntry 1 }

    filterProfile-OutputFilters-Index-o	OBJECT-TYPE
	SYNTAX	INTEGER
	ACCESS	read-only
	STATUS	mandatory
	DESCRIPTION	""
	::= { mibfilterProfile-OutputFiltersEntry 2 }

    filterProfile-OutputFilters-ValidEntry	OBJECT-TYPE
	SYNTAX	INTEGER {
		    no (1),
		    yes (2)
		}
	ACCESS	read-write
	STATUS	mandatory
	DESCRIPTION	"When TRUE, this filter entry has been defined and properly initialized. When FALSE, this entry should be skipped when filtering."
	::= { mibfilterProfile-OutputFiltersEntry 3 }

    filterProfile-OutputFilters-Forward	OBJECT-TYPE
	SYNTAX	INTEGER {
		    no (1),
		    yes (2)
		}
	ACCESS	read-write
	STATUS	mandatory
	DESCRIPTION	"When TRUE a packet matching this filter will be forwarded or restart the idle timer. When FALSE a packet matching this filter will be dropped or not restart the idle timer."
	::= { mibfilterProfile-OutputFiltersEntry 4 }

    filterProfile-OutputFilters-oType	OBJECT-TYPE
	SYNTAX	INTEGER {
		    genericFilter (1),
		    ipFilter (2),
		    routeFilter (3),
		    ipxFilter (4),
		    tosFilter (5)
		}
	ACCESS	read-write
	STATUS	mandatory
	DESCRIPTION	"The type of filter contained in this entry. Used to select which of the following fields should be used."
	::= { mibfilterProfile-OutputFiltersEntry 5 }

    filterProfile-OutputFilters-GenFilter-Offset	OBJECT-TYPE
	SYNTAX	INTEGER
	ACCESS	read-write
	STATUS	mandatory
	DESCRIPTION	"Offset from start of frame of data to test."
	::= { mibfilterProfile-OutputFiltersEntry 6 }

    filterProfile-OutputFilters-GenFilter-Len	OBJECT-TYPE
	SYNTAX	INTEGER
	ACCESS	read-write
	STATUS	mandatory
	DESCRIPTION	"Number of octets to test. Max value is 8 octets."
	::= { mibfilterProfile-OutputFiltersEntry 7 }

    filterProfile-OutputFilters-GenFilter-More	OBJECT-TYPE
	SYNTAX	INTEGER {
		    no (1),
		    yes (2)
		}
	ACCESS	read-write
	STATUS	mandatory
	DESCRIPTION	"Include next entry in as part of filter."
	::= { mibfilterProfile-OutputFiltersEntry 8 }

    filterProfile-OutputFilters-GenFilter-CompNeq	OBJECT-TYPE
	SYNTAX	INTEGER {
		    no (1),
		    yes (2)
		}
	ACCESS	read-write
	STATUS	mandatory
	DESCRIPTION	"Defines type of comparison( Equals(FALSE) or Notequals(TRUE). Default is Equals."
	::= { mibfilterProfile-OutputFiltersEntry 9 }

    filterProfile-OutputFilters-GenFilter-Mask	OBJECT-TYPE
	SYNTAX	DisplayString
	ACCESS	read-write
	STATUS	mandatory
	DESCRIPTION	"A mask to be applied to the data at offset. Only the first len octets will be applied."
	::= { mibfilterProfile-OutputFiltersEntry 10 }

    filterProfile-OutputFilters-GenFilter-Value	OBJECT-TYPE
	SYNTAX	DisplayString
	ACCESS	read-write
	STATUS	mandatory
	DESCRIPTION	"The value to compare with the masked data. Only the first len octets will be compared."
	::= { mibfilterProfile-OutputFiltersEntry 11 }

    filterProfile-OutputFilters-IpFilter-Protocol	OBJECT-TYPE
	SYNTAX	INTEGER
	ACCESS	read-write
	STATUS	mandatory
	DESCRIPTION	"The protocol number of the protocol to filter for. If set to zero this entry will match any IP protocol."
	::= { mibfilterProfile-OutputFiltersEntry 12 }

    filterProfile-OutputFilters-IpFilter-SourceAddressMask	OBJECT-TYPE
	SYNTAX	IpAddress
	ACCESS	read-write
	STATUS	mandatory
	DESCRIPTION	"A mask to apply to a source address before comparison."
	::= { mibfilterProfile-OutputFiltersEntry 13 }

    filterProfile-OutputFilters-IpFilter-SourceAddress	OBJECT-TYPE
	SYNTAX	IpAddress
	ACCESS	read-write
	STATUS	mandatory
	DESCRIPTION	"A value to compare with the masked source addresses."
	::= { mibfilterProfile-OutputFiltersEntry 14 }

    filterProfile-OutputFilters-IpFilter-DestAddressMask	OBJECT-TYPE
	SYNTAX	IpAddress
	ACCESS	read-write
	STATUS	mandatory
	DESCRIPTION	"A mask to apply to a destination address before comparison."
	::= { mibfilterProfile-OutputFiltersEntry 15 }

    filterProfile-OutputFilters-IpFilter-DestAddress	OBJECT-TYPE
	SYNTAX	IpAddress
	ACCESS	read-write
	STATUS	mandatory
	DESCRIPTION	"A value to compare with the masked destination addresses."
	::= { mibfilterProfile-OutputFiltersEntry 16 }

    filterProfile-OutputFilters-IpFilter-oSrcPortCmp	OBJECT-TYPE
	SYNTAX	INTEGER {
		    none (1),
		    less (2),
		    eql (3),
		    gtr (4),
		    neq (5)
		}
	ACCESS	read-write
	STATUS	mandatory
	DESCRIPTION	"The type of comparison for the source port field. May be set to no comparison."
	::= { mibfilterProfile-OutputFiltersEntry 17 }

    filterProfile-OutputFilters-IpFilter-SourcePort	OBJECT-TYPE
	SYNTAX	INTEGER
	ACCESS	read-write
	STATUS	mandatory
	DESCRIPTION	"A value to compare with the source port. The comparison is defined by the sourceTest field."
	::= { mibfilterProfile-OutputFiltersEntry 18 }

    filterProfile-OutputFilters-IpFilter-oDstPortCmp	OBJECT-TYPE
	SYNTAX	INTEGER {
		    none (1),
		    less (2),
		    eql (3),
		    gtr (4),
		    neq (5)
		}
	ACCESS	read-write
	STATUS	mandatory
	DESCRIPTION	"The type of comparison for the destination port field. May be set to no comparison."
	::= { mibfilterProfile-OutputFiltersEntry 19 }

    filterProfile-OutputFilters-IpFilter-DestPort	OBJECT-TYPE
	SYNTAX	INTEGER
	ACCESS	read-write
	STATUS	mandatory
	DESCRIPTION	"A value to compare with the destination port. The comparison is defined by the destTest field."
	::= { mibfilterProfile-OutputFiltersEntry 20 }

    filterProfile-OutputFilters-IpFilter-TcpEstab	OBJECT-TYPE
	SYNTAX	INTEGER {
		    no (1),
		    yes (2)
		}
	ACCESS	read-write
	STATUS	mandatory
	DESCRIPTION	"Indicates whether to look at tcp packets in an established connection."
	::= { mibfilterProfile-OutputFiltersEntry 21 }

    filterProfile-OutputFilters-RouteFilter-SourceAddressMask	OBJECT-TYPE
	SYNTAX	IpAddress
	ACCESS	read-write
	STATUS	mandatory
	DESCRIPTION	"A mask to apply to a source address before comparison."
	::= { mibfilterProfile-OutputFiltersEntry 22 }

    filterProfile-OutputFilters-RouteFilter-SourceAddress	OBJECT-TYPE
	SYNTAX	IpAddress
	ACCESS	read-write
	STATUS	mandatory
	DESCRIPTION	"A value to compare with the masked source addresses."
	::= { mibfilterProfile-OutputFiltersEntry 23 }

    filterProfile-OutputFilters-RouteFilter-RouteMask	OBJECT-TYPE
	SYNTAX	IpAddress
	ACCESS	read-write
	STATUS	mandatory
	DESCRIPTION	"A mask to apply to a destination address before comparison."
	::= { mibfilterProfile-OutputFiltersEntry 24 }

    filterProfile-OutputFilters-RouteFilter-RouteAddress	OBJECT-TYPE
	SYNTAX	IpAddress
	ACCESS	read-write
	STATUS	mandatory
	DESCRIPTION	"A value to compare with the masked destination addresses."
	::= { mibfilterProfile-OutputFiltersEntry 25 }

    filterProfile-OutputFilters-RouteFilter-AddMetric	OBJECT-TYPE
	SYNTAX	INTEGER
	ACCESS	read-write
	STATUS	mandatory
	DESCRIPTION	"A value to be added to metric of the route, this is valid only when action is add."
	::= { mibfilterProfile-OutputFiltersEntry 26 }

    filterProfile-OutputFilters-RouteFilter-Action	OBJECT-TYPE
	SYNTAX	INTEGER {
		    none (1),
		    accept (2),
		    deny (3),
		    add (4)
		}
	ACCESS	read-write
	STATUS	mandatory
	DESCRIPTION	"The type of action taken when match occurs."
	::= { mibfilterProfile-OutputFiltersEntry 27 }

    filterProfile-OutputFilters-IpxFilter-SrcNetAddress	OBJECT-TYPE
	SYNTAX	DisplayString
	ACCESS	read-write
	STATUS	mandatory
	DESCRIPTION	"A value to compare with source network addresses."
	::= { mibfilterProfile-OutputFiltersEntry 28 }

    filterProfile-OutputFilters-IpxFilter-DestNetAddress	OBJECT-TYPE
	SYNTAX	DisplayString
	ACCESS	read-write
	STATUS	mandatory
	DESCRIPTION	"A value to compare with destination network addresses."
	::= { mibfilterProfile-OutputFiltersEntry 29 }

    filterProfile-OutputFilters-IpxFilter-SrcNodeAddress	OBJECT-TYPE
	SYNTAX	DisplayString
	ACCESS	read-write
	STATUS	mandatory
	DESCRIPTION	"A value to compare with source node addresses."
	::= { mibfilterProfile-OutputFiltersEntry 30 }

    filterProfile-OutputFilters-IpxFilter-DestNodeAddress	OBJECT-TYPE
	SYNTAX	DisplayString
	ACCESS	read-write
	STATUS	mandatory
	DESCRIPTION	"A value to compare with destination node addresses."
	::= { mibfilterProfile-OutputFiltersEntry 31 }

    filterProfile-OutputFilters-IpxFilter-SrcSocket	OBJECT-TYPE
	SYNTAX	DisplayString
	ACCESS	read-write
	STATUS	mandatory
	DESCRIPTION	"The type of comparison for the source socket field. May be set to no comparison."
	::= { mibfilterProfile-OutputFiltersEntry 32 }

    filterProfile-OutputFilters-IpxFilter-SrcSocketCmp	OBJECT-TYPE
	SYNTAX	INTEGER {
		    none (1),
		    less (2),
		    eql (3),
		    gtr (4),
		    neq (5)
		}
	ACCESS	read-write
	STATUS	mandatory
	DESCRIPTION	"The type of comparison for the source socket field. May be set to no comparison."
	::= { mibfilterProfile-OutputFiltersEntry 33 }

    filterProfile-OutputFilters-IpxFilter-DestSocket	OBJECT-TYPE
	SYNTAX	INTEGER
	ACCESS	read-write
	STATUS	mandatory
	DESCRIPTION	"A value to compare with the destination socket. The comparison is defined by the destTest field."
	::= { mibfilterProfile-OutputFiltersEntry 34 }

    filterProfile-OutputFilters-IpxFilter-DstSocketCmp	OBJECT-TYPE
	SYNTAX	INTEGER {
		    none (1),
		    less (2),
		    eql (3),
		    gtr (4),
		    neq (5)
		}
	ACCESS	read-write
	STATUS	mandatory
	DESCRIPTION	"The type of comparison for the destination socket field. May be set to no comparison."
	::= { mibfilterProfile-OutputFiltersEntry 35 }

    filterProfile-OutputFilters-TosFilter-Protocol	OBJECT-TYPE
	SYNTAX	INTEGER
	ACCESS	read-write
	STATUS	mandatory
	DESCRIPTION	"The protocol number of the protocol you like to support type-of-service. If set to zero this entry will match any IP protocol."
	::= { mibfilterProfile-OutputFiltersEntry 36 }

    filterProfile-OutputFilters-TosFilter-SourceAddressMask	OBJECT-TYPE
	SYNTAX	IpAddress
	ACCESS	read-write
	STATUS	mandatory
	DESCRIPTION	"A mask to apply to a source address before comparison."
	::= { mibfilterProfile-OutputFiltersEntry 37 }

    filterProfile-OutputFilters-TosFilter-SourceAddress	OBJECT-TYPE
	SYNTAX	IpAddress
	ACCESS	read-write
	STATUS	mandatory
	DESCRIPTION	"A value to compare with the masked source addresses."
	::= { mibfilterProfile-OutputFiltersEntry 38 }

    filterProfile-OutputFilters-TosFilter-DestAddressMask	OBJECT-TYPE
	SYNTAX	IpAddress
	ACCESS	read-write
	STATUS	mandatory
	DESCRIPTION	"A mask to apply to a destination address before comparison."
	::= { mibfilterProfile-OutputFiltersEntry 39 }

    filterProfile-OutputFilters-TosFilter-DestAddress	OBJECT-TYPE
	SYNTAX	IpAddress
	ACCESS	read-write
	STATUS	mandatory
	DESCRIPTION	"A value to compare with the masked destination addresses."
	::= { mibfilterProfile-OutputFiltersEntry 40 }

    filterProfile-OutputFilters-TosFilter-oSrcPortCmp	OBJECT-TYPE
	SYNTAX	INTEGER {
		    none (1),
		    less (2),
		    eql (3),
		    gtr (4),
		    neq (5)
		}
	ACCESS	read-write
	STATUS	mandatory
	DESCRIPTION	"The type of comparison for the source port field. May be set to no comparison."
	::= { mibfilterProfile-OutputFiltersEntry 41 }

    filterProfile-OutputFilters-TosFilter-SourcePort	OBJECT-TYPE
	SYNTAX	INTEGER
	ACCESS	read-write
	STATUS	mandatory
	DESCRIPTION	"A value to compare with the source port. The comparison is defined by the sourceTest field."
	::= { mibfilterProfile-OutputFiltersEntry 42 }

    filterProfile-OutputFilters-TosFilter-oDstPortCmp	OBJECT-TYPE
	SYNTAX	INTEGER {
		    none (1),
		    less (2),
		    eql (3),
		    gtr (4),
		    neq (5)
		}
	ACCESS	read-write
	STATUS	mandatory
	DESCRIPTION	"The type of comparison for the destination port field. May be set to no comparison."
	::= { mibfilterProfile-OutputFiltersEntry 43 }

    filterProfile-OutputFilters-TosFilter-DestPort	OBJECT-TYPE
	SYNTAX	INTEGER
	ACCESS	read-write
	STATUS	mandatory
	DESCRIPTION	"A value to compare with the destination port. The comparison is defined by the destTest field."
	::= { mibfilterProfile-OutputFiltersEntry 44 }

    filterProfile-OutputFilters-TosFilter-Precedence	OBJECT-TYPE
	SYNTAX	INTEGER {
		    n-000 (1),
		    n-001 (33),
		    n-010 (65),
		    n-011 (97),
		    n-100 (129),
		    n-101 (161),
		    n-110 (193),
		    n-111 (225)
		}
	ACCESS	read-write
	STATUS	mandatory
	DESCRIPTION	"Tag the precedence bits (priority bits) in the TOS octet of IP datagram header with this value when match occurs."
	::= { mibfilterProfile-OutputFiltersEntry 45 }

    filterProfile-OutputFilters-TosFilter-TypeOfService	OBJECT-TYPE
	SYNTAX	INTEGER {
		    normal (1),
		    cost (3),
		    reliability (5),
		    throughput (9),
		    latency (17)
		}
	ACCESS	read-write
	STATUS	mandatory
	DESCRIPTION	"Tag the type of service field in the TOS octet of IP datagram header with this value when match occurs."
	::= { mibfilterProfile-OutputFiltersEntry 46 }

    filterProfile-OutputFilters-TosFilter-MarkingType	OBJECT-TYPE
	SYNTAX	INTEGER {
		    precedenceTos (1),
		    dscp (2)
		}
	ACCESS	read-write
	STATUS	mandatory
	DESCRIPTION	"Select type of packet marking."
	::= { mibfilterProfile-OutputFiltersEntry 47 }

    filterProfile-OutputFilters-TosFilter-Dscp	OBJECT-TYPE
	SYNTAX	DisplayString
	ACCESS	read-write
	STATUS	mandatory
	DESCRIPTION	"DSCP tag to be used in marking of the packets (if marking-type = dscp)."
	::= { mibfilterProfile-OutputFiltersEntry 48 }


	-- The mibfilterProfile__input_filters table
	--
	-- This table contains parameters for the mibfilterProfile__input_filters profile
	--

    mibfilterProfile-InputFiltersTable	OBJECT-TYPE
	SYNTAX		SEQUENCE OF MibfilterProfile-InputFiltersEntry
	ACCESS		not-accessible
	STATUS		mandatory
	DESCRIPTION	"A list of mibfilterProfile__input_filters profile entries."
	::= { mibfilterProfile 3 }

    mibfilterProfile-InputFiltersEntry	OBJECT-TYPE
	SYNTAX		MibfilterProfile-InputFiltersEntry
	ACCESS		not-accessible
	STATUS		mandatory
	DESCRIPTION	"A mibfilterProfile__input_filters entry containing objects that
			 maps to the parameters of mibfilterProfile__input_filters profile."
	INDEX		{ filterProfile-InputFilters-FilterName, filterProfile-InputFilters-Index-o }
	::= { mibfilterProfile-InputFiltersTable 1 }

    MibfilterProfile-InputFiltersEntry ::=
	SEQUENCE {
	    filterProfile-InputFilters-FilterName
		DisplayString,
	    filterProfile-InputFilters-Index-o
		INTEGER,
	    filterProfile-InputFilters-ValidEntry
		INTEGER,
	    filterProfile-InputFilters-Forward
		INTEGER,
	    filterProfile-InputFilters-oType
		INTEGER,
	    filterProfile-InputFilters-GenFilter-Offset
		INTEGER,
	    filterProfile-InputFilters-GenFilter-Len
		INTEGER,
	    filterProfile-InputFilters-GenFilter-More
		INTEGER,
	    filterProfile-InputFilters-GenFilter-CompNeq
		INTEGER,
	    filterProfile-InputFilters-GenFilter-Mask
		DisplayString,
	    filterProfile-InputFilters-GenFilter-Value
		DisplayString,
	    filterProfile-InputFilters-IpFilter-Protocol
		INTEGER,
	    filterProfile-InputFilters-IpFilter-SourceAddressMask
		IpAddress,
	    filterProfile-InputFilters-IpFilter-SourceAddress
		IpAddress,
	    filterProfile-InputFilters-IpFilter-DestAddressMask
		IpAddress,
	    filterProfile-InputFilters-IpFilter-DestAddress
		IpAddress,
	    filterProfile-InputFilters-IpFilter-oSrcPortCmp
		INTEGER,
	    filterProfile-InputFilters-IpFilter-SourcePort
		INTEGER,
	    filterProfile-InputFilters-IpFilter-oDstPortCmp
		INTEGER,
	    filterProfile-InputFilters-IpFilter-DestPort
		INTEGER,
	    filterProfile-InputFilters-IpFilter-TcpEstab
		INTEGER,
	    filterProfile-InputFilters-RouteFilter-SourceAddressMask
		IpAddress,
	    filterProfile-InputFilters-RouteFilter-SourceAddress
		IpAddress,
	    filterProfile-InputFilters-RouteFilter-RouteMask
		IpAddress,
	    filterProfile-InputFilters-RouteFilter-RouteAddress
		IpAddress,
	    filterProfile-InputFilters-RouteFilter-AddMetric
		INTEGER,
	    filterProfile-InputFilters-RouteFilter-Action
		INTEGER,
	    filterProfile-InputFilters-IpxFilter-SrcNetAddress
		DisplayString,
	    filterProfile-InputFilters-IpxFilter-DestNetAddress
		DisplayString,
	    filterProfile-InputFilters-IpxFilter-SrcNodeAddress
		DisplayString,
	    filterProfile-InputFilters-IpxFilter-DestNodeAddress
		DisplayString,
	    filterProfile-InputFilters-IpxFilter-SrcSocket
		DisplayString,
	    filterProfile-InputFilters-IpxFilter-SrcSocketCmp
		INTEGER,
	    filterProfile-InputFilters-IpxFilter-DestSocket
		INTEGER,
	    filterProfile-InputFilters-IpxFilter-DstSocketCmp
		INTEGER,
	    filterProfile-InputFilters-TosFilter-Protocol
		INTEGER,
	    filterProfile-InputFilters-TosFilter-SourceAddressMask
		IpAddress,
	    filterProfile-InputFilters-TosFilter-SourceAddress
		IpAddress,
	    filterProfile-InputFilters-TosFilter-DestAddressMask
		IpAddress,
	    filterProfile-InputFilters-TosFilter-DestAddress
		IpAddress,
	    filterProfile-InputFilters-TosFilter-oSrcPortCmp
		INTEGER,
	    filterProfile-InputFilters-TosFilter-SourcePort
		INTEGER,
	    filterProfile-InputFilters-TosFilter-oDstPortCmp
		INTEGER,
	    filterProfile-InputFilters-TosFilter-DestPort
		INTEGER,
	    filterProfile-InputFilters-TosFilter-Precedence
		INTEGER,
	    filterProfile-InputFilters-TosFilter-TypeOfService
		INTEGER,
	    filterProfile-InputFilters-TosFilter-MarkingType
		INTEGER,
	    filterProfile-InputFilters-TosFilter-Dscp
		DisplayString
	}

    filterProfile-InputFilters-FilterName	OBJECT-TYPE
	SYNTAX	DisplayString
	ACCESS	read-only
	STATUS	mandatory
	DESCRIPTION	""
	::= { mibfilterProfile-InputFiltersEntry 1 }

    filterProfile-InputFilters-Index-o	OBJECT-TYPE
	SYNTAX	INTEGER
	ACCESS	read-only
	STATUS	mandatory
	DESCRIPTION	""
	::= { mibfilterProfile-InputFiltersEntry 2 }

    filterProfile-InputFilters-ValidEntry	OBJECT-TYPE
	SYNTAX	INTEGER {
		    no (1),
		    yes (2)
		}
	ACCESS	read-write
	STATUS	mandatory
	DESCRIPTION	"When TRUE, this filter entry has been defined and properly initialized. When FALSE, this entry should be skipped when filtering."
	::= { mibfilterProfile-InputFiltersEntry 3 }

    filterProfile-InputFilters-Forward	OBJECT-TYPE
	SYNTAX	INTEGER {
		    no (1),
		    yes (2)
		}
	ACCESS	read-write
	STATUS	mandatory
	DESCRIPTION	"When TRUE a packet matching this filter will be forwarded or restart the idle timer. When FALSE a packet matching this filter will be dropped or not restart the idle timer."
	::= { mibfilterProfile-InputFiltersEntry 4 }

    filterProfile-InputFilters-oType	OBJECT-TYPE
	SYNTAX	INTEGER {
		    genericFilter (1),
		    ipFilter (2),
		    routeFilter (3),
		    ipxFilter (4),
		    tosFilter (5)
		}
	ACCESS	read-write
	STATUS	mandatory
	DESCRIPTION	"The type of filter contained in this entry. Used to select which of the following fields should be used."
	::= { mibfilterProfile-InputFiltersEntry 5 }

    filterProfile-InputFilters-GenFilter-Offset	OBJECT-TYPE
	SYNTAX	INTEGER
	ACCESS	read-write
	STATUS	mandatory
	DESCRIPTION	"Offset from start of frame of data to test."
	::= { mibfilterProfile-InputFiltersEntry 6 }

    filterProfile-InputFilters-GenFilter-Len	OBJECT-TYPE
	SYNTAX	INTEGER
	ACCESS	read-write
	STATUS	mandatory
	DESCRIPTION	"Number of octets to test. Max value is 8 octets."
	::= { mibfilterProfile-InputFiltersEntry 7 }

    filterProfile-InputFilters-GenFilter-More	OBJECT-TYPE
	SYNTAX	INTEGER {
		    no (1),
		    yes (2)
		}
	ACCESS	read-write
	STATUS	mandatory
	DESCRIPTION	"Include next entry in as part of filter."
	::= { mibfilterProfile-InputFiltersEntry 8 }

    filterProfile-InputFilters-GenFilter-CompNeq	OBJECT-TYPE
	SYNTAX	INTEGER {
		    no (1),
		    yes (2)
		}
	ACCESS	read-write
	STATUS	mandatory
	DESCRIPTION	"Defines type of comparison( Equals(FALSE) or Notequals(TRUE). Default is Equals."
	::= { mibfilterProfile-InputFiltersEntry 9 }

    filterProfile-InputFilters-GenFilter-Mask	OBJECT-TYPE
	SYNTAX	DisplayString
	ACCESS	read-write
	STATUS	mandatory
	DESCRIPTION	"A mask to be applied to the data at offset. Only the first len octets will be applied."
	::= { mibfilterProfile-InputFiltersEntry 10 }

    filterProfile-InputFilters-GenFilter-Value	OBJECT-TYPE
	SYNTAX	DisplayString
	ACCESS	read-write
	STATUS	mandatory
	DESCRIPTION	"The value to compare with the masked data. Only the first len octets will be compared."
	::= { mibfilterProfile-InputFiltersEntry 11 }

    filterProfile-InputFilters-IpFilter-Protocol	OBJECT-TYPE
	SYNTAX	INTEGER
	ACCESS	read-write
	STATUS	mandatory
	DESCRIPTION	"The protocol number of the protocol to filter for. If set to zero this entry will match any IP protocol."
	::= { mibfilterProfile-InputFiltersEntry 12 }

    filterProfile-InputFilters-IpFilter-SourceAddressMask	OBJECT-TYPE
	SYNTAX	IpAddress
	ACCESS	read-write
	STATUS	mandatory
	DESCRIPTION	"A mask to apply to a source address before comparison."
	::= { mibfilterProfile-InputFiltersEntry 13 }

    filterProfile-InputFilters-IpFilter-SourceAddress	OBJECT-TYPE
	SYNTAX	IpAddress
	ACCESS	read-write
	STATUS	mandatory
	DESCRIPTION	"A value to compare with the masked source addresses."
	::= { mibfilterProfile-InputFiltersEntry 14 }

    filterProfile-InputFilters-IpFilter-DestAddressMask	OBJECT-TYPE
	SYNTAX	IpAddress
	ACCESS	read-write
	STATUS	mandatory
	DESCRIPTION	"A mask to apply to a destination address before comparison."
	::= { mibfilterProfile-InputFiltersEntry 15 }

    filterProfile-InputFilters-IpFilter-DestAddress	OBJECT-TYPE
	SYNTAX	IpAddress
	ACCESS	read-write
	STATUS	mandatory
	DESCRIPTION	"A value to compare with the masked destination addresses."
	::= { mibfilterProfile-InputFiltersEntry 16 }

    filterProfile-InputFilters-IpFilter-oSrcPortCmp	OBJECT-TYPE
	SYNTAX	INTEGER {
		    none (1),
		    less (2),
		    eql (3),
		    gtr (4),
		    neq (5)
		}
	ACCESS	read-write
	STATUS	mandatory
	DESCRIPTION	"The type of comparison for the source port field. May be set to no comparison."
	::= { mibfilterProfile-InputFiltersEntry 17 }

    filterProfile-InputFilters-IpFilter-SourcePort	OBJECT-TYPE
	SYNTAX	INTEGER
	ACCESS	read-write
	STATUS	mandatory
	DESCRIPTION	"A value to compare with the source port. The comparison is defined by the sourceTest field."
	::= { mibfilterProfile-InputFiltersEntry 18 }

    filterProfile-InputFilters-IpFilter-oDstPortCmp	OBJECT-TYPE
	SYNTAX	INTEGER {
		    none (1),
		    less (2),
		    eql (3),
		    gtr (4),
		    neq (5)
		}
	ACCESS	read-write
	STATUS	mandatory
	DESCRIPTION	"The type of comparison for the destination port field. May be set to no comparison."
	::= { mibfilterProfile-InputFiltersEntry 19 }

    filterProfile-InputFilters-IpFilter-DestPort	OBJECT-TYPE
	SYNTAX	INTEGER
	ACCESS	read-write
	STATUS	mandatory
	DESCRIPTION	"A value to compare with the destination port. The comparison is defined by the destTest field."
	::= { mibfilterProfile-InputFiltersEntry 20 }

    filterProfile-InputFilters-IpFilter-TcpEstab	OBJECT-TYPE
	SYNTAX	INTEGER {
		    no (1),
		    yes (2)
		}
	ACCESS	read-write
	STATUS	mandatory
	DESCRIPTION	"Indicates whether to look at tcp packets in an established connection."
	::= { mibfilterProfile-InputFiltersEntry 21 }

    filterProfile-InputFilters-RouteFilter-SourceAddressMask	OBJECT-TYPE
	SYNTAX	IpAddress
	ACCESS	read-write
	STATUS	mandatory
	DESCRIPTION	"A mask to apply to a source address before comparison."
	::= { mibfilterProfile-InputFiltersEntry 22 }

    filterProfile-InputFilters-RouteFilter-SourceAddress	OBJECT-TYPE
	SYNTAX	IpAddress
	ACCESS	read-write
	STATUS	mandatory
	DESCRIPTION	"A value to compare with the masked source addresses."
	::= { mibfilterProfile-InputFiltersEntry 23 }

    filterProfile-InputFilters-RouteFilter-RouteMask	OBJECT-TYPE
	SYNTAX	IpAddress
	ACCESS	read-write
	STATUS	mandatory
	DESCRIPTION	"A mask to apply to a destination address before comparison."
	::= { mibfilterProfile-InputFiltersEntry 24 }

    filterProfile-InputFilters-RouteFilter-RouteAddress	OBJECT-TYPE
	SYNTAX	IpAddress
	ACCESS	read-write
	STATUS	mandatory
	DESCRIPTION	"A value to compare with the masked destination addresses."
	::= { mibfilterProfile-InputFiltersEntry 25 }

    filterProfile-InputFilters-RouteFilter-AddMetric	OBJECT-TYPE
	SYNTAX	INTEGER
	ACCESS	read-write
	STATUS	mandatory
	DESCRIPTION	"A value to be added to metric of the route, this is valid only when action is add."
	::= { mibfilterProfile-InputFiltersEntry 26 }

    filterProfile-InputFilters-RouteFilter-Action	OBJECT-TYPE
	SYNTAX	INTEGER {
		    none (1),
		    accept (2),
		    deny (3),
		    add (4)
		}
	ACCESS	read-write
	STATUS	mandatory
	DESCRIPTION	"The type of action taken when match occurs."
	::= { mibfilterProfile-InputFiltersEntry 27 }

    filterProfile-InputFilters-IpxFilter-SrcNetAddress	OBJECT-TYPE
	SYNTAX	DisplayString
	ACCESS	read-write
	STATUS	mandatory
	DESCRIPTION	"A value to compare with source network addresses."
	::= { mibfilterProfile-InputFiltersEntry 28 }

    filterProfile-InputFilters-IpxFilter-DestNetAddress	OBJECT-TYPE
	SYNTAX	DisplayString
	ACCESS	read-write
	STATUS	mandatory
	DESCRIPTION	"A value to compare with destination network addresses."
	::= { mibfilterProfile-InputFiltersEntry 29 }

    filterProfile-InputFilters-IpxFilter-SrcNodeAddress	OBJECT-TYPE
	SYNTAX	DisplayString
	ACCESS	read-write
	STATUS	mandatory
	DESCRIPTION	"A value to compare with source node addresses."
	::= { mibfilterProfile-InputFiltersEntry 30 }

    filterProfile-InputFilters-IpxFilter-DestNodeAddress	OBJECT-TYPE
	SYNTAX	DisplayString
	ACCESS	read-write
	STATUS	mandatory
	DESCRIPTION	"A value to compare with destination node addresses."
	::= { mibfilterProfile-InputFiltersEntry 31 }

    filterProfile-InputFilters-IpxFilter-SrcSocket	OBJECT-TYPE
	SYNTAX	DisplayString
	ACCESS	read-write
	STATUS	mandatory
	DESCRIPTION	"The type of comparison for the source socket field. May be set to no comparison."
	::= { mibfilterProfile-InputFiltersEntry 32 }

    filterProfile-InputFilters-IpxFilter-SrcSocketCmp	OBJECT-TYPE
	SYNTAX	INTEGER {
		    none (1),
		    less (2),
		    eql (3),
		    gtr (4),
		    neq (5)
		}
	ACCESS	read-write
	STATUS	mandatory
	DESCRIPTION	"The type of comparison for the source socket field. May be set to no comparison."
	::= { mibfilterProfile-InputFiltersEntry 33 }

    filterProfile-InputFilters-IpxFilter-DestSocket	OBJECT-TYPE
	SYNTAX	INTEGER
	ACCESS	read-write
	STATUS	mandatory
	DESCRIPTION	"A value to compare with the destination socket. The comparison is defined by the destTest field."
	::= { mibfilterProfile-InputFiltersEntry 34 }

    filterProfile-InputFilters-IpxFilter-DstSocketCmp	OBJECT-TYPE
	SYNTAX	INTEGER {
		    none (1),
		    less (2),
		    eql (3),
		    gtr (4),
		    neq (5)
		}
	ACCESS	read-write
	STATUS	mandatory
	DESCRIPTION	"The type of comparison for the destination socket field. May be set to no comparison."
	::= { mibfilterProfile-InputFiltersEntry 35 }

    filterProfile-InputFilters-TosFilter-Protocol	OBJECT-TYPE
	SYNTAX	INTEGER
	ACCESS	read-write
	STATUS	mandatory
	DESCRIPTION	"The protocol number of the protocol you like to support type-of-service. If set to zero this entry will match any IP protocol."
	::= { mibfilterProfile-InputFiltersEntry 36 }

    filterProfile-InputFilters-TosFilter-SourceAddressMask	OBJECT-TYPE
	SYNTAX	IpAddress
	ACCESS	read-write
	STATUS	mandatory
	DESCRIPTION	"A mask to apply to a source address before comparison."
	::= { mibfilterProfile-InputFiltersEntry 37 }

    filterProfile-InputFilters-TosFilter-SourceAddress	OBJECT-TYPE
	SYNTAX	IpAddress
	ACCESS	read-write
	STATUS	mandatory
	DESCRIPTION	"A value to compare with the masked source addresses."
	::= { mibfilterProfile-InputFiltersEntry 38 }

    filterProfile-InputFilters-TosFilter-DestAddressMask	OBJECT-TYPE
	SYNTAX	IpAddress
	ACCESS	read-write
	STATUS	mandatory
	DESCRIPTION	"A mask to apply to a destination address before comparison."
	::= { mibfilterProfile-InputFiltersEntry 39 }

    filterProfile-InputFilters-TosFilter-DestAddress	OBJECT-TYPE
	SYNTAX	IpAddress
	ACCESS	read-write
	STATUS	mandatory
	DESCRIPTION	"A value to compare with the masked destination addresses."
	::= { mibfilterProfile-InputFiltersEntry 40 }

    filterProfile-InputFilters-TosFilter-oSrcPortCmp	OBJECT-TYPE
	SYNTAX	INTEGER {
		    none (1),
		    less (2),
		    eql (3),
		    gtr (4),
		    neq (5)
		}
	ACCESS	read-write
	STATUS	mandatory
	DESCRIPTION	"The type of comparison for the source port field. May be set to no comparison."
	::= { mibfilterProfile-InputFiltersEntry 41 }

    filterProfile-InputFilters-TosFilter-SourcePort	OBJECT-TYPE
	SYNTAX	INTEGER
	ACCESS	read-write
	STATUS	mandatory
	DESCRIPTION	"A value to compare with the source port. The comparison is defined by the sourceTest field."
	::= { mibfilterProfile-InputFiltersEntry 42 }

    filterProfile-InputFilters-TosFilter-oDstPortCmp	OBJECT-TYPE
	SYNTAX	INTEGER {
		    none (1),
		    less (2),
		    eql (3),
		    gtr (4),
		    neq (5)
		}
	ACCESS	read-write
	STATUS	mandatory
	DESCRIPTION	"The type of comparison for the destination port field. May be set to no comparison."
	::= { mibfilterProfile-InputFiltersEntry 43 }

    filterProfile-InputFilters-TosFilter-DestPort	OBJECT-TYPE
	SYNTAX	INTEGER
	ACCESS	read-write
	STATUS	mandatory
	DESCRIPTION	"A value to compare with the destination port. The comparison is defined by the destTest field."
	::= { mibfilterProfile-InputFiltersEntry 44 }

    filterProfile-InputFilters-TosFilter-Precedence	OBJECT-TYPE
	SYNTAX	INTEGER {
		    n-000 (1),
		    n-001 (33),
		    n-010 (65),
		    n-011 (97),
		    n-100 (129),
		    n-101 (161),
		    n-110 (193),
		    n-111 (225)
		}
	ACCESS	read-write
	STATUS	mandatory
	DESCRIPTION	"Tag the precedence bits (priority bits) in the TOS octet of IP datagram header with this value when match occurs."
	::= { mibfilterProfile-InputFiltersEntry 45 }

    filterProfile-InputFilters-TosFilter-TypeOfService	OBJECT-TYPE
	SYNTAX	INTEGER {
		    normal (1),
		    cost (3),
		    reliability (5),
		    throughput (9),
		    latency (17)
		}
	ACCESS	read-write
	STATUS	mandatory
	DESCRIPTION	"Tag the type of service field in the TOS octet of IP datagram header with this value when match occurs."
	::= { mibfilterProfile-InputFiltersEntry 46 }

    filterProfile-InputFilters-TosFilter-MarkingType	OBJECT-TYPE
	SYNTAX	INTEGER {
		    precedenceTos (1),
		    dscp (2)
		}
	ACCESS	read-write
	STATUS	mandatory
	DESCRIPTION	"Select type of packet marking."
	::= { mibfilterProfile-InputFiltersEntry 47 }

    filterProfile-InputFilters-TosFilter-Dscp	OBJECT-TYPE
	SYNTAX	DisplayString
	ACCESS	read-write
	STATUS	mandatory
	DESCRIPTION	"DSCP tag to be used in marking of the packets (if marking-type = dscp)."
	::= { mibfilterProfile-InputFiltersEntry 48 }

END
