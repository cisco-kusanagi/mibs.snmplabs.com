WESTERN-MULTIPLEX-RAD10006-MIB 

DEFINITIONS ::= BEGIN


IMPORTS 
    TRAP-TYPE               FROM RFC-1215
    DisplayString           FROM RFC1213-MIB
    trapSequenceNumber      FROM WESTERN-MULTIPLEX-MIB
    enterprises,
    OBJECT-TYPE             FROM RFC1155-SMI;

western-multiplex  OBJECT IDENTIFIER ::= { enterprises 3727 }
tsunami100-06      OBJECT IDENTIFIER ::= { western-multiplex 20 }
radio              OBJECT IDENTIFIER ::= { tsunami100-06 20 }

--   Hex16bit ::= DisplayString (SIZE (4))
--**********************************************************
--  Hex16bit represents the 16-bit hexadecimal value.
--  It is typically used to represent information that is
--  normally observed in hexadecimal notation, such as
--  bitmasks. Variables defined with this convention 
--  have their values displayed without a leading '0x' and
--  are in the range of "0x0000" - "0xffff".
--  Note: "HP Openview for Windows" does not properly display
--        variables that are specified with this textual
--        convention. 
--        Therefore, we use 'DisplayString (SIZE(4))'
--        instead of the preferred 'Hex16bit'.
--        We have left this definition for reference.
--**********************************************************

--   DateTimeStamp ::= DisplayString (SIZE(11..16))
--**********************************************************
--  DateTimeStamp represents the date and time of an event.
--  The Agent puts the internal timestamp
--  in the format "MM/DD/YYYY HH:MM"  where:
--         MM/DD/YYYY: is the month/day/year
--         HH:MM:SS:   is the hours:minutes in 
--                        military time (hours from 00-23).
--  Note: "HP Openview for Windows" does not properly display
--        variables that are specified with this textual
--        convention. 
--        Therefore, we use 'DisplayString (SIZE(11..16))'
--        instead of the preferred 'DateTimeStamp'.
--        We have left this definition for reference.
--**********************************************************



--**********************************************************
--*  MIB Objects
--**********************************************************
    --**********************************************************
    --*   CONFIG Subtree (radio Specific Platform)
    --*   enterprises.western-multiplex.tsunami100-06.radio.config
    --**********************************************************
config       OBJECT IDENTIFIER ::= { radio 1 }

--*************************************************
--*  The Radio Configuration
--*************************************************

cnfgT1LineCode OBJECT-TYPE
    SYNTAX      INTEGER
        {
        b8zs(1),                          --*  
        ami(2)                            --*  
        }
    ACCESS      read-write
    STATUS      mandatory
    DESCRIPTION
                "This persistent variable contains the current
                T1 line encoding/decoding method. 

                'B8ZS' selects the Bipolar With 8-bit Zero Substitution
                encoding/decoding.

                'AMI' selects Alternate Mark Inversion encoding/
                decoding.
                
                The default value for this variable is 'B8ZS'."
    ::= { config 1 }

cnfgT1LineBuildOut OBJECT-TYPE
    SYNTAX      INTEGER
        {
        lb-0-133-ft(1),                --*  
        lb-133-266-ft(2),              --*  
        lb-266-399-ft(3),              --*  
        lb-399-533-ft(4),              --*  
        lb-533-655-ft(5)               --*  
        }
    ACCESS      read-write
    STATUS      mandatory
    DESCRIPTION
                "This persistent variable contains the current T1
				Line Build Out configuration for the radio. 
                For DSX-1 applications, line lengths from 0 to 655 feet
                (as measured from the DS-1 connector to the DSX-1 
                cross connect) are selectable.  The five partition
                arrangement meets ANSI T1.102-1993 requirements when 
                using ABAM cable.

                The default value for this variable is 'lb-0-133-ft'."
    ::= { config 2 }

cnfgT1NearEndRadioLoopback OBJECT-TYPE
    SYNTAX      INTEGER
        {
        disabled(1),            --*  
        enabled(2)              --*  
        }
    ACCESS      read-write
    STATUS      mandatory
    DESCRIPTION
                "This non-persistent variable contains the current state of
                the loopback mode for the radio side of the T1 channel
                of the radio.

                'enabled' reconfigures the T1 data path of the radio.
                The data path is set to take data received from the radio
                side of the system and send it back out the transmitter of
				the radio.

                'disabled' turns off the T1 channel radio loopback
                mode, and allows T1 data received from the radio side of 
                the system to be presented to its Line Interface Unit, and
                T1 data received from the Line Interface Unit to be
                transmitted by the radio.

               The default value for this variable is disabled(2)."
    ::= { config 3 }

cnfgT1FarEndRadioLoopback OBJECT-TYPE
    SYNTAX      INTEGER
        {
        disabled(1),            --*  
        enabled(2)              --*  
        }
    ACCESS      read-write
    STATUS      mandatory
    DESCRIPTION
                "This non-persistent variable contains the current state of
                the loopback mode for the radio side of the T1 channel
                of the remote radio.

                'enabled' reconfigures the T1 data path of the radio.
                The data path is set to take data received from the radio
                side of the system and send it back out the transmitter of
		        the radio.

                'disabled' turns off the T1 channel radio loopback
                mode, and allows T1 data received from the radio side of 
                the system to be presented to its Line Interface Unit, and
                T1 data received from the Line Interface Unit to be
                transmitted by the radio.

               The default value for this variable is disabled(2)."
    ::= { config 4 }

cnfgT1InputAlarm OBJECT-TYPE
    SYNTAX      INTEGER
        {

        enabled(1),          --*  
        disabled(2)          --*  
        }
    ACCESS      read-write
    STATUS      mandatory
    DESCRIPTION
                "This non-persistent variable contains the configuration 
                setting of the T1 channel input. It allows the SNMP user
		        to control T1 channel input.

                'enabled' enables the T1 channel input.

                'disabled' disables the T1 channel input.
                
                The default value for this variable is 'disabled'."
    ::= { config 5 }

cnfgAIS OBJECT-TYPE
    SYNTAX      INTEGER
        {
        disabled(1),         --*  
        enabled(2)           --*  
        }
    ACCESS      read-write
    STATUS      mandatory
    DESCRIPTION
                "This non-persistent variable contains the configuration 
                setting of the AIS output. It allows the SNMP user to
		        control AIS output.

                'enabled' enables the AIS output.

                'disabled' disables the AIS output.
                
                The default value for this variable is 'disabled'."
    ::= { config 6 }

cnfgOrderwireAddr OBJECT-TYPE
    SYNTAX      DisplayString (SIZE(2))
    ACCESS      read-write
    STATUS      mandatory
    DESCRIPTION
                "This persistent variable contains the current number
                of the two-digit engineering orderwire (EOW) phone 
                number of the handset connected to the radio. The phone
		number can range from 00 to 99.  
               
                When a telephone user on another radio of this radio 
                network dials a two digit orderwire phone number matching
                this variable's value, then this radio rings its bell.
                
                The default value for this variable is '00', which sets
                the phone number of the local orderwire handset to 00."                
    ::= { config 7 }

cnfgLinkSecurityCode OBJECT-TYPE
    SYNTAX      DisplayString (SIZE(12))
    ACCESS      read-write
    STATUS      mandatory
    DESCRIPTION
                "This persistent variable contains the current number of the 
		        12-byte security code. It allows the SNMP user to read and set
				the link security code. The link security code has to be hex
				numbers (0 to f).

                There is no default value for this variable."
    ::= { config 8 }

cnfgLearningFilter OBJECT-TYPE
    SYNTAX      INTEGER
        {
        disabled(1),         --*  
        enabled(2)           --*  
        }
    ACCESS      read-write
    STATUS      mandatory
    DESCRIPTION
                "This persistent variable configures the learning filter.

                'disabled' turns off the learning filter.

                'enabled' turns on the learning filter.
               
                There is no default value for this variable."
    ::= { config 9 }

cnfgFiberOpticInterface OBJECT-TYPE
    SYNTAX      INTEGER
        {
        disabled(1),         --*  
        enabled(2)           --*  
        }
    ACCESS      read-write
    STATUS      mandatory
    DESCRIPTION
                "This persistent variable configures the fiber interface.

                'disabled' turns off the fiber interface.

                'enabled' turns on the fiber interface.
               
                There is no default value for this variable."
    ::= { config 10 }

cnfgEthernetDuplex  OBJECT-TYPE
    SYNTAX      INTEGER
        {
         full-duplex(1),       --*  
         half-duplex(2)        --*  
        }
    ACCESS      read-write
    STATUS      mandatory
    DESCRIPTION
                "This persistent variable contains the current configuration
		        of the ethernet communication mode.

                'full-duplex' indicates ethernet communicates in full duplex mode.

                'half-duplex' indicates ethernet communicates in half duplex mode.

                There is no default value for this variable."
    ::= { config 11 }

cnfgDataRate OBJECT-TYPE
    SYNTAX      INTEGER
        {
        full-duplex-45-MB(1),              --*  
        datarate2(2),                      --*  
        datarate3(3)
        }
    ACCESS      read-only
    STATUS      mandatory
    DESCRIPTION
                "This persistent variable contains the current configuration
		        of the data rate.
                'full-duplex-45-MB' indicates 45 MB data rate with full duplex
                 operation.

                 datarate2 is undefined yet.

                 datarate3 is undefined yet.

                There is no default value for this variable."
    ::= { config 12 }

cnfgInterfaceType OBJECT-TYPE
    SYNTAX      INTEGER
        {
        t1-100BaseT(1),                --*  
        t1-10BaseT(2)                  --*  
        }
    ACCESS      read-only
    STATUS      mandatory
    DESCRIPTION
                "This persistent variable contains the current configuration
		        of interface type.
                't1-100BaseT' indicates 100BaseT and a T1 channel.
                't1-10BaseT' indicates 10BaseT and a T1 channel.
                There is no default value for this variable."
    ::= { config 13 }

cnfgIDUSWVersion OBJECT-TYPE
    SYNTAX      DisplayString (SIZE(4))
    ACCESS      read-only
    STATUS      mandatory
    DESCRIPTION
                "This persistent variable contains the current number of the 
		        4-byte IDU software Version.
                There is no default value for this variable."
    ::= { config 14 }

cnfgNMUSWVersion OBJECT-TYPE
    SYNTAX      DisplayString (SIZE(4))
    ACCESS      read-only
    STATUS      mandatory
    DESCRIPTION
                "This persistent variable contains the current number of the 
		        4-byte NMU software Version.
                There is no default value for this variable."
    ::= { config 15 }

    
--***********************************************************************
--***********************************************************************
--***********************************************************************
--***********************************************************************

    --**********************************************************
    --*   PERF Subtree (radio Specific Platform)
    --*   enterprises.western-multiplex.tsunami100-06.radio.perf
    --**********************************************************
perf       OBJECT IDENTIFIER ::= { radio 4 }

--*************************************************************************
--*  The Performance Variables - System Monitored Parameters and Statistics
--*************************************************************************

perfCurrentBER    OBJECT-TYPE
    SYNTAX      DisplayString (SIZE(8))
    ACCESS      read-only
    STATUS      mandatory
    DESCRIPTION
                "This variable. 'perfCurrentBER' contains a calculation of
				the estimated bit error rate of the aggregate data channel,
				after FEC decoding."                
    ::= { perf 1 }

perfCurrentRSL OBJECT-TYPE
    SYNTAX      INTEGER
    ACCESS      read-only
    STATUS      mandatory
    DESCRIPTION
                "This variable, 'perfCurrentRSL' contains the current
                received signal level, measured in dBm. The received
		        signal level, or RSL, is measured in the Receiver Unit,
				or RCVR, of the radio."
   ::= { perf 2 }

perfErrorSeconds    OBJECT-TYPE
    SYNTAX      INTEGER
    ACCESS      read-only
    STATUS      mandatory
    DESCRIPTION
                "This variable. 'perfErrorSeconds' contains a count of the
				number of one second periods with one or more bit errors."
    ::= { perf 3 }

perfSeverelyErroredSeconds  OBJECT-TYPE
    SYNTAX      INTEGER
    ACCESS      read-only
    STATUS      mandatory
    DESCRIPTION
                "This variable. 'perfSeverelyErroredSeconds' contains a count
				of the number of one second periods with an error rate greater
				than 10^-6 for the entire one second." 
    ::= { perf 4 }

perfMinRSL OBJECT-TYPE
    SYNTAX      INTEGER
    ACCESS      read-only
    STATUS      mandatory
    DESCRIPTION
                "This variable,'perfMinRSL' contains the lowest received
				signal level within the measuring period. The received
				signal level, or RSL, is measured in dBm, in the Receiver
				Unit, or RCVR, of the radio."
   ::= { perf 5 }

perfMaxRSL OBJECT-TYPE
    SYNTAX      INTEGER
    ACCESS      read-only
    STATUS      mandatory
    DESCRIPTION
                "This variable, 'perfMaxRSL' contains the highest
                received signal level within the measuring period.
		The received signal level, or RSL, is measured in
		dBm, in the Receiver Unit, or RCVR, of the radio."
   ::= { perf 6 }

perfElapsedSecondsSinceReset  OBJECT-TYPE
    SYNTAX      INTEGER
    ACCESS      read-only
    STATUS      mandatory
    DESCRIPTION
                "This variable, 'perfElapsedSecondsSinceReset' contains a value
			    which corresponds to the total number of seconds has elapsed
				since the start of the performance measurement."               
  ::= { perf 7 }

perfHistoryReset    OBJECT-TYPE
    SYNTAX      INTEGER
        {
        history-reset(1),  --*  
        normal(2)            --*  
        }
    ACCESS      read-write
    STATUS      mandatory
    DESCRIPTION
                "This variable, 'perfHistoryReset' is a command to clear all the
		        counters in the performance table.

                Setting this variable to 'history-reset' will cause all the  
                counters in the performance table to be cleared.

                Setting this variable to 'normal' has no effect to the performance
                table."
  ::= { perf 8 }


--***********************************************************************
--***********************************************************************
--***********************************************************************
--***********************************************************************

    --******************************************************************
    --*   STATUS Subtree (radio Specific Platform)
    --*   enterprises.western-multiplex.tsunami100-06.radio.status
    --******************************************************************
status       OBJECT IDENTIFIER ::= { radio 2 }

statRadioLogHealth OBJECT-TYPE
    SYNTAX      INTEGER
        {
        normal-health(1),        --*
        warning-health(2),       --*
        minor-health(3),         --*
        major-health(4),         --*
        critical-health(5)       --*
        }
    ACCESS      read-only
    STATUS      mandatory
    DESCRIPTION
                "This non-persistent variable indicates the current health
                status of the radio, determined by the Network 
                Management Unit, or NMU's system event log. This MIB 
                variable can be polled to provide a high-level status of 
                the managed radio.

                This variable is identical to 'logRadioHEALTH' defined in
                the 'WESTERN-MULTIPLEX-MIB'.

                This variable indicates the highest severity level of
                any NMU system log record that has a 'health' and 'radio' 
                qualifiers.  Records that do not have a 'health' and a 
                'Radio' qualifier do not effect this variable.  Records 
                that have been 'NORMALIZED' (see the definition in 
                'logRecDescription' in 'WESTERN-MULTIPLEX-MIB') do not 
                effect this variable.
                
                'critical-health' is the highest severity level, followed 
                in decreasing order by 'major-health', 'minor-health', 
                'warning-health', and 'normal-health', which is the 
                lowest 'health' severity level.
                
                If this variable has a value of 'normal-health', then 
                either there are no records that effect health and are
                qualified by 'Radio' in the system log, or the only health
                effecting records qualified by 'radio' have a severity 
                level of 'normal-health'.

                There is no default value for this variable."
    ::= { status 1 }

statNMULink OBJECT-TYPE
    SYNTAX      INTEGER
        {
        link-down(1),         --*   
        link-up(2)           --*  
        }
    ACCESS      read-only
    STATUS      mandatory
    DESCRIPTION
                "This non-persistent variable contains the current status
                of the radio to nmu link . This MIB variable can be polled to
                provide a high-level status of the radio.

                'link-down' indicates that the radio to nmu link is currently
                down.

                'link-up' indicates that the radio to nmu link is currently up.
                
                The default value for this variable is link-down(1)."
    ::= { status 2  }

statAlarmSummary OBJECT-TYPE
    SYNTAX      INTEGER
        {
        alarm-unknown(1),         --*   
        alarm-normal(2),          --*  
        alarm-triggered(3) 
        }
    ACCESS      read-only
    STATUS      mandatory
    DESCRIPTION
                "This non-persistent variable contains the current status
                of the radio. This MIB variable can be polled to provide
		        a high-level status of the radio.

                'alarm_unknown' indicates that the radio to nmu link is currently
                down and the radio status cannot be determined. 

                'alarm_normal' indicates that the radio currently has no alarm
                condition.

                'alarm_triggered' indicates that the radio currently has one or
                more alarm conditions.
                
                The default value for this variable is alarm_unknown(1)."
    ::= { status 3 }

statT1Input OBJECT-TYPE
    SYNTAX      INTEGER
        {
        alarm-unknown(1),         --*   
        alarm-normal(2),          --*  
        alarm-triggered(3) 
        }
    ACCESS      read-only
    STATUS      mandatory
    DESCRIPTION
                "This non-persistent variable contains the current status
                of the radio. This MIB variable can be polled to provide
		        a high-level status of the radio.

                'alarm_unknown' indicates that the radio to nmu link is currently
                down and the radio status cannot be determined. 

                'alarm_normal' indicates that the radio's T1 Input currently has no alarm
                conditions.

                'alarm_triggered' indicates that the radio currently has no T1 input signal.
                
                The default value for this variable is alarm_unknown(1)."
    ::= { status 21  }

statT1CodeViolation OBJECT-TYPE
    SYNTAX      INTEGER
        {
        alarm-unknown(1),         --*   
        alarm-normal(2),          --*  
        alarm-triggered(3) 
        }
    ACCESS      read-only
    STATUS      mandatory
    DESCRIPTION
                "This non-persistent variable contains the current status
                of the radio. This MIB variable can be polled to provide
		        a high-level status of the radio.

                'alarm_unknown' indicates that the radio to nmu link is currently
                down and the radio status cannot be determined. 

                'alarm_normal' indicates that the radio's T1 input currently has no
				code violation alarm.

                'alarm_triggered' indicates that the radio's T1 input currently has an
				code violation alarm.
                
                The default value for this variable is alarm_unknown(1)."
    ::= { status 22  }

statT1LineDriver OBJECT-TYPE
    SYNTAX      INTEGER
        {
        alarm-unknown(1),         --*   
        alarm-normal(2),          --*  
        alarm-triggered(3) 
        }
    ACCESS      read-only
    STATUS      mandatory
    DESCRIPTION
                "This non-persistent variable contains the current status
                of the radio. This MIB variable can be polled to provide
		        a high-level status of the radio.

                'alarm_unknown' indicates that the radio to nmu link is currently
                down and the radio status cannot be determined. 

                'alarm_normal' indicates that the radio's T1 line build out currently
				has no alarm conditions.

                'alarm_triggered' indicates that the radio currently has an T1 line
				build out alarm.
                
                The default value for this variable is alarm_unknown(1)."
    ::= { status 23  }

statT1AIS OBJECT-TYPE
    SYNTAX      INTEGER
        {
        alarm-unknown(1),         --*   
        alarm-normal(2),          --*  
        alarm-triggered(3) 
        }
    ACCESS      read-only
    STATUS      mandatory
    DESCRIPTION
                "This non-persistent variable contains the current status
                of the radio. This MIB variable can be polled to provide
		        a high-level status of the radio.

                'alarm_unknown' indicates that the radio to nmu link is currently
                down and the radio status cannot be determined. 

                'alarm_normal' indicates that the radio currently has no AIS output.

                'alarm_triggered' indicates that the radio currently is generating  
                'Alarm indication Signal', or marking the T1 line with all ones, on
                the transmit output.
                
                The default value for this variable is alarm_unknown(1)."
    ::= { status 24  }

statRadioSync OBJECT-TYPE
    SYNTAX      INTEGER
        {
        alarm-unknown(1),         --*   
        alarm-normal(2),          --*  
        alarm-triggered(3) 
        }
    ACCESS      read-only
    STATUS      mandatory
    DESCRIPTION
                "This non-persistent variable contains the current status
                of the radio. This MIB variable can be polled to provide
		        a high-level status of the radio.

                'alarm_unknown' indicates that the radio to nmu link is currently
                down and the radio status cannot be determined. 

                'alarm_normal' indicates that the radio currently has no frame loss
                alarm.

                'alarm_triggered' indicates that the radio currently has a loss of 5
                or more consecutive frames on the received aggregate data. 
                
                The default value for this variable is alarm_unknown(1)."
    ::= { status 25  }

statBitError OBJECT-TYPE
    SYNTAX      INTEGER
        {
        alarm-unknown(1),         --*   
        alarm-normal(2),          --*  
        alarm-triggered(3) 
        }
    ACCESS      read-only
    STATUS      mandatory
    DESCRIPTION
                "This non-persistent variable contains the current status
                of the radio. This MIB variable can be polled to provide
		        a high-level status of the radio.

                'alarm_unknown' indicates that the radio to nmu link is currently
                down and the radio status cannot be determined. 

                'alarm_normal' indicates that the radio signal currently has a bit
                error rate, or BER, less than 10 to minus 6.

                'alarm_triggered' indicates that the radio signal currently has a
                bit error rate, or BER, less than 10 to minus 6.
                
                The default value for this variable is alarm_unknown(1)."
    ::= { status 26  }

statFan1 OBJECT-TYPE
    SYNTAX      INTEGER
        {
        alarm-unknown(1),         --*   
        alarm-normal(2),          --*  
        alarm-triggered(3) 
        }
    ACCESS      read-only
    STATUS      mandatory
    DESCRIPTION
                "This non-persistent variable contains the current status
                of the radio's . This MIB variable can be polled to provide
		        a high-level status of the radio.
 
                'alarm_unknown' indicates that the radio to nmu link is currently
                down and the radio status cannot be determined. 

                'alarm_normal' indicates that the radio fan 1 unit has no alarm.

                'alarm_triggered' indicates that the radio fan 1 unit is not present,
                unplugged, or is not rotating.
               
                The default value for this variable is alarm_unknown(1)."
    ::= { status 27 }

statFan2 OBJECT-TYPE
    SYNTAX      INTEGER
        {
        alarm-unknown(1),         --*   
        alarm-normal(2),          --*  
        alarm-triggered(3) 
        }
    ACCESS      read-only
    STATUS      mandatory
    DESCRIPTION
                "This non-persistent variable contains the current status
                of the radio's . This MIB variable can be polled to provide
		        a high-level status of the radio.

                'alarm_unknown' indicates that the radio to nmu link is currently
                down and the radio status cannot be determined. 

                'alarm_normal' indicates that the radio fan 2 unit has no alarm.

                'alarm_triggered' indicates that the radio fan 2 unit is not present,
                unplugged, or is not rotating.
               
                The default value for this variable is alarm_unknown(1)."
     ::= { status 28  }

statRxSynth OBJECT-TYPE
    SYNTAX      INTEGER
        {
        alarm-unknown(1),         --*   
        alarm-normal(2),          --*  
        alarm-triggered(3) 
        }
    ACCESS      read-only
    STATUS      mandatory
    DESCRIPTION
                "This non-persistent variable contains the current status
                of the radio's . This MIB variable can be polled to provide
		        a high-level status of the radio.

                'alarm_unknown' indicates that the radio to nmu link is currently
                down and the radio status cannot be determined. 

                'alarm_normal' indicates that the radio receive signal currently
                has no sync alarm.

                'alarm_triggered' indicates that the radio's receiver-synthesizer
				is currently in an alarm condition.

                The default value for this variable is alarm_unknown(1)."
    ::= { status 29 }

statTxSynth OBJECT-TYPE
    SYNTAX      INTEGER
        {
        alarm-unknown(1),         --*   
        alarm-normal(2),          --*  
        alarm-triggered(3) 
        }
    ACCESS      read-only
    STATUS      mandatory
    DESCRIPTION
                "This non-persistent variable contains the current status
                of the radio's . This MIB variable can be polled to provide
		        a high-level status of the radio.

                'alarm_unknown' indicates that the radio to nmu link is currently
                down and the radio status cannot be determined. 

                'alarm_normal' indicates that the radio Transmit signal currently
                has no sync alarm.

                'alarm_triggered' indicates that the radio's transmitter-synthesizer
				is currently in an alarm condition.
                
                The default value for this variable is alarm_unknown(1)."
    ::= { status 30  }


    --**********************************************************
    --*   MGMT Subtree (radio Specific Platform)
    --*   enterprises.western-multiplex.tsunami100-06.radio.mgmt
    --**********************************************************
mgmt       OBJECT IDENTIFIER ::= { radio 3 }

mgmtNMULinkTrapControl OBJECT-TYPE
    SYNTAX      INTEGER
        {
        no-trap(1),                           --*
        send-trap-on-alarm-transition(2),     --*
        send-trap-on-normal-transition(3),    --*
        send-trap-on-both-transitions(4)      --*
        }
    ACCESS      read-write
    STATUS      mandatory
    DESCRIPTION
                "This persistent variable controls whether the Agent will 
                attempt to send the 'nmuLinkTrap' trap whenever the 
                link condition between Radio and the NMU has a transition.
								
                The 'nmuLinkTrap' trap is defined in this MIB definition file.

                'no-trap' indicates that the NMU, should not generate any 
                SNMP trap on any transition. This is the default value.
                
                'send-trap-on-alarm-transition' indicates that the NMU will
                only generate a SNMP trap on the transition to the 'alarm'
                state. 

                'send-trap-on-normal-transition' indicates that the NMU will
				only generate a SNMP trap on the transition to the 'normal'
				state. 

                'send-trap-on-both-transitions' indicates that the NMU will
                generate a SNMP trap on any transition. 

                Whenever the SNMP Agent attempts to send the 'nmuLinkTrap'
                trap, other checks described below may prohibit this trap 
                from transmission.

                Whenever this variable prohibits a trap from being sent,
                then 'trapFilteredSpecific' will be incremented.

                This MIB variable is the first of four checks that the NMU
                Agent uses to filter traps, based upon 1) a specific 
                enable or disable control variable; 2) 'trapControl' which
                offers a gross on/off/limit control; 3) 'trapMgrTable' 
                with 'trapMgrControl' and 'trapMgrAddress' which filters 
                whether enterprise traps (such as this trap) and/or 
                standard (RFC 1215) traps are sent to each specific trap 
                manager; and 4) 'trapSeverityFilter' which filters traps 
                according to a controlling severity variable for the 
                specific trap, which in this case is described below, and
                is defined as 'mgmtNMULinkSeverity'.
                
                Whenever any of these trap filters cause a trap to be 
                filtered, the corresponding MIB statistic is incremented.
                These statistics are 'trapFilteredSpecific', 
                'trapFilteredControl', 'trapFilteredManager', and 
                'trapFilteredSeverity'.

                See the MIB descriptions (in this file, and in 
                'westmux.mib' file) for any of these above variables for 
                details."
    ::= { mgmt 1 }

mgmtNMULinkSeverity OBJECT-TYPE
    SYNTAX      INTEGER
        {
        normal(1),               --*
        warning(2),              --*
        minor(3),                --*
        major(4),                --*
        critical(5)              --*
        }
    ACCESS      read-write
    STATUS      mandatory
    DESCRIPTION
                "This persistent variable indicates the desired severity 
                level to be associated with the log event and the SNMP 
                trap that record the occurance of a particular event.  
                
                In this case, the event indicates the detection of a 
                transition of the link condition between the Radio and
		        the NMU.

                This severity level variable is associated with the
                'nmuLinkTrap' trap, and a log event message that indicates
				a change in the Radio's link condition to the NMU.

                'critical' is the highest severity level, followed in
				decreasing order by 'major', 'minor', 'warning', and
				'normal', which is the lowest severity level.

                The default severity level is 'normal'.

                This trap may also be filtered by 
                'mgmtNMULinkTrapControl'."
    ::= { mgmt 2 }

mgmtT1InputTrapControl OBJECT-TYPE
    SYNTAX      INTEGER
        {
        no-trap(1),                           --*
        send-trap-on-alarm-transition(2),     --*
        send-trap-on-normal-transition(3),    --*
        send-trap-on-both-transitions(4)      --*
        }
    ACCESS      read-write
    STATUS      mandatory
    DESCRIPTION
                "This persistent variable controls whether the Agent will 
                attempt to send the 't1InTrap' trap whenever the Radio
				has a transition of the T1 INPUT condition.

                The 't1InTrap' trap is defined in this MIB definition 
                file.

                'no-trap' indicates that the NMU, should not generate any 
                SNMP trap on any transition. This is the default value.
                
                'send-trap-on-alarm-transition' indicates that the NMU will
                only generate a SNMP trap on the transition to the 'alarm'
                state. 

                'send-trap-on-normal-transition' indicates that the NMU 
                will only generate a SNMP trap on the transition to the 
                'normal' state. 

                'send-trap-on-both-transitions' indicates that the NMU will
                generate a SNMP trap on any transition. 

                Whenever the SNMP Agent attempts to send the 't1InTrap'
                trap, other checks described below may prohibit this trap 
                from transmission.

                Whenever this variable prohibits a trap from being sent,
                then 'trapFilteredSpecific' will be incremented.

                This MIB variable is the first of four checks that the NMU
                Agent uses to filter traps, based upon 1) a specific 
                enable or disable control variable; 2) 'trapControl' which
                offers a gross on/off/limit control; 3) 'trapMgrTable' 
                with 'trapMgrControl' and 'trapMgrAddress' which filters 
                whether enterprise traps (such as this trap) and/or 
                standard (RFC 1215) traps are sent to each specific trap 
                manager; and 4) 'trapSeverityFilter' which filters traps 
                according to a controlling severity variable for the 
                specific trap, which in this case is described below, and
                is defined as 'mgmtT1InputSeverity'.
                
                Whenever any of these trap filters cause a trap to be 
                filtered, the corresponding MIB statistic is incremented.
                These statistics are 'trapFilteredSpecific', 
                'trapFilteredControl', 'trapFilteredManager', and 
                'trapFilteredSeverity'.

                See the MIB descriptions (in this file, and in 
                'westmux.mib' file) for any of these above variables for 
                details."
    ::= { mgmt 3 }

mgmtT1InputSeverity OBJECT-TYPE
    SYNTAX      INTEGER
        {
        normal(1),               --*
        warning(2),              --*
        minor(3),                --*
        major(4),                --*
        critical(5)              --*
        }
    ACCESS      read-write
    STATUS      mandatory
    DESCRIPTION
                "This persistent variable indicates the desired severity 
                level to be associated with the log event and the SNMP 
                trap that record the occurance of a particular event.  
                
                In this case, the event indicates the detection of a 
                transition of the T1 INPUT condition. 

                This severity level variable is associated with the
                't1InTrap' trap, and a log event message that indicates
                a change in the Radio's T1 Input condition.

                'critical' is the highest severity level, followed
                in decreasing order by 'major', 'minor', 'warning', 
                and 'normal', which is the lowest severity level.

                The default severity level is 'normal'.

                This trap may also be filtered by 
                'mgmtT1InputTrapControl'."
    ::= { mgmt 4 }

mgmtT1CodeViolationTrapControl OBJECT-TYPE
    SYNTAX      INTEGER
        {
        no-trap(1),                           --*
        send-trap-on-alarm-transition(2),     --*
        send-trap-on-normal-transition(3),    --*
        send-trap-on-both-transitions(4)      --*
        }
    ACCESS      read-write
    STATUS      mandatory
    DESCRIPTION
                "This persistent variable controls whether the Agent will 
                attempt to send the 't1CvTrap' trap whenever the
				Radio has a transition of the T1 Code Violation condition.

                The 't1CvTrap' trap is defined in this MIB definition 
                file.

                'no-trap' indicates that the NMU, should not generate any 
                SNMP trap on any transition. This is the default value.
                
                'send-trap-on-alarm-transition' indicates that the NMU will
                only generate a SNMP trap on the transition to the 'alarm'
                state. 

                'send-trap-on-normal-transition' indicates that the NMU 
                will only generate a SNMP trap on the transition to the 
                'normal' state. 

                'send-trap-on-both-transitions' indicates that the NMU will
                generate a SNMP trap on any transition. 

                Whenever the SNMP Agent attempts to send the 't1CvTrap' trap,
				other checks described below may prohibit this trap from
				transmission.

                Whenever this variable prohibits a trap from being sent,
                then 'trapFilteredSpecific' will be incremented.

                This MIB variable is the first of four checks that the NMU
                Agent uses to filter traps, based upon 1) a specific 
                enable or disable control variable; 2) 'trapControl' which
                offers a gross on/off/limit control; 3) 'trapMgrTable' 
                with 'trapMgrControl' and 'trapMgrAddress' which filters 
                whether enterprise traps (such as this trap) and/or 
                standard (RFC 1215) traps are sent to each specific trap 
                manager; and 4) 'trapSeverityFilter' which filters traps 
                according to a controlling severity variable for the 
                specific trap, which in this case is described below, and
                is defined as 'mgmtT1CodeViolationSeverity'.
                
                Whenever any of these trap filters cause a trap to be 
                filtered, the corresponding MIB statistic is incremented.
                These statistics are 'trapFilteredSpecific', 
                'trapFilteredControl', 'trapFilteredManager', and 
                'trapFilteredSeverity'.

                See the MIB descriptions (in this file, and in 
                'westmux.mib' file) for any of these above variables for 
                details."
    ::= { mgmt 5 }

mgmtT1CodeViolationSeverity OBJECT-TYPE
    SYNTAX      INTEGER
        {
        normal(1),               --*
        warning(2),              --*
        minor(3),                --*
        major(4),                --*
        critical(5)              --*
        }
    ACCESS      read-write
    STATUS      mandatory
    DESCRIPTION
                "This persistent variable indicates the desired severity 
                level to be associated with the log event and the SNMP 
                trap that record the occurance of a particular event.  
                
                In this case, the event indicates the detection of a 
                transition of the T1 Code Violation condition. 

                This severity level variable is associated with the
                't1CvTrap' trap, and a log event message that
				indicates a change in the Radio's T1 Code Violation
				condition.

                'critical' is the highest severity level, followed
                in decreasing order by 'major', 'minor', 'warning', 
                and 'normal', which is the lowest severity level.

                The default severity level is 'normal'.

                This trap may also be filtered by 
                'mgmtT1CodeViolationTrapControl'."
    ::= { mgmt 6 }

mgmtT1LineDriverTrapControl OBJECT-TYPE
    SYNTAX      INTEGER
        {
        no-trap(1),                           --*
        send-trap-on-alarm-transition(2),     --*
        send-trap-on-normal-transition(3),    --*
        send-trap-on-both-transitions(4)      --*
        }
    ACCESS      read-write
    STATUS      mandatory
    DESCRIPTION
                "This persistent variable controls whether the Agent will 
                attempt to send the 't1LoTrap' trap whenever the radio has
				a transition of the T1 line build out condition.

                The 't1LoTrap' trap is defined in this MIB definition file.

                'no-trap' indicates that the NMU, should not generate any 
                SNMP trap on any transition. This is the default value.
                
                'send-trap-on-alarm-transition' indicates that the NMU will
                only generate a SNMP trap on the transition to the 'alarm'
                state. 

                'send-trap-on-normal-transition' indicates that the NMU 
                will only generate a SNMP trap on the transition to the 
                'normal' state. 

                'send-trap-on-both-transitions' indicates that the NMU will
                generate a SNMP trap on any transition. 

                Whenever the SNMP Agent attempts to send the 't1LoTrap' trap,
				other checks described below may prohibit this trap from
                transmission.

                Whenever this variable prohibits a trap from being sent,
                then 'trapFilteredSpecific' will be incremented.

                This MIB variable is the first of four checks that the NMU
                Agent uses to filter traps, based upon 1) a specific 
                enable or disable control variable; 2) 'trapControl' which
                offers a gross on/off/limit control; 3) 'trapMgrTable' 
                with 'trapMgrControl' and 'trapMgrAddress' which filters 
                whether enterprise traps (such as this trap) and/or 
                standard (RFC 1215) traps are sent to each specific trap 
                manager; and 4) 'trapSeverityFilter' which filters traps 
                according to a controlling severity variable for the 
                specific trap, which in this case is described below, and
                is defined as 'mgmtT1LineDriverSeverity'.
                
                Whenever any of these trap filters cause a trap to be 
                filtered, the corresponding MIB statistic is incremented.
                These statistics are 'trapFilteredSpecific', 
                'trapFilteredControl', 'trapFilteredManager', and 
                'trapFilteredSeverity'.

                See the MIB descriptions (in this file, and in 
                'westmux.mib' file) for any of these above variables for 
                details."
    ::= { mgmt 7 }

mgmtT1LineDriverSeverity OBJECT-TYPE
    SYNTAX      INTEGER
        {
        normal(1),               --*
        warning(2),              --*
        minor(3),                --*
        major(4),                --*
        critical(5)              --*
        }
    ACCESS      read-write
    STATUS      mandatory
    DESCRIPTION
                "This persistent variable indicates the desired severity 
                level to be associated with the log event and the SNMP 
                trap that record the occurance of a particular event.  
                
                In this case, the event indicates the detection of a 
                transition of the T1 line build out condition. 

                This severity level variable is associated with the
                't1LoTrap' trap, and a log event message that indicates
				a change in the Radio's T1 line build out condition.

                'critical' is the highest severity level, followed
                in decreasing order by 'major', 'minor', 'warning', 
                and 'normal', which is the lowest severity level.

                The default severity level is 'normal'.

                This trap may also be filtered by 
                'mgmtT1LineDriverTrapControl'."
    ::= { mgmt 8 }

mgmtT1AISTrapControl OBJECT-TYPE
    SYNTAX      INTEGER
        {
        no-trap(1),                           --*
        send-trap-on-alarm-transition(2),     --*
        send-trap-on-normal-transition(3),    --*
        send-trap-on-both-transitions(4)      --*
        }
    ACCESS      read-write
    STATUS      mandatory
    DESCRIPTION
                "This persistent variable controls whether the Agent will 
                attempt to send the 't1AisTrap' trap whenever the radio
                has a transition of its T1 AIS Output condition.

                The 't1AisTrap' trap is defined in this MIB definition file.

                'no-trap' indicates that the NMU, should not generate any 
                SNMP trap on any transition. This is the default value.
                
                'send-trap-on-alarm-transition' indicates that the NMU will
                only generate a SNMP trap on the transition to the 'alarm'
                state. 

                'send-trap-on-normal-transition' indicates that the NMU 
                will only generate a SNMP trap on the transition to the 
                'normal' state. 

                'send-trap-on-both-transitions' indicates that the NMU will
                generate a SNMP trap on any transition. 

                Whenever the SNMP Agent attempts to send the 't1AisTrap' trap,
				other checks described below may prohibit this trap from
				transmission.

                Whenever this variable prohibits a trap from being sent,
                then 'trapFilteredSpecific' will be incremented.

                This MIB variable is the first of four checks that the NMU
                Agent uses to filter traps, based upon 1) a specific 
                enable or disable control variable; 2) 'trapControl' which
                offers a gross on/off/limit control; 3) 'trapMgrTable' 
                with 'trapMgrControl' and 'trapMgrAddress' which filters 
                whether enterprise traps (such as this trap) and/or 
                standard (RFC 1215) traps are sent to each specific trap 
                manager; and 4) 'trapSeverityFilter' which filters traps 
                according to a controlling severity variable for the 
                specific trap, which in this case is described below, and
                is defined as 'mgmtT1AISSeverity'.
                
                Whenever any of these trap filters cause a trap to be 
                filtered, the corresponding MIB statistic is incremented.
                These statistics are 'trapFilteredSpecific', 
                'trapFilteredControl', 'trapFilteredManager', and 
                'trapFilteredSeverity'.

                See the MIB descriptions (in this file, and in 
                'westmux.mib' file) for any of these above variables for 
                details."
    ::= { mgmt 9 }

mgmtT1AISSeverity OBJECT-TYPE
    SYNTAX      INTEGER
        {
        normal(1),               --*
        warning(2),              --*
        minor(3),                --*
        major(4),                --*
        critical(5)              --*
        }
    ACCESS      read-write
    STATUS      mandatory
    DESCRIPTION
                "This persistent variable indicates the desired severity 
                level to be associated with the log event and the SNMP 
                trap that record the occurance of a particular event.  
                
                In this case, the event indicates the detection of a 
                transition of the T1 AIS Output condition. 

                This severity level variable is associated with the
                't1AisTrap' trap, and a log event message that indicates
				a change in the Radio's AIS Out condition.

                'critical' is the highest severity level, followed
                in decreasing order by 'major', 'minor', 'warning', 
                and 'normal', which is the lowest severity level.

                The default severity level is 'normal'.

                This trap may also be filtered by 
                'mgmtT1AISTrapControl'."
    ::= { mgmt 10 }

mgmtRadioSyncTrapControl OBJECT-TYPE
    SYNTAX      INTEGER
        {
        no-trap(1),                           --*
        send-trap-on-alarm-transition(2),     --*
        send-trap-on-normal-transition(3),    --*
        send-trap-on-both-transitions(4)      --*
        }
    ACCESS      read-write
    STATUS      mandatory
    DESCRIPTION
                "This persistent variable controls whether the Agent will 
                attempt to send the 'radioSyncTrap' trap whenever the 
                Radio has a transition of the Frame Loss Alarm.

                The 'radioSyncTrap' trap is defined in this MIB definition file.

                'no-trap' indicates that the NMU, should not generate any 
                SNMP trap on any transition. This is the default value.
                
                'send-trap-on-alarm-transition' indicates that the NMU will
                only generate a SNMP trap on the transition to the 'alarm'
                state. 

                'send-trap-on-normal-transition' indicates that the NMU 
                will only generate a SNMP trap on the transition to the 
                'normal' state. 

                'send-trap-on-both-transitions' indicates that the NMU will
                generate a SNMP trap on any transition. 

                Whenever the SNMP Agent attempts to send the 'radioSyncTrap' trap,
				other checks described below may prohibit this trap from
				transmission.

                Whenever this variable prohibits a trap from being sent,
                then 'trapFilteredSpecific' will be incremented.

                This MIB variable is the first of four checks that the NMU
                Agent uses to filter traps, based upon 1) a specific 
                enable or disable control variable; 2) 'trapControl' which
                offers a gross on/off/limit control; 3) 'trapMgrTable' 
                with 'trapMgrControl' and 'trapMgrAddress' which filters 
                whether enterprise traps (such as this trap) and/or 
                standard (RFC 1215) traps are sent to each specific trap 
                manager; and 4) 'trapSeverityFilter' which filters traps 
                according to a controlling severity variable for the 
                specific trap, which in this case is described below, and
                is defined as 'mgmtRadioSyncSeverity'.
                
                Whenever any of these trap filters cause a trap to be 
                filtered, the corresponding MIB statistic is incremented.
                These statistics are 'trapFilteredSpecific', 
                'trapFilteredControl', 'trapFilteredManager', and 
                'trapFilteredSeverity'.

                See the MIB descriptions (in this file, and in 
                'westmux.mib' file) for any of these above variables for 
                details."
    ::= { mgmt 11 }

mgmtRadioSyncSeverity OBJECT-TYPE
    SYNTAX      INTEGER
        {
        normal(1),               --*
        warning(2),              --*
        minor(3),                --*
        major(4),                --*
        critical(5)              --*
        }
    ACCESS      read-write
    STATUS      mandatory
    DESCRIPTION
                "This persistent variable indicates the desired severity 
                level to be associated with the log event and the SNMP 
                trap that record the occurance of a particular event.  
                
                In this case, the event indicates the detection of a 
                transition of the Frame Loss alarm on the Radio.

                This severity level variable is associated with the
                'radioSyncTrap' trap, and a log event message that 
                indicates a change in the Frame Loss Alarm within
		        the Radio.

                'critical' is the highest severity level, followed
                in decreasing order by 'major', 'minor', 'warning', 
                and 'normal', which is the lowest severity level.

                The default severity level is 'normal'.

                This trap may also be filtered by 
                'mgmtRadioSynccTrapControl'."
    ::= { mgmt 12 }

mgmtBitErrorTrapControl OBJECT-TYPE
    SYNTAX      INTEGER
        {
        no-trap(1),                           --*
        send-trap-on-alarm-transition(2),     --*
        send-trap-on-normal-transition(3),    --*
        send-trap-on-both-transitions(4)      --*
        }
    ACCESS      read-write
    STATUS      mandatory
    DESCRIPTION
                "This persistent variable controls whether the Agent will 
                attempt to send the 'berTrap' trap whenever the Radio
                has a transition of the Bit Error Rate 6 (or BER6) Alarm.
		        The 6 refers to a bit error rate of 10 to the minus 6
		        (1.0 E -6).

                The 'berTrap' trap is defined in this MIB definition file.

                'no-trap' indicates that the NMU, should not generate any 
                SNMP trap on any transition. This is the default value.
                
                'send-trap-on-alarm-transition' indicates that the NMU will
                only generate a SNMP trap on the transition to the 'alarm'
                state. 

                'send-trap-on-normal-transition' indicates that the NMU will
				only generate a SNMP trap on the transition to the 'normal'
				state. 

                'send-trap-on-both-transitions' indicates that the NMU will
                generate a SNMP trap on any transition. 

                Whenever the SNMP Agent attempts to send the 'berTrap' 
                trap, other checks described below may prohibit this trap 
                from transmission.

                Whenever this variable prohibits a trap from being sent,
                then 'trapFilteredSpecific' will be incremented.

                This MIB variable is the first of four checks that the NMU
                Agent uses to filter traps, based upon 1) a specific 
                enable or disable control variable; 2) 'trapControl' which
                offers a gross on/off/limit control; 3) 'trapMgrTable' 
                with 'trapMgrControl' and 'trapMgrAddress' which filters 
                whether enterprise traps (such as this trap) and/or 
                standard (RFC 1215) traps are sent to each specific trap 
                manager; and 4) 'trapSeverityFilter' which filters traps 
                according to a controlling severity variable for the 
                specific trap, which in this case is described below, and
                is defined as 'mgmtBitErrorSeverity'.
                
                Whenever any of these trap filters cause a trap to be 
                filtered, the corresponding MIB statistic is incremented.
                These statistics are 'trapFilteredSpecific', 
                'trapFilteredControl', 'trapFilteredManager', and 
                'trapFilteredSeverity'.

                See the MIB descriptions (in this file, and in 'westmux.mib'
				file) for any of these above variables for details."
    ::= { mgmt 13 }

mgmtBitErrorSeverity OBJECT-TYPE
    SYNTAX      INTEGER
        {
        normal(1),               --*
        warning(2),              --*
        minor(3),                --*
        major(4),                --*
        critical(5)              --*
        }
    ACCESS      read-write
    STATUS      mandatory
    DESCRIPTION
                "This persistent variable indicates the desired severity 
                level to be associated with the log event and the SNMP 
                trap that record the occurance of a particular event.  
                
                In this case, the event indicates the detection of a 
                transition of the Bit Error Rate 6 (or BER6) Alarm on the 
                Radio. The 6 refers to a bit error rate of 10 to the minus
		        6 (1.0 E -6).

                This severity level variable is associated with the
                'berTrap' trap, and a log event message that indicates a
		        change in the BER 6 Alarm within the Radio.

                'critical' is the highest severity level, followed
                in decreasing order by 'major', 'minor', 'warning', 
                and 'normal', which is the lowest severity level.

                The default severity level is 'normal'.

                This trap may also be filtered by 
                'mgmtBitErrorTrapControl'."
    ::= { mgmt 14 }

mgmtFan1TrapControl OBJECT-TYPE
    SYNTAX      INTEGER
        {
        no-trap(1),                           --*
        send-trap-on-alarm-transition(2),     --*
        send-trap-on-normal-transition(3),    --*
        send-trap-on-both-transitions(4)      --*
        }
    ACCESS      read-write
    STATUS      mandatory
    DESCRIPTION
                "This persistent variable controls whether the Agent will 
                attempt to send the 'fan1Trap' trap whenever the 
                FAN 1 Unit has a transition of its FAN alarm.

                The 'fan1Trap' trap is defined in this MIB definition 
                file.

                'no-trap' indicates that the NMU, should not generate any 
                SNMP trap on any transition. This is the default value.
                
                'send-trap-on-alarm-transition' indicates that the NMU will
                only generate a SNMP trap on the transition to the 'alarm'
                state. 

                'send-trap-on-normal-transition' indicates that the NMU 
                will only generate a SNMP trap on the transition to the 
                'normal' state. 

                'send-trap-on-both-transitions' indicates that the NMU will
                generate a SNMP trap on any transition. 

                Whenever the SNMP Agent attempts to send the 'fan1Trap' trap,
				other checks described below may prohibit this trap from
				transmission.

                Whenever this variable prohibits a trap from being sent,
                then 'trapFilteredSpecific' will be incremented.

                This MIB variable is the first of four checks that the NMU
                Agent uses to filter traps, based upon 1) a specific 
                enable or disable control variable; 2) 'trapControl' which
                offers a gross on/off/limit control; 3) 'trapMgrTable' 
                with 'trapMgrControl' and 'trapMgrAddress' which filters 
                whether enterprise traps (such as this trap) and/or 
                standard (RFC 1215) traps are sent to each specific trap 
                manager; and 4) 'trapSeverityFilter' which filters traps 
                according to a controlling severity variable for the 
                specific trap, which in this case is described below, and
                is defined as 'mgmtFan1Severity'.
                
                Whenever any of these trap filters cause a trap to be 
                filtered, the corresponding MIB statistic is incremented.
                These statistics are 'trapFilteredSpecific', 
                'trapFilteredControl', 'trapFilteredManager', and 
                'trapFilteredSeverity'.

                See the MIB descriptions (in this file, and in 
                'westmux.mib' file) for any of these above variables for 
                details."
    ::= { mgmt 15 }

mgmtFan1Severity OBJECT-TYPE
    SYNTAX      INTEGER
        {
        normal(1),               --*
        warning(2),              --*
        minor(3),                --*
        major(4),                --*
        critical(5)              --*
        }
    ACCESS      read-write
    STATUS      mandatory
    DESCRIPTION
                "This persistent variable indicates the desired severity 
                level to be associated with the log event and the SNMP 
                trap that record the occurance of a particular event.  
                
                In this case, the event indicates the detection of a 
                transition of the FAN alarm on the FAN1 Unit.

                This severity level variable is associated with the
                'fan1Trap' trap, and a log event message that 
                indicates a change in the FAN1 alarm.

                'critical' is the highest severity level, followed
                in decreasing order by 'major', 'minor', 'warning', 
                and 'normal', which is the lowest severity level.

                The default severity level is 'normal'.

                This trap may also be filtered by 
                'mgmtFan1TrapControl'."
    ::= { mgmt 16 }

mgmtFan2TrapControl OBJECT-TYPE
    SYNTAX      INTEGER
        {
        no-trap(1),                           --*
        send-trap-on-alarm-transition(2),     --*
        send-trap-on-normal-transition(3),    --*
        send-trap-on-both-transitions(4)      --*
        }
    ACCESS      read-write
    STATUS      mandatory
    DESCRIPTION
                "This persistent variable controls whether the Agent will 
                attempt to send the 'fan2Trap' trap whenever the FAN2 Unit
				has a transition of its FAN alarm.

                The 'fan2Trap' trap is defined in this MIB definition 
                file.

                'no-trap' indicates that the NMU, should not generate any 
                SNMP trap on any transition. This is the default value.
                
                'send-trap-on-alarm-transition' indicates that the NMU will
                only generate a SNMP trap on the transition to the 'alarm'
                state. 

                'send-trap-on-normal-transition' indicates that the NMU 
                will only generate a SNMP trap on the transition to the 
                'normal' state. 

                'send-trap-on-both-transitions' indicates that the NMU will
                generate a SNMP trap on any transition. 

                Whenever the SNMP Agent attempts to send the 'fan2Trap'
		        trap, other checks described below may prohibit this trap
		        from transmission.

                Whenever this variable prohibits a trap from being sent,
                then 'trapFilteredSpecific' will be incremented.

                This MIB variable is the first of four checks that the NMU
                Agent uses to filter traps, based upon 1) a specific 
                enable or disable control variable; 2) 'trapControl' which
                offers a gross on/off/limit control; 3) 'trapMgrTable' 
                with 'trapMgrControl' and 'trapMgrAddress' which filters 
                whether enterprise traps (such as this trap) and/or 
                standard (RFC 1215) traps are sent to each specific trap 
                manager; and 4) 'trapSeverityFilter' which filters traps 
                according to a controlling severity variable for the 
                specific trap, which in this case is described below, and
                is defined as 'mgmtFan2Severity'.
                
                Whenever any of these trap filters cause a trap to be 
                filtered, the corresponding MIB statistic is incremented.
                These statistics are 'trapFilteredSpecific', 
                'trapFilteredControl', 'trapFilteredManager', and 
                'trapFilteredSeverity'.

                See the MIB descriptions (in this file, and in 
                'westmux.mib' file) for any of these above variables for 
                details."
    ::= { mgmt 17 }

mgmtFan2Severity OBJECT-TYPE
    SYNTAX      INTEGER
        {
        normal(1),               --*
        warning(2),              --*
        minor(3),                --*
        major(4),                --*
        critical(5)              --*
        }
    ACCESS      read-write
    STATUS      mandatory
    DESCRIPTION
                "This persistent variable indicates the desired severity 
                level to be associated with the log event and the SNMP 
                trap that record the occurance of a particular event.  
                
                In this case, the event indicates the detection of a 
                transition of the FAN alarm on the FAN2 Unit.

                This severity level variable is associated with the
                'fan2Trap' trap, and a log event message that 
                indicates a change in the FAN2 alarm.

                'critical' is the highest severity level, followed
                in decreasing order by 'major', 'minor', 'warning', 
                and 'normal', which is the lowest severity level.

                The default severity level is 'normal'.

                This trap may also be filtered by 
                'mgmtFan2TrapControl'."
    ::= { mgmt 18 }

mgmtRxSynthTrapControl OBJECT-TYPE
    SYNTAX      INTEGER
        {
        no-trap(1),                           --*
        send-trap-on-alarm-transition(2),     --*
        send-trap-on-normal-transition(3),    --*
        send-trap-on-both-transitions(4)      --*
        }
    ACCESS      read-write
    STATUS      mandatory
    DESCRIPTION
                "This persistent variable controls whether the Agent will 
                attempt to send the 'rxSynthTrap' trap whenever the 
                Radio has a transition of its receiver-sythesizer alarm
		        condition.

                The 'rxSynthTrap' trap is defined in this MIB definition file.

                'no-trap' indicates that the NMU, should not generate any 
                SNMP trap on any transition. This is the default value.
                
                'send-trap-on-alarm-transition' indicates that the NMU will
                only generate a SNMP trap on the transition to the 'alarm'
                state. 

                'send-trap-on-normal-transition' indicates that the NMU 
                will only generate a SNMP trap on the transition to the 
                'normal' state. 

                'send-trap-on-both-transitions' indicates that the NMU will
                generate a SNMP trap on any transition. 

                Whenever the SNMP Agent attempts to send the 'rxSynthTrap'
                trap, other checks described below may prohibit this trap 
                from transmission.

                Whenever this variable prohibits a trap from being sent,
                then 'trapFilteredSpecific' will be incremented.

                This MIB variable is the first of four checks that the NMU
                Agent uses to filter traps, based upon 1) a specific 
                enable or disable control variable; 2) 'trapControl' which
                offers a gross on/off/limit control; 3) 'trapMgrTable' 
                with 'trapMgrControl' and 'trapMgrAddress' which filters 
                whether enterprise traps (such as this trap) and/or 
                standard (RFC 1215) traps are sent to each specific trap 
                manager; and 4) 'trapSeverityFilter' which filters traps 
                according to a controlling severity variable for the 
                specific trap, which in this case is described below, and
                is defined as 'mgmRxSynthSeverity'.
                
                Whenever any of these trap filters cause a trap to be 
                filtered, the corresponding MIB statistic is incremented.
                These statistics are 'trapFilteredSpecific', 
                'trapFilteredControl', 'trapFilteredManager', and 
                'trapFilteredSeverity'.

                See the MIB descriptions (in this file, and in 
                'westmux.mib' file) for any of these above variables for 
                details."
    ::= { mgmt 19 }

mgmtRxSynthSeverity OBJECT-TYPE
    SYNTAX      INTEGER
        {
        normal(1),               --*
        warning(2),              --*
        minor(3),                --*
        major(4),                --*
        critical(5)              --*
        }
    ACCESS      read-write
    STATUS      mandatory
    DESCRIPTION
                "This persistent variable indicates the desired severity 
                level to be associated with the log event and the SNMP 
                trap that record the occurance of a particular event.  
                
                In this case, the event indicates the detection of a 
                transition of the receiver-sythesizer alarm conditionb on
                the Radio.

                This severity level variable is associated with the
                'rxSynthTrap' trap, and a log event message that indicates
                 a change in this condition within the Radio.

                'critical' is the highest severity level, followed
                in decreasing order by 'major', 'minor', 'warning', 
                and 'normal', which is the lowest severity level.

                The default severity level is 'normal'.

                This trap may also be filtered by 
                'mgmtRxSynthTrapControl'."
    ::= { mgmt 20 }

mgmtTxSynthTrapControl OBJECT-TYPE
    SYNTAX      INTEGER
        {
        no-trap(1),                           --*
        send-trap-on-alarm-transition(2),     --*
        send-trap-on-normal-transition(3),    --*
        send-trap-on-both-transitions(4)      --*
        }
    ACCESS      read-write
    STATUS      mandatory
    DESCRIPTION
                "This persistent variable controls whether the Agent will 
                attempt to send the 'txSynthTrap' trap whenever the 
                Radio has a transition of its tansmitter-synthesizer alarm
		        condition.

                The 'TxSynthTrap' trap is defined in this MIB definition file.

                'no-trap' indicates that the NMU, should not generate any 
                SNMP trap on any transition. This is the default value.
                
                'send-trap-on-alarm-transition' indicates that the NMU will
                only generate a SNMP trap on the transition to the 'alarm'
                state. 

                'send-trap-on-normal-transition' indicates that the NMU 
                will only generate a SNMP trap on the transition to the 
                'normal' state. 

                'send-trap-on-both-transitions' indicates that the NMU will
                generate a SNMP trap on any transition. 

                Whenever the SNMP Agent attempts to send the 'TxSynthTrap'
                trap, other checks described below may prohibit this trap 
                from transmission.

                Whenever this variable prohibits a trap from being sent,
                then 'trapFilteredSpecific' will be incremented.

                This MIB variable is the first of four checks that the NMU
                Agent uses to filter traps, based upon 1) a specific 
                enable or disable control variable; 2) 'trapControl' which
                offers a gross on/off/limit control; 3) 'trapMgrTable' 
                with 'trapMgrControl' and 'trapMgrAddress' which filters 
                whether enterprise traps (such as this trap) and/or 
                standard (RFC 1215) traps are sent to each specific trap 
                manager; and 4) 'trapSeverityFilter' which filters traps 
                according to a controlling severity variable for the 
                specific trap, which in this case is described below, and
                is defined as 'mgmtTxSynthSeverity'.
                
                Whenever any of these trap filters cause a trap to be 
                filtered, the corresponding MIB statistic is incremented.
                These statistics are 'trapFilteredSpecific', 
                'trapFilteredControl', 'trapFilteredManager', and 
                'trapFilteredSeverity'.

                See the MIB descriptions (in this file, and in 'westmux.mib'
				file) for any of these above variables for details."
    ::= { mgmt 21 }

mgmtTxSynthSeverity OBJECT-TYPE
    SYNTAX      INTEGER
        {
        normal(1),               --*
        warning(2),              --*
        minor(3),                --*
        major(4),                --*
        critical(5)              --*
        }
    ACCESS      read-write
    STATUS      mandatory
    DESCRIPTION
                "This persistent variable indicates the desired severity 
                level to be associated with the log event and the SNMP 
                trap that record the occurance of a particular event.  
                
                In this case, the event indicates the detection of a 
                transition of the transmitter-synthesizer alarm condition
                on the Radio.

                This severity level variable is associated with the
                'txSynthTrap' trap, and a log event message that 
                indicates a change in this condition within the Radio.

                'critical' is the highest severity level, followed
                in decreasing order by 'major', 'minor', 'warning', 
                and 'normal', which is the lowest severity level.

                The default severity level is 'normal'.

                This trap may also be filtered by 
                'mgmtTxSynthTrapControl'."
    ::= { mgmt 22 }


--*************************************************
--*  Radio Trap Hysteresis
--*************************************************
mgmtTrapHysteresis OBJECT-TYPE
    SYNTAX      INTEGER   (0..120)
    ACCESS      read-write
    STATUS      mandatory
    DESCRIPTION
                "This persistent variable indicates the desired hysteresis
                time value that allows the trap management sub-system to 
                generate any of the 16 SNMP Western Multiplex radio 
                traps.  

                This control, allows a radio alarm event to be NORMALIZED 
                within the 'mgmtTrapHysteresis' time limit. If the event
                is not normalized, then the associated radio trap will be 
                sent if not filtered by the associate 'mgmtXXXTrapControl'
                variable, or the 'mgmtXXXSeverity' variable, which also
                controls the generation of this trap.  In addition
                trap management controls may filter this trap from being
                sent.

                The units are in seconds with the default value value of
                120 which is the maximum allowed.  The value of 0 is the 
                minimum, which allows the trap to be generated 
                immediately.  The timing resolution is plus/minus 15 
                seconds."
    ::= { mgmt 61 }

    --********************************************************************
    --* RADIO TRAP
    --*  enterprises.western-multiplex.tsunami100-06.radio.status
    --********************************************************************
nmuLinkTrap TRAP-TYPE
    ENTERPRISE status 
    VARIABLES { trapSequenceNumber, 
                mgmtNMULinkSeverity,
                statNMULink
              }
    DESCRIPTION
                "This trap is generated by the SNMP Agent when the Agent
                has detected a transition in the link condition between
		        the Radio and the NMU..

                This trap may be filtered by 'mgmtNMULinkTrapControl', 
                which is a specific Trap control that can be used to 
                specifically enable or disable this trap.  See the 
                definition of this variable above for details about this 
                filter, and the other trap filtering mechanisms.

                The 'trapSequenceNumber,' variable bound within the trap
                can be used by management stations and network administrators
				to detect when a trap has been lost during transmission.

                The 'mgmtNMULinkSeverity' variable bound within the trap 
                indicates the configured severity level associated with 
                this event.

                A value of 'LINK-UP', indicates that the link between the
		        Radio and NMU is not in an alarm state. A value of 'LINK-DOWN',
		        however, means that the link between the two entities might
		        be down or one side stops responding to the othe side.

                The row/column variables included in the trap are:
                 system.trap.trapSequenceNumber;
                 radio.mgmt.mgmtNMULinkSeverity."
    ::= 1

t1InTrap TRAP-TYPE
    ENTERPRISE status 
    VARIABLES { trapSequenceNumber, 
                mgmtT1InputSeverity,
                statT1Input
              }
    DESCRIPTION
                "This trap is generated by the SNMP Agent when the Agent
                has detected a transition in Radio, T1 Input condition.

                This trap may be filtered by 'mgmtT1InputTrapControl', 
                which is a specific Trap control that can be used to 
                specifically enable or disable this trap.  See the 
                definition of this variable above for details about this 
                filter, and the other trap filtering mechanisms.

                The 'trapSequenceNumber,' variable bound within the trap
                can be used by management stations and network administrators
		        to detect when a trap has been lost during transmission.

                The 'mgmtT1InputSeverity' variable bound within the trap
                indicates the configured severity level associated with 
                this event.
                
                A value of 'NORMAL', indicates that the T1 Input condition
                is normal. A value of 'T1IN-ALM' indicates T1 line failure
		        due to loss of signal.

                The row/column variables included in the trap are:
                 system.trap.trapSequenceNumber;
                 radio.mgmt.mgmtT1InputSeverity;"
    ::= 2

t1CvTrap TRAP-TYPE
    ENTERPRISE status 
    VARIABLES { trapSequenceNumber, 
                mgmtT1CodeViolationSeverity,
                statT1CodeViolation
              }
    DESCRIPTION
                "This trap is generated by the SNMP Agent when the Agent
                has detected a transition Radio's, Code Violation condition.

                This trap may be filtered by 'mgmtT1CodeViolationTrapControl', 
                which is a specific Trap control that can be used to spcifically
				enable or disable this trap.  See the definition of this variable
				above for details about this filter, and the other trap filtering
				mechanisms.

                The 'trapSequenceNumber,' variable bound within the trap can
                be used by management stations and network administrators to 
		        detect when a trap has been lost during transmission.

                The 'mgmtT1CodeViolationSeverity' variable bound within the
				trap indicates the configured severity level associated with 
                this event.
                
                A value of 'NORMAL', indicates that the Code Violation condition
				is normal. A value of 'T1CV-ALM' indicates code violation condition
				on the T1 input.
				
                The row/column variables included in the trap are:
                 system.trap.trapSequenceNumber;
                 radio.mgmt.mgmtT1CodeViolationSeverity."
    ::= 3

t1LoTrap TRAP-TYPE
    ENTERPRISE status 
    VARIABLES { trapSequenceNumber, 
                mgmtT1LineDriverSeverity,
                statT1LineDriver
              }
    DESCRIPTION
                "This trap is generated by the SNMP Agent when the Agent
                has detected a transition in Radio, T1 line build out
				condition.

                This trap may be filtered by 'mgmtT1LineDriverTrapControl', 
                which is a specific Trap control that can be used to 
                specifically enable or disable this trap.  See the 
                definition of this variable above for details about this 
                filter, and the other trap filtering mechanisms.

                The 'trapSequenceNumber,' variable bound within the trap
                can be used by management stations and network administrators
		        to detect when a trap has been lost during transmission.

                The 'mgmtT1LineDriverSeverity' variable bound within the trap
                indicates the configured severity level associated with 
                this event.
                
                A value of 'NORMAL', indicates that the T1 Line build out
                condition is normal. A value of 'T1LO-ALM' indicates T1 line
                build out has an alarm.

                The row/column variables included in the trap are:
                 system.trap.trapSequenceNumber;
                 radio.mgmt.mgmtT1LineDriverSeverity;"
    ::= 4

t1AisTrap TRAP-TYPE
    ENTERPRISE status 
    VARIABLES { trapSequenceNumber, 
                mgmtT1AISSeverity,
                statT1AIS
              }
    DESCRIPTION
                "This trap is generated by the SNMP Agent when the Agent
                has detected a transition in the Radio's,T1 AIS Output condition.

                This trap may be filtered by 'mgmtT1AISTrapControl', 
                which is a specific Trap control that can be used to 
                specifically enable or disable this trap.  See the 
                definition of this variable above for details about this 
                filter, and the other trap filtering mechanisms.

                The 'trapSequenceNumber,' variable bound within the trap can
                be used by management stations and network administrators to
				detect when a trap has been lost during transmission.

                The 'mgmtT1AISSeverity' variable bound within the trap
                indicates the configured severity level associated with 
                this event.
                
                A value of 'NORMAL', indicates that the T1 AIS Output condition
                is normal. A value of 'T1AIS-ALM', indicates that the Radio is
                generating 'Alarm Indication Signal', or marking the T1 line
                with all ones, on the transmit output.When this occurs there is
                an interruption in the RF signal due to 'FRAME-LOSS', 'BER-3',
		        or a 'DEMUX' hard alarm conditions.
				
                The row/column variables included in the trap are:
                 system.trap.trapSequenceNumber;
                 radio.mgmt.mgmtT1AISSeverity."
    ::= 5

radioSyncTrap TRAP-TYPE
    ENTERPRISE status 
    VARIABLES { trapSequenceNumber, 
                mgmtRadioSyncSeverity,
                statRadioSync
              }
    DESCRIPTION
                "This trap is generated by the SNMP Agent when the Agent
                has detected a transition in the Radio's, Frame Loss alarm. 

                This trap may be filtered by 'mgmtRadioSyncTrapControl',
		        which is a specific Trap control that can be used to
		        specifically enable or disable this trap. See the 
		        definition of this variable above for details about this
		        filter, and the other trap filtering mechanisms.

                The 'trapSequenceNumber,' variable bound within the trap can
                be used by management stations and network administrators to
				detect when a trap has been lost during transmission.

                The 'mgmtRadioSyncSeverity' variable bound within the trap indicates
				the configured severity level associated with this event.
              
                A value of 'NORMAL', indicates that Frame Loss Alarm is not
                in an alarm state. A value 'RADIOSYN-ALM' indicates a loss of 5 or
                more consecutive frames on the received aggregate data (input
                to the demultiplexer function of the MUX).
								
                The row/column variables included in the trap are:
                 system.trap.trapSequenceNumber;
                 radio.mgmt.mgmtRadioSyncSeverity."
    ::= 6

berTrap TRAP-TYPE
    ENTERPRISE status 
    VARIABLES { trapSequenceNumber, 
                mgmtBitErrorSeverity,
                statBitError
              }
    DESCRIPTION
                "This trap is generated by the SNMP Agent when the Agent
                has detected a transition in the Radio's, Bit Error Rate 6
		        (or BER6) Alarm. The 6 refers to a bit error rate of 10 to
		        the minus 6 (1.0 E -6).

                This trap may be filtered by 'mgmtBitErrorTrapControl', 
                which is a specific Trap control that can be used to 
                specifically enable or disable this trap. See the 
                definition of this variable above for details about this 
                filter, and the other trap filtering mechanisms.

                The 'trapSequenceNumber,' variable bound within the trap can
                be used by management stations and network administrators
				to detect when a trap has been lost during transmission.

                The 'mgmtBitErrorSeverity' variable bound within the trap
		        indicates the configured severity level associated with
		        this event.

                A value of 'NORMAL', indicates that BER is less than 10 to the
                minus 6. A value of 'BER-6', indicates that the radio signal has
		        a bit error rate, or BER, greater than 10 to minu 6, (1.0 E -6).

                The row/column variables included in the trap are:
                 system.trap.trapSequenceNumber;
                 radio.mgmt.mgmtBitErrorSeverity."
    ::= 7

fan1Trap TRAP-TYPE
    ENTERPRISE status 
    VARIABLES { trapSequenceNumber, 
                mgmtFan1Severity,
                statFan1
              }
    DESCRIPTION
                "This trap is generated by the SNMP Agent when the Agent
                has detected a transition in the fan1 Unit's, alarm.

                This trap may be filtered by 'mgmtFan1TrapControl', 
                which is a specific Trap control that can be used to 
                specifically enable or disable this trap.  See the 
                definition of this variable above for details about this 
                filter, and the other trap filtering mechanisms.

                The 'trapSequenceNumber,' variable bound within the trap
                can be used by management stations and network 
                administrators to detect when a trap has been lost during
                transmission.

                The 'mgmtFan1Severity' variable bound within the  trap
                indicates the configured severity level associated with
                this event.

                A value of 'NORMAL', indicates that the fan1 unit has no 
                alarm state. A value of 'FAN1-ALM', indicates that the fan1
                unit is not present, unplugged, or is not rotating. 

                The row/column variables included in the trap are:
                 system.trap.trapSequenceNumber;
                 radio.mgmt.mgmtFan1Severity."
    ::= 8

fan2Trap TRAP-TYPE
    ENTERPRISE status 
    VARIABLES { trapSequenceNumber, 
                mgmtFan2Severity,
                statFan2
              }
    DESCRIPTION
                "This trap is generated by the SNMP Agent when the Agent
                has detected a transition in the fan2 Unit's, alarm.

                This trap may be filtered by 'mgmtFan2TrapControl', 
                which is a specific Trap control that can be used to 
                specifically enable or disable this trap.  See the 
                definition of this variable above for details about this 
                filter, and the other trap filtering mechanisms.

                The 'trapSequenceNumber,' variable bound within the trap
                can be used by management stations and network administrators
				to detect when a trap has been lost during transmission.

                The 'mgmtFan2Severity' variable bound within the trap
                indicates the configured severity level associated with
                this event.
                
                A value of 'NORMAL', indicates that the fan2 unit has no 
                alarm state. A value of 'FAN2-ALM', indicates that the fan2
                unit is not present, unplugged, or is not rotating. 

                The row/column variables included in the trap are:
                 system.trap.trapSequenceNumber;
                 radio.mgmt.mgmtFan2Severity."
    ::= 9

rxSynthTrap TRAP-TYPE
    ENTERPRISE status 
    VARIABLES { trapSequenceNumber, 
                mgmtRxSynthSeverity,
                statRxSynth
              }
    DESCRIPTION
                "This trap is generated by the SNMP Agent when the Agent
                has detected a transition in Radio's, receiver-synthesizer
				alarm condition.

                This trap may be filtered by 'mgmtRxSynthTrapControl',
		        which is a specific Trap control that can be used to
		        specifically enable or disable this trap. See the definition
		        of this variable above for details about this filter, and
		        the other trap filtering mechanisms.

                The 'trapSequenceNumber,' variable bound within the trap
                can be used by management stations and network administrators
		        to detect when a trap has been lost during transmission.

                The 'mgmtRxSynthSeverity' variable bound within the 
                trap indicates the configured severity level associated 
                with this event.

                A value of 'NORMAL', indicates that receiver-synthesizer is not
				in an alarm state. A value of 'RX-SYNTH-ALM', indicates that the
				receiver synthesizer has an alarm.
				
                The row/column variables included in the trap are:
                 system.trap.trapSequenceNumber;
                 radio.mgmt.mgmtRxSynthSeverity."
    ::= 10

txSynthTrap TRAP-TYPE
    ENTERPRISE status 
    VARIABLES { trapSequenceNumber, 
                mgmtTxSynthSeverity,
                statTxSynth
              }
    DESCRIPTION
                "This trap is generated by the SNMP Agent when the Agent
                has detected a transition in Radio's, transmitter-synthesizer
				alarm condition.

                This trap may be filtered by 'mgmtTxSynthTrapControl',
		        which is a specific Trap control that can be used to
		        specifically enable or disable this trap. See the definition
		        of this variable above for details about this filter, and
		        the other trap filtering mechanisms.

                The 'trapSequenceNumber,' variable bound within the trap
                can be used by management stations and network administrators
		        to detect when a trap has been lost during transmission.

                The 'mgmtTxSynthSeverity' variable bound within the 
                trap indicates the configured severity level associated 
                with this event.

                A value of 'NORMAL', indicates that transmitter-synthesizer is
				not in an alarm state. A value of 'TX-SYNTH-ALM', indicates that
				the transmitter-synthesizer has an alarm condition.

                The row/column variables included in the trap are:
                 system.trap.trapSequenceNumber;
                 radio.mgmt.mgmtTxSynthSeverity."
    ::= 11


    END
