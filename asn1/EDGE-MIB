-- 3COM EDGE MIB 
-- MIB File Generated on 14-Dec-1998 at 17:15:32

EDGE-MIB DEFINITIONS ::= BEGIN

IMPORTS
   enterprises,
   experimental,
   IpAddress,
   TimeTicks,
   Gauge,
   Counter
      FROM RFC1155-SMI
   DisplayString
      FROM RFC1213-MIB
   OBJECT-TYPE
      FROM RFC-1212;


usr OBJECT IDENTIFIER ::= { enterprises 429 }

nas OBJECT IDENTIFIER ::= { usr 1 }

edge OBJECT IDENTIFIER ::= { nas 24 }

edgeServerStat OBJECT IDENTIFIER ::= { edge 1 }

edgeServerStatTable OBJECT-TYPE
SYNTAX SEQUENCE OF EdgeServerStatEntry
ACCESS not-accessible
STATUS mandatory
DESCRIPTION
"Table containing objects for statistics for the EdgeServer  
Gateway Cards in the chassis."
::= { edgeServerStat 1 }

edgeServerStatEntry OBJECT-TYPE
SYNTAX EdgeServerStatEntry
ACCESS not-accessible
STATUS mandatory
DESCRIPTION
"There is one Configuration row for each Gateway Card in the 
NAS chassis."
INDEX { edgeSsIndex }
::= { edgeServerStatTable 1 }

EdgeServerStatEntry ::=
SEQUENCE {
edgeSsIndex
    INTEGER,
edgeSsProcessorTime
    INTEGER,
edgeSsInterruptPerSec
    INTEGER,
edgeSsDiskPercentUsed
    INTEGER,
edgeSsFreeMegabytes
    INTEGER,
edgeSsPercentDiskTime
    INTEGER,
edgeSsPercentDiskReadTime
    INTEGER,
edgeSsPercentDiskWriteTime
    INTEGER,
edgeSsMemoryPercentUsed
    INTEGER,
edgeSsPageFaultsPerSec
    INTEGER,
edgeSsInfrastructManufacturer
    DisplayString,
edgeSsedgeTechnology
    DisplayString,
edgeSsCurrentSwLoadRevision
    DisplayString,
edgeSsPreviousSwLoadRevision
    DisplayString,
edgeSsHwLoadRevision
    DisplayString,
edgeSsComputerName
    DisplayString,
edgeSsSysUpTime
    Counter
}

edgeSsIndex OBJECT-TYPE
SYNTAX INTEGER
ACCESS read-only
STATUS mandatory
DESCRIPTION
"A unique index identifying the Gateway Card to which the 
EdgeServer statistics table objects pertain"
::= { edgeServerStatEntry 1 }

edgeSsProcessorTime OBJECT-TYPE
SYNTAX INTEGER
ACCESS read-only
STATUS mandatory
DESCRIPTION
"This object gives the Time the CPU spen executing non-idle 
thread."
::= { edgeServerStatEntry 2 }

edgeSsInterruptPerSec OBJECT-TYPE
SYNTAX INTEGER
ACCESS read-only
STATUS mandatory
DESCRIPTION
"This object is the number of interrupts received and 
servicced per second."
::= { edgeServerStatEntry 3 }

edgeSsDiskPercentUsed OBJECT-TYPE
SYNTAX INTEGER
ACCESS read-only
STATUS mandatory
DESCRIPTION
"This object is the Percent of the Disk used Space."
::= { edgeServerStatEntry 4 }

edgeSsFreeMegabytes OBJECT-TYPE
SYNTAX INTEGER
ACCESS read-only
STATUS mandatory
DESCRIPTION
"This object is the unallocated space on drive."
::= { edgeServerStatEntry 5 }

edgeSsPercentDiskTime OBJECT-TYPE
SYNTAX INTEGER
ACCESS read-only
STATUS mandatory
DESCRIPTION
"This object is the percent of time disk is busy servicing 
read/write requests."
::= { edgeServerStatEntry 6 }

edgeSsPercentDiskReadTime OBJECT-TYPE
SYNTAX INTEGER
ACCESS read-only
STATUS mandatory
DESCRIPTION
"This object is the percent of time disk is busy servicing 
read requests."
::= { edgeServerStatEntry 7 }

edgeSsPercentDiskWriteTime OBJECT-TYPE
SYNTAX INTEGER
ACCESS read-only
STATUS mandatory
DESCRIPTION
"This object is the percent of time disk is busy servicing 
write requests."
::= { edgeServerStatEntry 8 }

edgeSsMemoryPercentUsed OBJECT-TYPE
SYNTAX INTEGER
ACCESS read-only
STATUS mandatory
DESCRIPTION
"This object is the physical Used percentage of memory."
::= { edgeServerStatEntry 9 }

edgeSsPageFaultsPerSec OBJECT-TYPE
SYNTAX INTEGER
ACCESS read-only
STATUS mandatory
DESCRIPTION
"This object is the Rate of faulted pages handled by 
processor per second."
::= { edgeServerStatEntry 10 }

edgeSsInfrastructManufacturer OBJECT-TYPE
SYNTAX DisplayString (SIZE(0..32))
ACCESS read-only
STATUS mandatory
DESCRIPTION
"This object is the Customer Identifier."
::= { edgeServerStatEntry 11 }

edgeSsedgeTechnology OBJECT-TYPE
SYNTAX DisplayString (SIZE(0..32))
ACCESS read-only
STATUS mandatory
DESCRIPTION
"This object is the edge Technology used on the NAC."
::= { edgeServerStatEntry 12 }

edgeSsCurrentSwLoadRevision OBJECT-TYPE
SYNTAX DisplayString (SIZE(0..12))
ACCESS read-only
STATUS mandatory
DESCRIPTION
"This object is the current revision of the Software load."
::= { edgeServerStatEntry 13 }

edgeSsPreviousSwLoadRevision OBJECT-TYPE
SYNTAX DisplayString (SIZE(0..12))
ACCESS read-only
STATUS mandatory
DESCRIPTION
"This object is the previous revision of the Software load."
::= { edgeServerStatEntry 14 }

edgeSsHwLoadRevision OBJECT-TYPE
SYNTAX DisplayString (SIZE(0..12))
ACCESS read-only
STATUS mandatory
DESCRIPTION
"This object is the revision of the Hardware Load."
::= { edgeServerStatEntry 15 }

edgeSsComputerName OBJECT-TYPE
SYNTAX DisplayString (SIZE(0..255))
ACCESS read-write
STATUS mandatory
DESCRIPTION
"This object is the Windows NT Computer Name"
::= { edgeServerStatEntry 16 }

edgeSsSysUpTime OBJECT-TYPE
SYNTAX Counter
ACCESS read-only
STATUS mandatory
DESCRIPTION
"This object is the EdgeServer System Up Time in Minutes."
::= { edgeServerStatEntry 17 }

-- The EdgeServer Configuration Debug Level Group

edgeCfgDebugLevel OBJECT IDENTIFIER ::= { edge 2 }

edgeCfgDebugLevelTable OBJECT-TYPE
SYNTAX SEQUENCE OF EdgeCfgDebugLevelEntry
ACCESS not-accessible
STATUS mandatory
DESCRIPTION
"Table containing objects for configuring Debug Levels  for 
EdgeServer Gateway Cards in the chassis."
::= { edgeCfgDebugLevel 1 }

edgeCfgDebugLevelEntry OBJECT-TYPE
SYNTAX EdgeCfgDebugLevelEntry
ACCESS not-accessible
STATUS mandatory
DESCRIPTION
"There is one Configuration row for each Gateway Card in the 
NAS chassis."
INDEX { edgeCfgDbgIndex }
::= { edgeCfgDebugLevelTable 1 }

EdgeCfgDebugLevelEntry ::=
SEQUENCE {
edgeCfgDbgIndex
    INTEGER,
edgeCfgDbgIp
    INTEGER,
edgeCfgDbgPPP
    INTEGER,
edgeCfgDbgTDM
    INTEGER,
edgeCfgDbgFrameService
    INTEGER,
edgeCfgDbgPacketBus
    INTEGER,
edgeCfgDbgCallControl
    INTEGER,
edgeCfgDbgDataTransfer
    INTEGER,
edgeCfgDbgCompression
    INTEGER
}

edgeCfgDbgIndex OBJECT-TYPE
SYNTAX INTEGER
ACCESS read-only
STATUS mandatory
DESCRIPTION
"A unique index identifying the Gateway Card to which the 
Debug Level parameters table objects pertain"
::= { edgeCfgDebugLevelEntry 1 }

edgeCfgDbgIp OBJECT-TYPE
SYNTAX INTEGER{
  none(1),
  minimum(2),
  medium(3),
  high(4)
}
ACCESS read-write
STATUS mandatory
DESCRIPTION
"This object configures the Debug Level for Ip Debug 
Systems."
::= { edgeCfgDebugLevelEntry 2 }

edgeCfgDbgPPP OBJECT-TYPE
SYNTAX INTEGER{
  none(1),
  minimum(2),
  medium(3),
  high(4)
}
ACCESS read-write
STATUS mandatory
DESCRIPTION
"This object configures the Debug Level for PPP Debug 
Systems."
::= { edgeCfgDebugLevelEntry 3 }

edgeCfgDbgTDM OBJECT-TYPE
SYNTAX INTEGER{
  none(1),
  minimum(2),
  medium(3),
  high(4)
}
ACCESS read-write
STATUS mandatory
DESCRIPTION
"This object configures the Debug Level for TDM Debug 
Systems."
::= { edgeCfgDebugLevelEntry 4 }

edgeCfgDbgFrameService OBJECT-TYPE
SYNTAX INTEGER{
  none(1),
  minimum(2),
  medium(3),
  high(4)
}
ACCESS read-write
STATUS mandatory
DESCRIPTION
"This object configures the Debug Level for Frame Service 
Debug Systems."
::= { edgeCfgDebugLevelEntry 5 }

edgeCfgDbgPacketBus OBJECT-TYPE
SYNTAX INTEGER{
  none(1),
  minimum(2),
  medium(3),
  high(4)
}
ACCESS read-write
STATUS mandatory
DESCRIPTION
"This object configures the Debug Level for Packet Bus Debug 
Systems."
::= { edgeCfgDebugLevelEntry 6 }

edgeCfgDbgCallControl OBJECT-TYPE
SYNTAX INTEGER{
  none(1),
  minimum(2),
  medium(3),
  high(4)
}
ACCESS read-write
STATUS mandatory
DESCRIPTION
"This object configures the Debug Level for Call Control 
Debug Systems."
::= { edgeCfgDebugLevelEntry 7 }

edgeCfgDbgDataTransfer OBJECT-TYPE
SYNTAX INTEGER{
  none(1),
  minimum(2),
  medium(3),
  high(4)
}
ACCESS read-write
STATUS mandatory
DESCRIPTION
"This object configures the Debug Level for Data Transfer 
Debug Systems."
::= { edgeCfgDebugLevelEntry 8 }

edgeCfgDbgCompression OBJECT-TYPE
SYNTAX INTEGER{
  none(1),
  minimum(2),
  medium(3),
  high(4)
}
ACCESS read-write
STATUS mandatory
DESCRIPTION
"This object configures the Debug Level for Compression 
Debug Systems."
::= { edgeCfgDebugLevelEntry 9 }

-- The EdgeServer Configuration Memory Utilization Trap Group

edgeMemUtlTrap OBJECT IDENTIFIER ::= { edge 3 }

edgeMemUtlTrapTable OBJECT-TYPE
SYNTAX SEQUENCE OF EdgeMemUtlTrapEntry
ACCESS not-accessible
STATUS mandatory
DESCRIPTION
"Table containing objects for Memory Utilization Trap for 
EdgeServer Gateway Cards in the chassis."
::= { edgeMemUtlTrap 1 }

edgeMemUtlTrapEntry OBJECT-TYPE
SYNTAX EdgeMemUtlTrapEntry
ACCESS not-accessible
STATUS mandatory
DESCRIPTION
"There is one Operational row for each Gateway Card in the 
NAS chassis."
INDEX { edgeMemUtlTrIndex }
::= { edgeMemUtlTrapTable 1 }

EdgeMemUtlTrapEntry ::=
SEQUENCE {
edgeMemUtlTrIndex
    INTEGER,
edgeMemUtlTrMrgOperStatus
    INTEGER,
edgeMemUtlTrNonOperStatus
    INTEGER,
edgeMemUtlTrClearStatus
    INTEGER,
edgeMemUtlTrMrgOperThreshCnt
    INTEGER,
edgeMemUtlTrNonOperThreshCnt
    INTEGER,
edgeMemUtlTrClearThreshCnt
    INTEGER,
edgeMemUtlTrMrgOperThreshTimer
    INTEGER,
edgeMemUtlTrNonOperThreshTimer
    INTEGER,
edgeMemUtlTrClearThreshTimer
    INTEGER,
edgeMemUtlTrStatus
    INTEGER
}

edgeMemUtlTrIndex OBJECT-TYPE
SYNTAX INTEGER
ACCESS read-only
STATUS mandatory
DESCRIPTION
"A unique index identifying the Gateway Card to which the 
Memory Utilization Trap objects pertain"
::= { edgeMemUtlTrapEntry 1 }

edgeMemUtlTrMrgOperStatus OBJECT-TYPE
SYNTAX INTEGER{
  enableTraps(1),
  disableTraps(2)
}
ACCESS read-write
STATUS mandatory
DESCRIPTION
"This object is the operational Memory Utilization status 
Marginally operational trap enable/disable."
::= { edgeMemUtlTrapEntry 2 }

edgeMemUtlTrNonOperStatus OBJECT-TYPE
SYNTAX INTEGER{
  enableTraps(1),
  disableTraps(2)
}
ACCESS read-write
STATUS mandatory
DESCRIPTION
"This object is the operational Memory Utilization status 
Non operational trap enable/disable."
::= { edgeMemUtlTrapEntry 3 }

edgeMemUtlTrClearStatus OBJECT-TYPE
SYNTAX INTEGER{
  enableTraps(1),
  disableTraps(2)
}
ACCESS read-write
STATUS mandatory
DESCRIPTION
"This object is the operatinal Memory Utilization status 
Clear trap enable/disable."
::= { edgeMemUtlTrapEntry 4 }

edgeMemUtlTrMrgOperThreshCnt OBJECT-TYPE
SYNTAX INTEGER
ACCESS read-write
STATUS mandatory
DESCRIPTION
"This object is the Memory Utilization Marginally 
Operational Trap Threshold Count."
::= { edgeMemUtlTrapEntry 5 }

edgeMemUtlTrNonOperThreshCnt OBJECT-TYPE
SYNTAX INTEGER
ACCESS read-write
STATUS mandatory
DESCRIPTION
"This object is the Memory Utilization Non Operational Trap 
Threshold Count."
::= { edgeMemUtlTrapEntry 6 }

edgeMemUtlTrClearThreshCnt OBJECT-TYPE
SYNTAX INTEGER
ACCESS read-write
STATUS mandatory
DESCRIPTION
"This object is the Memory Utilization Clear Trap Threshold 
Count."
::= { edgeMemUtlTrapEntry 7 }

edgeMemUtlTrMrgOperThreshTimer OBJECT-TYPE
SYNTAX INTEGER
ACCESS read-write
STATUS mandatory
DESCRIPTION
"This object is the Memory Utilization Marginally 
Operational Trap Threshold Time."
::= { edgeMemUtlTrapEntry 8 }

edgeMemUtlTrNonOperThreshTimer OBJECT-TYPE
SYNTAX INTEGER
ACCESS read-write
STATUS mandatory
DESCRIPTION
"This object is the Memory Utilization Non Operational Trap 
Threshold Time."
::= { edgeMemUtlTrapEntry 9 }

edgeMemUtlTrClearThreshTimer OBJECT-TYPE
SYNTAX INTEGER
ACCESS read-write
STATUS mandatory
DESCRIPTION
"This object is the Memory Utilization Clear Trap Threshold 
Time."
::= { edgeMemUtlTrapEntry 10 }

edgeMemUtlTrStatus OBJECT-TYPE
SYNTAX INTEGER{
  operational(1),
  marginallyOperational(2),
  nonOperational(3)
}
ACCESS read-only
STATUS mandatory
DESCRIPTION
"This object is the Status of the Memory utilization trap."
::= { edgeMemUtlTrapEntry 11 }

-- The EdgeServer CPU Configuration Utilization Trap Group

edgeCpuUtlTrap OBJECT IDENTIFIER ::= { edge 4 }

edgeCpuUtlTrapTable OBJECT-TYPE
SYNTAX SEQUENCE OF EdgeCpuUtlTrapEntry
ACCESS not-accessible
STATUS mandatory
DESCRIPTION
"Table containing objects for CPU Utilization Trap for 
EdgeServer Gateway Cards in the chassis."
::= { edgeCpuUtlTrap 1 }

edgeCpuUtlTrapEntry OBJECT-TYPE
SYNTAX EdgeCpuUtlTrapEntry
ACCESS not-accessible
STATUS mandatory
DESCRIPTION
"There is one Operational row for each Gateway Card in the 
NAS chassis."
INDEX { edgeCpuUtlTrIndex }
::= { edgeCpuUtlTrapTable 1 }

EdgeCpuUtlTrapEntry ::=
SEQUENCE {
edgeCpuUtlTrIndex
    INTEGER,
edgeCpuUtlTrMrgOperStatus
    INTEGER,
edgeCpuUtlTrNonOperStatus
    INTEGER,
edgeCpuUtlTrClearStatus
    INTEGER,
edgeCpuUtlTrMrgOperThreshCnt
    INTEGER,
edgeCpuUtlTrNonOperThreshCnt
    INTEGER,
edgeCpuUtlTrClearThreshCnt
    INTEGER,
edgeCpuUtlTrMrgOperThreshTimer
    INTEGER,
edgeCpuUtlTrNonOperThreshTimer
    INTEGER,
edgeCpuUtlTrClearThreshTimer
    INTEGER,
edgeCpuUtlTrStatus
    INTEGER
}

edgeCpuUtlTrIndex OBJECT-TYPE
SYNTAX INTEGER
ACCESS read-only
STATUS mandatory
DESCRIPTION
"A unique index identifying the Gateway Card to which the 
CPU Utilization Trap objects pertain"
::= { edgeCpuUtlTrapEntry 1 }

edgeCpuUtlTrMrgOperStatus OBJECT-TYPE
SYNTAX INTEGER{
  enableTraps(1),
  disableTraps(2)
}
ACCESS read-write
STATUS mandatory
DESCRIPTION
"This object is see the current operation of the CPU 
Utilization status Marginally operational trap 
enable/disable."
::= { edgeCpuUtlTrapEntry 2 }

edgeCpuUtlTrNonOperStatus OBJECT-TYPE
SYNTAX INTEGER{
  enableTraps(1),
  disableTraps(2)
}
ACCESS read-write
STATUS mandatory
DESCRIPTION
"This object is to see the curent operation of the CPU 
Utilization status Non operational trap enable/disable."
::= { edgeCpuUtlTrapEntry 3 }

edgeCpuUtlTrClearStatus OBJECT-TYPE
SYNTAX INTEGER{
  enableTraps(1),
  disableTraps(2)
}
ACCESS read-write
STATUS mandatory
DESCRIPTION
"This object is to see the current operation the CPU 
Utilization status Clear trap enable/disable."
::= { edgeCpuUtlTrapEntry 4 }

edgeCpuUtlTrMrgOperThreshCnt OBJECT-TYPE
SYNTAX INTEGER
ACCESS read-write
STATUS mandatory
DESCRIPTION
"This object is the CPU Utilization Marginally Operational 
Trap Threshold Count."
::= { edgeCpuUtlTrapEntry 5 }

edgeCpuUtlTrNonOperThreshCnt OBJECT-TYPE
SYNTAX INTEGER
ACCESS read-write
STATUS mandatory
DESCRIPTION
"This object is the CPU Utilization Non Operational Trap 
Threshold Count."
::= { edgeCpuUtlTrapEntry 6 }

edgeCpuUtlTrClearThreshCnt OBJECT-TYPE
SYNTAX INTEGER
ACCESS read-write
STATUS mandatory
DESCRIPTION
"This object is the CPU Utilization Clear Trap Threshold 
Count."
::= { edgeCpuUtlTrapEntry 7 }

edgeCpuUtlTrMrgOperThreshTimer OBJECT-TYPE
SYNTAX INTEGER
ACCESS read-write
STATUS mandatory
DESCRIPTION
"This object is the CPU Utilization Marginally Operational 
Trap Threshold Time."
::= { edgeCpuUtlTrapEntry 8 }

edgeCpuUtlTrNonOperThreshTimer OBJECT-TYPE
SYNTAX INTEGER
ACCESS read-write
STATUS mandatory
DESCRIPTION
"This object is the CPU Utilization Non Operational Trap 
Threshold Time."
::= { edgeCpuUtlTrapEntry 9 }

edgeCpuUtlTrClearThreshTimer OBJECT-TYPE
SYNTAX INTEGER
ACCESS read-write
STATUS mandatory
DESCRIPTION
"This object is the CPU Utilization Clear Trap Threshold 
Time."
::= { edgeCpuUtlTrapEntry 10 }

edgeCpuUtlTrStatus OBJECT-TYPE
SYNTAX INTEGER{
  operational(1),
  marginallyOperational(2),
  nonOperational(3)
}
ACCESS read-only
STATUS mandatory
DESCRIPTION
"This object is the CPU Utilization trap status."
::= { edgeCpuUtlTrapEntry 11 }

-- The EdgeServer Configuration DISK Utilization Trap Group

edgeDskUtlTrap OBJECT IDENTIFIER ::= { edge 5 }

edgeDskUtlTrapTable OBJECT-TYPE
SYNTAX SEQUENCE OF EdgeDskUtlTrapEntry
ACCESS not-accessible
STATUS mandatory
DESCRIPTION
"Table containing objects for DISK Utilization Trap for 
EdgeServer Gateway Cards in the chassis."
::= { edgeDskUtlTrap 1 }

edgeDskUtlTrapEntry OBJECT-TYPE
SYNTAX EdgeDskUtlTrapEntry
ACCESS not-accessible
STATUS mandatory
DESCRIPTION
"There is one Operational row for each Gateway Card in the 
NAS chassis."
INDEX { edgeDskUtlTrIndex }
::= { edgeDskUtlTrapTable 1 }

EdgeDskUtlTrapEntry ::=
SEQUENCE {
edgeDskUtlTrIndex
    INTEGER,
edgeDskUtlTrMrgOperStatus
    INTEGER,
edgeDskUtlTrNonOperStatus
    INTEGER,
edgeDskUtlTrClearStatus
    INTEGER,
edgeDskUtlTrMrgOperThreshCnt
    INTEGER,
edgeDskUtlTrNonOperThreshCnt
    INTEGER,
edgeDskUtlTrClearThreshCnt
    INTEGER,
edgeDskUtlTrMrgOperThreshTimer
    INTEGER,
edgeDskUtlTrNonOperThreshTimer
    INTEGER,
edgeDskUtlTrClearThreshTimer
    INTEGER,
edgeDskUtlTrStatus
    INTEGER
}

edgeDskUtlTrIndex OBJECT-TYPE
SYNTAX INTEGER
ACCESS read-only
STATUS mandatory
DESCRIPTION
"A unique index identifying the Gateway Card to which the 
DISK Utilization Trap objects pertain"
::= { edgeDskUtlTrapEntry 1 }

edgeDskUtlTrMrgOperStatus OBJECT-TYPE
SYNTAX INTEGER{
  enableTraps(1),
  disableTraps(2)
}
ACCESS read-write
STATUS mandatory
DESCRIPTION
"This object is see the current setting of the DISK 
Utilization status Marginally operational trap 
enable/disable."
::= { edgeDskUtlTrapEntry 2 }

edgeDskUtlTrNonOperStatus OBJECT-TYPE
SYNTAX INTEGER{
  enableTraps(1),
  disableTraps(2)
}
ACCESS read-write
STATUS mandatory
DESCRIPTION
"This object is to see the current setting of the DISK 
Utilization status Non operational trap enable/disable."
::= { edgeDskUtlTrapEntry 3 }

edgeDskUtlTrClearStatus OBJECT-TYPE
SYNTAX INTEGER{
  enableTraps(1),
  disableTraps(2)
}
ACCESS read-write
STATUS mandatory
DESCRIPTION
"This object is to see the current operational setting of 
the DISK Utilization status Clear trap enable/disable."
::= { edgeDskUtlTrapEntry 4 }

edgeDskUtlTrMrgOperThreshCnt OBJECT-TYPE
SYNTAX INTEGER
ACCESS read-write
STATUS mandatory
DESCRIPTION
"This object is the DISK Utilization Marginally Operational 
Trap Threshold Count."
::= { edgeDskUtlTrapEntry 5 }

edgeDskUtlTrNonOperThreshCnt OBJECT-TYPE
SYNTAX INTEGER
ACCESS read-write
STATUS mandatory
DESCRIPTION
"This object is the DISK Utilization Non Operational Trap 
Threshold Count."
::= { edgeDskUtlTrapEntry 6 }

edgeDskUtlTrClearThreshCnt OBJECT-TYPE
SYNTAX INTEGER
ACCESS read-write
STATUS mandatory
DESCRIPTION
"This object is the DISK Utilization Clear Trap Threshold 
Count."
::= { edgeDskUtlTrapEntry 7 }

edgeDskUtlTrMrgOperThreshTimer OBJECT-TYPE
SYNTAX INTEGER
ACCESS read-write
STATUS mandatory
DESCRIPTION
"This object is the DISK Utilization Marginally Operational 
Trap Threshold Time."
::= { edgeDskUtlTrapEntry 8 }

edgeDskUtlTrNonOperThreshTimer OBJECT-TYPE
SYNTAX INTEGER
ACCESS read-write
STATUS mandatory
DESCRIPTION
"This object is the DISK Utilization Non Operational Trap 
Threshold Time."
::= { edgeDskUtlTrapEntry 9 }

edgeDskUtlTrClearThreshTimer OBJECT-TYPE
SYNTAX INTEGER
ACCESS read-write
STATUS mandatory
DESCRIPTION
"This object is the DISK Utilization Clear Trap Threshold 
Time."
::= { edgeDskUtlTrapEntry 10 }

edgeDskUtlTrStatus OBJECT-TYPE
SYNTAX INTEGER{
  operational(1),
  marginallyOperational(2),
  nonOperational(3)
}
ACCESS read-only
STATUS mandatory
DESCRIPTION
"This object is the DISK Utilization trap status."
::= { edgeDskUtlTrapEntry 11 }

edgeCmd OBJECT IDENTIFIER ::= { edge 6 }

edgeCmdTable OBJECT-TYPE
SYNTAX SEQUENCE OF EdgeCmdEntry
ACCESS not-accessible
STATUS mandatory
DESCRIPTION
"The IP Card Command table contains an entry for each of the 
manageable IP Gateway Card in the chassis.  It provides a 
means through which to take specific actions on one or more 
IP Gateway cards in the NAS chassis."
::= { edgeCmd 1 }

edgeCmdEntry OBJECT-TYPE
SYNTAX EdgeCmdEntry
ACCESS not-accessible
STATUS mandatory
DESCRIPTION
"There is one IP Gateway Card Command entry per IP Gateway 
Card in the chassis."
INDEX { edgeCmdIndex }
::= { edgeCmdTable 1 }

EdgeCmdEntry ::=
SEQUENCE {
edgeCmdIndex
    INTEGER,
edgeCmdMgtStationId
    OCTET STRING,
edgeCmdReqId
    INTEGER,
edgeCmdFunction
    INTEGER,
edgeCmdForce
    INTEGER,
edgeCmdParam
    OCTET STRING,
edgeCmdResult
    INTEGER,
edgeCmdCode
    INTEGER
}

edgeCmdIndex OBJECT-TYPE
SYNTAX INTEGER
ACCESS read-only
STATUS mandatory
DESCRIPTION
"A unique value for each IP Gateway Card in the chassis.  
The value of this object matches the value of the index of 
the correspond1ing IP Gateway Card's entry in the entity 
table of the chassis MIB."
::= { edgeCmdEntry 1 }

edgeCmdMgtStationId OBJECT-TYPE
SYNTAX OCTET STRING (SIZE(0..8))
ACCESS read-write
STATUS mandatory
DESCRIPTION
"This object is a generic read-write variable that a 
Management Station (MS) can use to guarantee that the 
results from a given command are the results of a command 
issued by that specific MS.  Each MS must SET a unique 
value to this object when doing commands and GET the value 
of this object together with ipgwCmdReqId and ipgwCmdResult 
to detect interference from other MSs."
::= { edgeCmdEntry 2 }

edgeCmdReqId OBJECT-TYPE
SYNTAX INTEGER
ACCESS read-only
STATUS mandatory
DESCRIPTION
"This object contains the value of the request-id field in 
the SNMP PDU which invoked the current or most recent 
command or test on this IP Gateway Card.  If the request-id 
is unknown or undefined, this object contains the value 
zero."
::= { edgeCmdEntry 3 }

edgeCmdFunction OBJECT-TYPE
SYNTAX INTEGER{
  noCommand(1),
  softwareReset(7),
  bulkfileUpload(9)
}
ACCESS read-write
STATUS mandatory
DESCRIPTION
"This object contains a value which describes the command 
which is being invoked."
::= { edgeCmdEntry 4 }

edgeCmdForce OBJECT-TYPE
SYNTAX INTEGER{
  force(1),
  noForce(2)
}
ACCESS read-write
STATUS mandatory
DESCRIPTION
"In some cases, the IP Gateway Card may be in a state such 
that certain commands could adversely affect connections.  
In such cases, a command request with this object not 
present or set to noForce will result in a warning.  If the 
operator elects to ignore such warnings, this object can be 
set to force in a subsequent issue of the command to cause 
the command to be carried out regardless of its potentially 
hazzardous effects."
::= { edgeCmdEntry 5 }

edgeCmdParam OBJECT-TYPE
SYNTAX OCTET STRING
ACCESS read-write
STATUS mandatory
DESCRIPTION
"This object contains parameters that are specific to the 
particular command being issued.  In some cases, there will 
be no aditional parameters required."
::= { edgeCmdEntry 6 }

edgeCmdResult OBJECT-TYPE
SYNTAX INTEGER{
  none(1),
  success(2),
  inProgress(3),
  notSupported(4),
  unAbleToRun(5),
  aborted(6),
  failed(7)
}
ACCESS read-only
STATUS mandatory
DESCRIPTION
"This object contains the result of the most recently 
requested command or test, or the value none(1) if no 
commands have been requested since the last reset."
::= { edgeCmdEntry 7 }

edgeCmdCode OBJECT-TYPE
SYNTAX INTEGER{
  noError(1),
  unable(2),
  unrecognizedCommand(6),
  slotEmpty(8),
  noResponse(12),
  unsupportedCommand(20),
  deviceDisabled(22),
  testFailed(25),
  userInterfaceActive(58),
  pendingSoftwareDownload(73)
}
ACCESS read-only
STATUS mandatory
DESCRIPTION
"The value of this object upon command completion indicates 
a further description of what went wrong if the command was 
unsuccessful.  In the case of tests, a bit mapped result of 
each of the sub-tests performed can be found in the status 
table."
::= { edgeCmdEntry 8 }

END
