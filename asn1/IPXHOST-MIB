IPXHOST-MIB DEFINITIONS ::= BEGIN
	IMPORTS
        OBJECT-TYPE, MODULE-IDENTITY,
        Counter32, Integer32
				  FROM SNMPv2-SMI
        DisplayString
                  FROM SNMPv2-TC
        PhysAddress, common, UsrConfigStatus
                  FROM USR-DEFINITIONS-MIB;
    usrIpx MODULE-IDENTITY
        LAST-UPDATED "200205051400Z"
        ORGANIZATION "CommWorks Corporation, a 3Com Company"
        CONTACT-INFO "Customer Support"
        DESCRIPTION
                 "The commWorks enterprise defined MIB objects for IPX"
--      REVISION "200205051400Z"
--      DESCRIPTION "Converted to SNMPv2"
    ::= { common 4 }
   -- textual conventions
   -- 
   -- textual conventions are like pre-processor macro in 'C'
   --        (i.e. #define statements)
   -- Use them to define your own 'datatypes'
   -- memory size, expressed in units of 1024bytes
   KBytes ::=    INTEGER (0..2147483647)
   NetNumber ::= OCTET STRING (SIZE(4))
   UsrIpxStates ::= INTEGER   
                        {
                        initializing(1),
	                    enable(2),   -- Normal state following powerup of reenable.
                        shutdown(3), -- Immediately following a disable command.
                        disable(4)   -- Following RIP shutdown. 
                         }
   -- Begin managed object definitions here...
    usrIpxVersionNumber OBJECT-TYPE
         SYNTAX       Integer32
         MAX-ACCESS   read-only
         STATUS       current
         DESCRIPTION
            "The version number for the IPX module."
         ::= { usrIpx 1 }
     usrIpxSplitEqualCostRoutes OBJECT-TYPE
        SYNTAX   INTEGER {
                        disable(0),
                        enable(1)
                        }
         MAX-ACCESS   read-write
         STATUS       current
         DESCRIPTION
            "Allow splitting of equal cost routes. IPX maintains multiple routes to 
             the same destination network.  When this field is enabled IPX will split
             traffic over the multiple routes.  This is also know as load balancing.
             Not currently supported by the code."
         ::= { usrIpx 2 }
    usrIpxProtocolPriority OBJECT-TYPE
         SYNTAX   INTEGER (1..3)
         MAX-ACCESS   read-write
         STATUS       current
         DESCRIPTION
                "The IPX priority relative to other protocols. 
                 Not currently supported by the code."
         ::= { usrIpx 3 }
    usrIpxMaxRegisteredPaths OBJECT-TYPE
         SYNTAX   INTEGER (1..255)
         MAX-ACCESS   read-write
         STATUS       current
         DESCRIPTION
                "The maximum number of routes to be maintained in the box. 
                 Not currently supported by the code."
         ::= { usrIpx 4 }
    usrIpxDefaultGateway OBJECT-TYPE
         SYNTAX   OCTET STRING (SIZE(10))
         MAX-ACCESS   read-write
         STATUS       current
         DESCRIPTION
                "The Default Gateway. The first leading bytes are IPX network number and the
                trailing 6 bytes of this string should contain ethernet address."
         --CONFIGURABLE
         ::= { usrIpx 5 }
     usrIpxRipTracingState OBJECT-TYPE
          SYNTAX      INTEGER {
                        disable(0),
                        enable(1)
                       }
          MAX-ACCESS      read-write
          STATUS          current
          DESCRIPTION "The state of RIP Packet Tracing. When this is enabled 
                       each packet that the IPX RIP software receives is 
                       printed to the console. This object is only applicable
                       on specially compiled DEBUG software versions."
         --CONFIGURABLE
     ::= {usrIpx 6}
     usrIpxSapTracingState OBJECT-TYPE
          SYNTAX      INTEGER {
                        disable(0),
                        enable(1)
                       }
          MAX-ACCESS      read-write
          STATUS          current
          DESCRIPTION "The state of SAP Packet Tracing. When this is enabled
                       each packet that the IPX SAP software receives is
                       printed to the console. This object is only applicable
                       on specially compiled DEBUG software versions."
         --CONFIGURABLE
     ::= {usrIpx 7}
-- IPX Static Route
--
    usrIpxStaticRouteTable OBJECT-TYPE
         SYNTAX  SEQUENCE OF USRIPXStaticRouteEntry 
         MAX-ACCESS  not-accessible
         STATUS      current
         DESCRIPTION
            ""
    ::= { usrIpx 8 }
     usrIpxStaticRouteEntry OBJECT-TYPE
        SYNTAX      USRIPXStaticRouteEntry
        MAX-ACCESS  not-accessible
        STATUS      current
        DESCRIPTION "Each entry corresponds to one static route."
        INDEX   {
                usrIpxStaticRouteSysInstance,
                usrIpxStaticRouteCircIndex,
                usrIpxStaticRouteNetNum
               }
     ::= {usrIpxStaticRouteTable 1}
     USRIPXStaticRouteEntry ::= 
          SEQUENCE {
               usrIpxStaticRouteSysInstance
                    Integer32,
               usrIpxStaticRouteCircIndex
                    Integer32,
               usrIpxStaticRouteNetNum
                    NetNumber,
               usrIpxStaticRouteExistState
                    INTEGER,
               usrIpxStaticRouteTicks
                    Integer32,
               usrIpxStaticRouteHopCount
                    Integer32,
               usrIpxStaticRouteNextHopNICAddress
                    PhysAddress,
               usrIpxStaticRouteNextHopNetNum
                    NetNumber
               }
     usrIpxStaticRouteSysInstance OBJECT-TYPE
        SYNTAX      Integer32
        MAX-ACCESS      read-write
        STATUS      	current
        DESCRIPTION "The unique identifier of the instance of IPX to
                      which this row corresponds."
     ::= {usrIpxStaticRouteEntry 1}
     usrIpxStaticRouteCircIndex OBJECT-TYPE
        SYNTAX      Integer32
        MAX-ACCESS      read-write
        STATUS      	current
        DESCRIPTION "The unique identifier of the circuit used to
                     reach the first hop in the static route."
     ::= {usrIpxStaticRouteEntry 2}
     usrIpxStaticRouteNetNum OBJECT-TYPE
        SYNTAX      NetNumber
        MAX-ACCESS      read-write
        STATUS      	current
        DESCRIPTION "The IPX network number of the route's destination."
        --CONFIGURABLE
     ::= {usrIpxStaticRouteEntry 3}
     usrIpxStaticRouteExistState OBJECT-TYPE
        SYNTAX      INTEGER {
                        off(1),
                        on(2)
                       }
        MAX-ACCESS      read-write
        STATUS      	current
        DESCRIPTION "The validity of this static route.  Entries with the
                     value set to off may be deleted from the table at the
                     implementation's discretion."
     ::= {usrIpxStaticRouteEntry 4}
     usrIpxStaticRouteTicks OBJECT-TYPE
        SYNTAX      Integer32
        MAX-ACCESS      read-write
        STATUS      	current
        DESCRIPTION "The delay, in ticks, to reach the route's destination."
        --CONFIGURABLE
     ::= {usrIpxStaticRouteEntry 5}
     usrIpxStaticRouteHopCount OBJECT-TYPE
        SYNTAX      Integer32
        MAX-ACCESS      read-write
        STATUS      	current
        DESCRIPTION "The number of router hops necessary to reach the destination."
        --CONFIGURABLE
     ::= {usrIpxStaticRouteEntry 6}
     usrIpxStaticRouteNextHopNICAddress OBJECT-TYPE
        SYNTAX      PhysAddress
        MAX-ACCESS      read-write
        STATUS      	current
        DESCRIPTION "The NIC address of the next router in the routing path to the destination."
        --CONFIGURABLE
     ::= {usrIpxStaticRouteEntry 7}
     usrIpxStaticRouteNextHopNetNum OBJECT-TYPE
        SYNTAX      NetNumber
        MAX-ACCESS      read-write
        STATUS      	current
        DESCRIPTION "The Next Hop Network Number of the router in the routing path to the destination."
        --CONFIGURABLE
     ::= {usrIpxStaticRouteEntry 8}
-- Static Services Table
--   This table contains information for all services reached via a
--   static route.
    usrIpxStaticServTable OBJECT-TYPE
         SYNTAX      SEQUENCE OF USRIPXStaticServEntry
         MAX-ACCESS      not-accessible
         STATUS      	current
         DESCRIPTION "The Static Services table contains information about
                      all services reached via statically configured routes."
       ::= {usrIpx 9}
    usrIpxStaticServEntry OBJECT-TYPE
         SYNTAX      USRIPXStaticServEntry
         MAX-ACCESS      not-accessible
         STATUS      	current
         DESCRIPTION "Each entry corresponds to one service."
         INDEX       {
                        usrIpxStaticServSysInstance,
                        usrIpxStaticServCircIndex,
                        usrIpxStaticServName,
                        usrIpxStaticServType
                      }
       ::= {usrIpxStaticServTable 1}
    USRIPXStaticServEntry ::= 
             SEQUENCE {
                           usrIpxStaticServSysInstance
                              Integer32,
                           usrIpxStaticServCircIndex
                              Integer32,
                           usrIpxStaticServName
                              OCTET STRING,
                           usrIpxStaticServType
                              OCTET STRING,
                           usrIpxStaticServExistState
                              INTEGER,
                           usrIpxStaticServNetNum
                              NetNumber,
                           usrIpxStaticServNode
                              OCTET STRING,
                           usrIpxStaticServSocket
                              OCTET STRING,
                           usrIpxStaticServHopCount
                              Integer32,
                           usrIpxStaticServNextHopNICAddress
                              PhysAddress,
                           usrIpxStaticServNextHopNetNum
                              NetNumber
                          }
    usrIpxStaticServSysInstance OBJECT-TYPE
         SYNTAX      Integer32
         MAX-ACCESS      read-write
         STATUS      	current
         DESCRIPTION "The unique identifier of the instance of IPX to which
                      this entry corresponds."
    ::= {usrIpxStaticServEntry 1}
    usrIpxStaticServCircIndex OBJECT-TYPE
         SYNTAX      Integer32
         MAX-ACCESS      read-write
         STATUS      	current
         DESCRIPTION "The circuit used to reach this service."
       ::= {usrIpxStaticServEntry 2}
    usrIpxStaticServName OBJECT-TYPE
         SYNTAX      OCTET STRING (SIZE(1..48))
         MAX-ACCESS      read-write
         STATUS      	current
         DESCRIPTION "The service name."
         --CONFIGURABLE
       ::= {usrIpxStaticServEntry 3}
    usrIpxStaticServType OBJECT-TYPE
         SYNTAX      OCTET STRING (SIZE(2))
         MAX-ACCESS      read-write
         STATUS      	current
         DESCRIPTION "The service type."
         --CONFIGURABLE
       ::= {usrIpxStaticServEntry 4}
    usrIpxStaticServExistState OBJECT-TYPE
         SYNTAX      INTEGER {
                          off(1),
                          on(2)
                           }
         MAX-ACCESS      read-write
         STATUS      	current
         DESCRIPTION "The validity of this static service.  Entries with the
                      value set to off may be deleted from the table at the
                      implementation's discretion."
       ::= {usrIpxStaticServEntry 5}
    usrIpxStaticServNetNum OBJECT-TYPE
         SYNTAX      NetNumber
         MAX-ACCESS      read-write
         STATUS      	current
         DESCRIPTION "The IPX network number portion of the IPX address of the
                      service."
         --CONFIGURABLE
       ::= {usrIpxStaticServEntry 6}
    usrIpxStaticServNode OBJECT-TYPE
         SYNTAX      OCTET STRING (SIZE(6))
         MAX-ACCESS      read-write
         STATUS      	current
         DESCRIPTION "The node portion of the IPX address of the service."
         --CONFIGURABLE
       ::= {usrIpxStaticServEntry 7}
    usrIpxStaticServSocket OBJECT-TYPE
         SYNTAX      OCTET STRING (SIZE(2))
         MAX-ACCESS      read-write
         STATUS      	current
         DESCRIPTION "The socket portion of the IPX address of the service."
         --CONFIGURABLE
       ::= {usrIpxStaticServEntry 8}
    usrIpxStaticServHopCount OBJECT-TYPE
         SYNTAX      Integer32
         MAX-ACCESS      read-write
         STATUS      	current
         DESCRIPTION "The number of router hops to the server on which the service resides."
         --CONFIGURABLE
       ::= {usrIpxStaticServEntry 9}
    usrIpxStaticServNextHopNICAddress OBJECT-TYPE
         SYNTAX      PhysAddress
         MAX-ACCESS      read-write
         STATUS      	current
         DESCRIPTION "The NIC address of next router in the path to the 
                      server on which the service resides."
         --CONFIGURABLE
       ::= {usrIpxStaticServEntry 10}
    usrIpxStaticServNextHopNetNum OBJECT-TYPE
         SYNTAX      NetNumber
         MAX-ACCESS      read-write
         STATUS      	current
         DESCRIPTION "The network number of the next router in path to the 
                      server on which the service resides."
         --CONFIGURABLE
       ::= {usrIpxStaticServEntry 11}
-- Portal MIB Variables
--
    usrIpxPortalTable OBJECT-TYPE
         SYNTAX  SEQUENCE OF USRIpxPortalEntry 
         MAX-ACCESS  not-accessible
         STATUS  	current
         DESCRIPTION
            ""
    ::= { usrIpx 10 }
     usrIpxPortalEntry OBJECT-TYPE
        SYNTAX      USRIpxPortalEntry
        MAX-ACCESS      not-accessible
        STATUS      	current
        DESCRIPTION "Each entry corresponds to one static route."
        INDEX   {
                usrIpxPortalSysInstance,
                usrIpxPortalPortNumber
               }
     ::= {usrIpxPortalTable 1}
     USRIpxPortalEntry ::= 
          SEQUENCE {
               usrIpxPortalSysInstance
                    Integer32,
               usrIpxPortalPortNumber
                    Integer32,
               usrIpxPortalNetBiosState
                    INTEGER,
               usrIpxPortalNetworkDelay
                    Integer32,
               usrIpxPortalMaxNumberRipEntries
                    Integer32,
               usrIpxPortalMaxNumberSapEntries
                    Integer32,
               usrIpxPortalRipBroadcastState
                    INTEGER,
               usrIpxPortalSapBroadcastState
                    INTEGER,
               usrIpxPortalRipPeriodicState
                    INTEGER,
               usrIpxPortalSapPeriodicState
                    INTEGER,
               usrIpxPortalNetBiosNameCachingState
                    INTEGER,
               usrIpxPortalNetBiosHops
                    Integer32,
               usrIpxPortalDiagnosticState
                    INTEGER,
               usrIpxPortalNetBiosNameCachingTimer
                    Integer32,
               usrIpxPortalMaxLearningRetries
                    Integer32,
               usrIpxPortalIpxwanState
                    INTEGER,
               usrIpxPortalLargeHopCount
                    Counter32,
               usrIpxPortalNetbsLargeHopCount
                    Counter32,
               usrIpxPortalNoNetRipPkt
                    Counter32,
               usrIpxPortalPathNotFoundToRoute
                    Counter32,
               usrIpxPortalNumberOfAgedRoutes
                    Counter32,
               usrIpxPortalWrongNetRipPkt
                    Counter32,
               usrIpxPortalNumberOfAgedSaps
                    Counter32,
               usrIpxPortalNumberOfWDogReqRcvd
                    Counter32,
               usrIpxPortalNumberOfWDogRspSent
                    Counter32,
               usrIpxPortalNumberOfSerialPktsRcvd
                    Counter32,
               usrIpxPortalNumberOfEchoReqRcvd
                    Counter32,
               usrIpxPortalNumberOfEchoRspSent
                    Counter32,
               usrIpxPortalNumberOfPktsTooLargeRcvd
                    Counter32,
               usrIpxPortalRipReceiveState
                    INTEGER,
               usrIpxPortalSapReceiveState
                    INTEGER
               }
     usrIpxPortalSysInstance OBJECT-TYPE
        SYNTAX      Integer32
        MAX-ACCESS      read-write
        STATUS      	current
        DESCRIPTION "The unique identifier of the instance of IPX to
                      which this row corresponds."
     ::= {usrIpxPortalEntry 1}
     usrIpxPortalPortNumber OBJECT-TYPE
        SYNTAX      Integer32
        MAX-ACCESS      read-write
        STATUS      	current
        DESCRIPTION "The unique identifier for this IPX portal."
     ::= {usrIpxPortalEntry 2}
     usrIpxPortalNetBiosState OBJECT-TYPE
        SYNTAX      INTEGER {
                        disable(0),
                        enable(1)
                       }
        MAX-ACCESS      read-write
        STATUS      	current
        DESCRIPTION "The state of NetBios Processing. When enabled the 
                     router maintains a NetBios name table."
     ::= {usrIpxPortalEntry 3}
     usrIpxPortalNetworkDelay OBJECT-TYPE
        SYNTAX      Integer32
        MAX-ACCESS      read-write
        STATUS      	current
        DESCRIPTION "The delay, in ticks, for this portal interface."
     ::= {usrIpxPortalEntry 4}
     usrIpxPortalMaxNumberRipEntries OBJECT-TYPE
        SYNTAX      Integer32
        MAX-ACCESS      read-write
        STATUS      	current
        DESCRIPTION "The maximum number of entries within a RIP packet."
     ::= {usrIpxPortalEntry 5}
     usrIpxPortalMaxNumberSapEntries OBJECT-TYPE
        SYNTAX      Integer32
        MAX-ACCESS      read-write
        STATUS      	current
        DESCRIPTION "The maximum number of entries within a SAP packet."
     ::= {usrIpxPortalEntry 6}
     usrIpxPortalRipBroadcastState OBJECT-TYPE
        SYNTAX      INTEGER {
                        disable(0),
                        enable(1)
                       }
        MAX-ACCESS      read-write 
        STATUS      	current
        DESCRIPTION "RIP broadcast packet state. When enabled IPX RIP will be enabled
                     to send out RIP request packets transmitted over this portal. 
                     To totally disable RIP traffic usrIpxPortalRipPeriodicState
                     must also be set to disable."
     ::= {usrIpxPortalEntry 7}
     usrIpxPortalSapBroadcastState OBJECT-TYPE
        SYNTAX      INTEGER {
                        disable(0),
                        enable(1)
                       }
        MAX-ACCESS      read-write
        STATUS      	current
        DESCRIPTION "SAP broadcast packet state. When enabled IPX SAP will be enabled
                     to send out SAP request packets transmitted over this portal. 
                     To totally disable SAP traffic usrIpxPortalSapPeriodicState
                     must also be set to disable."
     ::= {usrIpxPortalEntry 8}
     usrIpxPortalRipPeriodicState OBJECT-TYPE
        SYNTAX      INTEGER {
                        disable(0),
                        enable(1)
                       }
        MAX-ACCESS      read-write
        STATUS      	current
        DESCRIPTION "RIP periodic state."
     ::= {usrIpxPortalEntry 9}
     usrIpxPortalSapPeriodicState OBJECT-TYPE
        SYNTAX      INTEGER {
                        disable(0),
                        enable(1)
                       }
        MAX-ACCESS      read-write
        STATUS      	current
        DESCRIPTION "Controls sending periodic SAP broadcasts over this portal."
     ::= {usrIpxPortalEntry 10}
     usrIpxPortalNetBiosNameCachingState OBJECT-TYPE
        SYNTAX      INTEGER {
                        disable(0),
                        enable(1)
                       }
        MAX-ACCESS      read-write
        STATUS      	current
        DESCRIPTION "NetBios name caching state. When enabled IPX will maintain a table
                     of NetBios names"
     ::= {usrIpxPortalEntry 11}
     usrIpxPortalNetBiosHops OBJECT-TYPE
        SYNTAX      Integer32 (0..65535)
        MAX-ACCESS      read-write
        STATUS      	current
        DESCRIPTION "NetBios maximum number of hops."
     ::= {usrIpxPortalEntry 12}
     usrIpxPortalDiagnosticState OBJECT-TYPE
        SYNTAX      INTEGER {
                        disable(0),
                        enable(1)
                       }
        MAX-ACCESS      read-write
        STATUS      	current
        DESCRIPTION "Diagnostic state."
     ::= {usrIpxPortalEntry 13}
     usrIpxPortalNetBiosNameCachingTimer OBJECT-TYPE
        SYNTAX      Integer32
        MAX-ACCESS      read-write
        STATUS      	current
        DESCRIPTION "NetBios name caching timer."
     ::= {usrIpxPortalEntry 14}
     usrIpxPortalMaxLearningRetries OBJECT-TYPE
        SYNTAX      Integer32
        MAX-ACCESS      read-write
        STATUS      	current
        DESCRIPTION "Maximum number of learning retries."
     ::= {usrIpxPortalEntry 15}
     usrIpxPortalIpxwanState OBJECT-TYPE
        SYNTAX      INTEGER {
                        disable(0),
                        enable(1)
                       }
        MAX-ACCESS      read-write
        STATUS      	current
        DESCRIPTION "Ipxwan State."
        --CONFIGURABLE
     ::= {usrIpxPortalEntry 16}
     usrIpxPortalLargeHopCount OBJECT-TYPE
        SYNTAX      Counter32
        MAX-ACCESS      read-only
        STATUS      	current
        DESCRIPTION "Displays number of IPX pkts with Large hop count."
        --CONFIGURABLE
     ::= {usrIpxPortalEntry 17}
     usrIpxPortalNetbsLargeHopCount OBJECT-TYPE
        SYNTAX      Counter32
        MAX-ACCESS      read-only
        STATUS      	current
        DESCRIPTION "Displays number of Netbios pkts with Large hop count."
        --CONFIGURABLE
     ::= {usrIpxPortalEntry 18}
     usrIpxPortalNoNetRipPkt OBJECT-TYPE
        SYNTAX      Counter32
        MAX-ACCESS      read-only
        STATUS      	current
        DESCRIPTION "Displays number of Netbios pkts with Large hop count."
        --CONFIGURABLE
     ::= {usrIpxPortalEntry 19}
     usrIpxPortalPathNotFoundToRoute OBJECT-TYPE
        SYNTAX      Counter32
        MAX-ACCESS      read-only
        STATUS      	current
        DESCRIPTION "Displays number of Netbios pkts with Large hop count."
        --CONFIGURABLE
     ::= {usrIpxPortalEntry 20}
     usrIpxPortalNumberOfAgedRoutes OBJECT-TYPE
        SYNTAX      Counter32
        MAX-ACCESS      read-only
        STATUS      	current
        DESCRIPTION "Displays number of routes that r aged in routing table"
        --CONFIGURABLE
     ::= {usrIpxPortalEntry 21}
     usrIpxPortalWrongNetRipPkt OBJECT-TYPE
        SYNTAX      Counter32
        MAX-ACCESS      read-only
        STATUS      	current
        DESCRIPTION "Displays number of routes that r aged in routing table"
        --CONFIGURABLE
     ::= {usrIpxPortalEntry 22}
     usrIpxPortalNumberOfAgedSaps OBJECT-TYPE
        SYNTAX      Counter32
        MAX-ACCESS      read-only
        STATUS      	current
        DESCRIPTION "Displays number of routes that r aged in routing table"
        --CONFIGURABLE
     ::= {usrIpxPortalEntry 23}
     usrIpxPortalNumberOfWDogReqRcvd OBJECT-TYPE
        SYNTAX      Counter32
        MAX-ACCESS      read-only
        STATUS      	current
        DESCRIPTION "Displays number of routes that r aged in routing table"
        --CONFIGURABLE
     ::= {usrIpxPortalEntry 24}
     usrIpxPortalNumberOfWDogRspSent OBJECT-TYPE
        SYNTAX      Counter32
        MAX-ACCESS      read-only
        STATUS      	current
        DESCRIPTION "Displays number of routes that r aged in routing table"
        --CONFIGURABLE
     ::= {usrIpxPortalEntry 25}
     usrIpxPortalNumberOfSerialPktsRcvd OBJECT-TYPE
        SYNTAX      Counter32
        MAX-ACCESS      read-only
        STATUS      	current
        DESCRIPTION "Displays number of routes that r aged in routing table"
        --CONFIGURABLE
     ::= {usrIpxPortalEntry 26}
     usrIpxPortalNumberOfEchoReqRcvd OBJECT-TYPE
        SYNTAX      Counter32
        MAX-ACCESS      read-only
        STATUS      	current
        DESCRIPTION "Displays number of routes that r aged in routing table"
        --CONFIGURABLE
     ::= {usrIpxPortalEntry 27}
     usrIpxPortalNumberOfEchoRspSent OBJECT-TYPE
        SYNTAX      Counter32
        MAX-ACCESS      read-only
        STATUS      	current
        DESCRIPTION "Displays number of routes that r aged in routing table"
        --CONFIGURABLE
     ::= {usrIpxPortalEntry 29}
     usrIpxPortalNumberOfPktsTooLargeRcvd OBJECT-TYPE
        SYNTAX      Counter32
        MAX-ACCESS      read-only
        STATUS      	current
        DESCRIPTION "Displays number of routes that r aged in routing table"
        --CONFIGURABLE
     ::= {usrIpxPortalEntry 30}
     usrIpxPortalRipReceiveState OBJECT-TYPE
        SYNTAX      INTEGER {
                       disable(0),
                       enable(1)
                       }
        MAX-ACCESS      read-write
        STATUS      	current
        DESCRIPTION "RIP receive packet state. When enabled IPX RIP will be enabled
                     to receive RIP packets over this portal.
                     To totally disable RIP traffic usrIpxPortalRipPeriodicState
                     must also be set to disable."
        --CONFIGURABLE
     ::= {usrIpxPortalEntry 31}
     usrIpxPortalSapReceiveState OBJECT-TYPE
        SYNTAX      INTEGER {
                        disable(0),
                        enable(1)
                       }
        MAX-ACCESS      read-write
        STATUS      	current
        DESCRIPTION "SAP receive packet state. When enabled IPX SAP will be enabled
                     to receive SAP packets over this portal.
                     To totally disable SAP traffic usrIpxPortalSapPeriodicState
                     must also be set to disable."
        --CONFIGURABLE
     ::= {usrIpxPortalEntry 32}
     usrIpxDynamicNetworkRangeStart OBJECT-TYPE
        SYNTAX   NetNumber
        MAX-ACCESS   read-write
        STATUS   	current
        DESCRIPTION
                "This is the first number in a range of network numbers IPX 
                 uses to dynamically assign to dial-in users.  The end of 
                 the range is determined by the object usrIpxMaxDynamicNetworkNumbers"
        --CONFIGURABLE
     ::= { usrIpx 11 }
     usrIpxMaxDynamicNetworkNumbers OBJECT-TYPE
        SYNTAX      Integer32
        MAX-ACCESS      read-write
        STATUS      	current
        DESCRIPTION "Maximum number of network addresses available to allocate to
                     dial-in users."
        --CONFIGURABLE
     ::= { usrIpx 12 }
     usrIpxSaveConfigFlag OBJECT-TYPE
        SYNTAX      UsrConfigStatus
        MAX-ACCESS      read-write
        STATUS      	current
        DESCRIPTION "Setting the value of this object to `save' causes the values
                 of the IPX configuration to be written out to the current IPX
                 config file, which is stored in the ipxConfigFile object. While
                 the new ConfigFile is being written, the IPX process
                 will set the value of this flag set to `saving''. Any
                 attempts to set the value while it is  not `normal'
                 (i.e. the file is currently being written to the
                 ConfigFile) will result in a badValue error being
                 returned. Setting the value to `normal' will result in no
                 action."
     ::= { usrIpx 13 }
    usrIpxConfigFileName OBJECT-TYPE
        SYNTAX      DisplayString
        MAX-ACCESS      read-only
        STATUS      	current
        DESCRIPTION        
          "The name of a ConfigFile to read/write permanent database records.
           If the value of this object is an empty string, then the
           IPX process uses the default name `@file://IpxProcess.cfg'. "
    ::= { usrIpx 14 }
     usrIpxState OBJECT-TYPE
        SYNTAX      UsrIpxStates 
        MAX-ACCESS      read-only
        STATUS      	current
        DESCRIPTION "Ipx state."
     ::= { usrIpx 15 }
     usrIpxEnable OBJECT-TYPE
        SYNTAX      INTEGER {
                        disable(0),
                        enable(1)
                       }
        MAX-ACCESS      read-write
        STATUS      	current
        DESCRIPTION "To enable or disable IPX.  When Disable is set the RIP process
                     will send out shutdown messages on all its ports in order
                     to inform neighboring routers that our routes are no longer
                     valid."
        --CONFIGURABLE
     ::= { usrIpx 16 }
-- USR Service Table
--   This table contains information for all services acquired via a
--   static sap or learned sap using a reduced set of indices which is common
--   to both Static and Non-Static SAPs. This is possible in the USR application
--   as a Static SAP entry that is added to the Static table does in the add process 
--   fill out the Non-Static field members that are contained in the same entry
--   structure. 
--   For the USR application, one entry structure is used for both Static and Non-Static 
--   and the instance index for both entries, although contained in different field 
--   members is always hard-wired to '1', and the Circuit index for Static entries is 
--   always hardwired to '0'.
--   Notes: (1.) This table was added to provide delete capability for learned saps
--          which requires write access. Write access is not available for
--          the IPX Service Table contained in the novell ipx mib.
--          In addition it also provides the mechanism to delete learned or
--          or statically entered saps.
--          (2.) The USR implementation of rows for both Static and Non-Static 
--          primary entries is a doubly linked list which has both entry types linked 
--          into one list. This one list is anchored at a common point which the mib 
--          entry for each of the two types refer to as starting point for accessing
--          that type's specific row instance. The whole list is actually scanned
--          for matching indices. This is conceptually different implementation
--          than what one might expect from a strictly SNMP mib row implementation,
--          where a binary tree structure might be expected with a node in the tree
--          representing an instance and providing branching to other nodes for
--          multiple instances. The USR application's implementation for mib rows is
--          is a non-sorted (all new Static and Non-Static SAP entries are always
--          added to the end of the list) linked list.
--          (3.) The intention for this table is only to provide a mapping overlay
--          of the Static and Non-Static row entries in order to provide a means
--          for deleting learned SAP entries as well as statically entered SAP entries.
    usrIpxServTable OBJECT-TYPE
        SYNTAX      SEQUENCE OF USRIpxServEntry
        MAX-ACCESS      not-accessible
        STATUS      	current
        DESCRIPTION "The Services table contains information about
                     all services reached via statically entered saps
                     or learned saps."
    ::= {usrIpx 17}
    usrIpxServEntry OBJECT-TYPE
        SYNTAX      USRIpxServEntry
        MAX-ACCESS      not-accessible
        STATUS      	current
        DESCRIPTION "Each entry corresponds to one service."
            INDEX       {
                        usrIpxServName,
                        usrIpxServType
                      }
    ::= {usrIpxServTable 1}
    USRIpxServEntry ::= 
             SEQUENCE {
                           usrIpxServName
                              OCTET STRING,
                           usrIpxServType
                              OCTET STRING,
                           usrIpxServExistState
                              INTEGER,
                           usrIpxServProtocol
                              INTEGER,
                           usrIpxServNetNum
                              NetNumber,
                           usrIpxServNode
                              OCTET STRING,
                           usrIpxServSocket
                              OCTET STRING,
                           usrIpxServHopCount
                              Integer32
                          }
    usrIpxServName OBJECT-TYPE
        SYNTAX      OCTET STRING (SIZE(1..48))
        MAX-ACCESS      read-write
        STATUS      	current
        DESCRIPTION "The service name."
        --CONFIGURABLE
    ::= {usrIpxServEntry 1}
    usrIpxServType OBJECT-TYPE
        SYNTAX      OCTET STRING (SIZE(2))
        MAX-ACCESS      read-write
        STATUS      	current
        DESCRIPTION "The service type."
        --CONFIGURABLE
    ::= {usrIpxServEntry 2}
    usrIpxServExistState OBJECT-TYPE
        SYNTAX      INTEGER {
                            off(1),
                            on(2)
                           }
        MAX-ACCESS      read-write
        STATUS      	current
        DESCRIPTION "The validity of this service.  Entries with the
                     value set to off may be deleted from the table at the
                     implementation's discretion."
    ::= {usrIpxServEntry 3}
    usrIpxServProtocol OBJECT-TYPE
        SYNTAX      INTEGER {
                        other(1),
                        local(2),
                        nlsp(4),
                        static(5),
                        sap(6)
                       }
        MAX-ACCESS      read-write
        STATUS      	current
        DESCRIPTION "The protocol from which knowledge of this service was
                     obtained."
    ::= {usrIpxServEntry 4}
    usrIpxServNetNum OBJECT-TYPE
        SYNTAX      NetNumber
        MAX-ACCESS      read-write
        STATUS      	current
        DESCRIPTION "The IPX network number portion of the IPX address of the
                     service."
        --CONFIGURABLE
    ::= {usrIpxServEntry 5}
    usrIpxServNode OBJECT-TYPE
        SYNTAX      OCTET STRING (SIZE(6))
        MAX-ACCESS      read-write
        STATUS      	current
        DESCRIPTION "The node portion of the IPX address of the service."
        --CONFIGURABLE
    ::= {usrIpxServEntry 6}
    usrIpxServSocket OBJECT-TYPE
        SYNTAX      OCTET STRING (SIZE(2))
        MAX-ACCESS      read-write
        STATUS      	current
        DESCRIPTION "The socket portion of the IPX address of the service."
        --CONFIGURABLE
    ::= {usrIpxServEntry 7}
    usrIpxServHopCount OBJECT-TYPE
        SYNTAX      Integer32
        MAX-ACCESS      read-write
        STATUS      	current
        DESCRIPTION "The number of router hops to the server on which the 
                     service resides."
        --CONFIGURABLE
    ::= {usrIpxServEntry 8}
    usrIpxDelServiceAll OBJECT-TYPE
        SYNTAX  INTEGER {
                        nonStatic(0)
                         }
        MAX-ACCESS  read-write
        STATUS  	current
        DESCRIPTION "This object is used to clear the whole SAP table.
                 Current support is only for clearing all non-static
                 SAP entries."
    ::= { usrIpx 18 }
-- Destination Table - this table almost duplicate a destination table
-- from standard novell_ipx.mib with an exception of a new field:
-- usrIpxDestExistState
--
--   The Destination table contains information about all known
--   destinations.  The routing information shown in this table represents
--   the path currently being used to reach the destination.
    usrIpxDestTable OBJECT-TYPE
        SYNTAX      SEQUENCE OF USRIPXDestEntry
        MAX-ACCESS      not-accessible
        STATUS      	current
        DESCRIPTION "The Destination table contains information about all
                    known destinations."
   ::= {usrIpx 19}
    usrIpxDestEntry OBJECT-TYPE
        SYNTAX      USRIPXDestEntry
        MAX-ACCESS      not-accessible
        STATUS      	current
        DESCRIPTION "Each entry corresponds to one destination."
            INDEX       {
                       usrIpxDestSysInstance,
                       usrIpxDestNetNum
                       }
   ::= {usrIpxDestTable 1}
    USRIPXDestEntry ::= SEQUENCE {
                     usrIpxDestSysInstance
                        Integer32,
                     usrIpxDestNetNum
                        NetNumber,
                     usrIpxDestProtocol
                        INTEGER,
                     usrIpxDestTicks
                        Integer32,
                     usrIpxDestHopCount
                        Integer32,
                     usrIpxDestNextHopCircIndex
                        Integer32,
                     usrIpxDestNextHopNICAddress
                        PhysAddress,
                     usrIpxDestNextHopNetNum
                        NetNumber,
                     usrIpxDestExistState
                        INTEGER
                    }
    usrIpxDestSysInstance OBJECT-TYPE
        SYNTAX      Integer32
        MAX-ACCESS      read-only
        STATUS      	current
        DESCRIPTION "The unique identifier of the instance of IPX
                to which this row corresponds."
   ::= {usrIpxDestEntry 1}
    usrIpxDestNetNum OBJECT-TYPE
        SYNTAX      NetNumber
        MAX-ACCESS      read-only
        STATUS      	current
        DESCRIPTION "The IPX network number of the destination."
   ::= {usrIpxDestEntry 2}
    usrIpxDestProtocol OBJECT-TYPE
        SYNTAX      INTEGER {
                        other(1),
                        local(2),
                        rip(3),
                        nlsp(4),
                        static(5)
                       }
        MAX-ACCESS      read-only
        STATUS      	current
        DESCRIPTION "The routing protocol from which knowledge of this
                destination was obtained."
   ::= {usrIpxDestEntry 3}
    usrIpxDestTicks OBJECT-TYPE
        SYNTAX      Integer32
        MAX-ACCESS      read-only
        STATUS      	current
        DESCRIPTION "The delay in ticks to reach this destination."
    ::= {usrIpxDestEntry 4}
    usrIpxDestHopCount OBJECT-TYPE
        SYNTAX      Integer32
        MAX-ACCESS      read-only
        STATUS      	current
        DESCRIPTION "The number of hops necessary to reach the destination."
    ::= {usrIpxDestEntry 5}
    usrIpxDestNextHopCircIndex OBJECT-TYPE
        SYNTAX      Integer32
        MAX-ACCESS      read-only
        STATUS      	current
        DESCRIPTION "The unique identifier of the circuit used to reach the 
                next hop."
    ::= {usrIpxDestEntry 6}
    usrIpxDestNextHopNICAddress OBJECT-TYPE
        SYNTAX      PhysAddress
        MAX-ACCESS      read-only
        STATUS      	current
        DESCRIPTION "The NIC address of the next hop."
    ::= {usrIpxDestEntry 7}
    usrIpxDestNextHopNetNum OBJECT-TYPE
        SYNTAX      NetNumber
        MAX-ACCESS      read-only
        STATUS      	current
        DESCRIPTION "The IPX network number of the next hop."
    ::= {usrIpxDestEntry 8}
    usrIpxDestExistState OBJECT-TYPE
        SYNTAX      INTEGER {
                      off(1),
                      on(2)
                       }
        MAX-ACCESS      read-write
        STATUS      	current
        DESCRIPTION "The validity of the route to this destination.  
                Valid row entry has this field set to on. 
                Learned routes with the value set to off will
                be removed from the routing table immediately, 
                static routes may be deleted from the table at the
                implementation's discretion."
    ::= {usrIpxDestEntry 9}
    usrIpxDelRouteAll OBJECT-TYPE
        SYNTAX  INTEGER {
           disable(0),
           enable(1)
        }
        MAX-ACCESS  read-write
        STATUS  	current
        DESCRIPTION "This object is used to clear the whole routing table"
    ::= { usrIpx 20 }
    usrPPPIpxAddress OBJECT-TYPE
        SYNTAX   OCTET STRING (SIZE(4))
        MAX-ACCESS   read-write
        STATUS   	current 
        DESCRIPTION
                "The IPX ADDRESS assigned to all PPP user's if they are configured as such."
        --CONFIGURABLE
        ::= { usrIpx 21 }
END         -- End IPX host MIB definitions
