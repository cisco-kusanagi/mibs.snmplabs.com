--
--  Title:  Appian Serial Interface MIB
--
--  Dated:  01/4/00
--  Author: D. Theriault
--
--  Description:
--
--  This MIB file contains the definitions and support for the Appian
--  Optical Services Access Platform(s).
-- 
--  The Appian Serial Interface MIB supports all RS232 like serial interfaces
--  on the OSAP platform.
--
--
APPIAN-PPORT-SERIAL-MIB DEFINITIONS ::= BEGIN

    IMPORTS

        acPport, AcAdminStatus, AcOpStatus, AcNodeId    FROM APPIAN-SMI-MIB

        acChassisCurrentTime, acChassisRingId           FROM APPIAN-CHASSIS-MIB

        MODULE-IDENTITY, OBJECT-TYPE, IpAddress, 
        NOTIFICATION-TYPE                               FROM SNMPv2-SMI

        DisplayString                                   FROM SNMPv2-TC;


--
-- Appian Serial MIB
--

acSerial  MODULE-IDENTITY

        LAST-UPDATED    "0002231600Z"
        ORGANIZATION    "Appian Communications, Inc."
        CONTACT-INFO    "Douglas Theriault"
        
        DESCRIPTION     "Appian Serial Interface MIB for RS232 like interfaces."
        REVISION        "0002231600Z"

        DESCRIPTION     "Engineering draft version, not for release."

        ::= { acPport 2 }

--
-- Serial Port Interface Table
--

acSerialTable   OBJECT-TYPE
    SYNTAX  SEQUENCE OF AcSerialEntry
    MAX-ACCESS  not-accessible
    STATUS      current
    DESCRIPTION
    "Each Switch Control Processor supports a debug port as well as a management
    access or craft CLI port.  The system will initialize the acSerialTable when
    the system boots or an SCP has been reset."

    ::= { acSerial 1 }

acSerialEntry   OBJECT-TYPE
    SYNTAX  AcSerialEntry
    MAX-ACCESS  not-accessible
    STATUS      current
    DESCRIPTION
    "A row in the serial table contains configurable parameters and statistics
    for each serial interface on this platform."

    INDEX { acSerialNodeId, acSerialSlot, acSerialPort }

    ::= { acSerialTable 1 }

    AcSerialEntry ::=
        SEQUENCE {
            acSerialNodeId                  AcNodeId,
            acSerialSlot                    INTEGER,
            acSerialPort                    INTEGER,
            acSerialAdminStatus             AcAdminStatus,
            acSerialOpStatus                AcOpStatus,
            acSerialOpCode                  INTEGER,
            acSerialOpMode                  INTEGER,
            acSerialBaudRate                INTEGER,
            acSerialParity                  INTEGER,
            acSerialNumberBits              INTEGER,
            acSerialIpAddress               IpAddress,
            acSerialIpSubnet                IpAddress,
            acSerialRxOctets                INTEGER,
            acSerialTxOctets                INTEGER,
            acSerialInterfaceName           DisplayString
        }
--
-- Serial Port Interface Entry
--

acSerialNodeId    OBJECT-TYPE
    SYNTAX  AcNodeId
    MAX-ACCESS  accessible-for-notify
    STATUS  current
    DESCRIPTION
    "The node id is the id for this specific node in the OSAP ring."

    ::= { acSerialEntry 1 }

acSerialSlot    OBJECT-TYPE
    SYNTAX  INTEGER (1..4)
    MAX-ACCESS  accessible-for-notify
    STATUS      current
    DESCRIPTION
    "The control processor slot upon which the serial port is located."

    ::= { acSerialEntry 2 }

acSerialPort    OBJECT-TYPE
    SYNTAX  INTEGER (1..2)
    MAX-ACCESS      accessible-for-notify
    STATUS  current
    DESCRIPTION
    "The physical port number on acSerialEntrySlot where this connector is located."

    ::= { acSerialEntry 3 }


acSerialAdminStatus  OBJECT-TYPE
    SYNTAX  AcAdminStatus
    MAX-ACCESS  read-write
    STATUS      current
    DESCRIPTION
    "Appian Administrative Status attribute used to set the provisioning
    state as either activate(1), inactivate(2) or delete(3).  Refer to
    the Appian-SMI.mib file for additional information."

    DEFVAL { inactivate }
    
    ::= { acSerialEntry 4 }

acSerialOpStatus  OBJECT-TYPE
    SYNTAX  AcOpStatus
    MAX-ACCESS  read-only
    STATUS  current
    DESCRIPTION
    "The current operational status of the serial port driver and services 
    supporting this interface."
    
    ::= { acSerialEntry 5 }

acSerialOpCode  OBJECT-TYPE
    SYNTAX  INTEGER
    MAX-ACCESS  read-only
    STATUS  current
    DESCRIPTION
    "Provides a detailed status code which can be used to isolate a problem
    or state condition reported in acSerialEntryOpStatus."
    
    ::= { acSerialEntry 6 }    

acSerialOpMode  OBJECT-TYPE
    SYNTAX  INTEGER {
                unknown(0),
                terminal(1),
                ppp(2)
            }
    MAX-ACCESS  read-write
    STATUS      current
    DESCRIPTION
    "Determines the mode of operation for the serial port.  If the
    serial port is using a raw terminal(1) or if we are to run PPP
    over this port as an alternative EMS access mechanism."

    DEFVAL { terminal }
    
    ::= { acSerialEntry 7 }

acSerialBaudRate    OBJECT-TYPE
    SYNTAX  INTEGER {
                unknown(0),
                auto(1),
                baud9600(2),
                baud19200(3),
                baud56000(4),
                baud64000(5),
                baud115000(6)
            }
    MAX-ACCESS  read-write
    STATUS      current
    DESCRIPTION
    "User configured baud rate for use on the serial port.  When
    set to Auto(1), the driver will negotiate baud rate."

    DEFVAL { auto }
    
    ::= { acSerialEntry 8 }

acSerialParity  OBJECT-TYPE
    SYNTAX  INTEGER {
                unknown(0),
                none(1),
                odd(2),
                even(3)
             }
    MAX-ACCESS  read-write
    STATUS      current
    DESCRIPTION
    "User configurable partity which is used on the serial port."

    DEFVAL { none }
    
    ::= { acSerialEntry 9 }

acSerialNumberBits  OBJECT-TYPE
    SYNTAX  INTEGER {
                unknown(0),
                bits-7(1),
                bits-8(2)
            }
    MAX-ACCESS  read-write
    STATUS      current
    DESCRIPTION
    "Number of bits-per-byte used over the serial port."

    DEFVAL { bits-8 }
    
    ::= { acSerialEntry 10 }

acSerialIpAddress   OBJECT-TYPE
    SYNTAX  IpAddress
    MAX-ACCESS  read-write
    STATUS      current
    DESCRIPTION
    "The IP Addressed used on the serial port during PPP sessions.
    If chSerialMode is equal to PPP-DHCP, this field is not needed
    otherwise a static IP Address is required in this field."

    DEFVAL { 0 }
    
    ::= { acSerialEntry 11 }

acSerialIpSubnet    OBJECT-TYPE
    SYNTAX  IpAddress
    MAX-ACCESS  read-write
    STATUS      current
    DESCRIPTION
    "The IP Subnet Mask in dotted notation for use on the serial 
    port during PPP sessions."

    DEFVAL { 0 }
    
    ::= { acSerialEntry 12 }

acSerialRxOctets    OBJECT-TYPE
    SYNTAX  INTEGER
    MAX-ACCESS  read-only
    STATUS      current
    DESCRIPTION
    "The number of bytes read by the serial port driver."

    ::= { acSerialEntry 13 }

acSerialTxOctets    OBJECT-TYPE
    SYNTAX  INTEGER
    MAX-ACCESS  read-only
    STATUS      current
    DESCRIPTION
    "The number of bytes transmitted by the serial port driver."

    ::= { acSerialEntry 14 }

acSerialInterfaceName   OBJECT-TYPE
    SYNTAX  DisplayString (SIZE(0..64))
    MAX-ACCESS  read-write
    STATUS      current
    DESCRIPTION
    "A user configurable ASCII name of up to 64 bytes in length, which is 
    assigned for this interface."

    DEFVAL { "Serial Interface" }

    ::= { acSerialEntry 15 }

--
-- Serial Port Trap definitions
--
acSerialTraps   OBJECT IDENTIFIER ::= { acSerial 0 }

acSerialLinkDownTrap  NOTIFICATION-TYPE
    OBJECTS { acChassisCurrentTime, acChassisRingId, acSerialNodeId, 
              acSerialSlot, acSerialPort }
    STATUS  current
    DESCRIPTION
    "The Serial Port driver for this interface has detected the port to be
    in the down state."
    
    ::= { acSerialTraps 1 }
    

acSerialLinkUpTrap  NOTIFICATION-TYPE
    OBJECTS { acChassisCurrentTime, acChassisRingId, acSerialNodeId, 
              acSerialSlot, acSerialPort }
    STATUS  current
    DESCRIPTION
    "The Serial Port driver for this interface has detected the port to be
    in the down state."
    
    ::= { acSerialTraps 2 }
    
acSerialStatsResetTrap  NOTIFICATION-TYPE
    OBJECTS { acChassisCurrentTime, acChassisRingId, acSerialNodeId, 
              acSerialSlot, acSerialPort }
    STATUS  current
    DESCRIPTION
    "The statistics for this serial port have been reset to zero(0) and may
    cause problems for long term trending functions."
    
    ::= { acSerialTraps 3 }
    
acSerialCfgErrorTrap  NOTIFICATION-TYPE
    OBJECTS { acChassisCurrentTime, acChassisRingId, acSerialNodeId, 
              acSerialSlot, acSerialPort, acSerialOpCode }
    STATUS  current
    DESCRIPTION
    "A configuration request for this serial interface has been detected as
    incorrect or corrupted."
    
    ::= { acSerialTraps 4 }
    

END
