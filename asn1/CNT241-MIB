--
--
--          Computer Network Technology, Corp.
--              6000 Nathan Lane North 
--              Plymouth, Minnesota  55442   
--
--                phone:  (763) 268-6000
--                  fax:  (763) 268-6800
--              support:  1-800-NET-TECH
--                email:  cnt.com
--
--      MIB Version:     1.8
--      Product Family:  CNT Zeus(2) Subagent(4) Service Monitor(1)
--
-- +------------+ if you change this mib, you increment the version number.
-- | Attention! | Also, this MIB is supported by service monitory subagent,
-- +------------+ and that agent must also be compiled with this mib version.
--
-- Version 1.5: Change syntax to make compilable with Adventnet. 11/14/2000 qvh
-- Version 1.6: Change read-write(1) to read_read(1) because some compiler do 
--              not understand it.
-- Version 1.7: Change SmMessageIndex to be after SmMessageText because it created in-compatibility problem in CMF vs Advanenet.
-- Version 1.8: Change read_write read_only to read-write-access and read-only-access because Mosy compiler doesn't
--              support Underscore. 10/2001

CNT241-MIB DEFINITIONS ::= BEGIN

	IMPORTS
	TRAP-TYPE FROM RFC-1215
		enterprises, Counter
			FROM RFC1065-SMI
		OBJECT-TYPE
			FROM RFC-1212
			DisplayString FROM RFC1213-MIB
		cnt2Subagent
			FROM CNT2-MIB;

---     cnt             OBJECT IDENTIFIER ::= { enterprises 333 }
---     cnt2            OBJECT IDENTIFIER ::= { cnt 2 }
---     cnt2Subagent    OBJECT IDENTIFIER ::= { cnt2 4 }


	-- the CNT Service Monitor
	cnt2Sm		OBJECT IDENTIFIER ::= { cnt2Subagent 1 }

	-- the CNT Service Monitor groups
	cnt2SmHw	OBJECT IDENTIFIER ::= { cnt2Sm 1 } -- Hardware
	cnt2SmSw	OBJECT IDENTIFIER ::= { cnt2Sm 2 } -- Software
        -- cnt2SmMsg has been deprecated and replaced by cnt2SmMessage
	cnt2SmMsg	OBJECT IDENTIFIER ::= { cnt2Sm 3 } -- Messages
	cnt2SmMessage	OBJECT IDENTIFIER ::= { cnt2Sm 4 } -- Messages


	-- Service Monitor Hardware
	-- cnt2SmHw	OBJECT IDENTIFIER ::= { cnt2Subagent 1 }

	-- Service Monitor Hardware Probe

	cnt2SmHwTemperatureF OBJECT-TYPE
		SYNTAX  INTEGER
		ACCESS  read-only
		STATUS  mandatory
		DESCRIPTION
			"The temperature in Farenheit of the node in 
			the range (0..255).
			If/when the temperature transitions from below
			113 degrees to above 113 degrees, a advisory trap
			will be sent.
			If/when the temperature transitions from below
			131 degrees to above 131 degrees, a repair trap
			will be sent."
		::= { cnt2SmHw 1 }

	cnt2SmHwTapeDriveState OBJECT-TYPE
		SYNTAX  INTEGER {
				not-present(1),
				ok(2),
				failed(3)
			}
		ACCESS  read-only
		STATUS  mandatory
		DESCRIPTION
			"The state of the DAT tape drive."
		::= { cnt2SmHw 2 }

	cnt2SmHwCdRomDriveState OBJECT-TYPE
		SYNTAX  INTEGER {
				not-present(1),
				ok(2),
				failed(3)
			}
		ACCESS  read-only
		STATUS  mandatory
		DESCRIPTION
			"The state of the CD drive."
		::= { cnt2SmHw 3 }

	cnt2SmHwTapeMounted OBJECT-TYPE
		SYNTAX  INTEGER {
				not-applicable(1),
				empty(2),
				mounted(3)
			}
		ACCESS  read-only
		STATUS  mandatory
		DESCRIPTION
			"Indicates whether the DAT tape drive contains a
			tape."
		::= { cnt2SmHw 4 }

	cnt2SmHwCdRomMounted OBJECT-TYPE
		SYNTAX  INTEGER {
				not-applicable(1),
				empty(2),
				mounted(3)
			}
		ACCESS  read-only
		STATUS  mandatory
		DESCRIPTION
			"Indicates whether the CD drive contains a CD."
		::= { cnt2SmHw 5 }

	cnt2SmHwServiceLed OBJECT-TYPE
		SYNTAX  INTEGER {
				off(1),
				on(2)
			}
		ACCESS  read-only
		STATUS  mandatory
		DESCRIPTION
			"The state of the service LED."
		::= { cnt2SmHw 6 }

	cnt2SmHwIplSwitch OBJECT-TYPE
		SYNTAX  INTEGER {
				off(1),
				on(2)
			}
		ACCESS  read-only
		STATUS  mandatory
		DESCRIPTION
			"The state of the IPL switch."
		::= { cnt2SmHw 7 }


	cnt2SmHwAdapterTable OBJECT-TYPE
		SYNTAX  SEQUENCE OF Cnt2SmHwAdapterEntry
		ACCESS  not-accessible
		STATUS  mandatory
		DESCRIPTION
			"List of adapters in the node." 
		::= { cnt2SmHw 8 }

	cnt2SmHwAdapterEntry OBJECT-TYPE
		SYNTAX  Cnt2SmHwAdapterEntry
		ACCESS  not-accessible
		STATUS  mandatory
		DESCRIPTION
			"A adapter entry."
		INDEX   { cnt2SmHwAdapterIndex }
		::= { cnt2SmHwAdapterTable 1 }

	Cnt2SmHwAdapterEntry ::= SEQUENCE {
		cnt2SmHwAdapterIndex
			INTEGER,
		cnt2SmHwAdapterOperState
			INTEGER,
		cnt2SmHwAdapterAdminState
			INTEGER
	}

	cnt2SmHwAdapterIndex OBJECT-TYPE
		SYNTAX  INTEGER
		ACCESS  read-only
		STATUS  mandatory
		DESCRIPTION
			"The relative index of this adapter entry 
			within the node."
		::= { cnt2SmHwAdapterEntry 1 }

	cnt2SmHwAdapterOperState OBJECT-TYPE
		SYNTAX  INTEGER {
				ok(1),
				not-ok(2)
			}
		ACCESS  read-only
		STATUS  mandatory
		DESCRIPTION
			"The state of the adapter in this slot."
		::= { cnt2SmHwAdapterEntry 2 }

	cnt2SmHwAdapterAdminState OBJECT-TYPE
		SYNTAX  INTEGER {
				enabled(1),
				disabled(2),
				reset(3)
			}
		ACCESS  read-write
		STATUS  mandatory
		DESCRIPTION
			"The state of the adapter in this slot."
		::= { cnt2SmHwAdapterEntry 3 }


	cnt2SmHwCardTable OBJECT-TYPE
		SYNTAX  SEQUENCE OF Cnt2SmHwCardEntry
		ACCESS  not-accessible
		STATUS  mandatory
		DESCRIPTION
			"List of adapters in the node." 
		::= { cnt2SmHw 9 }

	cnt2SmHwCardEntry OBJECT-TYPE
		SYNTAX  Cnt2SmHwCardEntry
		ACCESS  not-accessible
		STATUS  mandatory
		DESCRIPTION
			"A adapter entry."
		INDEX   { cnt2SmCardAdapterIndex, cnt2SmHwCardIndex }
		::= { cnt2SmHwCardTable 1 }

	Cnt2SmHwCardEntry ::= SEQUENCE {
		cnt2SmCardAdapterIndex
			INTEGER,
		cnt2SmHwCardIndex
			INTEGER,
		cnt2SmHwCardOperState
			INTEGER,
		cnt2SmHwCardAdminState
			INTEGER
	}

	cnt2SmCardAdapterIndex OBJECT-TYPE
		SYNTAX  INTEGER
		ACCESS  read-only
		STATUS  mandatory
		DESCRIPTION
			"The relative index of this adapter entry 
			within the node."
		::= { cnt2SmHwCardEntry 1 }

	cnt2SmHwCardIndex OBJECT-TYPE
		SYNTAX  INTEGER
		ACCESS  read-only
		STATUS  mandatory
		DESCRIPTION
			"The relative index of this adapter entry 
			within the node."
		::= { cnt2SmHwCardEntry 2 }

	cnt2SmHwCardOperState OBJECT-TYPE
		SYNTAX  INTEGER {
				ok(1),
				not-ok(2)
			}
		ACCESS  read-only
		STATUS  mandatory
		DESCRIPTION
			"The state of the adapter in this slot."
		::= { cnt2SmHwCardEntry 3 }

	cnt2SmHwCardAdminState OBJECT-TYPE
		SYNTAX  INTEGER {
				enabled(1),
				disabled(2),
				reset(3)
			}
		ACCESS  read-only
		STATUS  mandatory
		DESCRIPTION
			"The state of the adapter in this slot."
		::= { cnt2SmHwCardEntry 4 }


	cnt2SmHwPowerSupplyTable OBJECT-TYPE
		SYNTAX  SEQUENCE OF Cnt2SmHwPowerSupplyEntry
		ACCESS  not-accessible
		STATUS  mandatory
		DESCRIPTION
			"List of power supplies in the node." 
		::= { cnt2SmHw 10 }

	cnt2SmHwPowerSupplyEntry OBJECT-TYPE
		SYNTAX  Cnt2SmHwPowerSupplyEntry
		ACCESS  not-accessible
		STATUS  mandatory
		DESCRIPTION
			"A power supply entry."
		INDEX   { cnt2SmHwPowerSupplyIndex }
		::= { cnt2SmHwPowerSupplyTable 1 }

	Cnt2SmHwPowerSupplyEntry ::= SEQUENCE {
		cnt2SmHwPowerSupplyIndex
			INTEGER,
		cnt2SmHwPowerSupplyACState
			INTEGER,
		cnt2SmHwPowerSupplyDCState
			INTEGER
	}

	cnt2SmHwPowerSupplyIndex OBJECT-TYPE
		SYNTAX  INTEGER
		ACCESS  read-only
		STATUS  mandatory
		DESCRIPTION
			"The relative index of this power supply entry 
			within the node."
		::= { cnt2SmHwPowerSupplyEntry 1 }

	cnt2SmHwPowerSupplyACState OBJECT-TYPE
		SYNTAX  INTEGER {
				ok(1),
				not-ok(2),
				absent(3)
			}
		ACCESS  read-only
		STATUS  mandatory
		DESCRIPTION
			"The AC state of this power supply."
		::= { cnt2SmHwPowerSupplyEntry 2 }

	cnt2SmHwPowerSupplyDCState OBJECT-TYPE
		SYNTAX  INTEGER {
				ok(1),
				not-ok(2),
				absent(3)
			}
		ACCESS  read-only
		STATUS  mandatory
		DESCRIPTION
			"The DC state of this power supply."
		::= { cnt2SmHwPowerSupplyEntry 3 }


	cnt2SmHwFanTable OBJECT-TYPE
		SYNTAX  SEQUENCE OF Cnt2SmHwFanEntry
		ACCESS  not-accessible
		STATUS  mandatory
		DESCRIPTION
			"List of power supplies in the node." 
		::= { cnt2SmHw 11 }

	cnt2SmHwFanEntry OBJECT-TYPE
		SYNTAX  Cnt2SmHwFanEntry
		ACCESS  not-accessible
		STATUS  mandatory
		DESCRIPTION
			"A fan entry."
		INDEX   { cnt2SmHwFanIndex }
		::= { cnt2SmHwFanTable 1 }

	Cnt2SmHwFanEntry ::= SEQUENCE {
		cnt2SmHwFanIndex
			INTEGER,
		cnt2SmHwFanState
			INTEGER
	}

	cnt2SmHwFanIndex OBJECT-TYPE
		SYNTAX  INTEGER
		ACCESS  read-only
		STATUS  mandatory
		DESCRIPTION
			"The relative index of this fan entry 
			within the node."
		::= { cnt2SmHwFanEntry 1 }

	cnt2SmHwFanState OBJECT-TYPE
		SYNTAX  INTEGER {
				ok(1),
				not-ok(2)
			}
		ACCESS  read-only
		STATUS  mandatory
		DESCRIPTION
			"The state of this fan."
		::= { cnt2SmHwFanEntry 2 }


	-- Service Monitor Software
	-- cnt2SmSw	OBJECT IDENTIFIER ::= { cnt2Subagent 2 }

	cnt2SmNumModules OBJECT-TYPE
		SYNTAX  INTEGER
		ACCESS  read-only
		STATUS  mandatory
		DESCRIPTION
			"The number of software modules making up the set
			referred to as the Service Monitor."
		::= { cnt2SmSw 1 }
		
	cnt2SmSwTable OBJECT-TYPE
		SYNTAX  SEQUENCE OF Cnt2SmSwEntry
		ACCESS  not-accessible
		STATUS  mandatory
		DESCRIPTION
			"List of entries in the service monitor software 
			module table."
		::= { cnt2SmSw 2 }

	cnt2SmSwEntry OBJECT-TYPE
		SYNTAX  Cnt2SmSwEntry
		ACCESS  not-accessible
		STATUS  mandatory
		DESCRIPTION
			"A service monitor software module entry."
		INDEX   { cnt2SmSwIndex }
		::= { cnt2SmSwTable 1 }

	Cnt2SmSwEntry ::= SEQUENCE {
		cnt2SmSwIndex
			INTEGER,
		cnt2SmSwName
			DisplayString,
		cnt2SmSwFunction
			INTEGER,
		cnt2SmSwMajorVersion
			INTEGER,
		cnt2SmSwMinorVersion
			INTEGER
	}

	cnt2SmSwIndex OBJECT-TYPE
		SYNTAX  INTEGER
		ACCESS  read-only
		STATUS  mandatory
		DESCRIPTION
			"The relative index of this software module entry 
			within the service monitor."
		::= { cnt2SmSwEntry 1 }

	cnt2SmSwName OBJECT-TYPE
		SYNTAX  DisplayString
		ACCESS  read-only
		STATUS  mandatory
		DESCRIPTION
			"The name of the service monitor module."
		::= { cnt2SmSwEntry 2 }

	cnt2SmSwFunction OBJECT-TYPE
		SYNTAX  INTEGER {
				loading(1),
				dumping(2),
				configuration(3),
				messages(4),
				hw-monitoring(5),
				tracing(6),
				snmp-master-agent(7),
				console(8),
				utilities(9)
			}
		ACCESS  read-only
		STATUS  mandatory
		DESCRIPTION
			"The primary function performed by this
			software module."
		::= { cnt2SmSwEntry 3 }

	cnt2SmSwMajorVersion OBJECT-TYPE
		SYNTAX  INTEGER
		ACCESS  read-only
		STATUS  mandatory
		DESCRIPTION
			"The major version number of this software
			module."
		::= { cnt2SmSwEntry 4 }

	cnt2SmSwMinorVersion OBJECT-TYPE
		SYNTAX  INTEGER
		ACCESS  read-only
		STATUS  mandatory
		DESCRIPTION
			"The minor version number of this software
			module."
		::= { cnt2SmSwEntry 5 }

	cnt2SmSwSlot OBJECT-TYPE
		SYNTAX  INTEGER
		ACCESS  read-only
		STATUS  mandatory
		DESCRIPTION
			"The slot number of the active Service Monitor."
		::= { cnt2SmSw 3 }

	cnt2SmSwAccess OBJECT-TYPE
		SYNTAX  INTEGER {
				read-write-access(1),
				read-only-access(2)
			}
		ACCESS  read-only
		STATUS  mandatory
		DESCRIPTION
			"The access permissions of the active Service Monitor."
		::= { cnt2SmSw 4 }
		

        -- **************************************************************
        -- * The following messages table is deprecated.  It has been   *
        -- * replaced by cnt2SmMessage.                                 * 
        -- **************************************************************
	-- Service Monitor Messages
	-- cnt2SmMsg	OBJECT IDENTIFIER ::= { cnt2Sm 3 }

	cnt2SmNumMsgs OBJECT-TYPE
		SYNTAX  INTEGER
		ACCESS  read-only
		STATUS  deprecated
		DESCRIPTION
			"The number of messages in the system message
			file that have been entered by all modules within
			the node."
			::= { cnt2SmMsg 1 }
		
	cnt2SmMsgTable OBJECT-TYPE
		SYNTAX  SEQUENCE OF Cnt2SmMsgEntry
		ACCESS  not-accessible
		STATUS  deprecated
		DESCRIPTION
			"List of entries in the service monitor message 
			file.  This file contains any messages that has
			been entered by any software residing in the node."
		::= { cnt2SmMsg 2 }

	cnt2SmMsgEntry OBJECT-TYPE
		SYNTAX  Cnt2SmMsgEntry
		ACCESS  not-accessible
		STATUS  deprecated
		DESCRIPTION
			"A message file entry."
		INDEX   { cnt2SmMsgIndex }
		::= { cnt2SmMsgTable 1 }

	Cnt2SmMsgEntry ::= SEQUENCE {
		cnt2SmMsgIndex
			INTEGER,
		cnt2SmMsgSeverity
			INTEGER,
		cnt2SmMsgProcessName
			DisplayString,
		cnt2SmMsgNumber
			INTEGER,
		cnt2SmMsgSlotNumber
			INTEGER,
		cnt2SmMsgDateTime
			DisplayString,
		cnt2SmMsgErrorNumber
			INTEGER,
		cnt2SmMsgContent
			DisplayString
	}

	cnt2SmMsgIndex OBJECT-TYPE
		SYNTAX  INTEGER
		ACCESS  read-only
		STATUS  deprecated
		DESCRIPTION
			"The relative index of this message entry 
			within the message file."
		::= { cnt2SmMsgEntry 1 }

	cnt2SmMsgSeverity OBJECT-TYPE
		SYNTAX  INTEGER {
				emergency(1),
				alert(2),
				criticial(3),
				error(4),
				warning(5),
				notice(6),
				information(7),
				debug(8)
			}
		ACCESS  read-only
		STATUS  deprecated
		DESCRIPTION
			"The severity of this message."
		::= { cnt2SmMsgEntry 2 }

	cnt2SmMsgProcessName OBJECT-TYPE
		SYNTAX  DisplayString
		ACCESS  read-only
		STATUS  deprecated
		DESCRIPTION
			"The name of the process that sent this
			message to the message server."
		::= { cnt2SmMsgEntry 3 }

	cnt2SmMsgNumber OBJECT-TYPE
		SYNTAX  INTEGER
		ACCESS  read-only
		STATUS  deprecated
		DESCRIPTION
			"The number of this message.  Each module
			numbers its message type as another way of
			describing it.  This message can then be 
			cross-referenced in the CNT system messages
			reference manual."
		::= { cnt2SmMsgEntry 4 }


	cnt2SmMsgSlotNumber OBJECT-TYPE
		SYNTAX  DisplayString
		ACCESS  read-only
		STATUS  deprecated
		DESCRIPTION
			"The slot number of the module that sent this
			message to the message server."
		::= { cnt2SmMsgEntry 5 }

	cnt2SmMsgDateTime OBJECT-TYPE
		SYNTAX  DisplayString
		ACCESS  read-only
		STATUS  deprecated
		DESCRIPTION
			"The date and time that this message was sent
			to the message server."
		::= { cnt2SmMsgEntry 6 }

	cnt2SmMsgErrorNumber OBJECT-TYPE
		SYNTAX  INTEGER
		ACCESS  read-only
		STATUS  deprecated
		DESCRIPTION
			"The number of the Error message which caused us
			to generate this error message.  Each module
			numbers its message errors as another way of
			describing it."  
		::= { cnt2SmMsgEntry 7 }
		
	cnt2SmMsgContent OBJECT-TYPE
		SYNTAX  DisplayString
		ACCESS  read-only
		STATUS  deprecated
		DESCRIPTION
			"The textual detail of the message sent to
			the message server."
		::= { cnt2SmMsgEntry 8 }


        -- **************************************************************
        -- * The following messages table replaces the cnt2SmMsg table  *
        -- * which has been deprecated.                                 * 
        -- **************************************************************

	-- Service Monitor Messages
	-- cnt2SmMessage OBJECT IDENTIFIER ::= { cnt2Sm 4 }

	cnt2SmMsgTableSize OBJECT-TYPE
		SYNTAX  INTEGER
		ACCESS  read-write
		STATUS  mandatory
		DESCRIPTION
			"The number of messages that are available through
			SNMP access.  This message table is limited to the
                        most recent number messages specified by this object."
			::= { cnt2SmMessage 1 }

	cnt2SmMessageTable OBJECT-TYPE
		SYNTAX  SEQUENCE OF Cnt2SmMessageEntry
		ACCESS  not-accessible
		STATUS  mandatory
		DESCRIPTION
			"List of entries in the service monitor message 
			file.  This file contains any messages that has
			been entered by any software residing in the node."
		::= { cnt2SmMessage 2 }

	cnt2SmMessageEntry OBJECT-TYPE
		SYNTAX  Cnt2SmMessageEntry
		ACCESS  not-accessible
		STATUS  mandatory
		DESCRIPTION
			"A message file entry."
		INDEX	{cnt2SmMessageText }
		::= { cnt2SmMessageTable 1 }

-- The SmMessageText and SmMessageIndex was in this order because we want
-- to provide downward compatible between differrent version of MIBS out there.

	Cnt2SmMessageEntry ::= SEQUENCE {
		cnt2SmMessageText
			DisplayString,
		cnt2SmMessageIndex
			INTEGER
	}
        cnt2SmMessageText OBJECT-TYPE
                SYNTAX  DisplayString
                ACCESS  read-only
                STATUS  mandatory
                DESCRIPTION
                        "The textual detail of the message sent to
			the message server."
		::= { cnt2SmMessageEntry 1 }

		cnt2SmMessageIndex OBJECT-TYPE
				SYNTAX	INTEGER
                ACCESS  read-only
                STATUS  mandatory
                DESCRIPTION
                        "The textual index of the message sent to
			the message server."
		::= { cnt2SmMessageEntry 2 }


	cnt2SmMsgToTrapFilter OBJECT-TYPE
		SYNTAX  INTEGER {
				emergency(1),
				alert(2),
				criticial(3),
				error(4),
				warning(5),
				notice(6),
				information(7),
                                none(8)
			}
		ACCESS  read-write
		STATUS  mandatory
		DESCRIPTION
			"Messages in cnt2SmMessageTable can be sent as 
                        traps to selected destinations.  However, the 
                        messages are filtered by severity before they 
                        are forwarded as traps.  This object determines 
                        which of the messages are filtered.  All messages 
                        with severity equal and lower in value than the 
                        value of this object are forwarded as traps.  
                        Severity levels range from 0 (lowest) to 7 
                        (highest).  A value of 0 would cause all 
                        messages to be forwarded as traps."
			::= { cnt2SmMessage 3 }

        -- **************************************************************
        -- * The following traps 1-8 have been replaced by traps 9-15   *
        -- **************************************************************

        cnt2smEmergencyMsg TRAP-TYPE
                ENTERPRISE cnt2Sm
                VARIABLES { cnt2SmMsgProcessName,
                            cnt2SmMsgNumber,
                            cnt2SmMsgSlotNumber,
                            cnt2SmMsgDateTime,
                            cnt2SmMsgErrorNumber,
                            cnt2SmMsgContent }
                DESCRIPTION
                        "An emergency level trap (0) signifies that an
                        event has occured which has rendered the system
                        unusable. All modules and interfaces will be
                        affected."
                ::= 1
 
        cnt2smAlertMsg TRAP-TYPE
                ENTERPRISE cnt2Sm
                VARIABLES { cnt2SmMsgProcessName,
                            cnt2SmMsgNumber,
                            cnt2SmMsgSlotNumber,
                            cnt2SmMsgDateTime,
                            cnt2SmMsgErrorNumber,
                            cnt2SmMsgContent }
                DESCRIPTION
                        "An Alert level trap (1) signifies that an
                        event has occured which requires that immediate
                        action be taken. The module will be affected."
                ::= 2
 
        cnt2smCriticalMsg TRAP-TYPE
                ENTERPRISE cnt2Sm
                VARIABLES { cnt2SmMsgProcessName,
                            cnt2SmMsgNumber,
                            cnt2SmMsgSlotNumber,
                            cnt2SmMsgDateTime,
                            cnt2SmMsgErrorNumber,
                            cnt2SmMsgContent }
                DESCRIPTION
                        "A Critical level trap (1) signifies that an
                        event has occured for which action should be
                        taken.  The module will be affected."
 
                ::= 3
 
        cnt2smErrorMsg TRAP-TYPE
                ENTERPRISE cnt2Sm
                VARIABLES { cnt2SmMsgProcessName,
                            cnt2SmMsgNumber,
                            cnt2SmMsgSlotNumber,
                            cnt2SmMsgDateTime,
                            cnt2SmMsgErrorNumber,
                            cnt2SmMsgContent }
                DESCRIPTION
                        "An Error level trap (3) signifies that an
                        event has occured that has resulted in errors.
                        The module will probably be affected."
                ::= 4
 
        cnt2smWarningMsg TRAP-TYPE
                ENTERPRISE cnt2Sm
                VARIABLES { cnt2SmMsgProcessName,
                            cnt2SmMsgNumber,
                            cnt2SmMsgSlotNumber,
                            cnt2SmMsgDateTime,
                            cnt2SmMsgErrorNumber,
                            cnt2SmMsgContent }
                DESCRIPTION
                        "A Warning level trap (4) signifies that an
                        event has occured that may affect the module."
                ::= 5
 
        cnt2smNoticeMsg TRAP-TYPE
                ENTERPRISE cnt2Sm
                VARIABLES { cnt2SmMsgProcessName,
                            cnt2SmMsgNumber,
                            cnt2SmMsgSlotNumber,
                            cnt2SmMsgDateTime,
                            cnt2SmMsgErrorNumber,
                            cnt2SmMsgContent }
                DESCRIPTION
                        "A Notice level trap (1) signifies that an
                        event has occured that is normal but that has
                        significance. The module should be unaffected"
                ::= 6
 
        cnt2smInfoMsg TRAP-TYPE
                ENTERPRISE cnt2Sm
                VARIABLES { cnt2SmMsgProcessName,
                            cnt2SmMsgNumber,
                            cnt2SmMsgSlotNumber,
                            cnt2SmMsgDateTime,
                            cnt2SmMsgErrorNumber,
                            cnt2SmMsgContent }
                DESCRIPTION
                        "An Informaiton level trap (6) signifies that an
                        event has occured that informational in severity
                        and that the module will not be affected by this
                        error."
                ::= 7
 
        cnt2smDebugMsg TRAP-TYPE
                ENTERPRISE cnt2Sm
                VARIABLES { cnt2SmMsgProcessName,
                            cnt2SmMsgNumber,
                            cnt2SmMsgSlotNumber,
                            cnt2SmMsgDateTime,
                            cnt2SmMsgErrorNumber,
                            cnt2SmMsgContent }
                DESCRIPTION
                        "A Debug level trap (7) signifies that an
                        event has occured at a debug level that is
                        informational. The module will not be
                        affected by this error."
                ::= 8
 

        -- **************************************************************
        -- * The following traps 9-15 have replaced traps 1-8           *
        -- **************************************************************

	cnt2smEmergencyTrap TRAP-TYPE
		ENTERPRISE cnt2Sm
		VARIABLES { cnt2SmMessageText }
		DESCRIPTION
			"An emergency level trap signifies that an
			event has occured which has rendered the system
			unusable. All modules and interfaces will be
			affected."
		::= 9
		
	cnt2smAlertTrap TRAP-TYPE
		ENTERPRISE cnt2Sm
		VARIABLES { cnt2SmMessageText }
		DESCRIPTION
			"An Alert level trap signifies that an
			event has occured which requires that immediate 
			action be taken. The module will be affected."
		::= 10
		
	cnt2smCriticalTrap TRAP-TYPE
		ENTERPRISE cnt2Sm
		VARIABLES { cnt2SmMessageText }
		DESCRIPTION
			"A Critical level trap signifies that an
			event has occured for which action should be
			taken.  The module will be affected."

		::= 11
		
	cnt2smErrorTrap TRAP-TYPE
		ENTERPRISE cnt2Sm
		VARIABLES { cnt2SmMessageText }
		DESCRIPTION
			"An Error level trap signifies that an
			event has occured that has resulted in errors.
			The module will probably be affected."
		::= 12
		
	cnt2smWarningTrap TRAP-TYPE
		ENTERPRISE cnt2Sm
		VARIABLES { cnt2SmMessageText }
		DESCRIPTION
			"A Warning level trap signifies that an
			event has occured that may affect the module."
		::= 13
		
	cnt2smNoticeTrap TRAP-TYPE
		ENTERPRISE cnt2Sm
		VARIABLES { cnt2SmMessageText }
		DESCRIPTION
			"A Notice level trap signifies that an
			event has occured that is normal but that has
			significance. The module should be unaffected"
		::= 14
		
	cnt2smInfoTrap TRAP-TYPE
		ENTERPRISE cnt2Sm
		VARIABLES { cnt2SmMessageText }
		DESCRIPTION
			"An Informaiton level trap signifies that an
			event has occured that informational in severity
			and that the module will not be affected by this
			error."
		::= 15
		
END
