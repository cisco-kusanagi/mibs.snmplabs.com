DSG-IF-STD-MIB DEFINITIONS ::= BEGIN
IMPORTS
    MODULE-IDENTITY,
    OBJECT-TYPE, 
    NOTIFICATION-TYPE,
    Integer32,
    Unsigned32, 
    Counter32                FROM SNMPv2-SMI         --RFC 2578

    OBJECT-GROUP,
    NOTIFICATION-GROUP,
    MODULE-COMPLIANCE        FROM SNMPv2-CONF        -- RFC 2580

    MacAddress,               
    TruthValue               FROM SNMPv2-TC          -- RFC 2579

    InetAddressType, 
    InetAddress,
    InetAddressPrefixLength,
    InetPortNumber           FROM INET-ADDRESS-MIB   -- RFC 3291

    ifPhysAddress            FROM IF-MIB             -- RFC 2863 

    docsDevEvLevel,
    docsDevEvId,
    docsDevEvText            FROM DOCS-CABLE-DEVICE-MIB   -- RFC 4639

    docsIfCmCmtsAddress,
    docsIfDocsisBaseCapability,
    docsIfCmStatusDocsisOperMode,
    docsIfCmStatusModulationType
                             FROM DOCS-IF-MIB  -- RFI MIB v2.0 draft 05(DOCSIS 2.0)
                                               -- RFC 4546 (OSSIv3.0 for DOCSIS 3.0)
    Dsid                     FROM DOCS-IF3-MIB             

    clabProjDocsis           FROM CLAB-DEF-MIB;

dsgIfStdMib MODULE-IDENTITY
    LAST-UPDATED  "201706150000Z" -- June 15, 2017
    ORGANIZATION "Cable Television Laboratories, Inc."
    CONTACT-INFO 
             "Postal: Cable Television Laboratories, Inc. 
                      858 Coal Creek Circle 
                      Louisville, Colorado 80027
                      U.S.A. 
             Phone : +1 303-661-9100 
             Fax   : +1 303-661-9199 
             E-mail: mibs@cablelabs.com"
    DESCRIPTION
            "Licensed under the Apache License, Version 2.0 (the 'License');
            you may not use this file except in compliance with the License.
            You may obtain a copy of the License at:
 
                http://www.apache.org/licenses/LICENSE-2.0
 
            Unless required by applicable law or agreed to in writing, software
            distributed under the License is distributed on an 'AS IS' BASIS,
            WITHOUT WARRANTIES OR CONDITIONS OF ANY KIND, either express or 
            implied.

            See the License for the specific language governing permissions and
            limitations under the License.

            This MIB module provides the management objects of 
            the DOCSIS Set-top Gateway (DSG) client controller 
            CM component for DSG operations of Set-top devices.
            Copyright 1999-2017 Cable Television Laboratories, Inc.
            All rights reserved."   
    REVISION    "201706150000Z" -- June 15, 2017
    DESCRIPTION
            "Revised per DSG-N-17.1740-1 to add Apache License
            information."
    REVISION    "201208090000Z" -- August 9, 2012
    DESCRIPTION
            "This revision includes ECNs DSG-N-12.1056-3 and 
             is published as part of the CableLabs DOCSIS 
             Set-top Gateway (DSG) Interface Specification 
             CM-SP-DSG-I21." 
    REVISION    "201203290000Z" -- March 29, 2012
    DESCRIPTION
            "This revision includes ECNs DSG-N-12.1037-1 and 
             DSG-N-12.1048-1 and is published as part of the 
             CableLabs DOCSIS Set-top Gateway (DSG) Interface              
             Specification CM-SP-DSG-I20."
    REVISION    "201106230000Z" -- June 23, 2011
    DESCRIPTION
            "This revision is published to add the Set-top Extender
             Bridge (SEB) functionality as part of Specification 
             CM-SP-DSG-I18."
    REVISION    "200905290000Z" -- May 29, 2009
    DESCRIPTION
            "This revision is published as part of the CableLabs
             DOCSIS Set-top Gateway (DSG) Interface
             Specification CM-SP-DSG-I14."
    REVISION    "200806260000Z" -- June 26, 2008
    DESCRIPTION
            "This revision is published as part of the CableLabs
             DOCSIS Set-top Gateway (DSG) Interface
             Specification CM-SP-DSG-I12."
    REVISION    "200702230000Z" -- February 23, 2007
    DESCRIPTION
            "This revision is published as part of the CableLabs
            DOCSIS Set-top Gateway (DSG) Interface 
            Specification CM-SP-DSG-I10."
    REVISION    "200607280000Z" -- July 28, 2006
    DESCRIPTION
            "This revision is published as part of the CableLabs
            DOCSIS Set-top Gateway (DSG) Interface 
            Specification CM-SP-DSG-I08."
    ::= { clabProjDocsis 4 }

-----------------------------------------------------------------------
--
-- DSG eCM MIB objects that represent the DSG Configuration parameters
-- Tunnels information and list of available downstream channels
-- carrying the Set-top box content.
--
------------------------------------------------------------------------

dsgIfStdNotifications     OBJECT IDENTIFIER ::= { dsgIfStdMib 0 }
dsgIfStdMibObjects        OBJECT IDENTIFIER ::= { dsgIfStdMib 1 }
dsgIfStdConfig            OBJECT IDENTIFIER ::= { dsgIfStdMibObjects 1 }
dsgIfStdTunnelFilter      OBJECT IDENTIFIER ::= { dsgIfStdMibObjects 2 }
dsgIfStdDsgChannelList    OBJECT IDENTIFIER ::= { dsgIfStdMibObjects 3 }
dsgIfStdDsgSeb            OBJECT IDENTIFIER ::= { dsgIfStdMibObjects 4 }

------------------------------------------------------------------------
-- DSG eCM Scalar objects
------------------------------------------------------------------------

dsgIfStdDsgMode OBJECT-TYPE
    SYNTAX      INTEGER {
                none(0),
                basic(1), --deprecated
                advanced(2)
                }
    MAX-ACCESS  read-only 
    STATUS      current 
    DESCRIPTION 
            "The DSG Mode of operation of this device.
             The value 'none' indicates that the eCM is 
             not performing DSG operations." 
    ::= { dsgIfStdConfig 1 }

dsgIfStdTdsg1 OBJECT-TYPE
    SYNTAX      Unsigned32
    UNITS       "seconds"
    MAX-ACCESS  read-only
    STATUS      current
    DESCRIPTION
            "The configured value for the Tdsg1 timer."
    DEFVAL { 2 }
    ::= { dsgIfStdConfig 2 }

dsgIfStdTdsg2 OBJECT-TYPE
    SYNTAX      Unsigned32
    UNITS       "seconds"
    MAX-ACCESS  read-only
    STATUS      current
    DESCRIPTION
            "The configured value for the Tdsg2 timer."
    DEFVAL { 600 }
    ::= { dsgIfStdConfig 3 }

dsgIfStdTdsg3 OBJECT-TYPE
    SYNTAX      Unsigned32
    UNITS       "seconds"
    MAX-ACCESS  read-only
    STATUS      current
    DESCRIPTION
            "The configured value for the Tdsg3 timer."
    DEFVAL { 300 } 
    ::= { dsgIfStdConfig 4 }

dsgIfStdTdsg4 OBJECT-TYPE
    SYNTAX      Unsigned32
    UNITS       "seconds"
    MAX-ACCESS  read-only
    STATUS      current
    DESCRIPTION
            "The configured value for the Tdsg4 timer."
    DEFVAL { 1800 }
    ::= { dsgIfStdConfig 5 }

dsgIfStdTdsg1Timeouts OBJECT-TYPE
    SYNTAX      Counter32
    MAX-ACCESS  read-only
    STATUS      current
    DESCRIPTION
            "The number of times Tdsg1 expired in the DSG eCM since 
            last reboot."
    ::= { dsgIfStdConfig 6 }
    
dsgIfStdTdsg2Timeouts OBJECT-TYPE
    SYNTAX      Counter32
    MAX-ACCESS  read-only
    STATUS      current
    DESCRIPTION
            "The number of times Tdsg2 expired in the DSG eCM since
            last reboot."
    ::= { dsgIfStdConfig 7 }

dsgIfStdTdsg3Timeouts OBJECT-TYPE
    SYNTAX      Counter32
    MAX-ACCESS  read-only
    STATUS      current
    DESCRIPTION
            "The number of times Tdsg3 expired in the DSG eCM since
            last reboot."
    ::= { dsgIfStdConfig 8 }

dsgIfStdTdsg4Timeouts OBJECT-TYPE
    SYNTAX      Counter32
    MAX-ACCESS  read-only
    STATUS      current
    DESCRIPTION
            "The number of times Tdsg4 expired in the DSG eCM since
            last reboot."
    ::= { dsgIfStdConfig 9 }
    
dsgIfStdOneWayRecovery OBJECT-TYPE
    SYNTAX INTEGER {
           retryUp(1),
           scan(2)
    }
    MAX-ACCESS read-write
    STATUS current
    DESCRIPTION
           "This objects describes what the eCM does when the
           Tdsg3 timer expires. A value of retryUp(1) indicates that
           the eCM will remain on the current downstream channel(s) and
           will attempt to re-establish the upstream. A value of scan(2)
           indicates that the eCM will scan for new downstream channel(s).
           The value of the object is retained in nonvolatile storage."
    DEFVAL { 2 }
    ::= { dsgIfStdConfig 10 }

------------------------------------------------------------------------
-- Active Tunnel filters
------------------------------------------------------------------------

dsgIfStdTunnelFilterTable OBJECT-TYPE 
    SYNTAX      SEQUENCE OF DsgIfStdTunnelFilterEntry 
    MAX-ACCESS  not-accessible 
    STATUS      current
    DESCRIPTION
            "A table of the active DSG Tunnel Filters. Each DSG Tunnel
            Filter is used to identify packets to forward to a DSG 
            Client. Conceptually, each DSG Tunnel is composed of one 
            or more DSG tunnel filters. "
    ::= { dsgIfStdTunnelFilter 1 } 

dsgIfStdTunnelFilterEntry OBJECT-TYPE 
    SYNTAX      DsgIfStdTunnelFilterEntry 
    MAX-ACCESS  not-accessible 
    STATUS      current 
    DESCRIPTION 
            "The DSG eCM will have one entry for each DSG Tunnel
            Filter. 
            One or more entries in this table are created when the DSG 
            Client Controller instructs the eCM to begin forwarding traffic 
            from a particular DSG Tunnel. When the Client Controller 
            instructs the eCM that traffic from a DSG Tunnel should no longer 
            be forwarded, the eCM deletes corresponding entries from this 
            table. 

            Note that a DSG Tunnel Filter is constructed by the DSG Client 
            Controller using an unspecified algorithm and based on information 
            in the DCD. Statistics like the packet and octet counts apply to 
            the DSG Tunnel Filter and not necessarily to a DSG Rule."
    INDEX { dsgIfStdTunnelFilterIndex }
    ::= { dsgIfStdTunnelFilterTable 1 }

DsgIfStdTunnelFilterEntry ::=  SEQUENCE {
    dsgIfStdTunnelFilterIndex              Unsigned32,
    dsgIfStdTunnelFilterApplicationId      Integer32,
    dsgIfStdTunnelFilterMacAddress         MacAddress,
    dsgIfStdTunnelFilterIpAddressType      InetAddressType,
    dsgIfStdTunnelFilterSrcIpAddr          InetAddress,
    dsgIfStdTunnelFilterSrcIpMask          InetAddress,
    dsgIfStdTunnelFilterDestIpAddr         InetAddress,
    dsgIfStdTunnelFilterDestPortStart      InetPortNumber,
    dsgIfStdTunnelFilterDestPortEnd        InetPortNumber,
    dsgIfStdTunnelFilterPkts               Counter32,
    dsgIfStdTunnelFilterOctets             Counter32,
    dsgIfStdTunnelFilterTimeActive         Counter32,
    dsgIfStdTunnelFilterTunnelId           Unsigned32,
    dsgIfStdTunnelFilterDsid               Dsid,
    dsgIfStdTunnelFilterClientIdType       INTEGER,
    dsgIfStdTunnelFilterClientIdValue      OCTET STRING
    }

dsgIfStdTunnelFilterIndex OBJECT-TYPE
    SYNTAX      Unsigned32 
    MAX-ACCESS  not-accessible
    STATUS      current 
    DESCRIPTION 
            "The unique index of entries in this table." 
    ::= { dsgIfStdTunnelFilterEntry 1 }

dsgIfStdTunnelFilterApplicationId OBJECT-TYPE
    SYNTAX      Integer32 (-1 | 0.. 65535)
    MAX-ACCESS  read-only
    STATUS      deprecated
    DESCRIPTION 
            "The Application ID of the DSG Tunnel associated with this DSG Tunnel 
            Filter. This object returns -1 for: DSG Tunnels that
            do not have an associated Application ID or for DSG Tunnels
            for which the Application ID is unknown. In an OpenCable
            Host, this object returns '0' for a DSG Tunnel whose client
            resides on the Card. This object has been replaced by the
            dsgIfStdTunnelFilterClientIdType and dsgIfStdTunnelFilterClientIdValue
            objects." 
    DEFVAL { -1 }
    ::= { dsgIfStdTunnelFilterEntry 2 }

dsgIfStdTunnelFilterMacAddress OBJECT-TYPE
    SYNTAX      MacAddress
    MAX-ACCESS  read-only
    STATUS      current 
    DESCRIPTION 
            "The destination MAC Address 
             matching this DSG Tunnel Filter entry." 
    ::= { dsgIfStdTunnelFilterEntry 3 }

dsgIfStdTunnelFilterIpAddressType OBJECT-TYPE
    SYNTAX      InetAddressType 
    MAX-ACCESS  read-only
    STATUS      current 
    DESCRIPTION 
            "The type of InetAddress for dsgIfStdTunnelFilterSrcIpAddr,
            dsgIfStdTunnelFilterSrcIpMask and 
            dsgIfStdTunnelFilterDestIpAddr. Currently DSG Agents, DSG Client
            Controllers and DSG eCMs are not required to support 
            IPv6 DSG classifiers. " 
    ::= { dsgIfStdTunnelFilterEntry 4 }

dsgIfStdTunnelFilterSrcIpAddr OBJECT-TYPE
    SYNTAX      InetAddress
    MAX-ACCESS  read-only
    STATUS      current 
    DESCRIPTION 
            "The source IP Address matching this DSG Tunnel Filter. This
            object is used in conjunction with dsgIfStdTunnelFilterSrcMask. A value of
            zero indicates that source IP Address filtering does not apply.
            The type of this address is determined by the value of the
            dsgIfStdTunnelFilterIpAddressType object."
    DEFVAL { '00000000'h }
    ::= { dsgIfStdTunnelFilterEntry 5 }

dsgIfStdTunnelFilterSrcIpMask OBJECT-TYPE
    SYNTAX      InetAddress
    MAX-ACCESS  read-only
    STATUS      current 
    DESCRIPTION 
            "The Source IP Mask to be used with 
            dsgIfStdTunnelFilterSrcIpAddr  when comparing 
            a packet to this DSG Tunnel Filter.
            The type of this address is determined by the value of the
            dsgIfStdTunnelFilterIpAddressType object."
    DEFVAL { 'FFFFFFFF'h }
    ::= { dsgIfStdTunnelFilterEntry 6 }

dsgIfStdTunnelFilterDestIpAddr OBJECT-TYPE
    SYNTAX      InetAddress
    MAX-ACCESS  read-only
    STATUS      current 
    DESCRIPTION 
            "The destination IP Address matching this DSG Tunnel Filter. A value of
            zero indicates that destination IP Address filtering does
            not apply. The type of this address is determined by the
            value of the dsgIfStdTunnelFilterIpAddressType object."
    DEFVAL { '00000000'h }
    ::= { dsgIfStdTunnelFilterEntry 7 }

dsgIfStdTunnelFilterDestPortStart OBJECT-TYPE
    SYNTAX      InetPortNumber
    MAX-ACCESS  read-only
    STATUS      current 
    DESCRIPTION 
            "The lower UDP destination port value in the range matching this DSG Tunnel Filter. "
    DEFVAL { 0 } 
    ::= { dsgIfStdTunnelFilterEntry 8 }

dsgIfStdTunnelFilterDestPortEnd OBJECT-TYPE
    SYNTAX      InetPortNumber
    MAX-ACCESS  read-only
    STATUS      current 
    DESCRIPTION 
            "The upper UDP destination port value in the range matching this DSG Tunnel Filter."
    DEFVAL { 65535 } 
    ::= { dsgIfStdTunnelFilterEntry 9 }

dsgIfStdTunnelFilterPkts OBJECT-TYPE
    SYNTAX      Counter32
    UNITS       "packets"
    MAX-ACCESS  read-only
    STATUS      current 
    DESCRIPTION 
            "The total number of Packets  matching this DSG Tunnel Filter entry since creation of the entry."
    ::= { dsgIfStdTunnelFilterEntry 10 }

dsgIfStdTunnelFilterOctets OBJECT-TYPE
    SYNTAX      Counter32
    UNITS       "octets" 
    MAX-ACCESS  read-only
    STATUS      current 
    DESCRIPTION 
            "The total number of octets matching this DSG Tunnel Filter entry since creation of the entry." 
    ::= { dsgIfStdTunnelFilterEntry 11 }

dsgIfStdTunnelFilterTimeActive OBJECT-TYPE
    SYNTAX      Counter32
    UNITS       "seconds"
    MAX-ACCESS  read-only
    STATUS      current 
    DESCRIPTION 
            "The total number of seconds that this DSG Tunnel Filter entry has
            been instantiated." 
    ::= { dsgIfStdTunnelFilterEntry 12 }

dsgIfStdTunnelFilterTunnelId OBJECT-TYPE
    SYNTAX      Unsigned32 (0 | 1..255)
    MAX-ACCESS  read-only
    STATUS      current 
    DESCRIPTION 
            "In DSG Advanced Mode, this value identifies the DSG Tunnel 
            corresponding to this DSG Tunnel
            Filter entry. This value may correspond to the DSG Rule ID
            from the DCD message."
    DEFVAL { 0 }
    ::= { dsgIfStdTunnelFilterEntry 13 }

dsgIfStdTunnelFilterDsid OBJECT-TYPE
    SYNTAX      Dsid 
    MAX-ACCESS  read-only
    STATUS      current
    DESCRIPTION
            "When operating with Multicast DSID Forwarding (MDF)
            enabled, this object contains the DSID value obtained
            from the DA-to-DSID TLV in the MDD. If no DSID has been advertised         
            for this tunnel MAC address then this object returns 0. 
            When MDF is disabled, this object returns 0. Pre-3.0 DOCSIS 
            devices are not required to instantiate this object."
    ::= { dsgIfStdTunnelFilterEntry 14 }

dsgIfStdTunnelFilterClientIdType OBJECT-TYPE
    SYNTAX      INTEGER {
        cableCard(0),
        broadcast(1),
        macAddress(2),
        caSystemId(3),
        applicationId(4)
        } 
    MAX-ACCESS  read-only
    STATUS      current 
    DESCRIPTION 
            "The value of cableCard(0) indicates a DSG Tunnel 
            requested by the CableCARD on an OpenCable
            Host. The value of broadcast(1) indicates a DSG Tunnel 
            for an industry standard flow identified by a DSG Broadcast ID.  
            The value of macAddress(2) indicates a DSG Tunnel for a 
            flow identified by a well known MAC Address. The value of 
            caSystemId(3) indicates a DSG Tunnel for a flow identified by 
            a CA_system_ID. The value of applicationId(4) indicates a DSG 
            Tunnel identified by an application ID." 
    ::= { dsgIfStdTunnelFilterEntry 15 }

dsgIfStdTunnelFilterClientIdValue OBJECT-TYPE
    SYNTAX      OCTET STRING (SIZE(0 | 6))
    MAX-ACCESS  read-only
    STATUS      current 
    DESCRIPTION 
            "The Client Identification Value. The content depends on
            the value of the dsgIfStdTunnelFilterClientIdType. 

            For dsgIfStdTunnelFilterClientIdType of type cableCard(0),
            this object will return a zero length string.
            For dsgIfStdTunnelFilterClientIdType of a type broadcast(1), 
            this object will have a 16-bit value whether or not it is a 
            length 0 or length 2 broadcast ID. If the value is 0, then 
            the encoded TLV in the DCD would be the original, zero length,
            broadcast ID. If the value is specified in Table 5-2, then
            the TLV in the DCD would be a length 2 broadcast ID
            followed by the value.

            For dsgIfStdTunnelFilterClientIdType of type macAddress(2), 
            this object will return a well known MAC address.
 
            For dsgIfStdTunnelFilterClientIdType of type caSystemId(3), 
            this object will return a CA System ID.
 
            For dsgIfStdTunnelFilterClientIdType of type applicationId(4),
            this object will return an application ID.

            Client IDs representing types broadcast(1), caSystemId(3) 
            or applicationId(4) are encoded in DCD messages as Unsigned
            integers and configured in this object as 6 octet string 
            with the 2 LSB for the client ID value, e.g., an 
            applicationId 2048 (0x0800) is encoded as '000000000800'h."

    REFERENCE 
            "DOCSIS Set-top Gateway (DSG) Interface"
     ::= { dsgIfStdTunnelFilterEntry 16 }

------------------------------------------------------------------------
-- DSG Channel List Table, one row per DSG Channel Frequency provided
-- in the DCD message.
------------------------------------------------------------------------

dsgIfStdDsgChannelListTable OBJECT-TYPE 
    SYNTAX      SEQUENCE OF DsgIfStdDsgChannelListEntry 
    MAX-ACCESS  not-accessible 
    STATUS      current
    DESCRIPTION
            "This table contains the list of DSG channels provided to
            the DSG eCM for use in scanning."
    ::= { dsgIfStdDsgChannelList 1 } 

dsgIfStdDsgChannelListEntry OBJECT-TYPE 
    SYNTAX      DsgIfStdDsgChannelListEntry 
    MAX-ACCESS  not-accessible 
    STATUS      current 
    DESCRIPTION 
            "The conceptual row for this table. The DSG eCM
             creates an entry per each downstream channel provided in 
             the DCD message. An entry is deleted when removed from the
             DCD message."
    INDEX { dsgIfStdDsgChannelListIndex }
    ::= { dsgIfStdDsgChannelListTable 1 }

DsgIfStdDsgChannelListEntry ::=  SEQUENCE {
    dsgIfStdDsgChannelListIndex      Unsigned32,
    dsgIfStdDsgChannelListFrequency  Unsigned32
    }

dsgIfStdDsgChannelListIndex OBJECT-TYPE
    SYNTAX      Unsigned32
    MAX-ACCESS  not-accessible
    STATUS      current 
    DESCRIPTION 
            "The unique identifier for entries in this table" 
    ::= { dsgIfStdDsgChannelListEntry 1 }

dsgIfStdDsgChannelListFrequency OBJECT-TYPE
    SYNTAX      Unsigned32
    UNITS       "Hertz"
    MAX-ACCESS  read-only
    STATUS      current 
    DESCRIPTION 
            "The downstream channel center frequency of this entry."
    ::= { dsgIfStdDsgChannelListEntry 2 }

--
-- DSG Set-top Extender Bridge (SEB) Object Definitions
--		
dsgIfStdDsgSebControlObject OBJECT-TYPE
    SYNTAX TruthValue
    MAX-ACCESS read-write
    STATUS current
    DESCRIPTION
            "This object controls the state of DSG SEB.
             When set to FALSE the device is prohibited
             from enabling DSG SEB, both as a client
             or a server."
    DEFVAL {TRUE}
    ::= { dsgIfStdDsgSeb 1 }

dsgIfStdDsgSebRole OBJECT-TYPE
	SYNTAX INTEGER
		{
		disabled(1),
		sebServerIneligible(2),
		sebServerNoClients(3),
		sebServerWithClients(4),
		sebClientNoTunnel(5),
		sebClientWithTunnel(6),
		attemptingTwoWay(7)
		}
	MAX-ACCESS read-only
	STATUS current
	DESCRIPTION
		"This object reports the current role of this
		device. The value of disabled(1) is used for a
		device where SEB is administratively disabled. The
		value of sebServerIneligible(2) is used for a 
		device that is two-way operational but is not
		eligible to act as a SEB Server. The value of
		sebServerNoClients(3) represents a device that is
		two-way operational and is eligible to act as a
		server, but does not have any clients. The value 
		of sebServerWithClients(4) represents a SEB Server
		with at least one established SEB Tunnel. The value
		of sebClientNoTunnel(5) represents a one-way device
             that has not established a SEB Tunnel. The value of
             sebClientWithTunnel(6) represents a one-way device
             that has successfully established a SEB Tunnel. The
		value of attemptingTwoWay(7) is used when a device
		is in the process of establishing DOCSIS upstream
		connectivity."
	::= { dsgIfStdDsgSeb 2 }

dsgIfStdDsgSebFomWeightUpstreamPower OBJECT-TYPE
	SYNTAX Unsigned32 
	MAX-ACCESS read-write
	STATUS current
	DESCRIPTION
		"This object controls the contribution
		of the upstream transmit power level term
		for the Figure of Merit Calculation."
	DEFVAL {100}
	::= {dsgIfStdDsgSeb 3 }

dsgIfStdDsgSebFomWeightDownstreamPower OBJECT-TYPE
	SYNTAX Unsigned32 
	MAX-ACCESS read-write
	STATUS current
	DESCRIPTION
		"This object controls the contribution
		of the downstream receive power level term
		for the Figure of Merit Calculation."
	DEFVAL {100}
	::= {dsgIfStdDsgSeb 4 }

dsgIfStdDsgSebFomWeightEqualizer OBJECT-TYPE
	SYNTAX Unsigned32 
	MAX-ACCESS read-write
	STATUS current
	DESCRIPTION
		"This object controls the contribution
		of the equalizer performance term
		for the Figure of Merit Calculation."
	DEFVAL {100}
	::= {dsgIfStdDsgSeb 5 }

dsgIfStdDsgSebFomUsPwrHr OBJECT-TYPE
	SYNTAX Unsigned32 
	MAX-ACCESS read-write
	STATUS current
	DESCRIPTION
		"This object defines the Upstream
		transmit power headroom value
		for the Figure of Merit Calculation."
	DEFVAL {6}
	::= {dsgIfStdDsgSeb 6 }

dsgIfStdDsgSebFomMfQpsk OBJECT-TYPE
	SYNTAX Unsigned32 
	MAX-ACCESS read-write
	STATUS current
	DESCRIPTION
		"This object defines the value
		of maximum power level for QPSK upstream
		for the Figure of Merit Calculation."
	DEFVAL {58}
	::= {dsgIfStdDsgSeb 7 }

dsgIfStdDsgSebFomMfQam16 OBJECT-TYPE
	SYNTAX Unsigned32 
	MAX-ACCESS read-write
	STATUS current
	DESCRIPTION
		"This object defines the value
		of maximum power level for QAM16 upstream
		for the Figure of Merit Calculation."
	DEFVAL {55}
	::= {dsgIfStdDsgSeb 8 }

dsgIfStdDsgSebFomMfQam64 OBJECT-TYPE
	SYNTAX Unsigned32 
	MAX-ACCESS read-write
	STATUS current
	DESCRIPTION
		"This object defines the value
		of maximum power level for QAM64 upstream
		for the Figure of Merit Calculation."
	DEFVAL {54}
	::= {dsgIfStdDsgSeb 9 }

dsgIfStdDsgSebFomDsDesPwr OBJECT-TYPE
	SYNTAX Integer32 
	MAX-ACCESS read-write
	STATUS current
	DESCRIPTION
		"This object defines the value
		of desired downstream receive power
		for the Figure of Merit Calculation."
	DEFVAL {0}
	::= {dsgIfStdDsgSeb 10 }

dsgIfStdDsgSebFomDspMin OBJECT-TYPE
	SYNTAX Integer32 
	MAX-ACCESS read-write
	STATUS current
	DESCRIPTION
		"This object defines the value
		of downstream receive power minimum
		for the Figure of Merit Calculation."
	DEFVAL {-6}
	::= {dsgIfStdDsgSeb 11 }

dsgIfStdDsgSebFomDspMax OBJECT-TYPE
	SYNTAX Integer32 
	MAX-ACCESS read-write
	STATUS current
	DESCRIPTION
		"This object defines the value
		of downstream receive power maximum
		for the Figure of Merit Calculation."
	DEFVAL {5}
	::= {dsgIfStdDsgSeb 12 }

dsgIfStdDsgSebFomNmteRng OBJECT-TYPE
	SYNTAX Unsigned32 
	MAX-ACCESS read-write
	STATUS current
	DESCRIPTION
		"This object defines the value
		of non-main tap energy range
		for the Figure of Merit Calculation."
	DEFVAL {80}
	::= {dsgIfStdDsgSeb 13 }

dsgIfStdDsgSebFomNmteMax OBJECT-TYPE
	SYNTAX Integer32 
	MAX-ACCESS read-write
	STATUS current
	DESCRIPTION
		"This object defines the value
		of non-main tap energy maximum
		for the Figure of Merit Calculation."
	DEFVAL {-5}
	::= {dsgIfStdDsgSeb 14 }


dsgIfStdDsgSebFomMtcMin OBJECT-TYPE
	SYNTAX Integer32 
	MAX-ACCESS read-write
	STATUS current
	DESCRIPTION
		"This object defines the value
		of main tap compression minimum
		for the Figure of Merit Calculation."
	DEFVAL {-2}
	::= {dsgIfStdDsgSeb 15 }

dsgIfStdDsgSebFom OBJECT-TYPE
	SYNTAX Unsigned32
	MAX-ACCESS read-only
	STATUS current
	DESCRIPTION
		"This object contains the value
		resulting from the FOM calculation."
	::= { dsgIfStdDsgSeb 16 }

dsgIfStdDsgSebTunnelTimeout OBJECT-TYPE
	SYNTAX Unsigned32(1..86400)
	MAX-ACCESS read-write
	STATUS current
	DESCRIPTION
		"The number of seconds the SEB Server will wait
		for the SEB Tunnel to be established by the SEBC
		after receiving the ClientConnect service action."
	DEFVAL { 120 }
	::= { dsgIfStdDsgSeb 17 }

dsgIfStdDsgSebTdsg3Override OBJECT-TYPE
	SYNTAX Integer32 (-1..2147483647)
	MAX-ACCESS read-write
	STATUS current
	DESCRIPTION
		"This object overrides the value of the Tdsg3 timeout
		specified in the DCD. A value of -1 indicates that the
		DCD value will be used. This object is ignored when
		dsgIfStdDsgSebControlObject is set to false."
	DEFVAL { -1 }
	::= { dsgIfStdDsgSeb 18 } 

dsgIfStdDsgSebConnectedDeviceTable OBJECT-TYPE
	SYNTAX SEQUENCE OF DsgIfStdDsgSebConnectedDeviceEntry
	MAX-ACCESS not-accessible
	STATUS current
	DESCRIPTION
		"For a SEB Server, a list of the connected devices.
             In general, each SEB Tunnel will be used for multiple
             devices and will therefore have multiple entries in this
             table. For a SEB Client, a list of devices contained within
             the client utilizing the SEB service."
	::= { dsgIfStdDsgSeb 19 }

dsgIfStdDsgSebConnectedDeviceEntry OBJECT-TYPE 
    SYNTAX      DsgIfStdDsgSebConnectedDeviceEntry
    MAX-ACCESS  not-accessible 
    STATUS      current 
    DESCRIPTION 
            "The conceptual row of dsgIfStdDsgSebConnectedDeviceTable."
	INDEX { dsgIfStdDsgSebConnectedDeviceIndex }
	::= { dsgIfStdDsgSebConnectedDeviceTable 1 }
		
DsgIfStdDsgSebConnectedDeviceEntry ::= 	SEQUENCE { 
	       dsgIfStdDsgSebConnectedDeviceIndex
			Unsigned32,
		dsgIfStdDsgSebConnectedDeviceMacAddress
			MacAddress,
		dsgIfStdDsgSebConnectedDeviceIpAddressType
			InetAddressType,
		dsgIfStdDsgSebConnectedDeviceIpAddress
			InetAddress,
		dsgIfStdDsgSebConnectedDeviceType
			INTEGER,
             dsgIfStdDsgSebTunnelClientIpAddressType
                    InetAddressType,
             dsgIfStdDsgSebTunnelClientIpAddress
                    InetAddress,
		dsgIfStdDsgSebTunnelClientPort
			Unsigned32,
             dsgIfStdDsgSebTunnelServerIpAddressType
                    InetAddressType,
             dsgIfStdDsgSebTunnelServerIpAddress
                    InetAddress,
             dsgIfStdDsgSebTunnelServerPort
                    Unsigned32
			 }

dsgIfStdDsgSebConnectedDeviceIndex OBJECT-TYPE
	SYNTAX Unsigned32 (1..256)
	MAX-ACCESS not-accessible
	STATUS current
	DESCRIPTION
		"The unique identifier for entries in this table"
	::= { dsgIfStdDsgSebConnectedDeviceEntry 1 }

		
dsgIfStdDsgSebConnectedDeviceMacAddress OBJECT-TYPE
	SYNTAX MacAddress
	MAX-ACCESS read-only
	STATUS current
	DESCRIPTION
		"MAC Address of the connected device."
	::= { dsgIfStdDsgSebConnectedDeviceEntry 2 }

dsgIfStdDsgSebConnectedDeviceIpAddressType OBJECT-TYPE
	SYNTAX InetAddressType
	MAX-ACCESS read-only
	STATUS current
	DESCRIPTION
"Type of IP Address for dsgIfStdDsgSebConnectedDeviceIpAddress."
	::= { dsgIfStdDsgSebConnectedDeviceEntry 3 }
		
dsgIfStdDsgSebConnectedDeviceIpAddress OBJECT-TYPE
	SYNTAX InetAddress
	MAX-ACCESS read-only
	STATUS current
	DESCRIPTION
		"Global IP address assigned by a DHCP server
             and used on the DOCSIS network for this device. 
             This object will report 0.0.0.0 if no address 
             has been assigned or if the address is unknown. 
             Note that the SEB Server will not generally know
             the DHCP-assigned addresses of the connected devices
             and will populate this object as 0.0.0.0."
	::= { dsgIfStdDsgSebConnectedDeviceEntry 4 }

		
dsgIfStdDsgSebConnectedDeviceType OBJECT-TYPE
	SYNTAX INTEGER
		{
		eSTB(1),
		cableCard(2), -- Deprecated
		eCM (3),
		other(4)
		}
	MAX-ACCESS read-only
	STATUS current
	DESCRIPTION
		"Type of device. Type cableCard(2) has been deprecated."
	::= { dsgIfStdDsgSebConnectedDeviceEntry 5 }

dsgIfStdDsgSebTunnelClientIpAddressType OBJECT-TYPE
	SYNTAX InetAddressType
	MAX-ACCESS read-only
	STATUS current
	DESCRIPTION
		"This object specifies the IP address type of
dsgIfStdDsgSebTunnelClientIpAddress."
	::= { dsgIfStdDsgSebConnectedDeviceEntry 6 }

dsgIfStdDsgSebTunnelClientIpAddress OBJECT-TYPE
	SYNTAX InetAddress
	MAX-ACCESS read-only
	STATUS current
	DESCRIPTION
		"The client side IP address of the SEB Tunnel.
             If a SEB Tunnel is not established, this 
             object will report 0.0.0.0."
	::= { dsgIfStdDsgSebConnectedDeviceEntry 7 }

dsgIfStdDsgSebTunnelClientPort OBJECT-TYPE
	SYNTAX Unsigned32
	MAX-ACCESS read-only
	STATUS current
	DESCRIPTION
		"The server side TCP port used by this tunnel.
              If a SEB Tunnel is not established, this
              object will report 0."
	::= { dsgIfStdDsgSebConnectedDeviceEntry 8 }

dsgIfStdDsgSebTunnelServerIpAddressType OBJECT-TYPE
	SYNTAX InetAddressType
	MAX-ACCESS read-only
	STATUS current
	DESCRIPTION
		"This object specifies the IP address type of
dsgIfStdDsgSebTunnelServerIpAddress."
	::= { dsgIfStdDsgSebConnectedDeviceEntry 9 }

dsgIfStdDsgSebTunnelServerIpAddress OBJECT-TYPE
	SYNTAX InetAddress
	MAX-ACCESS read-only
	STATUS current
	DESCRIPTION
		"The server side IP address of the SEB Tunnel.
             If a SEB Tunnel is not established, this 
             object will report 0.0.0.0."
	::= { dsgIfStdDsgSebConnectedDeviceEntry 10 }

dsgIfStdDsgSebTunnelServerPort OBJECT-TYPE
	SYNTAX Unsigned32
	MAX-ACCESS read-only
	STATUS current
	DESCRIPTION
		"The server side TCP port used by this tunnel.
              If a SEB Tunnel is not established, this
              object will report 0."
	::= { dsgIfStdDsgSebConnectedDeviceEntry 11 }

--
-- Notification Definitions
--

dsgIfStdUpstreamEnabledNotify NOTIFICATION-TYPE
    OBJECTS {
            docsDevEvLevel,
            docsDevEvId,
            docsDevEvText,
            ifPhysAddress,
            docsIfCmCmtsAddress,
            docsIfDocsisBaseCapability,
            docsIfCmStatusDocsisOperMode,
            docsIfCmStatusModulationType
           }
    STATUS      current
    DESCRIPTION
            "Indicates the eCM is being instructed to have the upstream
            transmitter enabled. This notification is send after CM 
            registration.
            Note that the objects docsIfDocsisBaseCapability, 
            docsIfCmStatusDocsisOperMode and
            docsIfCmStatusModulationType may not be supported in some
            situations (e.g., for 1.1 CMs in 1.0 mode these objects are
            optional, for 3.0 CMs docsIfCmStatusDocsisOperMode and 
            docsIfCmStatusModulationType are deprecated). 
            If that is the case, the above varbind objects
            are indicated as noSuchName or noSuchObject for 
            SNMPv1 and SNMPv2 notification PDUs respectively."
    ::= { dsgIfStdNotifications 1 }

dsgIfStdUpstreamDisabledNotify NOTIFICATION-TYPE
    OBJECTS {
            docsDevEvLevel,
            docsDevEvId,
            docsDevEvText,
            ifPhysAddress,
            docsIfCmCmtsAddress,
            docsIfDocsisBaseCapability,
            docsIfCmStatusDocsisOperMode,
            docsIfCmStatusModulationType
           }
    STATUS      current
    DESCRIPTION
            "Indicates the CM is being instructed to have the upstream
            transmitter disabled. This notification is only send when 
            the CM is registered and prior to disable the upstream
            transmitter. Note that the objects
            docsIfDocsisBaseCapability, docsIfCmStatusDocsisOperMode
            and docsIfCmStatusModulationType may not be supported in
            some situations (e.g., for 1.1 CMs in 1.0 mode these objects
            are optional, for 3.0 CMs docsIfCmStatusDocsisOperMode and 
            docsIfCmStatusModulationType are deprecated). 
            If that is the case the above varbind
            objects are indicated as noSuchName or noSuchObject for 
            SNMPv1 and SNMPv2 notification PDUs respectively."
    ::= { dsgIfStdNotifications 2 }

dsgIfStdTdsg2TimeoutNotify NOTIFICATION-TYPE
    OBJECTS {
            docsDevEvLevel,
            docsDevEvId,
            docsDevEvText,
            ifPhysAddress,
            docsIfCmCmtsAddress,
            docsIfDocsisBaseCapability,
            docsIfCmStatusDocsisOperMode,
            docsIfCmStatusModulationType
           }
    STATUS      current
    DESCRIPTION
            "Notifies that the eCM has a timeout Tdsg2. 
            Note that the objects docsIfDocsisBaseCapability, 
            docsIfCmStatusDocsisOperMode and 
            docsIfCmStatusModulationType may not be supported in some
            situations (e.g., for 1.1 CMs in 1.0 mode these objects are
            optional, for 3.0 CMs docsIfCmStatusDocsisOperMode and 
            docsIfCmStatusModulationType are deprecated). 
            If that is the case the above varbind objects
            are indicated as noSuchName or noSuchObject for 
            SNMPv1 and SNMPv2 notification PDUs respectively."
    ::= { dsgIfStdNotifications 3 }

-- 
-- Conformance definitions 
-- 
dsgIfStdConformance  OBJECT IDENTIFIER ::= { dsgIfStdMib 2 } 
dsgIfStdCompliances  OBJECT IDENTIFIER ::= { dsgIfStdConformance 1 } 
dsgIfStdGroups       OBJECT IDENTIFIER ::= { dsgIfStdConformance 2 } 


dsgIfStdBasicCompliance MODULE-COMPLIANCE 
    STATUS      current 
    DESCRIPTION 
            "The compliance statement for DOCSIS Set-top Gateway eCMs."

MODULE -- dsgIfStdMIB

 -- mandatory groups

MANDATORY-GROUPS {
                 dsgIfStdConfigGroup,
                 dsgIfStdNotifyGroup 
                 }
    ::= { dsgIfStdCompliances 1 } 

dsgIfStdDsgSebCompliance MODULE-COMPLIANCE
    STATUS current
    DESCRIPTION 
		"The compliance statement for DOCSIS Set-top Gateway devices
that support DSG SEB."

MODULE -- dsgIfStdMIB

-- mandatory groups

MANDATORY-GROUPS { 
                 dsgIfStdConfigGroup, 
                 dsgIfStdNotifyGroup, 
                 dsgIfStdDsgSebGroup }
    ::= { dsgIfStdCompliances 2 }


dsgIfStdConfigGroup OBJECT-GROUP
    OBJECTS {
            dsgIfStdDsgMode,
            dsgIfStdTdsg1,
            dsgIfStdTdsg2,
            dsgIfStdTdsg3,
            dsgIfStdTdsg4,
            dsgIfStdTdsg1Timeouts,
            dsgIfStdTdsg2Timeouts,
            dsgIfStdTdsg3Timeouts,
            dsgIfStdTdsg4Timeouts,
            dsgIfStdOneWayRecovery,
            dsgIfStdTunnelFilterMacAddress,
            dsgIfStdTunnelFilterIpAddressType,
            dsgIfStdTunnelFilterSrcIpAddr,
            dsgIfStdTunnelFilterSrcIpMask,
            dsgIfStdTunnelFilterDestIpAddr,
            dsgIfStdTunnelFilterDestPortStart,
            dsgIfStdTunnelFilterDestPortEnd,
            dsgIfStdTunnelFilterPkts,
            dsgIfStdTunnelFilterOctets,
            dsgIfStdTunnelFilterTimeActive,
            dsgIfStdTunnelFilterTunnelId,
            dsgIfStdTunnelFilterDsid,
            dsgIfStdTunnelFilterClientIdType,
            dsgIfStdTunnelFilterClientIdValue,
            dsgIfStdDsgChannelListFrequency
            }
    STATUS      current
    DESCRIPTION
            "A collection of configuration elements provided in DCD 
            messages and DSG operations."
    ::= { dsgIfStdGroups 1 } 

dsgIfStdNotifyGroup NOTIFICATION-GROUP
    NOTIFICATIONS { dsgIfStdUpstreamEnabledNotify, 
                  dsgIfStdUpstreamDisabledNotify,
                  dsgIfStdTdsg2TimeoutNotify
                  }
    STATUS      current
    DESCRIPTION
            "The collection of DSG notifications that the eCM reports
             as part of the Set-top device"
    ::= { dsgIfStdGroups 2 }

dsgIfStdDsgSebGroup OBJECT-GROUP
   OBJECTS { 
            dsgIfStdDsgSebControlObject,
            dsgIfStdDsgSebRole, 
            dsgIfStdDsgSebFomWeightUpstreamPower,
            dsgIfStdDsgSebFomWeightDownstreamPower,
            dsgIfStdDsgSebFomWeightEqualizer,
            dsgIfStdDsgSebFomUsPwrHr,
            dsgIfStdDsgSebFomMfQpsk,
            dsgIfStdDsgSebFomMfQam16,
            dsgIfStdDsgSebFomMfQam64,
            dsgIfStdDsgSebFomDsDesPwr,
            dsgIfStdDsgSebFomDspMin,
            dsgIfStdDsgSebFomDspMax,
            dsgIfStdDsgSebFomNmteRng,
            dsgIfStdDsgSebFomNmteMax,
            dsgIfStdDsgSebFomMtcMin,
            dsgIfStdDsgSebFom,
            dsgIfStdDsgSebTunnelTimeout,
            dsgIfStdDsgSebTdsg3Override,
            dsgIfStdDsgSebConnectedDeviceMacAddress,
            dsgIfStdDsgSebConnectedDeviceIpAddressType,
            dsgIfStdDsgSebConnectedDeviceIpAddress,
            dsgIfStdDsgSebConnectedDeviceType,
            dsgIfStdDsgSebTunnelClientIpAddressType,        
            dsgIfStdDsgSebTunnelClientIpAddress,
            dsgIfStdDsgSebTunnelClientPort,
            dsgIfStdDsgSebTunnelServerIpAddressType,
            dsgIfStdDsgSebTunnelServerIpAddress,
            dsgIfStdDsgSebTunnelServerPort
	     }
   STATUS current
   DESCRIPTION 
		"A collection of configuration elements in support of DSG SEB
		operation. These objects are required for both clients and
		servers."
   ::= { dsgIfStdGroups 3 }

END
