-- extracted from draft-kzm-imss-fc-fcsp-mib-00.txt
-- at Wed Jun 13 06:08:27 2007

T11-FC-SP-CERTS-MIB  DEFINITIONS ::= BEGIN

IMPORTS
    MODULE-IDENTITY, OBJECT-TYPE,
    mib-2, Unsigned32
                          FROM SNMPv2-SMI              -- [RFC2578]
    MODULE-COMPLIANCE,
    OBJECT-GROUP          FROM SNMPv2-CONF             -- [RFC2580]
    SnmpAdminString       FROM SNMP-FRAMEWORK-MIB      -- [RFC3411]
    fcmInstanceIndex      FROM FC-MGMT-MIB             -- [RFC4044]
    T11FabricIndex        FROM T11-TC-MIB              -- [RFC4439]
    t11FcSpAuEntityName   FROM T11-FC-SP-AUTHENTICATION-MIB;

t11FcSpCertsMIB  MODULE-IDENTITY
    LAST-UPDATED  "200702190000Z"
    ORGANIZATION  "T11"
    CONTACT-INFO
            "     Claudio DeSanti
                  Cisco Systems, Inc.
                  170 West Tasman Drive
                  San Jose, CA 95134 USA
                  EMail: cds@cisco.com

                  Keith McCloghrie
                  Cisco Systems, Inc.
                  170 West Tasman Drive
                  San Jose, CA 95134 USA
                  Email: kzm@cisco.com"
    DESCRIPTION
           "This MIB module defines management information specific to
           the use of certificates in conjunction with Fibre Channel's
           FC-SP specification.

           Since FC-SP leverages a subset of IPsec and IKEv2 (see RFC
           4595), a subset of the management information defined for
           the use of certificates with IPsec/IKEv2 is also applicable
           to FC-SP.  Thus, this MIB module leverages RFC wwww and
           RFC xxxx for the management of certificates, CAs and CRLs.
-- RFC Editor: replace wwww with actual RFC number for
-- [IPSP-IPSEC-ACTION], and replace xxxx with actual RFC number for
-- [IPSP-IKE-ACTION] & remove this note

           Specifically, the information defined in this MIB module
           consists of a pointer into the IPsec/IKEv2 MIB modules,
           plus minimal additional item(s) of information which are
           considered to be important in a Fibre Channel environment.

           Copyright (C) The IETF Trust (2007).  This version
           of this MIB module is part of RFC yyyy;  see the RFC
           itself for full legal notices."
-- RFC Editor: replace yyyy with actual RFC number & remove this note
    REVISION  "200702190000Z"
    DESCRIPTION
           "Initial version of this MIB module, published as RFCyyyy."
-- RFC-Editor, replace yyyy with actual RFC number & remove this note
    ::= { mib-2 nnn }  -- to be assigned by IANA
-- RFC Editor: replace nnn with IANA-assigned number & remove this note

t11FcSpCertsMIBObjects     OBJECT IDENTIFIER ::= { t11FcSpCertsMIB 1 }
t11FcSpCertsMIBConformance OBJECT IDENTIFIER ::= { t11FcSpCertsMIB 2 }
--
--  Certificate Information
--

t11FcSpCertsTable OBJECT-TYPE
    SYNTAX       SEQUENCE OF T11FcSpCertsEntry
    MAX-ACCESS   not-accessible
    STATUS       current
    DESCRIPTION
           "A table containing information on the use of certificates
           in FC-SP, including (but not limited to) the use of
           certificates with the Fibre Channel Certificate
           Authentication Protocol (FCAP) defined by FC-SP, or with
           FC-SP's use of IKEv2."
    ::= { t11FcSpCertsMIBObjects 1 }

t11FcSpCertsEntry OBJECT-TYPE
    SYNTAX       T11FcSpCertsEntry
    MAX-ACCESS   not-accessible
    STATUS       current
    DESCRIPTION
           "Each entry contains information related to one certificate
           for use by the FC-SP Authentication entity identified by
           t11FcSpAuEntityName, on a particular Fabric, which is managed
           as part of the Fibre Channel management instance identified
           by fcmInstanceIndex."
    INDEX  { fcmInstanceIndex, t11FcSpAuEntityName,
             t11FcSpCertFabricIndex, t11FcSpCertIndex }
    ::= { t11FcSpCertsTable 1 }

T11FcSpCertsEntry ::= SEQUENCE {
    t11FcSpCertFabricIndex    T11FabricIndex,
    t11FcSpCertIndex          Unsigned32,
    t11FcSpCertPointer        SnmpAdminString,
    t11FcSpCertUsage          INTEGER
}

t11FcSpCertFabricIndex OBJECT-TYPE
    SYNTAX       T11FabricIndex
    MAX-ACCESS   not-accessible
    STATUS       current
    DESCRIPTION
           "An index value which uniquely identifies a particular
           Fabric where the certificate is available for use."
    ::= { t11FcSpCertsEntry 1 }

t11FcSpCertIndex OBJECT-TYPE
    SYNTAX       Unsigned32
    MAX-ACCESS   not-accessible
    STATUS       current
    DESCRIPTION
           "This object distinguishes between the multiple certificates
           available for use with FC-SP on a particular Fabric."
    ::= { t11FcSpCertsEntry 2 }

t11FcSpCertPointer OBJECT-TYPE
    SYNTAX       SnmpAdminString (SIZE(0..32))
    MAX-ACCESS   read-only
    STATUS       current
    DESCRIPTION
           "This object contains the 'name' of a row in the
           ipsaCredentialTable, i.e., it points to the certificate which
           is represented by the row of the ipsaCredentialTable for
           which the value of ipsaCredName has the same value as the
           value of this object.  Further information about the
           certificate is available in that row.

           If and when there is no row in the psaCredentialTable for
           this certificate, the value of this object is the zero-length
           string."
    ::= { t11FcSpCertsEntry 3 }

t11FcSpCertUsage OBJECT-TYPE
    SYNTAX       INTEGER {
                     other(1),
                     ownDefaultCert(2),
                     ownCert(3),
                     rootCert(4)
                  }
    MAX-ACCESS   read-only
    STATUS       current
    DESCRIPTION
           "This object identifies how this certificate can be used:

              other -- none of the below;

              ownDefaultCert -- the certificate which the local entity
                       uses as its default certificate; the local entity
                       has at most one default certificate;

              ownCert  -- a certificate which the local entity can use
                       for itself, but which is not its default
                       certificate;

              rootCert -- a root certificate.
            "
    ::= { t11FcSpCertsEntry 4 }

--
-- Conformance
--

t11FcSpCertMIBCompliances
                  OBJECT IDENTIFIER ::= { t11FcSpCertsMIBConformance 1 }
t11FcSpCertMIBGroups
                  OBJECT IDENTIFIER ::= { t11FcSpCertsMIBConformance 2 }

t11FcSpCertMIBCompliance MODULE-COMPLIANCE
    STATUS       current
    DESCRIPTION
           "The compliance statement for entities which use
           certificates with FC-SP."

    MODULE  -- this module
        MANDATORY-GROUPS
            { t11FcSpCertInfoGroup }

    ::= { t11FcSpCertMIBCompliances 1 }

-- Units of Conformance

t11FcSpCertInfoGroup OBJECT-GROUP
    OBJECTS  {
                 t11FcSpCertPointer,
                 t11FcSpCertUsage
             }
    STATUS   current
    DESCRIPTION
           "A collection of objects containing information
           related to certificates available for use with FC-SP."
    ::= { t11FcSpCertMIBGroups 1 }

END

-- 
--    Copyright (C) The IETF Trust (2007).  This document is subject to the
--    rights, licenses and restrictions contained in BCP 78, and except as
--    set forth therein, the authors retain all their rights.
-- 
--    This document and the information contained herein are provided on an
--    "AS IS" basis and THE CONTRIBUTOR, THE ORGANIZATION HE/SHE REPRESENTS
--    OR IS SPONSORED BY (IF ANY), THE INTERNET SOCIETY, THE IETF TRUST AND
--    THE INTERNET ENGINEERING TASK FORCE DISCLAIM ALL WARRANTIES, EXPRESS
--    OR IMPLIED, INCLUDING BUT NOT LIMITED TO ANY WARRANTY THAT THE USE OF
--    THE INFORMATION HEREIN WILL NOT INFRINGE ANY RIGHTS OR ANY IMPLIED
--    WARRANTIES OF MERCHANTABILITY OR FITNESS FOR A PARTICULAR PURPOSE.
-- 
-- Disclaimer of validity
-- 
--    The IETF takes no position regarding the validity or scope of any
--    Intellectual Property Rights or other rights that might be claimed to
--    pertain to the implementation or use of the technology described in
--    this document or the extent to which any license under such rights
--    might or might not be available; nor does it represent that it has
--    made any independent effort to identify any such rights.  Information
--    on the procedures with respect to rights in RFC documents can be
--    found in BCP 78 and BCP 79.
-- 
--    Copies of IPR disclosures made to the IETF Secretariat and any
--    assurances of licenses to be made available, or the result of an
--    attempt made to obtain a general license or permission for the use of
--    such proprietary rights by implementers or users of this
--    specification can be obtained from the IETF on-line IPR repository at
--    http://www.ietf.org/ipr.
-- 
--    The IETF invites any interested party to bring to its attention any
--    copyrights, patents or patent applications, or other proprietary
--    rights that may cover technology that may be required to implement
--    this standard.  Please address the information to the IETF at
--    ietf-ipr@ietf.org.
-- 
-- Acknowledgment
-- 
--    Funding for the RFC Editor function is currently provided by the
--    Internet Society.
