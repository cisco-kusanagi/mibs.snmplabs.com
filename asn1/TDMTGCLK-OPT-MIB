-- Version 2.15.1.1 2001-06-05 14:22:02-04 

        TDMTGCLK-OPT-MIB DEFINITIONS ::= BEGIN

        IMPORTS
		  enterprises FROM RFC1155-SMI
            OBJECT-TYPE
                FROM RFC-1212;

                      codex OBJECT IDENTIFIER ::= { enterprises 449 }
         cdxProductSpecific OBJECT IDENTIFIER ::= { codex 2 }
                    cdx6500 OBJECT IDENTIFIER ::= { cdxProductSpecific 1 }

      cdx6500Configuration  OBJECT IDENTIFIER ::= { cdx6500 2 }
     cdx6500CfgGeneralGroup OBJECT IDENTIFIER ::= { cdx6500Configuration 2 }

          cdx6500Statistics OBJECT IDENTIFIER ::= { cdx6500 3 }
 cdx6500StatOtherStatsGroup OBJECT IDENTIFIER ::= { cdx6500Statistics 2 }
       cdx6500STTdmtgClkGroup OBJECT IDENTIFIER ::= { cdx6500StatOtherStatsGroup 17 } 

        DisplayString ::= OCTET STRING
        -- This data type is used to model textual information taken
        -- from the NVT ASCII character set.  By convention, objects
        -- with this syntax are declared as having SIZE (0..255)

        -- The TDMTG CLOCK  group

        cdx6500TdmtgClkTable OBJECT-TYPE
            SYNTAX SEQUENCE OF Cdx6500TdmtgClkCfgEntry
            ACCESS not-accessible
            STATUS mandatory
            DESCRIPTION
                "A list of Configuration parameters that makeup
                 the TDMTG Clock Table."
        ::= { cdx6500CfgGeneralGroup 29 }

        cdx6500TdmtgClkCfgEntry OBJECT-TYPE
            SYNTAX Cdx6500TdmtgClkCfgEntry 
            ACCESS not-accessible
            STATUS mandatory
            DESCRIPTION
                "Each entry contains the Configuration parameters for
                 each Tdmtg clock table."
            INDEX { cdx6500TdmtgClkEntryNumber }
        ::= { cdx6500TdmtgClkTable 1 }

        Cdx6500TdmtgClkCfgEntry ::=
            SEQUENCE {
                cdx6500TdmtgClkEntryNumber 
                    INTEGER,
                cdx6500TdmtgCardNumber
                    INTEGER,
                cdx6500TdmtgCardClkParticipation
                    INTEGER,
                cdx6500TdmtgGroup1ClkParticipation
                    INTEGER,
                cdx6500TdmtgGroup2ClkParticipation
                    INTEGER,
                cdx6500TdmtgGroup3ClkParticipation
                    INTEGER
                }

        cdx6500TdmtgClkEntryNumber OBJECT-TYPE
            SYNTAX INTEGER 
            ACCESS read-only
            STATUS mandatory
            DESCRIPTION
                "This identifies the particular TDMTG Network Clock Table
                 entry being configured. The number of instances
                 defined by this entry depends on the configured value
                 of the Maximum TDMTG Network Clock Entry parameter in the
                 Node record . "
        ::= { cdx6500TdmtgClkCfgEntry 1 }

        cdx6500TdmtgCardNumber OBJECT-TYPE
            SYNTAX INTEGER
            ACCESS read-only
            STATUS mandatory
            DESCRIPTION
                "Specifies the slot number in which the card resides.
	         Should be Entry No + 1."
        ::= { cdx6500TdmtgClkCfgEntry 2 }

        cdx6500TdmtgCardClkParticipation OBJECT-TYPE
            SYNTAX INTEGER {
		none 	(1),
		system-clock (2) 
                }
            ACCESS read-only
            STATUS mandatory
            DESCRIPTION
                "Specifies whether the card participates in System clock
		   none : Card does not participate in System clock
		   system-clock : Card participates in System clock."
        ::= { cdx6500TdmtgClkCfgEntry 3 }

       cdx6500TdmtgGroup1ClkParticipation OBJECT-TYPE 
            SYNTAX INTEGER {
                   group-clock (1),
		   card-clock  (2)
		}  
            ACCESS read-only
            STATUS mandatory
            DESCRIPTION
                "Specifies whether this group participates in Card Clock
		   group-clock : Group does not participate in Card clock
		   card-clock : Group participates in Card clock." 
        ::= { cdx6500TdmtgClkCfgEntry 4 }

       cdx6500TdmtgGroup2ClkParticipation OBJECT-TYPE
            SYNTAX INTEGER {
                   group-clock (1),
                   card-clock  (2)
                }
            ACCESS read-only
            STATUS mandatory
            DESCRIPTION
                "Specifies whether this group participates in Card Clock
                   group-clock : Group does not participate in Card clock
                   card-clock : Group participates in Card clock."
        ::= { cdx6500TdmtgClkCfgEntry 5 }

       cdx6500TdmtgGroup3ClkParticipation OBJECT-TYPE
            SYNTAX INTEGER {
                   group-clock (1),
                   card-clock  (2)
                }
            ACCESS read-only
            STATUS mandatory
            DESCRIPTION
                "Specifies whether this group participates in Card Clock
                   group-clock : Group does not participate in Card clock
                   card-clock : Group participates in Card clock."
        ::= { cdx6500TdmtgClkCfgEntry 6 }

        -- the TDMTG Clock Statistics Group for a restoral port

       cdx6500TdmtgStatSystemClkStatus  OBJECT-TYPE
            SYNTAX DisplayString (SIZE(0..255))
            ACCESS read-only
            STATUS optional
            DESCRIPTION
                "The Status of Current System Clock." 
        ::= { cdx6500STTdmtgClkGroup 1 }

       cdx6500TdmtgStatCardClkRegisteredTable OBJECT-TYPE
            SYNTAX SEQUENCE OF Cdx6500TdmtgStatClkRegisteredEntry 
            ACCESS not-accessible
            STATUS mandatory
            DESCRIPTION
                 "The Table of registered Card Clock Number."
        ::= { cdx6500STTdmtgClkGroup 2 }

        cdx6500TdmtgStatClkRegisteredEntry OBJECT-TYPE
            SYNTAX Cdx6500TdmtgStatClkRegisteredEntry
            ACCESS not-accessible
            STATUS mandatory
            DESCRIPTION
                "Each entry contains the Registered Card Clock." 
            INDEX { cdx6500TdmtgStatClkRegisteredEntryNumber }
        ::= { cdx6500TdmtgStatCardClkRegisteredTable 1 }

        Cdx6500TdmtgStatClkRegisteredEntry ::=
            SEQUENCE {
                cdx6500TdmtgStatClkRegisteredEntryNumber
                    INTEGER,
                cdx6500TdmtgStatCardClkRegistered 
                    DisplayString 
                }

        cdx6500TdmtgStatClkRegisteredEntryNumber OBJECT-TYPE
            SYNTAX INTEGER 
            ACCESS read-only
            STATUS mandatory
            DESCRIPTION
                "This identifies the particular cdx6500TdmtgStatCardClkRegisteredTable."
        ::= { cdx6500TdmtgStatClkRegisteredEntry 1 }
 
       cdx6500TdmtgStatCardClkRegistered OBJECT-TYPE
            SYNTAX DisplayString 
            ACCESS read-only
            STATUS optional
            DESCRIPTION
                "The status of current Registered Card Clock."
        ::= { cdx6500TdmtgStatClkRegisteredEntry 2 }

       cdx6500TdmtgStatGroupCardClkRegisteredTable OBJECT-TYPE
            SYNTAX SEQUENCE OF Cdx6500TdmtgStatGroupClkRegisteredEntry 
            ACCESS not-accessible
            STATUS mandatory
            DESCRIPTION
                 "The Table of registered Group Card Number."
        ::= { cdx6500STTdmtgClkGroup 3 }

        cdx6500TdmtgStatGroupClkRegisteredEntry OBJECT-TYPE
            SYNTAX Cdx6500TdmtgStatGroupClkRegisteredEntry
            ACCESS not-accessible
            STATUS mandatory
            DESCRIPTION
                "Each entry contains the Registered Group Card Clock."
            INDEX {cdx6500TdmtgStatClkEntryNumber, 
                   cdx6500TdmtgStatGroupClkRegisteredEntryNumber }
        ::= { cdx6500TdmtgStatGroupCardClkRegisteredTable 1 }

        Cdx6500TdmtgStatGroupClkRegisteredEntry ::=
            SEQUENCE {
                cdx6500TdmtgStatClkEntryNumber
                    INTEGER,
                cdx6500TdmtgStatGroupClkRegisteredEntryNumber 
                    INTEGER,
                cdx6500TdmtgStatGroupCardClkRegistered
                    DisplayString
                }

        cdx6500TdmtgStatClkEntryNumber OBJECT-TYPE
            SYNTAX INTEGER
            ACCESS read-only
            STATUS mandatory
            DESCRIPTION
                "This identifies the particular cdx6500TdmtgStatGroupCardClkRegisteredTable."
        ::= { cdx6500TdmtgStatGroupClkRegisteredEntry 1 }

        cdx6500TdmtgStatGroupClkRegisteredEntryNumber OBJECT-TYPE
            SYNTAX INTEGER
            ACCESS read-only
            STATUS mandatory
            DESCRIPTION
                "This identifies the particular cdx6500TdmtgStatGroupCardClkRegisteredTable."
        ::= { cdx6500TdmtgStatGroupClkRegisteredEntry 2 }

       cdx6500TdmtgStatGroupCardClkRegistered OBJECT-TYPE
            SYNTAX DisplayString
            ACCESS read-only
            STATUS optional
            DESCRIPTION
                "The status of current Registered Group Card Clock."
        ::= { cdx6500TdmtgStatGroupClkRegisteredEntry 3 }

    END
