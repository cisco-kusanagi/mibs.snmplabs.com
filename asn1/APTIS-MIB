--	Aptis Enterprise MIB (V2 SMI)
--
--	Nortel Networks
--	11 Elizabeth Drive
--	Chelmsford, MA 01824
--
--	Copyright (c) 1997-2000 Nortel Networks
--	All Rights Reserved.
--
--	See also: aptis_reg.mi2, aptis_config.mi2, aptis_monitoring.mi2 aptis_actions.mi2
--		  aptis_traps.mi2
--

APTIS-MIB DEFINITIONS ::= BEGIN

	IMPORTS
	    enterprises, MODULE-IDENTITY, OBJECT-IDENTITY
	        FROM SNMPv2-SMI
	    OBJECT-TYPE
	        FROM SNMPv2-SMI
	    TEXTUAL-CONVENTION
	        FROM SNMPv2-TC;

--
--	Delete the MODULE-IDENTITY if your SNMP tools don't like it.
--	

	aptisRootModule MODULE-IDENTITY
        LAST-UPDATED "0004140000Z"
        ORGANIZATION "Nortel Networks"
        CONTACT-INFO
            "   Technical Support/Customer Service
                Nortel Networks

                Postal: 11 Elizabeth Drive
                        Chelmsford, MA 01824

                Tel:
                In the USA: Dial 1-800-758-4827 to contact a Technical Support engineer.
                Outside the USA:  Contact your Regional Nortel Networks Support Prime.

                For information about the Nortel Networks Network Access Division,
                go to the World Wide Web (WWW) site at http://www.nortelnetworks.com."

		DESCRIPTION
			"Nortel Networks Aptis Enterprise MIB"

	::= { enterprises aptis(2637) aptis-reg(1) aptis-modules(1) 1 }


--	
--	Textual Conventions used in Aptis-MIB
--

	Boolean ::= TEXTUAL-CONVENTION
	    STATUS	current
	    DESCRIPTION	
		"A version of TruthValue that makes sense, corresponding
		to the natural values of true(1) and false(0)."
	    SYNTAX	INTEGER { false(0), true(1) }



	aptis OBJECT-IDENTITY
		STATUS 		current
		DESCRIPTION
			"The root of the sub-tree assigned to Aptis
			by the Internet Assigned Numbers Authority (IANA)."

	::= { enterprises 2637 }

--
--	This subtree is defined in aptis_reg.mib
--

	aptis-reg OBJECT-IDENTITY
		STATUS 		current
		DESCRIPTION
			"Sub-tree for registrations, including product 
			and individual system boards."

		::= { aptis 1 }

	aptis-generic OBJECT-IDENTITY
		STATUS current
		DESCRIPTION
			"Sub-tree for common object and event definitions."

		::= { aptis 2 }

	aptis-products OBJECT-IDENTITY
		STATUS current
		DESCRIPTION
			"Sub-tree for product-specific object and event 
			definitions."

		::= { aptis 3 }

--
--	Here are the top level generic subtrees, supported by all Aptis
--	products.   
--

--
--	This subtree is defined in aptis_config.mib
--

	aptis-config 		OBJECT-IDENTITY
		STATUS 		current
		DESCRIPTION
			"The collection of tables that make up the 
			persistent configuration of the system."

		::= { aptis-generic 1 }

--
--	This subtree is defined in aptis_monitoring.mib
--

	aptis-monitoring	OBJECT-IDENTITY
		STATUS		current
		DESCRIPTION
			"The collection of tables that allows monitoring
			of the dynamic state of the system."

		::= { aptis-generic 2 }

--
--	This subtree is defined in aptis_actions.mib
--

	aptis-actions		OBJECT-IDENTITY
		STATUS		current
		DESCRIPTION
			"This subtree contains variables which allow a
			management station to invoke certain administrative
			actions such as file transfers, etc.  These variables
			correspond to action commands in the CLI."

		::= { aptis-generic 3 }


	aptis-exp		OBJECT-IDENTITY
		STATUS		current
		DESCRIPTION
			"This subtree contains variables which are currently
			being tested and are not yet fully supported."

		::= { aptis-generic 4 }

--
--	This subtree is defined in aptis_traps.mib
--


	aptis-traps		OBJECT-IDENTITY
		STATUS		current
		DESCRIPTION
			"This subtree contains the aptis specific traps."

		::= { aptis-generic 5 }


--
--


	config-sync		OBJECT-IDENTITY
		STATUS		current
		DESCRIPTION
			"These variables are returned in SNMP Set Reply packets that modify 
			configuration, allowing the NMS to keep its configuration database
			synchronized with the switch.  They describe the state of the config
			database before and after a transaction that corresponds to an SNMP
			SET REQUEST.  These values only have meaning when appended to a SET-REPLY
			PDU."

		::= { aptis-exp 2 }


	prevGenNum		OBJECT-TYPE
		SYNTAX		INTEGER (0..2147483647)
		MAX-ACCESS	read-only
		STATUS		current
		DESCRIPTION	
			"The value of the database subtree's GenNum before the transaction
			was applied."

	::= { config-sync 1 }
					

	deltaCount		OBJECT-TYPE
		SYNTAX		INTEGER (0..2147483647)
		MAX-ACCESS	read-only
		STATUS		current
		DESCRIPTION	
			"The expected delta to the database subtree's GenNum value as a 
			result of the transaction in question."

	::= { config-sync 2 }

	currentGenNum		OBJECT-TYPE
		SYNTAX		INTEGER (0..2147483647)
		MAX-ACCESS	read-only
		STATUS		current
		DESCRIPTION	
			"The resulting value of the database subtree's GenNum after the 
			transaction has been applied."

	::= { config-sync 3 }

END
