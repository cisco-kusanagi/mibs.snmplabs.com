RIVERSTONE-TC-MIB DEFINITIONS ::= BEGIN

--  This module provides textual conventions used by Riverstone
--  Network's enterprise-specific SNMP API.
--
--  This module will be extended, as required.
--  Riverstone Networks reserves the right to make changes in
--  specification and other information contained in this document
--  without prior notice.  The reader should consult Riverstone Networks
--  to determine whether any such changes have been made.
--
--  In no event shall Riverstone Networks be liable for any incidental,
--  indirect, special, or consequential damages whatsoever (including
--  but not limited to lost profits) arising out of or related to this
--  document or the information contained in it, even if Riverstone
--  Networks has been advised of, known, or should have known, the
--  possibility of such damages.
--
--  Riverstone grants vendors, end-users, and other interested parties
--  a non-exclusive license to use this Specification in connection
--  with the management of Riverstone's products.
 
IMPORTS

    MODULE-IDENTITY
        FROM SNMPv2-SMI
    TEXTUAL-CONVENTION
        FROM SNMPv2-TC
    riverstoneMibs
        FROM RIVERSTONE-SMI-MIB;

rsTCMIB MODULE-IDENTITY  
    LAST-UPDATED "200206170000Z"  -- June 17, 2002
    ORGANIZATION "Riverstone Networks, Inc."
    CONTACT-INFO
    "Riverstone Networks, Inc
     5200 Great America Parkway
     Santa Clara, CA 95054
     (408) 878-6500
     nms-eng@riverstonenet.com
     http://www.riverstonenet.com"

    DESCRIPTION
         "This mib module defines the textual conventions used in
          various other Riverstone MIBs."

    REVISION     "200206170000Z"
    DESCRIPTION
         "Revision #2. RsQueuePolicy, RsDiscardPolicy textual 
          conventions added. These are used by RIVERSTONE-QUEUE-MIB."

    REVISION     "200203250000Z"
    DESCRIPTION
         "Revision #1. Provide textual conventions used in 
          RIVERSTONE-CONFIG-MIB. (hgr)"

 ::= { riverstoneMibs 10 }

RSConfigErrorCode ::= TEXTUAL-CONVENTION
       STATUS       current
       DESCRIPTION
        "A unique value, greater than zero defining the config file 
         transfer operation completion status."
       SYNTAX       INTEGER {
                      noStatus(1),
                      timeout(2),
                      networkError(3),
                      noSpace(4),
		      invalidConfig(5),
                      commandCompleted(6),
	              internalError(7),
                      tftpServerError(8)
                }

RSFileTransferProtocol ::= TEXTUAL-CONVENTION
       STATUS       current
       DESCRIPTION
        "A unique value, greater than zero defining the protocol used
         for file transfer operation on config files.  This list may
         be modified for later additions."
       SYNTAX       INTEGER {
                      other(1),
                      tftp(2),
                      rsh(3),
                      scp(4)
                }

RSTransferStatus ::= TEXTUAL-CONVENTION
       STATUS       current
       DESCRIPTION
        "A unique value, greater than zero defining the status of the
         previous transfer operation, if any."
       SYNTAX       INTEGER {
                      idle(1),
                      sending(2),
                      receiving(3),
                      transferComplete(4),
		      error(5)
                }

RSChangeSessionType ::= TEXTUAL-CONVENTION
       STATUS       current
       DESCRIPTION
        "A unique value, representing the session type of the change
         session."
       SYNTAX       INTEGER {
                      unknown(0),
                      other(1),
                      console(2),  -- Change done by console user
                      telnet(3),   -- Change done in a telnet session
                      ssh(4),      -- Change done in a ssh session
                      snmp(5)      -- Change done by snmp request
                }

RsQueuePolicy ::= TEXTUAL-CONVENTION
    STATUS current
    DESCRIPTION
        "The queuing policy for each port is by default priority queuing.
        In priority queuing, each flow is assigned a priority. The higher 
	priority flows go first. Within the priority queue, the flows 
	are serviced in a first in first out order. If the higher priority 
	queue is never empty, the other queues would starve. In fair
	queuing, each priority queue is serviced in a round-robin fashion. 
	Weighted fair queuing is fair queing for which each queue is 
	weighted. On the RS platform, priorityQueuing is known as 
	strict priority (SP)."

    SYNTAX INTEGER {
        unknown(0),
        priorityQueuing(1),
	fairQueuing(2),
        weightedFairQueuing(3)
    }

RsDiscardPolicy ::= TEXTUAL-CONVENTION
    STATUS current
    DESCRIPTION
	"The policy used by a queue to determine how frames should
	be dropped."
    SYNTAX INTEGER {
	unknown(0),
        lastInFirstOut(1),
	randomEarlyDetection(2),
	weightedRandomEarlyDetection(3)
    }

END
