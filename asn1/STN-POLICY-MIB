-- *****************************************************************
--
-- stn-pm.mib:  
--                Spring Tide Networks Policy MIB file.
--
--
--      Copyright (c) 2000 by Spring Tide Networks, Inc.
--                      ALL RIGHTS RESERVED       
--
-- *****************************************************************

-- MIB Object definitions for Spring Tide Network Policy Manager


STN-POLICY-MIB DEFINITIONS ::= BEGIN

    IMPORTS
	TEXTUAL-CONVENTION FROM SNMPv2-TC
        NOTIFICATION-TYPE, MODULE-IDENTITY,
        OBJECT-TYPE,
        IpAddress,
        Integer32,
        Unsigned32, 
        Counter32,
        Counter64,
        Gauge32
                FROM SNMPv2-SMI

        RowStatus,
        TimeStamp,
        TruthValue,
        DisplayString
                FROM SNMPv2-TC

        MODULE-COMPLIANCE 
                FROM SNMPv2-CONF

        InterfaceIndex
                FROM IF-MIB

        stnSystems
                FROM SPRING-TIDE-NETWORKS-SMI

        stnRouterIndex
                FROM STN-ROUTER-MIB;


    stnPm MODULE-IDENTITY
        LAST-UPDATED    "0012060000Z"
        ORGANIZATION    "Spring Tide Networks, Inc."
        CONTACT-INFO
                "
                Spring Tide Networks, Inc.
                Customer Service
                Postal: 3 Clock Tower Place
                        Maynard, MA 01754
                Tel:    1 888-786-4357
                Email:  stncs@springtidenet.com
                "
        DESCRIPTION     "Added stnPmClassTable"
        REVISION        "0005120000Z"
        DESCRIPTION
                "This MIB module describes managed objects of
                Spring Tide Networks policy module ."
        ::= { stnSystems 11 }


    --
    -- Top Level STN PM MIB Objects
    --
    stnPmObjects                OBJECT IDENTIFIER ::= { stnPm 1 }
    stnPmMibConformance         OBJECT IDENTIFIER ::= { stnPm 2 }

    stnPmService                OBJECT IDENTIFIER ::= { stnPmObjects 1 }
    stnPmPolicy                 OBJECT IDENTIFIER ::= { stnPmObjects 2 }
    stnPmPreference             OBJECT IDENTIFIER ::= { stnPmObjects 3 }
    stnPmIPsec                  OBJECT IDENTIFIER ::= { stnPmObjects 4 }
    stnPmEncaps                 OBJECT IDENTIFIER ::= { stnPmObjects 5 }
    stnPmManualSa               OBJECT IDENTIFIER ::= { stnPmObjects 6 }
    stnPmMarker                 OBJECT IDENTIFIER ::= { stnPmObjects 7 }
    stnPmProfile                OBJECT IDENTIFIER ::= { stnPmObjects 8 }
    stnPmQueue                  OBJECT IDENTIFIER ::= { stnPmObjects 9 }

    stnPmTraps                  OBJECT IDENTIFIER ::= { stnPmObjects 10 }
    stnPmFirewall               OBJECT IDENTIFIER ::= { stnPmObjects 11 }
    stnPmFirewallAction         OBJECT IDENTIFIER ::= { stnPmObjects 12 }
    stnPmServiceList            OBJECT IDENTIFIER ::= { stnPmObjects 13 }
    stnPmSLService              OBJECT IDENTIFIER ::= { stnPmObjects 14 }
    stnPmClass                  OBJECT IDENTIFIER ::= { stnPmObjects 15 }
    stnPMProxyTunnel            OBJECT IDENTIFIER ::= { stnPmObjects 16 }

    stnPmFirewallTrap           OBJECT IDENTIFIER ::= { stnPmTraps 1 }
    stnPmQosTrap                OBJECT IDENTIFIER ::= { stnPmTraps 2 }

    --
    -- Top Level STN PM Firewall Trap MIB Objects
    --
    stnPmFirewallTrapVars               OBJECT IDENTIFIER ::= { stnPmFirewallTrap 1 }
    stnPmFirewallNotificationPrefix     OBJECT IDENTIFIER ::= { stnPmFirewallTrap 2 }
    stnPmFirewallNotification           OBJECT IDENTIFIER ::= { stnPmFirewallNotificationPrefix 0 }

    --
    -- Top Level STN PM QoS Trap MIB Objects
    --
    stnPmQosTrapVars               OBJECT IDENTIFIER ::= { stnPmQosTrap 1 }
    stnPmQosNotificationPrefix     OBJECT IDENTIFIER ::= { stnPmQosTrap 2 }
    stnPmQosNotification           OBJECT IDENTIFIER ::= { stnPmQosNotificationPrefix 0 }

    -- Additional STN PM MIB Textual Conventions
    StnPmPolicyMatchType ::= TEXTUAL-CONVENTION
        STATUS      current
        DESCRIPTION "Types of match criteria for policy"
        SYNTAX         INTEGER {
                           any(1),
                           single(2),
                           range(3),
                           dynamic(4),
                           subnet(5)
                       }

    StnPmSelectorType ::= TEXTUAL-CONVENTION
        STATUS         current
        DESCRIPTION    "Selector type to use for connection"
        SYNTAX         INTEGER {
                            policy(1),
                            packet(2)
                        }

    StnPmAuthAlg ::= TEXTUAL-CONVENTION
        STATUS          current
        DESCRIPTION     "Types of authentication algorithms"
        SYNTAX          INTEGER {
                            none(1),
                            hmac-md5(2),
                            hmac-sha(3)
                        }

    StnPmEncrAlg ::= TEXTUAL-CONVENTION
        STATUS          current
        DESCRIPTION     "Types of encryption algorithms"
        SYNTAX          INTEGER {
                            none(1),
                            des(2),
                            des3(3)
                        }

    StnPmDirection ::= TEXTUAL-CONVENTION
        STATUS          current
        DESCRIPTION     "Types of directions"
        SYNTAX          INTEGER {
                            inbound(1),
                            outbound(2)
                        }

    StnPmBitRate ::= TEXTUAL-CONVENTION
        STATUS          current
        DESCRIPTION     "A data rate in bits/second."
        SYNTAX          Integer32 (0..'7FFFFFFF'h)

    --
    -- STN PM service table
    --

    stnPmServiceTable OBJECT-TYPE
        SYNTAX        SEQUENCE OF StnPmServiceEntry
        MAX-ACCESS    not-accessible
        STATUS        current
        DESCRIPTION   "A list of PM service entries."
        ::= { stnPmService 1 }
 
    stnPmServiceEntry OBJECT-TYPE
        SYNTAX          StnPmServiceEntry
        MAX-ACCESS      not-accessible
        STATUS          current
        DESCRIPTION     "Entry contains information about a particular 
                        policy manager service."  
        INDEX           { stnPmServiceIndex }
        ::= { stnPmServiceTable 1 }
 
    StnPmServiceEntry ::= 
        SEQUENCE {
                 stnPmServiceIndex              Integer32,
                 stnPmServiceName               DisplayString,
                 stnPmServiceIdleTimeout        Integer32,
                 stnPmServiceNumPolicies        Integer32,
                 stnPmServiceEnabled            TruthValue,
                 stnPmServiceType               INTEGER,
                 stnPmServiceFirewallID         Integer32
        }       

    stnPmServiceIndex OBJECT-TYPE
        SYNTAX          Integer32
        MAX-ACCESS      read-only
        STATUS          current
        DESCRIPTION     "Index into service table"
        ::= { stnPmServiceEntry 1 }

    stnPmServiceName OBJECT-TYPE
        SYNTAX          DisplayString (SIZE(0..65))
        MAX-ACCESS      read-only
        STATUS          current
        DESCRIPTION     "Name of service"
        ::= { stnPmServiceEntry 2 }

    stnPmServiceIdleTimeout OBJECT-TYPE
        SYNTAX          Integer32
        MAX-ACCESS      read-only
        STATUS          current
        DESCRIPTION     "Idle timeout for service"
        ::= { stnPmServiceEntry 3 }

    stnPmServiceNumPolicies OBJECT-TYPE
        SYNTAX          Integer32
        MAX-ACCESS      read-only
        STATUS          current
        DESCRIPTION     "Number of policies in this service"
        ::= { stnPmServiceEntry 4 }

    stnPmServiceEnabled OBJECT-TYPE
        SYNTAX          TruthValue
        MAX-ACCESS      read-only
        STATUS          current
        DESCRIPTION     "Flag to indicate if service is enabled"
        ::= { stnPmServiceEntry 5 }

    stnPmServiceType OBJECT-TYPE
        SYNTAX          INTEGER {
                            vpn(1),
                            firewall(2),
                            ip-fileter(3),
                            forwarding(4),
                            qos(5),
                            mpls(6)
                        }
        MAX-ACCESS      read-only
        STATUS          current
        DESCRIPTION     "Type of service"
        ::= { stnPmServiceEntry 7 }

    stnPmServiceFirewallID OBJECT-TYPE
        SYNTAX          Integer32
        MAX-ACCESS      read-only
        STATUS          current
        DESCRIPTION     "Instance of service's firewall record"
        ::= { stnPmServiceEntry 8 }


    --
    -- STN PM Policy Table
    --

    stnPmPolicyTable OBJECT-TYPE
        SYNTAX        SEQUENCE OF StnPmPolicyEntry
        MAX-ACCESS    not-accessible
        STATUS        current
        DESCRIPTION   "A list of policy entries."
        ::= { stnPmPolicy 1 }
 
    stnPmPolicyEntry OBJECT-TYPE
        SYNTAX          StnPmPolicyEntry
        MAX-ACCESS      not-accessible
        STATUS          current
        DESCRIPTION     "Entry contains information about a particular 
                        policy."
        INDEX           { stnPmPolicyServiceIndex, 
                          stnPmPolicyIndex }
        ::= { stnPmPolicyTable 1 }
 
    StnPmPolicyEntry ::= 
        SEQUENCE {
                stnPmPolicyServiceIndex             Integer32,
                stnPmPolicyIndex                    Integer32,
                stnPmPolicyName                     DisplayString,
                stnPmPolicySrcAddrMatchType         StnPmPolicyMatchType,
                stnPmPolicySrcAddr                  IpAddress,
                stnPmPolicySrcMask                  IpAddress,
                stnPmPolicySrcEndAddr               IpAddress,
                stnPmPolicyDestAddrMatchType        StnPmPolicyMatchType,
                stnPmPolicyDestAddr                 IpAddress,
                stnPmPolicyDestMask                 IpAddress,
                stnPmPolicyDestEndAddr              IpAddress,
                stnPmPolicySrcPortMatchType         StnPmPolicyMatchType,
                stnPmPolicySrcPort                  Integer32,
                stnPmPolicySrcEndPort               Integer32,
                stnPmPolicyDestPortMatchType        StnPmPolicyMatchType,
                stnPmPolicyDestPort                 Integer32,
                stnPmPolicyDestEndPort              Integer32,
                stnPmPolicyProtocolMatchType        StnPmPolicyMatchType,
                stnPmPolicyProtocol                 INTEGER,
                stnPmPolicyAction                   INTEGER,
                stnPmPolicyActionID                 Integer32,
                stnPmPolicyDirection                StnPmDirection,
                stnPmPolicyCreateMirror             TruthValue,
                stnPmPolicySrcAddrSelector          StnPmSelectorType,
                stnPmPolicyDestAddrSelector         StnPmSelectorType,
                stnPmPolicyEnabled                  TruthValue,
                stnPmPolicyMatches                  Integer32,
                stnPmPolicyMisses                   Integer32,
                stnPmPolicyMarkedOctets             Counter64,
                stnPmPolicyMarkedPkts               Counter64,
                stnPmPolicyIcmpTypes                Unsigned32,
                stnPmPolicyTosByteMatchType         StnPmPolicyMatchType,
                stnPmPolicyTosByteValue             INTEGER,
                stnPmPolicyTosByteMask              INTEGER,
                stnPmPolicyMarkerID                 Integer32,
                stnPmPolicyTxclassID                Integer32
        }


    stnPmPolicyServiceIndex OBJECT-TYPE
        SYNTAX          Integer32
        MAX-ACCESS      read-only
        STATUS          current
        DESCRIPTION     "Service index of policy"
        ::= { stnPmPolicyEntry 1 }

    stnPmPolicyIndex OBJECT-TYPE
        SYNTAX          Integer32
        MAX-ACCESS      read-only
        STATUS          current
        DESCRIPTION     "Policy index of policy"
        ::= { stnPmPolicyEntry 2 }

    stnPmPolicyName OBJECT-TYPE
        SYNTAX          DisplayString (SIZE(0..65))
        MAX-ACCESS      read-only
        STATUS          current
        DESCRIPTION     "Policy name"
        ::= { stnPmPolicyEntry 3 }

    stnPmPolicySrcAddrMatchType OBJECT-TYPE
        SYNTAX          StnPmPolicyMatchType
        MAX-ACCESS      read-only
        STATUS          current
        DESCRIPTION     "Type of match for source address"
        ::= { stnPmPolicyEntry 4 }

    stnPmPolicySrcAddr OBJECT-TYPE
        SYNTAX          IpAddress
        MAX-ACCESS      read-only
        STATUS          current
        DESCRIPTION     "Source address to match"
        ::= { stnPmPolicyEntry 5 }

    stnPmPolicySrcMask OBJECT-TYPE
        SYNTAX          IpAddress
        MAX-ACCESS      read-only
        STATUS          current
        DESCRIPTION     "Source IP netmask to match"
        ::= { stnPmPolicyEntry 6 }

    stnPmPolicySrcEndAddr OBJECT-TYPE
        SYNTAX          IpAddress
        MAX-ACCESS      read-only
        STATUS          current
        DESCRIPTION     "End of source address range to match"
        ::= { stnPmPolicyEntry 7 }

    stnPmPolicyDestAddrMatchType OBJECT-TYPE
        SYNTAX          StnPmPolicyMatchType
        MAX-ACCESS      read-only
        STATUS          current
        DESCRIPTION     "Type of match for source address"
        ::= { stnPmPolicyEntry 8 }

    stnPmPolicyDestAddr OBJECT-TYPE
        SYNTAX          IpAddress
        MAX-ACCESS      read-only
        STATUS          current
        DESCRIPTION     "Source address to match"
        ::= { stnPmPolicyEntry 9 }

    stnPmPolicyDestMask OBJECT-TYPE
        SYNTAX          IpAddress
        MAX-ACCESS      read-only
        STATUS          current
        DESCRIPTION     "Source IP netmask to match"
        ::= { stnPmPolicyEntry 10 }

    stnPmPolicyDestEndAddr OBJECT-TYPE
        SYNTAX          IpAddress
        MAX-ACCESS      read-only
        STATUS          current
        DESCRIPTION     "End of source address range to match"
        ::= { stnPmPolicyEntry 11 }

    stnPmPolicySrcPortMatchType OBJECT-TYPE
        SYNTAX          StnPmPolicyMatchType
        MAX-ACCESS      read-only
        STATUS          current
        DESCRIPTION     "Type of match for source port"
        ::= { stnPmPolicyEntry 12 }

    stnPmPolicySrcPort OBJECT-TYPE
        SYNTAX          Integer32
        MAX-ACCESS      read-only
        STATUS          current
        DESCRIPTION     "Source port to match"
        ::= { stnPmPolicyEntry 13 }

    stnPmPolicySrcEndPort OBJECT-TYPE
        SYNTAX          Integer32
        MAX-ACCESS      read-only
        STATUS          current
        DESCRIPTION     "End of source port range to match"
        ::= { stnPmPolicyEntry 14 }

    stnPmPolicyDestPortMatchType OBJECT-TYPE
        SYNTAX          StnPmPolicyMatchType
        MAX-ACCESS      read-only
        STATUS          current
        DESCRIPTION     "Type of match for destination port"
        ::= { stnPmPolicyEntry 15 }

    stnPmPolicyDestPort OBJECT-TYPE
        SYNTAX          Integer32
        MAX-ACCESS      read-only
        STATUS          current
        DESCRIPTION     "Destination port to match"
        ::= { stnPmPolicyEntry 16 }

    stnPmPolicyDestEndPort OBJECT-TYPE
        SYNTAX          Integer32
        MAX-ACCESS      read-only
        STATUS          current
        DESCRIPTION     "End of destination port range to match"
        ::= { stnPmPolicyEntry 17 }

    stnPmPolicyProtocolMatchType OBJECT-TYPE
        SYNTAX          StnPmPolicyMatchType
        MAX-ACCESS      read-only
        STATUS          current
        DESCRIPTION     "Type of match for protocol"
        ::= { stnPmPolicyEntry 18 }

    stnPmPolicyProtocol OBJECT-TYPE
        SYNTAX          INTEGER {
                            icmp(1),
                            tcp(6),
                            udp(17),
                            esp(50),
                            ah(51),
                            ipcomp(108)
                        }
        MAX-ACCESS      read-only
        STATUS          current
        DESCRIPTION     "Protocol to match"
        ::= { stnPmPolicyEntry 19 }

    stnPmPolicyAction OBJECT-TYPE
        SYNTAX          INTEGER {
                            deny(1),
                            permit(2),
                            secure(3),
                            encaps(4),
                            reject(5),
                            fec(6)
                        }
        MAX-ACCESS      read-only
        STATUS          current
        DESCRIPTION     "Type of action to take upon policy match"
        ::= { stnPmPolicyEntry 20 }

    stnPmPolicyActionID OBJECT-TYPE
        SYNTAX          Integer32
        MAX-ACCESS      read-only
        STATUS          current
        DESCRIPTION     "Configuration ID of action record"
        ::= { stnPmPolicyEntry 21 }

    stnPmPolicyDirection OBJECT-TYPE
        SYNTAX          StnPmDirection
        MAX-ACCESS      read-only
        STATUS          current
        DESCRIPTION     "Direction of policy"
        ::= { stnPmPolicyEntry 22 }

    stnPmPolicyCreateMirror OBJECT-TYPE     
        SYNTAX          TruthValue
        MAX-ACCESS      read-only
        STATUS          current
        DESCRIPTION     "Mirror policy flag"
        ::= { stnPmPolicyEntry 23 }

    stnPmPolicySrcAddrSelector OBJECT-TYPE
        SYNTAX          StnPmSelectorType
        MAX-ACCESS      read-only
        STATUS          current
        DESCRIPTION     "Source selector to choose for policy matching"
        ::= { stnPmPolicyEntry 24 }

    stnPmPolicyDestAddrSelector OBJECT-TYPE
        SYNTAX          StnPmSelectorType
        MAX-ACCESS      read-only
        STATUS          current
        DESCRIPTION     "Destination selector to choose for policy matching"
        ::= { stnPmPolicyEntry 25 }

    stnPmPolicyEnabled OBJECT-TYPE
        SYNTAX          TruthValue
        MAX-ACCESS      read-only
        STATUS          current
        DESCRIPTION     "Flag to indicate if policy is enabled"
        ::= { stnPmPolicyEntry 26 }

    stnPmPolicyMatches OBJECT-TYPE
        SYNTAX          Integer32
        MAX-ACCESS      read-only
        STATUS          current
        DESCRIPTION     "Number of times policy search matched this policy"
        ::= { stnPmPolicyEntry 27 }

    stnPmPolicyMisses OBJECT-TYPE
        SYNTAX          Integer32
        MAX-ACCESS      read-only
        STATUS          current
        DESCRIPTION     "Number of times policy search did not match this 
                         policy"
        ::= { stnPmPolicyEntry 28 }

    stnPmPolicyMarkedOctets OBJECT-TYPE
        SYNTAX          Counter64
        MAX-ACCESS      read-only
        STATUS          current
        DESCRIPTION     "Number of octets that have been marked for this 
                         policy."
        ::= { stnPmPolicyEntry 29 }

    stnPmPolicyMarkedPkts OBJECT-TYPE
        SYNTAX          Counter64
        MAX-ACCESS      read-only
        STATUS          current
        DESCRIPTION     "Number of packets that have been marked for this 
                         policy."
        ::= { stnPmPolicyEntry 30 }

    stnPmPolicyIcmpTypes OBJECT-TYPE
        SYNTAX          Unsigned32
        MAX-ACCESS      read-only
        STATUS          current
        DESCRIPTION     "ICMP Types matching the policy entry expressed as 
                         bit-map."
        ::= { stnPmPolicyEntry 31 }

    stnPmPolicyTosByteMatchType OBJECT-TYPE
        SYNTAX          StnPmPolicyMatchType
        MAX-ACCESS      read-only
        STATUS          current
        DESCRIPTION     "Type of match for TOS Byte"
        ::= { stnPmPolicyEntry 32 }

    stnPmPolicyTosByteValue OBJECT-TYPE
        SYNTAX          INTEGER
        MAX-ACCESS      read-only
        STATUS          current
        DESCRIPTION     "Value containing bits to set in TOS Byte"
        ::= { stnPmPolicyEntry 33 }

    stnPmPolicyTosByteMask OBJECT-TYPE
        SYNTAX          INTEGER
        MAX-ACCESS      read-only
        STATUS          current
        DESCRIPTION     "Mask indicating bits to match in TOS byte"
        ::= { stnPmPolicyEntry 34 }

    stnPmPolicyMarkerID OBJECT-TYPE
        SYNTAX          Integer32
        MAX-ACCESS      read-only
        STATUS          current
        DESCRIPTION     "Configuration ID of marker to apply"
        ::= { stnPmPolicyEntry 35 }

    stnPmPolicyTxclassID OBJECT-TYPE
        SYNTAX          Integer32
        MAX-ACCESS      read-only
        STATUS          current
        DESCRIPTION     "Configuration ID of transmit class to assign packet to"
        ::= { stnPmPolicyEntry 36 }



    --
    -- STN PM Preference table
    --

    stnPmPreferenceTable OBJECT-TYPE
        SYNTAX        SEQUENCE OF StnPmPreferenceEntry
        MAX-ACCESS    not-accessible
        STATUS        current
        DESCRIPTION   "Entry contains information about a particular
                      preference entry."
        ::= { stnPmPreference 1 }
 
    stnPmPreferenceEntry OBJECT-TYPE
        SYNTAX          StnPmPreferenceEntry
        MAX-ACCESS      not-accessible
        STATUS          current
        DESCRIPTION     "Entry contains information about a particular
                        preference."
        INDEX           { stnPmPreferenceIndex }
        ::= { stnPmPreferenceTable 1 }
 
    StnPmPreferenceEntry ::= 
        SEQUENCE {
                stnPmPreferenceIndex       Integer32,
                stnPmPreferenceNum         Integer32,
                stnPmPreferenceAhAlg       StnPmAuthAlg,
                stnPmPreferenceEspAuthAlg  StnPmAuthAlg,
                stnPmPreferenceEspEncrAlg  StnPmEncrAlg,
                stnPmPreferenceLifeTime    Integer32,
                stnPmPreferenceLifeBytes   Integer32,
                stnPmPreferenceIPsecID     Integer32,
                stnPmPreferencePFSGroup    INTEGER,
                stnPmPreferenceDescription DisplayString
        }

    stnPmPreferenceIndex OBJECT-TYPE
        SYNTAX          Integer32
        MAX-ACCESS      read-only
        STATUS          current
        DESCRIPTION     "Preference index"
        ::= { stnPmPreferenceEntry 1 }

    stnPmPreferenceNum OBJECT-TYPE
        SYNTAX          Integer32
        MAX-ACCESS      read-only
        STATUS          current
        DESCRIPTION     "Preference number"
        ::= { stnPmPreferenceEntry 2 }

    stnPmPreferenceAhAlg OBJECT-TYPE
        SYNTAX          StnPmAuthAlg
        MAX-ACCESS      read-only
        STATUS          current
        DESCRIPTION     "AH authentication algorithm"
        ::= { stnPmPreferenceEntry 3 }

    stnPmPreferenceEspAuthAlg OBJECT-TYPE
        SYNTAX          StnPmAuthAlg
        MAX-ACCESS      read-only
        STATUS          current
        DESCRIPTION     "ESP authentication algorithm"
        ::= { stnPmPreferenceEntry 4 }

    stnPmPreferenceEspEncrAlg OBJECT-TYPE
        SYNTAX          StnPmEncrAlg
        MAX-ACCESS      read-only
        STATUS          current
        DESCRIPTION     "ESP encryption algorithm"
        ::= { stnPmPreferenceEntry 5 }

    stnPmPreferenceLifeTime OBJECT-TYPE
        SYNTAX          Integer32
        MAX-ACCESS      read-only
        STATUS          current
        DESCRIPTION     "Life time in minutes"
        ::= { stnPmPreferenceEntry 6 }

    stnPmPreferenceLifeBytes OBJECT-TYPE
        SYNTAX          Integer32
        MAX-ACCESS      read-only
        STATUS          current
        DESCRIPTION     "Life value in kilobytes"
        ::= { stnPmPreferenceEntry 7 }

    stnPmPreferenceIPsecID OBJECT-TYPE
        SYNTAX          Integer32
        MAX-ACCESS      read-only
        STATUS          current
        DESCRIPTION     "ID of corresponding IPSEC record"
        ::= { stnPmPreferenceEntry 8 }

    stnPmPreferencePFSGroup OBJECT-TYPE
        SYNTAX          INTEGER {
                            group1(1),
                            group2(2),
                            group5(5)
                        }
        MAX-ACCESS      read-only
        STATUS          current
        DESCRIPTION     "ESP encryption algorithm"
        ::= { stnPmPreferenceEntry 9 }

    stnPmPreferenceDescription OBJECT-TYPE
        SYNTAX          DisplayString (SIZE(0..65))
        MAX-ACCESS      read-only
        STATUS          current
        DESCRIPTION     "Description of preference"
        ::= { stnPmPreferenceEntry 10 }


    --
    -- STN PM IPsec table
    --

    stnPmIPsecTable OBJECT-TYPE
        SYNTAX          SEQUENCE OF StnPmIPsecEntry
        MAX-ACCESS      not-accessible
        STATUS          current
        DESCRIPTION     "Entry contains information about a particular
                        IPsec entry."
        ::= { stnPmIPsec 1 }
 
    stnPmIPsecEntry OBJECT-TYPE
        SYNTAX          StnPmIPsecEntry
        MAX-ACCESS      not-accessible
        STATUS          current
        DESCRIPTION     "Entry contains information about a particular
                        IPsec entry."
        INDEX           { stnPmIPsecIndex }
        ::= { stnPmIPsecTable 1 }
 
    StnPmIPsecEntry ::= 
        SEQUENCE {
                stnPmIPsecIndex                     Integer32,
                stnPmIPsecPeerIpAddr                IpAddress,
                stnPmIPsecLocalIpAddr               IpAddress,
                stnPmIPsecMode                      INTEGER, 
                stnPmIPsecKeyNegType                INTEGER,
                stnPmIPsecName                      DisplayString,
                stnPmIPsecNumManualSAs              Integer32,
                stnPmIPsecNumPreferences            Integer32,
                stnPmIPsecReplayDetectionEnabled    TruthValue
        }

    stnPmIPsecIndex OBJECT-TYPE
        SYNTAX          Integer32
        MAX-ACCESS      read-only
        STATUS          current
        DESCRIPTION     "IPsec index"
        ::= { stnPmIPsecEntry 1 }

    stnPmIPsecPeerIpAddr OBJECT-TYPE
        SYNTAX          IpAddress
        MAX-ACCESS      read-only
        STATUS          current
        DESCRIPTION     "IP address of peer for tunnel endpoint"
        ::= { stnPmIPsecEntry 2 }

    stnPmIPsecLocalIpAddr OBJECT-TYPE
        SYNTAX          IpAddress
        MAX-ACCESS      read-only
        STATUS          current
        DESCRIPTION     "Local IP address for tunnel endpoint"
        ::= { stnPmIPsecEntry 3 }

    stnPmIPsecMode OBJECT-TYPE
        SYNTAX          INTEGER {
                            tunnel(1),
                            transport(2)
                        }
        MAX-ACCESS      read-only
        STATUS          current
        DESCRIPTION     "Type of IPsec connection to create"
        ::= { stnPmIPsecEntry 4 }

    stnPmIPsecKeyNegType OBJECT-TYPE
        SYNTAX          INTEGER {
                            ike(1),
                            manual(2)
                        }
        MAX-ACCESS      read-only
        STATUS          current
        DESCRIPTION     "Key negotiation method for IPsec Sa"
        ::= { stnPmIPsecEntry 5 }

    stnPmIPsecName OBJECT-TYPE
        SYNTAX          DisplayString (SIZE(0..65))
        MAX-ACCESS      read-only
        STATUS          current
        DESCRIPTION     "Description of IPsec entry"
        ::= { stnPmIPsecEntry 6 }

    stnPmIPsecNumManualSAs OBJECT-TYPE
        SYNTAX          Integer32
        MAX-ACCESS      read-only
        STATUS          current
        DESCRIPTION     "Number of manual SAs assigned to this IPsec record"
        ::= { stnPmIPsecEntry 7 }

    stnPmIPsecNumPreferences OBJECT-TYPE
        SYNTAX          Integer32
        MAX-ACCESS      read-only
        STATUS          current
        DESCRIPTION     "Number of preferences assigned to this IPsec record"
        ::= { stnPmIPsecEntry 8 }

    stnPmIPsecReplayDetectionEnabled OBJECT-TYPE
        SYNTAX          TruthValue
        MAX-ACCESS      read-only
        STATUS          current
        DESCRIPTION     "Enable Replay detection."
        ::= { stnPmIPsecEntry 9 }


    --
    -- STN PM Encaps table
    --

    stnPmEncapsTable OBJECT-TYPE
        SYNTAX        SEQUENCE OF StnPmEncapsEntry
        MAX-ACCESS    not-accessible
        STATUS        current
        DESCRIPTION   "Entry contains information about a particular
                      Encaps entry."
        ::= { stnPmEncaps 1 }
 
    stnPmEncapsEntry OBJECT-TYPE
        SYNTAX          StnPmEncapsEntry
        MAX-ACCESS      not-accessible
        STATUS          current
        DESCRIPTION     "Entry contains information about a particular
                        Encaps entry."
        INDEX           { stnPmEncapsIndex }
        ::= { stnPmEncapsTable 1 }
 
    StnPmEncapsEntry ::= 
        SEQUENCE {
                stnPmEncapsIndex       Integer32,
                stnPmEncapsPeerIpAddr  IpAddress,
                stnPmEncapsLocalIpAddr IpAddress,
                stnPmEncapsType        INTEGER, 
                stnPmEncapsGREKey      Integer32,
                stnPmEncapsName        DisplayString
        }

    stnPmEncapsIndex OBJECT-TYPE
        SYNTAX          Integer32
        MAX-ACCESS      read-only
        STATUS          current
        DESCRIPTION     "Encaps index"
        ::= { stnPmEncapsEntry 1 }

    stnPmEncapsPeerIpAddr OBJECT-TYPE
        SYNTAX          IpAddress
        MAX-ACCESS      read-only
        STATUS          current
        DESCRIPTION     "IP address of peer for tunnel endpoint"
        ::= { stnPmEncapsEntry 2 }

    stnPmEncapsLocalIpAddr OBJECT-TYPE
        SYNTAX          IpAddress
        MAX-ACCESS      read-only
        STATUS          current
        DESCRIPTION     "Local IP address for tunnel endpoint"
        ::= { stnPmEncapsEntry 3 }

    stnPmEncapsType OBJECT-TYPE
        SYNTAX          INTEGER {
                            ip-ip(1),
                            ip-gre(2)
                        }
        MAX-ACCESS      read-only
        STATUS          current
        DESCRIPTION     "Type of Encaps connection to create"
        ::= { stnPmEncapsEntry 4 }

    stnPmEncapsGREKey OBJECT-TYPE
        SYNTAX          Integer32
        MAX-ACCESS      read-only
        STATUS          current
        DESCRIPTION     "GRE key"
        ::= { stnPmEncapsEntry 5 }

    stnPmEncapsName OBJECT-TYPE
        SYNTAX          DisplayString (SIZE(0..65))
        MAX-ACCESS      read-only
        STATUS          current
        DESCRIPTION     "Description of Encaps entry"
        ::= { stnPmEncapsEntry 6 }

    --
    -- STN PM ManualSa table
    --

    stnPmManualSaTable OBJECT-TYPE
        SYNTAX        SEQUENCE OF StnPmManualSaEntry
        MAX-ACCESS    not-accessible
        STATUS        current
        DESCRIPTION   "Entry contains information about a particular
                      ManualSa entry."
        ::= { stnPmManualSa 1 }
 
    stnPmManualSaEntry OBJECT-TYPE
        SYNTAX          StnPmManualSaEntry
        MAX-ACCESS      not-accessible
        STATUS          current
        DESCRIPTION     "Entry contains information about a particular
                        ManualSa entry."
        INDEX           { stnPmManualSaIndex }
        ::= { stnPmManualSaTable 1 }
 
    StnPmManualSaEntry ::= 
        SEQUENCE {
                stnPmManualSaIndex       Integer32,
                stnPmManualSaPeerIpAddr  IpAddress,
                stnPmManualSaDirection   StnPmDirection,
                stnPmManualSaSPI         Integer32,
                stnPmManualSaAhAlg       StnPmAuthAlg,
                stnPmManualSaAhKey       OCTET STRING,
                stnPmManualSaEspAuthAlg  StnPmAuthAlg,
                stnPmManualSaEspAuthKey  OCTET STRING,
                stnPmManualSaEspEncrAlg  StnPmEncrAlg,
                stnPmManualSaEspEncrKey  OCTET STRING,
                stnPmManualSaIPsecID     Integer32, 
                stnPmManualSaDescription DisplayString
        }

    stnPmManualSaIndex OBJECT-TYPE
        SYNTAX          Integer32
        MAX-ACCESS      read-only
        STATUS          current
        DESCRIPTION     "ManualSa index"
        ::= { stnPmManualSaEntry 1 }

    stnPmManualSaPeerIpAddr OBJECT-TYPE
        SYNTAX          IpAddress
        MAX-ACCESS      read-only
        STATUS          current
        DESCRIPTION     "IP address of peer for tunnel endpoint"
        ::= { stnPmManualSaEntry 2 }

    stnPmManualSaDirection OBJECT-TYPE
        SYNTAX          StnPmDirection
        MAX-ACCESS      read-only
        STATUS          current
        DESCRIPTION     "Direction of manual SA"
        ::= { stnPmManualSaEntry 3 }

    stnPmManualSaSPI OBJECT-TYPE
        SYNTAX          Integer32
        MAX-ACCESS      read-only
        STATUS          current
        DESCRIPTION     "SPI of manual SA"
        ::= { stnPmManualSaEntry 4 }

    stnPmManualSaAhAlg OBJECT-TYPE
        SYNTAX          StnPmAuthAlg
        MAX-ACCESS      read-only
        STATUS          current
        DESCRIPTION     "AH authentication algorithm"
        ::= { stnPmManualSaEntry 5 }

    stnPmManualSaAhKey OBJECT-TYPE
        SYNTAX          OCTET STRING (SIZE(0..128))
        MAX-ACCESS      read-only
        STATUS          current
        DESCRIPTION     "Authentication key for AH protocol"
        ::= { stnPmManualSaEntry 6 }

    stnPmManualSaEspAuthAlg OBJECT-TYPE
        SYNTAX          StnPmAuthAlg
        MAX-ACCESS      read-only
        STATUS          current
        DESCRIPTION     "ESP authentication algorithm"
        ::= { stnPmManualSaEntry 7 }

    stnPmManualSaEspAuthKey OBJECT-TYPE
        SYNTAX          OCTET STRING (SIZE(0..128))
        MAX-ACCESS      read-only
        STATUS          current
        DESCRIPTION     "Authentication key for ESP protocol"
        ::= { stnPmManualSaEntry 8 }

    stnPmManualSaEspEncrAlg OBJECT-TYPE
        SYNTAX          StnPmEncrAlg
        MAX-ACCESS      read-only
        STATUS          current
        DESCRIPTION     "ESP encryption algorithm"
        ::= { stnPmManualSaEntry 9 }

    stnPmManualSaEspEncrKey OBJECT-TYPE
        SYNTAX          OCTET STRING (SIZE(0..128))
        MAX-ACCESS      read-only
        STATUS          current
        DESCRIPTION     "Encryption key for ESP protocol"
        ::= { stnPmManualSaEntry 10 }

    stnPmManualSaIPsecID OBJECT-TYPE
        SYNTAX          Integer32
        MAX-ACCESS      read-only
        STATUS          current
        DESCRIPTION     "Index or corresponding IPsec record"
        ::= { stnPmManualSaEntry 11 }

    stnPmManualSaDescription OBJECT-TYPE
        SYNTAX          DisplayString (SIZE(0..65))
        MAX-ACCESS      read-only
        STATUS          current
        DESCRIPTION     "Description of manual SA entry"
        ::= { stnPmManualSaEntry 12 }

    --
    -- STN PM Qos Notification support objects.
    --

    stnPmQosLatestFlowCB      OBJECT-TYPE
        SYNTAX          Integer32
        MAX-ACCESS      read-only
        STATUS          current
        DESCRIPTION     "Value of the FlowCB Created"
        ::= { stnPmQosTrapVars 1 }
    
    stnPmQosLastDroppedPacket      OBJECT-TYPE
        SYNTAX          Integer32
        MAX-ACCESS      read-only
        STATUS          current
        DESCRIPTION     "Value of a dropped packet" 
        ::= { stnPmQosTrapVars 2 }

    --
    -- STN PM QoS Traps / Notifications
    --

    stnPmQosFlowCBCreated NOTIFICATION-TYPE
        OBJECTS         {   stnRouterIndex,
                            stnPmQosLatestFlowCB
                        }
        STATUS          current
        DESCRIPTION     "This trap is generated by Policy manager's QoS 
                        subsystem. This SNMP trap is generated in response 
                        to QoS creating and installing a flow."
        ::= { stnPmQosNotification 1 }


    stnPmQosFlowCBRemoved NOTIFICATION-TYPE
        OBJECTS         {   stnRouterIndex,
                            stnPmQosLatestFlowCB
                        }
        STATUS          current
        DESCRIPTION     "This trap is generated by Policy manager's QoS 
                        subsystem. This SNMP trap is generated in response 
                        to QoS removing a flow."
        ::= { stnPmQosNotification 2 }

    stnPmQosShapingPacketDiscard NOTIFICATION-TYPE
        OBJECTS         {   stnRouterIndex,
                            stnPmQosLastDroppedPacket
                        }
        STATUS          current
        DESCRIPTION     "This trap is generated by Policy manager's QoS 
                        subsystem. This SNMP trap is generated in response 
                        to QoS dropping a packet due to rate shaping."
        ::= { stnPmQosNotification 3 }

    stnPmQosThresholdPacketDiscard NOTIFICATION-TYPE
        OBJECTS         {   stnRouterIndex,
                            stnPmQosLastDroppedPacket
                        }
        STATUS          current
        DESCRIPTION     "This trap is generated by Policy manager's QoS 
                        subsystem. This SNMP trap is generated in response 
                        to QoS dropping a packet due to exceeding a threshold."
        ::= { stnPmQosNotification 4 }

    --
    -- STN PM Marker Table
    --

    stnPmMarkerTable OBJECT-TYPE
        SYNTAX          SEQUENCE OF StnPmMarkerEntry
        MAX-ACCESS      not-accessible
        STATUS          current
        DESCRIPTION     "Entry contains information about a particular
                        Marker entry."
        ::= { stnPmMarker 1 }
 
    stnPmMarkerEntry OBJECT-TYPE
        SYNTAX          StnPmMarkerEntry
        MAX-ACCESS      not-accessible
        STATUS          current
        DESCRIPTION     "Entry contains information about a particular
                        Marker entry."
        INDEX           { stnPmMarkerIndex }
        ::= { stnPmMarkerTable 1 }
 
    StnPmMarkerEntry ::= 
        SEQUENCE {
                stnPmMarkerIndex           Integer32,
                stnPmMarkerName            DisplayString,
                stnPmMarkerByteValue       INTEGER,
                stnPmMarkerByteMask        INTEGER,
                stnPmMarkerMarkedOctets    Counter64,
                stnPmMarkerMarkedPkts      Counter64
        }

    stnPmMarkerIndex OBJECT-TYPE
        SYNTAX          Integer32
        MAX-ACCESS      read-only
        STATUS          current
        DESCRIPTION     "Marker index"
        ::= { stnPmMarkerEntry 1 }

    stnPmMarkerName OBJECT-TYPE
        SYNTAX          DisplayString (SIZE(0..65))
        MAX-ACCESS      read-only
        STATUS          current
        DESCRIPTION     "Description of Marker entry"
        ::= { stnPmMarkerEntry 2 }

    stnPmMarkerByteValue OBJECT-TYPE
        SYNTAX          INTEGER
        MAX-ACCESS      read-only
        STATUS          current
        DESCRIPTION     "Value that the masked TOS byte must match"
        ::= { stnPmMarkerEntry 3 }

    stnPmMarkerByteMask OBJECT-TYPE
        SYNTAX          INTEGER
        MAX-ACCESS      read-only
        STATUS          current
        DESCRIPTION     "Mask applied to TOS byte for match"
        ::= { stnPmMarkerEntry 4 }

    stnPmMarkerMarkedOctets OBJECT-TYPE
        SYNTAX          Counter64
        MAX-ACCESS      read-only
        STATUS          current
        DESCRIPTION     "Number of octets marked by this Marker."
        ::= { stnPmMarkerEntry 5 }

    stnPmMarkerMarkedPkts OBJECT-TYPE
        SYNTAX          Counter64
        MAX-ACCESS      read-only
        STATUS          current
        DESCRIPTION     "Number of packets marked by this Marker."
        ::= { stnPmMarkerEntry 6 }


    --
    -- STN PM Profile Table
    --

    stnPmProfileTable OBJECT-TYPE
        SYNTAX          SEQUENCE OF StnPmProfileEntry
        MAX-ACCESS      not-accessible
        STATUS          current
        DESCRIPTION     "Entry contains information about a particular
                        Profile entry."
        ::= { stnPmProfile 1 }
 
    stnPmProfileEntry OBJECT-TYPE
        SYNTAX          StnPmProfileEntry
        MAX-ACCESS      not-accessible
        STATUS          current
        DESCRIPTION     "Entry contains information about a particular
                        Profile entry."
        INDEX           { stnPmProfileIndex }
        ::= { stnPmProfileTable 1 }
 
    StnPmProfileEntry ::= 
        SEQUENCE {
                stnPmProfileIndex                   Integer32,
                stnPmProfileEnabled                 TruthValue,
                stnPmProfileName                    DisplayString,
                stnPmProfileCommittedRate           Integer32,
                stnPmProfileCommittedBurst          Integer32,
                stnPmProfileExcessRate              Integer32,
                stnPmProfileExcessBurst             Integer32,
                stnPmProfileConformAction           INTEGER,
                stnPmProfileConformActionID         Integer32,
                stnPmProfileConformOctets           Counter64,
                stnPmProfileConformPkts             Counter64,
                stnPmProfileCautionAction           INTEGER,
                stnPmProfileCautionActionID         Integer32,
                stnPmProfileCautionOctets           Counter64,
                stnPmProfileCautionPkts             Counter64,
                stnPmProfileExceedAction            INTEGER,
                stnPmProfileExceedActionID          Integer32,
                stnPmProfileExceedOctets            Counter64,
                stnPmProfileExceedPkts              Counter64
        }

    stnPmProfileIndex OBJECT-TYPE
        SYNTAX          Integer32
        MAX-ACCESS      read-only
        STATUS          current
        DESCRIPTION     "Profile index"
        ::= { stnPmProfileEntry 1 }

    stnPmProfileEnabled OBJECT-TYPE
        SYNTAX          TruthValue
        MAX-ACCESS      read-only
        STATUS          current
        DESCRIPTION     "Flag to indicate if profile is enabled"
        ::= { stnPmProfileEntry 2 }

    stnPmProfileName OBJECT-TYPE
        SYNTAX          DisplayString (SIZE(0..65))
        MAX-ACCESS      read-only
        STATUS          current
        DESCRIPTION     "Description of Profile entry"
        ::= { stnPmProfileEntry 3 }

    stnPmProfileCommittedRate OBJECT-TYPE
        SYNTAX          Integer32
        MAX-ACCESS      read-only
        STATUS          current
        DESCRIPTION     "Rate in kbits per second the user or network is 
        committed to transmit."
        ::= { stnPmProfileEntry 4 }

    stnPmProfileCommittedBurst OBJECT-TYPE
        SYNTAX          Integer32
        MAX-ACCESS      read-only
        STATUS          current
        DESCRIPTION     "Maximum number of kbytes in a single transmission 
                        burst"
        ::= { stnPmProfileEntry 5 }

    stnPmProfileExcessRate OBJECT-TYPE
        SYNTAX          Integer32
        MAX-ACCESS      read-only
        STATUS          current
        DESCRIPTION     "Maximum acceptable rate in kbits per second the 
                        user or network is committed to transmit"
        ::= { stnPmProfileEntry 6 }

    stnPmProfileExcessBurst OBJECT-TYPE
        SYNTAX          Integer32
        MAX-ACCESS      read-only
        STATUS          current
        DESCRIPTION     "Maximum number of bytes in a single maximum 
                        transmission burst"
        ::= { stnPmProfileEntry 7 }

    stnPmProfileConformAction OBJECT-TYPE
        SYNTAX          INTEGER {
                            deny(1),
                            permit(2),
                            markandforward(3),
                            shape(4)
                        }
        MAX-ACCESS      read-only
        STATUS          current
        DESCRIPTION     "Type of action to take for conformant frames"
        ::= { stnPmProfileEntry 8 }

    stnPmProfileConformActionID OBJECT-TYPE
        SYNTAX          Integer32
        MAX-ACCESS      read-only
        STATUS          current
        DESCRIPTION     "Configuration ID of conform action record"
        ::= { stnPmProfileEntry 9 }

    stnPmProfileCautionAction OBJECT-TYPE
        SYNTAX          INTEGER {
                            deny(1),
                            permit(2),
                            markandforward(3),
                            shape(4)
                        }
        MAX-ACCESS      read-only
        STATUS          current
        DESCRIPTION     "Type of action to take for caution frames"
        ::= { stnPmProfileEntry 10 }

    stnPmProfileConformOctets OBJECT-TYPE
        SYNTAX          Counter64
        MAX-ACCESS      read-only
        STATUS          current
        DESCRIPTION     "Number of octets in conformant frames that have arrived."
        ::= { stnPmProfileEntry 11 }

    stnPmProfileConformPkts OBJECT-TYPE
        SYNTAX          Counter64
        MAX-ACCESS      read-only
        STATUS          current
        DESCRIPTION     "Number of conformant frames that have arrived."
        ::= { stnPmProfileEntry 12 }

    stnPmProfileCautionActionID OBJECT-TYPE
        SYNTAX          Integer32
        MAX-ACCESS      read-only
        STATUS          current
        DESCRIPTION     "Configuration ID of caution action record"
        ::= { stnPmProfileEntry 13 }

    stnPmProfileExceedAction OBJECT-TYPE
        SYNTAX          INTEGER {
                            deny(1),
                            permit(2),
                            markandforward(3),
                            shape(4)
                        }
        MAX-ACCESS      read-only
        STATUS          current
        DESCRIPTION     "Type of action to take for exceeding frames"
        ::= { stnPmProfileEntry 14 }

    stnPmProfileCautionOctets OBJECT-TYPE
        SYNTAX          Counter64
        MAX-ACCESS      read-only
        STATUS          current
        DESCRIPTION     "Number of octets in caution frames that have arrived."
        ::= { stnPmProfileEntry 15 }

    stnPmProfileCautionPkts OBJECT-TYPE
        SYNTAX          Counter64
        MAX-ACCESS      read-only
        STATUS          current
        DESCRIPTION     "Number of caution frames that have arrived."
        ::= { stnPmProfileEntry 16 }

    stnPmProfileExceedActionID OBJECT-TYPE
        SYNTAX          Integer32
        MAX-ACCESS      read-only
        STATUS          current
        DESCRIPTION     "Configuration ID of exceeding action record"
        ::= { stnPmProfileEntry 17 }

    stnPmProfileExceedOctets OBJECT-TYPE
        SYNTAX          Counter64
        MAX-ACCESS      read-only
        STATUS          current
        DESCRIPTION     "Number of octets in exceeding frames that have arrived."
        ::= { stnPmProfileEntry 18 }

    stnPmProfileExceedPkts OBJECT-TYPE
        SYNTAX          Counter64
        MAX-ACCESS      read-only
        STATUS          current
        DESCRIPTION     "Number of exceeding frames that have arrived."
        ::= { stnPmProfileEntry 19 }

    --
    -- STN PM Queue Table
    --

    stnPmQueueTable OBJECT-TYPE
        SYNTAX        SEQUENCE OF StnPmQueueEntry
        MAX-ACCESS    not-accessible
        STATUS        current
        DESCRIPTION   "Entry contains information about a particular
                      Queue entry."
        ::= { stnPmQueue 1 }
 
    stnPmQueueEntry OBJECT-TYPE
        SYNTAX          StnPmQueueEntry
        MAX-ACCESS      not-accessible
        STATUS          current
        DESCRIPTION     "Entry contains information about a particular
                        Queue entry."
        INDEX           { stnPmQueueIndex }
        ::= { stnPmQueueTable 1 }
 
    StnPmQueueEntry ::= 
        SEQUENCE {
                stnPmQueueIndex           Integer32,
                stnPmQueueName            DisplayString,
                stnPmQueueThreshold       Integer32,
                stnPmQueueDropType        INTEGER,
                stnPmQueueDropHCOctets    Counter64,
                stnPmQueueDropHCPkts      Counter64,
                stnPmQueueQueueLen        Counter32,
                stnPmQueueMaxQueueLen     Counter32
        }

    stnPmQueueIndex OBJECT-TYPE
        SYNTAX          Integer32
        MAX-ACCESS      read-only
        STATUS          current
        DESCRIPTION     "Queue index"
        ::= { stnPmQueueEntry 1 }

    stnPmQueueName OBJECT-TYPE
        SYNTAX          DisplayString (SIZE(0..65))
        MAX-ACCESS      read-only
        STATUS          current
        DESCRIPTION     "Description of Queue entry"
        ::= { stnPmQueueEntry 2 }

    stnPmQueueThreshold OBJECT-TYPE
        SYNTAX          Integer32
        MAX-ACCESS      read-only
        STATUS          current
        DESCRIPTION     "Queue Drop Threshold"
        ::= { stnPmQueueEntry 3 }

    stnPmQueueDropType OBJECT-TYPE
        SYNTAX          INTEGER { 
                            other (1), 
                            tailDrop (2), 
                            headDrop (3) 
                        }
        MAX-ACCESS      read-only
        STATUS          current
        DESCRIPTION     "Type of algorithm used to drop packets when threshold
                        is reached"
        ::= { stnPmQueueEntry 4 }

    stnPmQueueDropHCOctets OBJECT-TYPE
        SYNTAX          Counter64
        MAX-ACCESS      read-only
        STATUS          current
        DESCRIPTION     "Number of octets that have been dropped this queue."
        ::= { stnPmQueueEntry 5 }

    stnPmQueueDropHCPkts OBJECT-TYPE
        SYNTAX          Counter64
        MAX-ACCESS      read-only
        STATUS          current
        DESCRIPTION     "Number of packets that have been dropped this queue."
        ::= { stnPmQueueEntry 6 }

    stnPmQueueQueueLen OBJECT-TYPE
        SYNTAX          Counter32
        MAX-ACCESS      read-only
        STATUS          current
        DESCRIPTION     "Number of packets currently in the queue."
        ::= { stnPmQueueEntry 7 }

    stnPmQueueMaxQueueLen OBJECT-TYPE
        SYNTAX          Counter32
        MAX-ACCESS      read-only
        STATUS          current
        DESCRIPTION     "Maximum number of packets in queue since last 
                        statistics reset."
        ::= { stnPmQueueEntry 8 }

    --
    -- STN PM Firewall Notification support objects.
    --

    stnPmFirewallEventLogMsg    OBJECT-TYPE
        SYNTAX          DisplayString (SIZE(0..255))
        MAX-ACCESS      read-only
        STATUS          current
        DESCRIPTION     "Describes SNMP Trap generated by STN Firewall"
        ::= { stnPmFirewallTrapVars 1 }

    --
    -- STN PM Firewall Traps / Notifications
    -- 

    stnPmFirewallLog NOTIFICATION-TYPE
        OBJECTS         {   stnRouterIndex,
                            stnPmServiceIndex,
                            stnPmPolicyIndex,
                            stnPmFirewallEventLogMsg
                        }
        STATUS          current
        DESCRIPTION     "This trap is generated by Policy manager's Firewall 
                        subsystem. This SNMP trap is generated in response to 
                        firewall event logging."

        ::= { stnPmFirewallNotification 1 }


    --
    -- STN PM Firewall Table
    --

    stnPmFirewallTable OBJECT-TYPE
        SYNTAX          SEQUENCE OF StnPmFirewallEntry
        MAX-ACCESS      not-accessible
        STATUS          current
        DESCRIPTION     "Entry contains information about a particular
                        Firewall entry."
        ::= { stnPmFirewall 1 }
 
    stnPmFirewallEntry OBJECT-TYPE
        SYNTAX          StnPmFirewallEntry
        MAX-ACCESS      not-accessible
        STATUS          current
        DESCRIPTION     "Entry contains information about a particular
                        Firewall entry."
        INDEX           { stnPmFirewallIndex }
        ::= { stnPmFirewallTable 1 }
 
    StnPmFirewallEntry ::= 
        SEQUENCE {
                stnPmFirewallIndex                      Integer32,
                stnPmFirewallName                       DisplayString,
                stnPmFirewallAcceptOtherIPOptions       TruthValue,
                stnPmFirewallAcceptSourceRouting        TruthValue,
                stnPmFirewallTcpAckLifeTime             Integer32,
                stnPmFirewallTcpSynLifeTime             Integer32,
                stnPmFirewallTcpFinLifeTime             Integer32,
                stnPmFirewallTcpRstLifeTime             Integer32,
                stnPmFirewallTcpInactivityLifeTime      Integer32,
                stnPmFirewallUdpInactivityLifeTime      Integer32,
                stnPmFirewallSynAttackDetection         TruthValue,
                stnPmFirewallLandAttackDetection        TruthValue,
                stnPmFirewallPingFloodingDetection      TruthValue,
                stnPmFirewallPingOfDeathDetection       TruthValue,
                stnPmFirewallPortScanDetection          TruthValue,
                stnPmFirewallPingScanDetection          TruthValue,
                stnPmFirewallTcpSynBacklogQueueSize     Integer32,
                stnPmFirewallPingsPerMinute             Integer32,
                stnPmFirewallMaxPingSize                Integer32,
                stnPmFirewallEnableDynamicPortApps      Unsigned32,
                stnPmFirewallMaxDynHashTableSize        Integer32,
                stnPmFirewallMinLogPeriod               Integer32
        }

    stnPmFirewallIndex OBJECT-TYPE
        SYNTAX          Integer32
        MAX-ACCESS      read-only
        STATUS          current
        DESCRIPTION     "Firewall index"
        ::= { stnPmFirewallEntry 1 }

    stnPmFirewallName OBJECT-TYPE
        SYNTAX          DisplayString (SIZE(0..65))
        MAX-ACCESS      read-only
        STATUS          current
        DESCRIPTION     "Description of firewall entry"
        ::= { stnPmFirewallEntry 2 }

    stnPmFirewallAcceptOtherIPOptions OBJECT-TYPE
        SYNTAX          TruthValue
        MAX-ACCESS      read-only
        STATUS          current
        DESCRIPTION     "Accept packets with other IP options 
                         (non source routing)."
        ::= { stnPmFirewallEntry 3 }

    stnPmFirewallAcceptSourceRouting OBJECT-TYPE
        SYNTAX          TruthValue
        MAX-ACCESS      read-only
        STATUS          current
        DESCRIPTION     "Accept packets with source routing options"
        ::= { stnPmFirewallEntry 4 }

    stnPmFirewallTcpAckLifeTime OBJECT-TYPE
        SYNTAX          Integer32
        MAX-ACCESS      read-only
        STATUS          current
        DESCRIPTION     "TCP ACK lifetime"
        ::= { stnPmFirewallEntry 5 }

    stnPmFirewallTcpSynLifeTime OBJECT-TYPE
        SYNTAX          Integer32
        MAX-ACCESS      read-only
        STATUS          current
        DESCRIPTION     "TCP SYN lifetime"
        ::= { stnPmFirewallEntry 6 }

    stnPmFirewallTcpFinLifeTime OBJECT-TYPE
        SYNTAX          Integer32
        MAX-ACCESS      read-only
        STATUS          current
        DESCRIPTION     "TCP FIN lifetime"
        ::= { stnPmFirewallEntry 7 }

    stnPmFirewallTcpRstLifeTime OBJECT-TYPE
        SYNTAX          Integer32
        MAX-ACCESS      read-only
        STATUS          current
        DESCRIPTION     "TCP RST lifetime"
        ::= { stnPmFirewallEntry 8 }

    stnPmFirewallTcpInactivityLifeTime OBJECT-TYPE
        SYNTAX          Integer32
        MAX-ACCESS      read-only
        STATUS          current
        DESCRIPTION     "TCP inactivity lifetime"
        ::= { stnPmFirewallEntry  9 }

    stnPmFirewallUdpInactivityLifeTime OBJECT-TYPE
        SYNTAX          Integer32
        MAX-ACCESS      read-only
        STATUS          current
        DESCRIPTION     "UDP inactivity lifetime"
        ::= { stnPmFirewallEntry 10 }

    stnPmFirewallSynAttackDetection OBJECT-TYPE
        SYNTAX          TruthValue
        MAX-ACCESS      read-only
        STATUS          current
        DESCRIPTION     "Enable SYN attack detection"
        ::= { stnPmFirewallEntry 11 }

    stnPmFirewallLandAttackDetection OBJECT-TYPE
        SYNTAX          TruthValue
        MAX-ACCESS      read-only
        STATUS          current
        DESCRIPTION     "Enable Land attack detection"
        ::= { stnPmFirewallEntry 12 }

    stnPmFirewallPingFloodingDetection OBJECT-TYPE
        SYNTAX          TruthValue
        MAX-ACCESS      read-only
        STATUS          current
        DESCRIPTION     "Enable ping flooding attack detection"
        ::= { stnPmFirewallEntry 13 }

    stnPmFirewallPingOfDeathDetection OBJECT-TYPE
        SYNTAX          TruthValue
        MAX-ACCESS      read-only
        STATUS          current
        DESCRIPTION     "Enable ping of death attack detection"
        ::= { stnPmFirewallEntry 14 }

    stnPmFirewallPortScanDetection OBJECT-TYPE
        SYNTAX          TruthValue
        MAX-ACCESS      read-only
        STATUS          current
        DESCRIPTION     "Enable port scan attack detection"
        ::= { stnPmFirewallEntry 15 }

    stnPmFirewallPingScanDetection OBJECT-TYPE
        SYNTAX          TruthValue
        MAX-ACCESS      read-only
        STATUS          current
        DESCRIPTION     "Enable ping scan/sweep attack detection"
        ::= { stnPmFirewallEntry 16 }

    stnPmFirewallTcpSynBacklogQueueSize OBJECT-TYPE
        SYNTAX          Integer32
        MAX-ACCESS      read-only
        STATUS          current
        DESCRIPTION     "Size of the SYN backlog queue"
        ::= { stnPmFirewallEntry 17  }

    stnPmFirewallPingsPerMinute OBJECT-TYPE
        SYNTAX          Integer32
        MAX-ACCESS      read-only
        STATUS          current
        DESCRIPTION     "Maximum number of pings allowed per minute"
        ::= { stnPmFirewallEntry 18  }

    stnPmFirewallMaxPingSize OBJECT-TYPE
        SYNTAX          Integer32
        MAX-ACCESS      read-only
        STATUS          current
        DESCRIPTION     "Maximum allowable size for ping"
        ::= { stnPmFirewallEntry 19  }

    stnPmFirewallEnableDynamicPortApps OBJECT-TYPE
        SYNTAX          Unsigned32
        MAX-ACCESS      read-only
        STATUS          current
        DESCRIPTION     "Enabled Dynamic port applications expressed as 
                         bit-map."
        ::= { stnPmFirewallEntry 20 }

    stnPmFirewallMaxDynHashTableSize OBJECT-TYPE
        SYNTAX          Integer32
        MAX-ACCESS      read-only
        STATUS          current
        DESCRIPTION     "Max dynamic hash table size - must be a power of 2."
        ::= { stnPmFirewallEntry 21  }

    stnPmFirewallMinLogPeriod OBJECT-TYPE
        SYNTAX          Integer32
        MAX-ACCESS      read-only
        STATUS          current
        DESCRIPTION     "Minimim period between event logs"
        ::= { stnPmFirewallEntry 22  }

    --
    -- STN PM Firewall Action Table
    --

    stnPmFirewallActionTable OBJECT-TYPE
        SYNTAX          SEQUENCE OF StnPmFirewallActionEntry
        MAX-ACCESS      not-accessible
        STATUS          current
        DESCRIPTION     "Entry contains information about a particular
                        Firewall Action entry."
        ::= { stnPmFirewallAction 1 }
 
    stnPmFirewallActionEntry OBJECT-TYPE
        SYNTAX          StnPmFirewallActionEntry
        MAX-ACCESS      not-accessible
        STATUS          current
        DESCRIPTION     "Entry contains information about a particular
                        Firewall Action entry."
        INDEX           { stnPmFirewallActionIndex }
        ::= { stnPmFirewallActionTable 1 }
 
    StnPmFirewallActionEntry ::= 
        SEQUENCE {
                stnPmFirewallActionIndex                Integer32,
                stnPmFirewallActionName                 DisplayString,
                stnPmFirewallActionTrackingType         INTEGER,
                stnPmFirewallActionStateful             TruthValue,
                stnPmFirewallActionInactivityLifeTime   Integer32,
                stnPmFirewallActionRejectAction         INTEGER
        }

    stnPmFirewallActionIndex OBJECT-TYPE
        SYNTAX          Integer32
        MAX-ACCESS      read-only
        STATUS          current
        DESCRIPTION     "Firewall Action index"
        ::= { stnPmFirewallActionEntry 1 }

    stnPmFirewallActionName OBJECT-TYPE
        SYNTAX          DisplayString (SIZE(0..65))
        MAX-ACCESS      read-only
        STATUS          current
        DESCRIPTION     "Description of firewall entry"
        ::= { stnPmFirewallActionEntry 2 }

    stnPmFirewallActionTrackingType OBJECT-TYPE
        SYNTAX          INTEGER {
                            none(1),
                            short(2),
                            long(3),
                            trap(4)
                        }
        MAX-ACCESS      read-only
        STATUS          current
        DESCRIPTION     "TCP ACK lifetime"
        ::= { stnPmFirewallActionEntry 3 }

    stnPmFirewallActionStateful OBJECT-TYPE
        SYNTAX          TruthValue
        MAX-ACCESS      read-only
        STATUS          current
        DESCRIPTION     "Perform stateful processing"
        ::= { stnPmFirewallActionEntry 4 }

    stnPmFirewallActionInactivityLifeTime OBJECT-TYPE
        SYNTAX          Integer32
        MAX-ACCESS      read-only
        STATUS          current
        DESCRIPTION     "Inactivity lifetime"
        ::= { stnPmFirewallActionEntry 5 }

    stnPmFirewallActionRejectAction OBJECT-TYPE
        SYNTAX          INTEGER {
                            none(1),
                            icmpUnreachPort(2),
                            tcpReset(3)
                        }
        MAX-ACCESS      read-only
        STATUS          current
        DESCRIPTION     "Firewall policy reject action."
        ::= { stnPmFirewallActionEntry 6 }

    --
    -- STN PM Service List Table
    --

    stnPmServiceListTable OBJECT-TYPE
        SYNTAX          SEQUENCE OF StnPmServiceListEntry
        MAX-ACCESS      not-accessible
        STATUS          current
        DESCRIPTION     "Entry contains information about a particular
                        Firewall Action entry."
        ::= { stnPmServiceList 1 }
 
    stnPmServiceListEntry OBJECT-TYPE
        SYNTAX          StnPmServiceListEntry
        MAX-ACCESS      not-accessible
        STATUS          current
        DESCRIPTION     "Entry contains information about a particular
                        Firewall Action entry."
        INDEX           { stnPmServiceListIndex }
        ::= { stnPmServiceListTable 1 }
 
    StnPmServiceListEntry ::= 
        SEQUENCE {
                stnPmServiceListIndex               Integer32,
                stnPmServiceListName                DisplayString,
                stnPmServiceListConnIdleTimeout     Integer32,
                stnPmServiceListNumServices         Integer32,
                stnPmServiceListEnabled             TruthValue
        }

    stnPmServiceListIndex OBJECT-TYPE
        SYNTAX          Integer32
        MAX-ACCESS      read-only
        STATUS          current
        DESCRIPTION     "Service List Action index"
        ::= { stnPmServiceListEntry 1 }

    stnPmServiceListName OBJECT-TYPE
        SYNTAX          DisplayString (SIZE(0..65))
        MAX-ACCESS      read-only
        STATUS          current
        DESCRIPTION     "Description of service list entry"
        ::= { stnPmServiceListEntry 2 }

    stnPmServiceListConnIdleTimeout OBJECT-TYPE
        SYNTAX          Integer32
        MAX-ACCESS      read-only
        STATUS          current
        DESCRIPTION     "Idle timeout"
        ::= { stnPmServiceListEntry 3 }

        stnPmServiceListNumServices OBJECT-TYPE
        SYNTAX          Integer32
        MAX-ACCESS      read-only
        STATUS          current
        DESCRIPTION     "Number of services in this serviceList"
        ::= { stnPmServiceListEntry 4 }

    stnPmServiceListEnabled OBJECT-TYPE
        SYNTAX          TruthValue
        MAX-ACCESS      read-only
        STATUS          current
        DESCRIPTION     "Flag to indicate if service is enabled"
        ::= { stnPmServiceListEntry 5 }


    --
    -- STN PM service-list service table
    --

    stnPmSLServiceTable OBJECT-TYPE
        SYNTAX        SEQUENCE OF StnPmSLServiceEntry
        MAX-ACCESS    not-accessible
        STATUS        current
        DESCRIPTION   "A list of PM service entries."
        ::= { stnPmSLService 1 }
 
    stnPmSLServiceEntry OBJECT-TYPE
        SYNTAX          StnPmSLServiceEntry
        MAX-ACCESS      not-accessible
        STATUS          current
        DESCRIPTION     "Entry contains information about a particular 
                        policy manager service."  
        INDEX           { stnPmSLIndex,
                          stnPmSLServiceIndex }
        ::= { stnPmSLServiceTable 1 }
 
    StnPmSLServiceEntry ::= 
        SEQUENCE {
                stnPmSLIndex                   Integer32,
                stnPmSLServiceIndex            Integer32,
                stnPmSLServiceName             DisplayString,
                stnPmSLServiceIdleTimeout      Integer32,
                stnPmSLServiceNumPolicies      Integer32,
                stnPmSLServiceEnabled          TruthValue,
                stnPmSLServiceType             INTEGER,
                stnPmSLServiceFirewallID       Integer32
        }       

    stnPmSLIndex OBJECT-TYPE
        SYNTAX          Integer32
        MAX-ACCESS      read-only
        STATUS          current
        DESCRIPTION     "Index into service-list table"
        ::= { stnPmSLServiceEntry 1 }

    stnPmSLServiceIndex OBJECT-TYPE
        SYNTAX          Integer32
        MAX-ACCESS      read-only
        STATUS          current
        DESCRIPTION     "Index into service table"
        ::= { stnPmSLServiceEntry 2 }

    stnPmSLServiceName OBJECT-TYPE
        SYNTAX          DisplayString (SIZE(0..65))
        MAX-ACCESS      read-only
        STATUS          current
        DESCRIPTION     "Name of service"
        ::= { stnPmSLServiceEntry 3 }

    stnPmSLServiceIdleTimeout OBJECT-TYPE
        SYNTAX          Integer32
        MAX-ACCESS      read-only
        STATUS          current
        DESCRIPTION     "Idle timeout for service"
        ::= { stnPmSLServiceEntry 4 }

    stnPmSLServiceNumPolicies OBJECT-TYPE
        SYNTAX          Integer32
        MAX-ACCESS      read-only
        STATUS          current
        DESCRIPTION     "Number of policies in this service"
        ::= { stnPmSLServiceEntry 5 }

    stnPmSLServiceEnabled OBJECT-TYPE
        SYNTAX          TruthValue
        MAX-ACCESS      read-only
        STATUS          current
        DESCRIPTION     "Flag to indicate if service is enabled"
        ::= { stnPmSLServiceEntry 6 }

    stnPmSLServiceType OBJECT-TYPE
        SYNTAX          INTEGER {
                            vpn(1),
                            firewall(2),
                            ip-fileter(3),
                            forwarding(4),
                            qos(5),
                            mpls(6)
                        }
        MAX-ACCESS      read-only
        STATUS          current
        DESCRIPTION     "Type of service"
        ::= { stnPmSLServiceEntry 7 }

    stnPmSLServiceFirewallID OBJECT-TYPE
        SYNTAX          Integer32
        MAX-ACCESS      read-only
        STATUS          current
        DESCRIPTION     "Instance of service's firewall record"
        ::= { stnPmSLServiceEntry 8 }


    --
    -- STN PM class definition/status table
    --

    stnPmClassTable OBJECT-TYPE
        SYNTAX        SEQUENCE OF StnPmClassEntry
        MAX-ACCESS    not-accessible
        STATUS        current
        DESCRIPTION   "This table is a 'flattened' version of a hierarchical 
                      class trees that specify the bandwidth allocation for 
                      the CBQ interfaces of the system.

                      Each tree is rooted at an interface. A class may either 
                      be a leaf, meaning it has no children, or it may be an 
                      interior class which has children. As packets are 
                      forwarded out an interface, they are compared to the 
                      'flow definition' of each class down the tree until a 
                      matching leaf is found or until all classes are 
                      traversed. Once a matching class is found, the packet is 
                      transmitted or not based on the constraints configured 
                      for the class, most importantly the allocated bandwidth 
                      as identified by stnPmClassRate. If no matching class is
                      found, the packet is dropped."
        ::= { stnPmClass 1 }

    stnPmClassEntry OBJECT-TYPE
        SYNTAX        StnPmClassEntry
        MAX-ACCESS    not-accessible
        STATUS        current
        DESCRIPTION   "Information about a single traffic class. Traffic 
                      classes are identified by their associated interface's 
                      ifIndex and their name. (Which means class names must be
                      unique for a particular interface.)

                      Finally, the following objects cannot be modified once 
                      the row is active: stnPmClassParent, and 
                      stnPmClassQueueElasticityFactor."
        INDEX { stnPmIfIndex, stnPmTxclassInstance }
        ::= { stnPmClassTable 1 }

    StnPmClassEntry ::=
        SEQUENCE {
                stnPmIfIndex                        InterfaceIndex,
                stnPmTxclassInstance                Integer32,
                stnPmClassName                      DisplayString,
                stnPmClassParent                    DisplayString,
                -- Configuration Parameters
                stnPmClassRate                      StnPmBitRate,
                stnPmClassPriority                  Integer32,
                stnPmClassMaxIdle                   Integer32,
                stnPmClassMinIdle                   Integer32,
                stnPmClassMaxQueueLen               Integer32,
                -- Status        
                stnPmClassOperStatus                INTEGER,
                stnPmClassBwUse                     INTEGER,
                stnPmClassUnsatisfied               TruthValue,
                stnPmClassQueueSize                 Gauge32,
                -- Max Bandwidth 
                stnPmClassMaxRate                   StnPmBitRate,
                -- Class description
                stnPmClassDescription               DisplayString,
                -- Statistics
                stnPmClassStatsHighWater            Counter32,
                stnPmClassStatsIdle                 Integer32,
                stnPmClassStatsQueuedPkts           Gauge32,
                stnPmClassStatsOctets               Counter32,
                stnPmClassStatsPkts                 Counter32,
                stnPmClassStatsOverLimits           Counter32,
                stnPmClassStatsBorrowAttempts       Counter32,
                stnPmClassStatsDroppedOctets        Counter32,
                stnPmClassStatsDroppedPkts          Counter32,
                stnPmClassStatsThrottles            Counter32,
                stnPmClassStatsUnsatisfieds         Counter32,
                stnPmClassStatsAggrOctets           Counter32,
                stnPmClassStatsAggrPkts             Counter32
       }

    stnPmIfIndex OBJECT-TYPE
        SYNTAX          InterfaceIndex
        MAX-ACCESS      read-only
        STATUS          current
        DESCRIPTION     "A sequence number that identifies a particular 
                        interface the class has been installed on."
        ::= { stnPmClassEntry 1 }

    stnPmTxclassInstance OBJECT-TYPE
        SYNTAX          Integer32
        MAX-ACCESS      read-only
        STATUS          current
        DESCRIPTION     "The instance of the configuration record for the 
                        tranmsit class that the interface is using."
        ::= { stnPmClassEntry 2 }

    stnPmClassName OBJECT-TYPE
        SYNTAX          DisplayString (SIZE (1..64))
        MAX-ACCESS      read-only
        STATUS          current
        DESCRIPTION     "A user-defined name for the traffic class. This is 
                        the unique identifier for the class within the scope 
                        of the interface. For example, the class that defines 
                        the IP address range for a particular customer might 
                        be 'Customer Fred Co.'"
        ::= { stnPmClassEntry 3 }

    stnPmClassParent OBJECT-TYPE
        SYNTAX          DisplayString (SIZE (1..64))
        MAX-ACCESS      read-only
        STATUS          current
        DESCRIPTION     "Name of class parent"
        DEFVAL      { "interface" }
        ::= { stnPmClassEntry 4 }

    stnPmClassRate OBJECT-TYPE      
        SYNTAX          StnPmBitRate
        UNITS           "bits per second"
        MAX-ACCESS      read-only
        STATUS          current
        DESCRIPTION     "A fraction of the bandwidth of the root interface to 
                        be allocated to this traffic class. Note that 
                        specifying 0 bits/second effectively filters all 
                        traffic that matches this class' flow specification. 
                        Also note that the sum of bit rates for all classes 
                        defined under the same class must be less than or 
                        equal to stnPmClassRate of the parent."
        DEFVAL      { 0 }
        ::= { stnPmClassEntry 5 }

    stnPmClassPriority OBJECT-TYPE        
        SYNTAX          Integer32 (1..7)
        MAX-ACCESS      read-only
        STATUS          current
        DESCRIPTION     "The priority for this class. The smaller the value, 
                        the higher the priority. Delay-sensitive flows (such 
                        as video or audio) should be given higher priority 
                        values."
        DEFVAL      { 3 }
        ::= { stnPmClassEntry 6 }

    stnPmClassMaxIdle OBJECT-TYPE
        SYNTAX          Integer32
        UNITS           "tens of nanoseconds"
        MAX-ACCESS      read-only
        STATUS          current
        DESCRIPTION     "An upper bound for the average idle time (see the 
                        DESCRIPTION of stnPmClassStatsIdle). Thus, 
                        stnPmClassMaxIdle limits the 'credit' given to a class
                        that has recently been under its allocation."
        DEFVAL      { 0 }
        ::= { stnPmClassEntry 7 }

    stnPmClassMinIdle OBJECT-TYPE
        SYNTAX          Integer32
        UNITS           "tens of nanoseconds"
        MAX-ACCESS      read-only
        STATUS          current
        DESCRIPTION     "The negative lower bound of the average idle. Thus, a
                        negative minidle lets the router 'remember' that a 
                        class has recently used more than its allocated 
                        bandwidth."
        DEFVAL      { 0 }
        ::= { stnPmClassEntry 8 }

    stnPmClassMaxQueueLen OBJECT-TYPE
        SYNTAX          Integer32 (0..200)
        MAX-ACCESS      read-only
        STATUS          current
        DESCRIPTION     "A factor used to influence whether this traffic class
                        gets a proportionally larger or smaller queue size 
                        than other classes. Other factors in the queue size 
                        include the percent bandwidth allocated to this class 
                        and the priority."
        DEFVAL      { 100 }
        ::= { stnPmClassEntry 9 }

    stnPmClassOperStatus OBJECT-TYPE
        SYNTAX          INTEGER {
                            up(1),
                            down(2),
                            downConflict(3),
                            autoClassActive(4)
                        }
        MAX-ACCESS      read-only
        STATUS          current
        DESCRIPTION     "The actual operational status of the traffic class. 
                        The value 'up(1)' means this traffic class is in use, 
                        the value 'down(2)' indicates the traffic class is not
                        in use either due to an internal problem or because it
                        (or an ancestor) is administratively disabled, and the
                        value 'downConflict(3)' indicates the class definition
                        conflicts with those of its siblings. The value 
                        autoClassActive(4) means that the class is a 
                        dynamically created AutoClass, which may not be 
                        modified in any way until it is saved to Non-Volatile 
                        configuration memory. After an AutoClass is saved to 
                        NVRAM, it's operational status will transistion to up
                        (1)."
        ::= { stnPmClassEntry 10 }
                    
    stnPmClassBwUse OBJECT-TYPE     
        SYNTAX          INTEGER {
                            atLimit(1),
                            underLimit(2),
                            overLimit(3)
                        }
        MAX-ACCESS      read-only
        STATUS          current
        DESCRIPTION     "An indication of whether this traffic class has used 
                        its allocated bandwidth, has not used its allocated 
                        bandwidth or has used more than its allocated 
                        bandwidth and is therefore 'atLimit(1)', 
                        'underLimit(2)', or 'overLimit(3)' respectively."
        ::= { stnPmClassEntry 11 }

    stnPmClassUnsatisfied OBJECT-TYPE       
        SYNTAX          TruthValue
        MAX-ACCESS      read-only
        STATUS          current
        DESCRIPTION     "An indication of whether this traffic class is
                        'unsatisfied'. The value of this object is 'true(1)' 
                        if it is underLimit and has a persistent backlog, 
                        meaning it has packets waiting in its queue. The value 
                        is 'false(1)' otherwise. Note that a class can be 
                        considered satisfied if it is underLimit and it just 
                        hasn't had anything to transmit. 

                        The presence of an unsatisfied class indicates that 
                        some other class is overLimit and 'hogging' bandwidth. 
                        Persistently unsatisfied classes indicate that tuning 
                        some of the parameters (such as stnPmClassMaxIdle or 
                        stnPmClassBounded) may be necessary."
        ::= { stnPmClassEntry 12 }

    stnPmClassQueueSize OBJECT-TYPE       
        SYNTAX          Gauge32 (0..2048)
        MAX-ACCESS      read-only
        STATUS          current
        DESCRIPTION     "The size of the queue associated with this traffic
                        class. This is the maximum number of packets that can 
                        be in the queue, not the number that are currently 
                        queued (see stnPmClassStatsQueuedPkts)."
        ::= { stnPmClassEntry 13 }

    stnPmClassMaxRate OBJECT-TYPE      
        SYNTAX          StnPmBitRate
        UNITS           "bits per second"
        MAX-ACCESS      read-only
        STATUS          current
        DESCRIPTION     "The maximum bandwidth the class may achieve, including
                        bandwidth allocated to this class, and any bandwidth 
                        that may be borrowed. A value of zero (0) indicates 
                        that this feature is not being used. The 
                        stnPmClassMaxRate must be set to a value higher than 
                        the stnPmClassRate, but may also exceed the parent 
                        class's stnPmClassRate."
        DEFVAL      { 0 }
        ::= { stnPmClassEntry 14 }

    stnPmClassDescription OBJECT-TYPE
        SYNTAX          DisplayString (SIZE(0..255))
        MAX-ACCESS      read-only
        STATUS          current
        DESCRIPTION     "Textual name associated with this class."
        ::= { stnPmClassEntry 15 }
    stnPmClassStatsHighWater OBJECT-TYPE       
        SYNTAX          Counter32
        MAX-ACCESS      read-only
        STATUS          current
        DESCRIPTION     "The historical maximum number of packets that were 
                        queued for this class since the system was last 
                        reinitialized."
        ::= { stnPmClassEntry 16 }

    stnPmClassStatsIdle OBJECT-TYPE
        SYNTAX          Integer32
        UNITS           "tens of nanoseconds"
        MAX-ACCESS      read-only
        STATUS          current
        DESCRIPTION     "The difference between the desired time and the 
                        measured actual time between the most recent packet 
                        transmissions for the last two packets sent from this 
                        class. When the connection is sending perfectly at its
                        allocated rate, then stnPmClassIdle is zero. When the 
                        connection is sending more than its allocated 
                        bandwidth, then stnPmClassIdle is negative."
        ::= { stnPmClassEntry 17 }

    stnPmClassStatsQueuedPkts OBJECT-TYPE      
        SYNTAX          Gauge32
        MAX-ACCESS      read-only
        STATUS          current
        DESCRIPTION     "The current number of packets in the class' queue."
        ::= { stnPmClassEntry 18 }

    stnPmClassStatsOctets OBJECT-TYPE       
        SYNTAX          Counter32
        MAX-ACCESS      read-only
        STATUS          current
        DESCRIPTION     "The number of bytes transmitted for this traffic 
                        class. Note that a class with a configured 
                        stnPmClassRate of 0 bits/second will never transmit 
                        any octets and therefore this object's value will be 0.
                        These filtered octets will be counted as part of 
                        stnPmClassStatsDroppedOctets."
        ::= { stnPmClassEntry 19 }

    stnPmClassStatsPkts OBJECT-TYPE       
        SYNTAX          Counter32
        MAX-ACCESS      read-only
        STATUS          current
        DESCRIPTION     "The number of packets transmitted for this traffic
                        class. Note that a class with a configured 
                        stnPmClassRate of 0 bits/second will never transmit 
                        any packets and therefore this object's value will be 
                        0. These filtered packets will be counted as part of 
                        stnPmClassStatsDroppedPkts."
        ::= { stnPmClassEntry 20 }

    stnPmClassStatsOverLimits OBJECT-TYPE      
        SYNTAX          Counter32
        MAX-ACCESS      read-only
        STATUS          current
        DESCRIPTION     "A count of the number of times the class used more 
                        than its allocated bandwidth."
        ::= { stnPmClassEntry 21 }

    stnPmClassStatsBorrowAttempts OBJECT-TYPE  
        SYNTAX          Counter32
        MAX-ACCESS      read-only
        STATUS          current
        DESCRIPTION     "A count of the number of times the class attempted to
                        'borrow' bandwidth from another class."
        ::= { stnPmClassEntry 22 }

    stnPmClassStatsDroppedOctets OBJECT-TYPE
        SYNTAX          Counter32
        MAX-ACCESS      read-only
        STATUS          current
        DESCRIPTION     "A count of the number of octets dropped for this class
                        because of lack of buffer space in the queue or 
                        because the class exceeded its allocated bandwidth."
        ::= { stnPmClassEntry 23 }
    
    stnPmClassStatsDroppedPkts OBJECT-TYPE     
        SYNTAX          Counter32
        MAX-ACCESS      read-only
        STATUS          current
        DESCRIPTION     "A count of the number of packets dropped for this 
                        class because of lack of buffer space in the queue or 
                        because the class exceeded its allocated bandwidth."
        ::= { stnPmClassEntry 24 }

    stnPmClassStatsThrottles OBJECT-TYPE       
        SYNTAX          Counter32
        MAX-ACCESS      read-only
        STATUS          current
        DESCRIPTION     "A count of the number of times the class was 
                        throttled (not allowed to transmit packets) by the 
                        link-sharing algorithm."
        ::= { stnPmClassEntry 25 }

    stnPmClassStatsUnsatisfieds OBJECT-TYPE
        SYNTAX          Counter32
        MAX-ACCESS      read-only
        STATUS          current
        DESCRIPTION     "A count of the number of times the class was 
                        unsatisfied, as indicated by the stnPmClassUnsatisfied
                        object."
        ::= { stnPmClassEntry 26 }
    
    stnPmClassStatsAggrOctets OBJECT-TYPE       
        SYNTAX          Counter32
        MAX-ACCESS      read-only
        STATUS          current
        DESCRIPTION     "The aggregate number of bytes transmitted by the 
                        children of this traffic class."
        ::= { stnPmClassEntry 27 }

    stnPmClassStatsAggrPkts OBJECT-TYPE       
        SYNTAX          Counter32
        MAX-ACCESS      read-only
        STATUS          current
        DESCRIPTION     "The aggregate number of packets transmitted by the 
                        children of this traffic class."
        ::= { stnPmClassEntry 28 }

END
