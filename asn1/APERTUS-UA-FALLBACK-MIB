APERTUS-UA-FALLBACK-MIB DEFINITIONS ::= BEGIN

	IMPORTS
		mib-2
			FROM RFC1213-MIB
		MODULE-IDENTITY, OBJECT-TYPE, OBJECT-IDENTITY,
		TimeTicks, IpAddress, Counter32, Gauge32
			FROM SNMPv2-SMI
		TEXTUAL-CONVENTION, RowStatus, DisplayString, TruthValue
			FROM SNMPv2-TC
		MODULE-COMPLIANCE, OBJECT-GROUP
			FROM SNMPv2-CONF;

internet      OBJECT IDENTIFIER ::= { iso org(3) dod(6) 1 }

directory     OBJECT IDENTIFIER ::= { internet 1 }

mgmt          OBJECT IDENTIFIER ::= { internet 2 }

experimental  OBJECT IDENTIFIER ::= { internet 3 }

private       OBJECT IDENTIFIER ::= { internet 4 }
enterprises   OBJECT IDENTIFIER ::= { private 1 }

	apertus OBJECT IDENTIFIER ::= { enterprises 543 }

	isg OBJECT IDENTIFIER ::= { apertus 3 }

	aperua OBJECT IDENTIFIER ::= { isg 3 }

	aperfallback OBJECT IDENTIFIER ::= { aperua 3 }

	aperFallbackMIB OBJECT IDENTIFIER ::= { aperfallback 1 }




	aperFallbackMIBObjects       OBJECT IDENTIFIER ::= { aperFallbackMIB 1 }

	-- (Old-style) groups in the apertus Threshold extension

	aperFallbackConfig  OBJECT IDENTIFIER ::= { aperFallbackMIBObjects 1 }
	aperFallbackDomain  OBJECT IDENTIFIER ::= { aperFallbackMIBObjects 2 }
	aperFallbackNode  OBJECT IDENTIFIER ::= { aperFallbackMIBObjects 3 }

	-- Fallbackold config information group
	aperFallbackConfigStatus OBJECT-TYPE
		SYNTAX      INTEGER {	ready(1),
								loading(2),
								down(3) }
		ACCESS  read-only
		STATUS      mandatory
		DESCRIPTION
               "Status of Universal Access server"
		::= { aperFallbackConfig 1 }

	aperFallbackConfigUpTime OBJECT-TYPE
		SYNTAX      TimeTicks
		ACCESS  read-only
		STATUS      mandatory
		DESCRIPTION
               "This value represents the time elapsed since the server
                was started in 1/100nths of a second."
		::= { aperFallbackConfig 2 }

	-- Fallbackold zone information group

	aperFallbackDomainTable OBJECT-TYPE
		SYNTAX      SEQUENCE OF AperFallbackDomainEntry
		ACCESS  not-accessible
		STATUS      mandatory
		DESCRIPTION
	               "Domain information broken down domain name."
		::= { aperFallbackDomain 1 }

	aperFallbackDomainEntry OBJECT-TYPE
		SYNTAX      AperFallbackDomainEntry
		ACCESS  not-accessible
		STATUS      mandatory
		DESCRIPTION
               "This table contains information on each of the load balance
				domains under its control."
		INDEX     { aperFallbackDomainName }
		::= { aperFallbackDomainTable 1 }

	AperFallbackDomainEntry ::=
		SEQUENCE {
			aperFallbackDomainName
				DisplayString,
			aperFallbackDomainUpServers
				INTEGER,
			aperFallbackDomainDownServers
				INTEGER
		    }

	aperFallbackDomainName OBJECT-TYPE
		SYNTAX		DisplayString
		ACCESS  read-only	
		STATUS		mandatory
		DESCRIPTION
			"The zone name for this load-balance domain."
		::= { aperFallbackDomainEntry 1 }

	aperFallbackDomainUpServers OBJECT-TYPE
		SYNTAX		INTEGER ( -2147483648..2147483647 )
		ACCESS	read-only
		STATUS		mandatory
		DESCRIPTION
			"The number of servers that are up at this time."
		::= { aperFallbackDomainEntry 2 }

	aperFallbackDomainDownServers OBJECT-TYPE
		SYNTAX		INTEGER ( -2147483648..2147483647 )
		ACCESS	read-only
		STATUS		mandatory
		DESCRIPTION
			"The number of servers in list that are marked as down at this
			 time."
		::= { aperFallbackDomainEntry 3 }


	-- Fallbackold zone information group

	aperFallbackNodeTable OBJECT-TYPE
		SYNTAX      SEQUENCE OF AperFallbackNodeEntry
		ACCESS  not-accessible
		STATUS      mandatory
		DESCRIPTION
               "Node information broken down domain name and IP address"
		::= { aperFallbackNode 1 }

	aperFallbackNodeEntry OBJECT-TYPE
		SYNTAX      AperFallbackNodeEntry
		ACCESS  not-accessible
		STATUS      mandatory
		DESCRIPTION
               "This table contains information on each of the machines
				in the different laod balance zones."
		INDEX     { aperFallbackNodeName,
					aperFallbackNodeIP }
		::= { aperFallbackNodeTable 1 }

	AperFallbackNodeEntry ::=
		SEQUENCE {
			aperFallbackNodeName
				DisplayString,
			aperFallbackNodeIP
				IpAddress,
			aperFallbackNodeHostIndex
				INTEGER,
			aperFallbackNodePoolIndex
				INTEGER,
			aperFallbackNodeStatus
				INTEGER,
			aperFallbackNodeResponseTime
				TimeTicks
		    }

	aperFallbackNodeName OBJECT-TYPE
		SYNTAX		DisplayString
		ACCESS  read-only	
		STATUS		mandatory
		DESCRIPTION
			"The zone name for this Node."
		::= { aperFallbackNodeEntry 1 }

	aperFallbackNodeIP OBJECT-TYPE
		SYNTAX		IpAddress
		ACCESS  read-only	
		STATUS		mandatory
		DESCRIPTION
			"The IP address of the NODE."
		::= { aperFallbackNodeEntry 2 }

	aperFallbackNodeHostIndex OBJECT-TYPE
		SYNTAX      INTEGER (0..2147483647 )
		ACCESS  read-only
		STATUS      mandatory
		DESCRIPTION
			"This value is the host index within the domain.  The lower the
			 number, the higher the preference towards using the node for all
			 name to address mappings."
		::= { aperFallbackNodeEntry 3 }

	aperFallbackNodePoolIndex OBJECT-TYPE
		SYNTAX		INTEGER (0..255)
		ACCESS	read-only
		STATUS		mandatory
		DESCRIPTION
			"This value is the pool index.  When all nodes with a lower index
			are down, the items with next highest pool index are considered
			for fallback usage."
		::= { aperFallbackNodeEntry 4 }


	aperFallbackNodeStatus OBJECT-TYPE
		SYNTAX		INTEGER {	up(1),
								down(2),
								notqueried(3) }
		ACCESS	read-only
		STATUS		mandatory
		DESCRIPTION
			"Indicates the status of the node.  Up(1) shows that the node is
			 up and is being considered for use.  Down(2) indicates that
			 the last query to the NODE image resulted in a down marker for
			 the node.  Admindown(3) indicates that an administrator took
			 the node offline manually (from the UA server end).
			 Notqueried(4) is used to indicate that a node has never been
			 queried."
		::= { aperFallbackNodeEntry 5 }

	aperFallbackNodeResponseTime OBJECT-TYPE
		SYNTAX      TimeTicks
		ACCESS  read-only
		STATUS      mandatory
		DESCRIPTION
               "Response time in MS of last node access.  A value of 0 is
                returned if NodeStatus is not ready(1) or if the node
				has never been queried"
		::= { aperFallbackNodeEntry 6 }

END
