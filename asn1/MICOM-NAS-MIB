--
-- MIB Revision Dated: 05-31-96 
--
--
-- MIB Revision : 1.0 dated 1-17-97
-- Change Desc. : None. 
-- 
-- MIB Revision : 1.1 dated 04-22-97 Shri
-- Change desc  : Add capabilities to the objects.
--
-- MIB Revision : 1.2 dated 5-17-97
-- Change Desc. : Updated Description entry DESC -BP
-- 
-- *** RELEASE 3.0 ***
-- MIB Revision : 1.3 dated 6-18-98
-- Change Desc. : Changed Displaystring range for 
--				  nasDNDigits to (SIZE(1..40)). 
--				  Obsoleted server counter reset 
--				  object, "nasOSCARCntrZero". -A. Llanes
--

MICOM-NAS-MIB DEFINITIONS ::= BEGIN
	IMPORTS
		Counter, IpAddress 
                   		 	FROM RFC1155-SMI
		OBJECT-TYPE
                    		FROM RFC-1212
		TRAP-TYPE
                			FROM RFC-1215
		micom-oscar 
							FROM MICOM-OSCAR-MIB
		DisplayString 
							FROM SNMPv2-TC;


-- group OBJECT IDENTIFIERs

micom-nas OBJECT IDENTIFIER ::= {micom-oscar 16}
nasBase OBJECT IDENTIFIER ::= {micom-nas 1}
nasStat OBJECT IDENTIFIER ::= {micom-nas 2}
nasOscar OBJECT IDENTIFIER ::= {micom-nas 3}
nasDn OBJECT IDENTIFIER ::= {micom-nas 4}
nasNvParam OBJECT IDENTIFIER ::= {micom-nas 5}


-- Basic System Parameters
--   This group contains the system parameters required by the NAS
--   It contains the management information that should be made
--   available by all implementations of the Network Address Server

nasOSCARHelloTime OBJECT-TYPE
   	SYNTAX  INTEGER (60..8000)
   	ACCESS  read-write
   	STATUS  mandatory
	DESCRIPTION
	  "NAME = ServerAgeingTime;
	   DESC = The Server age time for ageing the registered \
		  MPA entries.;
	   HELP = If the server does not receive \
		  a HELLO packet from the MPA within this time \
		  the MPA's registered numbers will be removed. \
		  This accounts for MPAs coming up and going down. \
		  The value should be a multiple \
		  of the MPA's HelloTime. Recommended value \
		  is atleast twice of that of the MPA's \
		  HelloTime. This parameter is stored \
		  in permanent storage whose copy is \
		  accessible thru the MIB object \
		  nasNvOSCARHelloTime.;
	   CAPABILITIES = NET_CFG, VPN_NONE;"
   ::= { nasBase 1 }

nasOSCARCntrZero OBJECT-TYPE
   	SYNTAX      INTEGER { reset(1) }
	ACCESS      write-only
	STATUS     	obsolete 
	DESCRIPTION
	  "NAME = ServerCounterReset;
       DESC = This object was obsoleted as of release \
	      3.0; and is included here only to support \
	      backwards compatibility for software \
	      versions prior to release 3.0. \
	   	  Facility to zero the statistical counters \
          of this NAS.;
	   HELP = Setting this parameter to reset will \
		  zero out the counters from the NAS \
		  Stat Group. This is useful when collecting \
		  statistics over a period of time for analysis;
	   CAPABILITIES = NET_CFG, VPN_NONE;"
   ::= {nasBase 2}

nasOSCARTableSize OBJECT-TYPE
   	SYNTAX      Counter 
	ACCESS      read-only
	STATUS      mandatory
	DESCRIPTION
	  "NAME = NumofRegisteredMPAs;
	   DESC = Aggregrate of MPAs (belonging to all customers) \
		  that are currently registered with this server;
	   HELP = A zero value would either mean \
		  that no MPAs are currently active \
		  or are reachable by this server, or this \
		  server is not known to the MPAs;
	   CAPABILITIES = NET_CFG, VPN_NONE;"
   ::= {nasBase 3}

nasDNDNAdbSize OBJECT-TYPE
   	SYNTAX      Counter 
	ACCESS      read-only
	STATUS      mandatory
	DESCRIPTION
	  "NAME = NumofRegisteredDNs;
	   DESC = Aggregrate of DNs (belonging to all customers) \
		  that are currently registered with this server.
	   HELP = A zero value would either mean \
		  that no MPAs are currently active \
		  or are reachable by this server, or this \
		  server is not known to the MPAs;
	   CAPABILITIES = NET_CFG, VPN_NONE;"
   ::= {nasBase 4}


-- NAS Statistics Group
--   This group contains the counters maintaining the vital 
--   statistics for this NAS. This group should be made
--   available by all implementations of the Network Address Server

nasInDNARequests OBJECT-TYPE
	SYNTAX      Counter 
	ACCESS      read-only
	STATUS      mandatory
	DESCRIPTION
	  "NAME = AddressMappingRequestRecvd;
	   DESC = Aggregrate of Address Mapping requests \
		  received by this server from MPAs \
		  belonging to all customers served by this NAS;
	   HELP = Number of DN-DNA mappings requested \
		  by this NAS.;
	   CAPABILITIES = NET_CFG, VPN_NONE;"
   ::= {nasStat 1}

nasInDNAResolveds OBJECT-TYPE
	SYNTAX      Counter 
	ACCESS      read-only
	STATUS      mandatory
	DESCRIPTION
	  "NAME = AddressMappingsResolved;
	   DESC = Number of DN-DNA mappings resolved by \
		  this NAS.;
	   HELP = Number of DN-DNA mappings resolved by \
		  this NAS. This  includes requests from \
		  MPAs belonging to all the Customers \
		  serviced by this Network Address Server.;
	   CAPABILITIES = NET_CFG, VPN_NONE;"
   ::= {nasStat 2}

nasInDNAUnResolveds OBJECT-TYPE
	SYNTAX      Counter 
	ACCESS      read-only
	STATUS      mandatory
	DESCRIPTION
	  "NAME = AddressMappingRequestFails;
	   DESC = Aggregrate of address mapping requests this \
		  server was unable to resolve.;
	   HELP = Includes all customers serviced by this server. \
		  A very high value could indicate call attempts \
		  to a telephone serviced by a down or \
		  unreachable MPA;
	   CAPABILITIES = NET_CFG, VPN_NONE;"
   ::= {nasStat 3}

nasInNACHellos OBJECT-TYPE
	SYNTAX      Counter 
	ACCESS      read-only
	STATUS      mandatory
	DESCRIPTION
	  "NAME = HellosRecvd;
	   DESC = Aggregrate of HELLO messages received from \
		  all MPAs belonging to all customers that \
		  are serviced by this NAS;
	   HELP = Includes Hellos from MPAs \
		  belonging to all the Customers \
		  serviced by this Network Address Server.;
	   CAPABILITIES = NET_CFG, VPN_NONE;"
   ::= {nasStat 4}

nasInRegisters OBJECT-TYPE
	SYNTAX      Counter 
	ACCESS      read-only
	STATUS      mandatory
	DESCRIPTION
	  "NAME = RegisterMessageRcvd;
	   DESC = Aggregrate of Register messages received \
		  by this server from MPAs belonging to all\
                  customers serviced by this NAS ;
	   HELP = If this value is greater than NumofRegisterdMPAs \
		  it would indicate that a few MPAs have had to \
		  re-register. A MPA may have to re-register if \
		  this server aged out it's registered entries \
		  or if the MPA had a configuration change or \
		  a MPA has rebooted;
	   CAPABILITIES = NET_CFG, VPN_NONE;"
   ::= {nasStat 5}

nasInUnknowns OBJECT-TYPE
	SYNTAX      Counter 
	ACCESS      read-only
	STATUS      mandatory
	DESCRIPTION
	  "NAME = UnknownMessagesReceived;
	   DESC = Number of Unknown messages received \
		  by this server.;
	   HELP = This includes messages \
		  from MPAs belonging to all the Customers \
		  serviced by this Network Address Server. \
		  This value should be zero. A non-zero \
		  value would indicate a different \
		  application sharing the same UDP port;
	   CAPABILITIES = NET_CFG, VPN_NONE;"
   ::= {nasStat 6}

nasOSCARRegSuccess OBJECT-TYPE
	SYNTAX      Counter 
	ACCESS      read-only
	STATUS      mandatory
	DESCRIPTION
	  "NAME = SuccessfulRegistrations;
	   DESC = Number of Register packets successfully \
		  serviced by this server.;
	   HELP = ;
	   CAPABILITIES = NET_CFG, VPN_NONE;"
   ::= {nasStat 7}

nasOSCARRegFails OBJECT-TYPE
	SYNTAX      Counter 
	ACCESS      read-only
	STATUS      mandatory
	DESCRIPTION
	  "NAME = RegistrationFails;
	   DESC = Number of MPA registration attempts failed \
		  by this server;
	   HELP = The server may fail an registration atttempt \
		  for the following reasons : \
		  the received packet was incorrect or \
		  the server ran out of memory;
	   CAPABILITIES = NET_CFG, VPN_NONE;"
   ::= {nasStat 8}

nasOSCARTimedOuts OBJECT-TYPE
	SYNTAX      Counter 
	ACCESS      read-only
	STATUS      mandatory
	DESCRIPTION
	  "NAME = NumOfMPAsTimedOut;
	   DESC = Number of MPAs aged out from the database \
		  as HELLO messages were not received in time;
	   HELP = A very high number could be a due to : \
		  IP network congestion or failure and hence \
		  HELLO messages are not reaching this server, or \
		  The MPAs have gone out of service;
	   CAPABILITIES = NET_CFG, VPN_NONE;"
   ::= {nasStat 9}

nasOutNASHellos OBJECT-TYPE
	SYNTAX      Counter 
	ACCESS      read-only
	STATUS      mandatory
	DESCRIPTION
	  "NAME = NumOfNASHellosSent;
	   DESC = Number of NAS Hello Messages sent out \
		  by this NAS.;
	   HELP = These messages are sent \
		  if solicited by the MPA. The MPA solicits \
		  a HELLO message from the server in \
		  an attempt to re-establish communication;
	   CAPABILITIES = NET_CFG, VPN_NONE;"
   ::= {nasStat 10}

nasOutRegisterRequests OBJECT-TYPE
	SYNTAX      Counter 
	ACCESS      read-only
	STATUS      mandatory
	DESCRIPTION
	  "NAME = ;
	   DESC = Number of NAS Register-Request Messages \
		  sent out by this NAS.;
	   HELP = ;
	   CAPABILITIES = NET_CFG, VPN_NONE;"
   ::= {nasStat 11}


-- NAS OSCAR Table
--   This table contains one entry for each access device registered with 
--   the NAS.  It contains the management information that should
--   be made available by all implementations of the NAS.

nasOSCARTable OBJECT-TYPE
	SYNTAX      SEQUENCE OF NasOSCAREntry
	ACCESS      not-accessible
	STATUS      mandatory
	DESCRIPTION
	  "NAME = ;
	   DESC = The NAS MPA table listing;
	   HELP = ;
	   CAPABILITIES = NET_CFG, VPN_NONE;"
   ::= {nasOscar 1}

nasOSCAREntry OBJECT-TYPE
	SYNTAX      NasOSCAREntry
	ACCESS      not-accessible
	STATUS      mandatory
	DESCRIPTION
	  "NAME = ;
	   DESC = Each entry corresponds to one MPA \
		  registered with the system.;
	   HELP = ;
	   CAPABILITIES = ;"
   INDEX       { nasOSCARCustomerId, nasOSCARDNADigits }
   ::= {nasOSCARTable 1}

NasOSCAREntry ::= SEQUENCE {
                        nasOSCARCustomerId
                           INTEGER,
                        nasOSCARDNADigits
                           DisplayString,
                        nasOSCARState
                           INTEGER,
                        nasOSCARIpAddr
                           IpAddress,
                        nasOSCARSuppDns
                           Counter
                    }
                           
nasOSCARCustomerId OBJECT-TYPE
	SYNTAX      INTEGER (1..65535)
	ACCESS      read-only
	STATUS      mandatory
	DESCRIPTION
	  "NAME = ;
	   DESC = The unique identifier of the customer \
		  network. This is one of the indicies \
		  to a row in this table.;
	   HELP = This is one of the indicies \
		  to a row in this table.;
	   CAPABILITIES = ;"
   ::= {nasOSCAREntry 1}

nasOSCARDNADigits OBJECT-TYPE
	SYNTAX      DisplayString(SIZE(1..48))
	ACCESS      read-only
	STATUS      mandatory
	DESCRIPTION
	  "NAME = ;
	   DESC = The DNA digits in ASCII format which \
		  uniquely identify the row in the table.;
	   HELP = Every MPA an unique DNA number \
		  assigned to it.;
	   CAPABILITIES = ;"
   ::= {nasOSCAREntry 2}

nasOSCARState OBJECT-TYPE
	SYNTAX      INTEGER { valid(1), invalid(2) }
	ACCESS      read-only
	STATUS      mandatory
	DESCRIPTION
	  "NAME = ;
	   DESC = The validity of this entry in the MPA \
		  table.;
	   HELP = ;
	   CAPABILITIES = ;"
   ::= {nasOSCAREntry 3}

nasOSCARIpAddr OBJECT-TYPE
	SYNTAX      IpAddress
	ACCESS      read-only
	STATUS      mandatory
	DESCRIPTION
	  "NAME = ;
	   DESC = The network address used by the MPA \
		  to communicate with this NAS.;
	   HELP = ;
	   CAPABILITIES = ;"
   ::= {nasOSCAREntry 4}

nasOSCARSuppDns OBJECT-TYPE
	SYNTAX      Counter
	ACCESS      read-only
	STATUS      mandatory
	DESCRIPTION
	  "NAME = ;
	   DESC = The number of DN entries supported by \
		  this MPA. This is the size of the \
		  MPA's Egress Table.;
	   HELP = ;
	   CAPABILITIES = ;"
   ::= {nasOSCAREntry 5}


-- NAS DN Table
--   This table contains one entry for each DN-DNA mapping registered 
--   with the NAS.  It contains the management information that 
--   should be made available by all implementations of the NAS.

nasDNTable OBJECT-TYPE
	SYNTAX      SEQUENCE OF NasDNEntry
	ACCESS      not-accessible
	STATUS      mandatory
	DESCRIPTION
	  "NAME = ;
	   DESC = The NAS DN Table.;
	   HELP = ;
	   CAPABILITIES = NET_CFG, VPN_NONE;"
   ::= {nasDn 1}

nasDNEntry OBJECT-TYPE
	SYNTAX      NasDNEntry
	ACCESS      not-accessible
	STATUS      mandatory
	DESCRIPTION
	  "NAME = ;
	   DESC = Each entry corresponds to one DN registered \
		  with the system.;
	   HELP = ;
	   CAPABILITIES = ;"
   INDEX       { nasDNCustomerId, nasDNDigits }
   ::= {nasDNTable 1}

NasDNEntry ::= SEQUENCE {
                        nasDNCustomerId
                           INTEGER,
                        nasDNDigits
                           DisplayString,
                        nasDNDNADigits
                           DisplayString,
                        nasDNState
                           INTEGER
                    }
                           
nasDNCustomerId OBJECT-TYPE
	SYNTAX      INTEGER (1..65535)
	ACCESS      read-only
	STATUS      mandatory
	DESCRIPTION
	  "NAME = ;
	   DESC = The unique identifier of the customer \
		  network.;
	   HELP = This is one of the indicies \
		  to a row in this table.;
	   CAPABILITIES = ;"
   ::= {nasDNEntry 1}

nasDNDigits OBJECT-TYPE
	SYNTAX      DisplayString(SIZE(1..40))
	ACCESS      read-only
	STATUS      mandatory
	DESCRIPTION
	  "NAME = ;
	   DESC = The DN digits in ASCII format which \
		  uniquely identify the row in the table. \
		  For software releases prior to 3.0, the \
		  string range was restricted to (SIZE(1..24)).;
	   HELP = Every Egress Entry has an unique DN \
		  number assigned to the channel.;
	   CAPABILITIES = ;"
   ::= {nasDNEntry 2}

nasDNDNADigits OBJECT-TYPE
	SYNTAX      DisplayString(SIZE(1..48))
	ACCESS      read-only
	STATUS      mandatory
	DESCRIPTION
	  "NAME = ;
	   DESC = The DNA digits in ASCII format which \
		  uniquely identify the MPA which \
		  supports this DN.;
	   HELP = Every MPA has a \
		  unique DNA number assigned to it.;
	   CAPABILITIES = ;"
   ::= {nasDNEntry 3}

nasDNState OBJECT-TYPE
	SYNTAX      INTEGER { valid(1), invalid(2) }
	ACCESS      read-only
	STATUS      mandatory
	DESCRIPTION
	  "NAME = ;
	   DESC = The validity of this entry in the DN \
		  table.;
	   HELP = ;
	   CAPABILITIES = ;"
   ::= {nasDNEntry 4}


-- Flash Configuration Parameters
--   This group contains the system parameters stored in permanent
--   memory. It contains the management information that should be made
--   available by all implementations of the Network Address Server

nasNvOSCARHelloTime OBJECT-TYPE
	SYNTAX  INTEGER (60..8000)
	ACCESS  read-only
	STATUS  mandatory 
	DESCRIPTION
	  "NAME = ;
       DESC = The NAS Ageing time for ageing the registered \
		  MPA entries.;
	   HELP = This should be a multiple \
		  of the NAC HelloTime. Recommended value \
		  is atleast twice of that of the NAC \
		  HelloTime. This parameter is stored \
		  in permanent storage. The operating \
		  value is accessible thru the MIB object \
		  nasOSCARHelloTime.;
	   CAPABILITIES = NET_CFG, VPN_NONE;"
   ::= { nasNvParam 1 }

END
