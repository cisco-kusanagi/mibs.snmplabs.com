--  ==================================================================
--  LANCAST PROPRIETARY PHYSICAL ENTITIES MIB
--  ==================================================================

--  =================================================================
    LC-PHYSICAL-ENTITIES-MIB
   
--  NOTES: 
--
--    1) The mib compiler renames a MIB Module name by adding
--       an extension of -A.  This results in the following error:
--       The module identity for "LC-PHYSICAL-ENTITIES-MIB-A" conflicts with 
--       the one for "LC-PHYSICAL-ENTITIES-MIB" which prevents the generation
--       of an output file.  
--
--       This is resolved by commenting out the following in the control file:
--       a) the IMPORT statement of MODULE-IDENTITY
--       b) the full MODULE-IDENTITY clause AND replace it with:
--
--       physicalEntities OBJECT IDENTIFIER ::= { lancastMibModulesA 2 }  
--       
--       You will get the following warning but it can be ignored.
--         "Warning:  A MIB module must start with exactly one invocation of
--         the MODULE-IDENTITY macro immediately following an optional IMPORTS
--         clause."
   
--
   
   DEFINITIONS ::= BEGIN

   IMPORTS
   
   MODULE-IDENTITY, OBJECT-TYPE, NOTIFICATION-TYPE, Integer32
        FROM SNMPv2-SMI
   DisplayString
        FROM SNMPv2-TC
   lancastMibModulesA, lancastTraps
        FROM LANCAST-MIB;
  
-- =======================================================================
-- MODULE IDENTITY & REVISION HISTORY
-- =======================================================================
	  physicalEntities  MODULE-IDENTITY
			LAST-UPDATED		"9903031200Z"
			ORGANIZATION		"Lancast Inc"
			CONTACT-INFO		"Contact:
											 Customer Service
											 Tel:	1-877-526-2278 ext 136
											 Fax:	1-603-594-2887
											 Web:	info@lancast.com"
			DESCRIPTION
							"This is the enterprise MIB definition file for the 
             Physical Entities of Lancast Managed products.
							
							Copyright 1999 Lancast Inc."
							
		  REVISION "9903031200Z"
		  				
		  DESCRIPTION	  				
		  				"REV 1.0  original Draft"
		  				
		  ::= { lancastMibModulesA 2 }
			 
--  ======================================================================
--  PHYSICAL ENTITIES BRANCH OID:  1.3.6.1.4.1.2745.1.2
--  ======================================================================
--  stackGroup          OBJECT IDENTIFIER ::= { physicalEntities 1 }      
    chassisGroup        OBJECT IDENTIFIER ::= { physicalEntities 2 }
    backPlaneGroup      OBJECT IDENTIFIER ::= { physicalEntities 3 }
    powerSupplyGroup    OBJECT IDENTIFIER ::= { physicalEntities 4 }    
    modulesGroup        OBJECT IDENTIFIER ::= { physicalEntities 5 }
    ePortGroup          OBJECT IDENTIFIER ::= { physicalEntities 6 }
    serialPortGroup     OBJECT IDENTIFIER ::= { physicalEntities 7 }
  
      
-- =======================================================================
--  The Chassis Group
--  chassisTable  OID:    1.3.6.1.4.1.2745.2.2.1
-- =======================================================================
  chassisTable  OBJECT-TYPE
    SYNTAX       SEQUENCE OF ChassisTableEntry
    MAX-ACCESS   not-accessible
    STATUS       current
    DESCRIPTION
      "A table of relevent information pertaining to each chassis
      contained within this system."
    ::= {chassisGroup 1 }

  chassisTableEntry OBJECT-TYPE
    SYNTAX       ChassisTableEntry
    MAX-ACCESS   not-accessible
    STATUS       current
    DESCRIPTION
      "An entry in the table, containing relevant information about a specific
      chassis contained within this system."
    INDEX   { chassisEntityIndex }
    ::= {chassisTable 1}
    
  ChassisTableEntry ::= SEQUENCE {
      chassisEntityIndex            Integer32,
      chassisDescription            DisplayString,
      chassisPartNumber             DisplayString,
      chassisNumSlots               Integer32,
      chassisCurrentTemp            Integer32,
      chassisMaxTemp                Integer32,
      chassisReset                  INTEGER,
      lastEntityResetReason         INTEGER,
      lastEntityResetIndex          Integer32,
      lastEntityResetTime           DisplayString,
      lastEntityResetType           INTEGER
    }

  chassisEntityIndex OBJECT-TYPE
    SYNTAX      Integer32
    MAX-ACCESS  read-only
    STATUS      current
    DESCRIPTION
      "A unique value, the entPhysicalIndex from the entity MIB, which identifies
      this chassis."
    ::= { chassisTableEntry 1 }

  chassisDescription  OBJECT-TYPE
    SYNTAX       DisplayString    (SIZE (1..64))
    MAX-ACCESS   read-only
    STATUS       current
    DESCRIPTION
      "A textual string describing a chassis contained within this system."
    ::= { chassisTableEntry 2 }   
    
  chassisPartNumber OBJECT-TYPE
    SYNTAX       DisplayString   (SIZE (1..64))
    MAX-ACCESS   read-only
    STATUS       current
    DESCRIPTION
      "A textual string of the part number assigned to this chassis."
    ::= { chassisTableEntry 3 }
    
  chassisNumSlots OBJECT-TYPE
    SYNTAX       Integer32
    MAX-ACCESS   read-only
    STATUS       current
    DESCRIPTION
      "The number of I/O slots that this chassis supports."
    ::= { chassisTableEntry 4 }
      
  chassisCurrentTemp OBJECT-TYPE
    SYNTAX       Integer32
    MAX-ACCESS   read-only
    STATUS       current
    DESCRIPTION
      "The temperature of this chassis measured in Celcius degrees.
      This object will be contained in the tempStatusChange trap,"
    ::= { chassisTableEntry 5 }

  chassisMaxTemp OBJECT-TYPE
    SYNTAX       Integer32
    MAX-ACCESS   read-only
    STATUS       current
    DESCRIPTION
      "The maximum temperature for this chassis.  If this temperature
      is exceeded failures may result.  This object will be contained
      in the tempStatusChange Trap,"
    ::= { chassisTableEntry 6 }   
    
  chassisReset OBJECT-TYPE
    SYNTAX  INTEGER {
      reset            (1),
      resetable        (2),
      not-resetable    (3)
    }
    MAX-ACCESS  read-write
    STATUS  current
    DESCRIPTION
        "The trigger to reset this chassis.  If the design of this chassis does
        not include this feature then this object will default to not-resetable
        and no sets to this object will be allowed.  If the design does permit
        a reset then the only valid state that a user can set this object to is
        is reset.  A read of this object will return either resetable or
        not-resetable."
    ::= { chassisTableEntry 7 } 

  lastEntityResetReason OBJECT-TYPE
    SYNTAX  INTEGER {
      cold-start        (1),
      nms-sw-reset      (2),
      download-reset    (3),
      watch-dog-timeout (4)
    }
    MAX-ACCESS  read-only
    STATUS  current
    DESCRIPTION
      "This object specifies the reason the last reset was applied.
      This object is included in the entityResetTrap pdu."
    ::= { chassisTableEntry 8 }
    
  lastEntityResetIndex OBJECT-TYPE
    SYNTAX       Integer32
    MAX-ACCESS   read-only
    STATUS       current
    DESCRIPTION
      "This object specifies the physical entity index, entPhysicalIndex from
      the entity MIB, of the last entity that was reset. This object is 
      included in the entityResetTrap pdu."
    ::= { chassisTableEntry 9 }
    
  lastEntityResetTime OBJECT-TYPE
    SYNTAX  DisplayString (SIZE (1..64))
    MAX-ACCESS  read-only
    STATUS  current
    DESCRIPTION
      "This object specifies the time the last reset was applied to an entity.
      This object is included in the entityResetTrap pdu."
    ::= { chassisTableEntry 10 }
    
   lastEntityResetType OBJECT-TYPE
    SYNTAX  INTEGER {
        chassis (3),
        module  (9),
        port    (10)      
    }
    MAX-ACCESS  read-only
    STATUS  current
    DESCRIPTION
      "This object specifies the type of entity that was last reset.
      The values are are a subset from the entity mib entPhysicalClass object."
    ::= { chassisTableEntry 11 }


-- =======================================================================
--  The Backplane Group
--  backplaneTable  OID:    1.3.6.1.4.1.2745.2.3.1
-- =======================================================================
  backPlaneTable OBJECT-TYPE
    SYNTAX       SEQUENCE OF BackPlaneTableEntry
    MAX-ACCESS   not-accessible
    STATUS       current
    DESCRIPTION
      "A table of relevent information pertaining to a backplane
      contained within this system."
    ::= { backPlaneGroup 1 }

  backPlaneTableEntry  OBJECT-TYPE
    SYNTAX       BackPlaneTableEntry
    MAX-ACCESS   not-accessible
    STATUS       current
    DESCRIPTION
      "An entry in the table, containing relevant information about a specific
      backplane contained within this system."
    INDEX   {  backPlaneEntityIndex }
    ::= { backPlaneTable 1}
    
   BackPlaneTableEntry  ::= SEQUENCE {
      backPlaneEntityIndex            Integer32,
      backPlaneDescription            DisplayString,
      backPlanePartNumber             DisplayString,
      backPlaneSerialNumber           DisplayString,
      backPlaneManufactureDate        DisplayString,
      backPlaneHWRevisionNumber       DisplayString
      }

  backPlaneEntityIndex OBJECT-TYPE
    SYNTAX       Integer32
    MAX-ACCESS   read-only
    STATUS       current
    DESCRIPTION
      "A unique value, the entPhysicalIndex from the entity MIB, that identifies
      a back plane for which this entry contains information."	
    ::= { backPlaneTableEntry 1 }

  backPlaneDescription  OBJECT-TYPE
    SYNTAX       DisplayString    (SIZE (1..64))
    MAX-ACCESS   read-only
    STATUS       current
    DESCRIPTION
      "A textual string describing a backPlane contained within this system."
    ::= { backPlaneTableEntry 2 }   
    
  backPlanePartNumber OBJECT-TYPE
    SYNTAX       DisplayString   (SIZE (1..64))
    MAX-ACCESS   read-only
    STATUS       current
    DESCRIPTION
      "A textual string of the part number of this back plane."
    ::= { backPlaneTableEntry 3 }

  backPlaneSerialNumber OBJECT-TYPE
    SYNTAX       DisplayString (SIZE (1..64))
    MAX-ACCESS   read-only
    STATUS       current
    DESCRIPTION
      "A textual string of the serial number of this back plane."
    ::= { backPlaneTableEntry 4 }

  backPlaneManufactureDate OBJECT-TYPE
    SYNTAX       DisplayString (SIZE (1..64))
    MAX-ACCESS   read-only
    STATUS       current
    DESCRIPTION
      "A textual string of the manufacture date of this back plane."
    ::= { backPlaneTableEntry 5 }

  backPlaneHWRevisionNumber OBJECT-TYPE
    SYNTAX       DisplayString (SIZE (1..64))
    MAX-ACCESS   read-only
    STATUS       current
    DESCRIPTION
      "A textual string of the hardware revision date of this back plane."
    ::= { backPlaneTableEntry 6 }

    
-- =======================================================================
--  The Power  Supply Group
--  powerSupplyTable  OID:    1.3.6.1.4.1.2745.2.4.1
-- =======================================================================
  powerSupplyTable  OBJECT-TYPE
    SYNTAX       SEQUENCE OF PowerSupplyTableEntry
    MAX-ACCESS   not-accessible
    STATUS       current
    DESCRIPTION
      "A table of relevent information pertaining to a backplane
      contained within this system."
    ::= { powerSupplyGroup 1 }

  powerSupplyTableEntry  OBJECT-TYPE
    SYNTAX       PowerSupplyTableEntry
    MAX-ACCESS   not-accessible
    STATUS       current
    DESCRIPTION
      "An entry in the table, containing relevant information about a specific
      backplane contained within this system."
    INDEX   {  powerSupplyEntityIndex }
    ::= { powerSupplyTable 1}
    
  PowerSupplyTableEntry  ::= SEQUENCE 
  	 {
    powerSupplyEntityIndex            Integer32,
    powerSupplyStatus                 INTEGER,
    powerSupplyType                   INTEGER,
    powerSupply5vCurrent              Integer32,
    powerSupply5vMin                  Integer32,
    powerSupply5vMax                  Integer32,
    powerSupplyUnitIdentifier         INTEGER
    }

  powerSupplyEntityIndex OBJECT-TYPE
    SYNTAX       Integer32
    MAX-ACCESS   read-only
    STATUS       current
    DESCRIPTION
      "A unique value, the entPhysicalIndex from the entity MIB, that identifies
      a power supply for which this entry contains information."	  		
    ::= { powerSupplyTableEntry 1 }
  
  powerSupplyStatus OBJECT-TYPE
    SYNTAX  INTEGER{
        on    (1),
        off   (2)   
    }   
    MAX-ACCESS  read-only
    STATUS  current
    DESCRIPTION
        "The on off state of this power supply."
    ::= { powerSupplyTableEntry 2 }

  powerSupplyType OBJECT-TYPE
    SYNTAX  INTEGER {
        ac          (1),
        dc          (2),
        universal   (3)
        }
    MAX-ACCESS  read-only
    STATUS  current
    DESCRIPTION
      "The type of this power supply."
    ::= { powerSupplyTableEntry 3 }
        
  powerSupply5vCurrent OBJECT-TYPE
    SYNTAX       Integer32
    MAX-ACCESS   read-only
    STATUS       current
    DESCRIPTION
      "The actual voltage level of this 5 volt supply as measured in
      millivolts."
    ::= { powerSupplyTableEntry 4 }
    
  powerSupply5vMin OBJECT-TYPE
    SYNTAX       Integer32
    MAX-ACCESS   read-only
    STATUS       current
    DESCRIPTION
      "The minimum operating voltage level of this 5 volt supply, measured in
      millivolts."
    ::= { powerSupplyTableEntry 5 }   

  powerSupply5vMax OBJECT-TYPE
    SYNTAX       Integer32
    MAX-ACCESS   read-only
    STATUS       current
    DESCRIPTION
      "The maximum operating voltage level of this 5 volt supply, measured in
      millivolts."
    ::= { powerSupplyTableEntry 6 }
    
  powerSupplyUnitIdentifier OBJECT-TYPE
    SYNTAX  INTEGER {
        ps-A (1),
        ps-B (2)
        }
    MAX-ACCESS  read-only
    STATUS  current
    DESCRIPTION
      "The identifier of this supply."
    ::= { powerSupplyTableEntry 7 }
               

-- =======================================================================
--  Modules Group Branch OID:   1.3.6.1.4.1.2745.2.5
--
--  Module Table OID:           1.3.6.1.4.1.2745.2.5.1
--  Managment Table OID:        1.3.6.1.4.1.2745.2.5.2
--  Single Twister OID:         1.3.6.1.4.1.2745.2.5.3
--  Dual Twister OID:           1.3.6.1.4.1.2745.2.5.4
--  Redundant Twister OID:      1.3.6.1.4.1.2745.2.5.5
--
-- =======================================================================
  moduleTable OBJECT-TYPE
    SYNTAX       SEQUENCE OF ModuleTableEntry
    MAX-ACCESS   not-accessible
    STATUS       current
    DESCRIPTION
      "A table of common information relevent to modules within this system."
    ::= { modulesGroup 1 }

  moduleTableEntry OBJECT-TYPE
    SYNTAX       ModuleTableEntry
    MAX-ACCESS   not-accessible
    STATUS       current
    DESCRIPTION
      "An entry in the common module information table."
    INDEX   { modEntityIndex }
    ::= { moduleTable 1 }

  ModuleTableEntry  ::= SEQUENCE 
  	{
    modEntityIndex                Integer32,
    modAdminState                 INTEGER,
    modOperStatus                 INTEGER,
    modType                       INTEGER,
    modDescription                DisplayString,
    modName                       DisplayString,
    modPartNumber                 DisplayString,
    modSerialNumber               DisplayString,
    modManufactureDate            DisplayString,
    modDiagnosticTestStatus       DisplayString,
    modHWRevisionNumber           DisplayString,
    modNumPorts                   Integer32,
    modFirstSlot                  Integer32,
    modNumSlotsOccupied           Integer32,
    modReset                      INTEGER
    }

  modEntityIndex OBJECT-TYPE
    SYNTAX       Integer32
    MAX-ACCESS   read-only
    STATUS       current
    DESCRIPTION        
      "A unique value, entPhysicalIndex from the entity MIB, that identifies a
      module for which this entry contains information."
    ::= { moduleTableEntry 1 }

  modAdminState OBJECT-TYPE
    SYNTAX INTEGER {
      not-applicable  (0),
      up              (1),
      down            (2)
    } 
    MAX-ACCESS   read-write
    STATUS       current
    DESCRIPTION 
      "The desired state of up or down of this module.	If the design of this
      module does not include the abiltiy to control this module then
      this object will default to not-applicable and no sets to this object
      will be allowed. If the design does permit control then up and down
      are the valid states that a user can set this object to."
    ::= { moduleTableEntry 2 }    
    
  modOperStatus OBJECT-TYPE
    SYNTAX INTEGER {
      up    (1),
      down  (2)
      } 
    MAX-ACCESS   read-only
    STATUS       current
    DESCRIPTION 
      "The current operational (up/down) state of this module."
    ::= { moduleTableEntry 3 }    
    
  modType OBJECT-TYPE
    SYNTAX  INTEGER {
      unknown                     (1),
      reserved                    (2),
      mgmnt                       (3),
      singleTwister               (4),
      dualTwister                 (5),
      redundantTwister            (6),
      displayModule               (7),
      singleTwister2              (8),
      fixedPort                   (9),
      rateAdapter                 (10),
      gigabitTwister              (11)
    }
    MAX-ACCESS   read-only
    STATUS       current
    DESCRIPTION
      "The type of module resident in this system."
    ::= { moduleTableEntry 4 }

  modDescription OBJECT-TYPE
    SYNTAX       DisplayString (SIZE (1..64))
    MAX-ACCESS   read-only
    STATUS       current
    DESCRIPTION
      "A textual description of this type of module."
    ::= { moduleTableEntry 5 }  

  modName OBJECT-TYPE
    SYNTAX       DisplayString (SIZE (1..64))
    MAX-ACCESS   read-write
    STATUS       current
    DESCRIPTION
      "A user defined name for this module."
    ::= { moduleTableEntry 6 }    

  modPartNumber OBJECT-TYPE
    SYNTAX       DisplayString  (SIZE (1..64))
    MAX-ACCESS   read-only
    STATUS       current
    DESCRIPTION
      "A textual string identifying the part number of this module."
    ::= { moduleTableEntry 7 }
    
  modSerialNumber OBJECT-TYPE
    SYNTAX       DisplayString  (SIZE (1..64))
    MAX-ACCESS   read-only
    STATUS       current
    DESCRIPTION
      "A textual string identifying the serieal number of this module."
    ::= { moduleTableEntry 8 }
    
  modManufactureDate OBJECT-TYPE
    SYNTAX       DisplayString  (SIZE (1..64))
    MAX-ACCESS   read-only
    STATUS       current
    DESCRIPTION
      "A textual string identifying the date that this module was
      manufactured."
    ::= { moduleTableEntry 9 }
    
  modDiagnosticTestStatus OBJECT-TYPE
    SYNTAX       DisplayString  (SIZE (1..64))
    MAX-ACCESS   read-only
    STATUS       current
    DESCRIPTION
      "A textual string indicating the status of the last diagnostic test
      performed on this module including the date and time."
    ::= { moduleTableEntry 10 }
    
  modHWRevisionNumber OBJECT-TYPE
    SYNTAX       DisplayString  (SIZE (1..64))
    MAX-ACCESS   read-only
    STATUS       current
    DESCRIPTION
      "A textual string identifying the hardware revision number of this
      module."
    ::= { moduleTableEntry 11 }
    
  modNumPorts OBJECT-TYPE
    SYNTAX       Integer32
    MAX-ACCESS   read-only
    STATUS       current
    DESCRIPTION
        "The number of ports conntained within this module."
    ::= { moduleTableEntry 12 }                     
    
  modFirstSlot OBJECT-TYPE
    SYNTAX       Integer32
    MAX-ACCESS   read-only
    STATUS       current
    DESCRIPTION
      "The first slot which is the leftmost slot that this module physically
      resides in."
    ::= { moduleTableEntry 13 }                 
    
  modNumSlotsOccupied OBJECT-TYPE
    SYNTAX       Integer32
    MAX-ACCESS   read-only
    STATUS       current
    DESCRIPTION
      "The total number of slots that this module physically occupies."
    ::= { moduleTableEntry 14 }
    
  modReset OBJECT-TYPE
    SYNTAX  INTEGER {
          reset          (1),
          resetable      (2),
          not-resetable  (3)
    }
    MAX-ACCESS   read-write
    STATUS       current
    DESCRIPTION
      "The trigger to reset this module.  If the design of this	module does 
      not include this feature then this object will default to not-resetable
      and no sets to this object will be allowed.  If the design does permit
      a reset then the only valid state that a user can set this object to is
      is reset.  A read of this object will return either resetable or
      not-resetable."
    ::= { moduleTableEntry 15 }                 
    
--  ======================================================================
--  Managment Module Table 
--  Table OID:      1.3.6.1.4.1.2745.2.5.2
--  ======================================================================
  mgmntTable  OBJECT-TYPE
    SYNTAX       SEQUENCE OF MgmntTableEntry
    MAX-ACCESS   not-accessible
    STATUS       current
    DESCRIPTION
      "A table of information common to management modules within this system."
    ::= { modulesGroup 2 }
    
  mgmntTableEntry OBJECT-TYPE
    SYNTAX       MgmntTableEntry
    MAX-ACCESS   not-accessible
    STATUS       current
    DESCRIPTION
      "An entry in the managment module information table."
    INDEX   { mgmntEntityIndex }
    ::= { mgmntTable 1 }

  MgmntTableEntry  ::= SEQUENCE 
  	{
    mgmntEntityIndex              Integer32,  
    mgmntBootImageName            DisplayString,
    mgmntBootImageVersion         DisplayString,
    mgmntCoreImageName            DisplayString,
    mgmntCoreImageVersion         DisplayString,
    mgmntAppImageName             DisplayString,
    mgmntAppImageVersion          DisplayString,
    mgmntRamMemorySize            Integer32,
    mgmntFlashMemorySize          Integer32,
    mgmntNVRamMemorySize          Integer32,
    mgmnt5vCurrent                Integer32,      
    mgmnt5vMin                    Integer32,
    mgmnt5vMax                    Integer32,
    mgmnt3pt3vCurrent             Integer32,      
    mgmnt3pt3vMin                 Integer32,
    mgmnt3pt3vMax                 Integer32,
    mgmntDiagnosticBootError      INTEGER
    }

  mgmntEntityIndex OBJECT-TYPE
    SYNTAX       Integer32
    MAX-ACCESS   read-only
    STATUS       current
    DESCRIPTION        
      "A unique value, the entPhysicalIndex from the entity MIB, that
      identifies a managemnt module for which this entry contains
      information."
    ::= { mgmntTableEntry 1 }   

  mgmntBootImageName  OBJECT-TYPE   
    SYNTAX       DisplayString (SIZE (1..64))
    MAX-ACCESS   read-only
    STATUS       current
    DESCRIPTION
      "A textual description of the name of the Boot image."
    ::= { mgmntTableEntry 2 }
    
  mgmntBootImageVersion OBJECT-TYPE
    SYNTAX       DisplayString (SIZE (1..64))
    MAX-ACCESS   read-only
    STATUS       current
    DESCRIPTION
      "A textual description of the version of the Boot image
      The vesion will include the time and date of the build."
    ::= { mgmntTableEntry 3 }

  mgmntCoreImageName  OBJECT-TYPE
    SYNTAX       DisplayString (SIZE (1..64))
    MAX-ACCESS   read-only
    STATUS       current
    DESCRIPTION
      "A textual description of the name of the Core image."
    ::= { mgmntTableEntry 4 }
    
  mgmntCoreImageVersion OBJECT-TYPE
    SYNTAX       DisplayString (SIZE (1..64))
    MAX-ACCESS   read-only
    STATUS       current
    DESCRIPTION
      "A textual description of the version of the Core image
      The vesion will include the time and date of the build."
    ::= { mgmntTableEntry 5 }
    
  mgmntAppImageName OBJECT-TYPE   
    SYNTAX       DisplayString (SIZE (1..64))
    MAX-ACCESS   read-only
    STATUS       current
    DESCRIPTION
      "A textual description of the name of the Application (personality)
      image."
    ::= { mgmntTableEntry 6 }
    
  mgmntAppImageVersion  OBJECT-TYPE
    SYNTAX       DisplayString (SIZE (1..64))
    MAX-ACCESS   read-only
    STATUS       current
    DESCRIPTION
      "A textual description of the version of the Application (personality)
      image.  The vesion will include the time and date of the build."
    ::= { mgmntTableEntry 7 }
            
  mgmntRamMemorySize OBJECT-TYPE
    SYNTAX       Integer32
    MAX-ACCESS   read-only
    STATUS       current
    DESCRIPTION        
      "The size of RAM memory measured in number of bytes."
    ::= { mgmntTableEntry 8 }   

  mgmntFlashMemorySize OBJECT-TYPE
    SYNTAX       Integer32
    MAX-ACCESS   read-only
    STATUS       current
    DESCRIPTION        
      "The size of Flash memory measured in number of bytes."
    ::= { mgmntTableEntry 9 }   

  mgmntNVRamMemorySize OBJECT-TYPE
    SYNTAX       Integer32
    MAX-ACCESS   read-only
    STATUS       current
    DESCRIPTION        
      "The size of Non Volatile Ram memory measured in number of bytes."
    ::= { mgmntTableEntry 10 }
    
  mgmnt5vCurrent OBJECT-TYPE
    SYNTAX       Integer32
    MAX-ACCESS   read-only
    STATUS       current
    DESCRIPTION
      "The actual voltage level of this 3.3 volt input as measured in
      millivolts."
    ::= { mgmntTableEntry 11 }
    
  mgmnt5vMin OBJECT-TYPE
    SYNTAX       Integer32
    MAX-ACCESS   read-only
    STATUS       current
    DESCRIPTION
      "The minimum operating voltage level of this 5 volt input, measured in
      millivolts."
    ::= { mgmntTableEntry 12 }   

  mgmnt5vMax OBJECT-TYPE
    SYNTAX       Integer32
    MAX-ACCESS   read-only
    STATUS       current
    DESCRIPTION
      "The maximum operating voltage level of this 5 volt input, measured in
      millivolts."
    ::= { mgmntTableEntry 13 }              
    
  mgmnt3pt3vCurrent OBJECT-TYPE
    SYNTAX       Integer32
    MAX-ACCESS   read-only
    STATUS       current
    DESCRIPTION
      "The actual voltage level of this 3.3 volt input as measured in
      millivolts."
    ::= { mgmntTableEntry 14 }
    
  mgmnt3pt3vMin OBJECT-TYPE
    SYNTAX       Integer32
    MAX-ACCESS   read-only
    STATUS       current
    DESCRIPTION
      "The minimum operating voltage level of this 3.3 volt input, measured in
      millivolts."
    ::= { mgmntTableEntry 15 }   

  mgmnt3pt3vMax OBJECT-TYPE
    SYNTAX       Integer32
    MAX-ACCESS   read-only
    STATUS       current
    DESCRIPTION
      "The maximum operating voltage level of this 3.3 volt input, measured in
      millivolts."
    ::= { mgmntTableEntry 16 }         
    
  mgmntDiagnosticBootError OBJECT-TYPE
    SYNTAX  INTEGER {
           on   (1),
           off  (2)
    }
    MAX-ACCESS   read-only
    STATUS       current
    DESCRIPTION
      "This object indicates the status of the diagnostic boot tests. 
      An error is indicated by turning the error indicator on the management 
      module is on." 
    ::= { mgmntTableEntry 17 }
    
--  ======================================================================
--  Single Twister Module Table
--  Table OID:      1.3.6.1.4.1.2745.2.5.3
--  ======================================================================        
  singleTwisterTable OBJECT-TYPE
    SYNTAX       SEQUENCE OF SingleTwisterTableEntry
    MAX-ACCESS   not-accessible
    STATUS       current
    DESCRIPTION
      "A table of information common to single twister modules."
    ::= { modulesGroup 3 }

  singleTwisterTableEntry OBJECT-TYPE
    SYNTAX       SingleTwisterTableEntry
    MAX-ACCESS   not-accessible
    STATUS       current
    DESCRIPTION
      "An entry in the single Twister table of information."
    INDEX   { stwEntityIndex }
    ::= { singleTwisterTable 1 }

  SingleTwisterTableEntry  ::= SEQUENCE 	{
    stwEntityIndex                  Integer32,
    stwLinkLossCarryForward         INTEGER
    }

  stwEntityIndex OBJECT-TYPE
    SYNTAX       Integer32
    MAX-ACCESS   read-only
    STATUS       current
    DESCRIPTION        
      "A unique value, the entPhysicalIndex from the entity MIB, that
      identifies a single twister module for which this entry contains
      information."  
    ::= { singleTwisterTableEntry 1 }

  stwLinkLossCarryForward OBJECT-TYPE
    SYNTAX  INTEGER {
      enable        (1),
      disable       (2)   
    }
    MAX-ACCESS   read-write
    STATUS       current
    DESCRIPTION
     "The ability of an input port to forward the link test pulse
      to its output port.  If disabled the output port will always generate
      link pulses, regardless of input port link status."
 
    ::= { singleTwisterTableEntry 2 }

--  ======================================================================
--  Dual Twister Module Table
--  Table OID:      1.3.6.1.4.1.2745.2.5.4
--  ======================================================================      
   dualTwisterTable OBJECT-TYPE
    SYNTAX       SEQUENCE OF DualTwisterTableEntry
    MAX-ACCESS   not-accessible
    STATUS       current
    DESCRIPTION
      "A table of information common to dual twister modules."
    ::= { modulesGroup 4 }

  dualTwisterTableEntry OBJECT-TYPE
    SYNTAX       DualTwisterTableEntry
    MAX-ACCESS   not-accessible
    STATUS       current
    DESCRIPTION
      "An entry in the dual Twister table of information."
    INDEX   { stwEntityIndex }
    ::= { dualTwisterTable 1 }

  DualTwisterTableEntry  ::= SEQUENCE {
    dtwEntityIndex                  Integer32,
    dtwLinkLossCarryForward         INTEGER
    }

  dtwEntityIndex OBJECT-TYPE
    SYNTAX       Integer32
    MAX-ACCESS   read-only
    STATUS       current
    DESCRIPTION        
      "A unique value, the entPhysicalIndex from the entity MIB, that identifies
      a dual twister module for which this entry contains information."      
    ::= { dualTwisterTableEntry 1 }

  dtwLinkLossCarryForward OBJECT-TYPE
    SYNTAX  INTEGER {
      enable       (1),
      disable      (2)   
    }
    MAX-ACCESS   read-write
    STATUS       current
    DESCRIPTION
     "The ability of an input port to forward the link test pulse
      to its output port.  If disabled the output port will always
      generate link pulses, regardless of input port link status."      
    ::= { dualTwisterTableEntry 2 }


--  =================================================================
--  Redundant Twister Table
--  Table OID:      1.3.6.1.4.1.2745.2.5.5
--  =================================================================

  redundantTwisterTable OBJECT-TYPE
    SYNTAX       SEQUENCE OF RedundantTwisterTableEntry
    MAX-ACCESS   not-accessible
    STATUS       current
    DESCRIPTION
      "A table of information common to redundant twister modules."
    ::= { modulesGroup 5 }

  redundantTwisterTableEntry OBJECT-TYPE
    SYNTAX       RedundantTwisterTableEntry
    MAX-ACCESS   not-accessible
    STATUS       current
    DESCRIPTION
      "An entry in the table containing redundant twister information."
    INDEX   { rtwEntityIndex }
    ::= { redundantTwisterTable 1 }

  RedundantTwisterTableEntry  ::= SEQUENCE 
  	 {
    rtwEntityIndex                Integer32,
    rtwAutoRestorePrimary         INTEGER,
    rtwLinkLossCarryForward       INTEGER,
    rtwActivePort                 INTEGER,
    rtwRedundantTransmission      INTEGER,
    rtwSecondarySwitchOver        INTEGER,
    rtwLinkPulseControl           INTEGER,
    rtwModeControl                INTEGER,
    rtwABSelect                   INTEGER
    }

  rtwEntityIndex OBJECT-TYPE
    SYNTAX       Integer32
    MAX-ACCESS   read-only
    STATUS       current
    DESCRIPTION        
      "A unique value, the entPhysicalIndex from the entity MIB, that
      identifies a redundant twister module for which this entry contains
      information."     
    ::= { redundantTwisterTableEntry 1 }

  rtwAutoRestorePrimary OBJECT-TYPE
    SYNTAX  INTEGER {
      enable           (1),
      disable          (2),
      not-selectable   (3)
    }
    MAX-ACCESS   read-write
    STATUS       current
    DESCRIPTION
      "This object controls the ability to perform auto restoration back to
      the primary circuit if a secondary switchover had previously occurred.
      When rtwModeControl is selectAB then this object is not selectable and
      a read of this value will always return not selectable."
    ::= { redundantTwisterTableEntry 2 }
    
  rtwLinkLossCarryForward OBJECT-TYPE
    SYNTAX  INTEGER {
      enable   (1),
      disable  (2)   
    }
    MAX-ACCESS   read-write
    STATUS       current
    DESCRIPTION
      "The ability of an input port to forward the link test pulse
      to its output port.  If disabled the output port will always generate
      link pulses, regardless of input port link status."
    ::= { redundantTwisterTableEntry 3 }
    
  rtwActivePort OBJECT-TYPE
    SYNTAX  INTEGER {
      primary     (1),
      secondary   (2)
    }
    MAX-ACCESS   read-only
    STATUS       current
    DESCRIPTION
      "This object reflects the port that is both receiving and transmitting
      packets. If the active port is the secondary then the secondary led 
      indicator will be turned on."
    ::= { redundantTwisterTableEntry 4 }
    
  rtwRedundantTransmission OBJECT-TYPE
    SYNTAX  INTEGER {
      not-applicable  (0),
      enable          (1),
      disable         (2)
    }
    MAX-ACCESS   read-write
    STATUS       current
    DESCRIPTION
      "The ability of the primary and secondary output ports to
      transmit the received main input signal simultaneously.  When
      rtwModeControl is selectAB then this object is not selectable and
      a read of this value will always return not-applicable."
    ::= { redundantTwisterTableEntry 5 }

  rtwSecondarySwitchOver OBJECT-TYPE
    SYNTAX  INTEGER {
       yes   (1),
       no    (2)
    }
    MAX-ACCESS   read-only
    STATUS       current
    DESCRIPTION
      "This object reflects whether an automatic switch from the primary port 
      to the secondary port has taken place."
    ::= { redundantTwisterTableEntry 6 }

  rtwLinkPulseControl OBJECT-TYPE
    SYNTAX  INTEGER {
      not-applicable    (0),    
      both-ports        (1),
      active-port       (2)
    }
    MAX-ACCESS   read-write
    STATUS       current
    DESCRIPTION
      "This object controls the forwarding of the link test pulse to both
      the primary and secondary ports or the slected port in rtwActivePort.
      When rtwModeControl is selectAB then this object is not selectable and
      a read of this value will always return not-applicable."
    ::= { redundantTwisterTableEntry 7 }

 rtwModeControl OBJECT-TYPE
    SYNTAX  INTEGER {
      redundant   (1),
      selectAB    (2)
    }
    MAX-ACCESS   read-write
    STATUS       current
    DESCRIPTION
      "This objects selects the operational mode. Redundant mode
      provides automatic switchover for port failure redundancy
      while ABSelect provides a basic A/B port selector."
    ::= { redundantTwisterTableEntry 8 }
    
 rtwABSelect OBJECT-TYPE
    SYNTAX  INTEGER {
      selectA        (1),
      selectB        (2),
      not-selectable (3)
    }
    MAX-ACCESS   read-write
    STATUS       current
    DESCRIPTION
      "This object selects the output port that will send and receive
      packets.  If the design of this module does not include the 
      abiltiy to select the mode, then this object will default to
      not-selectable and no sets to this object will be allowed."
    ::= { redundantTwisterTableEntry 9 }                

-- =======================================================================
--  EPort Group
--  EPortTable OID:     1.3.6.1.4.1.2745.2.6
-- ======================================================================= 
  ePortTable OBJECT-TYPE
    SYNTAX       SEQUENCE OF EPortTableEntry
    MAX-ACCESS   not-accessible
    STATUS       current
    DESCRIPTION
      "A table of relevant information about the ports(s) contained
      within a module."
    ::= {ePortGroup 1 }

  ePortTableEntry OBJECT-TYPE
    SYNTAX       EPortTableEntry
    MAX-ACCESS   not-accessible
    STATUS       current
    DESCRIPTION
      "An entry in the table containing port related information
      within a module."
    INDEX   { ePortEntityIndex }
    ::= { ePortTable 1 }

  EPortTableEntry  ::= SEQUENCE {
    ePortEntityIndex          Integer32,
    ePortIfIndex              Integer32,
    ePortType                 INTEGER,
    ePortDescription          DisplayString,
    ePortName                 DisplayString,
    ePortLinkStatus           INTEGER,
    ePortAdminState           INTEGER,
    ePortOperStatus           INTEGER,      
    ePortDuplexAdmin          INTEGER,
    ePortDuplexOper           INTEGER,    
    ePortSpeedAdmin           INTEGER,
    ePortSpeedOper            INTEGER,    
    ePortAutoNegotiationAdmin INTEGER,
    ePortAutoNegotiationOper  INTEGER,  
    ePortReset                INTEGER,
    ePortActivity             INTEGER,
    ePortConnector            INTEGER,
    ePortParentRelPos         Integer32
    }

  ePortEntityIndex OBJECT-TYPE
    SYNTAX       Integer32
    MAX-ACCESS   read-only
    STATUS       current
    DESCRIPTION
      "A unique value, the entPhysicalIndex from the entity MIB, that
      identifies a port for which this entry contains information."
    ::= { ePortTableEntry 1 }

  ePortIfIndex OBJECT-TYPE
    SYNTAX       Integer32
    MAX-ACCESS   read-only
    STATUS       current
    DESCRIPTION 
      "A unique identifier indicating the MIB-II interface number of this port.
      NOTE:   ports on media translators DO NOT conform to MIB-II definition
              of an interface."
    ::= { ePortTableEntry 2 } 

  ePortType OBJECT-TYPE
    SYNTAX  INTEGER{
        other               (1),
        e10BaseT            (2),
        e10BaseFL-MM        (3),
        e10BaseFL-SM        (4),             
        e100BaseTX          (5),
        e100BaseFX-MM       (6),
        e100BaseFX-SM       (7),
        e10-100Base-TX      (8),        
        e1000Base-LX        (9),
        e1000Base-SX        (10),
        e1000Base-FX        (11),
        e10Base-SX          (12),
        e100Base-SX         (13)
        }
    MAX-ACCESS   read-only
    STATUS       current
    DESCRIPTION
      "A unique value that identifies the type of port.  Included in the 
      port type is the maximum speed at which this port may operate at and
      the cable type."
    ::= { ePortTableEntry 3 }
  
  ePortDescription OBJECT-TYPE
    SYNTAX       DisplayString (SIZE (1..64))
    MAX-ACCESS   read-only
    STATUS       current
    DESCRIPTION
      "A textual description of this type of port."
    ::= { ePortTableEntry 4 }

  ePortName   OBJECT-TYPE
    SYNTAX       DisplayString (SIZE (1..64))
    MAX-ACCESS   read-write
    STATUS       current
    DESCRIPTION
      "The user defined name of this port."
    ::= { ePortTableEntry 5 }           
    
  ePortLinkStatus OBJECT-TYPE
    SYNTAX INTEGER {
      link-detected   (1),
      no-link         (2)
      } 
    MAX-ACCESS   read-only
    STATUS       current
    DESCRIPTION 
      "The link status of this port.  This status indicates the reception of
      link test pulse signals generated from an attached device.    
      This object is used in the ePortLinkStatusChangeTrap."
    ::= { ePortTableEntry 6 }

  ePortAdminState OBJECT-TYPE
    SYNTAX INTEGER {
      not-applicable  (0),    
      enable          (1),
      disable         (2)
      } 
    MAX-ACCESS   read-write
    STATUS       current
    DESCRIPTION
      "The desired state of this port.	If the design of this
      module does not include the abiltiy to control this port then
      this object will default to not-applicable and no sets to this object
      will be allowed. If the design does permit control then enable and
      disable are the only valid states that a user can set this object to.
      This object is used in the PortControlTrap."
    ::= { ePortTableEntry 7 }
    
  ePortOperStatus OBJECT-TYPE
    SYNTAX INTEGER {
      enable   (1),
      disable  (2)
      } 
    MAX-ACCESS   read-only
    STATUS       current
    DESCRIPTION
      "This object indicates the current operational state of this port."
    ::= { ePortTableEntry 8 }         
        
  ePortDuplexAdmin OBJECT-TYPE
    SYNTAX INTEGER {
      not-applicable  (0),    
      half            (1),
      full            (2)
      } 
    MAX-ACCESS   read-write
    STATUS       current
    DESCRIPTION 
      "This object specifies the desired state of half or full duplex mode for
      this port. If the design of this module does not include the ability to
      select duplex, then this object will default to not-applicable and no 
      sets to this object will be allowed. If the design does permit duplex
      selection then half and full are the valid  states that a user can set
      this object to."
    ::= { ePortTableEntry 9 }   

  ePortDuplexOper OBJECT-TYPE
    SYNTAX INTEGER {
      half(1),
      full(2)
      } 
    MAX-ACCESS  read-only
    STATUS  current
    DESCRIPTION 
      "This object indicates the current duplex mode of this port."
    ::= { ePortTableEntry 10 }    
    
  ePortSpeedAdmin OBJECT-TYPE
    SYNTAX INTEGER {
      not-applicable  (0),    
      tenMbit         (1),
      onehundredMbit  (2),
      gigabit         (3)
      } 
    MAX-ACCESS   read-write
    STATUS       current
    DESCRIPTION 
      "This object indicates the current speed that this port is operating 
      at. If the design of this module does not include the abiltiy to control
      the speed of this then this object will default to not-applicable and no
      sets to this object will be allowed. If the design does permit control
      then all but not-applicable are valid states that a user can set this
      object to."			
    ::= { ePortTableEntry 11 }

  ePortSpeedOper OBJECT-TYPE
    SYNTAX INTEGER {
      tenMbit         (1),
      onehundredMbit  (2),
      gigabit         (3)
      } 
    MAX-ACCESS   read-only
    STATUS       current
    DESCRIPTION 
      "This object specifies the desired speed that this port is operating at."
    ::= { ePortTableEntry 12 }
    
  ePortAutoNegotiationAdmin OBJECT-TYPE
    SYNTAX INTEGER {
      not-applicable  (0),    
      enable          (1),
      disable         (2)
      } 
    MAX-ACCESS   read-write
    STATUS       current
    DESCRIPTION 
      "This object indicates the current state of auto negotiation for this
      port.  If the design of this module does not include the ability to 
      select auto negotiation, then this object will default to not-applicable
      and no sets to this object will be allowed. If the design does permit
      auto negotiation selection then all but not-applicable are valid states
      that a user can set this object to."
    ::= { ePortTableEntry 13 }

  ePortAutoNegotiationOper OBJECT-TYPE
    SYNTAX INTEGER {
      enable   (1),
      disable  (2)
      } 
    MAX-ACCESS   read-only
    STATUS       current
    DESCRIPTION 
      "This object specifices the desired state of auto negotiation selection.
      If enabled, this port is capable of auto negotiating full/half duplex
      and port speed selection."
    ::= { ePortTableEntry 14 }
        
  ePortReset OBJECT-TYPE
    SYNTAX  INTEGER {
      reset            (1),
      resetable        (2),
      not-resetable    (3)
    }
    MAX-ACCESS   read-write
    STATUS       current
    DESCRIPTION
      "The trigger to reset this port.  If the design of this	module does 
      not include this feature then this object will default to not-resetable
      and no sets to this object will be allowed.  If the design does permit
      a reset then the only valid state that a user can set this object to is
      is reset.  A read of this object will return either resetable or
      not-resetable."
    ::= { ePortTableEntry 15 }
    
  ePortActivity OBJECT-TYPE
    SYNTAX  INTEGER {
         inactive  (1),
         active    (2)
    }
    MAX-ACCESS   read-only
    STATUS       current
    DESCRIPTION
      "This object indicates data reception and transmision activity on
      the active port(s)."
    ::= { ePortTableEntry 16 }

  ePortConnector OBJECT-TYPE
    SYNTAX  INTEGER {
         other     (1),
         rj11      (2),
         rj21      (3),
         rj45      (4),         
         bnc       (5),
         sc        (6),
         st        (7),
         sma       (8),
         mt-rj     (9),
         vf-45     (10)
    }
    MAX-ACCESS   read-only
    STATUS       current
    DESCRIPTION
      "This object indicates the connector type that this port supports."
    ::= { ePortTableEntry 17 }
    
  ePortParentRelPos OBJECT-TYPE
    SYNTAX       Integer32
    MAX-ACCESS   read-only
    STATUS       current
    DESCRIPTION
      "This object indicates this ports relative position in the module
      to which it is member of."
    ::= { ePortTableEntry 18 }
        
-- =======================================================================
--  The serialPort Group
--  serialPortTable  OID:    1.3.6.1.4.1.2745.2.7
-- =======================================================================
  serialPortTable  OBJECT-TYPE
    SYNTAX       SEQUENCE OF SerialPortTableEntry
    MAX-ACCESS   not-accessible
    STATUS       current
    DESCRIPTION
      "A table of relevent information pertaining to each serial port
      contained within this system."
    ::= {serialPortGroup 1 }

  serialPortTableEntry OBJECT-TYPE
    SYNTAX       SerialPortTableEntry
    MAX-ACCESS   not-accessible
    STATUS       current
    DESCRIPTION
      "An entry in the table, containing relevant information about a specific
      serial port contained within this system."
    INDEX   { serialPortEntityIndex }
    ::= {serialPortTable 1}
    
  SerialPortTableEntry ::= SEQUENCE {
      serialPortEntityIndex            Integer32,
      serialPortDescription            DisplayString,
      serialPortName                   DisplayString,
      serialPortSpeed                  INTEGER,
      serialPortDataBits               INTEGER,
      serialPortParity                 INTEGER,
      serialPortStopBits               INTEGER,
      serialPortFlowControl            INTEGER,
      serialPortConnector              INTEGER
    }

  serialPortEntityIndex OBJECT-TYPE
    SYNTAX       Integer32
    MAX-ACCESS   read-only
    STATUS       current
    DESCRIPTION
      "A unique value, the entPhysicalIndex from the entity MIB, which identifies
      this serial port."
    ::= { serialPortTableEntry 1 }

 serialPortDescription  OBJECT-TYPE
    SYNTAX       DisplayString    (SIZE (1..64))
    MAX-ACCESS   read-only
    STATUS       current
    DESCRIPTION
      "A textual description of this type of port."
    ::= { serialPortTableEntry 2 }   


  serialPortName  OBJECT-TYPE
    SYNTAX       DisplayString    (SIZE (1..64))
    MAX-ACCESS   read-write
    STATUS       current
    DESCRIPTION
    "The user defined name of this port."
    ::= { serialPortTableEntry 3 }   
        
  serialPortSpeed OBJECT-TYPE
    SYNTAX  INTEGER {
        baud-9600  (9600),
        baud-19200 (19200),
        baud-38400 (38400)
        }
    MAX-ACCESS  read-only
    STATUS  current
    DESCRIPTION
      "The speed that this port transmits and receives at."
    ::= { serialPortTableEntry 4 }
      
  serialPortDataBits OBJECT-TYPE
    SYNTAX  INTEGER {
       five   (5),
       six    (6),
       seven  (7),
       eight  (8)
       }    
    MAX-ACCESS   read-only
    STATUS       current
    DESCRIPTION
      "The number of bits in a character."
    ::= { serialPortTableEntry 5 }

  serialPortParity OBJECT-TYPE
    SYNTAX  INTEGER {
            none  (1),
            even  (2),
            odd   (3),
            mark  (4),
            space (5)
         }             
    MAX-ACCESS   read-only
    STATUS       current
    DESCRIPTION
     "The port's sense of a character parity bit."
    ::= { serialPortTableEntry 6 }
    
  serialPortStopBits OBJECT-TYPE
    SYNTAX  INTEGER {
        one      (1),
        one-five (2),
        two      (3)
        }
    MAX-ACCESS   read-only
    STATUS       current
    DESCRIPTION
        "The number of stop bits for this port."
    ::= { serialPortTableEntry 7 } 
    
  serialPortFlowControl OBJECT-TYPE
    SYNTAX  INTEGER {
       none      (1),
       xon-xoff  (2),
       hardware  (3)
       }
    MAX-ACCESS   read-only
    STATUS       current
    DESCRIPTION
        "The type of flow control for this port."
    ::= { serialPortTableEntry 8 } 

  serialPortConnector OBJECT-TYPE
    SYNTAX  INTEGER {
       db9    (1),
       db25   (2),
       rj45   (3)
       }
    MAX-ACCESS   read-only
    STATUS       current
    DESCRIPTION
        "This object indicates the connector type that this port supports."
    ::= { serialPortTableEntry 9 } 
    
    
--  ======================================================================
--  Lancast Proprietary Traps
--  NOTE:   These trap numbers must be maintained. The use of trap numbers
--          is our internal mechanism of mapping between v1 and v2 traps.
--
--  NOTE:   Other lancast proprietary mib files have traps specified.
--          
--          lcentity MIB uses trap number 10  entConfigChange
--
--			Please verify any changes to prevent conflicts.
-- =======================================================================  
  tempStatusChange NOTIFICATION-TYPE
    OBJECTS  { chassisEntityIndex, chassisCurrentTemp, chassisMaxTemp }
    STATUS   current
    DESCRIPTION
      "This trap will be sent when the temperature falls outside of
      the exceptable range. The values of chassisEntityIndex, chassisCurrentTemp
      and chassisMaxTemp will be included in this traps varBind list."
    ::= { lancastTraps 11 }
    
  backPlaneFailure NOTIFICATION-TYPE
    OBJECTS  { modFirstSlot }
    STATUS   current    
    DESCRIPTION
      "This trap will be sent when there is a backplane failure.  The value of
      modFirstSlot will be included in this traps varBind list."
    ::= { lancastTraps 12 }    

  powerSupply5vChange NOTIFICATION-TYPE
    OBJECTS  { powerSupplyEntityIndex, powerSupply5vCurrent, powerSupply5vMin,
               powerSupply5vMax, powerSupplyUnitIdentifier }
    STATUS   current                  
    DESCRIPTION
      "This trap will be sent when the voltage from the 5 volt power supply
      falls outside of the exceptable range.  The values of powerSupplyEntityIndex,
      powerSupply5vCurrent, powerSupplyMin, powerSupply5vMax and
      powerSupplyUnitIdentifier will be included in this traps varBind list."
    ::= { lancastTraps 13 }
    
  powerSupplyStatusChange NOTIFICATION-TYPE
    OBJECTS  { powerSupplyEntityIndex, powerSupplyStatus, powerSupplyUnitIdentifier }
    STATUS   current    
    DESCRIPTION
      "This trap will be sent when a power supply is either turned on or off.
      The values of powerSupplyEntityIndex, powerSupplyStatus and powerSupplyUnitIdentifier
      will be included in this traps varBind list."
    ::= { lancastTraps 14 }

  powerSupplyInsertion NOTIFICATION-TYPE
    OBJECTS  { powerSupplyEntityIndex, powerSupplyType, powerSupplyUnitIdentifier }
    STATUS   current
    DESCRIPTION
      "This trap will be sent when a power supply is inserted.
      The values of powerSupplyEntityIndex, powerSupplyType and powerSupplyUnitIdentifier
      will be included in this traps varBind list."
    ::= { lancastTraps 15 }

  powerSupplyRemoval NOTIFICATION-TYPE
    OBJECTS  { powerSupplyEntityIndex, powerSupplyType, powerSupplyUnitIdentifier }
    STATUS   current
    DESCRIPTION
      "This trap will be sent when a power supply is removed.
      The values of powerSupplyEntityIndex, powerSupplyType and powerSupplyUnitIdentifier
      will be included in this traps varBind list."
    ::= { lancastTraps 16 }

  chassisEntityReset NOTIFICATION-TYPE
    OBJECTS  { lastEntityResetIndex, lastEntityResetReason, lastEntityResetTime }
    STATUS   current    
    DESCRIPTION
      "This trap is sent when a chassis is reset.  The values of lastEntityResetIndex,
      lastEntityResetReason, and lastEntityResetTime  will be included in this traps
      varBind list."
    ::= { lancastTraps 17 }

  moduleEntityReset NOTIFICATION-TYPE
    OBJECTS  { lastEntityResetIndex, lastEntityResetReason, lastEntityResetTime,
               modType, modFirstSlot, modNumSlotsOccupied }
    STATUS   current                  
    DESCRIPTION
      "This trap is sent when a module is reset.  The values of lastEntityResetIndex,
      lastEntityResetReason, and lastEntityResetTime, modType, modFirstSlot and
      modNumSlotsOccupied will be included in this traps varBind list."
    ::= { lancastTraps 18 }
  
  eportEntityReset NOTIFICATION-TYPE
    OBJECTS  { lastEntityResetIndex, lastEntityResetReason, lastEntityResetTime,
               modType, modFirstSlot, modNumSlotsOccupied, ePortParentRelPos }
    STATUS   current                  
    DESCRIPTION
      "This trap is sent when a port is reset.  The values of lastEntityResetIndex,
      lastEntityResetReason, and lastEntityResetTime, modType, modFirstSlot,
      modNumSlotsOccupied, and ePortParentRelPos  will be included in this traps
      varBind list."
    ::= { lancastTraps 19 }
  
  moduleInsertion NOTIFICATION-TYPE
    OBJECTS  { modEntityIndex, modType, modFirstSlot, modNumSlotsOccupied }
    STATUS   current    
    DESCRIPTION
      "This trap is sent when a module is inserted to a slot.
      The values of modEntityIndex, modFirstSlot, modType, modNumSlotsOccupied
      will be included in this traps varBind list."			
    ::= { lancastTraps 20 }
    
  moduleRemoval NOTIFICATION-TYPE
    OBJECTS  { modEntityIndex, modType, modFirstSlot, modNumSlotsOccupied }
    STATUS   current     
    DESCRIPTION
      "This trap is sent when a module is removed from a slot.
      The values of modEntityIndex, modFirstSlot, modType, modNumSlotsOccupied
      will be included in this traps varBind list."			
    ::= { lancastTraps 21 }
    
  unknownModule    NOTIFICATION-TYPE
    OBJECTS  { modEntityIndex, modType, modFirstSlot }
    STATUS   current    
    DESCRIPTION
      "This trap is sent when a module is inserted and it's type cannot be 
      determined.    The values of modEntityIndex, modType, modFirstSlot, 
      modNumSlotsOccupied will be included in this traps varBind list."			
    ::= { lancastTraps 22 }
    
  moduleFailure    NOTIFICATION-TYPE
    OBJECTS  { modFirstSlot }
    STATUS   current    
    DESCRIPTION
      "This trap is sent when a module fails and thus is inaccessible.
      The value of modFirtSlot will be included in this traps varBind list."			      
    ::= { lancastTraps 23 }
    
  ePortLinkStatusChange NOTIFICATION-TYPE
    OBJECTS   { ePortEntityIndex, ePortLinkStatus, modType, modFirstSlot,
                modNumSlotsOccupied }
    STATUS   current                  
    DESCRIPTION
      "This trap is sent when there is a change in the link state of a port.
      The values of ePortLinkStatus, ePortIndex, modType, modFirstSlot,
      and modNumSlotsOccupied will be included in this
      traps varBind list."
    ::= { lancastTraps 24 }

  ePortAdminChange NOTIFICATION-TYPE
    OBJECTS   { ePortEntityIndex, ePortAdminState, modType, modFirstSlot,
                modNumSlotsOccupied }
    STATUS   current                  
    DESCRIPTION
      "This trap is sent when a user changes the admin state of a port
      from enable to disable or vice versa.  The values of ePortAdminState
      ePortEntityIndex, modType, modFirstSlot, modNumSlotsOccupied,
      will be included in this traps varBind list."
    ::= { lancastTraps 25 }

  rtwSwitchOverChange NOTIFICATION-TYPE
    OBJECTS   { rtwEntityIndex, rtwActivePort, modFirstSlot,
                modNumSlotsOccupied }
    STATUS   current                  
    DESCRIPTION
      "This trap is sent when a switchover from the primary to the secondary
      port and vice versa has occured. The values of rtwEntityIndex,    
      rtwActivePort, modFirstSlot, modNumSlotsOccupied will be 
      included in this traps varBind list."
    ::= { lancastTraps 26 }


  END
