APERTUS-UA-BASE-MIB DEFINITIONS ::= BEGIN

	IMPORTS
		mib-2
			FROM RFC1213-MIB
		OBJECT-TYPE
			FROM RFC-1212
		Counter FROM RFC1155-SMI
		TimeTicks, MODULE-IDENTITY, OBJECT-TYPE, OBJECT-IDENTITY, IpAddress
			FROM SNMPv2-SMI
		TEXTUAL-CONVENTION, RowStatus, DisplayString, TruthValue
			FROM SNMPv2-TC
		MODULE-COMPLIANCE, OBJECT-GROUP
			FROM SNMPv2-CONF;

internet      OBJECT IDENTIFIER ::= { iso org(3) dod(6) 1 }

directory     OBJECT IDENTIFIER ::= { internet 1 }

mgmt          OBJECT IDENTIFIER ::= { internet 2 }

experimental  OBJECT IDENTIFIER ::= { internet 3 }

private       OBJECT IDENTIFIER ::= { internet 4 }
enterprises   OBJECT IDENTIFIER ::= { private 1 }


	apertus OBJECT IDENTIFIER ::= { enterprises 543 }

	isg OBJECT IDENTIFIER ::= { apertus 3 }

	aperua OBJECT IDENTIFIER ::= { isg 3 }

	aperbaseua OBJECT IDENTIFIER ::= { aperua 1 }

	aperUaMIB OBJECT IDENTIFIER ::= { aperbaseua 1 }

	aperUaMIBObjects       OBJECT IDENTIFIER ::= { aperUaMIB 1 }

	-- (Old-style) groups in the apertus UA gateway MIB.

	aperUaConfig  OBJECT IDENTIFIER ::= { aperUaMIBObjects 1 }
	aperUaDomain  OBJECT IDENTIFIER ::= { aperUaMIBObjects 2 }


	-- UaMIB Configuration Group

	aperUaConfigStatus OBJECT-TYPE
		SYNTAX      INTEGER { ready(1),
                             loading(2),
                             down(3) }
		ACCESS  read-only
		STATUS      mandatory
		DESCRIPTION
               "Status of Universal Access server"
		::= { aperUaConfig 1 }

	aperUaConfigUpTime OBJECT-TYPE
		SYNTAX      TimeTicks
		ACCESS  read-only
		STATUS      mandatory
		DESCRIPTION
               "This value represents the time elapsed since the server
                was started in 1/100nths of a second."
		::= { aperUaConfig 2 }

	aperUaConfigResetTime OBJECT-TYPE
		SYNTAX      TimeTicks
		ACCESS  read-only
		STATUS      mandatory
		DESCRIPTION
               "This value represents the time elapsed since the server
                was reset in 1/100nths of a second."
		::= { aperUaConfig 3 }

   -- UA server domain information
	aperUaDomainTable OBJECT-TYPE
		SYNTAX      SEQUENCE OF AperUaDomainEntry
		ACCESS  not-accessible
		STATUS      mandatory
		DESCRIPTION
               "Domain information broken down domain name."
		::= { aperUaDomain 1 }

	aperUaDomainEntry OBJECT-TYPE
		SYNTAX      AperUaDomainEntry
		ACCESS  not-accessible
		STATUS      mandatory
		DESCRIPTION
               "This table contains information on each of the load balance
				domains under its control."
		INDEX     { aperUaDomainName }
		::= { aperUaDomainTable 1 }

	AperUaDomainEntry ::=
		SEQUENCE {
			aperUaDomainName
				DisplayString,
			aperUaDomainQueries
				Counter,
			aperUaDomainLastAnswer
				IpAddress,
			aperUaDomainLastQueryTime
				TimeTicks,
			aperUaDomainType
				DisplayString,
			aperUaDomainTypeOID
				OBJECT IDENTIFIER
		    }

	aperUaDomainName OBJECT-TYPE
		SYNTAX		DisplayString
		ACCESS  read-only	
		STATUS		mandatory
		DESCRIPTION
			"The zone name for this load-balance domain."
		::= { aperUaDomainEntry 1 }

	aperUaDomainQueries OBJECT-TYPE
		SYNTAX		Counter
		ACCESS	read-only
		STATUS		mandatory
		DESCRIPTION
			"The number of queries that have occured for this zone."
		::= { aperUaDomainEntry 2 }

	aperUaDomainLastAnswer OBJECT-TYPE
		SYNTAX		IpAddress
		ACCESS	read-only
		STATUS		mandatory
		DESCRIPTION
			"The IP address for the last answer given out to a resolve
			 request on this zone.  A value of 0.0.0.0 indicates that
			 no answer has been given yet."
		::= { aperUaDomainEntry 3 }

	aperUaDomainLastQueryTime OBJECT-TYPE
		SYNTAX		TimeTicks
		ACCESS	read-only
		STATUS		mandatory
		DESCRIPTION
			"The time since the last query for this zone in 1/100nths of a
			 second.  This value is only valid if aperUaDomainLastAnswer
			 is not 0.0.0.0."
		::= { aperUaDomainEntry 4 }

	aperUaDomainType OBJECT-TYPE
		SYNTAX		DisplayString (SIZE (0..128))
		ACCESS	read-only
		STATUS		mandatory
		DESCRIPTION
			"A textual note as to what type of Decision Process is being
			 used within the zone."
		::= { aperUaDomainEntry 5 }

	aperUaDomainTypeOID OBJECT-TYPE
		SYNTAX		OBJECT IDENTIFIER
		ACCESS	read-only
		STATUS		mandatory
		DESCRIPTION
			"The OID of the MIB area for this Decision Process type.  Accessing
			 this area will detail the decision information and host
			 addresses."
		::= { aperUaDomainEntry 6 }

END
