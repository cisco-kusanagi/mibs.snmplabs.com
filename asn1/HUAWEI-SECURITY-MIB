-- ===================================================================
-- Copyright (C) 2015 by HUAWEI TECHNOLOGIES. All rights reserved.
-- Description:
-- Reference:
-- Version: V2.27
-- ===================================================================
          
    HUAWEI-SECURITY-MIB DEFINITIONS ::= BEGIN
 
    IMPORTS
        EnabledStatus
            FROM P-BRIDGE-MIB
        MODULE-IDENTITY, OBJECT-TYPE, NOTIFICATION-TYPE, Integer32, Unsigned32
            FROM SNMPv2-SMI
        DateAndTime, DisplayString, TEXTUAL-CONVENTION
            FROM SNMPv2-TC
          hwDatacomm            
              FROM HUAWEI-MIB            
        NOTIFICATION-GROUP, OBJECT-GROUP, MODULE-COMPLIANCE
            FROM SNMPv2-CONF;
                 
    hwSecurityMIB MODULE-IDENTITY 
        LAST-UPDATED "201510141420Z"
        ORGANIZATION "Huawei Technologies Co.,Ltd."
          CONTACT-INFO 
            "Huawei Industrial Base
                Bantian, Longgang
                 Shenzhen 518129
                 People's Republic of China
                 Website: http://www.huawei.com
                 Email: support@huawei.com"
          DESCRIPTION 
              "The private mib file includes the general extent 
              information of the device.hwDatacomm(165).hwSecurityMIB."    
        REVISION "201510141420Z"  
        DESCRIPTION
              "Add hwAntiAttack hwAntiAttackObjectGroup hwBaseSecurityAntiAttackRateRising hwBaseSecurityAntiAttackRateResume for DFNS(LDM)"
        REVISION "201509291648Z"  
        DESCRIPTION
              "Add hwCfgApTrapObject hwCfgApTrap hwCfgApTrapFailAlarm for Virtual-Access"
        REVISION "201505262023Z"
        DESCRIPTION
              "Add hwBaseArpVlanCarTrap"
        REVISION "201504071102Z"
        DESCRIPTION
              "Add hwBaseSecurityTtlExpiredLoop"
        REVISION "201503241012Z"
        DESCRIPTION
              "Add hwDapPortChange,hwDapMibPortChange for DAP"
	REVISION "201409182020Z"
	DESCRIPTION  
              "MIB file fo APP alarm and MADEFEND."  
	REVISION "201409182020Z"
	DESCRIPTION 
              "MIB file for NETSEC."       	
        REVISION "201310241529Z"
        DESCRIPTION
            "Add hwArpsLearnStrictCheck"               
        REVISION "201310181123Z"
        DESCRIPTION
            "Add webAuthServer(36) for hwAppliApperProtocol"  
        REVISION "201306051756Z"
        DESCRIPTION
            "Add the indispensable fields, e.g. chassisid and slotid for hwBaseSecurityUrpfDiscardedRateRising, hwBaseSecurityUrpfDiscardedRateResume, hwBaseSecurityTcpIpAttackDiscardedRateRising, 
	      hwBaseSecurityTcpIpAttackDiscardedRateResume, hwBaseSecurityMaDiscardedRateRising, hwBaseSecurityMaDiscardedRateResume, hwBaseSecurityApplicationApperceiveDiscardedRateRising and hwBaseSecurityApplicationApperceiveDiscardedRateResume"
        REVISION "201305201404Z"
        DESCRIPTION
            "Add telnetv6Server(64),telnetv6Client(65),tftpv6Client(66),icmpv6(67),dnsv6(68),pimv6(69),sshv6Server(70),ospfv3(71),bgpv6(72),ftpv6Client(73),ftpv6Server(74) for hwAppliApperProtocol"
        REVISION "201304171111Z"
        DESCRIPTION
            "Add the VB object hwBaseSecurityStormControlInterfaceVlanID for hwBaseSecurityStormControlInterface and hwBaseSecurityStormControlInterfaceResume"
        REVISION "201304081653Z"
        DESCRIPTION
            "Add ipprotocol(19) for hwMaDefendProtocol ."
        REVISION "201303061443Z"
        DESCRIPTION
            "SOC add IPv6"
        REVISION "201404041301Z"
        DESCRIPTION
            "SOC modify SeqNo"
        REVISION "201503241012Z"
        DESCRIPTION
            "CP-CAR Add hwAppliApperProtocolDescirption hwTcpIpDefendProtocolDescirption"
          ::= { hwDatacomm 165 }  
          
                            
      hwBaseSecurityMIBObjects OBJECT IDENTIFIER ::= { hwSecurityMIB 1 }
      
      hwLocalUrpf OBJECT IDENTIFIER ::= { hwBaseSecurityMIBObjects 2 }
             
      hwLocalUrpfTable OBJECT-TYPE
          SYNTAX      SEQUENCE OF HwLocalUrpfEntry
          MAX-ACCESS  not-accessible
          STATUS      current
          DESCRIPTION
              " The table lists the information about local URPF Packets. "
          ::= { hwLocalUrpf 1 }
            
      hwLocalUrpfEntry OBJECT-TYPE
          SYNTAX HwLocalUrpfEntry
          MAX-ACCESS not-accessible
          STATUS current
          DESCRIPTION
              " The table lists the information about local URPF protection." 
          INDEX  { hwLocalUrpfChassisId , hwLocalUrpfSlotId }    
          ::= { hwLocalUrpfTable 1 }           
    
      HwLocalUrpfEntry  ::= 
          SEQUENCE{
              hwLocalUrpfChassisId
                  INTEGER,   
              hwLocalUrpfSlotId
                  Integer32,   
              hwLocalUrpfCurrentRateLow             
                  Integer32,
              hwLocalUrpfCurrentRateHigh             
                  Integer32,
              hwLocalUrpfNotifyEnabledStatus
                  EnabledStatus,
              hwLocalUrpfRateThreshold
                  Integer32, 
              hwLocalUrpfRateInterval
                  Integer32              
                  }                      

      hwLocalUrpfChassisId OBJECT-TYPE
          SYNTAX      INTEGER{
                       clc1(1),
                       clc2(2),
                       clc3(3),
                       clc4(4),
                       clc5(5),
                       clc6(6),
                       clc7(7),
                       clc8(8)
                      }
          MAX-ACCESS accessible-for-notify
          STATUS      current
          DESCRIPTION              
              "The Data index of local URPF,the chassis ID indicates the slot on which chassis is configured with URPF."
          ::= { hwLocalUrpfEntry 1 }
          
      hwLocalUrpfSlotId OBJECT-TYPE
          SYNTAX Integer32(1..16)
          MAX-ACCESS accessible-for-notify
          STATUS current
          DESCRIPTION
              "The Data index of local URPF,the slot configured with URPF."
          ::= { hwLocalUrpfEntry 2 }
          
      hwLocalUrpfCurrentRateLow OBJECT-TYPE
          SYNTAX      Integer32
          MAX-ACCESS  read-only
          STATUS      current
          DESCRIPTION              
              "The lower 32 bits discard number during the interval of local URPF.unit(packet)."
          ::= { hwLocalUrpfEntry 11 }
          
      hwLocalUrpfCurrentRateHigh OBJECT-TYPE
          SYNTAX      Integer32
          MAX-ACCESS  read-only
          STATUS      current
          DESCRIPTION
              "The upper 32 bits discard number during the interval of local URPF.unit(packet)."
          ::= { hwLocalUrpfEntry 12 } 
          
      hwLocalUrpfNotifyEnabledStatus OBJECT-TYPE
        SYNTAX        EnabledStatus
        MAX-ACCESS    read-only
        STATUS        current
        DESCRIPTION              
              "The alarm state of local URPF."
        ::= { hwLocalUrpfEntry 13 }
        
      hwLocalUrpfRateThreshold OBJECT-TYPE
        SYNTAX Integer32
        MAX-ACCESS read-only
        STATUS current
        DESCRIPTION
              "Local URPF's discard threshold during the configured interval.unit(packet)."
        ::= { hwLocalUrpfEntry 14 } 
      
      hwLocalUrpfRateInterval OBJECT-TYPE
        SYNTAX        Integer32
        MAX-ACCESS    read-only
        STATUS        current
        DESCRIPTION             
              "The detection interval of the local URPF.unit(s). "
        ::= { hwLocalUrpfEntry 15 }
           
      hwTcpIpDefend OBJECT IDENTIFIER ::= { hwBaseSecurityMIBObjects 3 }
                                  
      hwTcpIpDefendTable OBJECT-TYPE
          SYNTAX      SEQUENCE OF HwTcpIpDefendEntry
          MAX-ACCESS  not-accessible
          STATUS      current
          DESCRIPTION              
              "This table list the information about TCPIP protection."
          ::= { hwTcpIpDefend 1 }
            
      hwTcpIpDefendEntry OBJECT-TYPE
          SYNTAX      HwTcpIpDefendEntry
          MAX-ACCESS  not-accessible
          STATUS      current
          DESCRIPTION
              "This table list the information about TCPIP protection." 
          INDEX  { hwTcpIpDefendChassisId, 
                   hwTcpIpDefendSlotId,
                   hwTcpIpDefendType
                 }    
          ::= { hwTcpIpDefendTable 1 }  
                       
      HwTcpIpDefendEntry  ::= 
          SEQUENCE{
              hwTcpIpDefendChassisId
                  INTEGER,   
              hwTcpIpDefendSlotId
                  Integer32,   
              hwTcpIpDefendType
                  INTEGER,   
              hwTcpIpDefendCurrentRateLow             
                  Integer32,
              hwTcpIpDefendCurrentRateHigh             
                  Integer32,
              hwTcpIpDefendNotifyEnabledStatus
                  EnabledStatus,
              hwTcpIpDefendRateThreshold
                  Integer32,
              hwTcpIpDefendRateInterval
                  Integer32,
              hwTcpIpDefendProtocolDescirption
                  OCTET STRING	
                  }                  

      hwTcpIpDefendChassisId OBJECT-TYPE
          SYNTAX      INTEGER{
                       clc1(1),
                       clc2(2),
                       clc3(3),
                       clc4(4),
                       clc5(5),
                       clc6(6),
                       clc7(7),
                       clc8(8)
                      }
          MAX-ACCESS accessible-for-notify
          STATUS      current
          DESCRIPTION
              "The Data index of TCPIP protection,the chassis ID indicates the slot on which chassis is configured with TCPIP protection."
          ::= { hwTcpIpDefendEntry 1 }
          
      hwTcpIpDefendSlotId OBJECT-TYPE
          SYNTAX      Integer32(1..16)
          MAX-ACCESS accessible-for-notify
          STATUS      current
          DESCRIPTION
              "The Data index of TCPIP protection,the slot configured with TCPIP protection."
          ::= { hwTcpIpDefendEntry 2 }
          
      hwTcpIpDefendType OBJECT-TYPE
          SYNTAX      INTEGER{
                       abnormalPacket(1),
                       udpPacket(2),
                       tcpSyn(3),
                       ipFragmentation(4)
                      }
          MAX-ACCESS accessible-for-notify
          STATUS      current
          DESCRIPTION
              "The Data index of TCPIP protection,the type of TCPIP protection."
          ::= { hwTcpIpDefendEntry 3 }
          
      hwTcpIpDefendCurrentRateLow OBJECT-TYPE
          SYNTAX      Integer32
          MAX-ACCESS  read-only
          STATUS      current
          DESCRIPTION
              "The lower 32 bits discard number during the interval of TCPIP protection.unit(packet)."
          ::= { hwTcpIpDefendEntry 11 }
          
      hwTcpIpDefendCurrentRateHigh OBJECT-TYPE
          SYNTAX      Integer32
          MAX-ACCESS  read-only
          STATUS      current
          DESCRIPTION
              "The upper 32 bits discard number during the interval of TCPIP protection.unit(packet)."
          ::= { hwTcpIpDefendEntry 12 }
      
      hwTcpIpDefendNotifyEnabledStatus OBJECT-TYPE
          SYNTAX      EnabledStatus
          MAX-ACCESS  read-only
          STATUS      current
          DESCRIPTION
              "The alarm state of TCPIP protection."
          ::= { hwTcpIpDefendEntry 13 }
          
      hwTcpIpDefendRateThreshold OBJECT-TYPE
          SYNTAX      Integer32
          MAX-ACCESS  read-only
          STATUS      current
          DESCRIPTION
              "TCPIP protection's discard threshold during the configured interval.unit(packet)."
          ::= { hwTcpIpDefendEntry 14 } 
          
      hwTcpIpDefendRateInterval OBJECT-TYPE
          SYNTAX      Integer32
          MAX-ACCESS  read-only
          STATUS      current
          DESCRIPTION
              "The detection interval of TCPIP protection.unit(s)."
          ::= { hwTcpIpDefendEntry 15 }
	  
      hwTcpIpDefendProtocolDescirption OBJECT-TYPE
          SYNTAX OCTET STRING
          MAX-ACCESS  read-only
          STATUS      current
          DESCRIPTION
              "The descirption of Protocol."
          ::= { hwTcpIpDefendEntry 16 }		  
          
      hwMaDefend OBJECT IDENTIFIER ::= { hwBaseSecurityMIBObjects 4 }

      hwMaDefendTable OBJECT-TYPE
          SYNTAX      SEQUENCE OF HwMaDefendEntry
          MAX-ACCESS  not-accessible
          STATUS      current
          DESCRIPTION
              "This table list the information about management and application protection."
          ::= { hwMaDefend 1 }
            
      hwMaDefendEntry OBJECT-TYPE
          SYNTAX      HwMaDefendEntry
          MAX-ACCESS  not-accessible
          STATUS      current
          DESCRIPTION
              "This table list the information about management and application protection."
          INDEX  { hwMaDefendChassisId,
                   hwMaDefendSlotId, 
                   hwMaDefendProtocol}    
          ::= { hwMaDefendTable 1 }  
                       
      HwMaDefendEntry  ::= 
          SEQUENCE{
              hwMaDefendChassisId
                  INTEGER,   
              hwMaDefendSlotId
                  Integer32,
              hwMaDefendProtocol
                  INTEGER,  
              hwMaDefendCurrentRateLow             
                  Integer32,
              hwMaDefendCurrentRateHigh             
                  Integer32,
              hwMaDefendNotifyEnabledStatus
                  EnabledStatus,
              hwMaDefendRateThreshold
                  Integer32,
              hwMaDefendRateInterval
                  Integer32           
                  }                  

      hwMaDefendChassisId OBJECT-TYPE
          SYNTAX     INTEGER{
                     clc1(1),
                     clc2(2),
                     clc3(3),
                     clc4(4),
                     clc5(5),
                     clc6(6),
                     clc7(7),
                     clc8(8)
                     }
          MAX-ACCESS accessible-for-notify
          STATUS     current
          DESCRIPTION
              "The Data index of management and application protection,the chassis ID indicates the slot on which chassis is configured with management and application protection."
          ::= { hwMaDefendEntry 1 }
          
      hwMaDefendSlotId OBJECT-TYPE
          SYNTAX     Integer32(1..16)
          MAX-ACCESS accessible-for-notify
          STATUS     current
          DESCRIPTION
              "The Data index of management and application protection,the slots configured with management and application protection."
          ::= { hwMaDefendEntry 2 }
      
      hwMaDefendProtocol OBJECT-TYPE
        SYNTAX INTEGER {ftp(1),ssh(2),snmp(3),telnet(4),tftp(5),bgp(6),ldp(7),rsvp(8),ospf(9),rip(10),isis(11),pim(12),ntp(13),lspping(14),dhcpc(15),dhcpr(16),tcp(17),udp(18),ipprotocol(19)}

          MAX-ACCESS accessible-for-notify
          STATUS     current
          DESCRIPTION
              "The Data index of management and application protection,the protocols configured in management and application protection."
          ::= { hwMaDefendEntry 3 }
          
      hwMaDefendCurrentRateLow OBJECT-TYPE
          SYNTAX     Integer32
          MAX-ACCESS read-only
          STATUS     current
          DESCRIPTION
              "The lower 32 bits discard number during the interval of management and application protection.unit(packet)."
          ::= { hwMaDefendEntry 11 }
          
      hwMaDefendCurrentRateHigh OBJECT-TYPE
          SYNTAX     Integer32
          MAX-ACCESS read-only
          STATUS     current
          DESCRIPTION
              "The upper 32 bits discard number during the interval of management and application protection.unit(packet)."
          ::= { hwMaDefendEntry 12 }
      
      hwMaDefendNotifyEnabledStatus OBJECT-TYPE
        SYNTAX       EnabledStatus
        MAX-ACCESS   read-only
        STATUS       current
        DESCRIPTION
              "The alarm state of management and application protection."
            ::= { hwMaDefendEntry 13 }
            
      hwMaDefendRateThreshold OBJECT-TYPE
          SYNTAX     Integer32
          MAX-ACCESS read-only
          STATUS     current
          DESCRIPTION
              "The discard threshold of management and application protection during the configured interval.unit(packet)."
          ::= { hwMaDefendEntry 14 }
          
      hwMaDefendRateInterval OBJECT-TYPE
          SYNTAX     Integer32
          MAX-ACCESS read-only
          STATUS     current
          DESCRIPTION
              "The detection interval of management and application protection. unit(s)."
          ::= { hwMaDefendEntry 15 }  
                     
          
      hwApplicationApperceive OBJECT IDENTIFIER ::= { hwBaseSecurityMIBObjects 5 }
      
      hwApplicationApperceiveTable OBJECT-TYPE
          SYNTAX      SEQUENCE OF HwApplicationApperceiveEntry
          MAX-ACCESS  not-accessible
          STATUS      current
          DESCRIPTION
              "This table list the information about Application-Apperceive protection."
          ::= { hwApplicationApperceive 1 }
            
      hwApplicationApperceiveEntry OBJECT-TYPE
          SYNTAX      HwApplicationApperceiveEntry
          MAX-ACCESS  not-accessible
          STATUS      current
          DESCRIPTION
              "This table list the information about Application-Apperceive protection."
          INDEX  { hwAppliApperChassisId,
                   hwAppliApperSlotId, 
                   hwAppliApperProtocol}    
          ::= { hwApplicationApperceiveTable 1 }  
                       
      HwApplicationApperceiveEntry  ::= 
          SEQUENCE{
              hwAppliApperChassisId
                  INTEGER,   
              hwAppliApperSlotId
                  Integer32,
              hwAppliApperProtocol
                  INTEGER,  
              hwAppliApperCurrentRateLow             
                  Integer32,
              hwAppliApperCurrentRateHigh             
                  Integer32,
              hwAppliApperNotifyEnabledStatus
                  EnabledStatus,
              hwAppliApperRateThreshold
                  Integer32,
              hwAppliApperRateInterval
                  Integer32,
	      hwAppliApperProtocolDescirption
		  OCTET STRING
                  }                  

      hwAppliApperChassisId OBJECT-TYPE
          SYNTAX     INTEGER{
                     clc1(1),
                     clc2(2),
                     clc3(3),
                     clc4(4),
                     clc5(5),
                     clc6(6),
                     clc7(7),
                     clc8(8)
                     }
          MAX-ACCESS accessible-for-notify
          STATUS     current
          DESCRIPTION
              "The Data index of Application-Apperceive protection,the chassis ID indicates the slot on which chassis is configured with Application-Apperceive protection."
          ::= { hwApplicationApperceiveEntry 1 }
          
      hwAppliApperSlotId OBJECT-TYPE
          SYNTAX Integer32(1..16)
          MAX-ACCESS accessible-for-notify
          STATUS current
          DESCRIPTION
              "The Data index of Application-Apperceive protection,the slots configured with Application-Apperceive protection."
          ::= { hwApplicationApperceiveEntry 2 }
          
      hwAppliApperProtocol OBJECT-TYPE
        SYNTAX INTEGER {ftpServer(1),sshServer(2),snmp(3),telnetServer(4),tftp(5),bgp(6),ldp(7),rsvp(8),ospf(9),rip(10),isis(11),sftpSever(12),icmp(13),msdp(14),pim(15),ipv4Arp(16),bpdu(17),dhcp(18),lacp(19),ntp(20),radius(21),hwTacacs(22),lspPing(23),igmp(24),vgmp(25),rrpp(26),vrrp(27),bfd(28),mplsOam(29),eth8021ag(30),ftpClient(31),telnetClient(32),sshClient(33),sftpClient(34),dnsClient(35),webAuthServer(36),telnetv6Server(64),telnetv6Client(65),tftpv6Client(66),icmpv6(67),dnsv6(68),pimv6(69),sshv6Server(70),ospfv3(71),bgpv6(72),ftpv6Client(73),ftpv6Server(74)}

          MAX-ACCESS accessible-for-notify
          STATUS current
          DESCRIPTION
              "The Data index of Application-Apperceive protection,the protocol configured in Application-Apperceive protection."
          ::= { hwApplicationApperceiveEntry 3 }
          
      hwAppliApperCurrentRateLow OBJECT-TYPE
          SYNTAX Integer32
          MAX-ACCESS read-only
          STATUS current
          DESCRIPTION
              "The lower 32 bits discard number during the interval of Application-Apperceive protection.unit(packet)."
          ::= { hwApplicationApperceiveEntry 11 }
          
      hwAppliApperCurrentRateHigh OBJECT-TYPE
          SYNTAX Integer32
          MAX-ACCESS read-only
          STATUS current
          DESCRIPTION
              "The upper 32 bits discard number during the interval of Application-Apperceive protection.unit(packet)."
          ::= { hwApplicationApperceiveEntry 12 }
      
      hwAppliApperNotifyEnabledStatus OBJECT-TYPE
        SYNTAX EnabledStatus
        MAX-ACCESS read-only
        STATUS current
        DESCRIPTION
            "The alarm state of Application-Apperceive protection."
        ::= { hwApplicationApperceiveEntry 13 }
            
      hwAppliApperRateThreshold OBJECT-TYPE
          SYNTAX Integer32
          MAX-ACCESS read-only
          STATUS current
          DESCRIPTION
              "The discard threshold of Application-Apperceive protection during the configured interval.unit(packet)."
          ::= { hwApplicationApperceiveEntry 14 }     
      
      hwAppliApperRateInterval OBJECT-TYPE
          SYNTAX Integer32
          MAX-ACCESS read-only
          STATUS current
          DESCRIPTION
              "The detect interval of Application-Apperceive protection. unit(s)."
          ::= { hwApplicationApperceiveEntry 15 }
	  
      hwAppliApperProtocolDescirption OBJECT-TYPE
          SYNTAX OCTET STRING
          MAX-ACCESS  read-only
          STATUS      current
          DESCRIPTION
              "The descirption of Protocol."
          ::= { hwApplicationApperceiveEntry 16 }      
      
      hwDefdPortVlan OBJECT IDENTIFIER ::= { hwBaseSecurityMIBObjects 6 } 
      
      hwDefdPortVlanTable OBJECT-TYPE
      	  SYNTAX		SEQUENCE OF HwDefdPortVlanEntry
      	  MAX-ACCESS    not-accessible
      	  STATUS		current
      	  DESCRIPTION
      	  	" The table lists the information about defend port vlan packet. "   
      	  ::= { hwDefdPortVlan 1 }        
      	  

      hwDefdPortVlanEntry OBJECT-TYPE
          SYNTAX      HwDefdPortVlanEntry
          MAX-ACCESS  not-accessible
          STATUS      current
          DESCRIPTION
              "This table list the information about defend port vlan ."
          INDEX  { hwDefdPortVlanIfIndex }    
          ::= { hwDefdPortVlanTable 1 }  
      
      HwDefdPortVlanEntry ::=   
          SEQUENCE{       
              hwDefdPortVlanIfIndex          
                  Integer32,    
              hwDefdPortVlanIfName
                  OCTET STRING,  
              hwDefdPortVlanId
                  Integer32,  
              hwDefdPortVlanCheckProtocol
                  OCTET STRING	  
              }       		
  
      hwDefdPortVlanIfIndex OBJECT-TYPE
          SYNTAX Integer32(1..2147483647)
          MAX-ACCESS accessible-for-notify
          STATUS current
          DESCRIPTION
              "Interface Index, equal to ifIndex."
          ::= { hwDefdPortVlanEntry 1 } 
          
      hwDefdPortVlanIfName OBJECT-TYPE
          SYNTAX OCTET STRING (SIZE (1..256))
          MAX-ACCESS read-only
          STATUS current
          DESCRIPTION
              "The name of the interface."
          ::= { hwDefdPortVlanEntry 2 }   
              
      hwDefdPortVlanId OBJECT-TYPE
          SYNTAX     Integer32(0..4096)
          MAX-ACCESS read-only
          STATUS     current
          DESCRIPTION
              "The Data index of defend port vlan."
          ::= { hwDefdPortVlanEntry 3 }
          
          
      hwDefdPortVlanCheckProtocol OBJECT-TYPE
          SYNTAX OCTET STRING (SIZE (1..100)) 
          MAX-ACCESS read-only
          STATUS current
          DESCRIPTION
              "Check protocol name."
          ::= { hwDefdPortVlanEntry 4 }
          

     hwSocAttackTrapObject OBJECT IDENTIFIER ::= { hwBaseSecurityMIBObjects 7 }
		

     hwSocAttackInfoTable OBJECT-TYPE
			SYNTAX SEQUENCE OF HwSocAttackInfoEntry
			MAX-ACCESS not-accessible
			STATUS current
			DESCRIPTION
				" The table lists the information about Security Operation Center. "
			::= { hwSocAttackTrapObject 1 }
		

		hwSocAttackInfoEntry OBJECT-TYPE
			SYNTAX HwSocAttackInfoEntry
			MAX-ACCESS not-accessible
			STATUS current
			DESCRIPTION
				"This table list the information about Securty Operation Center detected one attack."
			INDEX { hwSocAttackSeqNo }
			::= { hwSocAttackInfoTable 1 }
		
		HwSocAttackInfoEntry ::=
			SEQUENCE { 
				hwSocAttackSeqNo
					Integer32,
				hwSocAttackPossib
					OCTET STRING,
				hwSocAttackReason
					OCTET STRING,
				hwSocAttackIfName
					OCTET STRING,
				hwSocAttackSubIfName
					OCTET STRING,
				hwSocAttackVlanIndex
					OCTET STRING,
				hwSocAttackUserQinQIndex
					OCTET STRING,
				hwSocAttackMacAddr
					OCTET STRING,
				hwSocAttackIPAddr
					OCTET STRING,
				hwSocAttackIPv6Addr 
					OCTET STRING								
			 }


		hwSocAttackSeqNo OBJECT-TYPE
			SYNTAX Integer32 (1..16777215)
			MAX-ACCESS read-only
			STATUS current
			DESCRIPTION
				"The sequence number of attack infomation."
			::= { hwSocAttackInfoEntry 1 }
			
		hwSocAttackPossib OBJECT-TYPE
			SYNTAX OCTET STRING (SIZE (0..32))
			MAX-ACCESS read-only
			STATUS current
			DESCRIPTION
				"The prabability of the attack ."
			::= { hwSocAttackInfoEntry 2 }
		

		hwSocAttackReason OBJECT-TYPE
			SYNTAX OCTET STRING (SIZE (0..63))
			MAX-ACCESS read-only
			STATUS current
			DESCRIPTION
				"The reason of the attack ."
			::= { hwSocAttackInfoEntry 3 }
		

		hwSocAttackIfName OBJECT-TYPE
			SYNTAX OCTET STRING (SIZE (0..63))
			MAX-ACCESS read-only
			STATUS current
			DESCRIPTION
				"The interface of the attack"
			::= { hwSocAttackInfoEntry 4 }
		

		hwSocAttackSubIfName OBJECT-TYPE
			SYNTAX OCTET STRING (SIZE (0..256))
			MAX-ACCESS read-only
			STATUS current
			DESCRIPTION
				"The sub-interface of the attack"
			::= { hwSocAttackInfoEntry 5 }
		

		hwSocAttackVlanIndex OBJECT-TYPE
			SYNTAX OCTET STRING (SIZE (0..32))
			MAX-ACCESS read-only
			STATUS current
			DESCRIPTION
				"The vlan of the attack"
			::= { hwSocAttackInfoEntry 6 }
		

		hwSocAttackUserQinQIndex OBJECT-TYPE
			SYNTAX OCTET STRING (SIZE (0..64))
			MAX-ACCESS read-only
			STATUS current
			DESCRIPTION
				"The UserQinQ of the attack"
			::= { hwSocAttackInfoEntry 7 }
		

		hwSocAttackMacAddr OBJECT-TYPE
			SYNTAX OCTET STRING (SIZE (0..128))
			MAX-ACCESS read-only
			STATUS current
			DESCRIPTION
				"The MAC of the attack"
			::= { hwSocAttackInfoEntry 8 }
		

		hwSocAttackIPAddr OBJECT-TYPE
			SYNTAX OCTET STRING (SIZE (0..128))
			MAX-ACCESS read-only
			STATUS current
			DESCRIPTION
				"The IP of the attack"
			::= { hwSocAttackInfoEntry 9 }
			
		hwSocAttackIPv6Addr OBJECT-TYPE
			SYNTAX OCTET STRING (SIZE (0..128))
			MAX-ACCESS read-only
			STATUS current
			DESCRIPTION
				"The IPv6 of the attack"
			::= { hwSocAttackInfoEntry 10 }	
			
    
  
      hwBaseSecurityNotifications OBJECT IDENTIFIER ::= { hwBaseSecurityMIBObjects 11 }
      
      hwBaseSecurityUrpfDiscardedRateRising NOTIFICATION-TYPE
          OBJECTS { 
	      hwLocalUrpfCurrentRateLow, 
	      hwLocalUrpfCurrentRateHigh, 
	      hwLocalUrpfRateThreshold,
	      hwLocalUrpfChassisId, 
              hwLocalUrpfSlotId}
          STATUS current
          DESCRIPTION 
              " The discard packets exceed the threshold of local URPF protection."
          ::= { hwBaseSecurityNotifications 1 }
            
      hwBaseSecurityUrpfDiscardedRateResume NOTIFICATION-TYPE
          OBJECTS { 
	      hwLocalUrpfCurrentRateLow, 
	      hwLocalUrpfCurrentRateHigh, 
	      hwLocalUrpfRateThreshold,
	      hwLocalUrpfChassisId, 
              hwLocalUrpfSlotId}
          STATUS current
          DESCRIPTION 
              " The alarm of local URPF is resumed."
          ::= { hwBaseSecurityNotifications  2 } 
          
      hwBaseSecurityTcpIpAttackDiscardedRateRising NOTIFICATION-TYPE
          OBJECTS {
	      hwTcpIpDefendCurrentRateLow, 
	      hwTcpIpDefendCurrentRateHigh,
	      hwTcpIpDefendRateThreshold, 
	      hwTcpIpDefendRateInterval,
              hwTcpIpDefendChassisId, 
              hwTcpIpDefendSlotId, 
              hwTcpIpDefendType,
	      hwTcpIpDefendProtocolDescirption}
          STATUS current
          DESCRIPTION 
              " The discard packets exceed the threshold of TCPIP protection. "
          ::= { hwBaseSecurityNotifications 3 }
            
      hwBaseSecurityTcpIpAttackDiscardedRateResume NOTIFICATION-TYPE
          OBJECTS { 
	      hwTcpIpDefendCurrentRateLow, 
	      hwTcpIpDefendCurrentRateHigh,
	      hwTcpIpDefendRateThreshold, 
	      hwTcpIpDefendRateInterval,
	      hwTcpIpDefendChassisId, 
              hwTcpIpDefendSlotId, 
              hwTcpIpDefendType,
	      hwTcpIpDefendProtocolDescirption}
          STATUS current
          DESCRIPTION 
              " The alarm of TCPIP protection is resumed. "
          ::= { hwBaseSecurityNotifications  4 }
          
      hwBaseSecurityMaDiscardedRateRising NOTIFICATION-TYPE
          OBJECTS { 
	      hwMaDefendCurrentRateLow, 
	      hwMaDefendCurrentRateHigh, 
	      hwMaDefendRateThreshold, 
	      hwMaDefendRateInterval,
              hwMaDefendChassisId, 
              hwMaDefendSlotId, 
              hwMaDefendProtocol}
          STATUS current
          DESCRIPTION 
              " The discard packets exceed the threshold of management and application protection."
          ::= { hwBaseSecurityNotifications 5 }
            
      hwBaseSecurityMaDiscardedRateResume NOTIFICATION-TYPE
          OBJECTS { 
	      hwMaDefendCurrentRateLow, 
	      hwMaDefendCurrentRateHigh, 
	      hwMaDefendRateThreshold, 
	      hwMaDefendRateInterval,
	      hwMaDefendChassisId, 
              hwMaDefendSlotId, 
              hwMaDefendProtocol}
          STATUS current
          DESCRIPTION 
              " The alarm of management and application protection is resumed. "
          ::= { hwBaseSecurityNotifications  6 }
          
      hwBaseSecurityApplicationApperceiveDiscardedRateRising NOTIFICATION-TYPE
          OBJECTS {	  
	      hwAppliApperCurrentRateLow, 
	      hwAppliApperCurrentRateHigh,
	      hwAppliApperRateThreshold, 
	      hwAppliApperRateInterval,
		  hwAppliApperChassisId, 
              hwAppliApperSlotId, 
              hwAppliApperProtocol,
	      hwAppliApperProtocolDescirption}
          STATUS current
          DESCRIPTION 
              " The discard packets exceed the threshold of Application-Apperceive protection. "
          ::= { hwBaseSecurityNotifications 7 }
            
      hwBaseSecurityApplicationApperceiveDiscardedRateResume NOTIFICATION-TYPE
          OBJECTS { 
	      hwAppliApperCurrentRateLow, 
	      hwAppliApperCurrentRateHigh,
	      hwAppliApperRateThreshold, 
	      hwAppliApperRateInterval,
		  hwAppliApperChassisId, 
              hwAppliApperSlotId, 
              hwAppliApperProtocol,
	      hwAppliApperProtocolDescirption}
          STATUS current
          DESCRIPTION 
              "The alarm of Application-Apperceive protection is resumed."
          ::= { hwBaseSecurityNotifications  8 }  
                   
     hwBaseSecurityStormControlInterface NOTIFICATION-TYPE
          OBJECTS { 
           hwBaseSecurityStormControlInterfaceChassisId, 
           hwBaseSecurityStormControlInterfaceSlotId, 
            hwBaseSecurityStormControlInterfaceName,
            hwBaseSecurityStormControlInterfaceVlanID}
          STATUS current
          DESCRIPTION 
              "The alarm of storm-control detection."
          ::= { hwBaseSecurityNotifications  9 }
                   
     hwBaseSocAttackTrap NOTIFICATION-TYPE
	 OBJECTS { 
             hwSocAttackSeqNo, 
             hwSocAttackPossib, 
	     hwSocAttackReason, 
	     hwSocAttackIfName, 
	     hwSocAttackSubIfName, 
	     hwSocAttackVlanIndex, 
	     hwSocAttackUserQinQIndex, 
	     hwSocAttackMacAddr, 
	     hwSocAttackIPAddr, 
	     hwSocAttackIPv6Addr }
		   STATUS current
		   DESCRIPTION 
		   "An attack occur on the Network. "
	::= { hwBaseSecurityNotifications 12 }
		

     hwBaseSocAttackResumeTrap NOTIFICATION-TYPE
	 OBJECTS {
             hwSocAttackSeqNo, 
             hwSocAttackPossib, 
	     hwSocAttackReason, 
	     hwSocAttackIfName, 
	     hwSocAttackSubIfName, 
	     hwSocAttackVlanIndex, 
	     hwSocAttackUserQinQIndex, 
	     hwSocAttackMacAddr, 
	     hwSocAttackIPAddr, 
	     hwSocAttackIPv6Addr }
		   STATUS current
		   DESCRIPTION 
		   "An attack cancels on the Network."
	::= { hwBaseSecurityNotifications 13 }
                      
    hwBaseSecurityStormControlInterfaceResume NOTIFICATION-TYPE
        OBJECTS {
            hwBaseSecurityStormControlInterfaceChassisId,
            hwBaseSecurityStormControlInterfaceSlotId,
            hwBaseSecurityStormControlInterfaceName,
            hwBaseSecurityStormControlInterfaceVlanID}
        STATUS current
        DESCRIPTION
            "L2 loop detect alarm cleared."
        ::= { hwBaseSecurityNotifications 14 }

    hwBaseSecurityTtlExpiredLoop NOTIFICATION-TYPE
        OBJECTS {
            hwTtlExpiredLoopChassisId,
            hwTtlExpiredLoopSlotId,
            hwTtlExpiredLoopLastRateLow,
            hwTtlExpiredLoopLastRateHigh,
            hwTtlExpiredLoopCurrentRateLow,
            hwTtlExpiredLoopCurrentRateHigh,
            hwTtlExpiredLoopRateInterval,
            hwTtlExpiredLoopRateThreshold}
        STATUS current
        DESCRIPTION
            "The alarm of ttl-expired loop detection."
        ::= { hwBaseSecurityNotifications 15 }

    hwBaseSecurityTtlExpiredLoopResume NOTIFICATION-TYPE
        OBJECTS {
            hwTtlExpiredLoopChassisId,
            hwTtlExpiredLoopSlotId,
            hwTtlExpiredLoopLastRateLow,
            hwTtlExpiredLoopLastRateHigh,
            hwTtlExpiredLoopCurrentRateLow,
            hwTtlExpiredLoopCurrentRateHigh,
            hwTtlExpiredLoopRateInterval,
            hwTtlExpiredLoopRateThreshold}
        STATUS current
        DESCRIPTION
            "TTL-Expired loop alarm cleared."
        ::= { hwBaseSecurityNotifications 16 }

     hwBaseArpVlanCarTrap NOTIFICATION-TYPE
	 OBJECTS { 
	     hwBaseArpVlanCarLogIfName,
	     hwBaseArpVlanCarPhyIfName}
		   STATUS current
		   DESCRIPTION 
		   "ARP VLAN CAR took effect on an interface, which may be because a loop occurred on the interface."
	::= { hwBaseSecurityNotifications 17 }
		

     hwBaseArpVlanCarResumeTrap NOTIFICATION-TYPE
	 OBJECTS {
	     hwBaseArpVlanCarLogIfName,
	     hwBaseArpVlanCarPhyIfName}
		   STATUS current
		   DESCRIPTION 
		   "ARP VLAN CAR become ineffective on an interface."
	::= { hwBaseSecurityNotifications 18 }

      hwBaseSecurityAntiAttackRateRising NOTIFICATION-TYPE
          OBJECTS { 
          hwAntiAttackType,
          hwAntiAttackRateThreshold,
          hwAntiAttackCurrentRate}
          STATUS current
          DESCRIPTION
              " The rate of packets exceed the threshold of anti-attack alarm. "
          ::= { hwBaseSecurityNotifications 19 }

      hwBaseSecurityAntiAttackRateResume NOTIFICATION-TYPE
          OBJECTS {
          hwAntiAttackType,
          hwAntiAttackRateThreshold, 
          hwAntiAttackCurrentRate}
          STATUS current
          DESCRIPTION
              " The alarm of anti-attack alarm is resumed. "
          ::= { hwBaseSecurityNotifications  20 }  
          
      hwMacFilter OBJECT IDENTIFIER ::= { hwBaseSecurityMIBObjects 12 }

      hwMacFilterModeTable OBJECT-TYPE
          SYNTAX      SEQUENCE OF HwMacFilterModeEntry
          MAX-ACCESS  not-accessible
          STATUS      current
          DESCRIPTION
              "This table list the information about mac-filter statistics."
          ::= { hwMacFilter 1 }
            
      hwMacFilterModeEntry  OBJECT-TYPE
          SYNTAX      HwMacFilterModeEntry
          MAX-ACCESS  not-accessible
          STATUS      current
          DESCRIPTION
              "This table list the information about mac-filter statistics."
          INDEX  { hwMacFilterIfIndex }
          ::= { hwMacFilterModeTable 1 }
                       
      HwMacFilterModeEntry  ::= 
          SEQUENCE{
              hwMacFilterIfIndex
                  Integer32,
              hwMacFilterInterface
                  DisplayString,
              hwMacFilterEnableMode
                  INTEGER,
              hwMacFilterMatchNum
                  Integer32
                  }
 
      hwMacFilterIfIndex OBJECT-TYPE
            SYNTAX     Integer32
            MAX-ACCESS not-accessible
            STATUS current
            DESCRIPTION
                "Mac-filter interface index."
            ::= { hwMacFilterModeEntry 1 }

      hwMacFilterInterface OBJECT-TYPE
            SYNTAX DisplayString (SIZE (1..128))
            MAX-ACCESS read-only
            STATUS current
            DESCRIPTION
                "Mac-filter interface name."
            ::= { hwMacFilterModeEntry 2 }

      hwMacFilterEnableMode OBJECT-TYPE
            SYNTAX     INTEGER{
                           none(0),
                           whitelist(1),
                           balcklist(2)
                              }
            MAX-ACCESS read-only
            STATUS current
            DESCRIPTION
                "Mac-filter enable mode."
            ::= { hwMacFilterModeEntry 3 }

      hwMacFilterMatchNum OBJECT-TYPE
          SYNTAX     Integer32
          MAX-ACCESS read-only
          STATUS     current
          DESCRIPTION
              "Mac-filter if-match number."
          ::= { hwMacFilterModeEntry 4 }
  
      hwMacFilterMacAddrTable OBJECT-TYPE
          SYNTAX      SEQUENCE OF HwMacFilterMacAddrEntry
          MAX-ACCESS  not-accessible
          STATUS      current
          DESCRIPTION
              "This table list the information about mac-filter if-match mac-address."
          ::= { hwMacFilter 2 }
            
      hwMacFilterMacAddrEntry OBJECT-TYPE
          SYNTAX      HwMacFilterMacAddrEntry
          MAX-ACCESS  not-accessible
          STATUS      current
          DESCRIPTION
              "This table list the information about mac-filter if-match mac-address."
          INDEX  { hwMacFilterIfindex,
                   hwMacFilterMacAddr}
          ::= { hwMacFilterMacAddrTable 1 }  
                       
      HwMacFilterMacAddrEntry  ::= 
          SEQUENCE{
              hwMacFilterIfindex
                  Integer32,
              hwMacFilterInterfaceBuf
                  DisplayString,
              hwMacFilterMacAddr
                  DisplayString
                  } 

      hwMacFilterIfindex OBJECT-TYPE
          SYNTAX     Integer32
          MAX-ACCESS not-accessible
          STATUS current
          DESCRIPTION
              "Mac-filter interface index."
          ::= { hwMacFilterMacAddrEntry 1 }

      hwMacFilterInterfaceBuf OBJECT-TYPE
          SYNTAX DisplayString (SIZE (1..128))
          MAX-ACCESS read-only
          STATUS current
          DESCRIPTION
              "Mac-filter interface name."
          ::= { hwMacFilterMacAddrEntry 2 }

      hwMacFilterMacAddr OBJECT-TYPE
          SYNTAX DisplayString (SIZE (1..100))
          MAX-ACCESS not-accessible
          STATUS current
          DESCRIPTION
              "Mac-filter if-match mac-address."
          ::= { hwMacFilterMacAddrEntry 3 }
          
    hwBaseSecurityStormControlInterfaceObjects OBJECT IDENTIFIER ::= { hwBaseSecurityMIBObjects 13 }

    hwBaseSecurityStormControlInterfaceTable OBJECT-TYPE
        SYNTAX  SEQUENCE OF HwBaseSecurityStormControlInterfaceEntry
        MAX-ACCESS not-accessible
        STATUS current
        DESCRIPTION
            "A Table about storm-control interface information."
        ::= { hwBaseSecurityStormControlInterfaceObjects 1 }


    hwBaseSecurityStormControlInterfaceEntry OBJECT-TYPE
        SYNTAX HwBaseSecurityStormControlInterfaceEntry 
        MAX-ACCESS not-accessible
        STATUS current
        DESCRIPTION
            "Description."
        INDEX { hwBaseSecurityStormControlInterfaceChassisId,hwBaseSecurityStormControlInterfaceSlotId }
        ::= { hwBaseSecurityStormControlInterfaceTable 1 }


    HwBaseSecurityStormControlInterfaceEntry ::= SEQUENCE {
        hwBaseSecurityStormControlInterfaceChassisId 
            Integer32,
        hwBaseSecurityStormControlInterfaceSlotId 
            Integer32,
        hwBaseSecurityStormControlInterfaceName 
            OCTET STRING,
        hwBaseSecurityStormControlInterfaceVlanID 
            Integer32
        }


    hwBaseSecurityStormControlInterfaceChassisId OBJECT-TYPE
        SYNTAX Integer32 (1..128)
        MAX-ACCESS accessible-for-notify
        STATUS current
        DESCRIPTION
            "The chassis ID indicates the slot on which chassis is configured with storm control."
        ::= { hwBaseSecurityStormControlInterfaceEntry 1 }


    hwBaseSecurityStormControlInterfaceSlotId OBJECT-TYPE
        SYNTAX Integer32 (1..128)
        MAX-ACCESS accessible-for-notify
        STATUS current
        DESCRIPTION
            "The slot configured with storm control."
        ::= { hwBaseSecurityStormControlInterfaceEntry 2 }


    hwBaseSecurityStormControlInterfaceName OBJECT-TYPE
        SYNTAX OCTET STRING (SIZE (0..63))
        MAX-ACCESS read-only
        STATUS current
        DESCRIPTION
            "The interface name."
        ::= { hwBaseSecurityStormControlInterfaceEntry 3 }


    hwBaseSecurityStormControlInterfaceVlanID OBJECT-TYPE
        SYNTAX Integer32 (0..4094)
        MAX-ACCESS accessible-for-notify
        STATUS current
        DESCRIPTION
            "The VlanID of VlanIF which the interface join in."
        ::= { hwBaseSecurityStormControlInterfaceEntry 4 }

    hwBaseArpVlanCarTrapObject OBJECT IDENTIFIER ::= { hwBaseSecurityMIBObjects 14 }

    hwBaseArpVlanCarInfoTable OBJECT-TYPE
        SYNTAX  SEQUENCE OF HwBaseArpVlanCarInfoEntry 
        MAX-ACCESS not-accessible
        STATUS current
        DESCRIPTION
            "A Table about arp vlan car information."
        ::= { hwBaseArpVlanCarTrapObject 1 }


    hwBaseArpVlanCarInfoEntry OBJECT-TYPE
        SYNTAX HwBaseArpVlanCarInfoEntry 
        MAX-ACCESS not-accessible
        STATUS current
        DESCRIPTION
            "Description."
        INDEX { hwBaseArpVlanCarLogIfName,hwBaseArpVlanCarPhyIfName }
        ::= { hwBaseArpVlanCarInfoTable 1 }


    HwBaseArpVlanCarInfoEntry ::= SEQUENCE {
        hwBaseArpVlanCarLogIfName 
            OCTET STRING,
        hwBaseArpVlanCarPhyIfName 
            OCTET STRING,
        hwBaseArpVlanCarVlanId
            Integer32
        }

    hwBaseArpVlanCarLogIfName OBJECT-TYPE
        SYNTAX OCTET STRING
        MAX-ACCESS read-only
        STATUS current
        DESCRIPTION
            "The logic interface name."
        ::= { hwBaseArpVlanCarInfoEntry 1 }


    hwBaseArpVlanCarPhyIfName OBJECT-TYPE
        SYNTAX OCTET STRING
        MAX-ACCESS read-only
        STATUS current
        DESCRIPTION
            "The physical interface name."
        ::= { hwBaseArpVlanCarInfoEntry 2 }

    hwBaseArpVlanCarVlanId OBJECT-TYPE
        SYNTAX Integer32 (0..4094)
        MAX-ACCESS read-only
        STATUS current
        DESCRIPTION
            "The VlanId of arp vlan car."
        ::= { hwBaseArpVlanCarInfoEntry 3 }


    hwTtlExpiredLoop OBJECT IDENTIFIER ::= { hwBaseSecurityMIBObjects 15 }

    hwTtlExpiredLoopTable OBJECT-TYPE
        SYNTAX  SEQUENCE OF HwTtlExpiredLoopEntry
        MAX-ACCESS not-accessible
        STATUS current
        DESCRIPTION
            "A Table about TTL-expired loop information."
        ::= { hwTtlExpiredLoop 1 }


    hwTtlExpiredLoopEntry OBJECT-TYPE
        SYNTAX HwTtlExpiredLoopEntry 
        MAX-ACCESS not-accessible
        STATUS current
        DESCRIPTION
            "Description."
        INDEX { hwTtlExpiredLoopChassisId,hwTtlExpiredLoopSlotId }
        ::= { hwTtlExpiredLoopTable 1 }


    HwTtlExpiredLoopEntry ::= SEQUENCE {
        hwTtlExpiredLoopChassisId 
            Unsigned32,
        hwTtlExpiredLoopSlotId 
            Unsigned32,
        hwTtlExpiredLoopLastRateLow 
            Unsigned32,
        hwTtlExpiredLoopLastRateHigh 
            Unsigned32,
        hwTtlExpiredLoopCurrentRateLow 
            Unsigned32,
        hwTtlExpiredLoopCurrentRateHigh 
            Unsigned32,
        hwTtlExpiredLoopRateInterval 
            Unsigned32,
        hwTtlExpiredLoopRateThreshold 
            Unsigned32
        }

 
    hwTtlExpiredLoopChassisId OBJECT-TYPE
        SYNTAX Unsigned32
        MAX-ACCESS accessible-for-notify
        STATUS current
        DESCRIPTION
            "The chassis ID indicates the chassis ttl-expired loop occur."
        ::= { hwTtlExpiredLoopEntry 1 }


    hwTtlExpiredLoopSlotId OBJECT-TYPE
        SYNTAX Unsigned32
        MAX-ACCESS accessible-for-notify
        STATUS current
        DESCRIPTION
            "The slot ID indicates the slot ttl-expired loop occur."
        ::= { hwTtlExpiredLoopEntry 2 }


    hwTtlExpiredLoopLastRateLow OBJECT-TYPE
        SYNTAX Unsigned32
        MAX-ACCESS read-only
        STATUS current
        DESCRIPTION
            "The lower 32 bits of last discard bytes."
        ::= { hwTtlExpiredLoopEntry 3 }


    hwTtlExpiredLoopLastRateHigh OBJECT-TYPE
        SYNTAX Unsigned32
        MAX-ACCESS read-only
        STATUS current
        DESCRIPTION
            "The high 32 bits of last discard bytes."
        ::= { hwTtlExpiredLoopEntry 4 }


    hwTtlExpiredLoopCurrentRateLow OBJECT-TYPE
        SYNTAX Unsigned32
        MAX-ACCESS read-only
        STATUS current
        DESCRIPTION
            "The lower 32 bits of current discard bytes."
        ::= { hwTtlExpiredLoopEntry 5 }


    hwTtlExpiredLoopCurrentRateHigh OBJECT-TYPE
        SYNTAX Unsigned32
        MAX-ACCESS read-only
        STATUS current
        DESCRIPTION
            "The high 32 bits of current discard bytes."
        ::= { hwTtlExpiredLoopEntry 6 }


    hwTtlExpiredLoopRateInterval OBJECT-TYPE
        SYNTAX Unsigned32
        MAX-ACCESS read-only
        STATUS current
        DESCRIPTION
            "Interval."
        ::= { hwTtlExpiredLoopEntry 7 }


    hwTtlExpiredLoopRateThreshold OBJECT-TYPE
        SYNTAX Unsigned32
        MAX-ACCESS read-only
        STATUS current
        DESCRIPTION
            "Threshold."
        ::= { hwTtlExpiredLoopEntry 8 }

      hwAntiAttack OBJECT IDENTIFIER ::= { hwBaseSecurityMIBObjects 16 }

      hwAntiAttackTable OBJECT-TYPE
          SYNTAX      SEQUENCE OF HwAntiAttackEntry
          MAX-ACCESS  not-accessible
          STATUS      current
          DESCRIPTION
              "This table list the information about anti-attack alarm."
          ::= { hwAntiAttack 1 }

      hwAntiAttackEntry OBJECT-TYPE
          SYNTAX      HwAntiAttackEntry
          MAX-ACCESS  not-accessible
          STATUS      current
          DESCRIPTION
              "This table list the information about anti-attack alarm."
          INDEX  { hwAntiAttackType}
          ::= { hwAntiAttackTable 1 }

      HwAntiAttackEntry  ::=
          SEQUENCE{
              hwAntiAttackType
                  INTEGER,
              hwAntiAttackRateThreshold
                  Integer32,
              hwAntiAttackCurrentRate
                  Integer32
                  }

      hwAntiAttackType OBJECT-TYPE
          SYNTAX     INTEGER{
                       abnormal(1),
                       fragment(2),
                       tcpSyn(3),
                       udpFlood(4),
                       icmpFlood(5)
                      }
          MAX-ACCESS read-only
          STATUS     current
          DESCRIPTION
              "The data index of anti-attack, attack type configured in anti-attack alarm."
          ::= { hwAntiAttackEntry 1 }

      hwAntiAttackRateThreshold OBJECT-TYPE
          SYNTAX     Integer32
          MAX-ACCESS read-only
          STATUS     current
          DESCRIPTION
              "The alarm threshold of anti-attack alarm during the processing of pkt-flooding.unit(bps)."
          ::= { hwAntiAttackEntry 2 }

      hwAntiAttackCurrentRate OBJECT-TYPE
          SYNTAX     Integer32
          MAX-ACCESS read-only
          STATUS     current
          DESCRIPTION
              "The current rate of anti-attack alarm. unit(bps)."
          ::= { hwAntiAttackEntry 3 }
          
        hwMeSecurityMIBObjects OBJECT IDENTIFIER ::= { hwSecurityMIB 2 }
        
        hwSecurityTrapObject OBJECT IDENTIFIER ::= { hwMeSecurityMIBObjects 1 }
        
        hwStrackTrapObject OBJECT IDENTIFIER ::= { hwSecurityTrapObject 1 }
        
        hwStrackTotalPacket OBJECT-TYPE
            SYNTAX Integer32
            MAX-ACCESS accessible-for-notify
            STATUS current
            DESCRIPTION
                "The total packets of strack during the configured interval.unit(packet)."
            ::= { hwStrackTrapObject 1 }
        
        hwStrackEndTime OBJECT-TYPE
            SYNTAX DateAndTime
            MAX-ACCESS accessible-for-notify
            STATUS current
            DESCRIPTION
                "The data of strack."
            ::= { hwStrackTrapObject 2 }
        
        hwStrackSourceMac OBJECT-TYPE
            SYNTAX OCTET STRING
            MAX-ACCESS accessible-for-notify
            STATUS current
            DESCRIPTION
                "The data of strack."
            ::= { hwStrackTrapObject 3 }
        
        hwStrackPacketPVlan OBJECT-TYPE
            SYNTAX Integer32
            MAX-ACCESS accessible-for-notify
            STATUS current
            DESCRIPTION
                "The data of strack."
            ::= { hwStrackTrapObject 4 }
        
        hwStrackPacketCVlan OBJECT-TYPE
            SYNTAX Integer32
            MAX-ACCESS accessible-for-notify
            STATUS current
            DESCRIPTION
                "The data of strack."
            ::= { hwStrackTrapObject 5 }
        
        hwStrackPacketIfName OBJECT-TYPE
            SYNTAX OCTET STRING
            MAX-ACCESS accessible-for-notify
            STATUS current
            DESCRIPTION
                "The data of strack."
            ::= { hwStrackTrapObject 6 }
        

         hwStrackSourceIp OBJECT-TYPE
            SYNTAX OCTET STRING
            MAX-ACCESS accessible-for-notify
            STATUS current
            DESCRIPTION
                "The data of strack."
            ::= { hwStrackTrapObject 7 }
        hwArpsTrapObject OBJECT IDENTIFIER ::= { hwSecurityTrapObject 2 }
        

        hwArpsSourceInterface OBJECT-TYPE
            SYNTAX OCTET STRING
            MAX-ACCESS accessible-for-notify
            STATUS current
            DESCRIPTION
                "The data of arp security."
            ::= { hwArpsTrapObject 1 }
        

        hwArpsSourceIp OBJECT-TYPE
            SYNTAX OCTET STRING
            MAX-ACCESS accessible-for-notify
            STATUS current
            DESCRIPTION
                "TThe data of arp security."
            ::= { hwArpsTrapObject 2 }
        

        hwArpsSourceMac OBJECT-TYPE
            SYNTAX OCTET STRING
            MAX-ACCESS accessible-for-notify
            STATUS current
            DESCRIPTION
                "The data of arp security."
            ::= { hwArpsTrapObject 3 }
        

        hwArpsPVlan OBJECT-TYPE
            SYNTAX Integer32
            MAX-ACCESS accessible-for-notify
            STATUS current
            DESCRIPTION
                "The data of arp security."
            ::= { hwArpsTrapObject 4 }
        

        hwArpsCVlan OBJECT-TYPE
            SYNTAX Integer32
            MAX-ACCESS accessible-for-notify
            STATUS current
            DESCRIPTION
                "The data of arp security."
            ::= { hwArpsTrapObject 5 }
        

        hwArpsPacketDropNum OBJECT-TYPE
            SYNTAX Integer32
            MAX-ACCESS accessible-for-notify
            STATUS current
            DESCRIPTION
                "The number of packets discarded by arp inspection .unit(packet)."
            ::= { hwArpsTrapObject 6 }
        

        hwArpsAlarmThreshold OBJECT-TYPE
            SYNTAX Integer32
            MAX-ACCESS accessible-for-notify
            STATUS current
            DESCRIPTION
                "The alarm threshold of dynamic arp inspection during the configured interval.unit(packet)."
            ::= { hwArpsTrapObject 7 }
        
        hwArpsBlockTime OBJECT-TYPE
            SYNTAX Integer32
            MAX-ACCESS accessible-for-notify
            STATUS current
            DESCRIPTION
                "The data of time which ARP Packet will be blocked. unit(second)."
            ::= { hwArpsTrapObject 8 }
                
        hwIpsgTrapObject OBJECT IDENTIFIER ::= { hwSecurityTrapObject 3 }
        

        hwIpsgPacketDropNum OBJECT-TYPE
            SYNTAX Integer32
            MAX-ACCESS accessible-for-notify
            STATUS current
            DESCRIPTION
                "The data of ip source check ."
            ::= { hwIpsgTrapObject 1 }
        

        hwIpsgAlarmThreshold OBJECT-TYPE
            SYNTAX Integer32
            MAX-ACCESS accessible-for-notify
            STATUS current
            DESCRIPTION
                "The alarm threshold of ip source check during the configured interval.unit(packet)."
            ::= { hwIpsgTrapObject 2 }
        

        hwIpsgSourceInterface OBJECT-TYPE
            SYNTAX OCTET STRING
            MAX-ACCESS accessible-for-notify
            STATUS current
            DESCRIPTION
                "The data of ip souce check."
            ::= { hwIpsgTrapObject 3 }
        

        hwIcmpTrapObject OBJECT IDENTIFIER ::= { hwSecurityTrapObject 4 }
        

        hwIcmpPacketDropNum OBJECT-TYPE
            SYNTAX Integer32
            MAX-ACCESS accessible-for-notify
            STATUS current
            DESCRIPTION
                "The number of packets discarded by ip source check .unit(packet)."
            ::= { hwIcmpTrapObject 1 }
        

        hwIcmpAlarmThreshold OBJECT-TYPE
            SYNTAX Integer32
            MAX-ACCESS accessible-for-notify
            STATUS current
            DESCRIPTION
                "The alarm threshold of icmp defend during the configured interval.unit(packet)."
            ::= { hwIcmpTrapObject 2 }
        

        hwIcmpSourceInterface OBJECT-TYPE
            SYNTAX OCTET STRING
            MAX-ACCESS accessible-for-notify
            STATUS current
            DESCRIPTION
                "The data of icmp security."
            ::= { hwIcmpTrapObject 3 }
        
   hwDapTrapObject OBJECT IDENTIFIER ::= { hwSecurityTrapObject 5 }

   hwDapPortChange OBJECT-TYPE
        SYNTAX Integer32 
        MAX-ACCESS accessible-for-notify
        STATUS current
        DESCRIPTION
            "The alarm of dap port changed"
        ::= { hwDapTrapObject 1 }

   hwCfgApTrapObject OBJECT IDENTIFIER ::= { hwSecurityTrapObject 6 }

    hwCfgApUserName OBJECT-TYPE
        SYNTAX OCTET STRING (SIZE (0..128))
        MAX-ACCESS accessible-for-notify
        STATUS current
        DESCRIPTION
            "The name of user failed to configure access point."
        ::= { hwCfgApTrapObject 1 }
		
    hwCfgApIPAddress OBJECT-TYPE
        SYNTAX OCTET STRING (SIZE (0..128))
        MAX-ACCESS accessible-for-notify
        STATUS current
        DESCRIPTION
            "The IP-address of user failed to configure access point."
        ::= { hwCfgApTrapObject 2 }
		
    hwCfgApApID OBJECT-TYPE
        SYNTAX Integer32
        MAX-ACCESS accessible-for-notify
        STATUS current
        DESCRIPTION
            "The ID of access point failed to be configured."
        ::= { hwCfgApTrapObject 3 }
		
	hwCfgApOperation OBJECT-TYPE
        SYNTAX OCTET STRING (SIZE (0..128))
        MAX-ACCESS accessible-for-notify
        STATUS current
        DESCRIPTION
            "The operation of confiuration to access point."
        ::= { hwCfgApTrapObject 4 }

    hwCfgApReason OBJECT-TYPE
        SYNTAX OCTET STRING (SIZE (0..128))
        MAX-ACCESS accessible-for-notify
        STATUS current
        DESCRIPTION
            "The reason of failed to configure access point."
        ::= { hwCfgApTrapObject 5 }

        hwSecurityTraps OBJECT IDENTIFIER ::= { hwMeSecurityMIBObjects 2 }
        
        hwStrackTrap OBJECT IDENTIFIER ::= { hwSecurityTraps 1 }
        
        hwStrackUserInfo NOTIFICATION-TYPE
            OBJECTS { 
	        hwStrackPacketIfName, 
	        hwStrackSourceMac, 
	        hwStrackPacketCVlan, 
	        hwStrackPacketPVlan, 
	        hwStrackEndTime, 
                hwStrackTotalPacket }
            STATUS current
            DESCRIPTION 
                "The user data of strack."
            ::= { hwStrackTrap 1 }
        
        hwStrackIfVlanInfo NOTIFICATION-TYPE
            OBJECTS { 
	        hwStrackPacketIfName, 
	        hwStrackPacketCVlan, 
	        hwStrackPacketPVlan, 
	        hwStrackEndTime, 
	        hwStrackTotalPacket}
            STATUS current
            DESCRIPTION 
                "The data of strack."
            ::= { hwStrackTrap 2 }
        
    hwStrackDenyPacket NOTIFICATION-TYPE
        OBJECTS {
            hwStrackPacketIfName,
            hwStrackSourceMac,
            hwStrackSourceIp,
            hwStrackPacketCVlan,
            hwStrackPacketPVlan}
        STATUS current
        DESCRIPTION
            "The infomation of the packets discarded by strack."
        ::= { hwStrackTrap 3 }
    hwStrackErrorDown NOTIFICATION-TYPE
        OBJECTS {
            hwStrackPacketIfName}
        STATUS current
        DESCRIPTION
            "The interface that is shutdown by strack."
        ::= { hwStrackTrap 4 }

        hwStrackIpInfo NOTIFICATION-TYPE
            OBJECTS { 
	        hwStrackPacketIfName, 
		hwStrackSourceIp, 
		hwStrackPacketCVlan, 
		hwStrackPacketPVlan, 
		hwStrackEndTime, 
                hwStrackTotalPacket }
            STATUS current
            DESCRIPTION 
                "The user data of strack."
            ::= { hwStrackTrap 5 }
        hwArpsTrap OBJECT IDENTIFIER ::= { hwSecurityTraps 2 }
        

        hwArpsGatewayConflict NOTIFICATION-TYPE
            OBJECTS { 
	        hwArpsSourceInterface, 
		hwArpsSourceIp, 
		hwArpsSourceMac,
		hwArpsPVlan, 
		hwArpsCVlan}
            STATUS current
            DESCRIPTION 
                "The gateway conflict alarm is resumed."
            ::= { hwArpsTrap 1 }
        

        hwArpsEntryCheck NOTIFICATION-TYPE
            OBJECTS { 
	        hwArpsSourceInterface, 
		hwArpsSourceIp, 
		hwArpsSourceMac, 
		hwArpsPVlan, 
		hwArpsCVlan}
            STATUS current
            DESCRIPTION 
                "The arp talbe chekc alarm is resumed."
            ::= { hwArpsTrap 2 }
        

        hwArpsPacketCheck NOTIFICATION-TYPE
            OBJECTS { 
	        hwArpsSourceInterface, 
		hwArpsSourceIp, 
		hwArpsSourceMac, 
		hwArpsPVlan, 
		hwArpsCVlan}
            STATUS current
            DESCRIPTION 
                "The arp packet check alarm is resumed."
            ::= { hwArpsTrap 3 }
        

        hwArpsDaiDropALarm NOTIFICATION-TYPE
            OBJECTS { 
	        hwArpsPacketDropNum, 
	        hwArpsAlarmThreshold, 
	        hwArpsSourceInterface }
            STATUS current
            DESCRIPTION 
                "The DAI alarm is resumed."
            ::= { hwArpsTrap 4 }
        

        hwArpGlobleSpeedLimitALarm NOTIFICATION-TYPE
            OBJECTS { 
	        hwArpsAlarmThreshold }
            STATUS current
            DESCRIPTION 
                "The arp rate limit alarm is resumed."
            ::= { hwArpsTrap 5 }
        

        hwArpIfSpeedLimitALarm NOTIFICATION-TYPE
            OBJECTS { 
	        hwArpsAlarmThreshold, 
		hwArpsSourceInterface }
            STATUS current
            DESCRIPTION 
                "TThe arp rate limit alarm is resumed."
            ::= { hwArpsTrap 6 }
        

        hwArpVlanSpeedLimitALarm NOTIFICATION-TYPE
            OBJECTS { 
	        hwArpsAlarmThreshold, 
		hwArpsPVlan }
            STATUS current
            DESCRIPTION 
                "The arp rate limit alarm is resumed."
            ::= { hwArpsTrap 7 }
        

        hwArpMissGlobleSpeedLimitALarm NOTIFICATION-TYPE
            OBJECTS { 
	        hwArpsAlarmThreshold }
            STATUS current
            DESCRIPTION 
                "The arp miss rate limit alarm is resumed."
            ::= { hwArpsTrap 8 }
        

        hwArpMissIfSpeedLimitALarm NOTIFICATION-TYPE
            OBJECTS { 
	        hwArpsAlarmThreshold, 
	        hwArpsSourceInterface }
            STATUS current
            DESCRIPTION 
                "The arp miss rate limit alarm is resumed."
            ::= { hwArpsTrap 9 }
        

        hwArpMissVlanSpeedLimitALarm NOTIFICATION-TYPE
            OBJECTS { 
	        hwArpsAlarmThreshold, 
	        hwArpsPVlan }
            STATUS current
            DESCRIPTION 
                "The arp miss rate limit alarm is resumed."
            ::= { hwArpsTrap 10 }
        

        hwArpSourceIpSpeedLimitALarm NOTIFICATION-TYPE
            OBJECTS { 
	        hwArpsSourceIp, 
	        hwArpsAlarmThreshold }
            STATUS current
            DESCRIPTION 
                "The alarm of arp speed limit."
            ::= { hwArpsTrap 11 }
        

        hwArpMissSourceIpSpeedLimitALarm NOTIFICATION-TYPE
            OBJECTS { 
	        hwArpsSourceIp, 
	        hwArpsAlarmThreshold }
            STATUS current
            DESCRIPTION 
                "The alarm of arp miss speed limit."
            ::= { hwArpsTrap 12 }

        hwArpIfRateLimitBlockALarm NOTIFICATION-TYPE
            OBJECTS { 
	        hwArpsSourceInterface, 
		hwArpsBlockTime }
            STATUS current
            DESCRIPTION 
                "The arp rate limit block alarm is resumed."
            ::= { hwArpsTrap 13 }
        
    hwArpsLearnStrictCheck NOTIFICATION-TYPE
        OBJECTS {
            hwArpsSourceInterface,
            hwArpsSourceIp,
            hwArpsSourceMac,
            hwArpsPVlan}
        STATUS current
        DESCRIPTION
            "The alarm of arp learn strict check."
        ::= { hwArpsTrap 14 }

        hwIpsgTrap OBJECT IDENTIFIER ::= { hwSecurityTraps 3 }
        

        hwIpsgDropALarm NOTIFICATION-TYPE
            OBJECTS { 
	        hwIpsgPacketDropNum, 
	        hwIpsgAlarmThreshold, 
	        hwIpsgSourceInterface }
            STATUS current
            DESCRIPTION 
                "The ipsg alarm is resumed."
            ::= { hwIpsgTrap 1 }
        

        hwIcmpTrap OBJECT IDENTIFIER ::= { hwSecurityTraps 4 }
        

        hwIcmpGlobleDropALarm NOTIFICATION-TYPE
            OBJECTS { 
	        hwIcmpAlarmThreshold }
            STATUS current
            DESCRIPTION 
                "The icmp rate limit alarm is resumed."
            ::= { hwIcmpTrap 1 }
        

        hwIcmpIfDropALarm NOTIFICATION-TYPE
            OBJECTS { 
	        hwIcmpAlarmThreshold, 
	        hwIcmpSourceInterface }
            STATUS current
            DESCRIPTION 
                "The icmp rate limit alarm is resumed."
            ::= { hwIcmpTrap 2 }
                            
    hwDapTrap OBJECT IDENTIFIER ::= { hwSecurityTraps 5 }

    hwDapMibPortChange NOTIFICATION-TYPE
        OBJECTS {
            hwDapPortChange}
        STATUS current
        DESCRIPTION
            "The dap port is changed."
        ::= { hwDapTrap 1 }

        hwCfgApTrap OBJECT IDENTIFIER ::= { hwSecurityTraps 6 }

        hwCfgApTrapFailAlarm NOTIFICATION-TYPE
            OBJECTS {
            hwCfgApUserName,
            hwCfgApIPAddress,
            hwCfgApApID,
            hwCfgApOperation,
            hwCfgApReason }
        STATUS current
        DESCRIPTION
            "The operation failed to config access point."
        ::= { hwCfgApTrap 1 }

    hwTrafficSuppression OBJECT IDENTIFIER ::= { hwMeSecurityMIBObjects 3 }
    hwTrafficSuppressionTable OBJECT-TYPE
        SYNTAX  SEQUENCE OF HwTrafficSuppressionEntry
        MAX-ACCESS not-accessible
        STATUS current
        DESCRIPTION
            " The table lists the information about the configuration of traffic 
              suppression on an interface. "
        ::= { hwTrafficSuppression 1 }
    hwTrafficSuppressionEntry OBJECT-TYPE
        SYNTAX HwTrafficSuppressionEntry 
        MAX-ACCESS not-accessible
        STATUS current
        DESCRIPTION
            " The table lists the information about traffic suppression protection."
        INDEX { hwTrafficSuppressionIfIndex }
        ::= { hwTrafficSuppressionTable 1 }
    HwTrafficSuppressionEntry ::= SEQUENCE {
        hwTrafficSuppressionIfIndex 
            Integer32,
        hwTrafficSuppressionBcastRatio 
            Integer32
        }
    hwTrafficSuppressionIfIndex OBJECT-TYPE
        SYNTAX Integer32 
        MAX-ACCESS not-accessible
        STATUS current
        DESCRIPTION
            "The port index."
        ::= { hwTrafficSuppressionEntry 1 }
    hwTrafficSuppressionBcastRatio OBJECT-TYPE
        SYNTAX Integer32 (0..100)
        MAX-ACCESS read-write
        STATUS current
        DESCRIPTION
            " Broadcast-suppression ratio. Default is 100% . 100% indicates 
            that the broadcast isn't suppressed."
        ::= { hwTrafficSuppressionEntry 2 }
      hwSecurityConformance OBJECT IDENTIFIER ::= { hwSecurityMIB 11 }
    
      hwSecurityCompliances OBJECT IDENTIFIER ::= { hwSecurityConformance 1 }
        
      hwSecurityCompliance MODULE-COMPLIANCE
          STATUS current
          DESCRIPTION 
              "The compliance statement for systems supporting 
              the HUAWEI-SECURITY-MIB."
          MODULE 
              MANDATORY-GROUPS {  hwLocalUrpfObjectGroup, hwTcpIpDefendObjectGroup, hwMaDefendObjectGroup,
                                 hwApplicationApperceiveObjectGroup, hwBaseSecurityNotificationsObjectGroup,
                                 hwMeSecurityObjectGroup, hwMeSecurityTrapGroup, hwDefdPortVlanObjectGroup, hwSocAttackTrapGroup,
                                 hwAntiAttackObjectGroup}
          ::= { hwSecurityCompliances 1 }

      hwBaseSecurityGroups OBJECT IDENTIFIER ::= { hwSecurityConformance 2 }

      hwLocalUrpfObjectGroup OBJECT-GROUP
          OBJECTS{
              hwLocalUrpfCurrentRateLow,
              hwLocalUrpfCurrentRateHigh,
              hwLocalUrpfNotifyEnabledStatus,
              hwLocalUrpfRateThreshold,
              hwLocalUrpfRateInterval,
	      hwLocalUrpfChassisId, 
              hwLocalUrpfSlotId
                 }
          STATUS current       
          DESCRIPTION 
              "The alarm parameter of URPF."
          ::= { hwBaseSecurityGroups 2 } 
          
      hwTcpIpDefendObjectGroup OBJECT-GROUP
          OBJECTS{
              hwTcpIpDefendCurrentRateLow,
              hwTcpIpDefendCurrentRateHigh,
              hwTcpIpDefendNotifyEnabledStatus,
              hwTcpIpDefendRateThreshold,
              hwTcpIpDefendRateInterval,
	      hwTcpIpDefendChassisId, 
              hwTcpIpDefendSlotId, 
              hwTcpIpDefendType,
	      hwTcpIpDefendProtocolDescirption
                 }
          STATUS current       
          DESCRIPTION 
              "The alarm parameter of TCPIP protection."
          ::= { hwBaseSecurityGroups 3 }
          
      hwMaDefendObjectGroup OBJECT-GROUP
          OBJECTS{
              hwMaDefendCurrentRateLow,
              hwMaDefendCurrentRateHigh,
              hwMaDefendNotifyEnabledStatus,
              hwMaDefendRateThreshold,
              hwMaDefendRateInterval,
	      hwMaDefendChassisId, 
              hwMaDefendSlotId, 
              hwMaDefendProtocol
                  }
          STATUS current       
          DESCRIPTION 
              "The alarm parameter of management and application protection."
          ::= { hwBaseSecurityGroups 4 }
          
      hwApplicationApperceiveObjectGroup OBJECT-GROUP
          OBJECTS{
              hwAppliApperCurrentRateLow,
              hwAppliApperCurrentRateHigh,
              hwAppliApperNotifyEnabledStatus,
              hwAppliApperRateThreshold,
              hwAppliApperRateInterval,
	      hwAppliApperChassisId, 
              hwAppliApperSlotId,
              hwAppliApperProtocol,
	      hwAppliApperProtocolDescirption
                 }
          STATUS current       
          DESCRIPTION 
              "The alarm parameter of Application-Apperceive protection."
          ::= { hwBaseSecurityGroups 5 }     
          
      hwBaseSecurityNotificationsObjectGroup NOTIFICATION-GROUP
          NOTIFICATIONS{
              hwBaseSecurityUrpfDiscardedRateRising,
              hwBaseSecurityUrpfDiscardedRateResume,
              hwBaseSecurityTcpIpAttackDiscardedRateRising, 
              hwBaseSecurityTcpIpAttackDiscardedRateResume,
              hwBaseSecurityMaDiscardedRateRising, 
              hwBaseSecurityMaDiscardedRateResume,
              hwBaseSecurityApplicationApperceiveDiscardedRateRising, 
              hwBaseSecurityApplicationApperceiveDiscardedRateResume,
              hwBaseSecurityStormControlInterface                                ,
              hwBaseSocAttackTrap, 
              hwBaseSocAttackResumeTrap,     
              hwBaseSecurityStormControlInterfaceResume,
              hwBaseSecurityTtlExpiredLoop,
              hwBaseSecurityTtlExpiredLoopResume,
              hwBaseArpVlanCarTrap,
              hwBaseArpVlanCarResumeTrap,
              hwBaseSecurityAntiAttackRateRising,
              hwBaseSecurityAntiAttackRateResume
              }
          STATUS current       
          DESCRIPTION 
              "Total alarm of protection are resumed."
          ::= { hwBaseSecurityGroups 6 }
          
        hwMeSecurityObjectGroup OBJECT-GROUP
            OBJECTS { 
                hwStrackTotalPacket,
                hwStrackEndTime,
                hwStrackSourceMac,
                hwStrackPacketPVlan,
                hwStrackPacketCVlan,
                hwStrackPacketIfName,
                hwStrackSourceIp,
                hwArpsSourceInterface,
                hwArpsSourceIp,
                hwArpsSourceMac,
                hwArpsPVlan,
                hwArpsCVlan,
                hwArpsPacketDropNum,
                hwArpsAlarmThreshold,
                hwArpsBlockTime,
                hwIpsgPacketDropNum,
                hwIpsgAlarmThreshold,
                hwIpsgSourceInterface,
                hwIcmpPacketDropNum,
                hwIcmpAlarmThreshold,
                hwIcmpSourceInterface,
                hwDapPortChange,
                hwCfgApUserName,
                hwCfgApIPAddress,
                hwCfgApApID,
                hwCfgApOperation,
                hwCfgApReason
                }
            STATUS current
            DESCRIPTION 
                "The alarm parameter of huawei base security group."
            ::= { hwBaseSecurityGroups 7 }

        hwMeSecurityTrapGroup NOTIFICATION-GROUP
            NOTIFICATIONS { 
            hwStrackUserInfo,
            hwStrackIfVlanInfo,
            hwStrackDenyPacket,
            hwStrackErrorDown,
            hwStrackIpInfo,
            hwArpsGatewayConflict,
            hwArpsEntryCheck,
            hwArpsPacketCheck,
            hwArpsDaiDropALarm,
            hwArpGlobleSpeedLimitALarm,
            hwArpIfSpeedLimitALarm,
            hwArpVlanSpeedLimitALarm,
            hwArpMissGlobleSpeedLimitALarm,
            hwArpMissIfSpeedLimitALarm,
            hwArpMissVlanSpeedLimitALarm,
            hwArpSourceIpSpeedLimitALarm,
            hwArpMissSourceIpSpeedLimitALarm,
            hwArpIfRateLimitBlockALarm,
            hwArpsLearnStrictCheck,
            hwIpsgDropALarm,
            hwIcmpGlobleDropALarm,
            hwIcmpIfDropALarm,
            hwDapMibPortChange,
            hwCfgApTrapFailAlarm
                }
            STATUS current
            DESCRIPTION 
                "Total alarm of protection are resumed."
            ::= { hwBaseSecurityGroups 8 }

      hwDefdPortVlanObjectGroup OBJECT-GROUP
          OBJECTS{
              hwDefdPortVlanIfName,
              hwDefdPortVlanId,
              hwDefdPortVlanCheckProtocol
                  }
          STATUS current       
          DESCRIPTION 
              "The alarm parameter of l2 ring-route ."
          ::= { hwBaseSecurityGroups 9 }
          
     hwSocAttackTrapGroup OBJECT-GROUP
	OBJECTS { 
	    hwSocAttackSeqNo, 
	    hwSocAttackPossib, 
	    hwSocAttackReason, 
	    hwSocAttackIfName, 
	    hwSocAttackSubIfName, 
	    hwSocAttackVlanIndex, 
            hwSocAttackUserQinQIndex, 
	    hwSocAttackMacAddr, 
	    hwSocAttackIPAddr, 
	    hwSocAttackIPv6Addr 
	}
		  STATUS current
		  DESCRIPTION 
		  "The alarm parameter of Security Operation Center"
		  ::= { hwBaseSecurityGroups 11 }
          
      hwAntiAttackObjectGroup OBJECT-GROUP
          OBJECTS{
              hwAntiAttackType,
              hwAntiAttackRateThreshold,
              hwAntiAttackCurrentRate
                  }
          STATUS current
          DESCRIPTION
              "The alarm parameter of anti-attack alarm."
          ::= { hwBaseSecurityGroups 12 }
END

--
-- HUAWEI-SECURITY-MIB
--
