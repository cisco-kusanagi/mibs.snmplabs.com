--
-- This SMIv2 module has been generated by smidump 0.2-cvs. Do not edit.
--

SONUS-ISUP-SERVICE-GROUP-MIB DEFINITIONS ::= BEGIN

IMPORTS
    Integer32, MODULE-IDENTITY, NOTIFICATION-TYPE, OBJECT-TYPE
        FROM SNMPv2-SMI
    DateAndTime, DisplayString, RowStatus
        FROM SNMPv2-TC
    sonusEventClass, sonusEventDescription, sonusEventLevel
        FROM SONUS-COMMON-MIB
    sonusSignallingMIBs
        FROM SONUS-SMI
    PointCode, SonusAdminState, SonusName, SonusNameReference, 
    SonusPointCode, SonusSupportFlag
        FROM SONUS-TC;

sonusIsupServiceGroupMIB MODULE-IDENTITY
    LAST-UPDATED    "200107310000Z"
    ORGANIZATION    
            "Sonus Networks, Inc."
    CONTACT-INFO    
            "   Customer Support    
             Sonus Networks, Inc,
             5 Carlisle Road
             Westford, MA 01886
             USA
             
             Tel: 978-692-8999
             Fax: 978-392-9118
             E-mail: cs.snmp@sonusnet.com"
    DESCRIPTION     
            "The MIB Module for ISUP Service Group Management."
    ::= { sonusSignallingMIBs 1 }


sonusIsupServiceGroupMIBObjects OBJECT IDENTIFIER
    ::= { sonusIsupServiceGroupMIB 1 }

sonusIsupsgServiceGroup OBJECT IDENTIFIER
    ::= { sonusIsupServiceGroupMIBObjects 1 }

sonusIsupsgServiceGroupNextIndex OBJECT-TYPE
    SYNTAX          Integer32
    MAX-ACCESS      read-only
    STATUS          current
    DESCRIPTION     
            "The next valid index to use when creating a new sonusIsupsgServiceGroupEntry"
    ::= { sonusIsupsgServiceGroup 1 }

sonusIsupsgServiceGroupTable OBJECT-TYPE
    SYNTAX          SEQUENCE OF SonusIsupsgServiceGroupEntry
    MAX-ACCESS      not-accessible
    STATUS          current
    DESCRIPTION     
            "This table contains information about each ISUP Service Group
             configured to be a member of the node. 
             
             A management entity may create rows for Service Group that are
             anticipated to be supported in the future."
    ::= { sonusIsupsgServiceGroup 2 }

sonusIsupsgServiceGroupEntry OBJECT-TYPE
    SYNTAX          SonusIsupsgServiceGroupEntry
    MAX-ACCESS      not-accessible
    STATUS          current
    DESCRIPTION     
            "This table describes the ISUP Service Groups that are configured as
             members of the GSX9000 ISUP Service Group."
    INDEX           { sonusIsupsgServiceGroupListIndex }
    ::= { sonusIsupsgServiceGroupTable 1 }

SonusIsupsgServiceGroupEntry ::=
    SEQUENCE {
        sonusIsupsgServiceGroupListIndex Integer32,
        sonusIsupsgServiceGroupName     SonusName,
        sonusIsupsgServiceGroupRemotePointCode      PointCode,
        sonusIsupsgServiceGroupTG       SonusNameReference,
        sonusIsupsgServiceGroupSwitchType INTEGER,
        sonusIsupsgServiceGroupRevision INTEGER,
        sonusIsupsgServiceGroupHuntAlgorithm    INTEGER,
        sonusIsupsgServiceGroupCost     Integer32,
        sonusIsupsgServiceGroupCicControl INTEGER,
        sonusIsupsgServiceGroupContTestFreq   Integer32,
        sonusIsupsgServiceGroupOperation INTEGER,
        sonusIsupsgServiceGroupMode     INTEGER,
        sonusIsupsgServiceGroupAction   INTEGER,
        sonusIsupsgServiceGroupTimeout  Integer32,
        sonusIsupsgServiceGroupAdminState SonusAdminState,
        sonusIsupsgServiceGroupProfileName  DisplayString,
        sonusIsupsgServiceGroupRowStatus RowStatus,
        sonusIsupsgServiceGroupHopCounterState      SonusAdminState,
        sonusIsupsgServiceGroupHopCounterValue      Integer32,
        sonusIsupsgServiceGroupDiscTreatmentProfileName               SonusNameReference,
        sonusIsupsgServiceGroupTonePackageName      SonusNameReference,
        sonusIsupsgServiceGroupGrsStartup INTEGER,
        sonusIsupsgServiceGroupOlipCheck INTEGER,
        sonusIsupsgServiceGroupRemPc    SonusPointCode,
        sonusIsupsgServiceGroupExchangeType   INTEGER,
        sonusIsupsgServiceGroupInspectionTime     DateAndTime,
        sonusIsupsgServiceGroupInspectionFreq     INTEGER,
        sonusIsupsgServiceGroupInspectionState      SonusAdminState,
        sonusIsupsgServiceGroupSignalingProfileName           SonusNameReference,
        sonusIsupsgServiceGroupAccRespProcess     INTEGER,
        sonusIsupsgServiceGroupAccL1ARCancelpercentage              Integer32,
        sonusIsupsgServiceGroupAccL1DRCancelpercentage              Integer32,
        sonusIsupsgServiceGroupAccL2ARCancelpercentage              Integer32,
        sonusIsupsgServiceGroupAccL2DRCancelpercentage              Integer32,
        sonusIsupsgServiceGroupAccL3ARCancelpercentage              Integer32,
        sonusIsupsgServiceGroupAccL3DRCancelpercentage              Integer32,
        sonusIsupsgServiceGroupAccSendACL Integer32,
        sonusIsupsgServiceGroupGatewayOutage    INTEGER
    }

sonusIsupsgServiceGroupListIndex OBJECT-TYPE
    SYNTAX          Integer32 (1..128)
    MAX-ACCESS      read-only
    STATUS          current
    DESCRIPTION     
            "The index of the ISUP Service Group entry."
    ::= { sonusIsupsgServiceGroupEntry 1 }

sonusIsupsgServiceGroupName OBJECT-TYPE
    SYNTAX          SonusName
    MAX-ACCESS      read-write
    STATUS          current
    DESCRIPTION     
            "The name of the ISUP Service Group."
    ::= { sonusIsupsgServiceGroupEntry 2 }

sonusIsupsgServiceGroupRemotePointCode OBJECT-TYPE
    SYNTAX          PointCode
    MAX-ACCESS      read-write
    STATUS          current
    DESCRIPTION     
            "Identifies the SS7 Point Code of the ISUP Service Group in decimal format,
             the least significant three bytes representing Network-Cluster-Member values."
    ::= { sonusIsupsgServiceGroupEntry 3 }

sonusIsupsgServiceGroupTG OBJECT-TYPE
    SYNTAX          SonusNameReference
    MAX-ACCESS      read-write
    STATUS          current
    DESCRIPTION     
            "The Trunk Group, which the ISUP Service Group belongs to."
    ::= { sonusIsupsgServiceGroupEntry 4 }

sonusIsupsgServiceGroupSwitchType OBJECT-TYPE
    SYNTAX          INTEGER { dms500(1), dms250(2), dms200(3), dms100(4), 
                        lucent5ESS(5), lucent4ESS(6) }
    MAX-ACCESS      read-write
    STATUS          current
    DESCRIPTION     
            "The network switch type where the ISUP Service Group resides."
    ::= { sonusIsupsgServiceGroupEntry 5 }

sonusIsupsgServiceGroupRevision OBJECT-TYPE
    SYNTAX          INTEGER { ansi1992(1), ansi1995(2), itu1993(3), 
                        etsi2(4), nttfcc(5), itu1997(6), itu1988(7), 
                        ituq767(8), belgacom(9) }
    MAX-ACCESS      read-write
    STATUS          current
    DESCRIPTION     
            "The revision of the ISUP protocol supported on this Service Group."
    ::= { sonusIsupsgServiceGroupEntry 6 }

sonusIsupsgServiceGroupHuntAlgorithm OBJECT-TYPE
    SYNTAX          INTEGER { bottom2top(1), top2bottom(2), 
                        circuithi2lo(3), circuitlo2hi(4), 
                        mostnleastidle(5), circularbottom2top(6), 
                        circulartop2bottom(7) }
    MAX-ACCESS      read-write
    STATUS          current
    DESCRIPTION     
            "The hunting method used to select circuits for calls destined
             to the Service Group destination."
    ::= { sonusIsupsgServiceGroupEntry 7 }

sonusIsupsgServiceGroupCost OBJECT-TYPE
    SYNTAX          Integer32 (0..100)
    MAX-ACCESS      read-write
    STATUS          current
    DESCRIPTION     
            "The routing cost to the ISUP Service Group."
    ::= { sonusIsupsgServiceGroupEntry 8 }

sonusIsupsgServiceGroupCicControl OBJECT-TYPE
    SYNTAX          INTEGER { noCics(1), oddCics(2), evenCics(3), 
                        allCics(4) }
    MAX-ACCESS      read-write
    STATUS          current
    DESCRIPTION     
            "The CICs being controlled to resolve dual seizure."
    ::= { sonusIsupsgServiceGroupEntry 9 }

sonusIsupsgServiceGroupContTestFreq OBJECT-TYPE
    SYNTAX          Integer32 (0..16)
    MAX-ACCESS      read-write
    STATUS          current
    DESCRIPTION     
            "Identifies the frequency of continuity test to be performed on each circuit."
    ::= { sonusIsupsgServiceGroupEntry 10 }

sonusIsupsgServiceGroupOperation OBJECT-TYPE
    SYNTAX          INTEGER { block(1), unblock(2), reset(3) }
    MAX-ACCESS      read-write
    STATUS          current
    DESCRIPTION     
            "The operation to be applied to the circuits in the ISUP Service Group."
    ::= { sonusIsupsgServiceGroupEntry 11 }

sonusIsupsgServiceGroupMode OBJECT-TYPE
    SYNTAX          INTEGER { outOfService(1), inService(2) }
    MAX-ACCESS      read-write
    STATUS          current
    DESCRIPTION     
            "The mode of operation of circuits in the ISUP Service Group."
    ::= { sonusIsupsgServiceGroupEntry 12 }

sonusIsupsgServiceGroupAction OBJECT-TYPE
    SYNTAX          INTEGER { dryUp(1), force(2) }
    MAX-ACCESS      read-write
    STATUS          current
    DESCRIPTION     
            "The action taken on the circuits in the ISUP Service Group."
    ::= { sonusIsupsgServiceGroupEntry 13 }

sonusIsupsgServiceGroupTimeout OBJECT-TYPE
    SYNTAX          Integer32 (1..1440)
    MAX-ACCESS      read-write
    STATUS          current
    DESCRIPTION     
            "The timeout value in minutes for dryup action on the ISUP Service Group."
    ::= { sonusIsupsgServiceGroupEntry 14 }

sonusIsupsgServiceGroupAdminState OBJECT-TYPE
    SYNTAX          SonusAdminState
    MAX-ACCESS      read-write
    STATUS          current
    DESCRIPTION     
            "The admin state of the ISUP Service Group."
    ::= { sonusIsupsgServiceGroupEntry 15 }

sonusIsupsgServiceGroupProfileName OBJECT-TYPE
    SYNTAX          DisplayString (SIZE(0..23))
    MAX-ACCESS      read-write
    STATUS          current
    DESCRIPTION     
            "The ISUP Service Group profile name."
    ::= { sonusIsupsgServiceGroupEntry 16 }

sonusIsupsgServiceGroupRowStatus OBJECT-TYPE
    SYNTAX          RowStatus
    MAX-ACCESS      read-write
    STATUS          current
    DESCRIPTION     
            ""
    ::= { sonusIsupsgServiceGroupEntry 17 }

sonusIsupsgServiceGroupHopCounterState OBJECT-TYPE
    SYNTAX          SonusAdminState
    MAX-ACCESS      read-write
    STATUS          current
    DESCRIPTION     
            "The Hop Counter state for the ISUP Service Group."
    ::= { sonusIsupsgServiceGroupEntry 18 }

sonusIsupsgServiceGroupHopCounterValue OBJECT-TYPE
    SYNTAX          Integer32 (10..32)
    MAX-ACCESS      read-write
    STATUS          current
    DESCRIPTION     
            "Specifies the value of the Hop Counter if initiated by the switch."
    ::= { sonusIsupsgServiceGroupEntry 19 }

sonusIsupsgServiceGroupDiscTreatmentProfileName OBJECT-TYPE
    SYNTAX          SonusNameReference
    MAX-ACCESS      read-write
    STATUS          current
    DESCRIPTION     
            "The disconnect treatment profile to be used for this service."
    ::= { sonusIsupsgServiceGroupEntry 20 }

sonusIsupsgServiceGroupTonePackageName OBJECT-TYPE
    SYNTAX          SonusNameReference
    MAX-ACCESS      read-write
    STATUS          current
    DESCRIPTION     
            "The tone package to be used for this service."
    ::= { sonusIsupsgServiceGroupEntry 21 }

sonusIsupsgServiceGroupGrsStartup OBJECT-TYPE
    SYNTAX          INTEGER { disabled(1), enabled(2) }
    MAX-ACCESS      read-write
    STATUS          current
    DESCRIPTION     
            "Specifies whether support is enabled or disabled for
             GRS/GRA at Startup for the ISUP Service Group."
    ::= { sonusIsupsgServiceGroupEntry 22 }

sonusIsupsgServiceGroupOlipCheck OBJECT-TYPE
    SYNTAX          INTEGER { on(1), off(0) }
    MAX-ACCESS      read-write
    STATUS          current
    DESCRIPTION     
            "Specifies whether or not to check for the presence of an OLIP when determing
             that a call is invalid."
    ::= { sonusIsupsgServiceGroupEntry 23 }

sonusIsupsgServiceGroupRemPc OBJECT-TYPE
    SYNTAX          SonusPointCode
    MAX-ACCESS      read-write
    STATUS          current
    DESCRIPTION     
            "The Remote point code is not maintained as an OCTET STRING"
    ::= { sonusIsupsgServiceGroupEntry 24 }

sonusIsupsgServiceGroupExchangeType OBJECT-TYPE
    SYNTAX          INTEGER { none(1), typeA(2), typeB(3) }
    MAX-ACCESS      read-write
    STATUS          current
    DESCRIPTION     
            "The exchange type for the ISUP Service Group."
    ::= { sonusIsupsgServiceGroupEntry 25 }

sonusIsupsgServiceGroupInspectionTime OBJECT-TYPE
    SYNTAX          DateAndTime
    MAX-ACCESS      read-write
    STATUS          current
    DESCRIPTION     
            "Octet string that identifies the GMT time and date
             to start Periodic Circuit Inspection.
             
             	field  octects  contents    			  range
             	-----  -------  --------      			  -----
             1      1-2    year                      0..65536
             2       3     month                     1..12
             3       4     day                       1..31
             4       5     hour                      0..23
              5       6     minutes                   0..59
             6       7     seconds                   0..60
                        (use 60 for leap-second)
             7       8     deci-seconds              0..9
             8       9     direction from UTC        '+' / '-'
             9      10     hours from UTC            0..11
             10      11     minutes from UTC          0..59
             
             For example, Tuesday May 26, 1992 at 1:30:15 PM EDT would be
             displayed as:
             
             1992-5-26,13:30:15.0,-4:0
             
             * Notes:
             - the value of year is in network-byte order"
    ::= { sonusIsupsgServiceGroupEntry 26 }

sonusIsupsgServiceGroupInspectionFreq OBJECT-TYPE
    SYNTAX          INTEGER { onehour(1), threehours(2), sixhours(3), 
                        twelvehours(4), oneday(5), twodays(6) }
    MAX-ACCESS      read-write
    STATUS          current
    DESCRIPTION     
            ""
    DEFVAL          { oneday }
    ::= { sonusIsupsgServiceGroupEntry 27 }

sonusIsupsgServiceGroupInspectionState OBJECT-TYPE
    SYNTAX          SonusAdminState
    MAX-ACCESS      read-write
    STATUS          current
    DESCRIPTION     
            ""
    DEFVAL          { disabled }
    ::= { sonusIsupsgServiceGroupEntry 28 }

sonusIsupsgServiceGroupSignalingProfileName OBJECT-TYPE
    SYNTAX          SonusNameReference
    MAX-ACCESS      read-write
    STATUS          current
    DESCRIPTION     
            "The ISUP Signaling Profile to be used for this service."
    ::= { sonusIsupsgServiceGroupEntry 29 }

sonusIsupsgServiceGroupAccRespProcess OBJECT-TYPE
    SYNTAX          INTEGER { disabled(1), enabled(2) }
    MAX-ACCESS      read-write
    STATUS          current
    DESCRIPTION     
            "The ACC Processing state for the ISUP Service Group."
    ::= { sonusIsupsgServiceGroupEntry 30 }

sonusIsupsgServiceGroupAccL1ARCancelpercentage OBJECT-TYPE
    SYNTAX          Integer32 (0..100)
    MAX-ACCESS      read-write
    STATUS          current
    DESCRIPTION     
            "Specifies the percentage of Alternate Routed call to be cancel at Congestion Level 1."
    ::= { sonusIsupsgServiceGroupEntry 31 }

sonusIsupsgServiceGroupAccL1DRCancelpercentage OBJECT-TYPE
    SYNTAX          Integer32 (0..100)
    MAX-ACCESS      read-write
    STATUS          current
    DESCRIPTION     
            "Specifies the percentage of Direct Routed call to be cancel at Congestion Level 1."
    ::= { sonusIsupsgServiceGroupEntry 32 }

sonusIsupsgServiceGroupAccL2ARCancelpercentage OBJECT-TYPE
    SYNTAX          Integer32 (0..100)
    MAX-ACCESS      read-write
    STATUS          current
    DESCRIPTION     
            "Specifies the percentage of Alternate Routed call to be cancel at Congestion Level 2."
    ::= { sonusIsupsgServiceGroupEntry 33 }

sonusIsupsgServiceGroupAccL2DRCancelpercentage OBJECT-TYPE
    SYNTAX          Integer32 (0..100)
    MAX-ACCESS      read-write
    STATUS          current
    DESCRIPTION     
            "Specifies the percentage of Direct Routed call to be cancel at Congestion Level 2."
    ::= { sonusIsupsgServiceGroupEntry 34 }

sonusIsupsgServiceGroupAccL3ARCancelpercentage OBJECT-TYPE
    SYNTAX          Integer32 (0..100)
    MAX-ACCESS      read-write
    STATUS          current
    DESCRIPTION     
            "Specifies the percentage of Alternate Routed call to be cancel at Congestion Level 3."
    ::= { sonusIsupsgServiceGroupEntry 35 }

sonusIsupsgServiceGroupAccL3DRCancelpercentage OBJECT-TYPE
    SYNTAX          Integer32 (0..100)
    MAX-ACCESS      read-write
    STATUS          current
    DESCRIPTION     
            "Specifies the percentage of Direct Routed call to be cancel at Congestion Level 3."
    ::= { sonusIsupsgServiceGroupEntry 36 }

sonusIsupsgServiceGroupAccSendACL OBJECT-TYPE
    SYNTAX          Integer32 (0..3)
    MAX-ACCESS      read-write
    STATUS          current
    DESCRIPTION     
            "specifies the Max ACL value send to remote node for the ISUP Service Group. 0 means disabled"
    ::= { sonusIsupsgServiceGroupEntry 37 }

sonusIsupsgServiceGroupGatewayOutage OBJECT-TYPE
    SYNTAX          INTEGER { keepCalls(1), removeCalls(2) }
    MAX-ACCESS      read-write
    STATUS          current
    DESCRIPTION     
            "specifies if the service group should try to keep active calls when the ss7 gateway disconnects."
    DEFVAL          { keepCalls }
    ::= { sonusIsupsgServiceGroupEntry 38 }

sonusIsupsgServiceGroupStatTable OBJECT-TYPE
    SYNTAX          SEQUENCE OF SonusIsupsgServiceGroupStatEntry
    MAX-ACCESS      not-accessible
    STATUS          current
    DESCRIPTION     
            "This table contains status information about each ISUP access point
             in the GSX9000 Switch node.  ISUP Service Groups within the node can
             can be configured before SS7 connections is physically attached to
             the node.  The remote ISUP user part may be unavailable or the SS7
             links to the destination may not be connected or correctly configured.
             Therefore, it is possible that an access point can be unavailable,
             and is absent."
    ::= { sonusIsupServiceGroupMIBObjects 2 }

sonusIsupsgServiceGroupStatEntry OBJECT-TYPE
    SYNTAX          SonusIsupsgServiceGroupStatEntry
    MAX-ACCESS      not-accessible
    STATUS          current
    DESCRIPTION     
            "This table describes the status of the Service Groups that are configured
             as destinations ISUP nodes for the GSX9000 Switch node."
    INDEX           { sonusIsupsgServiceGroupStatListIndex }
    ::= { sonusIsupsgServiceGroupStatTable 1 }

SonusIsupsgServiceGroupStatEntry ::=
    SEQUENCE {
        sonusIsupsgServiceGroupStatListIndex    Integer32,
        sonusIsupsgServiceGroupStatName SonusNameReference,
        sonusIsupsgServiceGroupStatStatus INTEGER,
        sonusIsupsgServiceGroupStatLastInspectionTime             DateAndTime,
        sonusIsupsgServiceGroupStatNextInspectionTime             DateAndTime
    }

sonusIsupsgServiceGroupStatListIndex OBJECT-TYPE
    SYNTAX          Integer32 (0..127)
    MAX-ACCESS      read-only
    STATUS          current
    DESCRIPTION     
            "The index of the ISUP Service Group."
    ::= { sonusIsupsgServiceGroupStatEntry 1 }

sonusIsupsgServiceGroupStatName OBJECT-TYPE
    SYNTAX          SonusNameReference
    MAX-ACCESS      read-only
    STATUS          current
    DESCRIPTION     
            "The name of the ISUP Service Group."
    ::= { sonusIsupsgServiceGroupStatEntry 2 }

sonusIsupsgServiceGroupStatStatus OBJECT-TYPE
    SYNTAX          INTEGER { available(1), unavailable(2), congested(3) }
    MAX-ACCESS      read-only
    STATUS          current
    DESCRIPTION     
            "The state of the ISUP Service Group."
    ::= { sonusIsupsgServiceGroupStatEntry 3 }

sonusIsupsgServiceGroupStatLastInspectionTime OBJECT-TYPE
    SYNTAX          DateAndTime
    MAX-ACCESS      read-write
    STATUS          current
    DESCRIPTION     
            "Octet string that identifies the GMT time and date
             of the last Periodic Circuit Inspection.
             
             	field  octects  contents    			  range
             	-----  -------  --------      			  -----
             1      1-2    year                      0..65536
             2       3     month                     1..12
             3       4     day                       1..31
             4       5     hour                      0..23
              5       6     minutes                   0..59
             6       7     seconds                   0..60
                        (use 60 for leap-second)
             7       8     deci-seconds              0..9
             8       9     direction from UTC        '+' / '-'
             9      10     hours from UTC            0..11
             10      11     minutes from UTC          0..59
             
             For example, Tuesday May 26, 1992 at 1:30:15 PM EDT would be
             displayed as:
             
             1992-5-26,13:30:15.0,-4:0
             
             * Notes:
             - the value of year is in network-byte order"
    ::= { sonusIsupsgServiceGroupStatEntry 4 }

sonusIsupsgServiceGroupStatNextInspectionTime OBJECT-TYPE
    SYNTAX          DateAndTime
    MAX-ACCESS      read-write
    STATUS          current
    DESCRIPTION     
            "Octet string that identifies the GMT time and date
             of the next Periodic Circuit Inspection.
             
             	field  octects  contents    			  range
             	-----  -------  --------      			  -----
             1      1-2    year                      0..65536
             2       3     month                     1..12
             3       4     day                       1..31
             4       5     hour                      0..23
              5       6     minutes                   0..59
             6       7     seconds                   0..60
                        (use 60 for leap-second)
             7       8     deci-seconds              0..9
             8       9     direction from UTC        '+' / '-'
             9      10     hours from UTC            0..11
             10      11     minutes from UTC          0..59
             
             For example, Tuesday May 26, 1992 at 1:30:15 PM EDT would be
             displayed as:
             
             1992-5-26,13:30:15.0,-4:0
             
             * Notes:
             - the value of year is in network-byte order"
    ::= { sonusIsupsgServiceGroupStatEntry 5 }

sonusIsupsgSvcGrpProfile OBJECT IDENTIFIER
    ::= { sonusIsupServiceGroupMIBObjects 3 }

sonusIsupsgSvcGrpProfileNextIndex OBJECT-TYPE
    SYNTAX          Integer32
    MAX-ACCESS      read-only
    STATUS          current
    DESCRIPTION     
            "The next valid index to use when creating a new sonusIsupsgSvcGrpProfileEntry"
    ::= { sonusIsupsgSvcGrpProfile 1 }

sonusIsupsgSvcGrpProfileTable OBJECT-TYPE
    SYNTAX          SEQUENCE OF SonusIsupsgSvcGrpProfileEntry
    MAX-ACCESS      not-accessible
    STATUS          current
    DESCRIPTION     
            "This table contains ISUP Service Group profiles."
    ::= { sonusIsupsgSvcGrpProfile 2 }

sonusIsupsgSvcGrpProfileEntry OBJECT-TYPE
    SYNTAX          SonusIsupsgSvcGrpProfileEntry
    MAX-ACCESS      not-accessible
    STATUS          current
    DESCRIPTION     
            "This table describes the Service Group profile."
    INDEX           { sonusIsupsgSvcGrpProfileListIndex }
    ::= { sonusIsupsgSvcGrpProfileTable 1 }

SonusIsupsgSvcGrpProfileEntry ::=
    SEQUENCE {
        sonusIsupsgSvcGrpProfileListIndex Integer32,
        sonusIsupsgSvcGrpProfileName    SonusName,
        sonusIsupsgSvcGrpProfileTG      SonusNameReference,
        sonusIsupsgSvcGrpProfileSwitchType  INTEGER,
        sonusIsupsgSvcGrpProfileRevision INTEGER,
        sonusIsupsgSvcGrpProfileHuntAlgorithm     INTEGER,
        sonusIsupsgSvcGrpProfileCost    Integer32,
        sonusIsupsgSvcGrpProfileCicControl  INTEGER,
        sonusIsupsgSvcGrpProfileContTestFreq    Integer32,
        sonusIsupsgSvcGrpProfileAdminState  SonusAdminState,
        sonusIsupsgSvcGrpProfileRowStatus RowStatus,
        sonusIsupsgSvcGrpProfileHopCounterState       SonusAdminState,
        sonusIsupsgSvcGrpProfileHopCounterValue       Integer32,
        sonusIsupsgSvcGrpProfileDiscTreatmentProfileName                SonusNameReference,
        sonusIsupsgSvcGrpProfileTonePackageName       SonusNameReference,
        sonusIsupsgSvcGrpProfileGrsStartup  INTEGER,
        sonusIsupsgSvcGrpProfileOlipCheck INTEGER,
        sonusIsupsgSvcGrpProfileExchangeType    INTEGER,
        sonusIsupsgSvcGrpProfileInspectionTime      DateAndTime,
        sonusIsupsgSvcGrpProfileInspectionFreq      INTEGER,
        sonusIsupsgSvcGrpProfileInspectionState       SonusAdminState,
        sonusIsupsgSvcGrpProfileSignalingProfileName            SonusNameReference,
        sonusIsupsgSvcGrpProfileAccRespProcess      INTEGER,
        sonusIsupsgSvcGrpProfileAccL1ARCancelpercentage               Integer32,
        sonusIsupsgSvcGrpProfileAccL1DRCancelpercentage               Integer32,
        sonusIsupsgSvcGrpProfileAccL2ARCancelpercentage               Integer32,
        sonusIsupsgSvcGrpProfileAccL2DRCancelpercentage               Integer32,
        sonusIsupsgSvcGrpProfileAccL3ARCancelpercentage               Integer32,
        sonusIsupsgSvcGrpProfileAccL3DRCancelpercentage               Integer32,
        sonusIsupsgSvcGrpProfileAccSendACL  Integer32
    }

sonusIsupsgSvcGrpProfileListIndex OBJECT-TYPE
    SYNTAX          Integer32 (0..127)
    MAX-ACCESS      read-only
    STATUS          current
    DESCRIPTION     
            "The index of the ISUP Service Group Profile."
    ::= { sonusIsupsgSvcGrpProfileEntry 1 }

sonusIsupsgSvcGrpProfileName OBJECT-TYPE
    SYNTAX          SonusName
    MAX-ACCESS      read-write
    STATUS          current
    DESCRIPTION     
            "The name of the ISUP Service Group Profile."
    ::= { sonusIsupsgSvcGrpProfileEntry 2 }

sonusIsupsgSvcGrpProfileTG OBJECT-TYPE
    SYNTAX          SonusNameReference
    MAX-ACCESS      read-write
    STATUS          current
    DESCRIPTION     
            "The Trunk Group, which the ISUP Service Group belongs to."
    ::= { sonusIsupsgSvcGrpProfileEntry 3 }

sonusIsupsgSvcGrpProfileSwitchType OBJECT-TYPE
    SYNTAX          INTEGER { dms500(1), dms250(2), dms200(3), dms100(4), 
                        lucent5ESS(5), lucent4ESS(6) }
    MAX-ACCESS      read-write
    STATUS          current
    DESCRIPTION     
            "The network switch type where the ISUP Service Group resides."
    ::= { sonusIsupsgSvcGrpProfileEntry 4 }

sonusIsupsgSvcGrpProfileRevision OBJECT-TYPE
    SYNTAX          INTEGER { ansi1992(1), ansi1995(2), itu1993(3), 
                        etsi2(4), nttfcc(5), itu1997(6), itu1988(7), 
                        ituq767(8), belgacom(9) }
    MAX-ACCESS      read-write
    STATUS          current
    DESCRIPTION     
            "The revision of the ISUP protocol supported on this Service Group."
    ::= { sonusIsupsgSvcGrpProfileEntry 5 }

sonusIsupsgSvcGrpProfileHuntAlgorithm OBJECT-TYPE
    SYNTAX          INTEGER { bottom2top(1), top2bottom(2), 
                        circuithi2lo(3), circuitlo2hi(4), 
                        mostnleastidle(5), circularbottom2top(6), 
                        circulartop2bottom(7) }
    MAX-ACCESS      read-write
    STATUS          current
    DESCRIPTION     
            "The hunting method used to select circuits for calls destined
             to the Service Group destination."
    ::= { sonusIsupsgSvcGrpProfileEntry 6 }

sonusIsupsgSvcGrpProfileCost OBJECT-TYPE
    SYNTAX          Integer32 (0..100)
    MAX-ACCESS      read-write
    STATUS          current
    DESCRIPTION     
            "The routing cost to the ISUP Service Group."
    ::= { sonusIsupsgSvcGrpProfileEntry 7 }

sonusIsupsgSvcGrpProfileCicControl OBJECT-TYPE
    SYNTAX          INTEGER { noCics(1), oddCics(2), evenCics(3), 
                        allCics(4) }
    MAX-ACCESS      read-write
    STATUS          current
    DESCRIPTION     
            "The CICs being controlled to resolve dual seizure."
    ::= { sonusIsupsgSvcGrpProfileEntry 8 }

sonusIsupsgSvcGrpProfileContTestFreq OBJECT-TYPE
    SYNTAX          Integer32 (0..16)
    MAX-ACCESS      read-write
    STATUS          current
    DESCRIPTION     
            "Identifies the frequency of continuity test to be performed on each circuit."
    ::= { sonusIsupsgSvcGrpProfileEntry 9 }

sonusIsupsgSvcGrpProfileAdminState OBJECT-TYPE
    SYNTAX          SonusAdminState
    MAX-ACCESS      read-write
    STATUS          current
    DESCRIPTION     
            "The admin state of the ISUP Service Group Profile."
    ::= { sonusIsupsgSvcGrpProfileEntry 10 }

sonusIsupsgSvcGrpProfileRowStatus OBJECT-TYPE
    SYNTAX          RowStatus
    MAX-ACCESS      read-write
    STATUS          current
    DESCRIPTION     
            ""
    ::= { sonusIsupsgSvcGrpProfileEntry 11 }

sonusIsupsgSvcGrpProfileHopCounterState OBJECT-TYPE
    SYNTAX          SonusAdminState
    MAX-ACCESS      read-write
    STATUS          current
    DESCRIPTION     
            "The Hop Counter state of the ISUP Service Group Profile."
    ::= { sonusIsupsgSvcGrpProfileEntry 12 }

sonusIsupsgSvcGrpProfileHopCounterValue OBJECT-TYPE
    SYNTAX          Integer32 (10..20)
    MAX-ACCESS      read-write
    STATUS          current
    DESCRIPTION     
            "Specifies the value of the Hop Counter if initiated by the switch."
    ::= { sonusIsupsgSvcGrpProfileEntry 13 }

sonusIsupsgSvcGrpProfileDiscTreatmentProfileName OBJECT-TYPE
    SYNTAX          SonusNameReference
    MAX-ACCESS      read-write
    STATUS          current
    DESCRIPTION     
            "The disconnect treatment profile to be used for this service."
    ::= { sonusIsupsgSvcGrpProfileEntry 14 }

sonusIsupsgSvcGrpProfileTonePackageName OBJECT-TYPE
    SYNTAX          SonusNameReference
    MAX-ACCESS      read-write
    STATUS          current
    DESCRIPTION     
            "The tone package to be used for this service."
    ::= { sonusIsupsgSvcGrpProfileEntry 15 }

sonusIsupsgSvcGrpProfileGrsStartup OBJECT-TYPE
    SYNTAX          INTEGER { disabled(1), enabled(2) }
    MAX-ACCESS      read-write
    STATUS          current
    DESCRIPTION     
            "Specifies whether support is enabled or disabled for
             GRS/GRA at Startup for the ISUP Service Group."
    ::= { sonusIsupsgSvcGrpProfileEntry 16 }

sonusIsupsgSvcGrpProfileOlipCheck OBJECT-TYPE
    SYNTAX          INTEGER { on(1), off(0) }
    MAX-ACCESS      read-write
    STATUS          current
    DESCRIPTION     
            "Specifies the value of the Hop Counter if initiated by the switch."
    ::= { sonusIsupsgSvcGrpProfileEntry 17 }

sonusIsupsgSvcGrpProfileExchangeType OBJECT-TYPE
    SYNTAX          INTEGER { none(1), typeA(2), typeB(3) }
    MAX-ACCESS      read-write
    STATUS          current
    DESCRIPTION     
            "The exchange type for the ISUP Service Group."
    ::= { sonusIsupsgSvcGrpProfileEntry 18 }

sonusIsupsgSvcGrpProfileInspectionTime OBJECT-TYPE
    SYNTAX          DateAndTime
    MAX-ACCESS      read-write
    STATUS          current
    DESCRIPTION     
            "Octet string that identifies the GMT time and date
             to start Periodic Circuit Inspection.
             
             	field  octects  contents    			  range
             	-----  -------  --------      			  -----
             1      1-2    year                      0..65536
             2       3     month                     1..12
             3       4     day                       1..31
             4       5     hour                      0..23
              5       6     minutes                   0..59
             6       7     seconds                   0..60
                        (use 60 for leap-second)
             7       8     deci-seconds              0..9
             8       9     direction from UTC        '+' / '-'
             9      10     hours from UTC            0..11
             10      11     minutes from UTC          0..59
             
             For example, Tuesday May 26, 1992 at 1:30:15 PM EDT would be
             displayed as:
             
             1992-5-26,13:30:15.0,-4:0
             
             * Notes:
             - the value of year is in network-byte order"
    ::= { sonusIsupsgSvcGrpProfileEntry 19 }

sonusIsupsgSvcGrpProfileInspectionFreq OBJECT-TYPE
    SYNTAX          INTEGER { onehour(1), threehours(2), sixhours(3), 
                        twelvehours(4), oneday(5), twodays(6) }
    MAX-ACCESS      read-write
    STATUS          current
    DESCRIPTION     
            ""
    DEFVAL          { oneday }
    ::= { sonusIsupsgSvcGrpProfileEntry 20 }

sonusIsupsgSvcGrpProfileInspectionState OBJECT-TYPE
    SYNTAX          SonusAdminState
    MAX-ACCESS      read-write
    STATUS          current
    DESCRIPTION     
            ""
    DEFVAL          { disabled }
    ::= { sonusIsupsgSvcGrpProfileEntry 21 }

sonusIsupsgSvcGrpProfileSignalingProfileName OBJECT-TYPE
    SYNTAX          SonusNameReference
    MAX-ACCESS      read-write
    STATUS          current
    DESCRIPTION     
            "The ISUP Signaling Profile to be used for this service."
    ::= { sonusIsupsgSvcGrpProfileEntry 22 }

sonusIsupsgSvcGrpProfileAccRespProcess OBJECT-TYPE
    SYNTAX          INTEGER { disabled(1), enabled(2) }
    MAX-ACCESS      read-write
    STATUS          current
    DESCRIPTION     
            "The ACC Processing state for the ISUP Service Group Profile."
    ::= { sonusIsupsgSvcGrpProfileEntry 23 }

sonusIsupsgSvcGrpProfileAccL1ARCancelpercentage OBJECT-TYPE
    SYNTAX          Integer32 (1..100)
    MAX-ACCESS      read-write
    STATUS          current
    DESCRIPTION     
            "Specifies the percentage of Alternate Routed call to be cancel at Congestion Level 1."
    ::= { sonusIsupsgSvcGrpProfileEntry 24 }

sonusIsupsgSvcGrpProfileAccL1DRCancelpercentage OBJECT-TYPE
    SYNTAX          Integer32 (1..100)
    MAX-ACCESS      read-write
    STATUS          current
    DESCRIPTION     
            "Specifies the percentage of Direct Routed call to be cancel at Congestion Level 1."
    ::= { sonusIsupsgSvcGrpProfileEntry 25 }

sonusIsupsgSvcGrpProfileAccL2ARCancelpercentage OBJECT-TYPE
    SYNTAX          Integer32 (1..100)
    MAX-ACCESS      read-write
    STATUS          current
    DESCRIPTION     
            "Specifies the percentage of Alternate Routed call to be cancel at Congestion Level 2."
    ::= { sonusIsupsgSvcGrpProfileEntry 26 }

sonusIsupsgSvcGrpProfileAccL2DRCancelpercentage OBJECT-TYPE
    SYNTAX          Integer32 (1..100)
    MAX-ACCESS      read-write
    STATUS          current
    DESCRIPTION     
            "Specifies the percentage of Direct Routed call to be cancel at Congestion Level 2."
    ::= { sonusIsupsgSvcGrpProfileEntry 27 }

sonusIsupsgSvcGrpProfileAccL3ARCancelpercentage OBJECT-TYPE
    SYNTAX          Integer32 (1..100)
    MAX-ACCESS      read-write
    STATUS          current
    DESCRIPTION     
            "Specifies the percentage of Alternate Routed call to be cancel at Congestion Level 3."
    ::= { sonusIsupsgSvcGrpProfileEntry 28 }

sonusIsupsgSvcGrpProfileAccL3DRCancelpercentage OBJECT-TYPE
    SYNTAX          Integer32 (1..100)
    MAX-ACCESS      read-write
    STATUS          current
    DESCRIPTION     
            "Specifies the percentage of Direct Routed call to be cancel at Congestion Level 3."
    ::= { sonusIsupsgSvcGrpProfileEntry 29 }

sonusIsupsgSvcGrpProfileAccSendACL OBJECT-TYPE
    SYNTAX          Integer32 (0..3)
    MAX-ACCESS      read-write
    STATUS          current
    DESCRIPTION     
            "specifies the Max ACL value send to remote node for the ISUP Service Group. 0 means disabled"
    ::= { sonusIsupsgSvcGrpProfileEntry 30 }

sonusIsupsgCircuitTable OBJECT-TYPE
    SYNTAX          SEQUENCE OF SonusIsupsgCircuitEntry
    MAX-ACCESS      not-accessible
    STATUS          current
    DESCRIPTION     
            "The Isupsg Circuit table describes the circuits in the indexed Access
             Point. This table is unavailable if the sonusisupsgServiceGroupStatStatus
             object indicates that this access point is unavailable.
             
             If the sonusNodeServerType object returns either 'absent' or 
             'unknown' the value of all other objects within this table are 
             indeterministic."
    ::= { sonusIsupServiceGroupMIBObjects 4 }

sonusIsupsgCircuitEntry OBJECT-TYPE
    SYNTAX          SonusIsupsgCircuitEntry
    MAX-ACCESS      not-accessible
    STATUS          current
    DESCRIPTION     
            ""
    INDEX           { sonusIsupsgCircuitServiceListIndex, 
                      sonusIsupsgCircuitIdentityCode }
    ::= { sonusIsupsgCircuitTable 1 }

SonusIsupsgCircuitEntry ::=
    SEQUENCE {
        sonusIsupsgCircuitServiceListIndex  Integer32,
        sonusIsupsgCircuitIdentityCode  Integer32,
        sonusIsupsgCircuitServiceName   SonusNameReference,
        sonusIsupsgCircuitPortName      SonusNameReference,
        sonusIsupsgCircuitChannel       Integer32,
        sonusIsupsgCircuitDirection     INTEGER,
        sonusIsupsgCircuitMode          INTEGER,
        sonusIsupsgCircuitAction        INTEGER,
        sonusIsupsgCircuitTimeout       Integer32,
        sonusIsupsgCircuitAdminState    SonusAdminState,
        sonusIsupsgCircuitProfileName   SonusNameReference,
        sonusIsupsgCircuitRowStatus     RowStatus
    }

sonusIsupsgCircuitServiceListIndex OBJECT-TYPE
    SYNTAX          Integer32
    MAX-ACCESS      read-only
    STATUS          current
    DESCRIPTION     
            "The index of the ISUP Service Group circuit is defined for.."
    ::= { sonusIsupsgCircuitEntry 1 }

sonusIsupsgCircuitIdentityCode OBJECT-TYPE
    SYNTAX          Integer32 (0..16383)
    MAX-ACCESS      read-only
    STATUS          current
    DESCRIPTION     
            "Identifies the circuit identity code (CIC) for the circuit."
    ::= { sonusIsupsgCircuitEntry 2 }

sonusIsupsgCircuitServiceName OBJECT-TYPE
    SYNTAX          SonusNameReference
    MAX-ACCESS      read-write
    STATUS          current
    DESCRIPTION     
            "The name of the ISUP Service Group circuit is under."
    ::= { sonusIsupsgCircuitEntry 3 }

sonusIsupsgCircuitPortName OBJECT-TYPE
    SYNTAX          SonusNameReference
    MAX-ACCESS      read-write
    STATUS          current
    DESCRIPTION     
            "The name of the port circuit is on."
    ::= { sonusIsupsgCircuitEntry 4 }

sonusIsupsgCircuitChannel OBJECT-TYPE
    SYNTAX          Integer32 (1..32)
    MAX-ACCESS      read-write
    STATUS          current
    DESCRIPTION     
            "Identifies the channel the circuit represents."
    ::= { sonusIsupsgCircuitEntry 5 }

sonusIsupsgCircuitDirection OBJECT-TYPE
    SYNTAX          INTEGER { twoWay(1), oneWayIn(2), oneWayOut(3) }
    MAX-ACCESS      read-write
    STATUS          current
    DESCRIPTION     
            "Identifies the direction of traffic to be allowed on the circuit."
    ::= { sonusIsupsgCircuitEntry 6 }

sonusIsupsgCircuitMode OBJECT-TYPE
    SYNTAX          INTEGER { block(1), unblock(2), reset(3), cot(4) }
    MAX-ACCESS      read-write
    STATUS          current
    DESCRIPTION     
            "The mode of operation of the ISUP Circuit."
    ::= { sonusIsupsgCircuitEntry 7 }

sonusIsupsgCircuitAction OBJECT-TYPE
    SYNTAX          INTEGER { dryUp(1), force(2) }
    MAX-ACCESS      read-write
    STATUS          current
    DESCRIPTION     
            "The action taken on the ISUP Circuit."
    ::= { sonusIsupsgCircuitEntry 8 }

sonusIsupsgCircuitTimeout OBJECT-TYPE
    SYNTAX          Integer32 (1..1440)
    MAX-ACCESS      read-write
    STATUS          current
    DESCRIPTION     
            "The timeout value in minutes for dryup action on the ISUP Circuit."
    ::= { sonusIsupsgCircuitEntry 9 }

sonusIsupsgCircuitAdminState OBJECT-TYPE
    SYNTAX          SonusAdminState
    MAX-ACCESS      read-write
    STATUS          current
    DESCRIPTION     
            "The admin state of the ISUP Circuit."
    ::= { sonusIsupsgCircuitEntry 10 }

sonusIsupsgCircuitProfileName OBJECT-TYPE
    SYNTAX          SonusNameReference
    MAX-ACCESS      read-write
    STATUS          current
    DESCRIPTION     
            "The circuit profile name assigned to the ISUP circuit."
    ::= { sonusIsupsgCircuitEntry 11 }

sonusIsupsgCircuitRowStatus OBJECT-TYPE
    SYNTAX          RowStatus
    MAX-ACCESS      read-write
    STATUS          current
    DESCRIPTION     
            ""
    ::= { sonusIsupsgCircuitEntry 12 }

sonusIsupsgCircuitStatTable OBJECT-TYPE
    SYNTAX          SEQUENCE OF SonusIsupsgCircuitStatEntry
    MAX-ACCESS      not-accessible
    STATUS          current
    DESCRIPTION     
            "This table contains status information about each ISUP circuit 
             in the GSX9000 Switch node.  ISUP circuits within the node can
             can be configured before SS7 connections is physically attached to
             the node.  The remote ISUP circuit may not be equipped or configured.
             Therefore, it is possible that an ISUP circuit can be unavailable,
             and is absent."
    ::= { sonusIsupServiceGroupMIBObjects 5 }

sonusIsupsgCircuitStatEntry OBJECT-TYPE
    SYNTAX          SonusIsupsgCircuitStatEntry
    MAX-ACCESS      not-accessible
    STATUS          current
    DESCRIPTION     
            "This table describes the status of the configured ISUP circuits."
    INDEX           { sonusIsupsgCircuitStatServiceListIndex, 
                      sonusIsupsgCircuitStatIdentityCode }
    ::= { sonusIsupsgCircuitStatTable 1 }

SonusIsupsgCircuitStatEntry ::=
    SEQUENCE {
        sonusIsupsgCircuitStatServiceListIndex      Integer32,
        sonusIsupsgCircuitStatIdentityCode  Integer32,
        sonusIsupsgCircuitStatUsage     INTEGER,
        sonusIsupsgCircuitStatLocalMaint INTEGER,
        sonusIsupsgCircuitStatLocalHw   INTEGER,
        sonusIsupsgCircuitStatRemoteMaint INTEGER,
        sonusIsupsgCircuitStatRemoteHw  INTEGER,
        sonusIsupsgCircuitStatManualCot INTEGER
    }

sonusIsupsgCircuitStatServiceListIndex OBJECT-TYPE
    SYNTAX          Integer32
    MAX-ACCESS      read-only
    STATUS          current
    DESCRIPTION     
            "The index of the ISUP Service Group circuit is defined for.."
    ::= { sonusIsupsgCircuitStatEntry 1 }

sonusIsupsgCircuitStatIdentityCode OBJECT-TYPE
    SYNTAX          Integer32 (0..16383)
    MAX-ACCESS      read-only
    STATUS          current
    DESCRIPTION     
            "Identifies the circuit identity code (CIC) for the circuit."
    ::= { sonusIsupsgCircuitStatEntry 2 }

sonusIsupsgCircuitStatUsage OBJECT-TYPE
    SYNTAX          INTEGER { unequipped(1), idle(2), inBusy(3), 
                        outBusy(4), transientSetup(5), 
                        transientRelease(6), inContinuity(7), 
                        outContinuity(8) }
    MAX-ACCESS      read-only
    STATUS          current
    DESCRIPTION     
            "The usage state of the ISUP circuit."
    ::= { sonusIsupsgCircuitStatEntry 3 }

sonusIsupsgCircuitStatLocalMaint OBJECT-TYPE
    SYNTAX          INTEGER { unblocked(1), blocked(2), 
                        transientUnblock(3), transientBlock(4), 
                        notAvailable(5) }
    MAX-ACCESS      read-only
    STATUS          current
    DESCRIPTION     
            "The local maintenance state of the ISUP circuit."
    ::= { sonusIsupsgCircuitStatEntry 4 }

sonusIsupsgCircuitStatLocalHw OBJECT-TYPE
    SYNTAX          INTEGER { unblocked(1), blocked(2), 
                        transientUnblock(3), transientBlock(4), 
                        notAvailable(5) }
    MAX-ACCESS      read-only
    STATUS          current
    DESCRIPTION     
            "The local hardware state of the ISUP circuit."
    ::= { sonusIsupsgCircuitStatEntry 5 }

sonusIsupsgCircuitStatRemoteMaint OBJECT-TYPE
    SYNTAX          INTEGER { unblocked(1), blocked(2), 
                        transientUnblock(3), transientBlock(4), 
                        notAvailable(5) }
    MAX-ACCESS      read-only
    STATUS          current
    DESCRIPTION     
            "The remote maintenance state of the ISUP circuit."
    ::= { sonusIsupsgCircuitStatEntry 6 }

sonusIsupsgCircuitStatRemoteHw OBJECT-TYPE
    SYNTAX          INTEGER { unblocked(1), blocked(2), 
                        transientUnblock(3), transientBlock(4), 
                        notAvailable(5) }
    MAX-ACCESS      read-only
    STATUS          current
    DESCRIPTION     
            "The remote hardware state of the ISUP circuit."
    ::= { sonusIsupsgCircuitStatEntry 7 }

sonusIsupsgCircuitStatManualCot OBJECT-TYPE
    SYNTAX          INTEGER { notAvailable(1), pending(2), inProgress(3), 
                        pass(4), fail(5), abort(6), lpaFail(7) }
    MAX-ACCESS      read-only
    STATUS          current
    DESCRIPTION     
            "The manual continuity test state of the ISUP circuit."
    ::= { sonusIsupsgCircuitStatEntry 8 }

sonusIsupsgFarEndCircuitAdminTable OBJECT-TYPE
    SYNTAX          SEQUENCE OF SonusIsupsgFarEndCircuitAdminEntry
    MAX-ACCESS      not-accessible
    STATUS          current
    DESCRIPTION     
            "This table contains administrative information of ISUP circuits on the 
             far end switch GSX is connected to. ISUP circuits should be configured
             on the GSX node to get the corresponding far end circuit admin info. The
             far end ISUP circuit may be not equipped or not configured. Therefore,
             it is possible that the far end info of an ISUP circuit would be unavailable."
    ::= { sonusIsupServiceGroupMIBObjects 6 }

sonusIsupsgFarEndCircuitAdminEntry OBJECT-TYPE
    SYNTAX          SonusIsupsgFarEndCircuitAdminEntry
    MAX-ACCESS      not-accessible
    STATUS          current
    DESCRIPTION     
            "This table describes the far end status of the ISUP circuits."
    INDEX           { sonusIsupsgFarEndCircuitServiceListIndex, 
                      sonusIsupsgFarEndCircuitIdentityCode }
    ::= { sonusIsupsgFarEndCircuitAdminTable 1 }

SonusIsupsgFarEndCircuitAdminEntry ::=
    SEQUENCE {
        sonusIsupsgFarEndCircuitServiceListIndex        Integer32,
        sonusIsupsgFarEndCircuitIdentityCode    Integer32,
        sonusIsupsgFarEndCircuitValidationTestResult            INTEGER,
        sonusIsupsgFarEndCircuitGroupCarrier    INTEGER,
        sonusIsupsgFarEndCircuitCicControl  INTEGER,
        sonusIsupsgFarEndCircuitAlarmCarrier    INTEGER,
        sonusIsupsgFarEndCircuitContinuityRequirement             INTEGER,
        sonusIsupsgFarEndCircuitIdentificationTrunkNumber                 SonusNameReference,
        sonusIsupsgFarEndCircuitIdentificationOfficeA             SonusNameReference,
        sonusIsupsgFarEndCircuitIdentificationOfficeZ             SonusNameReference,
        sonusIsupsgFarEndCircuitLocationIdentification              SonusNameReference,
        sonusIsupsgFarEndCircuitCicControlConflict          INTEGER
    }

sonusIsupsgFarEndCircuitServiceListIndex OBJECT-TYPE
    SYNTAX          Integer32
    MAX-ACCESS      read-only
    STATUS          current
    DESCRIPTION     
            "The index of the ISUP Service Group far end circuit is defined for."
    ::= { sonusIsupsgFarEndCircuitAdminEntry 1 }

sonusIsupsgFarEndCircuitIdentityCode OBJECT-TYPE
    SYNTAX          Integer32 (0..16383)
    MAX-ACCESS      read-only
    STATUS          current
    DESCRIPTION     
            "Identifies the circuit identity code (CIC) for the circuit."
    ::= { sonusIsupsgFarEndCircuitAdminEntry 2 }

sonusIsupsgFarEndCircuitValidationTestResult OBJECT-TYPE
    SYNTAX          INTEGER { noResponse(0), successful(1), failure(2), 
                        notAvailable(3) }
    MAX-ACCESS      read-only
    STATUS          current
    DESCRIPTION     
            "Result of the far end validation test on the circuit."
    ::= { sonusIsupsgFarEndCircuitAdminEntry 3 }

sonusIsupsgFarEndCircuitGroupCarrier OBJECT-TYPE
    SYNTAX          INTEGER { noResponse(0), unknown(1), analog(2), 
                        digital(3), digitalAndAnalog(4) }
    MAX-ACCESS      read-only
    STATUS          current
    DESCRIPTION     
            "Circuit group carrier indicator of the far end circuit."
    ::= { sonusIsupsgFarEndCircuitAdminEntry 4 }

sonusIsupsgFarEndCircuitCicControl OBJECT-TYPE
    SYNTAX          INTEGER { noResponse(0), noCics(1), oddCics(2), 
                        evenCics(3), allCics(4) }
    MAX-ACCESS      read-only
    STATUS          current
    DESCRIPTION     
            "Double seizing control indicator of the far end circuit group."
    ::= { sonusIsupsgFarEndCircuitAdminEntry 5 }

sonusIsupsgFarEndCircuitAlarmCarrier OBJECT-TYPE
    SYNTAX          INTEGER { noResponse(0), unknown(1), 
                        softwareCarrier(2), hardwareCarrier(3) }
    MAX-ACCESS      read-only
    STATUS          current
    DESCRIPTION     
            "Alarm carrier indicator of the far end circuit group."
    ::= { sonusIsupsgFarEndCircuitAdminEntry 6 }

sonusIsupsgFarEndCircuitContinuityRequirement OBJECT-TYPE
    SYNTAX          INTEGER { noResponse(0), unknown(1), none(2), 
                        statistical(3), perCall(4) }
    MAX-ACCESS      read-only
    STATUS          current
    DESCRIPTION     
            "Continuity check requirements of the far end circuit group."
    ::= { sonusIsupsgFarEndCircuitAdminEntry 7 }

sonusIsupsgFarEndCircuitIdentificationTrunkNumber OBJECT-TYPE
    SYNTAX          SonusNameReference
    MAX-ACCESS      read-only
    STATUS          current
    DESCRIPTION     
            "Trunk number of the far end circuit identification."
    ::= { sonusIsupsgFarEndCircuitAdminEntry 8 }

sonusIsupsgFarEndCircuitIdentificationOfficeA OBJECT-TYPE
    SYNTAX          SonusNameReference
    MAX-ACCESS      read-only
    STATUS          current
    DESCRIPTION     
            "Office identification for the far end circuit. [ Ref: ANSI T1.113/3.11A ]
             With respect to offices A and Z the following conventions are used:
             (a) For one-way trunk groups, the originating switch that offers traffic to the trunk group is office A.
             (b) For two-way trunk groups, the switch with the lower alphanumeric CLLI code is designated office A.
             (c) For one-way subgroups of a divided trunk group, the originating switch is designated office A.
             (d) For two-way subgroups of a divided trunk group, the switch with the lower alphanumeric CLLI code is designated office A."
    ::= { sonusIsupsgFarEndCircuitAdminEntry 9 }

sonusIsupsgFarEndCircuitIdentificationOfficeZ OBJECT-TYPE
    SYNTAX          SonusNameReference
    MAX-ACCESS      read-only
    STATUS          current
    DESCRIPTION     
            "Office identification for the far end circuit. [ Ref: ANSI T1.113/3.11A ]
             With respect to offices A and Z the following conventions are used:
             (a) For one-way trunk groups, the originating switch that offers traffic to the trunk group is office A.
             (b) For two-way trunk groups, the switch with the lower alphanumeric CLLI code is designated office A.
             (c) For one-way subgroups of a divided trunk group, the originating switch is designated office A.
             (d) For two-way subgroups of a divided trunk group, the switch with the lower alphanumeric CLLI code is designated office A."
    ::= { sonusIsupsgFarEndCircuitAdminEntry 10 }

sonusIsupsgFarEndCircuitLocationIdentification OBJECT-TYPE
    SYNTAX          SonusNameReference
    MAX-ACCESS      read-only
    STATUS          current
    DESCRIPTION     
            "Location identification of the far end circuit in CLLI( town/state/building/subdivision ) format."
    ::= { sonusIsupsgFarEndCircuitAdminEntry 11 }

sonusIsupsgFarEndCircuitCicControlConflict OBJECT-TYPE
    SYNTAX          INTEGER { noResponse(0), yes(1), no(2) }
    MAX-ACCESS      read-only
    STATUS          current
    DESCRIPTION     
            "Double seizing control for farend and nearend conflict indicator of the circuit group."
    ::= { sonusIsupsgFarEndCircuitAdminEntry 12 }

sonusIsupsgFarEndCircuitStatTable OBJECT-TYPE
    SYNTAX          SEQUENCE OF SonusIsupsgFarEndCircuitStatEntry
    MAX-ACCESS      not-accessible
    STATUS          current
    DESCRIPTION     
            "This table contains status information of ISUP circuits on the 
             far end switch GSX is connected to. ISUP circuits should be configured
             on the GSX node to get the corresponding far end circuit status. The
             far end ISUP circuit may be not equipped or not configured. Therefore,
             it is possible that the far end status of an ISUP circuit would be unavailable."
    ::= { sonusIsupServiceGroupMIBObjects 7 }

sonusIsupsgFarEndCircuitStatEntry OBJECT-TYPE
    SYNTAX          SonusIsupsgFarEndCircuitStatEntry
    MAX-ACCESS      not-accessible
    STATUS          current
    DESCRIPTION     
            "This table describes the far end status of the ISUP circuits."
    INDEX           { sonusIsupsgFarEndCircuitStatServiceListIndex, 
                      sonusIsupsgFarEndCircuitStatIdentityCode }
    ::= { sonusIsupsgFarEndCircuitStatTable 1 }

SonusIsupsgFarEndCircuitStatEntry ::=
    SEQUENCE {
        sonusIsupsgFarEndCircuitStatServiceListIndex            Integer32,
        sonusIsupsgFarEndCircuitStatIdentityCode        Integer32,
        sonusIsupsgFarEndCircuitStatStatus  INTEGER,
        sonusIsupsgFarEndCircuitStatLocalMaint      INTEGER
    }

sonusIsupsgFarEndCircuitStatServiceListIndex OBJECT-TYPE
    SYNTAX          Integer32
    MAX-ACCESS      read-only
    STATUS          current
    DESCRIPTION     
            "The index of the ISUP Service Group far end circuit is defined for."
    ::= { sonusIsupsgFarEndCircuitStatEntry 1 }

sonusIsupsgFarEndCircuitStatIdentityCode OBJECT-TYPE
    SYNTAX          Integer32 (0..16383)
    MAX-ACCESS      read-only
    STATUS          current
    DESCRIPTION     
            "Identifies the circuit identity code (CIC) for the circuit."
    ::= { sonusIsupsgFarEndCircuitStatEntry 2 }

sonusIsupsgFarEndCircuitStatStatus OBJECT-TYPE
    SYNTAX          INTEGER { noResponse(0), transient(1), unequipped(2), 
                        inbusyActive(3), inbusyLocalBlocked(4), 
                        inbusyRemoteBlocked(5), 
                        inbusyLocalRemoteBlocked(6), outbusyActive(7), 
                        outbusyLocalBlocked(8), outbusyRemoteBlocked(9), 
                        outbusyLocalRemoteBlocked(10), idle(11), 
                        idleLocalBlocked(12), idleRemoteBlocked(13), 
                        idleLocalRemoteBlocked(14), notAvailable(15) }
    MAX-ACCESS      read-only
    STATUS          current
    DESCRIPTION     
            "The far end status of the ISUP circuit."
    ::= { sonusIsupsgFarEndCircuitStatEntry 3 }

sonusIsupsgFarEndCircuitStatLocalMaint OBJECT-TYPE
    SYNTAX          INTEGER { unblocked(1), blocked(2), 
                        transientUnblock(3), transientBlock(4), 
                        notAvailable(5) }
    MAX-ACCESS      read-only
    STATUS          current
    DESCRIPTION     
            "The local maintenance state of the ISUP circuit."
    ::= { sonusIsupsgFarEndCircuitStatEntry 4 }

sonusIsupsgSignalingProfile OBJECT IDENTIFIER
    ::= { sonusIsupServiceGroupMIBObjects 8 }

sonusIsupsgSignalingProfileNextIndex OBJECT-TYPE
    SYNTAX          Integer32
    MAX-ACCESS      read-only
    STATUS          current
    DESCRIPTION     
            "The next valid index to use when creating a new sonusIsupsgSignalingProfileEntry"
    ::= { sonusIsupsgSignalingProfile 1 }

sonusIsupsgSignalingProfileTable OBJECT-TYPE
    SYNTAX          SEQUENCE OF SonusIsupsgSignalingProfileEntry
    MAX-ACCESS      not-accessible
    STATUS          current
    DESCRIPTION     
            "This table contains information about each ISUP Signaling Profile
             configured to be a member of the node. 
             A management entity may create rows for Signaling Profile that are
             anticipated to be supported in the future."
    ::= { sonusIsupsgSignalingProfile 2 }

sonusIsupsgSignalingProfileEntry OBJECT-TYPE
    SYNTAX          SonusIsupsgSignalingProfileEntry
    MAX-ACCESS      not-accessible
    STATUS          current
    DESCRIPTION     
            "This table describes the ISUP Signaling Profile that are configured."
    INDEX           { sonusIsupsgSignalingProfileListIndex }
    ::= { sonusIsupsgSignalingProfileTable 1 }

SonusIsupsgSignalingProfileEntry ::=
    SEQUENCE {
        sonusIsupsgSignalingProfileListIndex    Integer32,
        sonusIsupsgSignalingProfileName SonusName,
        sonusIsupsgSignalingProfileCompat SonusSupportFlag,
        sonusIsupsgSignalingProfileAccessDel    SonusSupportFlag,
        sonusIsupsgSignalingProfileGenNum SonusSupportFlag,
        sonusIsupsgSignalingProfileGenNotif   SonusSupportFlag,
        sonusIsupsgSignalingProfileGenDigs  SonusSupportFlag,
        sonusIsupsgSignalingProfileLocNum SonusSupportFlag,
        sonusIsupsgSignalingProfileOrigIscPC    SonusSupportFlag,
        sonusIsupsgSignalingProfileUserTeleService          SonusSupportFlag,
        sonusIsupsgSignalingProfileSegmentation       SonusSupportFlag,
        sonusIsupsgSignalingProfileFallback   SonusSupportFlag,
        sonusIsupsgSignalingProfilePropDelay    SonusSupportFlag,
        sonusIsupsgSignalingProfileEMcid SonusSupportFlag,
        sonusIsupsgSignalingProfileHopCounter     SonusSupportFlag,
        sonusIsupsgSignalingProfileSubPriorityCls         SonusSupportFlag,
        sonusIsupsgSignalingProfileAPM  SonusSupportFlag,
        sonusIsupsgSignalingProfileConNumInAcm      SonusSupportFlag,
        sonusIsupsgSignalingProfileCauseInCpg     SonusSupportFlag,
        sonusIsupsgSignalingProfileMultiCarrierEnv          SonusSupportFlag,
        sonusIsupsgSignalingProfileCarrierSelection           SonusSupportFlag,
        sonusIsupsgSignalingProfileInrInf SonusSupportFlag,
        sonusIsupsgSignalingProfileCqmCqr SonusSupportFlag,
        sonusIsupsgSignalingProfileCallRef  SonusSupportFlag,
        sonusIsupsgSignalingProfileCfn  SonusSupportFlag,
        sonusIsupsgSignalingProfileFacility   SonusSupportFlag,
        sonusIsupsgSignalingProfilePam  SonusSupportFlag,
        sonusIsupsgSignalingProfileObciAnm  SonusSupportFlag,
        sonusIsupsgSignalingProfileDrs  SonusSupportFlag,
        sonusIsupsgSignalingProfileRedNum SonusSupportFlag,
        sonusIsupsgSignalingProfileLpa  SonusSupportFlag,
        sonusIsupsgSignalingProfileUcic SonusSupportFlag,
        sonusIsupsgSignalingProfileOlm  SonusSupportFlag,
        sonusIsupsgSignalingProfileBBRel SonusSupportFlag,
        sonusIsupsgSignalingProfileUsr  SonusSupportFlag,
        sonusIsupsgSignalingProfileBBIam SonusSupportFlag,
        sonusIsupsgSignalingProfileCallModMsgs      SonusSupportFlag,
        sonusIsupsgSignalingProfileCallDiv  SonusSupportFlag,
        sonusIsupsgSignalingProfileCallHist   SonusSupportFlag,
        sonusIsupsgSignalingProfileGenRef SonusSupportFlag,
        sonusIsupsgSignalingProfileMLPP SonusSupportFlag,
        sonusIsupsgSignalingProfileNSF  SonusSupportFlag,
        sonusIsupsgSignalingProfileRedNumRist     SonusSupportFlag,
        sonusIsupsgSignalingProfileRemoteOp   SonusSupportFlag,
        sonusIsupsgSignalingProfileServActv   SonusSupportFlag,
        sonusIsupsgSignalingProfileSigPointCode       SonusSupportFlag,
        sonusIsupsgSignalingProfileTmrPrime   SonusSupportFlag,
        sonusIsupsgSignalingProfileTransMedUsed       SonusSupportFlag,
        sonusIsupsgSignalingProfileUsiPrime   SonusSupportFlag,
        sonusIsupsgSignalingProfileRedNumInAcm      SonusSupportFlag,
        sonusIsupsgSignalingProfileRedNumInAnm      SonusSupportFlag,
        sonusIsupsgSignalingProfileUuiInRel   SonusSupportFlag,
        sonusIsupsgSignalingProfileConReqInFaa      SonusSupportFlag,
        sonusIsupsgSignalingProfileConReqInFar      SonusSupportFlag,
        sonusIsupsgSignalingProfileFac  SonusSupportFlag,
        sonusIsupsgSignalingProfileEchoControl      SonusSupportFlag,
        sonusIsupsgSignalingProfileBackwardGVNS       SonusSupportFlag,
        sonusIsupsgSignalingProfileCircAssMap     SonusSupportFlag,
        sonusIsupsgSignalingProfileCCSS SonusSupportFlag,
        sonusIsupsgSignalingProfileCallDivTreat       SonusSupportFlag,
        sonusIsupsgSignalingProfileCalledInNum      SonusSupportFlag,
        sonusIsupsgSignalingProfileCollectCallReq         SonusSupportFlag,
        sonusIsupsgSignalingProfileConfTreat    SonusSupportFlag,
        sonusIsupsgSignalingProfileCorrelationId        SonusSupportFlag,
        sonusIsupsgSignalingProfileCallOfrTreat       SonusSupportFlag,
        sonusIsupsgSignalingProfileCallTransNum       SonusSupportFlag,
        sonusIsupsgSignalingProfileCallTransRef       SonusSupportFlag,
        sonusIsupsgSignalingProfileDispInfo   SonusSupportFlag,
        sonusIsupsgSignalingProfileForwardGVNS      SonusSupportFlag,
        sonusIsupsgSignalingProfileLoopPrevention         SonusSupportFlag,
        sonusIsupsgSignalingProfileNetworkMgmt      SonusSupportFlag,
        sonusIsupsgSignalingProfileSCFId SonusSupportFlag,
        sonusIsupsgSignalingProfileUIDActionInd       SonusSupportFlag,
        sonusIsupsgSignalingProfileUIDCapInd    SonusSupportFlag,
        sonusIsupsgSignalingProfileConNumInCpg      SonusSupportFlag,
        sonusIsupsgSignalingProfileGenNumInCpg      SonusSupportFlag,
        sonusIsupsgSignalingProfileEchoCntrlInIam         SonusSupportFlag,
        sonusIsupsgSignalingProfileRemoteOpInRel        SonusSupportFlag,
        sonusIsupsgSignalingProfileAccessTransInFac           SonusSupportFlag,
        sonusIsupsgSignalingProfileGenNotifInFac        SonusSupportFlag,
        sonusIsupsgSignalingProfileUuindAnm   SonusSupportFlag,
        sonusIsupsgSignalingProfileUuindCpg   SonusSupportFlag,
        sonusIsupsgSignalingProfileNrmSupport     SonusSupportFlag,
        sonusIsupsgSignalingProfileCseInRlc   SonusSupportFlag,
        sonusIsupsgSignalingProfileUpaUpt SonusSupportFlag,
        sonusIsupsgSignalingProfileRecInCai   SonusSupportFlag,
        sonusIsupsgSignalingProfileTransitUnrec       SonusSupportFlag,
        sonusIsupsgSignalingProfileCcRaw SonusSupportFlag,
        sonusIsupsgSignalingProfileCctGrpBlockFlag          SonusSupportFlag,
        sonusIsupsgSignalingProfileCctGrpResetFlag          SonusSupportFlag,
        sonusIsupsgSignalingProfileBaseProfileName          SonusNameReference,
        sonusIsupsgSignalingProfileAdminState     SonusAdminState,
        sonusIsupsgSignalingProfileRowStatus    RowStatus,
        sonusIsupsgSignalingProfilePropDelayValue         Integer32,
        sonusIsupsgSignalingProfileU2USrvcLevel       INTEGER,
        sonusIsupsgSignalingProfileSAM  SonusSupportFlag,
        sonusIsupsgSignalingProfileFOT  SonusSupportFlag,
        sonusIsupsgSignalingProfileSpecialDigits        BITS,
        sonusIsupsgSignalingProfileTNS  SonusSupportFlag,
        sonusIsupsgSignalingProfileAwaitDigits      SonusSupportFlag,
        sonusIsupsgSignalingProfileAccessTrans      SonusSupportFlag,
        sonusIsupsgSignalingProfileJurisdiction       SonusSupportFlag,
        sonusIsupsgSignalingProfileOCN  SonusSupportFlag,
        sonusIsupsgSignalingProfileBusinessGrp      SonusSupportFlag,
        sonusIsupsgSignalingProfileConReq SonusSupportFlag,
        sonusIsupsgSignalingProfileInfoInd  SonusSupportFlag,
        sonusIsupsgSignalingProfileNtp  SonusSupportFlag,
        sonusIsupsgSignalingProfileNotifInd   SonusSupportFlag,
        sonusIsupsgSignalingProfileRedInfoAcm     SonusSupportFlag,
        sonusIsupsgSignalingProfileEgressService        SonusSupportFlag,
        sonusIsupsgSignalingProfileServCodeInd      SonusSupportFlag,
        sonusIsupsgSignalingProfileSpecProcReq      SonusSupportFlag,
        sonusIsupsgSignalingProfileTransReq   SonusSupportFlag,
        sonusIsupsgSignalingProfileChgNum SonusSupportFlag,
        sonusIsupsgSignalingProfileGenAddressREL        SonusSupportFlag,
        sonusIsupsgSignalingProfileUUIndAcm   SonusSupportFlag,
        sonusIsupsgSignalingProfileUUInfo SonusSupportFlag,
        sonusIsupsgSignalingProfileOperatorServInfo           SonusSupportFlag,
        sonusIsupsgSignalingProfileCvtCvr SonusSupportFlag,
        sonusIsupsgSignalingProfileGenName  SonusSupportFlag,
        sonusIsupsgSignalingProfileRedCap SonusSupportFlag,
        sonusIsupsgSignalingProfileRedCount   SonusSupportFlag,
        sonusIsupsgSignalingProfileSendTwoGrpMsgs         SonusSupportFlag,
        sonusIsupsgSignalingProfileAwaitTwoGrpMsgs          SonusSupportFlag,
        sonusIsupsgSignalingProfileCqmOnCardSwap        SonusSupportFlag,
        sonusIsupsgSignalingProfileAnsi95Grs    SonusSupportFlag,
        sonusIsupsgSignalingProfileCpgBeforeAcm       SonusSupportFlag
    }

sonusIsupsgSignalingProfileListIndex OBJECT-TYPE
    SYNTAX          Integer32 (1..128)
    MAX-ACCESS      read-only
    STATUS          current
    DESCRIPTION     
            "The index of the ISUP Signaling Profile entry."
    ::= { sonusIsupsgSignalingProfileEntry 1 }

sonusIsupsgSignalingProfileName OBJECT-TYPE
    SYNTAX          SonusName
    MAX-ACCESS      read-write
    STATUS          current
    DESCRIPTION     
            "The name of the ISUP Signaling Profile."
    ::= { sonusIsupsgSignalingProfileEntry 2 }

sonusIsupsgSignalingProfileCompat OBJECT-TYPE
    SYNTAX          SonusSupportFlag
    MAX-ACCESS      read-write
    STATUS          current
    DESCRIPTION     
            "Is compatibility supported for the ISUP Signaling Profile."
    ::= { sonusIsupsgSignalingProfileEntry 3 }

sonusIsupsgSignalingProfileAccessDel OBJECT-TYPE
    SYNTAX          SonusSupportFlag
    MAX-ACCESS      read-write
    STATUS          current
    DESCRIPTION     
            "Is Access Delivery Information supported for the ISUP Signaling Profile."
    ::= { sonusIsupsgSignalingProfileEntry 4 }

sonusIsupsgSignalingProfileGenNum OBJECT-TYPE
    SYNTAX          SonusSupportFlag
    MAX-ACCESS      read-write
    STATUS          current
    DESCRIPTION     
            "Is the generic number parameter supported for the ISUP Signaling Profile."
    ::= { sonusIsupsgSignalingProfileEntry 5 }

sonusIsupsgSignalingProfileGenNotif OBJECT-TYPE
    SYNTAX          SonusSupportFlag
    MAX-ACCESS      read-write
    STATUS          current
    DESCRIPTION     
            "Is the generic notification parameter supported for the ISUP Signaling Profile."
    ::= { sonusIsupsgSignalingProfileEntry 6 }

sonusIsupsgSignalingProfileGenDigs OBJECT-TYPE
    SYNTAX          SonusSupportFlag
    MAX-ACCESS      read-write
    STATUS          current
    DESCRIPTION     
            "Is the generic digits parameter supported for the ISUP Signaling Profile."
    ::= { sonusIsupsgSignalingProfileEntry 7 }

sonusIsupsgSignalingProfileLocNum OBJECT-TYPE
    SYNTAX          SonusSupportFlag
    MAX-ACCESS      read-write
    STATUS          current
    DESCRIPTION     
            "Is the location number parameter supported for the ISUP Signaling Profile."
    ::= { sonusIsupsgSignalingProfileEntry 8 }

sonusIsupsgSignalingProfileOrigIscPC OBJECT-TYPE
    SYNTAX          SonusSupportFlag
    MAX-ACCESS      read-write
    STATUS          current
    DESCRIPTION     
            "Is the originating ISC point code parameter supported for the ISUP Signaling Profile."
    ::= { sonusIsupsgSignalingProfileEntry 9 }

sonusIsupsgSignalingProfileUserTeleService OBJECT-TYPE
    SYNTAX          SonusSupportFlag
    MAX-ACCESS      read-write
    STATUS          current
    DESCRIPTION     
            "Is the user teleservice parameter supported for the ISUP Signaling Profile."
    ::= { sonusIsupsgSignalingProfileEntry 10 }

sonusIsupsgSignalingProfileSegmentation OBJECT-TYPE
    SYNTAX          SonusSupportFlag
    MAX-ACCESS      read-write
    STATUS          current
    DESCRIPTION     
            "Is segmentation supported for the ISUP Signaling Profile."
    ::= { sonusIsupsgSignalingProfileEntry 11 }

sonusIsupsgSignalingProfileFallback OBJECT-TYPE
    SYNTAX          SonusSupportFlag
    MAX-ACCESS      read-write
    STATUS          current
    DESCRIPTION     
            "Is fallback supported for the ISUP Signaling Profile."
    ::= { sonusIsupsgSignalingProfileEntry 12 }

sonusIsupsgSignalingProfilePropDelay OBJECT-TYPE
    SYNTAX          SonusSupportFlag
    MAX-ACCESS      read-write
    STATUS          current
    DESCRIPTION     
            "Is propagation delay supported for the ISUP Signaling Profile."
    ::= { sonusIsupsgSignalingProfileEntry 13 }

sonusIsupsgSignalingProfileEMcid OBJECT-TYPE
    SYNTAX          SonusSupportFlag
    MAX-ACCESS      read-write
    STATUS          current
    DESCRIPTION     
            "Is MCID supported for the ISUP Signaling Profile."
    ::= { sonusIsupsgSignalingProfileEntry 14 }

sonusIsupsgSignalingProfileHopCounter OBJECT-TYPE
    SYNTAX          SonusSupportFlag
    MAX-ACCESS      read-write
    STATUS          current
    DESCRIPTION     
            "Is the hop counter supported for the ISUP Signaling Profile."
    ::= { sonusIsupsgSignalingProfileEntry 15 }

sonusIsupsgSignalingProfileSubPriorityCls OBJECT-TYPE
    SYNTAX          SonusSupportFlag
    MAX-ACCESS      read-write
    STATUS          current
    DESCRIPTION     
            "Is the subscriber priority class parameter supported for the ISUP Signaling Profile."
    ::= { sonusIsupsgSignalingProfileEntry 16 }

sonusIsupsgSignalingProfileAPM OBJECT-TYPE
    SYNTAX          SonusSupportFlag
    MAX-ACCESS      read-write
    STATUS          current
    DESCRIPTION     
            "Is APM supported for the ISUP Signaling Profile."
    ::= { sonusIsupsgSignalingProfileEntry 17 }

sonusIsupsgSignalingProfileConNumInAcm OBJECT-TYPE
    SYNTAX          SonusSupportFlag
    MAX-ACCESS      read-write
    STATUS          current
    DESCRIPTION     
            "Is the connected number parameter supported in the ACM for the ISUP Signaling Profile."
    ::= { sonusIsupsgSignalingProfileEntry 18 }

sonusIsupsgSignalingProfileCauseInCpg OBJECT-TYPE
    SYNTAX          SonusSupportFlag
    MAX-ACCESS      read-write
    STATUS          current
    DESCRIPTION     
            "Is the cause parameter supported in the CPG for the ISUP Signaling Profile."
    ::= { sonusIsupsgSignalingProfileEntry 19 }

sonusIsupsgSignalingProfileMultiCarrierEnv OBJECT-TYPE
    SYNTAX          SonusSupportFlag
    MAX-ACCESS      read-write
    STATUS          current
    DESCRIPTION     
            "Is the multi carrier environment parameter supported for the ISUP Signaling Profile."
    ::= { sonusIsupsgSignalingProfileEntry 20 }

sonusIsupsgSignalingProfileCarrierSelection OBJECT-TYPE
    SYNTAX          SonusSupportFlag
    MAX-ACCESS      read-write
    STATUS          current
    DESCRIPTION     
            "Is carrier selection supported for the ISUP Signaling Profile."
    ::= { sonusIsupsgSignalingProfileEntry 21 }

sonusIsupsgSignalingProfileInrInf OBJECT-TYPE
    SYNTAX          SonusSupportFlag
    MAX-ACCESS      read-write
    STATUS          current
    DESCRIPTION     
            "Is INR/INF supported for the ISUP Signaling Profile."
    ::= { sonusIsupsgSignalingProfileEntry 22 }

sonusIsupsgSignalingProfileCqmCqr OBJECT-TYPE
    SYNTAX          SonusSupportFlag
    MAX-ACCESS      read-write
    STATUS          current
    DESCRIPTION     
            "Is CQM/CQR supported for the ISUP Signaling Profile."
    ::= { sonusIsupsgSignalingProfileEntry 23 }

sonusIsupsgSignalingProfileCallRef OBJECT-TYPE
    SYNTAX          SonusSupportFlag
    MAX-ACCESS      read-write
    STATUS          current
    DESCRIPTION     
            "Is the call reference parameter supported for the ISUP Signaling Profile."
    ::= { sonusIsupsgSignalingProfileEntry 24 }

sonusIsupsgSignalingProfileCfn OBJECT-TYPE
    SYNTAX          SonusSupportFlag
    MAX-ACCESS      read-write
    STATUS          current
    DESCRIPTION     
            "Is CFN supported for the ISUP Signaling Profile."
    ::= { sonusIsupsgSignalingProfileEntry 25 }

sonusIsupsgSignalingProfileFacility OBJECT-TYPE
    SYNTAX          SonusSupportFlag
    MAX-ACCESS      read-write
    STATUS          current
    DESCRIPTION     
            "Are FAA, FAR and FRJ supported for the ISUP Signaling Profile."
    ::= { sonusIsupsgSignalingProfileEntry 26 }

sonusIsupsgSignalingProfilePam OBJECT-TYPE
    SYNTAX          SonusSupportFlag
    MAX-ACCESS      read-write
    STATUS          current
    DESCRIPTION     
            "Is PAM supported for the ISUP Signaling Profile."
    ::= { sonusIsupsgSignalingProfileEntry 27 }

sonusIsupsgSignalingProfileObciAnm OBJECT-TYPE
    SYNTAX          SonusSupportFlag
    MAX-ACCESS      read-write
    STATUS          current
    DESCRIPTION     
            "Is the OBCI parameter supported in the ANM for the ISUP Signaling Profile."
    ::= { sonusIsupsgSignalingProfileEntry 28 }

sonusIsupsgSignalingProfileDrs OBJECT-TYPE
    SYNTAX          SonusSupportFlag
    MAX-ACCESS      read-write
    STATUS          current
    DESCRIPTION     
            "Is DRS supported the ISUP Signaling Profile."
    ::= { sonusIsupsgSignalingProfileEntry 29 }

sonusIsupsgSignalingProfileRedNum OBJECT-TYPE
    SYNTAX          SonusSupportFlag
    MAX-ACCESS      read-write
    STATUS          current
    DESCRIPTION     
            "Is the redirection number parameter supported for the ISUP Signaling Profile."
    ::= { sonusIsupsgSignalingProfileEntry 30 }

sonusIsupsgSignalingProfileLpa OBJECT-TYPE
    SYNTAX          SonusSupportFlag
    MAX-ACCESS      read-write
    STATUS          current
    DESCRIPTION     
            "Is LPA supported for the ISUP Signaling Profile."
    ::= { sonusIsupsgSignalingProfileEntry 31 }

sonusIsupsgSignalingProfileUcic OBJECT-TYPE
    SYNTAX          SonusSupportFlag
    MAX-ACCESS      read-write
    STATUS          current
    DESCRIPTION     
            "Is UCIC supported for the ISUP Signaling Profile."
    ::= { sonusIsupsgSignalingProfileEntry 32 }

sonusIsupsgSignalingProfileOlm OBJECT-TYPE
    SYNTAX          SonusSupportFlag
    MAX-ACCESS      read-write
    STATUS          current
    DESCRIPTION     
            "Is OLM supported for the ISUP Signaling Profile."
    ::= { sonusIsupsgSignalingProfileEntry 33 }

sonusIsupsgSignalingProfileBBRel OBJECT-TYPE
    SYNTAX          SonusSupportFlag
    MAX-ACCESS      read-write
    STATUS          current
    DESCRIPTION     
            "Are Blue Book parameters supported in REL for the ISUP Signaling Profile."
    ::= { sonusIsupsgSignalingProfileEntry 34 }

sonusIsupsgSignalingProfileUsr OBJECT-TYPE
    SYNTAX          SonusSupportFlag
    MAX-ACCESS      read-write
    STATUS          current
    DESCRIPTION     
            "Is USR supported for the ISUP Signaling Profile."
    ::= { sonusIsupsgSignalingProfileEntry 35 }

sonusIsupsgSignalingProfileBBIam OBJECT-TYPE
    SYNTAX          SonusSupportFlag
    MAX-ACCESS      read-write
    STATUS          current
    DESCRIPTION     
            "Are the Blue Book parameters supported in IAM for the ISUP Signaling Profile."
    ::= { sonusIsupsgSignalingProfileEntry 36 }

sonusIsupsgSignalingProfileCallModMsgs OBJECT-TYPE
    SYNTAX          SonusSupportFlag
    MAX-ACCESS      read-write
    STATUS          current
    DESCRIPTION     
            "Are CMR, CMA and CMRJ supported for the ISUP Signaling Profile."
    ::= { sonusIsupsgSignalingProfileEntry 37 }

sonusIsupsgSignalingProfileCallDiv OBJECT-TYPE
    SYNTAX          SonusSupportFlag
    MAX-ACCESS      read-write
    STATUS          current
    DESCRIPTION     
            "Is call diversion supported for the ISUP Signaling Profile."
    ::= { sonusIsupsgSignalingProfileEntry 38 }

sonusIsupsgSignalingProfileCallHist OBJECT-TYPE
    SYNTAX          SonusSupportFlag
    MAX-ACCESS      read-write
    STATUS          current
    DESCRIPTION     
            "Is the call history parameter supported for the ISUP Signaling Profile."
    ::= { sonusIsupsgSignalingProfileEntry 39 }

sonusIsupsgSignalingProfileGenRef OBJECT-TYPE
    SYNTAX          SonusSupportFlag
    MAX-ACCESS      read-write
    STATUS          current
    DESCRIPTION     
            "Is the generic reference parameter supported for the ISUP Signaling Profile."
    ::= { sonusIsupsgSignalingProfileEntry 40 }

sonusIsupsgSignalingProfileMLPP OBJECT-TYPE
    SYNTAX          SonusSupportFlag
    MAX-ACCESS      read-write
    STATUS          current
    DESCRIPTION     
            "Is the MLPP parameter supported for the ISUP Signaling Profile."
    ::= { sonusIsupsgSignalingProfileEntry 41 }

sonusIsupsgSignalingProfileNSF OBJECT-TYPE
    SYNTAX          SonusSupportFlag
    MAX-ACCESS      read-write
    STATUS          current
    DESCRIPTION     
            "Is the NSF parameter supported for the ISUP Signaling Profile."
    ::= { sonusIsupsgSignalingProfileEntry 42 }

sonusIsupsgSignalingProfileRedNumRist OBJECT-TYPE
    SYNTAX          SonusSupportFlag
    MAX-ACCESS      read-write
    STATUS          current
    DESCRIPTION     
            "Is the redirection number restriction parameter supported for the ISUP Signaling Profile."
    ::= { sonusIsupsgSignalingProfileEntry 43 }

sonusIsupsgSignalingProfileRemoteOp OBJECT-TYPE
    SYNTAX          SonusSupportFlag
    MAX-ACCESS      read-write
    STATUS          current
    DESCRIPTION     
            "Is the remote operations parameter supported for the ISUP Signaling Profile."
    ::= { sonusIsupsgSignalingProfileEntry 44 }

sonusIsupsgSignalingProfileServActv OBJECT-TYPE
    SYNTAX          SonusSupportFlag
    MAX-ACCESS      read-write
    STATUS          current
    DESCRIPTION     
            "Is the service activation parameter supported for the ISUP Signaling Profile."
    ::= { sonusIsupsgSignalingProfileEntry 45 }

sonusIsupsgSignalingProfileSigPointCode OBJECT-TYPE
    SYNTAX          SonusSupportFlag
    MAX-ACCESS      read-write
    STATUS          current
    DESCRIPTION     
            "Is the signaling point code parameter supported for the ISUP Signaling Profile."
    ::= { sonusIsupsgSignalingProfileEntry 46 }

sonusIsupsgSignalingProfileTmrPrime OBJECT-TYPE
    SYNTAX          SonusSupportFlag
    MAX-ACCESS      read-write
    STATUS          current
    DESCRIPTION     
            "Is the TMR prime parameter supported for the ISUP Signaling Profile."
    ::= { sonusIsupsgSignalingProfileEntry 47 }

sonusIsupsgSignalingProfileTransMedUsed OBJECT-TYPE
    SYNTAX          SonusSupportFlag
    MAX-ACCESS      read-write
    STATUS          current
    DESCRIPTION     
            "Is the transimission medium used parameter supported for the ISUP Signaling Profile."
    ::= { sonusIsupsgSignalingProfileEntry 48 }

sonusIsupsgSignalingProfileUsiPrime OBJECT-TYPE
    SYNTAX          SonusSupportFlag
    MAX-ACCESS      read-write
    STATUS          current
    DESCRIPTION     
            "Is the USI prime parameter supported for the ISUP Signaling Profile."
    ::= { sonusIsupsgSignalingProfileEntry 49 }

sonusIsupsgSignalingProfileRedNumInAcm OBJECT-TYPE
    SYNTAX          SonusSupportFlag
    MAX-ACCESS      read-write
    STATUS          current
    DESCRIPTION     
            "Is the rediction number supported in the ACM for the ISUP Signaling Profile."
    ::= { sonusIsupsgSignalingProfileEntry 50 }

sonusIsupsgSignalingProfileRedNumInAnm OBJECT-TYPE
    SYNTAX          SonusSupportFlag
    MAX-ACCESS      read-write
    STATUS          current
    DESCRIPTION     
            "Is the rediretion number supported in the ANM for the ISUP Signaling Profile."
    ::= { sonusIsupsgSignalingProfileEntry 51 }

sonusIsupsgSignalingProfileUuiInRel OBJECT-TYPE
    SYNTAX          SonusSupportFlag
    MAX-ACCESS      read-write
    STATUS          current
    DESCRIPTION     
            "Is the UUI parameter supported in the REL for the ISUP Signaling Profile."
    ::= { sonusIsupsgSignalingProfileEntry 52 }

sonusIsupsgSignalingProfileConReqInFaa OBJECT-TYPE
    SYNTAX          SonusSupportFlag
    MAX-ACCESS      read-write
    STATUS          current
    DESCRIPTION     
            "Is the connection request parameter supported in the FAA for the ISUP Signaling Profile."
    ::= { sonusIsupsgSignalingProfileEntry 53 }

sonusIsupsgSignalingProfileConReqInFar OBJECT-TYPE
    SYNTAX          SonusSupportFlag
    MAX-ACCESS      read-write
    STATUS          current
    DESCRIPTION     
            "Is the connection request parameter supported in the FAR for the ISUP Signaling Profile."
    ::= { sonusIsupsgSignalingProfileEntry 54 }

sonusIsupsgSignalingProfileFac OBJECT-TYPE
    SYNTAX          SonusSupportFlag
    MAX-ACCESS      read-write
    STATUS          current
    DESCRIPTION     
            "Is the FAC supported for the ISUP Signaling Profile."
    ::= { sonusIsupsgSignalingProfileEntry 55 }

sonusIsupsgSignalingProfileEchoControl OBJECT-TYPE
    SYNTAX          SonusSupportFlag
    MAX-ACCESS      read-write
    STATUS          current
    DESCRIPTION     
            "Is the echo control parameter supported for the ISUP Signaling Profile."
    ::= { sonusIsupsgSignalingProfileEntry 56 }

sonusIsupsgSignalingProfileBackwardGVNS OBJECT-TYPE
    SYNTAX          SonusSupportFlag
    MAX-ACCESS      read-write
    STATUS          current
    DESCRIPTION     
            "Is the backward GVNS parameter supported for the ISUP Signaling Profile."
    ::= { sonusIsupsgSignalingProfileEntry 57 }

sonusIsupsgSignalingProfileCircAssMap OBJECT-TYPE
    SYNTAX          SonusSupportFlag
    MAX-ACCESS      read-write
    STATUS          current
    DESCRIPTION     
            "Is the circuit assignment map parameter supported for the ISUP Signaling Profile."
    ::= { sonusIsupsgSignalingProfileEntry 58 }

sonusIsupsgSignalingProfileCCSS OBJECT-TYPE
    SYNTAX          SonusSupportFlag
    MAX-ACCESS      read-write
    STATUS          current
    DESCRIPTION     
            "Is the CCSS parameter supported for the ISUP Signaling Profile."
    ::= { sonusIsupsgSignalingProfileEntry 59 }

sonusIsupsgSignalingProfileCallDivTreat OBJECT-TYPE
    SYNTAX          SonusSupportFlag
    MAX-ACCESS      read-write
    STATUS          current
    DESCRIPTION     
            "Is the call diversion treatment parameter supported for the ISUP Signaling Profile."
    ::= { sonusIsupsgSignalingProfileEntry 60 }

sonusIsupsgSignalingProfileCalledInNum OBJECT-TYPE
    SYNTAX          SonusSupportFlag
    MAX-ACCESS      read-write
    STATUS          current
    DESCRIPTION     
            "Is the called IN number parameter supported for the ISUP Signaling Profile."
    ::= { sonusIsupsgSignalingProfileEntry 61 }

sonusIsupsgSignalingProfileCollectCallReq OBJECT-TYPE
    SYNTAX          SonusSupportFlag
    MAX-ACCESS      read-write
    STATUS          current
    DESCRIPTION     
            "Is the collect call request parameter supported for the ISUP Signaling Profile."
    ::= { sonusIsupsgSignalingProfileEntry 62 }

sonusIsupsgSignalingProfileConfTreat OBJECT-TYPE
    SYNTAX          SonusSupportFlag
    MAX-ACCESS      read-write
    STATUS          current
    DESCRIPTION     
            "Is the conference treatment parameter supported for the ISUP Signaling Profile."
    ::= { sonusIsupsgSignalingProfileEntry 63 }

sonusIsupsgSignalingProfileCorrelationId OBJECT-TYPE
    SYNTAX          SonusSupportFlag
    MAX-ACCESS      read-write
    STATUS          current
    DESCRIPTION     
            "Is the correlation ID parameter supported for the ISUP Signaling Profile."
    ::= { sonusIsupsgSignalingProfileEntry 64 }

sonusIsupsgSignalingProfileCallOfrTreat OBJECT-TYPE
    SYNTAX          SonusSupportFlag
    MAX-ACCESS      read-write
    STATUS          current
    DESCRIPTION     
            "Is the call offering treatment parameter supported for the ISUP Signaling Profile."
    ::= { sonusIsupsgSignalingProfileEntry 65 }

sonusIsupsgSignalingProfileCallTransNum OBJECT-TYPE
    SYNTAX          SonusSupportFlag
    MAX-ACCESS      read-write
    STATUS          current
    DESCRIPTION     
            "Is the call transfer number paramaeter supported for the ISUP Signaling Profile."
    ::= { sonusIsupsgSignalingProfileEntry 66 }

sonusIsupsgSignalingProfileCallTransRef OBJECT-TYPE
    SYNTAX          SonusSupportFlag
    MAX-ACCESS      read-write
    STATUS          current
    DESCRIPTION     
            "Is the call transfer reference parameter supported for the ISUP Signaling Profile."
    ::= { sonusIsupsgSignalingProfileEntry 67 }

sonusIsupsgSignalingProfileDispInfo OBJECT-TYPE
    SYNTAX          SonusSupportFlag
    MAX-ACCESS      read-write
    STATUS          current
    DESCRIPTION     
            "Is the display information parameter supported for the ISUP Signaling Profile."
    ::= { sonusIsupsgSignalingProfileEntry 68 }

sonusIsupsgSignalingProfileForwardGVNS OBJECT-TYPE
    SYNTAX          SonusSupportFlag
    MAX-ACCESS      read-write
    STATUS          current
    DESCRIPTION     
            "Is the forward GVNS parameter supported for the ISUP Signaling Profile."
    ::= { sonusIsupsgSignalingProfileEntry 69 }

sonusIsupsgSignalingProfileLoopPrevention OBJECT-TYPE
    SYNTAX          SonusSupportFlag
    MAX-ACCESS      read-write
    STATUS          current
    DESCRIPTION     
            "Is the loop prevention indicators parameter supported for the ISUP Signaling Profile."
    ::= { sonusIsupsgSignalingProfileEntry 70 }

sonusIsupsgSignalingProfileNetworkMgmt OBJECT-TYPE
    SYNTAX          SonusSupportFlag
    MAX-ACCESS      read-write
    STATUS          current
    DESCRIPTION     
            "Is network management controls parameter supported for the ISUP Signaling Profile."
    ::= { sonusIsupsgSignalingProfileEntry 71 }

sonusIsupsgSignalingProfileSCFId OBJECT-TYPE
    SYNTAX          SonusSupportFlag
    MAX-ACCESS      read-write
    STATUS          current
    DESCRIPTION     
            "Is the SCF ID parameter supported for the ISUP Signaling Profile."
    ::= { sonusIsupsgSignalingProfileEntry 72 }

sonusIsupsgSignalingProfileUIDActionInd OBJECT-TYPE
    SYNTAX          SonusSupportFlag
    MAX-ACCESS      read-write
    STATUS          current
    DESCRIPTION     
            "Is the UID action indicators parameter supported for the ISUP Signaling Profile."
    ::= { sonusIsupsgSignalingProfileEntry 73 }

sonusIsupsgSignalingProfileUIDCapInd OBJECT-TYPE
    SYNTAX          SonusSupportFlag
    MAX-ACCESS      read-write
    STATUS          current
    DESCRIPTION     
            "Is the UID capabilities parameter supported for the ISUP Signaling Profile."
    ::= { sonusIsupsgSignalingProfileEntry 74 }

sonusIsupsgSignalingProfileConNumInCpg OBJECT-TYPE
    SYNTAX          SonusSupportFlag
    MAX-ACCESS      read-write
    STATUS          current
    DESCRIPTION     
            "Is the connected number parameter supported in the CPG for the ISUP Signaling Profile."
    ::= { sonusIsupsgSignalingProfileEntry 75 }

sonusIsupsgSignalingProfileGenNumInCpg OBJECT-TYPE
    SYNTAX          SonusSupportFlag
    MAX-ACCESS      read-write
    STATUS          current
    DESCRIPTION     
            "Is the generic number parameter supported in the CPG for  the ISUP Signaling Profile."
    ::= { sonusIsupsgSignalingProfileEntry 76 }

sonusIsupsgSignalingProfileEchoCntrlInIam OBJECT-TYPE
    SYNTAX          SonusSupportFlag
    MAX-ACCESS      read-write
    STATUS          current
    DESCRIPTION     
            "Is the echo control parameter supported in the IAM for the ISUP Signaling Profile."
    ::= { sonusIsupsgSignalingProfileEntry 77 }

sonusIsupsgSignalingProfileRemoteOpInRel OBJECT-TYPE
    SYNTAX          SonusSupportFlag
    MAX-ACCESS      read-write
    STATUS          current
    DESCRIPTION     
            "Is the remote operations parameter supported in the REL for the ISUP Signaling Profile."
    ::= { sonusIsupsgSignalingProfileEntry 78 }

sonusIsupsgSignalingProfileAccessTransInFac OBJECT-TYPE
    SYNTAX          SonusSupportFlag
    MAX-ACCESS      read-write
    STATUS          current
    DESCRIPTION     
            "Is the access transport parameter supported in the FAC for the ISUP Signaling Profile."
    ::= { sonusIsupsgSignalingProfileEntry 79 }

sonusIsupsgSignalingProfileGenNotifInFac OBJECT-TYPE
    SYNTAX          SonusSupportFlag
    MAX-ACCESS      read-write
    STATUS          current
    DESCRIPTION     
            "Is the generic notification parameter supported for the ISUP Signaling Profile."
    ::= { sonusIsupsgSignalingProfileEntry 80 }

sonusIsupsgSignalingProfileUuindAnm OBJECT-TYPE
    SYNTAX          SonusSupportFlag
    MAX-ACCESS      read-write
    STATUS          current
    DESCRIPTION     
            "Is the UUI parameter supported in the ANM for the ISUP Signaling Profile."
    ::= { sonusIsupsgSignalingProfileEntry 81 }

sonusIsupsgSignalingProfileUuindCpg OBJECT-TYPE
    SYNTAX          SonusSupportFlag
    MAX-ACCESS      read-write
    STATUS          current
    DESCRIPTION     
            "Is the UUI parameter supported in the CPG for the ISUP Signaling Profile."
    ::= { sonusIsupsgSignalingProfileEntry 82 }

sonusIsupsgSignalingProfileNrmSupport OBJECT-TYPE
    SYNTAX          SonusSupportFlag
    MAX-ACCESS      read-write
    STATUS          current
    DESCRIPTION     
            "Is the NRM supported for the ISUP Signaling Profile."
    ::= { sonusIsupsgSignalingProfileEntry 83 }

sonusIsupsgSignalingProfileCseInRlc OBJECT-TYPE
    SYNTAX          SonusSupportFlag
    MAX-ACCESS      read-write
    STATUS          current
    DESCRIPTION     
            "Is the cause parameter supported in the RLC for the ISUP Signaling Profile."
    ::= { sonusIsupsgSignalingProfileEntry 84 }

sonusIsupsgSignalingProfileUpaUpt OBJECT-TYPE
    SYNTAX          SonusSupportFlag
    MAX-ACCESS      read-write
    STATUS          current
    DESCRIPTION     
            "Are UPA/UPT supported for the ISUP Signaling Profile."
    ::= { sonusIsupsgSignalingProfileEntry 85 }

sonusIsupsgSignalingProfileRecInCai OBJECT-TYPE
    SYNTAX          SonusSupportFlag
    MAX-ACCESS      read-write
    STATUS          current
    DESCRIPTION     
            "Is the recommnedation field supported in the cause parameter for the ISUP Signaling Profile."
    ::= { sonusIsupsgSignalingProfileEntry 86 }

sonusIsupsgSignalingProfileTransitUnrec OBJECT-TYPE
    SYNTAX          SonusSupportFlag
    MAX-ACCESS      read-write
    STATUS          current
    DESCRIPTION     
            "Is the transiting of unrecognised parameters supported for the ISUP service Group."
    ::= { sonusIsupsgSignalingProfileEntry 87 }

sonusIsupsgSignalingProfileCcRaw OBJECT-TYPE
    SYNTAX          SonusSupportFlag
    MAX-ACCESS      read-write
    STATUS          current
    DESCRIPTION     
            "Should raw ISUP messages be sent to CC for the ISUP Signaling Profile."
    ::= { sonusIsupsgSignalingProfileEntry 88 }

sonusIsupsgSignalingProfileCctGrpBlockFlag OBJECT-TYPE
    SYNTAX          SonusSupportFlag
    MAX-ACCESS      read-write
    STATUS          current
    DESCRIPTION     
            "The flag to be set to allow CGB and CGU messages in the ISUP Signaling Profile."
    DEFVAL          { supported }
    ::= { sonusIsupsgSignalingProfileEntry 89 }

sonusIsupsgSignalingProfileCctGrpResetFlag OBJECT-TYPE
    SYNTAX          SonusSupportFlag
    MAX-ACCESS      read-write
    STATUS          current
    DESCRIPTION     
            "The flag to be set to allow GRS messages in the ISUP Signaling Profile."
    DEFVAL          { supported }
    ::= { sonusIsupsgSignalingProfileEntry 90 }

sonusIsupsgSignalingProfileBaseProfileName OBJECT-TYPE
    SYNTAX          SonusNameReference
    MAX-ACCESS      read-write
    STATUS          current
    DESCRIPTION     
            "The ISUP Signaling Profile used as a base for the settings of this Signaling Profile."
    ::= { sonusIsupsgSignalingProfileEntry 91 }

sonusIsupsgSignalingProfileAdminState OBJECT-TYPE
    SYNTAX          SonusAdminState
    MAX-ACCESS      read-write
    STATUS          current
    DESCRIPTION     
            "The admin state of the ISUP Signaling Profile."
    ::= { sonusIsupsgSignalingProfileEntry 92 }

sonusIsupsgSignalingProfileRowStatus OBJECT-TYPE
    SYNTAX          RowStatus
    MAX-ACCESS      read-write
    STATUS          current
    DESCRIPTION     
            ""
    ::= { sonusIsupsgSignalingProfileEntry 93 }

sonusIsupsgSignalingProfilePropDelayValue OBJECT-TYPE
    SYNTAX          Integer32 (0..400)
    MAX-ACCESS      read-write
    STATUS          current
    DESCRIPTION     
            "The propagation delay value in milliseconds for this ISUP signaling profile."
    DEFVAL          { 0 }
    ::= { sonusIsupsgSignalingProfileEntry 94 }

sonusIsupsgSignalingProfileU2USrvcLevel OBJECT-TYPE
    SYNTAX          INTEGER { none(0), level1(1), level2(2), level3(3) }
    MAX-ACCESS      read-write
    STATUS          current
    DESCRIPTION     
            "The level of user to user services supported in the the ISUP Signaling Profile."
    DEFVAL          { none }
    ::= { sonusIsupsgSignalingProfileEntry 95 }

sonusIsupsgSignalingProfileSAM OBJECT-TYPE
    SYNTAX          SonusSupportFlag
    MAX-ACCESS      read-write
    STATUS          current
    DESCRIPTION     
            "Is the Subsequent Address Message supported for the ISUP Signaling Profile."
    DEFVAL          { unsupported }
    ::= { sonusIsupsgSignalingProfileEntry 96 }

sonusIsupsgSignalingProfileFOT OBJECT-TYPE
    SYNTAX          SonusSupportFlag
    MAX-ACCESS      read-write
    STATUS          current
    DESCRIPTION     
            "Is the Forward Transfer Message supported for the ISUP Signaling Profile."
    DEFVAL          { unsupported }
    ::= { sonusIsupsgSignalingProfileEntry 97 }

sonusIsupsgSignalingProfileSpecialDigits OBJECT-TYPE
    SYNTAX          BITS { digitA(0), digitB(1), digitC(2), digitD(3), 
                        digitE(4), digitF(5), none(6) }
    MAX-ACCESS      read-write
    STATUS          current
    DESCRIPTION     
            "Indicates the special digits which can appear in dialed digit strings 
             
             BIT 0 - Is digit A allowed in the digit string 
             BIT 1 - Is digit B allowed in the digit string 
             BIT 2 - Is digit C allowed in the digit string 
             BIT 3 - Is digit D allowed in the digit string 
             BIT 4 - Is digit E allowed in the digit string 
             BIT 5 - Is digit F allowed in the digit string 
             BIT 6 - No special digits in the digit string"
    ::= { sonusIsupsgSignalingProfileEntry 98 }

sonusIsupsgSignalingProfileTNS OBJECT-TYPE
    SYNTAX          SonusSupportFlag
    MAX-ACCESS      read-write
    STATUS          current
    DESCRIPTION     
            "Is the Transit Network Selection Parameter supported for the ISUP Signaling Profile."
    DEFVAL          { unsupported }
    ::= { sonusIsupsgSignalingProfileEntry 99 }

sonusIsupsgSignalingProfileAwaitDigits OBJECT-TYPE
    SYNTAX          SonusSupportFlag
    MAX-ACCESS      read-write
    STATUS          current
    DESCRIPTION     
            "Is Await Digits supported for this ISUP Signaling Profile."
    DEFVAL          { unsupported }
    ::= { sonusIsupsgSignalingProfileEntry 100 }

sonusIsupsgSignalingProfileAccessTrans OBJECT-TYPE
    SYNTAX          SonusSupportFlag
    MAX-ACCESS      read-write
    STATUS          current
    DESCRIPTION     
            "Is the Access Transport parameter supported for the ISUP Signaling Profile."
    DEFVAL          { supported }
    ::= { sonusIsupsgSignalingProfileEntry 101 }

sonusIsupsgSignalingProfileJurisdiction OBJECT-TYPE
    SYNTAX          SonusSupportFlag
    MAX-ACCESS      read-write
    STATUS          current
    DESCRIPTION     
            "Is the Jurisdiction parameter supported for the ISUP Signaling Profile."
    DEFVAL          { supported }
    ::= { sonusIsupsgSignalingProfileEntry 102 }

sonusIsupsgSignalingProfileOCN OBJECT-TYPE
    SYNTAX          SonusSupportFlag
    MAX-ACCESS      read-write
    STATUS          current
    DESCRIPTION     
            "Is the Original Called Number  parameter supported for the ISUP Signaling Profile."
    DEFVAL          { supported }
    ::= { sonusIsupsgSignalingProfileEntry 103 }

sonusIsupsgSignalingProfileBusinessGrp OBJECT-TYPE
    SYNTAX          SonusSupportFlag
    MAX-ACCESS      read-write
    STATUS          current
    DESCRIPTION     
            "Is the Business Group parameter supported for the ISUP Signaling Profile."
    DEFVAL          { supported }
    ::= { sonusIsupsgSignalingProfileEntry 104 }

sonusIsupsgSignalingProfileConReq OBJECT-TYPE
    SYNTAX          SonusSupportFlag
    MAX-ACCESS      read-write
    STATUS          current
    DESCRIPTION     
            "Is the Conection Request parameter supported for the ISUP Signaling Profile."
    DEFVAL          { supported }
    ::= { sonusIsupsgSignalingProfileEntry 105 }

sonusIsupsgSignalingProfileInfoInd OBJECT-TYPE
    SYNTAX          SonusSupportFlag
    MAX-ACCESS      read-write
    STATUS          current
    DESCRIPTION     
            "Is the Information Indicator parameter supported for the ISUP Signaling Profile."
    DEFVAL          { supported }
    ::= { sonusIsupsgSignalingProfileEntry 106 }

sonusIsupsgSignalingProfileNtp OBJECT-TYPE
    SYNTAX          SonusSupportFlag
    MAX-ACCESS      read-write
    STATUS          current
    DESCRIPTION     
            "Is the Network Transport supported for the ISUP Signaling Profile."
    DEFVAL          { supported }
    ::= { sonusIsupsgSignalingProfileEntry 107 }

sonusIsupsgSignalingProfileNotifInd OBJECT-TYPE
    SYNTAX          SonusSupportFlag
    MAX-ACCESS      read-write
    STATUS          current
    DESCRIPTION     
            "Is the Notification Indicator parameter supported for the ISUP Signaling Profile."
    DEFVAL          { supported }
    ::= { sonusIsupsgSignalingProfileEntry 108 }

sonusIsupsgSignalingProfileRedInfoAcm OBJECT-TYPE
    SYNTAX          SonusSupportFlag
    MAX-ACCESS      read-write
    STATUS          current
    DESCRIPTION     
            "Is the Redirection Information parameter supported in the ACM message
             for the ISUP Signaling Profile."
    DEFVAL          { supported }
    ::= { sonusIsupsgSignalingProfileEntry 109 }

sonusIsupsgSignalingProfileEgressService OBJECT-TYPE
    SYNTAX          SonusSupportFlag
    MAX-ACCESS      read-write
    STATUS          current
    DESCRIPTION     
            "Is the Egress Service parameter supported for the ISUP Signaling Profile."
    DEFVAL          { supported }
    ::= { sonusIsupsgSignalingProfileEntry 110 }

sonusIsupsgSignalingProfileServCodeInd OBJECT-TYPE
    SYNTAX          SonusSupportFlag
    MAX-ACCESS      read-write
    STATUS          current
    DESCRIPTION     
            "Is the Service Code Indicator parameter supported for the ISUP Signaling Profile."
    DEFVAL          { supported }
    ::= { sonusIsupsgSignalingProfileEntry 111 }

sonusIsupsgSignalingProfileSpecProcReq OBJECT-TYPE
    SYNTAX          SonusSupportFlag
    MAX-ACCESS      read-write
    STATUS          current
    DESCRIPTION     
            "Is the Special Processing Request parameter supported for the ISUP Signaling Profile."
    DEFVAL          { supported }
    ::= { sonusIsupsgSignalingProfileEntry 112 }

sonusIsupsgSignalingProfileTransReq OBJECT-TYPE
    SYNTAX          SonusSupportFlag
    MAX-ACCESS      read-write
    STATUS          current
    DESCRIPTION     
            "Is the Transaction Request parameter supported for the
             ISUP Signaling Profile."
    DEFVAL          { supported }
    ::= { sonusIsupsgSignalingProfileEntry 113 }

sonusIsupsgSignalingProfileChgNum OBJECT-TYPE
    SYNTAX          SonusSupportFlag
    MAX-ACCESS      read-write
    STATUS          current
    DESCRIPTION     
            "Is the Charge Number parameter supported for the ISUP Signaling Profile."
    DEFVAL          { supported }
    ::= { sonusIsupsgSignalingProfileEntry 114 }

sonusIsupsgSignalingProfileGenAddressREL OBJECT-TYPE
    SYNTAX          SonusSupportFlag
    MAX-ACCESS      read-write
    STATUS          current
    DESCRIPTION     
            "Is the Generic Address parameter supported in the REL message for the
             ISUP Signaling Profile."
    DEFVAL          { supported }
    ::= { sonusIsupsgSignalingProfileEntry 115 }

sonusIsupsgSignalingProfileUUIndAcm OBJECT-TYPE
    SYNTAX          SonusSupportFlag
    MAX-ACCESS      read-write
    STATUS          current
    DESCRIPTION     
            "Is the User to User Indicators parameter supported for the ISUP Signaling Profile."
    DEFVAL          { supported }
    ::= { sonusIsupsgSignalingProfileEntry 116 }

sonusIsupsgSignalingProfileUUInfo OBJECT-TYPE
    SYNTAX          SonusSupportFlag
    MAX-ACCESS      read-write
    STATUS          current
    DESCRIPTION     
            "Is the User to User Information parameter supported for the ISUP Signaling Profile."
    DEFVAL          { supported }
    ::= { sonusIsupsgSignalingProfileEntry 117 }

sonusIsupsgSignalingProfileOperatorServInfo OBJECT-TYPE
    SYNTAX          SonusSupportFlag
    MAX-ACCESS      read-write
    STATUS          current
    DESCRIPTION     
            "Is the Operator Service Information parameter supported for the ISUP Signaling Profile."
    DEFVAL          { supported }
    ::= { sonusIsupsgSignalingProfileEntry 118 }

sonusIsupsgSignalingProfileCvtCvr OBJECT-TYPE
    SYNTAX          SonusSupportFlag
    MAX-ACCESS      read-write
    STATUS          current
    DESCRIPTION     
            "Are the Circuit Validation Test/Response procedures supported for
             the ISUP Signaling Profile."
    DEFVAL          { supported }
    ::= { sonusIsupsgSignalingProfileEntry 119 }

sonusIsupsgSignalingProfileGenName OBJECT-TYPE
    SYNTAX          SonusSupportFlag
    MAX-ACCESS      read-write
    STATUS          current
    DESCRIPTION     
            "Is the Generic Name parameter supported for the ISUP Signaling Profile."
    DEFVAL          { supported }
    ::= { sonusIsupsgSignalingProfileEntry 120 }

sonusIsupsgSignalingProfileRedCap OBJECT-TYPE
    SYNTAX          SonusSupportFlag
    MAX-ACCESS      read-write
    STATUS          current
    DESCRIPTION     
            "Is the Redirection Capability parameter supported for the ISUP Signaling Profile."
    DEFVAL          { supported }
    ::= { sonusIsupsgSignalingProfileEntry 121 }

sonusIsupsgSignalingProfileRedCount OBJECT-TYPE
    SYNTAX          SonusSupportFlag
    MAX-ACCESS      read-write
    STATUS          current
    DESCRIPTION     
            "Is the Group Redirection Count parameter supported for the ISUP Signaling Profile."
    DEFVAL          { supported }
    ::= { sonusIsupsgSignalingProfileEntry 122 }

sonusIsupsgSignalingProfileSendTwoGrpMsgs OBJECT-TYPE
    SYNTAX          SonusSupportFlag
    MAX-ACCESS      read-write
    STATUS          current
    DESCRIPTION     
            "Set the Flag to Send Two Group Messages in the ISUP Signaling Profile."
    DEFVAL          { supported }
    ::= { sonusIsupsgSignalingProfileEntry 123 }

sonusIsupsgSignalingProfileAwaitTwoGrpMsgs OBJECT-TYPE
    SYNTAX          SonusSupportFlag
    MAX-ACCESS      read-write
    STATUS          current
    DESCRIPTION     
            "Set the Flag to Await Two Group Messages in the ISUP Signaling Profile."
    DEFVAL          { supported }
    ::= { sonusIsupsgSignalingProfileEntry 124 }

sonusIsupsgSignalingProfileCqmOnCardSwap OBJECT-TYPE
    SYNTAX          SonusSupportFlag
    MAX-ACCESS      read-write
    STATUS          current
    DESCRIPTION     
            "Set the Flag to perform CQM on Card Swap in the ISUP Signaling Profile."
    DEFVAL          { supported }
    ::= { sonusIsupsgSignalingProfileEntry 125 }

sonusIsupsgSignalingProfileAnsi95Grs OBJECT-TYPE
    SYNTAX          SonusSupportFlag
    MAX-ACCESS      read-write
    STATUS          current
    DESCRIPTION     
            "Should the ANSI-95 format for Group Reset Circuit (GRS), which includes
             optional parameters, be used."
    DEFVAL          { supported }
    ::= { sonusIsupsgSignalingProfileEntry 126 }

sonusIsupsgSignalingProfileCpgBeforeAcm OBJECT-TYPE
    SYNTAX          SonusSupportFlag
    MAX-ACCESS      read-write
    STATUS          current
    DESCRIPTION     
            "Should a CPG arriving before an ACM be transited."
    DEFVAL          { supported }
    ::= { sonusIsupsgSignalingProfileEntry 127 }

sonusIsupServiceGroupMIBNotifications OBJECT IDENTIFIER
    ::= { sonusIsupServiceGroupMIB 2 }

sonusIsupServiceGroupMIBNotificationsPrefix OBJECT IDENTIFIER
    ::= { sonusIsupServiceGroupMIBNotifications 0 }

sonusIsupServiceGroupMIBNotificationsObjects OBJECT IDENTIFIER
    ::= { sonusIsupServiceGroupMIBNotifications 1 }

sonusIsupSvcGrpName OBJECT-TYPE
    SYNTAX          DisplayString (SIZE(0..23))
    MAX-ACCESS      read-only
    STATUS          current
    DESCRIPTION     
            "Name of the ISUP service group."
    ::= { sonusIsupServiceGroupMIBNotificationsObjects 1 }

sonusIsupMaintReason OBJECT-TYPE
    SYNTAX          INTEGER { ss7GwRegistration(1), 
                        remoteSs7PointCodeAccess(2), trunkGroupMode(3), 
                        serviceGroupMode(4), circuitMode(5), ds1Mode(6), 
                        serverMode(7), localHardware(8), 
                        remoteMaintenance(9), remoteHardware(10), 
                        remoteUnequipped(11), ss7GwResynchronization(12) }
    MAX-ACCESS      read-only
    STATUS          current
    DESCRIPTION     
            "Maintenance reason for blocking/unblocking of the circuit."
    ::= { sonusIsupServiceGroupMIBNotificationsObjects 2 }

sonusIsupTrunkGrpName OBJECT-TYPE
    SYNTAX          DisplayString (SIZE(0..23))
    MAX-ACCESS      read-only
    STATUS          current
    DESCRIPTION     
            "Name of the trunk group."
    ::= { sonusIsupServiceGroupMIBNotificationsObjects 3 }

sonusIsupCircuit OBJECT-TYPE
    SYNTAX          Integer32 (0..16383)
    MAX-ACCESS      read-only
    STATUS          current
    DESCRIPTION     
            "Base circuit identity code (CIC) for the circuit."
    ::= { sonusIsupServiceGroupMIBNotificationsObjects 4 }

sonusIsupCircuitOffsets OBJECT-TYPE
    SYNTAX          BITS { cicOffset0(0), cicOffset1(1), cicOffset2(2), 
                        cicOffset3(3), cicOffset4(4), cicOffset5(5), 
                        cicOffset6(6), cicOffset7(7), cicOffset8(8), 
                        cicOffset9(9), cicOffset10(10), cicOffset11(11), 
                        cicOffset12(12), cicOffset13(13), 
                        cicOffset14(14), cicOffset15(15), 
                        cicOffset16(16), cicOffset17(17), 
                        cicOffset18(18), cicOffset19(19), 
                        cicOffset20(20), cicOffset21(21), 
                        cicOffset22(22), cicOffset23(23) }
    MAX-ACCESS      read-only
    STATUS          current
    DESCRIPTION     
            "Circuit maintenance status bitmap for CIC range starting with base CIC."
    ::= { sonusIsupServiceGroupMIBNotificationsObjects 5 }

sonusIsupCalledPartyNumber OBJECT-TYPE
    SYNTAX          DisplayString (SIZE(0..31))
    MAX-ACCESS      read-only
    STATUS          current
    DESCRIPTION     
            "Called Party Number."
    ::= { sonusIsupServiceGroupMIBNotificationsObjects 6 }

sonusIsupCallingPartyNumber OBJECT-TYPE
    SYNTAX          DisplayString (SIZE(0..31))
    MAX-ACCESS      read-only
    STATUS          current
    DESCRIPTION     
            "Calling Party Number."
    ::= { sonusIsupServiceGroupMIBNotificationsObjects 7 }

sonusIsupMaintCode OBJECT-TYPE
    SYNTAX          DisplayString (SIZE(0..31))
    MAX-ACCESS      read-only
    STATUS          current
    DESCRIPTION     
            "Maintainence code."
    ::= { sonusIsupServiceGroupMIBNotificationsObjects 8 }

sonusIsupSvcGrpInServiceNotification NOTIFICATION-TYPE
    OBJECTS         { sonusIsupSvcGrpName, sonusEventDescription, 
                      sonusEventClass, sonusEventLevel }
    STATUS          current
    DESCRIPTION     
            "This trap indicates that the ISUP Service Group was put in service by maintenance staff."
    ::= { sonusIsupServiceGroupMIBNotificationsPrefix 1 }

sonusIsupSvcGrpOutOfServiceNotification NOTIFICATION-TYPE
    OBJECTS         { sonusIsupSvcGrpName, sonusEventDescription, 
                      sonusEventClass, sonusEventLevel }
    STATUS          current
    DESCRIPTION     
            "This trap indicates that the ISUP Service Group was taken out of service by maintenance staff."
    ::= { sonusIsupServiceGroupMIBNotificationsPrefix 2 }

sonusIsupCircuitBlockedNotification NOTIFICATION-TYPE
    OBJECTS         { sonusIsupSvcGrpName, sonusIsupMaintReason, 
                      sonusIsupTrunkGrpName, sonusIsupCircuit, 
                      sonusIsupCircuitOffsets, sonusEventDescription, 
                      sonusEventClass, sonusEventLevel }
    STATUS          current
    DESCRIPTION     
            "This trap indicates that the ISUP Circuit(s) were blocked."
    ::= { sonusIsupServiceGroupMIBNotificationsPrefix 3 }

sonusIsupCircuitUnblockedNotification NOTIFICATION-TYPE
    OBJECTS         { sonusIsupSvcGrpName, sonusIsupMaintReason, 
                      sonusIsupTrunkGrpName, sonusIsupCircuit, 
                      sonusIsupCircuitOffsets, sonusEventDescription, 
                      sonusEventClass, sonusEventLevel }
    STATUS          current
    DESCRIPTION     
            "This trap indicates that the ISUP Circuit(s) were unblocked."
    ::= { sonusIsupServiceGroupMIBNotificationsPrefix 4 }

sonusIsupCircuitResetNotification NOTIFICATION-TYPE
    OBJECTS         { sonusIsupSvcGrpName, sonusIsupTrunkGrpName, 
                      sonusIsupCircuit, sonusIsupCircuitOffsets, 
                      sonusEventDescription, sonusEventClass, 
                      sonusEventLevel }
    STATUS          current
    DESCRIPTION     
            "This trap indicates that the ISUP Circuit(s) were reset."
    ::= { sonusIsupServiceGroupMIBNotificationsPrefix 5 }

sonusIsupContinuityRecheckFailureNotification NOTIFICATION-TYPE
    OBJECTS         { sonusIsupSvcGrpName, sonusIsupCircuit, 
                      sonusEventDescription, sonusEventClass, 
                      sonusEventLevel }
    STATUS          current
    DESCRIPTION     
            "This trap indicates that the Continuity Recheck on the ISUP circuit failed."
    ::= { sonusIsupServiceGroupMIBNotificationsPrefix 6 }

sonusIsupCicRegistrationFailedNotification NOTIFICATION-TYPE
    OBJECTS         { sonusIsupCircuit, sonusEventDescription, 
                      sonusEventClass, sonusEventLevel }
    STATUS          current
    DESCRIPTION     
            "This trap indicates that the CIC Registration failed after multiple retries."
    ::= { sonusIsupServiceGroupMIBNotificationsPrefix 7 }

sonusIsupHopCounterExhaustedNotification NOTIFICATION-TYPE
    OBJECTS         { sonusIsupSvcGrpName, sonusIsupCircuit, 
                      sonusIsupCalledPartyNumber, 
                      sonusIsupCallingPartyNumber, sonusEventDescription, 
                      sonusEventClass, sonusEventLevel }
    STATUS          current
    DESCRIPTION     
            "This trap indicates that the Hop Counter value received in IAM is zero."
    ::= { sonusIsupServiceGroupMIBNotificationsPrefix 8 }

sonusIsupRelWithExchangeRoutingErrorNotification NOTIFICATION-TYPE
    OBJECTS         { sonusIsupSvcGrpName, sonusIsupCircuit, 
                      sonusIsupCalledPartyNumber, 
                      sonusIsupCallingPartyNumber, sonusEventDescription, 
                      sonusEventClass, sonusEventLevel }
    STATUS          current
    DESCRIPTION     
            "This trap indicates that a REL message is received with Exchange Routing Error cause value."
    ::= { sonusIsupServiceGroupMIBNotificationsPrefix 9 }

sonusIsupCqmTimeoutNotification NOTIFICATION-TYPE
    OBJECTS         { sonusIsupCircuit, sonusEventDescription, 
                      sonusEventClass, sonusEventLevel }
    STATUS          current
    DESCRIPTION     
            "This trap indicates that the timed out has occured waiting for CQM response"
    ::= { sonusIsupServiceGroupMIBNotificationsPrefix 10 }

sonusIsupCvtTimeoutNotification NOTIFICATION-TYPE
    OBJECTS         { sonusIsupCircuit, sonusEventDescription, 
                      sonusEventClass, sonusEventLevel }
    STATUS          current
    DESCRIPTION     
            "This trap indicates that the timed out has occured waiting for CVT response"
    ::= { sonusIsupServiceGroupMIBNotificationsPrefix 11 }

sonusIsupFarendCircuitStateMismatchedNotification NOTIFICATION-TYPE
    OBJECTS         { sonusIsupCircuit, sonusEventDescription, 
                      sonusEventClass, sonusEventLevel }
    STATUS          current
    DESCRIPTION     
            "This trap indicates that the circuit/block state is mismatched as report by CQR"
    ::= { sonusIsupServiceGroupMIBNotificationsPrefix 12 }

sonusIsupCircuitTimerExpired NOTIFICATION-TYPE
    OBJECTS         { sonusIsupTrunkGrpName, sonusIsupSvcGrpName, 
                      sonusIsupCircuit, sonusIsupMaintCode, 
                      sonusEventDescription, sonusEventClass, 
                      sonusEventLevel }
    STATUS          current
    DESCRIPTION     
            "This trap indicates that the ISUP Circuit had a timer expire."
    ::= { sonusIsupServiceGroupMIBNotificationsPrefix 13 }

END -- end of module SONUS-ISUP-SERVICE-GROUP-MIB.
