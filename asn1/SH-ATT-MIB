--
-- SNMP MIB for AT&T SMART HUBs  (Release 1.0, 7/17/91)
--

SH-ATT-MIB --{ iso org(3) dod(6) internet(1) private(4) enterprises(1) att(74) }

DEFINITIONS ::= BEGIN

IMPORTS
     OBJECT-TYPE FROM RFC-1212
	  enterprises, IpAddress, Counter, TimeTicks
     FROM RFC1065-SMI
     DisplayString FROM SNMPv2-TC;

att-2				OBJECT IDENTIFIER ::= { enterprises 74 }
att-products			OBJECT IDENTIFIER ::= { att-2 1 }
att-mgmt			OBJECT IDENTIFIER ::= { att-2 2 }
att-hubmgtProd			OBJECT IDENTIFIER ::= { att-products 1 }
att-hubmgt			OBJECT IDENTIFIER ::= { att-mgmt 1 }

sh1BasicCtrlCapability		OBJECT IDENTIFIER ::= { att-hubmgt 1 }
sh1SelfTestCapability		OBJECT IDENTIFIER ::= { att-hubmgt 2 }
sh1PerfMonCapability		OBJECT IDENTIFIER ::= { att-hubmgt 3 }
sh1DownloadCapability		OBJECT IDENTIFIER ::= { att-hubmgt 4 }
sh1AddrTrackCapability		OBJECT IDENTIFIER ::= { att-hubmgt 5 }
sh1EnhancedCtrlCapability	OBJECT IDENTIFIER ::= { att-hubmgt 6 }
sh1SecurityCapability		OBJECT IDENTIFIER ::= { att-hubmgt 7 }


--
-- BASIC CONTROL CAPABILITY GROUP
--

sh1BasicCtrlHubID OBJECT-TYPE
    SYNTAX  OCTET STRING
    ACCESS  read-only
    STATUS  mandatory
    ::= { sh1BasicCtrlCapability 1 }

sh1BasicCtrlHubGroupCapacity OBJECT-TYPE
    SYNTAX  INTEGER
    ACCESS  read-only
    STATUS  mandatory
    ::= { sh1BasicCtrlCapability 2 }

sh1BasicCtrlGroupMap OBJECT-TYPE
    SYNTAX  OCTET STRING
    ACCESS  read-only
    STATUS  mandatory
    ::= { sh1BasicCtrlCapability 3 }

sh1BasicCtrlGroupID OBJECT-TYPE
    SYNTAX  INTEGER
    ACCESS  read-only
    STATUS  mandatory
    ::= { sh1BasicCtrlCapability 4 }

sh1BasicCtrlNumberOfPorts OBJECT-TYPE
    SYNTAX  INTEGER
    ACCESS  read-only
    STATUS  mandatory
    ::= { sh1BasicCtrlCapability 5 }


-- basic control port table

sh1BasicCtrlPortTable OBJECT-TYPE
    SYNTAX  SEQUENCE OF BasicControlPortEntry
    ACCESS  not-accessible
    STATUS  mandatory
    ::= { sh1BasicCtrlCapability 6 }

sh1BasicCtrlPortEntry OBJECT-TYPE
    SYNTAX  BasicControlPortEntry
    ACCESS  not-accessible
    STATUS  mandatory
    INDEX   { sh1BasicCtrlPortID }
    ::= { sh1BasicCtrlPortTable 1 }

BasicControlPortEntry ::= SEQUENCE {
    sh1BasicCtrlPortID
        INTEGER,
    sh1BasicCtrlPortType
        INTEGER,
    sh1BasicCtrlPortCtrl
        INTEGER,
    sh1BasicCtrlAutoPartitionState
        INTEGER
}

sh1BasicCtrlPortID OBJECT-TYPE
    SYNTAX  INTEGER
    ACCESS  read-only
    STATUS  mandatory
    ::= { sh1BasicCtrlPortEntry 1 }

sh1BasicCtrlPortType OBJECT-TYPE
    SYNTAX  INTEGER {
        other(1),           -- not listed here
        repeater(2),        -- 802.3 sec. 9 rptr port
        tenBASE-FAsync(3),  -- async port on 10BASE-FA
        tenBASE-FSynch(4)   -- sync port on 10BASE-FA
    }
    ACCESS  read-only
    STATUS  mandatory
    ::= { sh1BasicCtrlPortEntry 2 }

sh1BasicCtrlPortCtrl OBJECT-TYPE
    SYNTAX  INTEGER {
        other(1),
        disabled(2),
        enabled(3)
    }
    ACCESS  read-write
    STATUS  mandatory
    ::= { sh1BasicCtrlPortEntry 3 }

sh1BasicCtrlAutoPartitionState OBJECT-TYPE
    SYNTAX  INTEGER {
        other(1),
        notAutoPartitioned(2),
        autoPartitioned(3)
    }
    ACCESS  read-only
    STATUS  mandatory
    ::= { sh1BasicCtrlPortEntry 4 }


--
-- SELF-TEST CAPABILITY GROUP
--

sh1SelfTestHubResetTimeStamp OBJECT-TYPE
    SYNTAX  TimeTicks
    ACCESS  read-only
    STATUS  mandatory
    ::= { sh1SelfTestCapability 1 }

sh1SelfTestResetHubSystem OBJECT-TYPE
    SYNTAX  INTEGER {
        reset(1)
    }
    ACCESS  write-only
    STATUS  mandatory
    ::= { sh1SelfTestCapability 2 }

sh1SelfTestResetHub OBJECT-TYPE
    SYNTAX  INTEGER {
        reset(1)
    }
    ACCESS  write-only
    STATUS  mandatory
    ::= { sh1SelfTestCapability 3 }

sh1SelfTestExecuteSelfTest1 OBJECT-TYPE
    SYNTAX  INTEGER {
        performTest(1)
    }
    ACCESS  write-only
    STATUS  mandatory
    ::= { sh1SelfTestCapability 4 }

sh1SelfTestExecuteSelfTest2 OBJECT-TYPE
    SYNTAX  INTEGER {
        performTest(1)
    }
    ACCESS  write-only
    STATUS  mandatory
    ::= { sh1SelfTestCapability 5 }

sh1SelfTestHubHealthState OBJECT-TYPE
    SYNTAX  INTEGER {
        other(1),           -- undefined or unknown
        ok(2),              -- no known failures
        failed(3)           -- known failure condition
    }
    ACCESS  read-only
    STATUS  mandatory
    ::= { sh1SelfTestCapability 6 }

sh1SelfTestHubHealthData OBJECT-TYPE
    SYNTAX  OCTET STRING
    ACCESS  read-only
    STATUS  mandatory
    ::= { sh1SelfTestCapability 7 }


--
-- PERFORMANCE MONITORING CAPABILITY GROUP
--

sh1PerfMonFrameSize1Bound OBJECT-TYPE
    SYNTAX  INTEGER
    ACCESS  read-write
    STATUS  mandatory
    ::= { sh1PerfMonCapability 1 }

sh1PerfMonFrameSize2Bound OBJECT-TYPE
    SYNTAX  INTEGER
    ACCESS  read-write
    STATUS  mandatory
    ::= { sh1PerfMonCapability 2 }

sh1PerfMonFrameSize3Bound OBJECT-TYPE
    SYNTAX  INTEGER
    ACCESS  read-write
    STATUS  mandatory
    ::= { sh1PerfMonCapability 3 }

sh1PerfMonFrameSize4Bound OBJECT-TYPE
    SYNTAX  INTEGER
    ACCESS  read-write
    STATUS  mandatory
    ::= { sh1PerfMonCapability 4 }

sh1PerfMonRelayCounts OBJECT-TYPE
    SYNTAX  OCTET STRING
    ACCESS  read-only
    STATUS  mandatory
    ::= { sh1PerfMonCapability 5 }

sh1PerfMonTotalFramesReceivedOk OBJECT-TYPE
    SYNTAX  Counter
    ACCESS  read-only
    STATUS  mandatory
    ::= { sh1PerfMonCapability 6 }

sh1PerfMonTotalOctetsReceivedOk OBJECT-TYPE
    SYNTAX  Counter
    ACCESS  read-only
    STATUS  mandatory
    ::= { sh1PerfMonCapability 7 }

sh1PerfMonTotalCollisions OBJECT-TYPE
    SYNTAX  Counter
    ACCESS  read-only
    STATUS  mandatory
    ::= { sh1PerfMonCapability 8 }

sh1PerfMonTotalLateCollisions OBJECT-TYPE
    SYNTAX  Counter
    ACCESS  read-only
    STATUS  mandatory
    ::= { sh1PerfMonCapability 9 }

sh1PerfMonTotalRunts OBJECT-TYPE
    SYNTAX  Counter
    ACCESS  read-only
    STATUS  mandatory
    ::= { sh1PerfMonCapability 10 }

sh1PerfMonTotalShortEvents OBJECT-TYPE
    SYNTAX  Counter
    ACCESS  read-only
    STATUS  mandatory
    ::= { sh1PerfMonCapability 11 }

sh1PerfMonTotalFrameTooLongs OBJECT-TYPE
    SYNTAX  Counter
    ACCESS  read-only
    STATUS  mandatory
    ::= { sh1PerfMonCapability 12 }

sh1PerfMonTotalAutoPartitions OBJECT-TYPE
    SYNTAX  Counter
    ACCESS  read-only
    STATUS  mandatory
    ::= { sh1PerfMonCapability 13 }

sh1PerfMonTotalLongFragments OBJECT-TYPE
    SYNTAX  Counter
    ACCESS  read-only
    STATUS  mandatory
    ::= { sh1PerfMonCapability 14 }

sh1PerfMonTotalFifoErrors OBJECT-TYPE
    SYNTAX  Counter
    ACCESS  read-only
    STATUS  mandatory
    ::= { sh1PerfMonCapability 15 }

sh1PerfMonTotalFramesTransmittedOk OBJECT-TYPE
    SYNTAX  Counter
    ACCESS  read-only
    STATUS  mandatory
    ::= { sh1PerfMonCapability 16 }

sh1PerfMonTotalOctetsTransmittedOk OBJECT-TYPE
    SYNTAX  Counter
    ACCESS  read-only
    STATUS  mandatory
    ::= { sh1PerfMonCapability 17 }

sh1PerfMonTotalErrorEnergy OBJECT-TYPE
    SYNTAX  Counter
    ACCESS  read-only
    STATUS  mandatory
    ::= { sh1PerfMonCapability 18 }

sh1PerfMonTotalManchesterCodeViolations OBJECT-TYPE
    SYNTAX  Counter
    ACCESS  read-only
    STATUS  mandatory
    ::= { sh1PerfMonCapability 19 }

sh1PerfMonTotalBand1Frames OBJECT-TYPE
    SYNTAX  Counter
    ACCESS  read-only
    STATUS  mandatory
    ::= { sh1PerfMonCapability 20 }

sh1PerfMonTotalBand2Frames OBJECT-TYPE
    SYNTAX  Counter
    ACCESS  read-only
    STATUS  mandatory
    ::= { sh1PerfMonCapability 21 }

sh1PerfMonTotalBand3Frames OBJECT-TYPE
    SYNTAX  Counter
    ACCESS  read-only
    STATUS  mandatory
    ::= { sh1PerfMonCapability 22 }

sh1PerfMonTotalBand4Frames OBJECT-TYPE
    SYNTAX  Counter
    ACCESS  read-only
    STATUS  mandatory
    ::= { sh1PerfMonCapability 23 }

sh1PerfMonTotalBand5Frames OBJECT-TYPE
    SYNTAX  Counter
    ACCESS  read-only
    STATUS  mandatory
    ::= { sh1PerfMonCapability 24 }


-- Performance Monitoring Port Table

sh1PerfMonPortTable OBJECT-TYPE
    SYNTAX  SEQUENCE OF PerfMonPortEntry
    ACCESS  not-accessible
    STATUS  mandatory
    ::= { sh1PerfMonCapability 25 }

sh1PerfMonPortEntry OBJECT-TYPE
    SYNTAX  PerfMonPortEntry
    ACCESS  not-accessible
    STATUS  mandatory
    INDEX   { sh1PerfMonPortID }
    ::= { sh1PerfMonPortTable 1 }

PerfMonPortEntry ::= SEQUENCE {
    sh1PerfMonPortID
        INTEGER,
    sh1PerfMonPortCounts
        OCTET STRING,
    sh1PerfMonFramesReceivedOk
        Counter,
    sh1PerfMonOctetsReceivedOk
        Counter,
    sh1PerfMonCollisions
        Counter,
    sh1PerfMonLateCollisions
        Counter,
    sh1PerfMonRunts
        Counter,
    sh1PerfMonShortEvents
        Counter,
    sh1PerfMonFrameTooLongs
        Counter,
    sh1PerfMonAutoPartitions
        Counter,
    sh1PerfMonLongFragments
        Counter,
    sh1PerfMonFifoErrors
        Counter,
    sh1PerfMonFramesTransmittedOk
        Counter,
    sh1PerfMonOctetsTransmittedOk
        Counter,
    sh1PerfMonErrorEnergy
        Counter,
    sh1PerfMonManchesterCodeViolations
        Counter,
    sh1PerfMonBand1Frames
        Counter,
    sh1PerfMonBand2Frames
        Counter,
    sh1PerfMonBand3Frames
        Counter,
    sh1PerfMonBand4Frames
        Counter,
    sh1PerfMonBand5Frames
        Counter
}

sh1PerfMonPortID OBJECT-TYPE
    SYNTAX  INTEGER
    ACCESS  read-only
    STATUS  mandatory
    ::= { sh1PerfMonPortEntry 1 }

sh1PerfMonPortCounts OBJECT-TYPE
    SYNTAX  OCTET STRING
    ACCESS  read-only
    STATUS  mandatory
    ::= { sh1PerfMonPortEntry 2 }

sh1PerfMonFramesReceivedOk OBJECT-TYPE
    SYNTAX  Counter
    ACCESS  read-only
    STATUS  mandatory
    ::= { sh1PerfMonPortEntry 3 }

sh1PerfMonOctetsReceivedOk OBJECT-TYPE
    SYNTAX  Counter
    ACCESS  read-only
    STATUS  mandatory
    ::= { sh1PerfMonPortEntry 4 }

sh1PerfMonCollisions OBJECT-TYPE
    SYNTAX  Counter
    ACCESS  read-only
    STATUS  mandatory
    ::= { sh1PerfMonPortEntry 5 }

sh1PerfMonLateCollisions OBJECT-TYPE
    SYNTAX  Counter
    ACCESS  read-only
    STATUS  mandatory
    ::= { sh1PerfMonPortEntry 6 }

sh1PerfMonRunts OBJECT-TYPE
    SYNTAX  Counter
    ACCESS  read-only
    STATUS  mandatory
    ::= { sh1PerfMonPortEntry 7 }

sh1PerfMonShortEvents OBJECT-TYPE
    SYNTAX  Counter
    ACCESS  read-only
    STATUS  mandatory
    ::= { sh1PerfMonPortEntry 8 }

sh1PerfMonFrameTooLongs OBJECT-TYPE
    SYNTAX  Counter
    ACCESS  read-only
    STATUS  mandatory
    ::= { sh1PerfMonPortEntry 9 }

sh1PerfMonAutoPartitions OBJECT-TYPE
    SYNTAX  Counter
    ACCESS  read-only
    STATUS  mandatory
    ::= { sh1PerfMonPortEntry 10 }

sh1PerfMonLongFragments OBJECT-TYPE
    SYNTAX  Counter
    ACCESS  read-only
    STATUS  mandatory
    ::= { sh1PerfMonPortEntry 11 }

sh1PerfMonFifoErrors OBJECT-TYPE
    SYNTAX  Counter
    ACCESS  read-only
    STATUS  mandatory
    ::= { sh1PerfMonPortEntry 12 }

sh1PerfMonFramesTransmittedOk OBJECT-TYPE
    SYNTAX  Counter
    ACCESS  read-only
    STATUS  mandatory
    ::= { sh1PerfMonPortEntry 13 }

sh1PerfMonOctetsTransmittedOk OBJECT-TYPE
    SYNTAX  Counter
    ACCESS  read-only
    STATUS  mandatory
    ::= { sh1PerfMonPortEntry 14 }

sh1PerfMonErrorEnergy OBJECT-TYPE
    SYNTAX  Counter
    ACCESS  read-only
    STATUS  mandatory
    ::= { sh1PerfMonPortEntry 15 }

sh1PerfMonManchesterCodeViolations OBJECT-TYPE
    SYNTAX  Counter
    ACCESS  read-only
    STATUS  mandatory
    ::= { sh1PerfMonPortEntry 16 }

sh1PerfMonBand1Frames OBJECT-TYPE
    SYNTAX  Counter
    ACCESS  read-only
    STATUS  mandatory
    ::= { sh1PerfMonPortEntry 17 }

sh1PerfMonBand2Frames OBJECT-TYPE
    SYNTAX  Counter
    ACCESS  read-only
    STATUS  mandatory
    ::= { sh1PerfMonPortEntry 18 }

sh1PerfMonBand3Frames OBJECT-TYPE
    SYNTAX  Counter
    ACCESS  read-only
    STATUS  mandatory
    ::= { sh1PerfMonPortEntry 19 }

sh1PerfMonBand4Frames OBJECT-TYPE
    SYNTAX  Counter
    ACCESS  read-only
    STATUS  mandatory
    ::= { sh1PerfMonPortEntry 20 }

sh1PerfMonBand5Frames OBJECT-TYPE
    SYNTAX  Counter
    ACCESS  read-only
    STATUS  mandatory
    ::= { sh1PerfMonPortEntry 21 }


--
-- DOWNLOAD CAPABILITY GROUP
--

sh1DownloadImageFile OBJECT-TYPE
    SYNTAX  OCTET STRING
    ACCESS  read-write
    STATUS  mandatory
    ::= { sh1DownloadCapability 1 }

sh1DownloadIpAddress OBJECT-TYPE
    SYNTAX  IpAddress
    ACCESS  read-write
    STATUS  mandatory
    ::= { sh1DownloadCapability 2 }

sh1DownloadMacAddress OBJECT-TYPE
    SYNTAX  OCTET STRING
    ACCESS  read-write
    STATUS  mandatory
    ::= { sh1DownloadCapability 3 }

sh1DownloadExecute OBJECT-TYPE
    SYNTAX  INTEGER {
        performDownload(1)
    }
    ACCESS  read-write
    STATUS  mandatory
    ::= { sh1DownloadCapability 4 }


--
-- ADDRESS TRACKING CAPABILITY GROUP
--

sh1AddrTrackSendHubLearn OBJECT-TYPE
    SYNTAX  INTEGER {
        sendHubLearnFrame(1)
    }
    ACCESS  write-only
    STATUS  mandatory
    ::= { sh1AddrTrackCapability 1 }

sh1AddrTrackPortTable OBJECT-TYPE
    SYNTAX  SEQUENCE OF AddrTrackPortEntry
    ACCESS  not-accessible
    STATUS  mandatory
    ::= { sh1AddrTrackCapability 2 }

sh1AddrTrackPortEntry OBJECT-TYPE
    SYNTAX  AddrTrackPortEntry
    ACCESS  not-accessible
    STATUS  mandatory
    INDEX   { sh1AddrTrackPortID }
    ::= { sh1AddrTrackPortTable 1 }

AddrTrackPortEntry ::= SEQUENCE {
    sh1AddrTrackPortID
        INTEGER,
    sh1AddrTrackDetectedMacAddr
        OCTET STRING,
    sh1AddrTrackDetectedAddrType
        INTEGER,
    sh1AddrTrackAuthMacAddr
        OCTET STRING,
    sh1AddrTrackAuthAddrType
        INTEGER,
    sh1AddrTrackNewHubAddr
        OCTET STRING
}

sh1AddrTrackPortID OBJECT-TYPE
    SYNTAX  INTEGER
    ACCESS  read-only
    STATUS  mandatory
    ::= { sh1AddrTrackPortEntry 1 }

sh1AddrTrackDetectedMacAddr OBJECT-TYPE
    SYNTAX  OCTET STRING
    ACCESS  read-only
    STATUS  mandatory
    ::= { sh1AddrTrackPortEntry 2 }

sh1AddrTrackDetectedAddrType OBJECT-TYPE
    SYNTAX  INTEGER {
       none(1),
       singleAddress(2),
       hubAddress(3),
       multipleAddresses(4)
    }
    ACCESS  read-only
    STATUS  mandatory
    ::= { sh1AddrTrackPortEntry 3 }

sh1AddrTrackAuthMacAddr OBJECT-TYPE
    SYNTAX  OCTET STRING
    ACCESS  read-write
    STATUS  mandatory
    ::= { sh1AddrTrackPortEntry 4 }

sh1AddrTrackAuthAddrType OBJECT-TYPE
    SYNTAX  INTEGER {
       none(1),
       singleAddress(2),
       hubAddress(3),
       multipleAddresses(4)
    }
    ACCESS  read-write
    STATUS  mandatory
    ::= { sh1AddrTrackPortEntry 5 }

sh1AddrTrackNewHubAddr OBJECT-TYPE
    SYNTAX  OCTET STRING
    ACCESS  not-accessible                -- trap(alarm) only
    STATUS  mandatory
    ::= { sh1AddrTrackPortEntry 6 }



--
-- ENHANCED CONTROL CAPABILITY GROUP
--

sh1EnhCtrlResetFirmwareConfig OBJECT-TYPE
    SYNTAX  INTEGER {
        performReset(1)
    }
    ACCESS  write-only
    STATUS  mandatory
    ::= { sh1EnhancedCtrlCapability 1 }

sh1EnhCtrlHubVersion OBJECT-TYPE
    SYNTAX  OCTET STRING
    ACCESS  read-only
    STATUS  mandatory
    ::= { sh1EnhancedCtrlCapability 2 }

sh1EnhCtrlTrapMacAddr OBJECT-TYPE
    SYNTAX  OCTET STRING
    ACCESS  read-write
    STATUS  mandatory
    ::= { sh1EnhancedCtrlCapability 3 }

sh1EnhCtrlTrapIpAddr OBJECT-TYPE
    SYNTAX  IpAddress
    ACCESS  read-write
    STATUS  mandatory
    ::= { sh1EnhancedCtrlCapability 4 }

sh1EnhCtrlGatewayIpAddr OBJECT-TYPE
    SYNTAX  IpAddress
    ACCESS  read-write
    STATUS  mandatory
    ::= { sh1EnhancedCtrlCapability 5 }

sh1EnhCtrlNetworkMask OBJECT-TYPE
    SYNTAX  IpAddress
    ACCESS  read-write
    STATUS  mandatory
    ::= { sh1EnhancedCtrlCapability 6 }

sh1EnhCtrlHubIpAddr OBJECT-TYPE
    SYNTAX  IpAddress
    ACCESS  read-write
    STATUS  mandatory
    ::= { sh1EnhancedCtrlCapability 7 }

sh1EnhCtrlHubAlias OBJECT-TYPE
    SYNTAX  DisplayString
    ACCESS  read-write
    STATUS  mandatory
    ::= { sh1EnhancedCtrlCapability 8 }

sh1EnhCtrlRs232State OBJECT-TYPE
    SYNTAX  INTEGER {
        dteNotConnected(1),
        dteConnectedNotLoggedIn(2),
        dteConnectedLoggedIn(3)
    }
    ACCESS  read-only
    STATUS  mandatory
    ::= { sh1EnhancedCtrlCapability 9 }

sh1EnhCtrlRs232DataRate OBJECT-TYPE
    SYNTAX  INTEGER {
         bps300(1),
        bps1200(2),
        bps2400(3),
        bps4800(4),
        bps9600(5)
    }
    ACCESS  read-write
    STATUS  mandatory
    ::= { sh1EnhancedCtrlCapability 10 }

sh1EnhCtrlTrapCountPeriodCtrl OBJECT-TYPE
    SYNTAX  INTEGER
    ACCESS  read-write
    STATUS  mandatory
    ::= { sh1EnhancedCtrlCapability 11 }

sh1EnhCtrlTrapCountContentsCtrl OBJECT-TYPE
    SYNTAX  INTEGER {
	other(1),
	minimumContents(2),
	fullContents(3)
    }
    ACCESS  read-write
    STATUS  mandatory
    ::= { sh1EnhancedCtrlCapability 12 }

sh1EnhCtrlSendTrapConfig OBJECT-TYPE
    SYNTAX  INTEGER {
        sendTrapConfig(1)
    }
    ACCESS  write-only
    STATUS  mandatory
    ::= { sh1EnhancedCtrlCapability 13 }

sh1EnhCtrlPortTable  OBJECT-TYPE
    SYNTAX  SEQUENCE OF EnhancedControlPortEntry
    ACCESS  not-accessible
    STATUS  mandatory
    ::= { sh1EnhancedCtrlCapability 14 }

sh1EnhCtrlPortEntry OBJECT-TYPE
    SYNTAX  EnhancedControlPortEntry
    ACCESS  not-accessible
    STATUS  mandatory
    INDEX   { sh1EnhCtrlPortID }
    ::= { sh1EnhCtrlPortTable 1 }

EnhancedControlPortEntry ::= SEQUENCE {
    sh1EnhCtrlPortID
        INTEGER,
    sh1EnhCtrlLinkIntegrityCtrl
        INTEGER,
    sh1EnhCtrlLinkIntegrityAlarmCtrl
        INTEGER,
    sh1EnhCtrlLinkIntegrityState
        INTEGER,
    sh1EnhCtrlExtendedDistanceCtrl
        INTEGER,
    sh1EnhCtrlPortConfig
        OCTET STRING
}

sh1EnhCtrlPortID OBJECT-TYPE
    SYNTAX  INTEGER
    ACCESS  read-only
    STATUS  mandatory
    ::= { sh1EnhCtrlPortEntry 1 }

sh1EnhCtrlLinkIntegrityCtrl OBJECT-TYPE
    SYNTAX  INTEGER {
        other(1),
        disabled(2),
        enabled(3)
    }
    ACCESS  read-write
    STATUS  mandatory
    ::= { sh1EnhCtrlPortEntry 2 }

sh1EnhCtrlLinkIntegrityAlarmCtrl OBJECT-TYPE
    SYNTAX  INTEGER {
        other(1),
        disabled(2),
        enabled(3)
    }
    ACCESS  read-write
    STATUS  mandatory
    ::= { sh1EnhCtrlPortEntry 3 }

sh1EnhCtrlLinkIntegrityState OBJECT-TYPE
    SYNTAX  INTEGER {
       notApplicable(1),
       connected(2),
       failed(3)
    }
    ACCESS  read-only
    STATUS  mandatory
    ::= { sh1EnhCtrlPortEntry 4 }

sh1EnhCtrlExtendedDistanceCtrl OBJECT-TYPE
    SYNTAX  INTEGER {
        other(1),
        disabled(2),
        enabled(3)
    }
    ACCESS  read-write
    STATUS  mandatory
    ::= { sh1EnhCtrlPortEntry 5 }

sh1EnhCtrlPortConfig OBJECT-TYPE
    SYNTAX  OCTET STRING
    ACCESS  read-only
    STATUS  mandatory
    ::= { sh1EnhCtrlPortEntry 6 }


--
-- SECURITY CAPABILITY GROUP
--

sh1SecEavesdroppingCtrl OBJECT-TYPE
    SYNTAX  INTEGER {
        other(1),
        disabled(2),
        enabled(3)
    }
    ACCESS  read-write
    STATUS  mandatory
    ::= { sh1SecurityCapability 1 }

sh1SecIntrusionCtrl OBJECT-TYPE
    SYNTAX  INTEGER {
        other(1),
        disabled(2),
        enabled(3)
    }
    ACCESS  read-write
    STATUS  mandatory
    ::= { sh1SecurityCapability 2 }

sh1SecIntrusionAlarmCtrl OBJECT-TYPE
    SYNTAX  INTEGER {
        other(1),
        disabled(2),
        enabled(3)
    }
    ACCESS  read-write
    STATUS  mandatory
    ::= { sh1SecurityCapability 3 }

sh1SecPassword OBJECT-TYPE
    SYNTAX  OCTET STRING
    ACCESS  write-only
    STATUS  mandatory
    ::= { sh1SecurityCapability 4 }

sh1SecBadPasswords OBJECT-TYPE
    SYNTAX  Counter
    ACCESS  read-only
    STATUS  mandatory
    ::= { sh1SecurityCapability 5 }

sh1SecSettingAdminMacAddr OBJECT-TYPE
    SYNTAX  OCTET STRING
    ACCESS  read-only
    STATUS  mandatory
    ::= { sh1SecurityCapability 6 }

sh1SecSettingAdminIpAddr OBJECT-TYPE
    SYNTAX  IpAddress
    ACCESS  read-only
    STATUS  mandatory
    ::= { sh1SecurityCapability 7 }

sh1SecInbandSetsState OBJECT-TYPE
    SYNTAX  INTEGER {
        other(1),
        disabled(2),
        enabled(3)
    }
    ACCESS  read-only
    STATUS  mandatory
    ::= { sh1SecurityCapability 8 }

sh1SecPortTable  OBJECT-TYPE
    SYNTAX  SEQUENCE OF SecurityPortEntry
    ACCESS  not-accessible
    STATUS  mandatory
    ::= { sh1SecurityCapability 9 }

sh1SecPortEntry OBJECT-TYPE
    SYNTAX  SecurityPortEntry
    ACCESS  not-accessible
    STATUS  mandatory
    INDEX   { sh1SecPortID }
    ::= { sh1SecPortTable 1 }

SecurityPortEntry ::= SEQUENCE {
    sh1SecPortID
        INTEGER,
    sh1SecIntrusionAddr
        OCTET STRING,
    sh1SecIntrusionTimeStamp
        TimeTicks,
    sh1SecIntrusions
        Counter
}

sh1SecPortID OBJECT-TYPE
    SYNTAX  INTEGER
    ACCESS  read-only
    STATUS  mandatory
    ::= { sh1SecPortEntry 1 }

sh1SecIntrusionAddr OBJECT-TYPE
    SYNTAX  OCTET STRING
    ACCESS  read-only
    STATUS  mandatory
    ::= { sh1SecPortEntry 2 }

sh1SecIntrusionTimeStamp OBJECT-TYPE
    SYNTAX  TimeTicks
    ACCESS  read-only
    STATUS  mandatory
    ::= { sh1SecPortEntry 3 }

sh1SecIntrusions OBJECT-TYPE
    SYNTAX  Counter
    ACCESS  read-only
    STATUS  mandatory
    ::= { sh1SecPortEntry 4 }


END
