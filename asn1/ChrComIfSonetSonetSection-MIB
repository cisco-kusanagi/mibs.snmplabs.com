ChrComIfSonetSonetSection-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComIfSonet				FROM  Chromatis-MIB
	ifIndex					FROM  RFC1213-MIB
	TraceType				FROM  SonetTypes-MIB
	EnableDisableType			FROM  SonetTypes-MIB
	DisplayString			FROM  RFC1213-MIB
	SLoopbackType				FROM  SonetTypes-MIB;

-- chrComIfSonetSonetSection Table

chrComIfSonetSonetSectionTable		OBJECT-TYPE
	SYNTAX		SEQUENCE OF ChrComIfSonetSonetSectionEntry
	MAX-ACCESS	not-accessible
	STATUS		current
	DESCRIPTION
	"The Sonet Section private Table"
	::= { chrComIfSonet 4}

chrComIfSonetSonetSectionEntry		OBJECT-TYPE
	SYNTAX		ChrComIfSonetSonetSectionEntry
	MAX-ACCESS	not-accessible
	STATUS		current
	DESCRIPTION
	""
	INDEX  {  ifIndex }

--DEFAULT  get-function-async  MNIL_GetRoutine
--DEFAULT  set-function-async  MNIL_SetRoutine
--DEFAULT  next-function-async MNIL_NextRoutine
--DEFAULT  test-function-async MNIL_TestRoutine
--DEFAULT  cookie "SonetSection"
	::= { chrComIfSonetSonetSectionTable  1 }

ChrComIfSonetSonetSectionEntry  ::=
	SEQUENCE  {
	chrComIfSonetSectionTrace		TraceType,
	chrComIfSonetSectionTraceMatchCheckState EnableDisableType,
	chrComIfSonetTransmittedSectionTraceID DisplayString	(SIZE (0..64)),
	chrComIfSonetExpectedSectionTrace	DisplayString	(SIZE (0..64)),
	chrComIfSonetReceivedSectionTrace	DisplayString	(SIZE (0..64)),
	chrComIfSonetSectionLoopback		SLoopbackType,
	chrComIfSonetAlarmVector		Integer32	(0..65535),
	chrComIfSonetAlarmSeverityIndex	Unsigned32	(0..4294967295)
}

chrComIfSonetSectionTrace 	OBJECT-TYPE
	SYNTAX		TraceType
	MAX-ACCESS 	read-write
	STATUS 		current
	DESCRIPTION
	"Enables Selection of how Trace ID should be coded: whether a string of 16 bytes or 64 bytes"
	::= { chrComIfSonetSonetSectionEntry  1 }

chrComIfSonetSectionTraceMatchCheckState 	OBJECT-TYPE
	SYNTAX		EnableDisableType
	MAX-ACCESS 	read-write
	STATUS 		current
	DESCRIPTION
	"The field is used for enabling/disabling the section trace match check"
	::= { chrComIfSonetSonetSectionEntry  2 }

chrComIfSonetTransmittedSectionTraceID 	OBJECT-TYPE
	SYNTAX		DisplayString	(SIZE (0..64))
	MAX-ACCESS 	read-write
	STATUS 		current
	DESCRIPTION
	"This parameter defines the transmitted section trace ID"
	::= { chrComIfSonetSonetSectionEntry  3 }

chrComIfSonetExpectedSectionTrace 	OBJECT-TYPE
	SYNTAX		DisplayString	(SIZE (0..64))
	MAX-ACCESS 	read-write
	STATUS 		current
	DESCRIPTION
	"This parameter defined the expected section trace"
	::= { chrComIfSonetSonetSectionEntry  4 }

chrComIfSonetReceivedSectionTrace 	OBJECT-TYPE
	SYNTAX		DisplayString	(SIZE (0..64))
	MAX-ACCESS 	read-only
	STATUS 		current
	DESCRIPTION
	"The actually received section trace ID"
	::= { chrComIfSonetSonetSectionEntry  5 }

chrComIfSonetSectionLoopback 	OBJECT-TYPE
	SYNTAX		SLoopbackType
	MAX-ACCESS 	read-write
	STATUS 		current
	DESCRIPTION
	""
	::= { chrComIfSonetSonetSectionEntry  6 }

chrComIfSonetAlarmVector 	OBJECT-TYPE
	SYNTAX		Integer32	(0..65535)
	MAX-ACCESS 	read-only
	STATUS 		current
	DESCRIPTION
	"16 bit field.  the Sonet Section Alarm Vector field. "
	::= { chrComIfSonetSonetSectionEntry  7 }

chrComIfSonetAlarmSeverityIndex 	OBJECT-TYPE
	SYNTAX		Unsigned32	(0..4294967295)
	MAX-ACCESS 	read-write
	STATUS 		current
	DESCRIPTION
	""
	::= { chrComIfSonetSonetSectionEntry  8 }


END
