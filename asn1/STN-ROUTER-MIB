-- *****************************************************************
--
-- STN-ROUTER.mib:  
--      Spring Tide Networks Router MIB file.
--
--
--      Copyright (c) 1999, 2000 by Spring Tide Networks, Inc.
--                      ALL RIGHTS RESERVED       
--
-- *****************************************************************

-- MIB Object definitions for Spring Tide Network Virtual Routers


STN-ROUTER-MIB DEFINITIONS ::= BEGIN

    IMPORTS
        MODULE-IDENTITY,
        OBJECT-TYPE, 
        NOTIFICATION-TYPE, 
        IpAddress,
        Integer32,
        Unsigned32,
        TimeTicks
                FROM SNMPv2-SMI

        TEXTUAL-CONVENTION,
        DisplayString
                FROM SNMPv2-TC

        MODULE-COMPLIANCE
                FROM SNMPv2-CONF

        InterfaceIndex
                FROM IF-MIB

        stnSystems,
        stnNotification
                FROM SPRING-TIDE-NETWORKS-SMI

        stnEngineIndex, 
        stnEngineSlot,
        stnEngineCpu
                FROM STN-CHASSIS-MIB;


    stnRouter       MODULE-IDENTITY
        LAST-UPDATED    "0002160000Z"
        ORGANIZATION    "Spring Tide Networks, Inc."
        CONTACT-INFO
                "
                Spring Tide Networks, Inc.
                Customer Service
                Postal: 3 Clock Tower Place
                        Maynard, MA 01754
                Tel:    1 888-786-4357
                Email:  stncs@springtidenet.com
                "
        DESCRIPTION     "This MIB module describes managed objects of
                         Spring Tide Networks virtual routers plus associated
                         IP, PPP, and PPPOE interfaces."
        ::= { stnSystems 7 }


    --
    -- Top Level STN Router MIB Objects
    --
    stnRouterObjects        OBJECT IDENTIFIER ::= { stnRouter 1 }
    stnRouterMibConformance OBJECT IDENTIFIER ::= { stnRouter 2 }


    --
    -- Low Level STN Router MIB Objects
    --
    stnRouterNAT	    OBJECT IDENTIFIER ::= { stnRouterObjects 5 }
    stnRouterVEI	    OBJECT IDENTIFIER ::= { stnRouterObjects 6 }
    stnRouterAtmVpn	    OBJECT IDENTIFIER ::= { stnRouterObjects 7 }
    stnRouterVimuxMpls	OBJECT IDENTIFIER ::= { stnRouterObjects 8 }
    stnRouterVTI	    OBJECT IDENTIFIER ::= { stnRouterObjects 9 }

    
    InterfaceConnectionType ::= TEXTUAL-CONVENTION
        STATUS    current
        DESCRIPTION
                  "The type of an interface."
        SYNTAX    INTEGER { 
                            customer(1),                
                            provider(2),
                            ppp(4),
                            pppoe(5),
                            home(6)
                            }

    OperationState ::= TEXTUAL-CONVENTION  
        STATUS    current
        DESCRIPTION
                  "Operational states of a router or an interface."   
        SYNTAX    INTEGER { 
                            unassigned(1),
                            bufpend(2),         
                            assignpend(3),
                            assigned(4),
                            unassignbufpend(5),
                            unassignpend(6),
                            failedassign(7),
                            error(8)
                            }


    -- STN Router Table

    stnRouterTable OBJECT-TYPE
        SYNTAX        SEQUENCE OF StnRouterEntry
        MAX-ACCESS    not-accessible
        STATUS        current
        DESCRIPTION   "A list of router entries."
        ::= { stnRouterObjects 1 }
 
    stnRouterEntry OBJECT-TYPE
        SYNTAX          StnRouterEntry
        MAX-ACCESS      not-accessible
        STATUS          current
        DESCRIPTION     "Entry contains information about a particular 
                         router."
        INDEX           { stnRouterIndex }
        ::= { stnRouterTable 1 }
 
    StnRouterEntry ::= SEQUENCE {
                stnRouterIndex              Integer32,
                stnRouterType               INTEGER,
                stnRouterState              OperationState,
                stnRouterEngineID           Integer32,
                stnRouterHomeIpAddress      IpAddress,
                stnRouterEnabled            INTEGER,
                stnRouterName               DisplayString,
                stnRouterUpTime             TimeTicks,
                stnRouterActiveSlot         Integer32,
                stnRouterActiveCpu          Integer32,
                stnRouterConfiguredSlot     Integer32,
                stnRouterConfiguredCpu      Integer32,
                stnRouterStandbySlot        Integer32,
                stnRouterStandbyCpu         Integer32,
                stnRouterReassignOnFault    INTEGER,
                stnRouterServiceName        DisplayString,
                stnRouterServiceDomain      Integer32,
                stnRouterDefaultPolicyAction INTEGER
                }

    stnRouterIndex OBJECT-TYPE
        SYNTAX          Integer32
        MAX-ACCESS      read-only
        STATUS          current
        DESCRIPTION     "A sequence number that identifies a router
                        entry in the table."
        ::= { stnRouterEntry 1 }

    stnRouterType OBJECT-TYPE     
        SYNTAX          INTEGER { 
                                customer(1),            
                                provider(2),
                                admin(3)
                                }
        MAX-ACCESS      read-only
        STATUS          current
        DESCRIPTION     "The router type."
        ::= { stnRouterEntry  2 }

    stnRouterState OBJECT-TYPE
        SYNTAX          OperationState
        MAX-ACCESS      read-only
        STATUS          current
        DESCRIPTION     "The operational state of the router."
        ::= { stnRouterEntry  3 }

    stnRouterEngineID OBJECT-TYPE
        SYNTAX          Integer32
        MAX-ACCESS      read-only
        STATUS          current
        DESCRIPTION     "The engine to which this router is
                         currently assigned."
        ::= { stnRouterEntry  4 }

    stnRouterHomeIpAddress OBJECT-TYPE
        SYNTAX          IpAddress
        MAX-ACCESS      read-only
        STATUS          current
        DESCRIPTION     "The Home IP address of this router."
        ::= { stnRouterEntry  5 }

    stnRouterEnabled OBJECT-TYPE
        SYNTAX          INTEGER { 
                                enabled(1),             
                                disabled(2)
                                }
        MAX-ACCESS      read-only
        STATUS          current
        DESCRIPTION     "The variable to indicate if this router is enabled."
        ::= { stnRouterEntry  6 }

    stnRouterName OBJECT-TYPE
        SYNTAX          DisplayString (SIZE(1..32))
        MAX-ACCESS      read-only
        STATUS          current
        DESCRIPTION     "The name of this router."
        ::= { stnRouterEntry  7 }

    stnRouterUpTime OBJECT-TYPE
        SYNTAX          TimeTicks
        MAX-ACCESS      read-only
        STATUS          current
        DESCRIPTION     "The time (in hundredths of a second) since the
                         router was last re-initialized."
      ::= { stnRouterEntry  8 }

    stnRouterActiveSlot OBJECT-TYPE
        SYNTAX          Integer32
        MAX-ACCESS      read-only
        STATUS          current
        DESCRIPTION     "The slot/module to which this router is
                         currently assigned."
        ::= { stnRouterEntry  9 }

    stnRouterActiveCpu OBJECT-TYPE
        SYNTAX          Integer32
        MAX-ACCESS      read-only
        STATUS          current
        DESCRIPTION     "The CPU to which this router is
                         currently assigned."
        ::= { stnRouterEntry  10 }

    stnRouterConfiguredSlot OBJECT-TYPE
        SYNTAX          Integer32
        MAX-ACCESS      read-only
        STATUS          current
        DESCRIPTION     "The configured slot/module for this router."
        ::= { stnRouterEntry  11 }

    stnRouterConfiguredCpu OBJECT-TYPE
        SYNTAX          Integer32
        MAX-ACCESS      read-only
        STATUS          current
        DESCRIPTION     "The configured CPU for this router."
        ::= { stnRouterEntry  12 }

    stnRouterStandbySlot OBJECT-TYPE
        SYNTAX          Integer32
        MAX-ACCESS      read-only
        STATUS          current
        DESCRIPTION     "The standby slot/module for this router."
        ::= { stnRouterEntry  13 }

    stnRouterStandbyCpu OBJECT-TYPE
        SYNTAX          Integer32
        MAX-ACCESS      read-only
        STATUS          current
        DESCRIPTION     "The standby CPU for this router."
        ::= { stnRouterEntry  14 }

    stnRouterReassignOnFault OBJECT-TYPE
        SYNTAX          INTEGER { 
                                enabled(1),             
                                disabled(2)
                                }
        MAX-ACCESS      read-only
        STATUS          current
        DESCRIPTION     "The variable to indicate if this router should be
                         reassigned if the module where to fail."
        ::= { stnRouterEntry  15 }

    stnRouterServiceName OBJECT-TYPE
        SYNTAX          DisplayString (SIZE(1..64))
        MAX-ACCESS      read-only
        STATUS          current
        DESCRIPTION     "The service to which this router belongs."
        ::= { stnRouterEntry  16 }

    stnRouterServiceDomain OBJECT-TYPE
        SYNTAX          Integer32
        MAX-ACCESS      read-only
        STATUS          current
        DESCRIPTION     "The service domain to which this router belongs."
        ::= { stnRouterEntry  17 }

    stnRouterDefaultPolicyAction OBJECT-TYPE
        SYNTAX          INTEGER { 
                                deny(1),             
                                permit(2)
                                }
        MAX-ACCESS      read-only
        STATUS          current
        DESCRIPTION     "Action to take when a packet does not match
                         any policies."
        ::= { stnRouterEntry  18 }


    -- STN sub-network interface table

    stnSubnetInterfaceTable OBJECT-TYPE
        SYNTAX        SEQUENCE OF StnSubnetInterfaceEntry
        MAX-ACCESS    not-accessible
        STATUS        current
        DESCRIPTION   "A list of sub-network interface entries."
        ::= { stnRouterObjects 2 }
 
    stnSubnetInterfaceEntry OBJECT-TYPE
        SYNTAX          StnSubnetInterfaceEntry
        MAX-ACCESS      not-accessible
        STATUS          current
        DESCRIPTION     "Entry contains information about a particular 
                         sub-network interface."
        INDEX           { stnSubnetInterfaceIndex }
        ::= { stnSubnetInterfaceTable 1 } 
 
    StnSubnetInterfaceEntry ::= SEQUENCE {
                stnSubnetInterfaceIndex         Unsigned32,
                stnSubnetInterfaceEnabled       INTEGER,  
                stnSubnetInterfaceAddress       IpAddress,
                stnSubnetInterfaceMask          IpAddress,
                stnSubnetInterfaceVclid         Integer32,
                stnSubnetInterfaceType          InterfaceConnectionType,
                stnSubnetInterfaceState         OperationState,
                stnSubnetInterfaceRouterIndex   Integer32,
                stnSubnetInterfaceLinkType      INTEGER,
                stnSubnetInterfaceLinkInstance  Integer32,
                stnSubnetInterfaceForcedNextHop IpAddress,
                stnSubnetInterfaceServiceName   DisplayString
                }

    stnSubnetInterfaceIndex OBJECT-TYPE
        SYNTAX          Unsigned32
        MAX-ACCESS      read-only
        STATUS          current
        DESCRIPTION     "A sequence number that identifies a sub-network
                         interface entry in the table."
        ::= { stnSubnetInterfaceEntry 1 }

    stnSubnetInterfaceEnabled OBJECT-TYPE     
        SYNTAX          INTEGER { 
                                enabled(1),             
                                disabled(2)
                                }
        MAX-ACCESS      read-only
        STATUS          current
        DESCRIPTION     "Enable or disable the sub-network interface."
        ::= { stnSubnetInterfaceEntry  2 }

    stnSubnetInterfaceAddress OBJECT-TYPE     
        SYNTAX          IpAddress 
        MAX-ACCESS      read-only
        STATUS          current
        DESCRIPTION     "The IP address of this interface."
        ::= { stnSubnetInterfaceEntry  3 }

    stnSubnetInterfaceMask OBJECT-TYPE     
        SYNTAX          IpAddress 
        MAX-ACCESS      read-only
        STATUS          current
        DESCRIPTION     "The sub-network mask of this interface."
        ::= { stnSubnetInterfaceEntry  4 }

    stnSubnetInterfaceVclid OBJECT-TYPE
        SYNTAX          Integer32
        MAX-ACCESS      read-only
        STATUS          deprecated
        DESCRIPTION     "The vcl ID associated with this sub-network interface."
        ::= { stnSubnetInterfaceEntry 5 }

    stnSubnetInterfaceType OBJECT-TYPE     
        SYNTAX          InterfaceConnectionType
        MAX-ACCESS      read-only
        STATUS          current
        DESCRIPTION     "The interface type."
        ::= { stnSubnetInterfaceEntry  6 }

    stnSubnetInterfaceState OBJECT-TYPE     
        SYNTAX          OperationState 
        MAX-ACCESS      read-only
        STATUS          current
        DESCRIPTION     "The operational state of the sub-network interface."
        ::= { stnSubnetInterfaceEntry  7 }

    stnSubnetInterfaceRouterIndex OBJECT-TYPE     
        SYNTAX          Integer32 
        MAX-ACCESS      read-only
        STATUS          current
        DESCRIPTION     "The router this sub-network interface
                         is associated with."
        ::= { stnSubnetInterfaceEntry  8 }

    stnSubnetInterfaceLinkType OBJECT-TYPE
        SYNTAX          INTEGER {
                            vcLink(1),
                            vei(2),
                            home(3)
                        }
        MAX-ACCESS      read-only
        STATUS          current
        DESCRIPTION     "Indicates the type of link the subnet interface
                        is configured over."
        ::= { stnSubnetInterfaceEntry 9 }

    stnSubnetInterfaceLinkInstance OBJECT-TYPE
        SYNTAX          Integer32
        MAX-ACCESS      read-only
        STATUS          current
        DESCRIPTION     "The instance of the configuration record for the 
                        link the subnet interface is configured over."
        ::= { stnSubnetInterfaceEntry 10 }

    stnSubnetInterfaceForcedNextHop OBJECT-TYPE     
        SYNTAX          IpAddress 
        MAX-ACCESS      read-only
        STATUS          current
        DESCRIPTION     "The IP address of the next hop router that all IP 
                         traffic received on this interface will be sent to"
        ::= { stnSubnetInterfaceEntry  11 }

    stnSubnetInterfaceServiceName OBJECT-TYPE
        SYNTAX          DisplayString (SIZE(1..64))
        MAX-ACCESS      read-only
        STATUS          current
        DESCRIPTION     "The service to which this interface belongs."
        ::= { stnSubnetInterfaceEntry  12 }


    -- STN PPPOE Table

    stnPppoeTable OBJECT-TYPE
        SYNTAX        SEQUENCE OF StnPppoeEntry
        MAX-ACCESS    not-accessible
        STATUS        current
        DESCRIPTION   "A list of PPPOE interface entries."
        ::= { stnRouterObjects 3 }
 
    stnPppoeEntry OBJECT-TYPE
        SYNTAX          StnPppoeEntry
        MAX-ACCESS      not-accessible
        STATUS          current
        DESCRIPTION     "Entry contains information about a particular 
                         PPPOE interface."
        INDEX           { stnPppoeIndex }
        ::= { stnPppoeTable 1 }
 
    StnPppoeEntry ::= SEQUENCE {
                stnPppoeIndex           Integer32,
                stnPppoeType            InterfaceConnectionType,
                stnPppoeState           OperationState,
                stnPppoeVclid           Integer32,
                stnPppoeIfIndex         InterfaceIndex,
                stnPppoeRouterIndex     Integer32, 
                stnPppoeLinkType        INTEGER,
                stnPppoeLinkInstance    Integer32                 
                }

    stnPppoeIndex OBJECT-TYPE
        SYNTAX          Integer32
        MAX-ACCESS      read-only
        STATUS          current
        DESCRIPTION     "A sequence number that identifies a PPPOE
                         interface entry in the table."
        ::= { stnPppoeEntry 1 }

    stnPppoeType OBJECT-TYPE
        SYNTAX          InterfaceConnectionType
        MAX-ACCESS      read-only
        STATUS          current
        DESCRIPTION     "The interface type."
        ::= { stnPppoeEntry 2 }

    stnPppoeState OBJECT-TYPE
        SYNTAX          OperationState
        MAX-ACCESS      read-only
        STATUS          current
        DESCRIPTION     "The operational state of the PPPOE interface."
        ::= { stnPppoeEntry 3 }

    stnPppoeVclid OBJECT-TYPE
        SYNTAX          Integer32
        MAX-ACCESS      read-only
        STATUS          deprecated
        DESCRIPTION     "The vcl ID associated with this PPPOE interface."
        ::= { stnPppoeEntry 4 }

    stnPppoeIfIndex OBJECT-TYPE
        SYNTAX          InterfaceIndex
        MAX-ACCESS      read-only
        STATUS          current
        DESCRIPTION     "The ifindex."
        ::= { stnPppoeEntry 5 }

    stnPppoeRouterIndex OBJECT-TYPE
        SYNTAX          Integer32
        MAX-ACCESS      read-only
        STATUS          current
        DESCRIPTION     "The router this PPPOE interface is associated
                         with."
        ::= { stnPppoeEntry 6 }

    stnPppoeLinkType OBJECT-TYPE
        SYNTAX          INTEGER {
                            vcLink(1),
                            vei(2)
                        }
        MAX-ACCESS      read-only
        STATUS          current
        DESCRIPTION     "Indicates the type of link the PPPoE interface
                        is configured over."
        ::= { stnPppoeEntry 7 }

    stnPppoeLinkInstance OBJECT-TYPE
        SYNTAX          Integer32
        MAX-ACCESS      read-only
        STATUS          current
        DESCRIPTION     "The instance of the configuration record for the 
                        link the PPPoE interface is configured over."
        ::= { stnPppoeEntry 8 }


    -- STN PPP Table

    stnPppTable OBJECT-TYPE
        SYNTAX        SEQUENCE OF StnPppEntry
        MAX-ACCESS    not-accessible
        STATUS        current
        DESCRIPTION   "A list of PPP interface entries."
        ::= { stnRouterObjects 4 }
 
    stnPppEntry OBJECT-TYPE
        SYNTAX          StnPppEntry
        MAX-ACCESS      not-accessible
        STATUS          current
        DESCRIPTION     "Entry contains information about a particular 
                        session."
        INDEX           { stnPppIndex }
        ::= { stnPppTable 1 }
 
    StnPppEntry ::= SEQUENCE {
                stnPppIndex        Integer32,
                stnPppType         InterfaceConnectionType,
                stnPppState        OperationState,
                stnPppVclid        Integer32,
                stnPppIfIndex      InterfaceIndex,
                stnPppRouterIndex  Integer32    
                }

    stnPppIndex OBJECT-TYPE
        SYNTAX          Integer32
        MAX-ACCESS      read-only
        STATUS          current
        DESCRIPTION     "A sequence number that identifies a PPP
                         interface entry in the table."
        ::= { stnPppEntry 1 }

    stnPppType OBJECT-TYPE
        SYNTAX          InterfaceConnectionType
        MAX-ACCESS      read-only
        STATUS          current
        DESCRIPTION     "The interface type."
        ::= { stnPppEntry 2 }

    stnPppState OBJECT-TYPE
        SYNTAX          OperationState 
        MAX-ACCESS      read-only
        STATUS          current
        DESCRIPTION     "The operational state or the PPP interface."
        ::= { stnPppEntry 3 }

    stnPppVclid OBJECT-TYPE
        SYNTAX          Integer32
        MAX-ACCESS      read-only
        STATUS          current
        DESCRIPTION     "The vcl ID associated with this PPP interface."
        ::= { stnPppEntry 4 }

    stnPppIfIndex OBJECT-TYPE
        SYNTAX          InterfaceIndex
        MAX-ACCESS      read-only
        STATUS          current
        DESCRIPTION     "The ifindex."
        ::= { stnPppEntry 5 }

    stnPppRouterIndex OBJECT-TYPE
        SYNTAX          Integer32
        MAX-ACCESS      read-only
        STATUS          current
        DESCRIPTION     "The router this PPP interface is associated
                         with."
        ::= { stnPppEntry 6 }

    
    --
    -- STN Traps & Notifications 
    --
    stnRouterUp NOTIFICATION-TYPE
        OBJECTS         { stnRouterIndex, stnRouterState, 
                          stnRouterName,  stnEngineIndex, 
                          stnEngineSlot,  stnEngineCpu }
        STATUS          current
        DESCRIPTION     "A stnRouterUp trap signifies that the agent 
                        entity has detected that the stnRouterState 
                        object in the STN-ROUTER-MIB has transitioned to the 
                        assigned(4) state for one of its routers.
                        The generation of this trap can be controlled by the
                        RouterUpTraps configuration object."
        ::= { stnNotification 26 }

    stnRouterDown NOTIFICATION-TYPE
        OBJECTS         { stnRouterIndex, stnRouterState, 
                          stnRouterName,  stnEngineIndex, 
                          stnEngineSlot,  stnEngineCpu }
        STATUS          current
        DESCRIPTION     "A stnRouterDown trap signifies that the agent 
                        entity has detected that the stnRouterState 
                        object in the STN-ROUTER-MIB has transitioned to the  
                        failedassign(7) or error(8) state for one of its 
                        routers.
                        The generation of this trap can be controlled by the
                        RouterDownTraps configuration object."
        ::= { stnNotification 27 }

    stnRouterReassigned NOTIFICATION-TYPE
        OBJECTS         { stnRouterIndex, stnRouterState, 
                          stnRouterName,  stnEngineIndex, 
                          stnEngineSlot,  stnEngineCpu }
        STATUS          current
        DESCRIPTION     "A stnRouterReassigned trap signifies that the agent 
                        entity has detected that the stnRouterState 
                        object in the STN-ROUTER-MIB has transitioned to the  
                        the assigned(1) state for one of its routers.
                        The generation of this trap can be controlled by the
                        RouterReassignedTraps configuration object."
        ::= { stnNotification 28 }

    stnRouterReassignFailure NOTIFICATION-TYPE
        OBJECTS         { stnRouterIndex, stnRouterState, 
                          stnRouterName,  stnEngineIndex, 
                          stnEngineSlot,  stnEngineCpu }
        STATUS          current
        DESCRIPTION     "A stnRouterReassignFailure trap signifies that the 
                        agent entity has detected that the stnRouterState 
                        object in the STN-ROUTER-MIB has transitioned to the  
                        failedassign(7) or error(8) state for one of its 
                        routers.
                        The generation of this trap can be controlled by the
                        RouterReassignFailureTraps configuration object."
        ::= { stnNotification 29 }

    stnSubnetIfAssignFailure NOTIFICATION-TYPE
        OBJECTS         { stnSubnetInterfaceIndex,
                          stnSubnetInterfaceAddress, 
                          stnSubnetInterfaceVclid,
                          stnSubnetInterfaceState,
                          stnSubnetInterfaceRouterIndex,
                          stnSubnetInterfaceLinkType,
                          stnSubnetInterfaceLinkInstance }
        STATUS          current
        DESCRIPTION     "A stnSubnetIfAssignFailure trap signifies that the 
                        agent entity has detected that the 
                        stnSubnetInterfaceState object in the STN-ROUTER-MIB 
                        has transitioned to the failedassign(7) or error(8) 
                        state for one of its interfaces.
                        The generation of this trap can be controlled by the
                        stnEnableSubnetInterfaceTraps configuration object."
        ::= { stnNotification 30 }

    stnConfigAuditRouterFailure NOTIFICATION-TYPE
        OBJECTS         { stnEngineIndex,   stnEngineSlot,
                          stnEngineCpu,     stnRouterIndex }
        STATUS          current
        DESCRIPTION     "A stnConfigAuditRouterFailure trap signifies that the 
                        agent entity has detected an inconsistency between
                        an active and configured routers after a failover.
                        The generation of this trap can be controlled by the
                        CfgAuditRouterTraps configuration object."
        ::= { stnNotification 33 }

    stnConfigAuditSubnetIfFailure NOTIFICATION-TYPE
        OBJECTS         { stnEngineIndex,   stnEngineSlot, 
                          stnEngineCpu,     stnSubnetInterfaceIndex }
        STATUS          current
        DESCRIPTION     "A stnConfigAuditSubnetIfFailure trap signifies that 
                        agent entity has detected an inconsistency between
                        an active and configured subnet interface after a 
                        failover.
                        The generation of this trap can be controlled by the
                        CfgAuditSubnetIfTraps configuration object."
        ::= { stnNotification 34 }

    stnConfigAuditPppoeIfFailure NOTIFICATION-TYPE
        OBJECTS         { stnEngineIndex,   stnEngineSlot, 
                          stnEngineCpu,     stnPppoeRouterIndex }
        STATUS          current
        DESCRIPTION     "A stnConfigAuditPppoeIfFailure trap signifies that 
                        agent entity has detected an inconsistency between
                        an active and configured PPPOE interface after a 
                        failover.
                        The generation of this trap can be controlled by the
                        CfgAuditPppoeIfTraps configuration object."
        ::= { stnNotification 35 }

    stnConfigAuditPppIfFailure NOTIFICATION-TYPE
        OBJECTS         { stnEngineIndex,   stnEngineSlot, 
                          stnEngineCpu,     stnPppRouterIndex }
        STATUS          current
        DESCRIPTION     "A stnConfigAuditPppIfFailure trap signifies that 
                        agent entity has detected an inconsistency between
                        an active and configured PPP interface after a 
                        failover.
                        The generation of this trap can be controlled by the
                        CfgAuditPppIfTraps configuration object."
        ::= { stnNotification 36 }

    --
    -- Conformance Information
    --

END
