--
-- HUAWEI-L2VPN-OAM-MIB.mib
--

--  ==================================================================
-- Copyright (C) 2013 by  HUAWEI TECHNOLOGIES. All rights reserved.
-- 
-- Description: HUAWEI L2VPN OAM TRAP Management MIB
-- Reference:
-- Version:     V1.0
-- History:
--              V1.0 yueyongliang, 2011-04-21, publish
-- ==================================================================

    HUAWEI-L2VPN-OAM-MIB DEFINITIONS ::= BEGIN
 
        IMPORTS
            hwDatacomm            
                FROM HUAWEI-MIB            
            HWL2VpnVcEncapsType            
                FROM HUAWEI-VPLS-EXT-MIB            
            ifName, InterfaceIndexOrZero            
                FROM IF-MIB                                                                
            OBJECT-GROUP, MODULE-COMPLIANCE, NOTIFICATION-GROUP			
                FROM SNMPv2-CONF
            IpAddress, Unsigned32,
            OBJECT-TYPE, MODULE-IDENTITY, NOTIFICATION-TYPE            
                FROM SNMPv2-SMI;        
    
    
        -- 1.3.6.1.4.1.2011.5.25.119.9
    hwL2vpnOamTrap MODULE-IDENTITY 
        LAST-UPDATED "201309051400Z"        -- Sep 05, 2013 at 14:00 GMT
        ORGANIZATION 
            "Huawei Technologies Co.,Ltd."
        CONTACT-INFO 
            "Huawei Industrial Base
              Bantian, Longgang
               Shenzhen 518129
               People's Republic of China
               Website: http://www.huawei.com
               Email: support@huawei.com
             "
        DESCRIPTION 
            "The HUAWEI-L2VPN-OAM-MIB contains objects to
            manage OAM TRAP."
        
        -- Revision history
        REVISION "201309051400Z"
    	DESCRIPTION 
            "V2.03, modify import error."
        REVISION "201305131330Z"
    	DESCRIPTION 
            "V2.02, add hwL2vpnOamFdi, hwL2vpnOamFdiClear for PTN5900."
        REVISION "201303251452Z"
    	DESCRIPTION 
            "V2.01, add hwL2vpnOamSd1Far, hwL2vpnOamSd1FarClear, hwL2vpnOamSd2Far, hwL2vpnOamSd2FarClear for far-end packet loss."
        
       ::= { hwL2Vpn 9 }
                    
    
--
-- Node definitions
--
    
--  Node definitions
-- 
        -- 1.3.6.1.4.1.2011.5.25.119
        hwL2Vpn OBJECT IDENTIFIER ::= { hwDatacomm 119 }

        
--           
-- The OAM TRAP Attribute Group
-- 
        -- 1.3.6.1.4.1.2011.5.25.119.9.1
        hwL2vpnOamTrapMIBObjects OBJECT IDENTIFIER ::= { hwL2vpnOamTrap 1 }
        
--           
-- The PW Info
-- 
        -- 1.3.6.1.4.1.2011.5.25.119.9.1.1
        hwL2vpnServiceType OBJECT-TYPE
            SYNTAX INTEGER
                {
                vpwsPw(0),
                vplsPw(1)
                }
            MAX-ACCESS accessible-for-notify
            STATUS current
            DESCRIPTION
                "This object indicates the classification(vpws or vpls) of the PW."
            ::= { hwL2vpnOamTrapMIBObjects 1 }

        
        -- 1.3.6.1.4.1.2011.5.25.119.9.1.2
        hwL2vpnProtocolType OBJECT-TYPE
            SYNTAX INTEGER
                {
                static(0),
                ldp(1),
                bgp(2)
                }
            MAX-ACCESS accessible-for-notify
            STATUS current
            DESCRIPTION
                "This object indicates the protocol(static or ldp or bgp) of one PW's classification."
            ::= { hwL2vpnOamTrapMIBObjects 2 }

        
        -- 1.3.6.1.4.1.2011.5.25.119.9.1.3
        hwL2vpnVcID OBJECT-TYPE
            SYNTAX Unsigned32
            MAX-ACCESS accessible-for-notify
            STATUS current
            DESCRIPTION
                "This object indicates the ID of the PW.
                This object should contain a value of zero if not valid."
            ::= { hwL2vpnOamTrapMIBObjects 3 }

        
        -- 1.3.6.1.4.1.2011.5.25.119.9.1.4
        hwL2vpnVcType OBJECT-TYPE
            SYNTAX HWL2VpnVcEncapsType
            MAX-ACCESS accessible-for-notify
            STATUS current
            DESCRIPTION
                "This object indicates the type of the PW.
                This object should contain a value of zero if not valid."
            ::= { hwL2vpnOamTrapMIBObjects 4 }

        
        -- 1.3.6.1.4.1.2011.5.25.119.9.1.5
        hwL2vpnPeerAddr OBJECT-TYPE
            SYNTAX IpAddress    
            MAX-ACCESS accessible-for-notify
            STATUS current
            DESCRIPTION
                "This object contain the value of the peer node address 
                of the PW/PE maintenance protocol entity. This object  
                should contain a value of all zeroes if not applicable"
            ::= { hwL2vpnOamTrapMIBObjects 5 }

        
        -- 1.3.6.1.4.1.2011.5.25.119.9.1.6
        hwL2vpnIfIndex OBJECT-TYPE
            SYNTAX InterfaceIndexOrZero
            MAX-ACCESS accessible-for-notify
            STATUS current
            DESCRIPTION
                "This object indicates the index of the AC interface. 
                 This object should contain a value of zero if not valid."
            ::= { hwL2vpnOamTrapMIBObjects 6 }

        
        -- 1.3.6.1.4.1.2011.5.25.119.9.1.7
        hwL2vpnPwMaster OBJECT-TYPE
            SYNTAX INTEGER
                {
                primary(1),
                second(2)
                }
            MAX-ACCESS accessible-for-notify
            STATUS current
            DESCRIPTION
                "This object indicates the role (primary or second) of the PW.
                 This object should contain a value of zero if not valid."
            ::= { hwL2vpnOamTrapMIBObjects 7 }

        
        -- 1.3.6.1.4.1.2011.5.25.119.9.1.8
        hwL2vpnRmtSiteID OBJECT-TYPE
            SYNTAX Unsigned32
            MAX-ACCESS accessible-for-notify
            STATUS current
            DESCRIPTION
                "This object indicates the Route Distinguisher.
                 This object should contain a value of zero if not valid."
            ::= { hwL2vpnOamTrapMIBObjects 8 }

        
        -- 1.3.6.1.4.1.2011.5.25.119.9.1.9
        hwL2vpnInLabel OBJECT-TYPE
            SYNTAX Unsigned32
            MAX-ACCESS accessible-for-notify
            STATUS current
            DESCRIPTION
                "This object indicates the received label be used in PW.
                 This object should contain a value of zero if not valid."
            ::= { hwL2vpnOamTrapMIBObjects 9 }

        
        -- 1.3.6.1.4.1.2011.5.25.119.9.1.10
        hwL2vpnOutLabel OBJECT-TYPE
            SYNTAX Unsigned32
            MAX-ACCESS accessible-for-notify
            STATUS current
            DESCRIPTION
                "This object indicates the transfer label be used in pw.
                 This object should contain a value of zero if not valid."
            ::= { hwL2vpnOamTrapMIBObjects 10 }

        
        -- 1.3.6.1.4.1.2011.5.25.119.9.1.11
        hwL2vpnIfName OBJECT-TYPE
            SYNTAX OCTET STRING
            MAX-ACCESS accessible-for-notify
            STATUS current
            DESCRIPTION
                "This object indicates the AC interface's name.
                 This object should contain a value of null if not valid."
            ::= { hwL2vpnOamTrapMIBObjects 11 }

        
        -- 1.3.6.1.4.1.2011.5.25.119.9.1.12
        hwL2vpnVsiName OBJECT-TYPE
            SYNTAX OCTET STRING
            MAX-ACCESS accessible-for-notify
            STATUS current
            DESCRIPTION
                "This object indicates the the vsi's name.
                 This object should contain a value of null if not valid."
            ::= { hwL2vpnOamTrapMIBObjects 12 }


--           
-- L2VPN OAM Trap Definitions
-- 

        -- 1.3.6.1.4.1.2011.5.25.119.9.2
        hwL2vpnOamMIBTraps OBJECT IDENTIFIER ::= { hwL2vpnOamTrap 2 }
      
      
        -- 1.3.6.1.4.1.2011.5.25.119.9.2.1
        hwL2vpnOamDloc NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported an alarm about PW disconnection."
            ::= { hwL2vpnOamMIBTraps 1 }

        
        -- 1.3.6.1.4.1.2011.5.25.119.9.2.2
        hwL2vpnOamDlocClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported the clearing of the dLOC alarm."
            ::= { hwL2vpnOamMIBTraps 2 }
                            
        
        -- 1.3.6.1.4.1.2011.5.25.119.9.2.3
        hwL2vpnOamSd1Near NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported an alarm about the near-end packet loss exceeding sd1."
            ::= { hwL2vpnOamMIBTraps 3 }

        
        -- 1.3.6.1.4.1.2011.5.25.119.9.2.4
        hwL2vpnOamSd1NearClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported an alarm about the near-end packet loss dropping below sd1."
            ::= { hwL2vpnOamMIBTraps 4 }
        
        
        -- 1.3.6.1.4.1.2011.5.25.119.9.2.5
        hwL2vpnOamRdi NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported an alarm about a remote defect."
            ::= { hwL2vpnOamMIBTraps 5 }

        
        -- 1.3.6.1.4.1.2011.5.25.119.9.2.6
        hwL2vpnOamRdiClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported an alarm about the removal of the remote defect."
            ::= { hwL2vpnOamMIBTraps 6 }

        
        -- 1.3.6.1.4.1.2011.5.25.119.9.2.7
        hwL2vpnOamMeg NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported an unexpected MEG alarm."
            ::= { hwL2vpnOamMIBTraps 7 }

        
        -- 1.3.6.1.4.1.2011.5.25.119.9.2.8
        hwL2vpnOamMegClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported the clearing of the unexpected MEG alarm"
            ::= { hwL2vpnOamMIBTraps 8 }

        
        -- 1.3.6.1.4.1.2011.5.25.119.9.2.9
        hwL2vpnOamMep NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported an unexpected MEP alarm."
            ::= { hwL2vpnOamMIBTraps 9 }

        
        -- 1.3.6.1.4.1.2011.5.25.119.9.2.10
        hwL2vpnOamMepClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported an alarm about the clearing of the unexpected MEP alarm."
            ::= { hwL2vpnOamMIBTraps 10 }

        
        -- 1.3.6.1.4.1.2011.5.25.119.9.2.11
        hwL2vpnOamPeriod NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported an alarm about an unexpected CV packet period."
            ::= { hwL2vpnOamMIBTraps 11 }

        
        -- 1.3.6.1.4.1.2011.5.25.119.9.2.12
        hwL2vpnOamPeriodClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported an alarm about the rectification of the unexpected CV packet period."
            ::= { hwL2vpnOamMIBTraps 12 }

        
        -- 1.3.6.1.4.1.2011.5.25.119.9.2.13
        hwL2vpnOamAis NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported an AIS alarm."
            ::= { hwL2vpnOamMIBTraps 13 }

        
        -- 1.3.6.1.4.1.2011.5.25.119.9.2.14
        hwL2vpnOamAisClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported the clearing of the AIS alarm."
            ::= { hwL2vpnOamMIBTraps 14 }

        
        -- 1.3.6.1.4.1.2011.5.25.119.9.2.15
        hwL2vpnOamSd2Near NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported an alarm about the near-end packet loss exceeding sd2."
            ::= { hwL2vpnOamMIBTraps 15 }

        
        -- 1.3.6.1.4.1.2011.5.25.119.9.2.16
        hwL2vpnOamSd2NearClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported an alarm indicating the near-end packet loss dropping below sd2."
            ::= { hwL2vpnOamMIBTraps 16 }

        
        -- 1.3.6.1.4.1.2011.5.25.119.9.2.17
        hwL2vpnOamLck NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported a PW service layers LCK alarm."
            ::= { hwL2vpnOamMIBTraps 17 }

        
        -- 1.3.6.1.4.1.2011.5.25.119.9.2.18
        hwL2vpnOamLckClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported the PW service layers LCK alarm disappearance."
            ::= { hwL2vpnOamMIBTraps 18 }

        
        -- 1.3.6.1.4.1.2011.5.25.119.9.2.19
        hwL2vpnOamCsf NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported a CSF alarm."
            ::= { hwL2vpnOamMIBTraps 19 }

        
        -- 1.3.6.1.4.1.2011.5.25.119.9.2.20
        hwL2vpnOamCsfClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported the CSF alarm disappearance."
            ::= { hwL2vpnOamMIBTraps 20 }        


        -- 1.3.6.1.4.1.2011.5.25.119.9.2.21
        hwL2vpnOamExcess NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported a TTSI excess alarm."
            ::= { hwL2vpnOamMIBTraps 21 }

        -- 1.3.6.1.4.1.2011.5.25.119.9.2.22
        hwL2vpnOamExcessClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported the TTSI excess alarm disappearance."
            ::= { hwL2vpnOamMIBTraps 22 }

        -- 1.3.6.1.4.1.2011.5.25.119.9.2.23
        hwL2vpnOamMismatch NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported a TTSI mismatch alarm."
            ::= { hwL2vpnOamMIBTraps 23 }


        -- 1.3.6.1.4.1.2011.5.25.119.9.2.24
        hwL2vpnOamMismatchClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported the TTSI mismatch alarm disappearance."
            ::= { hwL2vpnOamMIBTraps 24 }

        -- 1.3.6.1.4.1.2011.5.25.119.9.2.25
        hwL2vpnOamMismerge NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported a TTSI mismerge alarm."
            ::= { hwL2vpnOamMIBTraps 25 }


        -- 1.3.6.1.4.1.2011.5.25.119.9.2.26
        hwL2vpnOamMismergeClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported the TTSI mismerge alarm disappearance."
            ::= { hwL2vpnOamMIBTraps 26 }

        -- 1.3.6.1.4.1.2011.5.25.119.9.2.27
        hwL2vpnOamFail NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported a failed-negotiation alarm."
            ::= { hwL2vpnOamMIBTraps 27 }


        -- 1.3.6.1.4.1.2011.5.25.119.9.2.28
        hwL2vpnOamFailClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported the failed-negotiation alarm disappearance."
            ::= { hwL2vpnOamMIBTraps 28 }

        -- 1.3.6.1.4.1.2011.5.25.119.9.2.29
        hwL2vpnOamDbdi NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported a DBDI alarm."
            ::= { hwL2vpnOamMIBTraps 29 }


        -- 1.3.6.1.4.1.2011.5.25.119.9.2.30
        hwL2vpnOamDbdiClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported the DBDI alarm disappearance."
            ::= { hwL2vpnOamMIBTraps 30 }
                        
        -- 1.3.6.1.4.1.2011.5.25.119.9.2.31
        hwL2vpnOamUnknown NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported an unknown limitation alarm."
            ::= { hwL2vpnOamMIBTraps 31 }


        -- 1.3.6.1.4.1.2011.5.25.119.9.2.32
        hwL2vpnOamUnknownClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported the unknown limitation alarm disappearance."
            ::= { hwL2vpnOamMIBTraps 32 }

        -- 1.3.6.1.4.1.2011.5.25.119.9.2.33
        hwL2vpnOamLocalLock NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported a local PW LOCK alarm."
            ::= { hwL2vpnOamMIBTraps 33 }
        
        -- 1.3.6.1.4.1.2011.5.25.119.9.2.34
        hwL2vpnOamLocalLockClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported the local LOCK PW alarm disappearance."
            ::= { hwL2vpnOamMIBTraps 34 }
            
        -- 1.3.6.1.4.1.2011.5.25.119.9.2.35
        hwL2vpnOamSd1Far NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported an alarm about the far-end packet loss exceeding sd1."
            ::= { hwL2vpnOamMIBTraps 35 }
      
        -- 1.3.6.1.4.1.2011.5.25.119.9.2.36
        hwL2vpnOamSd1FarClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported an alarm indicating the far-end packet loss dropping below sd1."
            ::= { hwL2vpnOamMIBTraps 36 }
       
        -- 1.3.6.1.4.1.2011.5.25.119.9.2.37
        hwL2vpnOamSd2Far NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported an alarm about the far-end packet loss exceeding sd2."
            ::= { hwL2vpnOamMIBTraps 37 }
        
        -- 1.3.6.1.4.1.2011.5.25.119.9.2.38
        hwL2vpnOamSd2FarClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported an alarm indicating the far-end packet loss dropping below sd2."
            ::= { hwL2vpnOamMIBTraps 38 }

        -- 1.3.6.1.4.1.2011.5.25.119.9.2.39
        hwL2vpnOamFdi NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported a FDI alarm."
            ::= { hwL2vpnOamMIBTraps 39 }
        
        -- 1.3.6.1.4.1.2011.5.25.119.9.2.40
        hwL2vpnOamFdiClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported the FDI alarm disappearance."
            ::= { hwL2vpnOamMIBTraps 40 }

--    Conformance information
-- 
		-- 1.3.6.1.4.1.2011.5.25.119.9.3
		hwL2vpnOamConformance OBJECT IDENTIFIER ::= { hwL2vpnOamTrap 3 }

		
		-- 1.3.6.1.4.1.2011.5.25.119.9.3.1
		hwL2vpnOamMIBCompliances OBJECT IDENTIFIER ::= { hwL2vpnOamConformance 1 }
		
		
		-- 1.3.6.1.4.1.2011.5.25.119.9.3.1.1
		hwL2vpnOamMIBCompliance MODULE-COMPLIANCE
			STATUS current
			DESCRIPTION 
				"The compliance statement for systems supporting the HUAWEI-L2VPN-OAM-MIB."
			MODULE -- this module
				MANDATORY-GROUPS { hwL2vpnOamGroup, hwL2vpnOamNotificationGroup }
			::= { hwL2vpnOamMIBCompliances 1 }
			
							
		-- 1.3.6.1.4.1.2011.5.25.119.9.3.2
		hwL2vpnOamGroups OBJECT IDENTIFIER ::= { hwL2vpnOamConformance 2 }

		
		-- 1.3.6.1.4.1.2011.5.25.119.9.3.2.1
		hwL2vpnOamGroup OBJECT-GROUP
			OBJECTS { hwL2vpnServiceType, hwL2vpnProtocolType, hwL2vpnVcID, hwL2vpnVcType, hwL2vpnPeerAddr, 
                                  hwL2vpnIfIndex, hwL2vpnPwMaster, hwL2vpnRmtSiteID, hwL2vpnInLabel, hwL2vpnOutLabel, 
                                  hwL2vpnIfName, hwL2vpnVsiName }
			STATUS current
			DESCRIPTION 
				"The L2VPN OAM group."
			::= { hwL2vpnOamGroups 1 }
										
												
		-- 1.3.6.1.4.1.2011.5.25.119.9.3.2.2
		hwL2vpnOamNotificationGroup NOTIFICATION-GROUP
			NOTIFICATIONS { hwL2vpnOamDloc, hwL2vpnOamDlocClear, hwL2vpnOamSd1Near, hwL2vpnOamSd1NearClear,  
			                hwL2vpnOamRdi, hwL2vpnOamRdiClear, hwL2vpnOamMeg, hwL2vpnOamMegClear, 
			                hwL2vpnOamMep, hwL2vpnOamMepClear , hwL2vpnOamPeriod, hwL2vpnOamPeriodClear, 
			                hwL2vpnOamAis, hwL2vpnOamAisClear, hwL2vpnOamSd2Near, hwL2vpnOamSd2NearClear, 
			                hwL2vpnOamLck, hwL2vpnOamLckClear, hwL2vpnOamCsf, hwL2vpnOamCsfClear, 
			                hwL2vpnOamExcess, hwL2vpnOamExcessClear, hwL2vpnOamMismatch, hwL2vpnOamMismatchClear,
				        hwL2vpnOamMismerge, hwL2vpnOamMismergeClear, hwL2vpnOamFail, hwL2vpnOamFailClear,
				        hwL2vpnOamDbdi, hwL2vpnOamDbdiClear, hwL2vpnOamUnknown, hwL2vpnOamUnknownClear,
				        hwL2vpnOamLocalLock, hwL2vpnOamLocalLockClear, hwL2vpnOamSd1Far, hwL2vpnOamSd1FarClear, hwL2vpnOamSd2Far, hwL2vpnOamSd2FarClear, hwL2vpnOamFdi, hwL2vpnOamFdiClear }
			STATUS current
			DESCRIPTION 
				"The L2VPN OAM Notification group."
			::= { hwL2vpnOamGroups 2 }			
			
    END

--
-- HUAWEI-L2VPN-OAM-MIB.mib
--
