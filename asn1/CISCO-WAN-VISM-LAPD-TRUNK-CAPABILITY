-- *****************************************************************
-- ciscoWanVismLapdTrunkCapabilities MIB
--
-- AGENT-CAPABILITIES mib for CISCO-WAN-LAPD-TRUNK-MIB in the VISM product
--
-- Copyright(c) 2001 by Cisco Systems,Inc.
--
-- Author: Sai Ganesamoorthi
-- *****************************************************************

CISCO-WAN-VISM-LAPD-TRUNK-CAPABILITY DEFINITIONS ::= BEGIN

IMPORTS
        MODULE-IDENTITY,
        Integer32
                FROM SNMPv2-SMI
        AGENT-CAPABILITIES
                FROM SNMPv2-CONF
        ciscoWanAgentCapability
                FROM CISCOWAN-SMI;

cwVismLapdTrunkCapability MODULE-IDENTITY
        LAST-UPDATED    "200108220000Z"
        ORGANIZATION    "Cisco Systems, Inc."
        CONTACT-INFO
                "       Cisco Systems
                        Customer Service

                Postal: 170 W Tasman Drive
                        San Jose, CA  95134
                        USA

                        Tel: +1 800 553-NETS

                E-mail: cs-vism@cisco.com"
        DESCRIPTION
                "The Agent Capabilities for CISCO-WAN-LAPD-TRUNK-MIB."

        REVISION        "200103150000Z"
        DESCRIPTION
                "Initial version of this MIB module"
        ::= { ciscoWanAgentCapability 336 }

cwVismLapdTrunkCapabilityV2R00 AGENT-CAPABILITIES
    PRODUCT-RELEASE      "VISM Release2.2"
    STATUS               current
    DESCRIPTION          "CISCO-WAN-LAPD-TRUNK-MIB Capabilities"

    SUPPORTS CISCO-WAN-LAPD-TRUNK-MIB
    INCLUDES { vismLapdTrunkGroup }

        VARIATION   vismLapdTrunkNum
        SYNTAX      Integer32 (1..8)
        DESCRIPTION "Valid range is 1 - 8."

        VARIATION   vismLapdTrunkRudpIndex
        SYNTAX      Integer32 (1..64)
        DESCRIPTION "Valid range is 1 - 64."

        VARIATION   vismLapdTrunkRowStatus
        SYNTAX INTEGER {
                       active(1),
                       createAndGo(4), 
                       destroy(6)
                       }
        DESCRIPTION "only supports active, createAndGo and Destroy"

    ::= { cwVismLapdTrunkCapability  1 }

END
