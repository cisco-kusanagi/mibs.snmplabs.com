ERI-DNX-OCTAL-T1E1-MIB DEFINITIONS ::= BEGIN

IMPORTS
	MODULE-IDENTITY, OBJECT-IDENTITY, OBJECT-TYPE, Integer32,
	IpAddress, NOTIFICATION-TYPE
		FROM SNMPv2-SMI
    DisplayString
        FROM SNMPv2-TC
    eriMibs
        FROM ERI-ROOT-SMI
    devices, PortStatus, DecisionType, DataSwitch, 
    FunctionSwitch, LinkPortAddress, LinkCmdStatus, trapSequence, 
    OneByteField
        FROM ERI-DNX-SMC-MIB;

eriDNXOctalT1E1MIB MODULE-IDENTITY 
      LAST-UPDATED    "200203080000Z"
      ORGANIZATION    "Eastern Research, Inc."
      CONTACT-INFO
                      "Customer Service
                Postal: Eastern Research, Inc.
                        225 Executive Drive
                        Moorestown, NJ 08057
                Phone:  +1-800-337-4374
                Email:  support@erinc.com"
      DESCRIPTION
              "The ERI Enterprise MIB Module for the DNX T1/E1 ports."

  	::= { eriMibs 2 }

-- *************************************************************************
-- The enterprise OID will be { iso(1) org(3) dod(6) internet(1) private(4)
--                              enterprises(1) virent(644) eri(2) dnx (4) 
--                              devices(2), dnxOT1E1(4) }

-- *************************************************************************
-- The Octal T1/E1 card is currently controlled via the Config or Diag groups.
-- The Configuration branch is used to perform all T1/E1 Link Configuration 
-- functions and the Diagnostic branch is used to run Link tests and view 
-- associated Link Statistics. 
-- *************************************************************************

dnxOT1E1    OBJECT IDENTIFIER   ::= { devices 4}
oteConfig   OBJECT IDENTIFIER 	::= { dnxOT1E1 1 }
oteDiag     OBJECT IDENTIFIER 	::= { dnxOT1E1 2 }

-- *************************************************************************
-- This table is the Octal T1/E1 configuration table
-- *************************************************************************

oT1E1ConfigTable OBJECT-TYPE
        SYNTAX SEQUENCE OF OT1E1ConfigEntry
        MAX-ACCESS not-accessible
        STATUS current
        DESCRIPTION
            "This is the Octal T1/E1 Configuration table which consists
            of an entry for each of the Octal T1/E1 card's 8 links(ports).
            The total number of entries depends on the number of Octal T1/E1 
            cards in the nest. Changes to the Link Configuration must be made
            on a record or row by row basis.  This means that any use of the 
            Set command on writable fields must include the oT1E1CfgCmdStatus
            field with a value of 'update' as the last variable in the SET PDU."
        ::= { oteConfig 1 }

oT1E1ConfigEntry OBJECT-TYPE
        SYNTAX OT1E1ConfigEntry
        MAX-ACCESS not-accessible
        STATUS current
        DESCRIPTION
            "The conceptual row of the Octal T1/E1 Configuration table. 
            A row in this table cannot be added or deleted, only modified
            using the oT1E1CfgCmdStatus field with a value of 'update' as 
            the last variable in the SET PDU. The oT1E1CfgCmdStatus field must
            be included as the last variable in a SET PDU for the action to 
            take effect. If the oT1E1CfgCmdStatus is missing from the SET PDU, 
            the GET RESPONSE will contain the SNMP error status of 'genErr' for 
            and an error index equal to the last variable."
        INDEX { oT1E1CfgLinkAddr }
        ::= { oT1E1ConfigTable 1 }

OT1E1ConfigEntry ::=
        SEQUENCE {
                oT1E1CfgLinkAddr    LinkPortAddress,   -- RO
                oT1E1CfgResource    Integer32,         -- RO
                oT1E1CfgLinkName    DisplayString,
                oT1E1Status         PortStatus,
                oT1E1ClearT1E1      INTEGER,                
                oT1E1LineType       INTEGER,
                oT1E1NetLoop        FunctionSwitch,
                oT1E1YelAlrm        DecisionType,
                oT1E1RecoverTime    INTEGER,
                oT1E1IdleCode       INTEGER,
                oT1E1EsfFormat      INTEGER,
                oT1E1CfgLBO         INTEGER,
                oT1E1CfgCmdStatus   LinkCmdStatus,
                oT1E1Gr303Facility  DecisionType,     -- obsolete
                oT1E1NationalBits   OneByteField,
                oT1E1InterNational  OneByteField
                }

oT1E1CfgLinkAddr OBJECT-TYPE
        SYNTAX LinkPortAddress
        MAX-ACCESS read-only
        STATUS current
        DESCRIPTION
           "This number uniquely identifies an Octal T1/E1 link resource. 
           This number will be used throughout the system to identify 
           a unique link. The format is represented using an IP address 
           syntax (4 byte string). Note that the maximum valid port 
           number will vary depending on the specified carrier and framing 
           options. For example, an octal T1/E1 device has 8 ports but the 
           DS3 has 28 ports.
            
               The 1st byte is reserved for future Nest Number use
               The 2nd byte represents the Slot Number (1-11)            
               The 3rd byte represents the Port Number (1-32)
               The 4th byte is reserved for future use           
           "
        ::= { oT1E1ConfigEntry 1 }

oT1E1CfgResource OBJECT-TYPE
        SYNTAX Integer32
        MAX-ACCESS read-only
        STATUS current
        DESCRIPTION
                "Uniquely identifies an Octal T1/E1 link in the system.
                 This number is provided as key to allow the manager to 
                 map this entry to a corresponding Resource Table entry."
        ::= { oT1E1ConfigEntry 2 }

oT1E1CfgLinkName OBJECT-TYPE
        SYNTAX DisplayString (SIZE(0..20))
        MAX-ACCESS read-write
        STATUS current
        DESCRIPTION
        	"This is the user friendly text name to identify the link."
        ::= { oT1E1ConfigEntry 3 }

oT1E1Status OBJECT-TYPE
        SYNTAX PortStatus
        MAX-ACCESS read-write
        STATUS current
        DESCRIPTION
           "Dictates the current status of the port, in-service or 
           out-of-service."
        ::= { oT1E1ConfigEntry 4 }

oT1E1ClearT1E1 OBJECT-TYPE
        SYNTAX INTEGER {
        	disabled (0),
        	framed   (1),
        	unframed (2)
        	}
        MAX-ACCESS read-write
        STATUS current
        DESCRIPTION
           "Determines if the port supports T1 or E1 unframed."
        ::= { oT1E1ConfigEntry 5 }

oT1E1LineType OBJECT-TYPE
        SYNTAX INTEGER {
        	e1 (0),
        	e1-crc (1),
        	e1-cas (2),
        	e1-cas-crc (3),
        	e1-unframed (4),
        	t1-esf-b8zs(5),
        	t1-esf-ami-62411 (6),
        	t1-d4-b8zs (7),
        	t1-d4-ami-62411 (8),
        	t1-b8zs-unframed (10),
        	t1-ami-unframed (11),
        	t1-d4-ami-clear (12),
        	t1-esf-ami-clear (13)
        	}
        MAX-ACCESS read-write
        STATUS current
        DESCRIPTION
           "Determines the type of framing used on the line.  Choose between 
           E1 (Europeon) or T1 type framing options. When value of oT1E1ClearT1E1
           is set to unframed (2), the only valid framing options are:
               e1-unframed (5)
               t1-b8zs-unframed (10)
               t1-ami-unframed (11)
           "
        ::= { oT1E1ConfigEntry 6 }

oT1E1NetLoop OBJECT-TYPE
        SYNTAX FunctionSwitch
        MAX-ACCESS read-write
        STATUS current
        DESCRIPTION
           "Determines whether or not the module should respond to loop 
           diagnostic commands received from the network supplier. Select 
           'enable' unless the commands are to be passed to another T1/E1 
           device."
        ::= { oT1E1ConfigEntry 7 }


oT1E1YelAlrm OBJECT-TYPE
        SYNTAX DecisionType
        MAX-ACCESS read-write
        STATUS current
        DESCRIPTION
           "Causes the module to discard data and send a yellow alarm if it
           is in a red alarm condition after the set recover time period. 
           'Yes' must be chosen if the network supplier is a common carrier, 
           such as a telephone company."
        ::= { oT1E1ConfigEntry 8 }

oT1E1RecoverTime OBJECT-TYPE
        SYNTAX INTEGER {
        	timeout-3-secs (3),
        	timeout-10-secs(10),
        	timeout-15-secs(15)
        	}
        MAX-ACCESS read-write
        STATUS current
        DESCRIPTION
           "This is the red alarm timeout value.  Determines the amount 
           of seconds the port will wait to stop sending the yellow alarm 
           when coming out of a red alarm condition. This field does not
           apply to E1 links."
        ::= { oT1E1ConfigEntry 9 }

oT1E1IdleCode OBJECT-TYPE
        SYNTAX INTEGER {
        	busy (0),
        	idle (1)
        	}
        MAX-ACCESS read-write
        STATUS current
        DESCRIPTION
           "Determines the whether the data that will be transmitted over 
           the unused Ds0s will be 'idle' or 'busy' (all 1's)."
        ::= { oT1E1ConfigEntry 10 }

oT1E1EsfFormat OBJECT-TYPE
        SYNTAX INTEGER {
            none (0),
        	att-54016 (1),
        	ansi-t1-403 (2)
        	}
        MAX-ACCESS read-write
        STATUS current
        DESCRIPTION
           "Determines the type of ESF network commands the T-1 link 
           will respond to. It has no meaning for D4 networks. With ESF 
           networks, this information must be obtained from the network 
           supplier. ESF does not apply to E1 links."
        ::= { oT1E1ConfigEntry 11 }

oT1E1CfgLBO OBJECT-TYPE
        SYNTAX INTEGER {
        	e1-shortHaul-0-6db (1),
        	e1-longHaul-0-34db (2),
        	t1-longHaul-0-0db (3),
        	t1-longHaul-7-5db (4),
        	t1-longHaul-15-0db (5),
        	t1-longHaul-22-5db (6),
        	t1-shortHaul-0-133ft (7),
        	t1-shortHaul-133-266ft (8),
        	t1-shortHaul-266-399ft (9),
        	t1-shortHaul-399-533ft (10),
        	t1-shortHaul-533-655ft (11)
        	}
        MAX-ACCESS read-write
        STATUS current
        DESCRIPTION
           "Determines the type of Line Build Out (LBO) used on the link.  
           Choose between short haul or long haul designations but this varies 
           between T1 & E1. E1 LBO is defined by authentication of signal 
           presented to receiving circuitry while T1 LBO can be defined by 
           cable length or signal.
           	
           	e1-shortHaul-0-6db		(1) 0 to -6 decibel loss
        	e1-longHaul-0-34db		(2) 0 to -34 decibel loss
        	
        	t1-longHaul-0-0db 		(3) 0.0 decibel loss
        	t1-longHaul-7-5db 		(4) 0.0 to -7.5 decibel loss
        	t1-longHaul-15-0db 		(5) 0.0 to -15.0 decibel loss
        	t1-longHaul-22-5db 		(6) 0.0 to -22.5 decibel loss
        	
        	t1-shortHaul-0-133ft   	(7) 0 to 133 feet of cable
        	t1-shortHaul-133-266ft 	(8)	133 to 266 feet of cable
        	t1-shortHaul-266-399ft 	(9) 266 to 399 feet of cable
        	t1-shortHaul-399-533ft 	(10) 399 to 533 feet of cable
        	t1-shortHaul-533-655ft 	(11) 533 to 655 feet of cable"
        ::= { oT1E1ConfigEntry 12 }

oT1E1CfgCmdStatus OBJECT-TYPE
        SYNTAX LinkCmdStatus
        MAX-ACCESS read-write
        STATUS current
        DESCRIPTION
           "The command status for this link configuration row/record.
           The value used in a SET will be replaced by a response
           value in the GET RESPONSE indicating success or failure.
           		
            Default Response State used in GET RESPONSE Command
                ready-for-command (0)
                    initial default status for a row           
                    
            T1/E1 Link Commands used in SET Command (1..99)            
                update-link-config(1)
                    Change existing Link Configuration
                inServiceAll (7)
                    Change Link Status to in-service for all 8 links.
                copyToAll (9)
                    Copy T1 Link configuration to all other links 
                    within the same device
                outOfServiceAll (12)
                    Change Link Status to out-of-service for all 8 links.
               		
            Response States used in GET RESPONSE Command (100..199)
                update-successful (101)
                    Link data has been successfully changed
                insvc-successful (107)
                    All Links have been successfully placed In Service
                copy-successful (109)
                    T1 Link data has been successfully copied to other links
                oos-successful (112)
                    All Links have been successfully placed Out of Service
               		
            T1/E1 Link Config Error Codes used in GET RESPONSE Command (200..699)
                err-general-link-config-error (400)
                    Unknown link configuration error occurred                
                err-invalid-link-status (401)
                    Unrecognized link status setting
                err-invalid-link-framing (402)         
                    Line framing type not valid for link type
                err-invalid-link-command (403)
                    Unrecognized link command-action
                err-invalid-link-lbo (404)
                    Line Build Out option not valid for link type 
                err-invalid-esf-format (405)
                    ESF type not applicable to link type
                err-invalid-network-loop (410)
                    Unrecognized network loop setting
                err-invalid-yellow-alrm (411)
                    Unrecognized yellow alarm setting
                err-invalid-red-timeout (412)
                    Unrecognized red alarm timeout
                err-invalid-idle-code (413)
                    Unrecognized idle code
                err-device-in-standby (414)
                    Can't change config for designated Standby device
                err-invalid-link-bits (427)
                    Reserved E1 National bits must be left at zero.
                err-data-locked-by-another-user (450)
                    Another administrative user is making changes to this
                    part of the system via a terminal session. Check Event
                    Log for user name
                err-snmp-parse-failed (500)
                    Agent could not parse variable
                err-invalid-snmp-type (501)
                    Variable ASN type does not match Agent defined type 
                err-invalid-snmp-var-size (502)
                    Variable size is too big"                 		
         ::= { oT1E1ConfigEntry 13 }

oT1E1Gr303Facility OBJECT-TYPE
        SYNTAX DecisionType
        MAX-ACCESS read-only
        STATUS obsolete
        DESCRIPTION
           "Enables link to be configured as a Gr303 Facility"
        ::= { oT1E1ConfigEntry 14 }

oT1E1NationalBits OBJECT-TYPE
        SYNTAX OneByteField
        MAX-ACCESS read-write
        STATUS current
        DESCRIPTION
           "Enables E1 National S-bits to be set to zero or one.
           This single byte field can be changed to set the values 
           of the E1 NFA byte in odd frames as depicted below:
           
              sa8 sa7 sa6 sa5 sa4 reserved bits
              --- --- --- --- --- -------------
              1    1   1   1   1   0   0   0      = F8 (default)
              
           Values should be entered in Hex.  If reserved bits are changed,
           an error code (427) will be returned in the command status.                 
           "
        ::= { oT1E1ConfigEntry 15 }

oT1E1InterNational OBJECT-TYPE
        SYNTAX OneByteField
        MAX-ACCESS read-write
        STATUS current
        DESCRIPTION
           "Enables InterNational S(i) Spare bit to be set to zero or one.
           This single byte field can be changed to set the values 
           of the Bit 1 of TS0 G.704 frame as depicted below:
           
                    reserved bits        S(i)
              -------------------------- -----
              0   0   0   0   0   0   0   1      = 01 (default)
              
           Values should be entered in Hex.  If reserved bits are changed,
           an error code (427) will be returned in the command status.
           "
        ::= { oT1E1ConfigEntry 16 }

-- *************************************************************************
--   This is the Trap Definitions section for the OCTAL-T1E1 MIB. 
-- *************************************************************************

dnxOT1E1Enterprise OBJECT-IDENTITY
      STATUS current
      DESCRIPTION "ERI DNX T1/E1 Enterprise for Alarms/Events"
    ::= { dnxOT1E1 0 }

oT1E1ConfigTrap NOTIFICATION-TYPE
        OBJECTS {
            trapSequence,
            oT1E1CfgLinkAddr,
            oT1E1CfgCmdStatus
            }
        STATUS current
        DESCRIPTION
              	"This trap is used to notify a NMS that a user has updated 
              	the configuration for specific T1/E1 Port."
        ::= { dnxOT1E1Enterprise 1 }
                                
END

-- *************************************************************************
--
--  MIB:    ERI-DNX-T3-MIB   
--
--  Purpose:
--          This will be the MIB for the DNX T3 Interface 
--          Module. This will provide for Configuration and Diagnostics
--          on any T3 card in the nest.
--
--  Contact: Eastern Research Inc. 1-800-337-4374  Email: support@erinc.com
--
-- *************************************************************************
