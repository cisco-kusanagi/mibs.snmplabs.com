NSCDXGLIP-MIB DEFINITIONS ::= BEGIN

-- Title:	NSC DX Greenline-IP MIB version 1.1 in concise format
-- Date:	12 August 1994
-- By:		John Lyman <john.lyman@nsco.network.com>

IMPORTS
	enterprises, OBJECT-TYPE, NetworkAddress, IpAddress,
	Counter, Gauge, TimeTicks
	    FROM RFC1155-SMI
	DisplayString
	    FROM RFC1213-MIB
        nscDx 
            FROM NSC-MIB;

--
-- The NSC DX Greenline-IP group
--

nscDxGreenline OBJECT IDENTIFIER ::= { nscDx 4 }

--
-- the Channel Table
--

nscDxGlChannelTable OBJECT-TYPE
	SYNTAX	SEQUENCE OF NscDxGlChannelEntry
	ACCESS	not-accessible
	STATUS	mandatory
	DESCRIPTION
		"List of channel interface entries."
	::= { nscDxGreenline 1 }

nscDxGlChannelEntry OBJECT-TYPE
	SYNTAX	NscDxGlChannelEntry
	ACCESS	not-accessible
	STATUS	mandatory
	DESCRIPTION
		"Channel interface entry."
	INDEX	{ nscDxGlChanEntKeyId }
	::= { nscDxGlChannelTable 1 }

NscDxGlChannelEntry ::= SEQUENCE {
	nscDxGlChanEntKeyId 
		INTEGER,
	nscDxGlChanEntType
		INTEGER,
	nscDxGlChanEntActivityState
		INTEGER,
	nscDxGlChanEntResetState
		INTEGER,
	nscDxGlChanEntIplState
		INTEGER,
	nscDxGlChanEntIpState
		INTEGER,
	nscDxGlChanEntOnlineOfflineState
		INTEGER,
	nscDxGlChanEntPolling
		INTEGER,
	nscDxGlChanEntActiveSubchannel
		INTEGER,
	nscDxGlChanEntMemoryResourcesLimited
		INTEGER,
	nscDxGlChanEntTagOverruns
		Counter,
	nscDxGlChanEntDcOverruns
		Counter,
	nscDxGlChanEntDsOverruns
		Counter,
	nscDxGlChanEntDmaParityErrors
		Counter,
	nscDxGlChanEntCrcErrors
		Counter,
	nscDxGlChanEntResetsDuringDma
		Counter,
	nscDxGlChanEntCmdParityErrors
		Counter,
	nscDxGlChanEntUnsupportedStatuses
		Counter,
	nscDxGlChanEntMiscompareParityErrors
		Counter,
	nscDxGlChanEntSelectionTimeouts
		Counter,
	nscDxGlChanEntStatusAcceptDiscIns
		Counter,
	nscDxGlChanEntStatusAcceptTimeouts
		Counter,
	nscDxGlChanEntStatusWaitDiscIns
		Counter,
	nscDxGlChanEntStatusWaitTimeouts
		Counter,
	nscDxGlChanEntOpInActiveTimeouts
		Counter,
	nscDxGlChanEntNumCus
		INTEGER,
	nscDxGlChanEntChannelStatus
		INTEGER
}

nscDxGlChanEntKeyId OBJECT-TYPE
	SYNTAX	INTEGER (0..'F'h)
	ACCESS	read-only
	STATUS	mandatory
	DESCRIPTION
		"Processor Key ID (KID). This is a unique
		value for each interface."
	::= { nscDxGlChannelEntry 1 }

nscDxGlChanEntType OBJECT-TYPE
	SYNTAX	INTEGER {
		    bus-tag-hci(1),
		    bus-tag-rci(2),
		    escon-hci(3),
		    escon-rci(4)
		}
	ACCESS	read-only
	STATUS	mandatory
	DESCRIPTION
		"Channel interface type."
	::= { nscDxGlChannelEntry 2 }

nscDxGlChanEntActivityState OBJECT-TYPE
	SYNTAX	INTEGER {
		    idle(1),
		    active(2),
		    stacked(3),
		    suppressible(4),
		    unsuppressible(5),
		    ipl(6),
		    wait-for-resources(7)
		}
	ACCESS	read-only
	STATUS	mandatory
	DESCRIPTION
		"This is the actual state of the HCI (which depends on the
		IP state and online/offline state of the HCI)."
	::= { nscDxGlChannelEntry 3 }

nscDxGlChanEntResetState OBJECT-TYPE
	SYNTAX	INTEGER {
		    none(1),
		    system-reset(2),
		    selective-reset(3),
		    ifdisc(4)
		}
	ACCESS	read-only
	STATUS	mandatory
	DESCRIPTION
		"This identifies the pending channel reset to process."
	::= { nscDxGlChannelEntry 4 }

nscDxGlChanEntIplState OBJECT-TYPE
	SYNTAX	INTEGER {
		    idle(1),
		    active(2),
		    stacked(3),
		    suppressible(4),
		    unsuppressible(5),
		    ipl(6),
		    wait-for-resources(7)
		}
	ACCESS	read-only
	STATUS	mandatory
	DESCRIPTION
		"This is the state prior to the first command chain being
		completed.  It is used for IPL."
	::= { nscDxGlChannelEntry 5 }

nscDxGlChanEntIpState OBJECT-TYPE
	SYNTAX	INTEGER {
		    off(1),
		    on(2)
		}
	ACCESS	read-only
	STATUS	mandatory
	DESCRIPTION
		"This indicates whether the interface has been set online by
		the coprocessor.  It indicates whether a Start I/F has been
		sent by the coprocessor."
	::= { nscDxGlChannelEntry 6 }

nscDxGlChanEntOnlineOfflineState OBJECT-TYPE
	SYNTAX	INTEGER {
		    off(1),
		    on(2)
		}
	ACCESS	read-only
	STATUS	mandatory
	DESCRIPTION
		"This indicates the state of the switch on the back of the
		HCI."
	::= { nscDxGlChannelEntry 7 }


nscDxGlChanEntPolling OBJECT-TYPE
	SYNTAX	INTEGER {
		    off(1),
		    on(2)
		}
	ACCESS	read-write
	STATUS	mandatory
	DESCRIPTION
		"For a bus-tag-hci type channel this indicates whether the 
		HCI will request polling on the RCIs that it connects to.  For
		a bus-tag-rci type channel this indicates whether the RCI will
		allow polling on its channel interface."
	::= { nscDxGlChannelEntry 8 }

nscDxGlChanEntActiveSubchannel OBJECT-TYPE
	SYNTAX	INTEGER (0..'FF'h)
	ACCESS	read-only
	STATUS	mandatory
	DESCRIPTION
		"The HCI device address of the active device."
	::= { nscDxGlChannelEntry 9 }

nscDxGlChanEntMemoryResourcesLimited OBJECT-TYPE
	SYNTAX	INTEGER {
		    false(1),
		    true(2)
		}
	ACCESS	read-only
	STATUS	mandatory
	DESCRIPTION
		"Indicator of memory resource limitation."
	::= { nscDxGlChannelEntry 10 }

nscDxGlChanEntTagOverruns OBJECT-TYPE
	SYNTAX	Counter
	ACCESS	read-only
	STATUS	mandatory
	DESCRIPTION
		"Number of channel overruns."
	::= { nscDxGlChannelEntry 11 }

nscDxGlChanEntDcOverruns OBJECT-TYPE
	SYNTAX	Counter
	ACCESS	read-only
	STATUS	mandatory
	DESCRIPTION
		"Number of channel overruns in DC interlock mode."
	::= { nscDxGlChannelEntry 12 }

nscDxGlChanEntDsOverruns OBJECT-TYPE
	SYNTAX	Counter
	ACCESS	read-only
	STATUS	mandatory
	DESCRIPTION
		"Number of channel overruns in data streaming mode."
	::= { nscDxGlChannelEntry 13 }

nscDxGlChanEntDmaParityErrors OBJECT-TYPE
	SYNTAX	Counter
	ACCESS	read-only
	STATUS	mandatory
	DESCRIPTION
		"Number of DMA parity errors."
	::= { nscDxGlChannelEntry 14 }

nscDxGlChanEntCrcErrors OBJECT-TYPE
	SYNTAX	Counter
	ACCESS	read-only
	STATUS	mandatory
	DESCRIPTION
		"Number of CRC errors."
	::= { nscDxGlChannelEntry 15 }

nscDxGlChanEntResetsDuringDma OBJECT-TYPE
	SYNTAX	Counter
	ACCESS	read-only
	STATUS	mandatory
	DESCRIPTION
		"Number of times the DMA operation has been
		terminated by channel resets (selective reset,
		interface reconnect, system reset)."
	::= { nscDxGlChannelEntry 16 }

nscDxGlChanEntCmdParityErrors OBJECT-TYPE
	SYNTAX	Counter
	ACCESS	read-only
	STATUS	mandatory
	DESCRIPTION
		"Number of channel command parity errors
		(a Bus parity error with Command Out active)."
	::= { nscDxGlChannelEntry 17 }

nscDxGlChanEntUnsupportedStatuses OBJECT-TYPE
	SYNTAX	Counter
	ACCESS	read-only
	STATUS	mandatory
	DESCRIPTION
		"Number of unsupported status errors."
	::= { nscDxGlChannelEntry 18 }

nscDxGlChanEntMiscompareParityErrors OBJECT-TYPE
	SYNTAX	Counter
	ACCESS	read-only
	STATUS	mandatory
	DESCRIPTION
		"Number of miscompare parity errors."
	::= { nscDxGlChannelEntry 19 }

nscDxGlChanEntSelectionTimeouts OBJECT-TYPE
	SYNTAX	Counter
	ACCESS	read-only
	STATUS	mandatory
	DESCRIPTION
		"Number of selection timeouts."
	::= { nscDxGlChannelEntry 20 }

nscDxGlChanEntStatusAcceptDiscIns OBJECT-TYPE
	SYNTAX	Counter
	ACCESS	read-only
	STATUS	mandatory
	DESCRIPTION
		"Number of status accept disconnect in errors."
	::= { nscDxGlChannelEntry 21 }

nscDxGlChanEntStatusAcceptTimeouts OBJECT-TYPE
	SYNTAX	Counter
	ACCESS	read-only
	STATUS	mandatory
	DESCRIPTION
		"Number of status accept timeouts."
	::= { nscDxGlChannelEntry 22 }

nscDxGlChanEntStatusWaitDiscIns OBJECT-TYPE
	SYNTAX	Counter
	ACCESS	read-only
	STATUS	mandatory
	DESCRIPTION
		"Number of status wait disconnect in errors."
	::= { nscDxGlChannelEntry 23 }

nscDxGlChanEntStatusWaitTimeouts OBJECT-TYPE
	SYNTAX	Counter
	ACCESS	read-only
	STATUS	mandatory
	DESCRIPTION
		"Number of status wait timeouts."
	::= { nscDxGlChannelEntry 24 }

nscDxGlChanEntOpInActiveTimeouts OBJECT-TYPE
	SYNTAX	Counter
	ACCESS	read-only
	STATUS	mandatory
	DESCRIPTION
		"Number of op inactive timeouts."
	::= { nscDxGlChannelEntry 25 }

nscDxGlChanEntNumCus OBJECT-TYPE
	SYNTAX	INTEGER
	ACCESS	read-only
	STATUS	mandatory
	DESCRIPTION
		"Number of control units per interface."
	::= { nscDxGlChannelEntry 26 }

nscDxGlChanEntChannelStatus OBJECT-TYPE
	SYNTAX	INTEGER {
		    connected(1),
		    notconnected(2)
		}
	ACCESS	read-only
	STATUS	mandatory
	DESCRIPTION
		"The status of the channel interface."
	::= { nscDxGlChannelEntry 27 }


--
-- The profiles.
--

nscDxGlProfiles OBJECT IDENTIFIER ::= { nscDxGreenline 2 }

nscDxGlProfControlUnitTable OBJECT-TYPE
	SYNTAX	SEQUENCE OF NscDxGlProfControlUnitEntry
	ACCESS	not-accessible
	STATUS	mandatory
	DESCRIPTION
		"List of Control Unit entries."
	::= { nscDxGlProfiles 1 }

nscDxGlProfControlUnitEntry OBJECT-TYPE
	SYNTAX	NscDxGlProfControlUnitEntry
	ACCESS	not-accessible
	STATUS	mandatory
	DESCRIPTION
		"Control Unit entry.  This entry defines controller and
		device operating characteristics.  Some of the
		characteristics are: the address ranges the HCI responds to,
		the type of devices that are supported, and the operational
		condition of the HCI interface device."
	INDEX	{ nscDxGlCuEntKeyId, nscDxGlCuEntCuNum }
	::= { nscDxGlProfControlUnitTable 1 }

NscDxGlProfControlUnitEntry ::= SEQUENCE {
	nscDxGlProfCuEntKeyId
		INTEGER,
	nscDxGlProfCuEntCuNum
		INTEGER,
	nscDxGlProfCuEntNumDevices
		INTEGER,
	nscDxGlProfCuEntOnlineOfflineState
		INTEGER,
	nscDxGlProfCuEntDeviceType
		DisplayString,
	nscDxGlProfCuEntHostStartingDevAddr
		INTEGER,
	nscDxGlProfCuEntHostEndingDevAddr
		INTEGER,
	nscDxGlProfCuEntHostChannelSpeed
		INTEGER,
	nscDxGlProfCuEntHostBufferRequirements
		INTEGER,
	nscDxGlProfCuEntRmtIpAddr
		IpAddress,
	nscDxGlProfCuEntRmtStartingDevAddr
		INTEGER,
	nscDxGlProfCuEntRmtBufferHold
		INTEGER,
	nscDxGlProfCuEntRmtChannelSpeed
		INTEGER,
	nscDxGlProfCuEntRmtBufferRequirements
		INTEGER,
	nscDxGlProfCuEntUnsolStatusOption
		INTEGER,
	nscDxGlProfCuEntDevDriverOptions
		INTEGER,
	nscDxGlProfCuEntHostBufferHold
		INTEGER,
	nscDxGlProfCuEntWindowSize
		INTEGER
}

nscDxGlProfCuEntKeyId OBJECT-TYPE
	SYNTAX	INTEGER (0..'F'h)
	ACCESS	read-only
	STATUS	mandatory
	DESCRIPTION
		"Processor Key ID (KID). This is a unique
		value for each interface."
	::= { nscDxGlProfControlUnitEntry 1 }

nscDxGlProfCuEntCuNum OBJECT-TYPE
	SYNTAX	INTEGER (0..'F'h)
	ACCESS	read-only
	STATUS	mandatory
	DESCRIPTION
		"The profile number of the controller.  The HCI supports up
		to 16 controller definitions (a unique set of operating and
		address characteristics for a type of device).  The
		controller establishes the operation conditions of a device."
	::= { nscDxGlProfControlUnitEntry 2 }

nscDxGlProfCuEntNumDevices OBJECT-TYPE
	SYNTAX	INTEGER
	ACCESS	read-only
	STATUS	mandatory
	DESCRIPTION
		"Number of devices on this control unit."
	::= { nscDxGlProfControlUnitEntry 3 }

nscDxGlProfCuEntOnlineOfflineState OBJECT-TYPE
	SYNTAX	INTEGER {
		    offline(1),	-- device(s) offline
		    online(2) 	-- device(s) online
		}
	ACCESS	read-write
	STATUS	mandatory
	DESCRIPTION
		"The profiled state of the device(s)."
	::= { nscDxGlProfControlUnitEntry 4 }

nscDxGlProfCuEntDeviceType OBJECT-TYPE
	SYNTAX	DisplayString (SIZE(0..8))
	ACCESS	read-write
	STATUS	mandatory
	DESCRIPTION
		"The type of device associated with the controller
		function.  The controller uses a specific CCW table
		tailored for the unique operating characteristics
		of that particular device.  It allows the controller
		to reference a table identifying the unique operating
		characteristics of that particular device type."
	::= { nscDxGlProfControlUnitEntry 5 }

nscDxGlProfCuEntHostStartingDevAddr OBJECT-TYPE
	SYNTAX	INTEGER (0..255)
	ACCESS	read-write
	STATUS	mandatory
	DESCRIPTION
		"The first HCI device address in the range of addresses
		associated with the specified controller definition."
	::= { nscDxGlProfControlUnitEntry 6 }

nscDxGlProfCuEntHostEndingDevAddr OBJECT-TYPE
	SYNTAX	INTEGER (0..255)
	ACCESS	read-write
	STATUS	mandatory
	DESCRIPTION
		"The last HCI device address in the range of addresses
		associated with the specified controller definition.
		NOTE: This is used in conjunction with the
		nscDxGlProfCuEntHostStartingDevAddr variable.  The total
		number of device addresses in range is bounded by the
		nscDxGlProfCuEntHostStartingDevAddr and
		nscDxGlProfCuEntHostEndingDevAddr values for the specified
		controller definition."
	::= { nscDxGlProfControlUnitEntry 7 }

nscDxGlProfCuEntHostChannelSpeed  OBJECT-TYPE
	SYNTAX	INTEGER {
		    dci(1),	-- Host 1.5 MBps DC Interlock
		    ds3(2),	-- Host 3.0 MBps Data streaming
		    ds4(3)	-- Host 4.5 MBps Data streaming
		}
	ACCESS	read-write
	STATUS	mandatory
	DESCRIPTION
		"The HCI channel speed to the host.  This defines to the HCI
		the data transfer protocol and data transfer rate used for the
		specified controller definition."
	::= { nscDxGlProfControlUnitEntry 8 }

nscDxGlProfCuEntHostBufferRequirements OBJECT-TYPE
	SYNTAX	INTEGER (0..255)
	ACCESS	read-write
	STATUS	mandatory
	DESCRIPTION
		"The number of data buffers the HCI will allocate for
		a write I/O command."
	::= { nscDxGlProfControlUnitEntry 9 }

nscDxGlProfCuEntRmtIpAddr OBJECT-TYPE
	SYNTAX	IpAddress
	ACCESS	read-write
	STATUS	mandatory
	DESCRIPTION
		"The IP address of the remote interface, either an RCI where
		devices are attached, or an HCI for CTC."
	::= { nscDxGlProfControlUnitEntry 10 }

nscDxGlProfCuEntRmtStartingDevAddr OBJECT-TYPE
	SYNTAX	INTEGER (0..255)
	ACCESS	read-write
	STATUS	mandatory
	DESCRIPTION
		"The first remote device address in the range of addresses
		associated with the specified controller definition.
		This can be used only to map addresses recognized by the
		host to different addresses at the device.  If address
		mapping is not used, nscDxGlProfCuEntRmtStartingDevAddr should
		be the same as nscDxGlProfCuEntHostStartingDevAddr."
	::= { nscDxGlProfControlUnitEntry 11 }

nscDxGlProfCuEntRmtBufferHold OBJECT-TYPE
	SYNTAX	INTEGER {
		    tbl-def(1),	-- uses the value defined in the device table
		    on(2),	-- enables rmt buffer hold for all operations
		    off(3)	-- disables rmt buffer hold for all operations
		}
	ACCESS	read-write
	STATUS	mandatory
	DESCRIPTION
		"This indicates whether an RCI should wait for all the
		data associated with a CCW to be received before starting
		the device.  Each device-type CCW table assigns this
		attribute to the appropriate CCW's for that device.  It is
		generally enabled for overrunable devices."
	::= { nscDxGlProfControlUnitEntry 12 }

nscDxGlProfCuEntRmtChannelSpeed OBJECT-TYPE
	SYNTAX	INTEGER {
		    dci(1),	-- remote 1.5 MBps DC Interlock
		    ds3(2),	-- remote 3.0 MBps Data streaming
		    ds4(3)	-- remote 4.5 MBps Data streaming
		}
	ACCESS	read-write
	STATUS	mandatory
	DESCRIPTION
		"The remote channel speed to the device.  This defines to the
		remote interface what data transfer protocol and data transfer
		rate should be used for the specified devices."
	::= { nscDxGlProfControlUnitEntry 13 }

nscDxGlProfCuEntRmtBufferRequirements OBJECT-TYPE
	SYNTAX	INTEGER (0..255)
	ACCESS	read-write
	STATUS	mandatory
	DESCRIPTION
		"The number of data buffers an RCI will allocate for read
		I/O commands."
	::= { nscDxGlProfControlUnitEntry 14 }

nscDxGlProfCuEntUnsolStatusOption  OBJECT-TYPE
	SYNTAX	INTEGER {
		    q-non-uc(1), -- always queue unsol status
		    discard(2),	 -- discard unsol status
		    q-uc(3)	 -- queue unsol status if Unit Check
		}
	ACCESS	read-write
	STATUS	mandatory
	DESCRIPTION
		"This variable profiles the HCI to handle unsolicited
		status.  When unsolicited status is received by the HCI from
		an RCI, the status is queued for presentation to the
		channel, except if the device is busy.  If the device is
		busy, the status is handled in one of the following ways,
		depending upon which option has been defined.
		    discard  - profiles the HCI to discard the unsolicited
		    	       status
		    q-non-uc - profiles the HCI to always queue the
		    	       unsolicited status
		    q-uc     - profiles the HCI to queue the unsolicited
			       status only if it contains Unit Check status"
	::= { nscDxGlProfControlUnitEntry 15 }

nscDxGlProfCuEntDevDriverOptions OBJECT-TYPE
	SYNTAX	INTEGER
	ACCESS	read-write
	STATUS	mandatory
	DESCRIPTION
		"The device driver options.  See the 7220/7256 Host &
		Remote Channel Interfaces (HCI & RCI) with Greenline-IP
		software (GLH-IP/GLD-IP) reference manual (460793).
		The value depends on the device driver in use."
	::= { nscDxGlProfControlUnitEntry 16 }

nscDxGlProfCuEntHostBufferHold OBJECT-TYPE
	SYNTAX	INTEGER {
		    tbl-def(1),	-- uses the value defined in the device table
		    on(2),	-- enables host buffer hold for all operations
		    off(3)	-- disables host buffer hold for all operations
		}
	ACCESS	read-write
	STATUS	mandatory
	DESCRIPTION
		"This indicates whether the HCI should wait for all of the
		data associated with a CCW to be received before reconnecting
		to the channel."
	::= { nscDxGlProfControlUnitEntry 17 }

nscDxGlProfCuEntWindowSize OBJECT-TYPE
	SYNTAX	INTEGER
	ACCESS	read-write
	STATUS	mandatory
	DESCRIPTION
		"This variable specifies the number of IP packets that
		transport will sent before it waits for an acknowledgement
		to come back.  The following value are allowed.
			1 =   8 packets.
			2 =  16 packets.
			3 =  32 packets.
			4 =  64 packets.
			5 = 128 packets.
			6 = 256 packets.
			7 = 512 packets."
	::= { nscDxGlProfControlUnitEntry 18 }

nscDxGlProfDeviceTable OBJECT-TYPE
	SYNTAX	SEQUENCE OF NscDxGlProfDeviceEntry
	ACCESS	not-accessible
	STATUS	mandatory
	DESCRIPTION
		"List of Device entries."
	::= { nscDxGlProfiles 2 }

nscDxGlProfDeviceEntry OBJECT-TYPE
	SYNTAX	NscDxGlProfDeviceEntry
	ACCESS	not-accessible
	STATUS	mandatory
	DESCRIPTION
		"Device entry.  States whether device is profiled online or
		offline."
	INDEX	{ nscDxGlDevEntKeyId, nscDxGlProfDevEntDevice }
	::= { nscDxGlProfDeviceTable 1 }

NscDxGlProfDeviceEntry ::= SEQUENCE {
	nscDxGlProfDevEntKeyId
	      INTEGER,
	nscDxGlProfDevEntDevice
	      INTEGER,
	nscDxGlProfDevEntOnOff
	      INTEGER
	}

nscDxGlProfDevEntKeyId OBJECT-TYPE
	SYNTAX	INTEGER (0..'F'h)
	ACCESS	read-only
	STATUS	mandatory
	DESCRIPTION
		"Processor Key ID (KID). This is a unique
		value for each interface."
	::= { nscDxGlProfDeviceEntry 1 }

nscDxGlProfDevEntDevice OBJECT-TYPE
	SYNTAX	INTEGER (0..255)
	ACCESS	read-only
	STATUS	mandatory
	DESCRIPTION
		"Starting address of the device."
	::= { nscDxGlProfDeviceEntry 2 }

nscDxGlProfDevEntOnOff OBJECT-TYPE
	SYNTAX	INTEGER {
		    offline(1),	-- disable the device
		    online(2)	-- enable the device
		}
	ACCESS	read-write
	STATUS	mandatory
	DESCRIPTION
		"Profile device online or offline."
	::= { nscDxGlProfDeviceEntry 3 }


nscDxGlDevStatusTable OBJECT-TYPE
	SYNTAX	SEQUENCE OF NscDxGlDevStatusEntry
	ACCESS	not-accessible
	STATUS	mandatory
	DESCRIPTION
		"List of Device Status entries."
	::= { nscDxGreenline 3 }

nscDxGlDevStatusEntry OBJECT-TYPE
	SYNTAX	NscDxGlDevStatusEntry
	ACCESS	not-accessible
	STATUS	mandatory
	DESCRIPTION
		"Device status entry."
	INDEX	{ nscDxGlDevStatusEntKeyId, nscDxGlDevStatusEntDeviceNum }
	::= { nscDxGlDevStatusTable 1 }

NscDxGlDevStatusEntry ::= SEQUENCE {
        nscDxGlDevStatusEntKeyId
		INTEGER,
        nscDxGlDevStatusEntDeviceNum
		INTEGER,
        nscDxGlDevStatusEntHostDevAddr
		INTEGER,
        nscDxGlDevStatusEntRmtDevAddr
		INTEGER,
        nscDxGlDevStatusEntOnOffState
		INTEGER,
        nscDxGlDevStatusEntReservedState
		INTEGER
}

nscDxGlDevStatusEntKeyId OBJECT-TYPE
	SYNTAX	INTEGER (0..'F'h)
	ACCESS	read-only
	STATUS	mandatory
	DESCRIPTION
		"Processor Key ID (KID). This is a unique
		value for each interface."
	::= { nscDxGlDevStatusEntry 1 }

nscDxGlDevStatusEntDeviceNum OBJECT-TYPE
	SYNTAX	INTEGER (0..255)
	ACCESS	read-only
	STATUS	mandatory
	DESCRIPTION
		"The device number."
	::= { nscDxGlDevStatusEntry 2 }

nscDxGlDevStatusEntHostDevAddr OBJECT-TYPE
	SYNTAX	INTEGER
	ACCESS	read-only
	STATUS	mandatory
	DESCRIPTION
		"The HCI device address."
	::= { nscDxGlDevStatusEntry 3 }

nscDxGlDevStatusEntRmtDevAddr OBJECT-TYPE
	SYNTAX	INTEGER
	ACCESS	read-only
	STATUS	mandatory
	DESCRIPTION
		"The remote device address."
	::= { nscDxGlDevStatusEntry 4 }

nscDxGlDevStatusEntOnOffState OBJECT-TYPE
	SYNTAX	INTEGER {
		    off(1),
		    on(2),
		    marked-off(3)
		}
	ACCESS	read-only
	STATUS	mandatory
	DESCRIPTION
		"Specifies if the device is online, offline, or marked
		offline."
	::= { nscDxGlDevStatusEntry 5 }

nscDxGlDevStatusEntReservedState OBJECT-TYPE
	SYNTAX	INTEGER {
		    unreserved(1),
		    reserved(2),
		    primed(3),
		    re-reserved(4)
		}
	ACCESS	read-only
	STATUS	mandatory
	DESCRIPTION
		"Specifies if the device is reserved by this HCI."
	::= { nscDxGlDevStatusEntry 6 }


nscDxGlSesStatsTable OBJECT-TYPE
	SYNTAX	SEQUENCE OF NscDxGlSesStatsEntry
	ACCESS	not-accessible
	STATUS	mandatory
	DESCRIPTION
		"List of Session statistics entries."
	::= { nscDxGreenline 4 }

nscDxGlSesStatsEntry OBJECT-TYPE
	SYNTAX	NscDxGlSesStatsEntry
	ACCESS	not-accessible
	STATUS	mandatory
	DESCRIPTION
		"Session statistics entry."
	INDEX	{ nscDxGlSesStatsEntKeyId }
	::= { nscDxGlSesStatsTable 1 }

NscDxGlSesStatsEntry ::= SEQUENCE {
        nscDxGlSesStatsEntKeyId
		INTEGER,
        nscDxGlSesStatsEntInControlReqs
		Counter,
        nscDxGlSesStatsEntInControlResps
		Counter,
        nscDxGlSesStatsEntInDevAvailResps
		Counter,
        nscDxGlSesStatsEntInDevStatResps
		Counter,
        nscDxGlSesStatsEntInInitReqs
		Counter,
        nscDxGlSesStatsEntInInitResps
		Counter,
        nscDxGlSesStatsEntInReserveReqs
		Counter,
        nscDxGlSesStatsEntInReserveResps
		Counter,
        nscDxGlSesStatsEntInSenseReqs
		Counter,
        nscDxGlSesStatsEntInSenseResps
		Counter,
        nscDxGlSesStatsEntInUnreserveReqs
		Counter,
        nscDxGlSesStatsEntInInvalids
		Counter,
        nscDxGlSesStatsEntOutControlReqs
		Counter,
        nscDxGlSesStatsEntOutControlResps
		Counter,
        nscDxGlSesStatsEntOutDevAvailResps
		Counter,
        nscDxGlSesStatsEntOutDevStatResps
		Counter,
        nscDxGlSesStatsEntOutInitReqs
		Counter,
        nscDxGlSesStatsEntOutInitResps
		Counter,
        nscDxGlSesStatsEntOutReserveReqs
		Counter,
        nscDxGlSesStatsEntOutReserveResps
		Counter,
        nscDxGlSesStatsEntOutSenseReqs
		Counter,
        nscDxGlSesStatsEntOutSenseResps
		Counter,
        nscDxGlSesStatsEntOutUnreserveReqs
		Counter,
        nscDxGlSesStatsEntOutInvalids
		Counter,
        nscDxGlSesStatsEntHciState
		INTEGER,
        nscDxGlSesStatsEntRciState
		INTEGER,
        nscDxGlSesStatsEntHciMaxSessions
		INTEGER,
        nscDxGlSesStatsEntRciMaxSessions
		INTEGER,
        nscDxGlSesStatsEntRciPollStatus
		INTEGER,
        nscDxGlSesStatsEntRciPollRequests
		INTEGER,
        nscDxGlSesStatsEntRciPollDevice
		INTEGER
}

nscDxGlSesStatsEntKeyId OBJECT-TYPE
	SYNTAX	INTEGER (0..'F'h)
	ACCESS	read-only
	STATUS	mandatory
	DESCRIPTION
		"Processor Key ID (KID). This is a unique
		value for each interface."
	::= { nscDxGlSesStatsEntry 1 }

nscDxGlSesStatsEntInControlReqs OBJECT-TYPE
	SYNTAX	Counter
	ACCESS	read-only
	STATUS	mandatory
	DESCRIPTION
		"The number of control request packets received by session."
	::= { nscDxGlSesStatsEntry 2 }

nscDxGlSesStatsEntInControlResps OBJECT-TYPE
	SYNTAX	Counter
	ACCESS	read-only
	STATUS	mandatory
	DESCRIPTION
		"The number of control response packets received by session."
	::= { nscDxGlSesStatsEntry 3 }

nscDxGlSesStatsEntInDevAvailResps OBJECT-TYPE
	SYNTAX	Counter
	ACCESS	read-only
	STATUS	mandatory
	DESCRIPTION
		"The number of device available response packets received by
		session."
	::= { nscDxGlSesStatsEntry 4 }

nscDxGlSesStatsEntInDevStatResps OBJECT-TYPE
	SYNTAX	Counter
	ACCESS	read-only
	STATUS	mandatory
	DESCRIPTION
		"The number of device status response packets received by
		session."
	::= { nscDxGlSesStatsEntry 5 }

nscDxGlSesStatsEntInInitReqs OBJECT-TYPE
	SYNTAX	Counter
	ACCESS	read-only
	STATUS	mandatory
	DESCRIPTION
		"The number of init request packets received by session."
	::= { nscDxGlSesStatsEntry 6 }

nscDxGlSesStatsEntInInitResps OBJECT-TYPE
	SYNTAX	Counter
	ACCESS	read-only
	STATUS	mandatory
	DESCRIPTION
		"The number of init response packets received by session."
	::= { nscDxGlSesStatsEntry 7 }

nscDxGlSesStatsEntInReserveReqs OBJECT-TYPE
	SYNTAX	Counter
	ACCESS	read-only
	STATUS	mandatory
	DESCRIPTION
		"The number of reserve request packets received by session."
	::= { nscDxGlSesStatsEntry 8 }

nscDxGlSesStatsEntInReserveResps OBJECT-TYPE
	SYNTAX	Counter
	ACCESS	read-only
	STATUS	mandatory
	DESCRIPTION
		"The number of reserve response packets received by session."
	::= { nscDxGlSesStatsEntry 9 }

nscDxGlSesStatsEntInSenseReqs OBJECT-TYPE
	SYNTAX	Counter
	ACCESS	read-only
	STATUS	mandatory
	DESCRIPTION
		"The number of sense request packets received by session."
	::= { nscDxGlSesStatsEntry 10 }

nscDxGlSesStatsEntInSenseResps OBJECT-TYPE
	SYNTAX	Counter
	ACCESS	read-only
	STATUS	mandatory
	DESCRIPTION
		"The number of sense response packets received by session."
	::= { nscDxGlSesStatsEntry 11 }

nscDxGlSesStatsEntInUnreserveReqs OBJECT-TYPE
	SYNTAX	Counter
	ACCESS	read-only
	STATUS	mandatory
	DESCRIPTION
		"The number of unreserve request packets received by session."
	::= { nscDxGlSesStatsEntry 12 }

nscDxGlSesStatsEntInInvalids OBJECT-TYPE
	SYNTAX	Counter
	ACCESS	read-only
	STATUS	mandatory
	DESCRIPTION
		"The number of invalid packets received by session."
	::= { nscDxGlSesStatsEntry 13 }

nscDxGlSesStatsEntOutControlReqs OBJECT-TYPE
	SYNTAX	Counter
	ACCESS	read-only
	STATUS	mandatory
	DESCRIPTION
		"The number of control request packets sent by session."
	::= { nscDxGlSesStatsEntry 14 }

nscDxGlSesStatsEntOutControlResps OBJECT-TYPE
	SYNTAX	Counter
	ACCESS	read-only
	STATUS	mandatory
	DESCRIPTION
		"The number of control response packets sent by session."
	::= { nscDxGlSesStatsEntry 15 }

nscDxGlSesStatsEntOutDevAvailResps OBJECT-TYPE
	SYNTAX	Counter
	ACCESS	read-only
	STATUS	mandatory
	DESCRIPTION
		"The number of device available response packets sent by
		session."
	::= { nscDxGlSesStatsEntry 16 }

nscDxGlSesStatsEntOutDevStatResps OBJECT-TYPE
	SYNTAX	Counter
	ACCESS	read-only
	STATUS	mandatory
	DESCRIPTION
		"The number of device status response packets sent by
		session."
	::= { nscDxGlSesStatsEntry 17 }

nscDxGlSesStatsEntOutInitReqs OBJECT-TYPE
	SYNTAX	Counter
	ACCESS	read-only
	STATUS	mandatory
	DESCRIPTION
		"The number of init request packets sent by session."
	::= { nscDxGlSesStatsEntry 18 }

nscDxGlSesStatsEntOutInitResps OBJECT-TYPE
	SYNTAX	Counter
	ACCESS	read-only
	STATUS	mandatory
	DESCRIPTION
		"The number of init response packets sent by session."
	::= { nscDxGlSesStatsEntry 19 }

nscDxGlSesStatsEntOutReserveReqs OBJECT-TYPE
	SYNTAX	Counter
	ACCESS	read-only
	STATUS	mandatory
	DESCRIPTION
		"The number of reserve request packets sent by session."
	::= { nscDxGlSesStatsEntry 20 }

nscDxGlSesStatsEntOutReserveResps OBJECT-TYPE
	SYNTAX	Counter
	ACCESS	read-only
	STATUS	mandatory
	DESCRIPTION
		"The number of reserve response packets sent by session."
	::= { nscDxGlSesStatsEntry 21 }

nscDxGlSesStatsEntOutSenseReqs OBJECT-TYPE
	SYNTAX	Counter
	ACCESS	read-only
	STATUS	mandatory
	DESCRIPTION
		"The number of sense request packets sent by session."
	::= { nscDxGlSesStatsEntry 22 }

nscDxGlSesStatsEntOutSenseResps OBJECT-TYPE
	SYNTAX	Counter
	ACCESS	read-only
	STATUS	mandatory
	DESCRIPTION
		"The number of sense response packets sent by session."
	::= { nscDxGlSesStatsEntry 23 }

nscDxGlSesStatsEntOutUnreserveReqs OBJECT-TYPE
	SYNTAX	Counter
	ACCESS	read-only
	STATUS	mandatory
	DESCRIPTION
		"The number of unreserve request packets sent by session."
	::= { nscDxGlSesStatsEntry 24 }

nscDxGlSesStatsEntOutInvalids OBJECT-TYPE
	SYNTAX	Counter
	ACCESS	read-only
	STATUS	mandatory
	DESCRIPTION
		"The number of invalid packets sent by session."
	::= { nscDxGlSesStatsEntry 25 }

nscDxGlSesStatsEntHciState OBJECT-TYPE
	SYNTAX	INTEGER {
		    closed(1),
		    initial-poll(2),
		    hci-wait(3),
		    active(4)
		}
	ACCESS	read-only
	STATUS	mandatory
	DESCRIPTION
		"The state of the HCI."
	::= { nscDxGlSesStatsEntry 26 }

nscDxGlSesStatsEntRciState OBJECT-TYPE
	SYNTAX	INTEGER {
		    closed(1),
		    initial-poll(2),
		    hci-wait(3),
		    active(4)
		}
	ACCESS	read-only
	STATUS	mandatory
	DESCRIPTION
		"The state of the RCI."
	::= { nscDxGlSesStatsEntry 27 }

nscDxGlSesStatsEntHciMaxSessions OBJECT-TYPE
	SYNTAX	INTEGER
	ACCESS	read-only
	STATUS	mandatory
	DESCRIPTION
		"Maximum number of HCIs that can be connected to the RCI."
	::= { nscDxGlSesStatsEntry 28 }

nscDxGlSesStatsEntRciMaxSessions OBJECT-TYPE
	SYNTAX	INTEGER
	ACCESS	read-only
	STATUS	mandatory
	DESCRIPTION
		"Maximum number of remote interfaces that can be connected
		to the HCI."
	::= { nscDxGlSesStatsEntry 29 }

nscDxGlSesStatsEntRciPollStatus OBJECT-TYPE
	SYNTAX	INTEGER {
		    disabled(1),
		    enabled(2)
		}
	ACCESS	read-only
	STATUS	mandatory
	DESCRIPTION
		"This indicates whether automatic device polling is active."
	::= { nscDxGlSesStatsEntry 30 }

nscDxGlSesStatsEntRciPollRequests OBJECT-TYPE
	SYNTAX	Counter
	ACCESS	read-only
	STATUS	mandatory
	DESCRIPTION
		"Poll request count."
	::= { nscDxGlSesStatsEntry 31 }

nscDxGlSesStatsEntRciPollDevice OBJECT-TYPE
	SYNTAX	INTEGER
	ACCESS	read-only
	STATUS	mandatory
	DESCRIPTION
		"Poll device number."
	::= { nscDxGlSesStatsEntry 32 }


nscDxGlSesHciConnTable OBJECT-TYPE
	SYNTAX	SEQUENCE OF NscDxGlSesHciConnEntry
	ACCESS	not-accessible
	STATUS	mandatory
	DESCRIPTION
		"List of session connection entries."
	::= { nscDxGreenline 5 }

nscDxGlSesHciConnEntry OBJECT-TYPE
	SYNTAX	NscDxGlSesHciConnEntry
	ACCESS	not-accessible
	STATUS	mandatory
	DESCRIPTION
		"Session connection entry."
	INDEX	{ nscDxGlSesHciConnEntKeyId, nscDxGlSesHciConnEntSesNum }
	::= { nscDxGlSesHciConnTable 1 }

NscDxGlSesHciConnEntry ::= SEQUENCE {
	nscDxGlSesHciConnEntKeyId
		INTEGER,
	nscDxGlSesHciConnEntSesNum
		INTEGER,
	nscDxGlSesHciConnEntIpAddress
		IpAddress,
	nscDxGlSesHciConnEntStatus
		INTEGER,
	nscDxGlSesHciConnEntSendState
		INTEGER,
	nscDxGlSesHciConnEntRecvState
		INTEGER,
	nscDxGlSesHciConnEntAddr
		INTEGER,
	nscDxGlSesHciConnEntFlags
		INTEGER,
	nscDxGlSesHciConnEntReconn
		INTEGER
}

nscDxGlSesHciConnEntKeyId OBJECT-TYPE
	SYNTAX	INTEGER (0..'F'h)
	ACCESS	read-only
	STATUS	mandatory
	DESCRIPTION
		"Processor Key ID (KID). This is a unique
		value for each interface."
	::= { nscDxGlSesHciConnEntry 1 }

nscDxGlSesHciConnEntSesNum OBJECT-TYPE
	SYNTAX	INTEGER
	ACCESS	read-only
	STATUS	mandatory
	DESCRIPTION
		"The session number."
	::= { nscDxGlSesHciConnEntry 2 }

nscDxGlSesHciConnEntIpAddress OBJECT-TYPE
	SYNTAX	IpAddress
	ACCESS	read-only
	STATUS	mandatory
	DESCRIPTION
		"The IP address of the remote RCI/HCI."
	::= { nscDxGlSesHciConnEntry 3 }

nscDxGlSesHciConnEntStatus OBJECT-TYPE
	SYNTAX	INTEGER {
		    closed(1),
		    init1(2),
		    init2(3),
		    open(4),
		    closing(5)
		}
	ACCESS	read-only
	STATUS	mandatory
	DESCRIPTION
		"Session status.  In normal operations it will be open"
	::= { nscDxGlSesHciConnEntry 4 }

nscDxGlSesHciConnEntSendState OBJECT-TYPE
	SYNTAX	INTEGER {
		    idle(6),
		    header(7),
		    data(8),
		    flush(9),
		    trailer(10)
		}
	ACCESS	read-only
	STATUS	mandatory
	DESCRIPTION
		"The current state of the outbound data stream."
	::= { nscDxGlSesHciConnEntry 5 }

nscDxGlSesHciConnEntRecvState OBJECT-TYPE
	SYNTAX	INTEGER {
		    idle(6),
		    header(7),
		    data(8),
		    flush(9),
		    trailer(10)
		}
	ACCESS	read-only
	STATUS	mandatory
	DESCRIPTION
		"The current state of the inbound data stream."
	::= { nscDxGlSesHciConnEntry 6 }

nscDxGlSesHciConnEntAddr OBJECT-TYPE
	SYNTAX	INTEGER
	ACCESS	read-only
	STATUS	mandatory
	DESCRIPTION
		"The local address of the device currently receiving data
		from the connected HCI."
	::= { nscDxGlSesHciConnEntry 7 }

nscDxGlSesHciConnEntFlags OBJECT-TYPE
	SYNTAX	INTEGER
	ACCESS	read-only
	STATUS	mandatory
	DESCRIPTION
		"Session flag information.  This is represented by an array
		of flags, with each flag represented by one hex digit which
		will have the value of one (on) or zero (off).  The value
		may have multiple flags set at the same time.  The following
		flags are currently in use.
			10000000 - Polling has been requested by this HCI
			 1000000 - Reset has been sent
			  100000 - Session is congested"
	::= { nscDxGlSesHciConnEntry 8 }

nscDxGlSesHciConnEntReconn OBJECT-TYPE
	SYNTAX	INTEGER
	ACCESS	read-only
	STATUS	mandatory
	DESCRIPTION
		"The amount of time in seconds between reconnects.  It is only
		valid if status is closed."
	::= { nscDxGlSesHciConnEntry 9 }


nscDxGlSesRciConnTable OBJECT-TYPE
	SYNTAX	SEQUENCE OF NscDxGlSesRciConnEntry
	ACCESS	not-accessible
	STATUS	mandatory
	DESCRIPTION
		"List of session connection entries."
	::= { nscDxGreenline 6 }

nscDxGlSesRciConnEntry OBJECT-TYPE
	SYNTAX	NscDxGlSesRciConnEntry
	ACCESS	not-accessible
	STATUS	mandatory
	DESCRIPTION
		"Session connection entry."
	INDEX	{ nscDxGlSesRciConnEntKeyId, nscDxGlSesRciConnEntSesNum }
	::= { nscDxGlSesRciConnTable 1 }

NscDxGlSesRciConnEntry ::= SEQUENCE {
	nscDxGlSesRciConnEntKeyId
		INTEGER,
	nscDxGlSesRciConnEntSesNum
		INTEGER,
	nscDxGlSesRciConnEntIpAddress
		IpAddress,
	nscDxGlSesRciConnEntStatus
		INTEGER,
	nscDxGlSesRciConnEntSendState
		INTEGER,
	nscDxGlSesRciConnEntRecvState
		INTEGER,
	nscDxGlSesRciConnEntAddr
		INTEGER,
	nscDxGlSesRciConnEntFlags
		INTEGER
}

nscDxGlSesRciConnEntKeyId OBJECT-TYPE
	SYNTAX	INTEGER (0..'F'h)
	ACCESS	read-only
	STATUS	mandatory
	DESCRIPTION
		"Processor Key ID (KID). This is a unique
		value for each interface."
	::= { nscDxGlSesRciConnEntry 1 }

nscDxGlSesRciConnEntSesNum OBJECT-TYPE
	SYNTAX	INTEGER
	ACCESS	read-only
	STATUS	mandatory
	DESCRIPTION
		"The session number."
	::= { nscDxGlSesRciConnEntry 2 }

nscDxGlSesRciConnEntIpAddress OBJECT-TYPE
	SYNTAX	IpAddress
	ACCESS	read-only
	STATUS	mandatory
	DESCRIPTION
		"The IP address of the remote HCI."
	::= { nscDxGlSesRciConnEntry 3 }

nscDxGlSesRciConnEntStatus OBJECT-TYPE
	SYNTAX	INTEGER {
		    closed(1),
		    init1(2),
		    init2(3),
		    open(4),
		    closing(5)
		}
	ACCESS	read-only
	STATUS	mandatory
	DESCRIPTION
		"Session status.  In normal operations it will be open"
	::= { nscDxGlSesRciConnEntry 4 }

nscDxGlSesRciConnEntSendState OBJECT-TYPE
	SYNTAX	INTEGER {
		    idle(6),
		    header(7),
		    data(8),
		    flush(9),
		    trailer(10)
		}
	ACCESS	read-only
	STATUS	mandatory
	DESCRIPTION
		"The current state of the outbound data stream."
	::= { nscDxGlSesRciConnEntry 5 }

nscDxGlSesRciConnEntRecvState OBJECT-TYPE
	SYNTAX	INTEGER {
		    idle(6),
		    header(7),
		    data(8),
		    flush(9),
		    trailer(10)
		}
	ACCESS	read-only
	STATUS	mandatory
	DESCRIPTION
		"The current state of the inbound data stream."
	::= { nscDxGlSesRciConnEntry 6 }

nscDxGlSesRciConnEntAddr OBJECT-TYPE
	SYNTAX	INTEGER
	ACCESS	read-only
	STATUS	mandatory
	DESCRIPTION
		"The local address of the device currently receiving data
		from this RCI."
	::= { nscDxGlSesRciConnEntry 7 }

nscDxGlSesRciConnEntFlags OBJECT-TYPE
	SYNTAX	INTEGER
	ACCESS	read-only
	STATUS	mandatory
	DESCRIPTION
		"Session flag information.  This is represented by an array
		of flags, with each flag represented by one hex digit which
		will have the value of one (on) or zero (off).  The value
		may have multiple flags set at the same time.  The following
		flags are currently in use.
			10000000 - Polling has been requested by remote HCI
			 1000000 - Reset has been sent
			  100000 - Session is congested"
	::= { nscDxGlSesRciConnEntry 8 }


nscDxGlSesDevTable OBJECT-TYPE
	SYNTAX	SEQUENCE OF NscDxGlSesDevEntry
	ACCESS	not-accessible
	STATUS	mandatory
	DESCRIPTION
		"List of session device entries."
	::= { nscDxGreenline 7 }

nscDxGlSesDevEntry OBJECT-TYPE
	SYNTAX	NscDxGlSesDevEntry
	ACCESS	not-accessible
	STATUS	mandatory
	DESCRIPTION
		"Session device entry."
	INDEX	{ nscDxGlSesDevEntKeyId, nscDxGlSesDevEntDevice }
	::= { nscDxGlSesDevTable 1 }

NscDxGlSesDevEntry ::= SEQUENCE {
	nscDxGlSesDevEntKeyId
		INTEGER,
	nscDxGlSesDevEntDevice
		INTEGER,
	nscDxGlSesDevEntReserve
		INTEGER,
	nscDxGlSesDevEntPrimed
		INTEGER,
	nscDxGlSesDevEntStat
		INTEGER,
	nscDxGlSesDevEntSenseData
		OCTET STRING
}

nscDxGlSesDevEntKeyId OBJECT-TYPE
	SYNTAX	INTEGER (0..'F'h)
	ACCESS	read-only
	STATUS	mandatory
	DESCRIPTION
		"Processor Key ID (KID). This is a unique
		value for each interface."
	::= { nscDxGlSesDevEntry 1 }

nscDxGlSesDevEntDevice OBJECT-TYPE
	SYNTAX	INTEGER (0..255)
	ACCESS	read-only
	STATUS	mandatory
	DESCRIPTION
		"The device address."
	::= { nscDxGlSesDevEntry 2 }

nscDxGlSesDevEntReserve OBJECT-TYPE
	SYNTAX	INTEGER
	ACCESS	read-only
	STATUS	mandatory
	DESCRIPTION
		"The session number of the HCI that has reserved the device.
                This value will -1 if the device is not currently reserved."
	::= { nscDxGlSesDevEntry 3 }

nscDxGlSesDevEntPrimed OBJECT-TYPE
	SYNTAX	INTEGER
	ACCESS	read-only
	STATUS	mandatory
	DESCRIPTION
		"Bit map with each bit representing an HCI that is waiting
		for the device to become unreserved.  The right most bit
		corresponds to HCI 0."
	::= { nscDxGlSesDevEntry 4 }

nscDxGlSesDevEntStat OBJECT-TYPE
	SYNTAX	INTEGER
	ACCESS	read-only
	STATUS	mandatory
	DESCRIPTION
		"The status of the device, as given in the following:
			0x80 - device is offline
			0x40 - device in online but does not respond
			0-7  - number of sense bytes"
	::= { nscDxGlSesDevEntry 5 }

nscDxGlSesDevEntSenseData OBJECT-TYPE
	SYNTAX	OCTET STRING (SIZE(0..6))
	ACCESS	read-only
	STATUS	mandatory
	DESCRIPTION
		"The sense bytes."
	::= { nscDxGlSesDevEntry 6 }


nscDxGlXportStatsTable OBJECT-TYPE
	SYNTAX	SEQUENCE OF NscDxGlXportStatsEntry
	ACCESS	not-accessible
	STATUS	mandatory
	DESCRIPTION
		"List of transport statistics entries."
	::= { nscDxGreenline 8 }

nscDxGlXportStatsEntry OBJECT-TYPE
	SYNTAX	NscDxGlXportStatsEntry
	ACCESS	not-accessible
	STATUS	mandatory
	DESCRIPTION
		"Transport statistics entry."
	INDEX	{ nscDxGlXportStatsEntKeyId }
	::= { nscDxGlXportStatsTable 1 }

NscDxGlXportStatsEntry ::= SEQUENCE {
	nscDxGlXportStatsEntKeyId
		INTEGER,
	nscDxGlXportStatsEntInAcks
		Counter,
	nscDxGlXportStatsEntInConnects
		Counter,
	nscDxGlXportStatsEntInDataDups
		Counter,
	nscDxGlXportStatsEntInDataInOrders
		Counter,
	nscDxGlXportStatsEntInDataInvalids
		Counter,
	nscDxGlXportStatsEntInDataInWindows
		Counter,
	nscDxGlXportStatsEntInDiscs
		Counter,
	nscDxGlXportStatsEntInNacks
		Counter,
	nscDxGlXportStatsEntInProbes
		Counter,
	nscDxGlXportStatsEntInProbeResps
		Counter,
	nscDxGlXportStatsEntBadPckts
		Counter,
	nscDxGlXportStatsEntBadXcbs
		Counter,
	nscDxGlXportStatsEntOutAcks
		Counter,
	nscDxGlXportStatsEntOutConnects
		Counter,
	nscDxGlXportStatsEntOutDatas
		Counter,
	nscDxGlXportStatsEntOutDiscs
		Counter,
	nscDxGlXportStatsEntOutNacks
		Counter,
	nscDxGlXportStatsEntOutProbes
		Counter,
	nscDxGlXportStatsEntOutProbeResps
		Counter,
	nscDxGlXportStatsEntReconns
		Counter,
	nscDxGlXportStatsEntRetransmits
		Counter,
	nscDxGlXportStatsEntBadChecksums
		Counter,
	nscDxGlXportStatsEntBadVersions
		Counter,
	nscDxGlXportStatsEntConnTimeouts
		Counter,
	nscDxGlXportStatsEntInitXcbExists
		Counter,
	nscDxGlXportStatsEntNoHdrSpaces
		Counter,
	nscDxGlXportStatsEntNoMemorys
		Counter,
	nscDxGlXportStatsEntNoPes
		Counter,
	nscDxGlXportStatsEntOutOfSeqDatas
		Counter,
	nscDxGlXportStatsEntShortPackets
		Counter
}

nscDxGlXportStatsEntKeyId OBJECT-TYPE
	SYNTAX	INTEGER (0..'F'h)
	ACCESS	read-only
	STATUS	mandatory
	DESCRIPTION
		"Processor Key ID (KID). This is a unique
		value for each interface."
	::= { nscDxGlXportStatsEntry 1 }

nscDxGlXportStatsEntInAcks OBJECT-TYPE
	SYNTAX	Counter
	ACCESS	read-only
	STATUS	mandatory
	DESCRIPTION
		"The number of ack packets received by transport."
	::= { nscDxGlXportStatsEntry 2 }

nscDxGlXportStatsEntInConnects OBJECT-TYPE
	SYNTAX	Counter
	ACCESS	read-only
	STATUS	mandatory
	DESCRIPTION
		"The number of connect packets received by transport."
	::= { nscDxGlXportStatsEntry 3 }

nscDxGlXportStatsEntInDataDups OBJECT-TYPE
	SYNTAX	Counter
	ACCESS	read-only
	STATUS	mandatory
	DESCRIPTION
		"The number of data dup packets received by transport."
	::= { nscDxGlXportStatsEntry 4 }

nscDxGlXportStatsEntInDataInOrders OBJECT-TYPE
	SYNTAX	Counter
	ACCESS	read-only
	STATUS	mandatory
	DESCRIPTION
		"The number of data in order packets received by transport."
	::= { nscDxGlXportStatsEntry 5 }

nscDxGlXportStatsEntInDataInvalids OBJECT-TYPE
	SYNTAX	Counter
	ACCESS	read-only
	STATUS	mandatory
	DESCRIPTION
		"The number of data invalid packets received by transport."
	::= { nscDxGlXportStatsEntry 6 }

nscDxGlXportStatsEntInDataInWindows OBJECT-TYPE
	SYNTAX	Counter
	ACCESS	read-only
	STATUS	mandatory
	DESCRIPTION
		"The number of data in window packets received by transport."
	::= { nscDxGlXportStatsEntry 7 }

nscDxGlXportStatsEntInDiscs OBJECT-TYPE
	SYNTAX	Counter
	ACCESS	read-only
	STATUS	mandatory
	DESCRIPTION
		"The number of disconnect packets received by transport."
	::= { nscDxGlXportStatsEntry 8 }

nscDxGlXportStatsEntInNacks OBJECT-TYPE
	SYNTAX	Counter
	ACCESS	read-only
	STATUS	mandatory
	DESCRIPTION
		"The number of nack packets received by transport."
	::= { nscDxGlXportStatsEntry 9 }

nscDxGlXportStatsEntInProbes OBJECT-TYPE
	SYNTAX	Counter
	ACCESS	read-only
	STATUS	mandatory
	DESCRIPTION
		"The number of probe packets received by transport."
	::= { nscDxGlXportStatsEntry 10 }

nscDxGlXportStatsEntInProbeResps OBJECT-TYPE
	SYNTAX	Counter
	ACCESS	read-only
	STATUS	mandatory
	DESCRIPTION
		"The number of probe response packets received by transport."
	::= { nscDxGlXportStatsEntry 11 }

nscDxGlXportStatsEntBadPckts OBJECT-TYPE
	SYNTAX	Counter
	ACCESS	read-only
	STATUS	mandatory
	DESCRIPTION
		"The number of bad packets received by transport."
	::= { nscDxGlXportStatsEntry 12 }

nscDxGlXportStatsEntBadXcbs OBJECT-TYPE
	SYNTAX	Counter
	ACCESS	read-only
	STATUS	mandatory
	DESCRIPTION
		"The number of bad xcb packets received by transport."
	::= { nscDxGlXportStatsEntry 13 }

nscDxGlXportStatsEntOutAcks OBJECT-TYPE
	SYNTAX	Counter
	ACCESS	read-only
	STATUS	mandatory
	DESCRIPTION
		"The number of ack packets sent by transport."
	::= { nscDxGlXportStatsEntry 14 }

nscDxGlXportStatsEntOutConnects OBJECT-TYPE
	SYNTAX	Counter
	ACCESS	read-only
	STATUS	mandatory
	DESCRIPTION
		"The number of connect packets sent by transport."
	::= { nscDxGlXportStatsEntry 15 }

nscDxGlXportStatsEntOutDatas OBJECT-TYPE
	SYNTAX	Counter
	ACCESS	read-only
	STATUS	mandatory
	DESCRIPTION
		"The number of data packets sent by transport."
	::= { nscDxGlXportStatsEntry 16 }

nscDxGlXportStatsEntOutDiscs OBJECT-TYPE
	SYNTAX	Counter
	ACCESS	read-only
	STATUS	mandatory
	DESCRIPTION
		"The number of disconnect packets sent by transport."
	::= { nscDxGlXportStatsEntry 17 }

nscDxGlXportStatsEntOutNacks OBJECT-TYPE
	SYNTAX	Counter
	ACCESS	read-only
	STATUS	mandatory
	DESCRIPTION
		"The number of nack packets sent by transport."
	::= { nscDxGlXportStatsEntry 18 }

nscDxGlXportStatsEntOutProbes OBJECT-TYPE
	SYNTAX	Counter
	ACCESS	read-only
	STATUS	mandatory
	DESCRIPTION
		"The number of probe packets sent by transport."
	::= { nscDxGlXportStatsEntry 19 }

nscDxGlXportStatsEntOutProbeResps OBJECT-TYPE
	SYNTAX	Counter
	ACCESS	read-only
	STATUS	mandatory
	DESCRIPTION
		"The number of probe response packets sent by transport."
	::= { nscDxGlXportStatsEntry 20 }

nscDxGlXportStatsEntReconns OBJECT-TYPE
	SYNTAX	Counter
	ACCESS	read-only
	STATUS	mandatory
	DESCRIPTION
		"The number of reconnect packets sent by transport."
	::= { nscDxGlXportStatsEntry 21 }

nscDxGlXportStatsEntRetransmits OBJECT-TYPE
	SYNTAX	Counter
	ACCESS	read-only
	STATUS	mandatory
	DESCRIPTION
		"The number of retransmit packets sent by transport."
	::= { nscDxGlXportStatsEntry 22 }

nscDxGlXportStatsEntBadChecksums OBJECT-TYPE
	SYNTAX	Counter
	ACCESS	read-only
	STATUS	mandatory
	DESCRIPTION
		"The number of bad checksum errors."
	::= { nscDxGlXportStatsEntry 23 }

nscDxGlXportStatsEntBadVersions OBJECT-TYPE
	SYNTAX	Counter
	ACCESS	read-only
	STATUS	mandatory
	DESCRIPTION
		"The number of bad version errors."
	::= { nscDxGlXportStatsEntry 24 }

nscDxGlXportStatsEntConnTimeouts OBJECT-TYPE
	SYNTAX	Counter
	ACCESS	read-only
	STATUS	mandatory
	DESCRIPTION
		"The number of connect timeout errors."
	::= { nscDxGlXportStatsEntry 25 }

nscDxGlXportStatsEntInitXcbExists OBJECT-TYPE
	SYNTAX	Counter
	ACCESS	read-only
	STATUS	mandatory
	DESCRIPTION
		"The number of xcb exists errors."
	::= { nscDxGlXportStatsEntry 26 }

nscDxGlXportStatsEntNoHdrSpaces OBJECT-TYPE
	SYNTAX	Counter
	ACCESS	read-only
	STATUS	mandatory
	DESCRIPTION
		"The number of no header space errors."
	::= { nscDxGlXportStatsEntry 27 }

nscDxGlXportStatsEntNoMemorys OBJECT-TYPE
	SYNTAX	Counter
	ACCESS	read-only
	STATUS	mandatory
	DESCRIPTION
		"The number of no memory errors."
	::= { nscDxGlXportStatsEntry 28 }

nscDxGlXportStatsEntNoPes OBJECT-TYPE
	SYNTAX	Counter
	ACCESS	read-only
	STATUS	mandatory
	DESCRIPTION
		"The number of no pe errors."
	::= { nscDxGlXportStatsEntry 29 }

nscDxGlXportStatsEntOutOfSeqDatas OBJECT-TYPE
	SYNTAX	Counter
	ACCESS	read-only
	STATUS	mandatory
	DESCRIPTION
		"The number of out of sequence data errors."
	::= { nscDxGlXportStatsEntry 30 }

nscDxGlXportStatsEntShortPackets OBJECT-TYPE
	SYNTAX	Counter
	ACCESS	read-only
	STATUS	mandatory
	DESCRIPTION
		"The number of short packets errors."
	::= { nscDxGlXportStatsEntry 31 }


nscDxGlXportConnTable OBJECT-TYPE
	SYNTAX	SEQUENCE OF NscDxGlXportConnEntry
	ACCESS	not-accessible
	STATUS	mandatory
	DESCRIPTION
		"List of transport connection entries."
	::= { nscDxGreenline 9 }

nscDxGlXportConnEntry OBJECT-TYPE
	SYNTAX	NscDxGlXportConnEntry
	ACCESS	not-accessible
	STATUS	mandatory
	DESCRIPTION
		"Transport connection entry."
	INDEX	{ nscDxGlXportConnEntKeyId, nscDxGlXportConnEntNum }
	::= { nscDxGlXportConnTable 1 }

NscDxGlXportConnEntry ::= SEQUENCE {
	nscDxGlXportConnEntKeyId
		INTEGER,
	nscDxGlXportConnEntNum
		INTEGER,
	nscDxGlXportConnEntLocalAddress
		IpAddress,
	nscDxGlXportConnEntLocalPort
		INTEGER,
	nscDxGlXportConnEntRemoteAddress
		IpAddress,
	nscDxGlXportConnEntRemotePort
		INTEGER,
	nscDxGlXportConnEntXopt
		INTEGER,
	nscDxGlXportConnEntWindowSize
		INTEGER,
	nscDxGlXportConnEntRoundTripTme
		INTEGER,
	nscDxGlXportConnEntSeqNumber
		INTEGER,
	nscDxGlXportConnEntXcbFlags
		INTEGER
}

nscDxGlXportConnEntKeyId OBJECT-TYPE
	SYNTAX	INTEGER (0..'F'h)
	ACCESS	read-only
	STATUS	mandatory
	DESCRIPTION
		"Processor Key ID (KID). This is a unique
		value for each interface."
	::= { nscDxGlXportConnEntry 1 }

nscDxGlXportConnEntNum OBJECT-TYPE
	SYNTAX	INTEGER
	ACCESS	read-only
	STATUS	mandatory
	DESCRIPTION
		"The transport connection number."
	::= { nscDxGlXportConnEntry 2 }

nscDxGlXportConnEntLocalAddress OBJECT-TYPE
	SYNTAX	IpAddress
	ACCESS	read-only
	STATUS	mandatory
	DESCRIPTION
		"The local IP address."
	::= { nscDxGlXportConnEntry 3 }

nscDxGlXportConnEntLocalPort OBJECT-TYPE
	SYNTAX	INTEGER
	ACCESS	read-only
	STATUS	mandatory
	DESCRIPTION
		"The local transport port number."
	::= { nscDxGlXportConnEntry 4 }

nscDxGlXportConnEntRemoteAddress OBJECT-TYPE
	SYNTAX	IpAddress
	ACCESS	read-only
	STATUS	mandatory
	DESCRIPTION
		"The remote IP address."
	::= { nscDxGlXportConnEntry 5 }

nscDxGlXportConnEntRemotePort OBJECT-TYPE
	SYNTAX	INTEGER
	ACCESS	read-only
	STATUS	mandatory
	DESCRIPTION
		"The remote transport port number."
	::= { nscDxGlXportConnEntry 6 }

nscDxGlXportConnEntXopt OBJECT-TYPE
	SYNTAX	INTEGER
	ACCESS	read-only
	STATUS	mandatory
	DESCRIPTION
		"Xport option information.  This is represented by an array
		of flags, with each flag represented by one hex digit which
		will have the value of one (on) or zero (off).  The value
		may have multiple flags set at the same time.  The following
		flags are currently in use.
			10000000 - Return data
			 1000000 - Fast search"
	::= { nscDxGlXportConnEntry 7 }

nscDxGlXportConnEntWindowSize OBJECT-TYPE
	SYNTAX	INTEGER
	ACCESS	read-only
	STATUS	mandatory
	DESCRIPTION
		"Window size specified as a packet count, 8, 16, 32, 64,
		128, or 256"
	::= { nscDxGlXportConnEntry 8 }

nscDxGlXportConnEntRoundTripTime OBJECT-TYPE
	SYNTAX	INTEGER
	ACCESS	read-only
	STATUS	mandatory
	DESCRIPTION
		"Round trip time in milliseconds."
	::= { nscDxGlXportConnEntry 9 }

nscDxGlXportConnEntSeqNumber OBJECT-TYPE
	SYNTAX	INTEGER
	ACCESS	read-only
	STATUS	mandatory
	DESCRIPTION
		"Sequence number."
	::= { nscDxGlXportConnEntry 10 }

nscDxGlXportConnEntXcbFlags OBJECT-TYPE
	SYNTAX	INTEGER
	ACCESS	read-only
	STATUS	mandatory
	DESCRIPTION
		"Xport flag information.  This is represented by an array
		of flags, with each flag represented by one hex digit which
		will have the value of one (on) or zero (off).  The value
		may have multiple flags set at the same time.  The following
		flags are currently in use.
			10000000 - Owed ack
			 1000000 - Owe ack
			  100000 - Owed probe
			   10000 - Congested"
	::= { nscDxGlXportConnEntry 11 }

END
