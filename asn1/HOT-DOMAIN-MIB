HOT-DOMAIN-MIB DEFINITIONS ::= BEGIN

 -- Version : 1.2
 -- Enterprise Domain MIB
 -- Copyright (C) 1998 Paradyne Corporation.
 -- Author  : Surajit Dey
 --
 -- Last Changed  : 10/20/1999 Wayne Jadoo
 -- Last Changed  : 1/15/1998 S. Dey
 -- Last Changed  : 10/28/1998 Rajesh Gowda


 -- History
 -- 12/17/1997 - S. Dey.
 --
 -- Initial Version.
 --
 -- 12/19/1997 - S. Dey.
 -- Included changes as per review meeting on 12/18.
 -- Changed VNID Id from read-only to read-write.
 -- Added domain name in pdnCardConfigTable.
 -- Added a new object to set VNID Id (index) of pdnCardConfigTable.
 -- Added new object for mode in pdnPortConfigTable.
 -- Added new objects in pdnClientConfigTable for
 -- Lease time, Lease remaining time and MAC address of client.
 --
 -- 1/5/1998 - S. Dey
 -- Changed the name of index from pdnPortConfigPort to pdnPortConfigIfIndex
 -- in pdnPortConfigTable.
 --
 -- 1/7/1998 - S. Dey
 -- Changed pdnClientconfigPort to pdnClientconfigIfIndex in 
 -- pdnClientconfigTable.
 --
 -- 1/15/98 - S. Dey
 -- Added comments from MIB WG meeting. Changed MIB name from
 -- ATLANTIS-BRIDGE... to HOT-BRIDGE....
 --
 -- 5/19/98 - Rajesh Gowda
 -- Added new group pdnCardGeneralParams
 --
 -- 10/29/98 - Rajesh Gowda
 -- 1. Added an object to pdnClientConfigTable
 --    a. pdnClientConfigSubnetMask
 -- 2. Changed all instances of the name VLAN (virtual LAN) 
 --    to VNID (virtual network ID)
 -- 
 --  10/20/99 Wayne Jadoo
 --  removed the mib-2 import and 
 --  imported ent-8800 from PDN-HEADER-MIB

 IMPORTS
    IpAddress
     FROM RFC1155-SMI
      DisplayString
     FROM RFC1213-MIB
    OBJECT-TYPE
     FROM RFC-1212
    ent-8800
     FROM PDN-HEADER-MIB;


 -- A 6 octet address in the "canonical" order

   MacAddress ::= OCTET STRING (SIZE (6))

   pdnDomain   OBJECT IDENTIFIER ::= { ent-8800 6 }


 -- groups for Domain MIB

	pdnCardConfig     OBJECT IDENTIFIER ::= { pdnDomain 1 }

	pdnPortConfig     OBJECT IDENTIFIER ::= { pdnDomain 2 }

	pdnClientConfig   OBJECT IDENTIFIER ::= { pdnDomain 3 }

	pdnCardGeneralParams  OBJECT IDENTIFIER ::= { pdnDomain 4 }

 -- CardTable group

 -- The Card Configuration Table

          pdnCardConfigTable OBJECT-TYPE
              SYNTAX  SEQUENCE OF PdnCardConfigEntry
              ACCESS  not-accessible
              STATUS  mandatory
              DESCRIPTION
                      "A table that contains information about
 	       Mux Forwarding, IP Filtering, IP Scoping 
 	       and domain name for each VNID."
              ::= { pdnCardConfig 1 }

          pdnCardConfigEntry OBJECT-TYPE
              SYNTAX  PdnCardConfigEntry
              ACCESS  not-accessible
              STATUS  mandatory
              DESCRIPTION
                      "A list of configuration information for each VNID."
              INDEX  { pdnCardConfigVnidId }
              ::= { pdnCardConfigTable 1 }


          PdnCardConfigEntry ::=
              SEQUENCE {
                  pdnCardConfigVnidId
                      INTEGER,
                  pdnCardConfigDomainName
                      DisplayString,
                  pdnCardConfigMuxFwd
                      INTEGER,
                  pdnCardConfigIPFiltering
                      INTEGER,
                  pdnCardConfigIPScoping
                      INTEGER,
                  pdnCardConfigDbUpdate
                      INTEGER
              }

          pdnCardConfigVnidId OBJECT-TYPE
              SYNTAX  INTEGER (1..4096)	-- VNID Id range 1..4094, null=4096
              ACCESS  read-write
              STATUS  mandatory
              DESCRIPTION
                      "The VNID Id number of the virtual network for which this entry
                      contains management information.
 	      'null' is used to create a new entry for MIB
 	      browsers which cannot create new entry but can
 	      only edit existing entry."
              ::= { pdnCardConfigEntry 1 }

          pdnCardConfigDomainName OBJECT-TYPE
              SYNTAX  DisplayString
              ACCESS  read-write
              STATUS  mandatory
              DESCRIPTION
                      "The Domain name of the ISP for this VNID."
              ::= { pdnCardConfigEntry 2 }

          pdnCardConfigMuxFwd OBJECT-TYPE
              SYNTAX  INTEGER { enable (1), disable (2) }
              ACCESS  read-write
              STATUS  mandatory
              DESCRIPTION
                      "This object shows if Mux Forwarding has been
 	      enabled or disabled by the user."
              ::= { pdnCardConfigEntry 3 }

          pdnCardConfigIPFiltering OBJECT-TYPE
              SYNTAX  INTEGER { enable (1), disable (2) }
              ACCESS  read-write
              STATUS  mandatory
              DESCRIPTION
                      "This object shows if IP Filtering has been
 	      enabled or disabled by the user."
              ::= { pdnCardConfigEntry 4 }

          pdnCardConfigIPScoping OBJECT-TYPE
              SYNTAX  INTEGER { enable (1), disable (2) }
              ACCESS  read-write
              STATUS  mandatory
              DESCRIPTION
                      "This object shows if IP Scoping has been
 	      enabled or disabled by the user."
              ::= { pdnCardConfigEntry 5 }

 --
 -- pdnCardConfigDbUpdate object has been added to facilitate
 -- setting of the index of this table (VNID Id).
 -- When "nop" is used in set PDU, no setting is done and "nop" is
 -- returned in the response PDU.
 -- When a new VNID needs to be added, the value will be set to 
 -- "update" in the set PDU. 
 -- When a VNID entry needs to be deleted, "delete" will be used in 
 -- the set PDU.
 --
 -- NOTE: The set PDU for the object pdnCardConfigDbUpdate must
 -- be sent after all other set PDU's have been sent for this table.
 --

          pdnCardConfigDbUpdate OBJECT-TYPE
              SYNTAX  INTEGER { nop (1), update (2), delete (3) }
              ACCESS  read-write
              STATUS  mandatory
              DESCRIPTION
                      "This object is used to control the setting
 	       of the objects in this table. When 'nop' is received,
 	       no objects are set. When 'update' is received, all
 	       objects in this table for which set PDU have been
 	       received prior to this set PDU will be set and a
 	       new entry will be created if the index does not exist.
 	       When 'delete' is received, the entry with the index 
 	       value will be deleted."
              ::= { pdnCardConfigEntry 6 }



 -- pdnPortConfig group
 -- The Port Configuration Table


          pdnPortConfigTable OBJECT-TYPE
              SYNTAX  SEQUENCE OF PdnPortConfigEntry
              ACCESS  not-accessible
              STATUS  mandatory
              DESCRIPTION
                      "A table that contains VNID configuration information
 	       for each port."
              ::= { pdnPortConfig 1 }

          pdnPortConfigEntry OBJECT-TYPE
              SYNTAX  PdnPortConfigEntry
              ACCESS  not-accessible
              STATUS  mandatory
              DESCRIPTION
                      "A list of configuration information for each port."
              INDEX  { pdnPortConfigVNID, pdnPortConfigIfIndex }
              ::= { pdnPortConfigTable 1 }


          PdnPortConfigEntry ::=
              SEQUENCE {
                  pdnPortConfigVNID
                      INTEGER,
                  pdnPortConfigIfIndex
                      INTEGER,
                  pdnPortConfigCfg
                      INTEGER,
                  pdnPortConfigDefNHR
                      IpAddress,
                  pdnPortConfigMode
                      INTEGER
              }

          pdnPortConfigVNID OBJECT-TYPE
              SYNTAX  INTEGER (1..4094)
              ACCESS  read-only
              STATUS  mandatory
              DESCRIPTION
                      "The VNID Id number of the virtual network for which this entry
                      contains management information."
              ::= { pdnPortConfigEntry 1 }

          pdnPortConfigIfIndex OBJECT-TYPE
              SYNTAX  INTEGER
              ACCESS  read-only
              STATUS  mandatory
              DESCRIPTION
                      "The value of the instance of the ifIndex object, defined
 	       in MIB-II, for the interface corresponding to this port."
              ::= { pdnPortConfigEntry 2 }

          pdnPortConfigCfg OBJECT-TYPE
              SYNTAX  INTEGER { activate (1), de-activate (2) }
              ACCESS  read-write
              STATUS  mandatory
              DESCRIPTION
                      "This object shows if this VNID has been made
 	      active or de-active for this port by the user."
              ::= { pdnPortConfigEntry 3 }

          pdnPortConfigDefNHR OBJECT-TYPE
              SYNTAX  IpAddress
              ACCESS  read-write
              STATUS  mandatory
              DESCRIPTION
                      "The Default Next Hop Router address for the
 	       specified VNID and port."
              ::= { pdnPortConfigEntry 4 }

          pdnPortConfigMode OBJECT-TYPE
              SYNTAX  INTEGER { implicit (1), explicit (2), no-tagging (3)}
              ACCESS  read-write
              STATUS  mandatory
              DESCRIPTION
                      "This object shows the configuration mode for this VNID and 
 	      for this port."
              ::= { pdnPortConfigEntry 5 }


 -- pdnClientConfig group
 -- The Client Configuration Table


          pdnClientConfigTable OBJECT-TYPE
              SYNTAX  SEQUENCE OF PdnClientConfigEntry
              ACCESS  not-accessible
              STATUS  mandatory
              DESCRIPTION
                      "A table that contains configuration information
 	       for each client."
              ::= { pdnClientConfig 1 }

          pdnClientConfigEntry OBJECT-TYPE
              SYNTAX  PdnClientConfigEntry
              ACCESS  not-accessible
              STATUS  mandatory
              DESCRIPTION
                      "A list of configuration information for each client."
              INDEX  { pdnClientConfigIfIndex, pdnClientConfigClientIndex }
              ::= { pdnClientConfigTable 1 }


          PdnClientConfigEntry ::=
              SEQUENCE {
                  pdnClientConfigIfIndex
                      INTEGER,
                  pdnClientConfigClientIndex
                      INTEGER,
                  pdnClientConfigAddr
                      IpAddress,
                  pdnClientConfigNHR
                      IpAddress,
                  pdnClientConfigVnidId
                      INTEGER,
                  pdnClientConfigType
                      INTEGER,
                  pdnClientConfigLeaseTime
                      INTEGER,
                  pdnClientConfigLeaseRemainTime
                      INTEGER,
                  pdnClientConfigMacAddr
                      MacAddress,
                  pdnClientConfigSubnetMask
                      IpAddress
              }

          pdnClientConfigIfIndex OBJECT-TYPE
              SYNTAX  INTEGER
              ACCESS  read-only
              STATUS  mandatory
              DESCRIPTION
                      "The ifIndex of the port for which this entry
                      contains management information."
              ::= { pdnClientConfigEntry 1 }

          pdnClientConfigClientIndex OBJECT-TYPE
              SYNTAX  INTEGER (1..32)
              ACCESS  read-only
              STATUS  mandatory
              DESCRIPTION
                      "The Client index of the Client for which this entry
                      contains management information."
              ::= { pdnClientConfigEntry 2 }

          pdnClientConfigAddr OBJECT-TYPE
              SYNTAX  IpAddress
              ACCESS  read-write
              STATUS  mandatory
              DESCRIPTION
                      "The IP address of the client specified by the client id."
              ::= { pdnClientConfigEntry 3 }

          pdnClientConfigNHR OBJECT-TYPE
              SYNTAX  IpAddress
              ACCESS  read-write
              STATUS  mandatory
              DESCRIPTION
                      "The Next Hop Router address for the client
 	       specified by the client index."
              ::= { pdnClientConfigEntry 4 }

          pdnClientConfigVnidId OBJECT-TYPE
              SYNTAX  INTEGER (1..4094)
              ACCESS  read-only
              STATUS  mandatory
              DESCRIPTION
                      "The VNID Id number of the Client for which this
                      client is configured."
              ::= { pdnClientConfigEntry 5 }

          pdnClientConfigType OBJECT-TYPE
              SYNTAX  INTEGER { static (1), dynamic (2) }
              ACCESS  read-only
              STATUS  mandatory
              DESCRIPTION
                      "The Configuration type of this entry -
 	       Static or Dynamic."
              ::= { pdnClientConfigEntry 6 }

          pdnClientConfigLeaseTime OBJECT-TYPE
              SYNTAX  INTEGER
              ACCESS  read-only
              STATUS  mandatory
              DESCRIPTION
                      "The Lease Time in seconds for this client."
              ::= { pdnClientConfigEntry 7 }

          pdnClientConfigLeaseRemainTime OBJECT-TYPE
              SYNTAX  INTEGER
              ACCESS  read-only
              STATUS  mandatory
              DESCRIPTION
                      "The Lease Remaining Time in seconds for this client."
              ::= { pdnClientConfigEntry 8 }

          pdnClientConfigMacAddr OBJECT-TYPE
              SYNTAX  MacAddress
              ACCESS  read-only
              STATUS  mandatory
              DESCRIPTION
                      "The MAC Address of the client."
              ::= { pdnClientConfigEntry 9 }

          pdnClientConfigSubnetMask OBJECT-TYPE
              SYNTAX  IpAddress
              ACCESS  read-only
              STATUS  mandatory
              DESCRIPTION
                      "The subnet mask of the client."
              ::= { pdnClientConfigEntry 10 }

 
 -- pdnCardGeneralParams group
 -- This group reflect the status of VNID tagging.
 
          pdnCardGeneralParamsVNIDMode  OBJECT-TYPE
              SYNTAX  INTEGER { 
                enable (1), 
                disable (2) 
              }
              ACCESS  read-write
              STATUS  mandatory
              DESCRIPTION
                      "The state of VNID tagging on the card."
              ::= { pdnCardGeneralParams 1 }

END
