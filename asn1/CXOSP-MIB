CXOSP-MIB DEFINITIONS ::= BEGIN


IMPORTS
-- used for autovlink
-- Status               FROM RFC1253-MIB  
   Validation, AreaID   FROM RFC1253-MIB
   OBJECT-TYPE          FROM RFC-1212
   cxOSP                FROM CXProduct-SMI;
-- This MIB module is used to define non standard MIB objects for OSPF
-- Standard mib rfc1253 is extended by these objects to allow proprietary
-- features such as area deletion (ospAreaStatus).
-- Note that area deletion is supported in rfc1580 (next OSPF MIB version)
-- and will no longer be required when the new standard is supported. Note
-- also that the object name ospAreaStatus has been used instead of 
-- ospfAreaStatus, which is used in rfc1580, to allow distinction.
   
     ospAreaTable OBJECT-TYPE
         SYNTAX   SEQUENCE OF OspAreaEntry
         ACCESS   not-accessible
         STATUS   mandatory
         DESCRIPTION
"Information describing the configured parameters and cumulative statistics 
of the router's attached areas."

         REFERENCE
            "OSPF Version 2, Section 6  The Area Data Structure"
         ::= { cxOSP 1 }

     ospAreaEntry OBJECT-TYPE
         SYNTAX   OspAreaEntry
         ACCESS   not-accessible
         STATUS   mandatory
         DESCRIPTION
"Information describing the configured parameters and cumulative statistics 
of one of the router's attached areas."

         INDEX { ospAreaId }
         ::= { ospAreaTable 1 }

     OspAreaEntry ::=
         SEQUENCE {
             ospAreaId
                 AreaID,
             ospAreaStatus
                 Validation
         }

     ospAreaId OBJECT-TYPE
         SYNTAX   AreaID
         ACCESS   read-write
         STATUS   mandatory
         DESCRIPTION
"A 32-bit integer uniquely identifying an area.  Area ID 0.0.0.0 is used 
for the OSPF backbone."

         REFERENCE
            "OSPF Version 2, Appendix C.2 Area parameters"
         ::= { ospAreaEntry 1 }

     ospAreaStatus OBJECT-TYPE
         SYNTAX   Validation
         ACCESS   read-write
         STATUS   mandatory
         DESCRIPTION
"This variable displays the validity or invalidity of the ospfAreaEntry 
entry (refer to rfc1253).  Setting it to 'invalid' has the effect of 
rendering it inoperative.  The internal effect (row removal) is 
implementation dependent."

         DEFVAL   { valid }
         ::= { ospAreaEntry 2 }

END
