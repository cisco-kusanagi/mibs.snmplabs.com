RFC1406Ext-MIB DEFINITIONS ::= BEGIN

--#CURRENT_VERSION 1

IMPORTS
	TimeTicks      FROM RFC1155-SMI
   OBJECT-TYPE    FROM RFC-1212

--  Proprietary Imports
     cxDSX1Ext   FROM CXProduct-SMI;


dsx1ExtMibLevel OBJECT-TYPE
   	SYNTAX	INTEGER
   	ACCESS	read-only
   	STATUS	mandatory
   	DESCRIPTION
      "Used to determine current MIB module release supported
      by the agent. Object is in decimal."
   	DEFVAL { 0 }
   	--#STARTING_VERSION 1
   	::= { cxDSX1Ext 1 }

dsx1ExtCfgTable      OBJECT-TYPE
		SYNTAX    SEQUENCE OF Dsx1ExtCfgEntry
		ACCESS    not-accessible
		STATUS    mandatory
		DESCRIPTION
		"The T1/E1 extensions configuration table."
		::= { cxDSX1Ext 10 }


dsx1ExtCfgEntry	 OBJECT-TYPE
		SYNTAX Dsx1ExtCfgEntry
		ACCESS    not-accessible
		STATUS    mandatory
		DESCRIPTION
		"An entry in the T1/E1 extensions configuration table."
		INDEX { dsx1ExtCfgLinkIndex }
		::= { dsx1ExtCfgTable 1 }

 Dsx1ExtCfgEntry	::=
		SEQUENCE {
		-- Parameters
			dsx1ExtCfgLinkIndex 			   INTEGER,

         dsx1ExtCfgPortStatus          INTEGER,
			dsx1ExtCfgTraps               INTEGER,
			dsx1ExtCfgLineBuildOut        INTEGER,
      -- Status
			dsx1ExtCfgCardType            INTEGER,
			dsx1ExtCfgLossTxClock         TimeTicks,
			dsx1ExtCfgLossSync            TimeTicks,
			dsx1ExtCfgLossCarrier         TimeTicks,
			dsx1ExtCfgT18ZeroDetect       TimeTicks,
			dsx1ExtCfgT116ZeroDetect      TimeTicks,
			dsx1ExtCfgT1RxB8ZSCode        TimeTicks,
			dsx1ExtCfgT1RxBlueAlarm       TimeTicks,
			dsx1ExtCfgT1RxYellowAlarm     TimeTicks,
			dsx1ExtCfgIoRegTest           INTEGER,
			dsx1ExtCfgSctRegTest          INTEGER,
			dsx1ExtCfgSctLatchRegTest     INTEGER,
-- Statistics
-- Controls
			dsx1ExtCfgReinit              INTEGER
         
			} 

dsx1ExtCfgLinkIndex 	OBJECT-TYPE
		SYNTAX    INTEGER (1..2)
		ACCESS    read-only
		STATUS    mandatory
		DESCRIPTION
		"Identifies the physical port with the T1/E1 (dsx1Ext) interface.

		Range of Values: 1 - 2

		Default Value: None

		Configuration Changed: administrative"
		::= { dsx1ExtCfgEntry  1 }


dsx1ExtCfgPortStatus        OBJECT-TYPE
		SYNTAX    INTEGER { disabled  (1),
							enabled   (2)
						  }
		ACCESS    read-write
		STATUS    mandatory
		DESCRIPTION
		"Indicates whether this T1/E1 (dsx1Ext) port is enabled or 
		disabled.

		Options:
		disabled (1): The port is physically present but will be
		disabled (deactivated) after the next reset.

		enabled (2): The port will become enabled (functional) after
		the next reset.

		Default Value: disabled (1)

		Configuration Changed: administrative"
		DEFVAL { disabled }
      --#STARTING_VERSION 1
		::= { dsx1ExtCfgEntry 10 }


dsx1ExtCfgTraps 	OBJECT-TYPE
		SYNTAX    INTEGER { disabled  (1),
				enabled   (2)
			}
		ACCESS    read-write
		STATUS    mandatory
		DESCRIPTION
		"Determines whether the software will produce a T1/E1 (dsx1...) 
		trap.
		
		Options:
		disabled (1):  The trap will not be produced.
		
		enabled (2):  The trap will be generated.
		
		Default Value:  disabled (1)
		
		Configuration Changed: administrative"
		DEFVAL { disabled }
      --#STARTING_VERSION 1
		::= { dsx1ExtCfgEntry 11 }


dsx1ExtCfgLineBuildOut 	OBJECT-TYPE
	SYNTAX    INTEGER (1..8)
		ACCESS    read-write
		STATUS    mandatory
		DESCRIPTION
		"Specifies the attenuation or Line Build Out to be used 
		on the transmitter side of the line. 
		
		Options:
		For T1
		1: 0 to 133 feet / 0 dB
		
		2: 133 to 266 feet
		
		3: 266 to 399 feet
		
		4: 399 to 533 feet
		
		5: 533 to 655 feet
		
		6: -7.5 dB
		
		7: -15 dB
		
		8: -22.5 dB
		
		For E1
		
		1: 75 Ohm (coax. cable)
		
		2: 120 Ohm (RJ45 shilded twisted pair)
		
		3: 75 Ohm ( with protection resistor)
		
		4: 120 Ohm ( with protection resistor)
		
		5: 75 Ohm (with high return loss 1:1.15)
		
		6: 120 Ohm (with high return loss 1:1.36)
		
		7: 75 Ohm (with high return loss 1:1.36)
		
		8: N/A
		
		
		Default Value: 1
		
		Configuration Changed: administrative"
		DEFVAL { 3 }
      --#STARTING_VERSION 1
		::= { dsx1ExtCfgEntry 12 }


dsx1ExtCfgCardType          OBJECT-TYPE
	SYNTAX    INTEGER { dsx1ExtNoCard (1),
					dsx1ExtT1Card (2),
					dsx1ExtE1Card (3)
			}
		ACCESS    read-only
		STATUS    mandatory
		DESCRIPTION
"Indicates the type of card connected to this CPU board.

Options:
dsx1ExtNoCard (1): Indicates that there is not a T1 or E1 card
connected to the line interface or the value indicates that if
there is a T1 or E1 card connected then the card is not
functional.

dsx1ExtT1Card (2): Indicates that a functional T1 card is connected
to the line interface.

dsx1ExtE1Card (3): Indicates that a functional E1 card is connected
to the line interface."
      --#STARTING_VERSION 1
		::= { dsx1ExtCfgEntry  50 }


dsx1ExtCfgLossTxClock       OBJECT-TYPE
	SYNTAX    TimeTicks
		ACCESS    read-only
		STATUS    mandatory
		DESCRIPTION
"Indicates the total time at which the transmit clock was
lost on this line interface. If no such event has occurred since
system startup, then the value will be zero."
      --#STARTING_VERSION 1
		::= { dsx1ExtCfgEntry  51 }


dsx1ExtCfgLossSync          OBJECT-TYPE
	SYNTAX    TimeTicks
		ACCESS    read-only
		STATUS    mandatory
		DESCRIPTION
"Indicates the total time at which the synchronization was
lost on this line interface. If no such event has occurred since
system startup, then the value will be zero."
      --#STARTING_VERSION 1
		::= { dsx1ExtCfgEntry  52 }


dsx1ExtCfgLossCarrier       OBJECT-TYPE
	SYNTAX    TimeTicks
		ACCESS    read-only
		STATUS    mandatory
		DESCRIPTION
"Indicates the total time at which the carrier was lost
on this line interface. If no such event has occurred since
system startup, then the value will be zero."
      --#STARTING_VERSION 1
		::= { dsx1ExtCfgEntry  53 }


dsx1ExtCfgT18ZeroDetect          OBJECT-TYPE
	SYNTAX    TimeTicks
		ACCESS    read-only
		STATUS    mandatory
		DESCRIPTION
"Indicates the total time that 8 consecutive zeros were received on 
this line interface. If no such event has occurred since system startup, 
then the value will be zero."
      --#STARTING_VERSION 1
		::= { dsx1ExtCfgEntry  54 }


dsx1ExtCfgT116ZeroDetect         OBJECT-TYPE
	SYNTAX    TimeTicks
		ACCESS    read-only
		STATUS    mandatory
		DESCRIPTION
"Indicates the total time that 16 consecutive zeros were
received on this line interface. If no such event has occurred
since system startup, then the value will be zero."
      --#STARTING_VERSION 1
		::= { dsx1ExtCfgEntry  55 }


dsx1ExtCfgT1RxB8ZSCode      OBJECT-TYPE
	SYNTAX    TimeTicks
		ACCESS    read-only
		STATUS    mandatory
		DESCRIPTION
"Indicates the total time that a B8ZS code word was
detected during reception on this line interface. If no such
event has occurred since system startup, then the value will be
zero.

Note: B8ZS code work detection occurs whether or not the B8ZS
mode is selected."
      --#STARTING_VERSION 1
		::= { dsx1ExtCfgEntry  56 }


dsx1ExtCfgT1RxBlueAlarm          OBJECT-TYPE
	SYNTAX    TimeTicks
		ACCESS    read-only
		STATUS    mandatory
		DESCRIPTION
"Indicates the total time that a 'blue alarm' was received
on this line interface. A blue alarm is an unframed signal
comprised of all ones (1s). If no such event has occurred
since system startup, then the value will be zero."
      --#STARTING_VERSION 1
		::= { dsx1ExtCfgEntry  57 }


dsx1ExtCfgT1RxYellowAlarm   OBJECT-TYPE
	SYNTAX    TimeTicks
		ACCESS    read-only
		STATUS    mandatory
		DESCRIPTION
"Indicates the total time that a 'yellow alarm' was
received on this line interface. A yellow alarm occurs when bit
2 of 256 consecutive channels is set to zero for at least 254
occurrences in D4 format mode or when 16 consecutive patterns of
00FF hex appear in FDL format mode. If no such event has occurred
since system startup, then the value will be zero."
      --#STARTING_VERSION 1
		::= { dsx1ExtCfgEntry  58 }


	dsx1ExtCfgIoRegTest    OBJECT-TYPE
		SYNTAX    INTEGER {
					failed              (1),
					passed              (2)
				}
		ACCESS    read-only
		STATUS    mandatory
		DESCRIPTION
"Indicates the test results for the T1/E1 I/O card registers."
      --#STARTING_VERSION 1
		::= { dsx1ExtCfgEntry  59 }


	dsx1ExtCfgSctRegTest        OBJECT-TYPE
		SYNTAX    INTEGER {
					failed              (1),
					passed              (2)
				}
		ACCESS    read-only
		STATUS    mandatory
		DESCRIPTION
"Indicates the test results for the T1 transceiver registers,
specifically the 12 Transmit Signaling Registers."
      --#STARTING_VERSION 1
		::= { dsx1ExtCfgEntry  60 }


	dsx1ExtCfgSctLatchRegTest   OBJECT-TYPE
		SYNTAX    INTEGER {
					failed                   (1),
					passed                   (2)
				}
		ACCESS    read-only
		STATUS    mandatory
		DESCRIPTION
"Indicates the test results for the T1 transceiver latch register,
specifically the second Status Register."
      --#STARTING_VERSION 1
		::= { dsx1ExtCfgEntry  61 }


dsx1ExtCfgReinit            OBJECT-TYPE
	SYNTAX    INTEGER
		ACCESS    write-only
		STATUS    mandatory
		DESCRIPTION
"When this object is set to any value, it reinitializes the 
corresponding port."
      --#STARTING_VERSION 1
		::= { dsx1ExtCfgEntry  81 }



END
