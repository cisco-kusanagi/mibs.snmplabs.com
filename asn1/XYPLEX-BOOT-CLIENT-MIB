-- Converted Xyplex Bootstrap Clients MIB
--   the 22 May 1991 version, Xyplex Document Number 420-0537-A

-- Changes:
--      Changed RFC1158-MIB to RFC1213-MIB.
--      Changed RFC1212-CONCISE-MIB to RFC-1212.
--      Removed redefinition of xyplex and added IMPORT instead.
--      Removed import for enterprises.


                    XYPLEX-BOOT-CLIENT-MIB DEFINITIONS ::= BEGIN

                    IMPORTS
                            DisplayString
                                    FROM RFC1213-MIB
                            OBJECT-TYPE
                                    FROM RFC-1212
                            xyplex
                                    FROM XYPLEX-SYSTEM-MIB;

            bootClient      OBJECT IDENTIFIER ::= { xyplex 12 }

            --  This MIB module uses the extended OBJECT-TYPE macro as
            --  defined in [9]
            --  this is the MIB module for clients of Xyplex bootstrap
            --  service
            -- the Bootstrap Client group
            -- Implementation of this group is mandatory for all Xyplex
            -- systems that use the Xyplex bootstrap service

            bootClientStatus OBJECT-TYPE
                SYNTAX DisplayString (SIZE (0..1400))
                ACCESS read-only
                STATUS mandatory
                DESCRIPTION
                    "The overall status of the bootstrapping operation, 
                    including, for example, what is presently happening 
                    and error information."
                ::= { bootClient 1 }

            END
