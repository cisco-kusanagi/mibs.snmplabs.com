RSI_-01-PCREMOTESTATUSIND-MIB DEFINITIONS ::= BEGIN

--
-- SST RSI_-01-PCREMOTESTATUSIND MIB
--

IMPORTS
    enterprises, Counter
        FROM RFC1155-SMI
    OBJECT-TYPE
        FROM RFC-1212
    DisplayString
        FROM RFC-1213
    TruthValue
            FROM RFC1253-MIB
    sstDevice, VerificationState
            FROM NCR-CORESST-MIB;

        rsi_-01-PcRemoteStatusInd    OBJECT IDENTIFIER ::= { sstDevice 30 }
        devObjs                 OBJECT IDENTIFIER ::= { rsi_-01-PcRemoteStatusInd 1 }
        srvObjs                 OBJECT IDENTIFIER ::= { rsi_-01-PcRemoteStatusInd 4 }

-----------------------------------------------------------
-- Device Service Miscellaneous Definitions
-----------------------------------------------------------
Reset              ::= INTEGER   { reset              (1) }


-----------------------------------------------------------
-- SST Device - RSI_-01-PcRemoteStatusInd
-----------------------------------------------------------

devManufacturer OBJECT-TYPE
	SYNTAX DisplayString
	ACCESS read-only
	STATUS optional
	DESCRIPTION 
	"The name of the manufacturer of the product."
	::= { devObjs 1 }

devProduct OBJECT-TYPE
	SYNTAX DisplayString
	ACCESS read-only
	STATUS optional    
	DESCRIPTION 
	"This attribute does not apply to SST devices."
	::= { devObjs 2 }

devVersion OBJECT-TYPE
	SYNTAX DisplayString
	ACCESS read-only
	STATUS optional    
	DESCRIPTION 
	"This attribute does not apply to SST devices."
	::= { devObjs 3 }

devSerialNo OBJECT-TYPE
	SYNTAX DisplayString
	ACCESS read-write
	STATUS optional    
	DESCRIPTION 
	"This attribute does not apply to SST devices."
	::= { devObjs 4 }

devInstallation OBJECT-TYPE
	SYNTAX DisplayString
	ACCESS read-only
	STATUS optional    
	DESCRIPTION 
	"The date and time, in DMI-defined format, when the component was (last) installed." 
	::= { devObjs 5 }

devVerify OBJECT-TYPE
	SYNTAX VerificationState
	ACCESS read-only
	STATUS optional    
	DESCRIPTION 
	"A level of verification that the device software is installed and functioning.
	This attribute is not currently supported."
	::= { devObjs 6 }

devName OBJECT-TYPE
	SYNTAX DisplayString
	ACCESS read-only
	STATUS mandatory    
	DESCRIPTION 
	"The unique, platform-defined name of the device."
	::= { devObjs 7 }

devShortDesc OBJECT-TYPE
	SYNTAX DisplayString
	ACCESS read-only
	STATUS mandatory    
	DESCRIPTION 
	"The platform-defined short description of the device."
	::= { devObjs 8 }

devLongDesc OBJECT-TYPE
	SYNTAX DisplayString
	ACCESS read-only
	STATUS mandatory    
	DESCRIPTION 
	"The platform-defined long description of the device."
	::= { devObjs 9 }

devUniversalId OBJECT-TYPE
	SYNTAX INTEGER
	ACCESS read-only
	STATUS mandatory    
	DESCRIPTION 
	"The unique, platform-defined identifier for the type of device."
	::= { devObjs 10 }

devVariant OBJECT-TYPE
	SYNTAX INTEGER
	ACCESS read-only
	STATUS mandatory    
	DESCRIPTION 
	"The identifier for the specific hardware configuration of the device, indicating what hardware the device has."
	::= { devObjs 11 }

devSummaryState OBJECT-TYPE
	SYNTAX ModuleState
	ACCESS read-only
	STATUS mandatory    
	DESCRIPTION 
	"The summary state of the device indicating the state of the device's least healthy module."
	::= { devObjs 12 }

-- SST End of Device Info

-----------------------------------------------------------
-- SST Service Table
-----------------------------------------------------------

srvServiceTable OBJECT-TYPE
	SYNTAX  SEQUENCE OF SrvServiceEntry
	ACCESS  not-accessible
	STATUS  mandatory
	DESCRIPTION                        
	"This group defines the attributes of the services associated with the device.."
	::= { srvObjs 1 }

srvServiceEntry OBJECT-TYPE
	SYNTAX  SrvServiceEntry
	ACCESS not-accessible
	STATUS  mandatory
	DESCRIPTION
	"This defines the contents of the table."
	INDEX   { srvServiceIndex }
	::= { srvServiceTable 1 }

SrvServiceEntry ::=
	SEQUENCE { 
		  srvServiceIndex        DisplayString,
		  srvServiceVariant      INTEGER,
		  srvServiceState        OCTET STRING,
		  srvServiceMaintenance  OCTET STRING,
		  srvServiceReplenishment OCTET STRING,
		  srvServiceClearState   Reset,
	      srvServiceClearTallies Reset
          }

srvServiceIndex OBJECT-TYPE
	SYNTAX DisplayString
	ACCESS read-only
	STATUS mandatory    
	DESCRIPTION 
	"A unique, platform-defined name for each service."
	::= { srvServiceEntry 1 }

srvServiceVariant OBJECT-TYPE
	SYNTAX INTEGER
	ACCESS read-only
	STATUS mandatory    
	DESCRIPTION 
	"The current configuration of the service, indicating the additional transaction facilities available to the transaction application."
	::= { srvServiceEntry 2 }

srvServiceState OBJECT-TYPE
	SYNTAX OCTET STRING
	ACCESS read-only
	STATUS mandatory    
	DESCRIPTION 
	"This indicates the current level of availability of the service parts to the transaction application."
	::= { srvServiceEntry 3 }

srvServiceMaintenance OBJECT-TYPE
	SYNTAX OCTET STRING
	ACCESS read-only
	STATUS mandatory    
	DESCRIPTION 
	"Maintenance information associated with the last state change in the service: M-Code, M-Status and M-Data."
	::= { srvServiceEntry 4 }

srvServiceReplenishment OBJECT-TYPE
	SYNTAX OCTET STRING
	ACCESS read-only
	STATUS mandatory    
	DESCRIPTION 
	"Replenishment status data associated with the last state change in the service: RS-Data."
	::= { srvServiceEntry 5 }

srvServiceClearState OBJECT-TYPE
	SYNTAX Reset
	ACCESS write-only
	STATUS mandatory    
	DESCRIPTION 
	"Setting the value of this attribute clears all parts of the service to a good (fully functioning and available) state, but does not guarantee that the fault has been cleared."
	::= { srvServiceEntry 6 }

srvServiceClearTallies OBJECT-TYPE
	SYNTAX Reset
	ACCESS write-only
	STATUS mandatory    
	DESCRIPTION 
	"Setting the value of this attribute clears all tallies supported by the service."
	::= { srvServiceEntry 7 }
	    

-----------------------------------------------------------
-- SST Service Tallies Table
-----------------------------------------------------------

srvServiceTallyTable OBJECT-TYPE
	SYNTAX  SEQUENCE OF SrvServiceTallyEntry
	ACCESS  not-accessible
	STATUS  mandatory
	DESCRIPTION                        
	"This group defines the attributes of the counters supported by the device service to record the operations, usage and performance of the device it manages."
	::= { srvObjs 2 }

srvServiceTallyEntry OBJECT-TYPE
	SYNTAX  SrvServiceTallyEntry
	ACCESS  not-accessible
	STATUS  mandatory
	DESCRIPTION
	"This defines the contents of the table."
	INDEX   { srvServiceNameIndex, 
		  srvServiceTallyIndex }
	::= { srvServiceTallyTable 1 }

SrvServiceTallyEntry ::=
	SEQUENCE { 
		  srvServiceNameIndex          DisplayString,
		  srvServiceTallyIndex         INTEGER,
		  srvServiceTallyName          DisplayString,
		  srvServiceTallyValue         Counter
		}

srvServiceNameIndex OBJECT-TYPE
	SYNTAX DisplayString
	ACCESS read-only
	STATUS mandatory    
	DESCRIPTION 
	"A unique name for each service."
	::= { srvServiceTallyEntry 1 }

srvServiceTallyIndex OBJECT-TYPE
	SYNTAX INTEGER
	ACCESS read-only
	STATUS mandatory    
	DESCRIPTION 
	"A unique number for each tally."
	::= { srvServiceTallyEntry 2 }

srvServiceTallyName OBJECT-TYPE
	SYNTAX DisplayString
	ACCESS read-only
	STATUS mandatory    
	DESCRIPTION 
	"A description of the tally."
	::= { srvServiceTallyEntry 3 }

srvServiceTallyValue OBJECT-TYPE
	SYNTAX Counter
	ACCESS read-only
	STATUS mandatory    
	DESCRIPTION 
	"The current value of the tally."
	::= { srvServiceTallyEntry 4 }
END
