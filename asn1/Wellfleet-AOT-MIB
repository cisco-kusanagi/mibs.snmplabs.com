Wellfleet-AOT-MIB DEFINITIONS ::= BEGIN

-- Created by mdl2asn version 3.1
-- Creation date: Wed Sep  6 16:57:28 EDT 1995
-- Edited by sbasu 

    IMPORTS

      IpAddress, Counter 
        FROM RFC1155-SMI
      OBJECT-TYPE
        FROM RFC-1212
      wfAsyncOverTcpGroup
        FROM Wellfleet-COMMON-MIB;


    wfAot		OBJECT IDENTIFIER ::= { wfAsyncOverTcpGroup 1 }

    wfAotDelete OBJECT-TYPE
        SYNTAX	INTEGER {
    		    created(1),
    		    deleted(2)
    		}
        ACCESS	read-write
        STATUS	mandatory
        DESCRIPTION
                "Create/Delete parameter. Default is created.
                User perform an SNMP SET operation on this object
                in order to create/delete AOT"
        DEFVAL	{ created }
        ::= { wfAot 1 }

    wfAotDisable OBJECT-TYPE
        SYNTAX	INTEGER {
    		    enabled(1),
    		    disabled(2)
    		}
        ACCESS	read-write
        STATUS	mandatory
        DESCRIPTION
                "Enable/Disable parameter. Default is enabled.
                User perform an SNMP SET operation on this object
                in order to enable/disable AOT"
        DEFVAL	{ enabled }
        ::= { wfAot 2 }

    wfAotState OBJECT-TYPE
        SYNTAX	INTEGER {
    		    up(1),
    		    down(2),
    		    init(3),
    		    notpresent(4)
    		}
        ACCESS	read-only
        STATUS	mandatory
        DESCRIPTION
                "The current state of AOT"
        DEFVAL	{ down }
        ::= { wfAot 3 }

    wfAotInterfaceTable OBJECT-TYPE
        SYNTAX	SEQUENCE OF WfAotInterfaceEntry
        ACCESS	not-accessible
        STATUS	mandatory
        DESCRIPTION
                "Interface table which lists all PASYNC line entries and other
                line related information"
        ::= { wfAsyncOverTcpGroup 2 }

    wfAotInterfaceEntry OBJECT-TYPE
        SYNTAX	WfAotInterfaceEntry
        ACCESS	not-accessible
        STATUS	mandatory
        DESCRIPTION
                "An entry in wfAotInterfaceTable"
        INDEX	{ wfAotInterfaceSlotNumber,
    		  wfAotInterfaceCctNumber }
        ::= { wfAotInterfaceTable 1 }

    WfAotInterfaceEntry ::= SEQUENCE {
    	    wfAotInterfaceDelete
    		INTEGER,
    	    wfAotInterfaceDisable
    		INTEGER,
    	    wfAotInterfaceCctNumber
    		INTEGER,
    	    wfAotInterfaceSlotNumber
    		INTEGER,
    	    wfAotInterfaceState
    		INTEGER,
    	    wfAotInterfaceType
    		INTEGER,
    	    wfAotInterfaceAttachedTo
    		INTEGER,
    	    wfAotInterfacePktCnt
    		Counter,
            wfAotKeepaliveInterval
                INTEGER,
            wfAotKeepaliveRto
                INTEGER,
            wfAotKeepaliveMaxRetry
                INTEGER
        }

    wfAotInterfaceDelete OBJECT-TYPE
        SYNTAX	INTEGER {
    		    created(1),
    		    deleted(2)
    		}
        ACCESS	read-write
        STATUS	mandatory
        DESCRIPTION
                "Create/Delete attribute. Default is Created
                Users perform SNMP SET operation on this object in
                order to create/delete a translation interface record"
        DEFVAL	{ created }
        ::= { wfAotInterfaceEntry 1 }

    wfAotInterfaceDisable OBJECT-TYPE
        SYNTAX	INTEGER {
    		    enabled(1),
    		    disabled(2)
    		}
        ACCESS	read-write
        STATUS	mandatory
        DESCRIPTION
                "Enables/Disables this mapping entry
                Setting of this attribute to DISABLED will disconnect
                all active sessions pertaining to this interface entry"
        DEFVAL	{ enabled }
        ::= { wfAotInterfaceEntry 2 }

    wfAotInterfaceCctNumber OBJECT-TYPE
        SYNTAX	INTEGER
        ACCESS	read-only
        STATUS	mandatory
        DESCRIPTION
                "The circuit from which the connection attempt is
                received that initiates a translation session."
        ::= { wfAotInterfaceEntry 3 }

    wfAotInterfaceSlotNumber OBJECT-TYPE
        SYNTAX	INTEGER
        ACCESS	read-only
        STATUS	mandatory
        DESCRIPTION
                "Slot number on which this interface is running"
        ::= { wfAotInterfaceEntry 4 }

    wfAotInterfaceState OBJECT-TYPE
        SYNTAX	INTEGER {
    		    up(1),
    		    down(2),
    		    init(3)
    		}
        ACCESS	read-only
        STATUS	mandatory
        DESCRIPTION
                "The current state of the Interface"
        DEFVAL	{ down }
        ::= { wfAotInterfaceEntry 5 }

    wfAotInterfaceType OBJECT-TYPE
        SYNTAX	INTEGER {
    		    singledrop(1),
    		    multidrop(2)
    		}
        ACCESS	read-write
        STATUS	mandatory
        DESCRIPTION
                "If this interface is point-to-point, i.e. no splitting
                occurs we can straight away deliver PASC frame to designated
                TCP circuit"
        DEFVAL	{ singledrop }
        ::= { wfAotInterfaceEntry 6 }

    wfAotInterfaceAttachedTo OBJECT-TYPE
        SYNTAX	INTEGER {
    		    primary(1),
    		    secondary(2)
    		}
        ACCESS	read-write
        STATUS	mandatory
        DESCRIPTION
                "Information that this interface is attached to the Primary or
                secondary PASC station"
        ::= { wfAotInterfaceEntry 7 }

    wfAotInterfacePktCnt OBJECT-TYPE
        SYNTAX	Counter
        ACCESS	read-only
        STATUS	mandatory
        DESCRIPTION
                "Interface packet count ..."
        ::= { wfAotInterfaceEntry 8 }

    wfAotKeepaliveInterval OBJECT-TYPE
        SYNTAX  INTEGER(0..86400)
        ACCESS  read-write
        STATUS  mandatory
        DESCRIPTION
                "Idle session timeout period, in seconds.  If an established
                TCP connection remains inactive for this interval, KEEPALIVE
                messages will be sent to the peer (if the Keepalive Timer is
                non-zero).  Setting the Idle Timer to zero disables the
                keepalive feature."
        DEFVAL  { 120 }
        ::= { wfAotInterfaceEntry 9 }

    wfAotKeepaliveRto OBJECT-TYPE
        SYNTAX  INTEGER(0..600)
        ACCESS  read-write
        STATUS  mandatory
        DESCRIPTION
                "KEEPALIVE retransmit timeout period, in seconds.  This is
                the interval at which unacknowledged KEEPALIVE messages will
                be retransmitted.  If the Idle Timer is set to zero, this
                timer ignored.  If the Idle Timer is non-zero and this timer
                IS zero, no KEEPALIVEs are sent and the session is terminated
                upon expiration of the Idle Timer."
        DEFVAL  { 4 }
        ::= { wfAotInterfaceEntry 10 }

    wfAotKeepaliveMaxRetry OBJECT-TYPE
        SYNTAX  INTEGER(0..99)
        ACCESS  read-write
        STATUS  mandatory
        DESCRIPTION
                "Number of unacknowledged KEEPALIVE messages retransmitted
                before the TCP session is terminated.  If this count is set
                to zero, only one KEEPALIVE message will be sent."
        DEFVAL  { 5 }
        ::= { wfAotInterfaceEntry 11 }

    wfAotPeerTable OBJECT-TYPE
        SYNTAX	SEQUENCE OF WfAotPeerEntry
        ACCESS	not-accessible
        STATUS	mandatory
        DESCRIPTION
                "Peer table lists all TCP connections this router will have
                with its peers"
        ::= { wfAsyncOverTcpGroup 3 }

    wfAotPeerEntry OBJECT-TYPE
        SYNTAX	WfAotPeerEntry
        ACCESS	not-accessible
        STATUS	mandatory
        DESCRIPTION
                "An entry in wfAotPeerTable"
        INDEX	{ wfAotPeerSlotNumber,
    		  wfAotPeerCctNumber,
    		  wfAotPeerRemoteIpAddr,
    		  wfAotPeerLocalTcpListenPort,
    		  wfAotPeerRemoteTcpListenPort,
    		  wfAotConnOriginator }
        ::= { wfAotPeerTable 1 }

    WfAotPeerEntry ::= SEQUENCE {
    	    wfAotPeerEntryDelete
    		INTEGER,
    	    wfAotPeerEntryDisable
    		INTEGER,
    	    wfAotPeerSlotNumber
    		INTEGER,
    	    wfAotPeerCctNumber
    		INTEGER,
    	    wfAotPeerRemoteIpAddr
    		IpAddress,
    	    wfAotConnOriginator
    		INTEGER,
    	    wfAotPeerLocalTcpListenPort
    		INTEGER,
    	    wfAotPeerRemoteTcpListenPort
    		INTEGER,
    	    wfAotPeerLocalTcpPort
    		INTEGER,
    	    wfAotPeerRemoteTcpPort
    		INTEGER
        }

    wfAotPeerEntryDelete OBJECT-TYPE
        SYNTAX	INTEGER {
    		    created(1),
    		    deleted(2)
    		}
        ACCESS	read-write
        STATUS	mandatory
        DESCRIPTION
                "Create/Delete attribute. Default is Created
                Users perform SNMP SET operation on this object in
                order to create/delete a peer record"
        DEFVAL	{ created }
        ::= { wfAotPeerEntry 1 }

    wfAotPeerEntryDisable OBJECT-TYPE
        SYNTAX	INTEGER {
    		    enabled(1),
    		    disabled(2)
    		}
        ACCESS	read-write
        STATUS	mandatory
        DESCRIPTION
                "Enables/Disables this mapping entry
                Setting of this attribute to DISABLED will disconnect
                all active sessions pertaining to this interface entry"
        DEFVAL	{ enabled }
        ::= { wfAotPeerEntry 2 }

    wfAotPeerSlotNumber OBJECT-TYPE
        SYNTAX	INTEGER
        ACCESS	read-only
        STATUS	mandatory
        DESCRIPTION
                "Slot number on which this peer entry is configured"
        ::= { wfAotPeerEntry 3 }

    wfAotPeerCctNumber OBJECT-TYPE
        SYNTAX	INTEGER
        ACCESS	read-only
        STATUS	mandatory
        DESCRIPTION
                "The circuit from which the connection attempt is
                received that initiates a translation session."
        ::= { wfAotPeerEntry 4 }

    wfAotPeerRemoteIpAddr OBJECT-TYPE
        SYNTAX	IpAddress
        ACCESS	read-only
        STATUS	mandatory
        DESCRIPTION
                "IP Address of the remote host with which this translation
                session is established."
        ::= { wfAotPeerEntry 5 }

    wfAotConnOriginator OBJECT-TYPE
        SYNTAX	INTEGER {
    		    self(1),
    		    partner(2)
    		}
        ACCESS	read-only
        STATUS	mandatory
        DESCRIPTION
                "Upon start up, based on the configuration either
                partner is going to initiate TCP conn. or myself"
        ::= { wfAotPeerEntry 6 }

    wfAotPeerLocalTcpListenPort OBJECT-TYPE
        SYNTAX	INTEGER(1000..9999)
        ACCESS	read-only
        STATUS	mandatory
        DESCRIPTION
                "Based on the field wfAotConnOriginator, SiteManager
                will allow user to configure only one of following two fields:

                if Originator = SELF  then
                   through SiteManager ask user to enter PeerTcpListenPort#
                else
                   through SiteManager ask user to enter LocalTcpListenPort#

                So, in any case one of the two fields will have NULL_VALUE."
        ::= { wfAotPeerEntry 7 }

    wfAotPeerRemoteTcpListenPort OBJECT-TYPE
        SYNTAX	INTEGER(1000..9999)
        ACCESS	read-only
        STATUS	mandatory
        DESCRIPTION
                "Peer listen port for TCP connection"
        ::= { wfAotPeerEntry 8 }

    wfAotPeerLocalTcpPort OBJECT-TYPE
        SYNTAX	INTEGER(1000..9999)
        ACCESS	read-only
        STATUS	mandatory
        DESCRIPTION
                "When TCP connection is established, we will have other TCP
                port number available which is assigned by the system from
                the available pool. We will fill in this information here
                in this READ_ONLY variable. Again, based on Originator
                only one of the following two fields will have valid value.
                if Originator = SELF then
                    fill in LocalTcpPort field inside the AOT module
                else
                    fill in PeerTcpPort field inside the AOT module

                In short,
                =========
                For Originator = SELF
                    PeerTcpListenPort and LocalTcpPort  entries are valid
                For Originator = PARTNER
                    LocalTcpListenPort and PeerTcpPort  entries are valid"
        ::= { wfAotPeerEntry 9 }

    wfAotPeerRemoteTcpPort OBJECT-TYPE
        SYNTAX	INTEGER(1000..9999)
        ACCESS	read-only
        STATUS	mandatory
        DESCRIPTION
                "Peer TCP port of the connection"
        ::= { wfAotPeerEntry 10 }

END  -- Wellfleet-AOT-MIB
