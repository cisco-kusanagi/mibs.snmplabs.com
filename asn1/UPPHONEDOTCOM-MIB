--
--
--   Copyright (c) 1999 Phone.com, Inc. All rights reserved.
--
--    THIS IS UNPUBLISHED PROPRIETARY SOURCE CODE OF
--                 Phone.com, Inc.
--    The copyright notice above does not evidence any
--    actual or intended publication of such source code.
--
-- 


    UPPHONEDOTCOM-MIB DEFINITIONS ::= BEGIN
	 
IMPORTS
	Counter, Gauge
		FROM RFC1155-SMI
	OBJECT-TYPE, enterprises, IpAddress
		FROM SNMPv2-SMI
	DisplayString
		FROM SNMPv2-TC
	TRAP-TYPE
		FROM RFC-1215
;	 

        phoneDotCom   OBJECT IDENTIFIER ::= { enterprises 1900 }

        -- 
        -- Infrastructure systems
        --
        
        systems OBJECT IDENTIFIER ::= { phoneDotCom 4 }
        
        --
        -- UPInit
        --
        
        upiInit  OBJECT IDENTIFIER ::= { systems 1 }

                upiInitDescriptionTable OBJECT-TYPE
                                SYNTAX  SEQUENCE OF UpiInitDescriptionEntry
                                ACCESS  not-accessible
                                STATUS  mandatory
                                DESCRIPTION
                                                "the table holding UPInit identifying information"
                                ::= { upiInit 1 }

                upiInitDescriptionEntry OBJECT-TYPE
                                SYNTAX  UpiInitDescriptionEntry
                                ACCESS  not-accessible
                                STATUS  mandatory
                                DESCRIPTION
                                                "the entry associated with each UPInit process"
                                INDEX   { upidInitIpAddr, upidInitProcessId }
                                ::= { upiInitDescriptionTable 1 }

                UpiInitDescriptionEntry ::= SEQUENCE {
                                upidInitIpAddr          IpAddress,
                                upidInitProcessId       INTEGER,
                                upidInitVersion         DisplayString,
                                upidInitProcessType     DisplayString,
                                upidInitHostName        DisplayString,
                                upidInitStartupTime     DisplayString

                }

        upidInitIpAddr OBJECT-TYPE
                SYNTAX     IpAddress
                ACCESS     read-only
                STATUS     mandatory
                DESCRIPTION
                        "the ip address of the host running UPInit"
                ::= { upiInitDescriptionEntry 1 }

        upidInitProcessId OBJECT-TYPE
                SYNTAX          INTEGER
                ACCESS          read-only
                STATUS          mandatory
                DESCRIPTION
                        "the process id of UPInit"
                ::= { upiInitDescriptionEntry 2 }

        upidInitVersion OBJECT-TYPE
                SYNTAX     DisplayString
                ACCESS     read-only
                STATUS     mandatory
                DESCRIPTION
                        "the version of the UP system"
                ::= { upiInitDescriptionEntry 3 }

        upidInitProcessType OBJECT-TYPE
                SYNTAX     DisplayString
                ACCESS     read-only
                STATUS     mandatory
                DESCRIPTION
                        "one of these : UPLInit, UPAdmInit, UPAppsInit"
                ::= { upiInitDescriptionEntry 4 }

        upidInitHostName OBJECT-TYPE
                SYNTAX     DisplayString
                ACCESS     read-only
                STATUS     mandatory
                DESCRIPTION
                        "the host name where the UPInit process runs"
                ::= { upiInitDescriptionEntry 5 }

        upidInitStartupTime OBJECT-TYPE
                SYNTAX     DisplayString
                ACCESS     read-only
                STATUS     mandatory
                DESCRIPTION
                        "the UPInit start up time"
                ::= { upiInitDescriptionEntry 6 }

                upiInitStats    OBJECT IDENTIFIER ::= { upiInit 2 }

        -- upiInitChildProcessTable
        -- This table describes information on all processes started by
                -- UPInit
        --

        upiInitChildProcessTable OBJECT-TYPE
                SYNTAX     SEQUENCE OF UpiInitChildProcessEntry
                ACCESS     not-accessible
                STATUS     mandatory
                DESCRIPTION
                        "the table holding child process identifying
                                                information"
                ::= { upiInitStats 1 }

        upiInitChildProcessEntry OBJECT-TYPE
                SYNTAX     UpiInitChildProcessEntry
                ACCESS     not-accessible
                STATUS     mandatory
                DESCRIPTION
                        "the entry associated with each child process"
                INDEX { upipInitIpAddr, upipInitProcessId, upipChildProcessId }
                ::= { upiInitChildProcessTable 1 }

        UpiInitChildProcessEntry ::= SEQUENCE {
                upipInitIpAddr                          IpAddress,
                upipInitProcessId                       INTEGER,
                upipChildProcessId                      INTEGER,
                upipInitProcessType                     DisplayString,
                upipChildProcessType            DisplayString,
                upipChildProcessIpAddr          IpAddress,
                upipChildProcessHostName        DisplayString,
                upipChildProcessExePath         DisplayString,
                upipChildProcessExeArgs         DisplayString,
                upipChildProcessState           DisplayString,
                upipChildProcessStatus          DisplayString,
                upipChildProcessStartTime       DisplayString,
                upipChildProcessStopTime        DisplayString
        }

        upipInitIpAddr  OBJECT-TYPE
                SYNTAX          IpAddress
                ACCESS          read-only
                STATUS          mandatory
                DESCRIPTION
                        "the ip address of the host where UPInit runs"
                ::= { upiInitChildProcessEntry 1 }

        upipInitProcessType OBJECT-TYPE
                SYNTAX     DisplayString
                ACCESS     read-only
                STATUS     mandatory
                DESCRIPTION
                        "the UPInit process type: UPAdmInit, UPLInit
                                                or UPApsInit"
                ::= { upiInitChildProcessEntry 2 }

        upipInitProcessId OBJECT-TYPE
                SYNTAX     INTEGER
                ACCESS     read-only
                STATUS     mandatory
                DESCRIPTION
                        "the UPInit process pid"
                ::= { upiInitChildProcessEntry 3 }

        upipChildProcessId OBJECT-TYPE
                SYNTAX     INTEGER
                ACCESS     read-only
                STATUS     mandatory
                DESCRIPTION
                        "the child process pid"
                ::= { upiInitChildProcessEntry 4 }

        upipChildProcessType OBJECT-TYPE
                SYNTAX          DisplayString
                ACCESS          read-only
                STATUS          mandatory
                DESCRIPTION
                        "the child process type, e.g. Dispatcher, Agent"
                ::= { upiInitChildProcessEntry 5 }

        upipChildProcessIpAddr  OBJECT-TYPE
                SYNTAX          IpAddress
                ACCESS          read-only
                STATUS          mandatory
                DESCRIPTION
                        "the ip address of the host where the child
                                                process runs"
                ::= { upiInitChildProcessEntry 6 }

        upipChildProcessHostName OBJECT-TYPE
                SYNTAX          DisplayString
                ACCESS          read-only
                STATUS          mandatory
                DESCRIPTION
                        "the name of the host where the child process runs"
                ::= { upiInitChildProcessEntry 7 }

        upipChildProcessExePath OBJECT-TYPE
                SYNTAX          DisplayString
                ACCESS          read-only
                STATUS          mandatory
                DESCRIPTION
                        "the execution path of the child process"
                ::= { upiInitChildProcessEntry 8 }

        upipChildProcessExeArgs OBJECT-TYPE
                SYNTAX          DisplayString
                ACCESS          read-only
                STATUS          mandatory
                DESCRIPTION
                        "the arguments used when exeuting the child process"
                ::= { upiInitChildProcessEntry 9 }

        upipChildProcessState OBJECT-TYPE
                SYNTAX     DisplayString
                ACCESS     read-only
                STATUS     mandatory
                DESCRIPTION
                        "the state of the child process"
                ::= { upiInitChildProcessEntry 10 }

        upipChildProcessStatus OBJECT-TYPE
                SYNTAX     DisplayString
                ACCESS     read-only
                STATUS     mandatory
                DESCRIPTION
                        "how the child process is started"
                ::= { upiInitChildProcessEntry 11 }

        upipChildProcessStartTime OBJECT-TYPE
                SYNTAX     DisplayString
                ACCESS     read-only
                STATUS     mandatory
                DESCRIPTION
                        "the child process start time"
                ::= { upiInitChildProcessEntry 12 }

        upipChildProcessStopTime OBJECT-TYPE
                SYNTAX     DisplayString
                ACCESS     read-only
                STATUS     mandatory
                DESCRIPTION
                        "the child process stop time"
                ::= { upiInitChildProcessEntry 13 }

        -- upiInitChildProcessStatsTable
        -- This table collects statistics information on all processes
                -- started by upiInit
        --

        upiInitChildProcessStatsTable OBJECT-TYPE
                SYNTAX     SEQUENCE OF UpiInitChildProcessStatsEntry
                ACCESS     not-accessible
                STATUS     mandatory
                DESCRIPTION
                        "the table holding child process statistics"
                ::= { upiInitStats 2 }

        upiInitChildProcessStatsEntry OBJECT-TYPE
                SYNTAX     UpiInitChildProcessStatsEntry
                ACCESS     not-accessible
                STATUS     mandatory
                DESCRIPTION
                        "the statistics associated with each child process
type"
                INDEX { upipsInitIpAddr, upipsInitProcessId,
                                                upipsChildProcessType}
                ::= { upiInitChildProcessStatsTable 1 }

        UpiInitChildProcessStatsEntry ::= SEQUENCE {
                upipsInitIpAddr                                 IpAddress,
                upipsInitProcessId                              INTEGER,
                upipsChildProcessType                   DisplayString,
                upipsInitProcessType                    DisplayString,
                                upipsChildProcessesStarted              Counter,
                                upipsChildProcessesDied                 Counter,
                                upipsChildProcessesRunning              Gauge
                }

                upipsInitIpAddr OBJECT-TYPE
                                SYNTAX  IpAddress
                                ACCESS  read-only
                                STATUS  mandatory
                                DESCRIPTION
                                                " the ip address of the host where UPInit runs"
                                ::= { upiInitChildProcessStatsEntry 1 }

                upipsInitProcessId OBJECT-TYPE
                                SYNTAX  INTEGER
                                ACCESS  read-only
                                STATUS  mandatory
                                DESCRIPTION
                                                " the UPInit process pid"
                                ::= { upiInitChildProcessStatsEntry 2 }

                upipsChildProcessType OBJECT-TYPE
                                SYNTAX  DisplayString
                                ACCESS  read-only
                                STATUS  mandatory
                                DESCRIPTION
                                                "the child process name, e.g. Dispatcher,Agent"
                                ::= { upiInitChildProcessStatsEntry 3 }

                upipsInitProcessType OBJECT-TYPE
                                SYNTAX  DisplayString
                                ACCESS  read-only
                                STATUS  mandatory
                                DESCRIPTION
                                                " the UPInit process name, e.g. UPLInit UPAdmInit"
                                ::= { upiInitChildProcessStatsEntry 4 }

                upipsChildProcessesStarted OBJECT-TYPE
                                SYNTAX  Counter
                                ACCESS  read-only
                                STATUS  mandatory
                                DESCRIPTION
                                                "the number of times processes of this type started"
                ::= { upiInitChildProcessStatsEntry 5 }

                upipsChildProcessesDied OBJECT-TYPE
                                SYNTAX  Counter
                                ACCESS  read-only
                                STATUS  mandatory
                                DESCRIPTION
                                                "the number of times processes of this type died"
                                ::= { upiInitChildProcessStatsEntry 6 }

                upipsChildProcessesRunning OBJECT-TYPE
                                SYNTAX  Gauge
                                ACCESS  read-only
                                STATUS  mandatory
                                DESCRIPTION
                                                "the number of times processes of this type running "
                                ::= { upiInitChildProcessStatsEntry 7 }

        upiInitTrapInfo OBJECT IDENTIFIER ::= { upiInit 20 }

        upitTrapInfo OBJECT-TYPE
                SYNTAX     DisplayString
                ACCESS     not-accessible
                STATUS     optional
                DESCRIPTION
                        "Text string which provides additional
                         information about the trap."
                ::= {  upiInitTrapInfo 1 }

        upitChildProcessHostName OBJECT-TYPE
                SYNTAX          DisplayString
                                ACCESS          read-only
                STATUS          mandatory
                DESCRIPTION
                        "the hostname of the host where child process runs"
                ::= { upiInitTrapInfo 2 }

        upitChildProcessType OBJECT-TYPE
                SYNTAX          DisplayString
                                ACCESS          read-only
                STATUS          mandatory
                DESCRIPTION
                        "the child process type e.g. Dispatcher, Agent"
                ::= { upiInitTrapInfo 3 }

        upitChildProcessId OBJECT-TYPE
                SYNTAX          INTEGER
                                ACCESS          read-only
                STATUS          mandatory
                DESCRIPTION
                        "the child process id"
                ::= { upiInitTrapInfo 4 }

        upiChildProcessStart TRAP-TYPE
                ENTERPRISE { upiInit }
                VARIABLES  { upidInitHostName,
                                                         upidInitProcessType,
                                         upidInitProcessId,
                                                         upitChildProcessHostName,
                                                         upitChildProcessType,
                                                         upitChildProcessId,
                                                         upitTrapInfo }
                DESCRIPTION
                       "An event that is generated when a child process
                        is started/restarted."
                ::= 300

        upiChildProcessShutdown TRAP-TYPE
                ENTERPRISE { upiInit }
                VARIABLES  { upidInitHostName,
                                                         upidInitProcessType,
                                         upidInitProcessId,
                                                         upitChildProcessHostName,
                                                         upitChildProcessType,
                                                         upitChildProcessId,
                                                         upitTrapInfo }
                DESCRIPTION
                       "An event that is generated when a child process
                        is shut down. upitTrapInfo gives the condition."
                ::= 301

        upiInitFailToStart TRAP-TYPE
                ENTERPRISE { upiInit }
                VARIABLES  { upidInitHostName,
                                                         upidInitProcessType,
                                         upidInitProcessId,
                                                         upitTrapInfo }
                DESCRIPTION
                       "An event that is generated when UPInit is failed to
                        start itself."
                ::= 302

        upiInitShutdown TRAP-TYPE
                ENTERPRISE { upiInit }
                VARIABLES  { upidInitHostName,
                                                         upidInitProcessType,
                                         upidInitProcessId,
                                                         upitTrapInfo }
                DESCRIPTION
                       "An event that is generated when UPInit is about to
                        shutdown itself."
                ::= 303

        upiAllChildProcessesStop        TRAP-TYPE
                ENTERPRISE { upiInit }
                VARIABLES  { upidInitHostName,
                                                         upidInitProcessType,
                                         upidInitProcessId,
                                                         upitTrapInfo }
                DESCRIPTION
                       "An event that is generated when UPInit is about to
                        stop all child processes."
                ::= 304

        upiAllChildProcessesRestart TRAP-TYPE
                ENTERPRISE { upiInit }
                VARIABLES  { upidInitHostName,
                                                         upidInitProcessType,
                                         upidInitProcessId,
                                                         upitTrapInfo }
                DESCRIPTION
                       "An event that is generated when UPInit is about to
                        restart all child process."
                ::= 305

        upiDatabaseConnectionDown TRAP-TYPE
                ENTERPRISE { upiInit }
                VARIABLES  { upidInitHostName,
                                                         upidInitProcessType,
                                         upidInitProcessId,
                                                         upitTrapInfo }
                DESCRIPTION
                       "An event that is generated when UPInit
                        detects that the database is down."
                ::= 306

        upiDatabaseConnectionUp TRAP-TYPE
                ENTERPRISE { upiInit }
                VARIABLES  { upidInitHostName,
                                                         upidInitProcessType,
                                         upidInitProcessId,
                                                         upitTrapInfo }
                DESCRIPTION
                       "An event that is generated when UPInit
                        detects that the database is back up."
                ::= 307

        upiChildProcessFailToStart TRAP-TYPE
                ENTERPRISE { upiInit }
                VARIABLES  { upidInitHostName,
                                                         upidInitProcessType,
                                         upidInitProcessId,
                                                         upitChildProcessType,
                                                         upitTrapInfo }
                DESCRIPTION
                       "An event that is generated when a child process
                        fails to start."
                ::= 308

        upiNoChildProcess TRAP-TYPE
                ENTERPRISE { upiInit }
                VARIABLES  { upidInitHostName,
                                                         upidInitProcessType,
                                         upidInitProcessId,
                                                         upitTrapInfo }
                DESCRIPTION
                       "An event that is generated when no child process
                        is started by this upiInit instance."
                ::= 309

        upiChildProcessesBelowMinimum TRAP-TYPE
                ENTERPRISE { upiInit }
                VARIABLES  { upidInitHostName,
                                                         upidInitProcessType,
                                         upidInitProcessId,
                                                         upitChildProcessType,
                                                         upitTrapInfo }
                DESCRIPTION
                       "An event that is generated when the number of child
                                                processes started by means of TCP-Connect mechanism
                                                as defined in the cfg_init_tab becomes less than 2.
                                                This really applies to number of agents in most cases"
                ::= 310


    --
    -- UpLink
    --
        
        upLink      OBJECT IDENTIFIER ::= { systems 2 }
        
        upLinkProcesses OBJECT IDENTIFIER ::= { upLink 1 }
                
        uplDispatcher   OBJECT IDENTIFIER ::= { upLinkProcesses 1 }
        
        --
        -- uplDispatcherDescription group
        -- This group describes information identifying UPLink Dispatcher 
        --

        uplDispatcherDescription  OBJECT IDENTIFIER ::= { uplDispatcher 1 }
 
        upldHostName OBJECT-TYPE
                SYNTAX     DisplayString
                ACCESS     read-only
                STATUS     mandatory
                DESCRIPTION
                        "Name of the host on which dispatcher resides."
                ::= { uplDispatcherDescription 1 }

        upldProcessId OBJECT-TYPE
                SYNTAX     INTEGER
                ACCESS     read-only
                STATUS     mandatory
                DESCRIPTION
                        "Process ID for the dispatcher."
                ::= { uplDispatcherDescription 2 }
 
        upldPortNumber OBJECT-TYPE
                SYNTAX     INTEGER
                ACCESS     read-only
                STATUS     mandatory
                DESCRIPTION
                        "Port number the dispatcher uses to listen for
                         incomming airlink requests."
                ::= { uplDispatcherDescription 3 }
 
        upldStartUpTime OBJECT-TYPE
                SYNTAX     DisplayString
                ACCESS     read-only
                STATUS     mandatory
                DESCRIPTION
                        "Time the dispatcher started."
                ::= { uplDispatcherDescription 4 }
 
        upldState OBJECT-TYPE
                SYNTAX     INTEGER { regular(1), redirect(2) }
                ACCESS     read-only
                STATUS     mandatory
                DESCRIPTION
                        "The state of the dispatcher: 
                            regular:  routes airlink requests to UPLAgents;
                            redirect: routes airlink requests to other
                                      UPLDispatchers permanently."
                ::= { uplDispatcherDescription 5 }
 
        --
        -- uplDispatcherStats group
        -- This group describes UPLink dispatcher statistics
        --

        uplDispatcherStats OBJECT IDENTIFIER ::= { uplDispatcher 2 }
 
        upldRequestsReceived OBJECT-TYPE
                SYNTAX     Counter
                ACCESS     read-only
                STATUS     mandatory
                DESCRIPTION
                        "Requests that have been received since the dispatcher
                         started."
                ::= { uplDispatcherStats 1 }

        upldRequestsDropped OBJECT-TYPE
                SYNTAX     Counter
                ACCESS     read-only
                STATUS     mandatory
                DESCRIPTION
                        "Requests that have been dropped due to lack of 
                         resources since the dispatcher started."
                ::= { uplDispatcherStats 2 }

        upldUplAgentsLoaded OBJECT-TYPE
                SYNTAX     Gauge
                ACCESS     read-only
                STATUS     mandatory
                DESCRIPTION
                        "Total number of agents currently loaded 
                         in the dispatcher."
                ::= { uplDispatcherStats 3 }

        upldUplAgentsDisconnected OBJECT-TYPE
                SYNTAX     Gauge
                ACCESS     read-only
                STATUS     mandatory
                DESCRIPTION
                        "Total number of agents currently disconnected
                         among all the agents loaded in the dispatcher."
                ::= { uplDispatcherStats 4 }
 
        upldSubscribersLoaded OBJECT-TYPE
                SYNTAX     Gauge
                ACCESS     read-only
                STATUS     mandatory
                DESCRIPTION
                        "Total number of subscribers currently loaded
                         in the dispatcher."
                ::= { uplDispatcherStats 5 }
 
        upldKeyExchanges OBJECT-TYPE
                SYNTAX     Counter
                ACCESS     read-only
                STATUS     mandatory
                DESCRIPTION
                        "Number of key exchanges since the dispatcher
                         started."
                ::= { uplDispatcherStats 6 }
 
        --
        -- uplDispatcherTraps
        -- This section describes traps originated by UPLDispatcher
        --

        uplDispatcherTrapInfo   OBJECT IDENTIFIER ::= { uplDispatcher 20 }

        upldTrapInfo OBJECT-TYPE
                SYNTAX     DisplayString
                ACCESS     not-accessible
                STATUS     optional
                DESCRIPTION
                        "Text string which provides additional
                         information about the trap."
                ::= {  uplDispatcherTrapInfo 1 }

        upldUplAgentId OBJECT-TYPE
                SYNTAX     INTEGER
                ACCESS     not-accessible
                STATUS     optional
                DESCRIPTION
                        "The UPLAgent identifier related to the trap."
                ::= {  uplDispatcherTrapInfo 2 }
 

        upldStartup TRAP-TYPE
                ENTERPRISE { upLink }
                VARIABLES  { upldHostName, upldProcessId, upldTrapInfo }
                DESCRIPTION
                       "An event that is generated when the dispatcher
                        is started." 
                ::= 100
 
        upldShutdown TRAP-TYPE
                ENTERPRISE { upLink }
                VARIABLES  { upldHostName, upldProcessId, upldTrapInfo }
                DESCRIPTION
                       "An event that is generated when the dispatcher
                        is shut down. upldTrapInfo gives the condition."
                ::= 101
 
        upldInvalidConfig TRAP-TYPE
                ENTERPRISE { upLink }
                VARIABLES  { upldHostName, upldProcessId, upldTrapInfo }
                DESCRIPTION
                       "An event that is generated when the dispatcher
                        detects an invalid configuration. upldTrapInfo
                        gives the configuration name."
                ::= 102
 
        upldUplAgentConnectionDown TRAP-TYPE
                ENTERPRISE { upLink }
                VARIABLES  { upldHostName,
                             upldProcessId,
                             upldUplAgentId,
                             upldTrapInfo }
                DESCRIPTION
                       "An event that is generated when the dispatcher
                        detects that the connection to the UPLAgent is 
                        down. The UPLAgent is identified by upldAgentId.
                        upldTrapInfo gives the host name where the 
                        UPLAgent resides."
                ::= 103

        upldDatabaseConnectionDown TRAP-TYPE
                ENTERPRISE { upLink }
                VARIABLES  { upldHostName, upldProcessId, upldTrapInfo }

                DESCRIPTION
                       "An event that is generated when the dispatcher
                        detects that the database is down."
                ::= 104

        upldOutOfResouce TRAP-TYPE
                ENTERPRISE { upLink }
                VARIABLES  { upldHostName, upldProcessId, upldTrapInfo }
                DESCRIPTION
                       "An event that is generated when the dispatcher
                        detects an out-of-resource condition. upldTrapInfo
                        gives the resource name" 
                ::= 105
        
        --
        -- New traps for Dispatcher
        --
        upldUplAgentConnectionUp TRAP-TYPE
                ENTERPRISE { upLink }
                VARIABLES  { upldHostName,
                             upldProcessId,
                             upldUplAgentId,
                             upldTrapInfo }
                DESCRIPTION
                       "An event that is generated when the dispatcher
                        detects that the connection to the UPLAgent has
                        come up. The UPLAgent is identified by upldAgentId.
                        upldTrapInfo gives the host name where the 
                        UPLAgent resides."
                ::= 106

        upldDatabaseConnectionUp TRAP-TYPE
                ENTERPRISE { upLink }
                VARIABLES  { upldHostName, upldProcessId, upldTrapInfo }

                DESCRIPTION
                       "An event that is generated when the dispatcher
                        detects that the database has come into service."
                ::= 107
        
        --
        -- UPLink Agent 
        --
        
    uplAgent    OBJECT IDENTIFIER ::= { upLinkProcesses 2 }
        
        --
        -- Agent Description info
        --
              
        --
        -- uplAgentDescriptionTable
        -- This table describes information identifying UPLink Agent
        --

        uplAgentDescriptionTable OBJECT-TYPE
                SYNTAX     SEQUENCE OF UplAgentDescriptionEntry
                ACCESS     not-accessible
                STATUS     mandatory
                DESCRIPTION
                        "The table holding uplAgent identifying information."
                ::= { uplAgent 1 }
  
        uplAgentDescriptionEntry OBJECT-TYPE
                SYNTAX     UplAgentDescriptionEntry
                ACCESS     not-accessible
                STATUS     mandatory
                DESCRIPTION
                        "The entry associated with each uplAgent."
                INDEX { uplaAgentIdentifier }
                ::= { uplAgentDescriptionTable 1 }
  
        UplAgentDescriptionEntry ::= SEQUENCE {
                uplaAgentIdentifier   INTEGER,
                uplaHostName          DisplayString,
                uplaProcessId         INTEGER,
        --        uplaPortNumber        INTEGER,
                uplaStartUpTime       DisplayString
        }

        uplaAgentIdentifier OBJECT-TYPE
                SYNTAX     INTEGER
                ACCESS     read-only
                STATUS     mandatory
                DESCRIPTION
                        "The unique identifier for each uplAgent."
                ::= { uplAgentDescriptionEntry 1 }

        uplaHostName OBJECT-TYPE
                SYNTAX     DisplayString
                ACCESS     read-only
                STATUS     mandatory
                DESCRIPTION
                        "The host name of the uplAgent host."
                ::= { uplAgentDescriptionEntry 2 }

        uplaProcessId OBJECT-TYPE
                SYNTAX     INTEGER
                ACCESS     read-only
                STATUS     mandatory
                DESCRIPTION
                        "The process id for the uplAgent."
                ::= { uplAgentDescriptionEntry 3 }

        --uplaPortNumber OBJECT-TYPE
        --        SYNTAX     INTEGER
        --        ACCESS     read-only
        --        STATUS     mandatory
        --        DESCRIPTION
        --                "The port number on which the uplAgent listens
        --                 for incoming SUGP requests."
        --        ::= { uplAgentDescriptionEntry 4 }

        uplaStartUpTime OBJECT-TYPE
                SYNTAX     DisplayString
                ACCESS     read-only
                STATUS     mandatory
                DESCRIPTION
                        "The date and time the uplAgent started."
                ::= { uplAgentDescriptionEntry 5 }


        uplAgentProxyStats      OBJECT IDENTIFIER ::= { uplAgent 2 }

        --
        -- uplAgentWebAccessStatsTable
        -- This table describes UPLink Agent proxy statistics
        --
        
        uplAgentWebAccessStatsTable OBJECT-TYPE
                SYNTAX     SEQUENCE OF UplAgentWebAccessStatsEntry
                ACCESS     not-accessible
                STATUS     mandatory
                DESCRIPTION
                        "The table holding Web access statistics."
                ::= { uplAgentProxyStats 1 }
 
        uplAgentWebAccessStatsEntry OBJECT-TYPE
                SYNTAX     UplAgentWebAccessStatsEntry
                ACCESS     not-accessible
                STATUS     mandatory
                DESCRIPTION
                        "The entry associated with each uplAgent."
                INDEX { uplawsAgentIdentifier }
                ::= { uplAgentWebAccessStatsTable 1 }
 
        UplAgentWebAccessStatsEntry ::= SEQUENCE {
                uplawsAgentIdentifier            INTEGER,
                uplaHttpRequestsStarted          Counter,
                uplaHttpRequestsSucceeded        Counter,
                uplaHttpMeanResponseTime         INTEGER,
                uplaHttpDeviationOfResponseTime  INTEGER,
                uplaHttpsRequestsStarted         Counter,
                uplaHttpsRequestsSucceeded       Counter,
                uplaHttpsMeanResponseTime        INTEGER,
                uplaHttpsDeviationOfResponseTime INTEGER
        }

        uplawsAgentIdentifier OBJECT-TYPE
                SYNTAX     INTEGER
                ACCESS     read-only
                STATUS     mandatory
                DESCRIPTION
                        "The unique identifier for each uplAgent."
                ::= { uplAgentWebAccessStatsEntry 1 }
 
        -- The following provide information about the non-secure http
        -- protocol interactions

        uplaHttpRequestsStarted OBJECT-TYPE
                SYNTAX     Counter
                ACCESS     read-only
                STATUS     mandatory
                DESCRIPTION
                        "Number of http requests initiated since
                         the uplAgent started."
                ::= { uplAgentWebAccessStatsEntry 2 }

        uplaHttpRequestsSucceeded OBJECT-TYPE
                SYNTAX     Counter
                ACCESS     read-only
                STATUS     mandatory
                DESCRIPTION
                        "Number of http requests that succeeded
                         among all http requests initiated
                         since the uplAgent started."
                ::= { uplAgentWebAccessStatsEntry 3 }

        uplaHttpMeanResponseTime OBJECT-TYPE
                SYNTAX     INTEGER
                ACCESS     read-only
                STATUS     mandatory
                DESCRIPTION
                        "Mean response time in milliseconds for 
                         http requests."
                ::= { uplAgentWebAccessStatsEntry 4 }

        uplaHttpDeviationOfResponseTime OBJECT-TYPE
                SYNTAX     INTEGER
                ACCESS     read-only
                STATUS     mandatory
                DESCRIPTION
                        "Standard Deviation of uplaHttpMeanResponseTime."
                ::= { uplAgentWebAccessStatsEntry 5 }

        -- The following provide information about the secure http
        -- protocol interactions
 
        uplaHttpsRequestsStarted OBJECT-TYPE
                SYNTAX     Counter
                ACCESS     read-only
                STATUS     mandatory
                DESCRIPTION
                        "Number of https requests initiated since
                         the uplAgent started."
                ::= { uplAgentWebAccessStatsEntry 6 }
 
        uplaHttpsRequestsSucceeded OBJECT-TYPE
                SYNTAX     Counter
                ACCESS     read-only
                STATUS     mandatory
                DESCRIPTION
                        "Number of https requests that succeeded
                         among all https requests initiated
                         since the uplAgent started."
                ::= { uplAgentWebAccessStatsEntry 7 }
 
        uplaHttpsMeanResponseTime OBJECT-TYPE
                SYNTAX     INTEGER
                ACCESS     read-only
                STATUS     mandatory
                DESCRIPTION
                        "Mean response time in milliseconds for 
                         https requests."
                ::= { uplAgentWebAccessStatsEntry 8 }
 
        uplaHttpsDeviationOfResponseTime OBJECT-TYPE
                SYNTAX     INTEGER
                ACCESS     read-only
                STATUS     mandatory
                DESCRIPTION
                        "Standard deviation of uplaHttpsMeanResponseTime."
                ::= { uplAgentWebAccessStatsEntry 9 }

        --
        -- Error stats for Agent Proxy (i.e. Non-protocol based)
        --     

        --
        -- uplAgentErrorStatsSummaryTable
        -- This table describes UPLink Agent errors statistics summary
        --

        uplAgentErrorStatsSummaryTable OBJECT-TYPE
                SYNTAX     SEQUENCE OF UplAgentErrorStatsSummaryEntry
                ACCESS     not-accessible
                STATUS     mandatory
                DESCRIPTION
                        "The table holding error-summary statistics."
                ::= { uplAgentProxyStats 2 }
 
        uplAgentErrorStatsSummaryEntry OBJECT-TYPE
                SYNTAX     UplAgentErrorStatsSummaryEntry
                ACCESS     not-accessible
                STATUS     mandatory
                DESCRIPTION
                        "The entry associated with each uplAgent."
                INDEX { uplaesAgentIdentifier }
                ::= { uplAgentErrorStatsSummaryTable 1 }
 
        UplAgentErrorStatsSummaryEntry ::= SEQUENCE {
                uplaesAgentIdentifier INTEGER,
                uplaTotalErrors       Counter,
                uplaSilentErrors      Counter,
                uplaDeviceErrors      Counter,
                uplaKeyErrors         Counter,
                uplaSessionErrors     Counter,
                uplaTransactionErrors Counter,
                uplaOtherErrors       Counter
        }

        uplaesAgentIdentifier OBJECT-TYPE
                SYNTAX     INTEGER
                ACCESS     read-only
                STATUS     mandatory
                DESCRIPTION
                        "The unique identifier for each uplAgent."
                ::= { uplAgentErrorStatsSummaryEntry 1 }
 
        uplaTotalErrors OBJECT-TYPE
                SYNTAX     Counter
                ACCESS     read-only
                STATUS     mandatory
                DESCRIPTION
                        "Total number of errors that have occurred since
                         the uplAgent started."
                ::= { uplAgentErrorStatsSummaryEntry 2 }

        uplaSilentErrors OBJECT-TYPE
                SYNTAX     Counter
                ACCESS     read-only
                STATUS     mandatory
                DESCRIPTION
                        "Number of error occurrences for the silent 
                         class of errors since the uplAgent started.
                         The silent class of errors refers to errors
                         caused by client requests, but for which the 
                         uplAgent does not send the errors back to the client." 
                ::= { uplAgentErrorStatsSummaryEntry 3 }
 
        uplaDeviceErrors OBJECT-TYPE
                SYNTAX     Counter
                ACCESS     read-only
                STATUS     mandatory
                DESCRIPTION
                        "Number of error occurences for the device
                         class of errors since the uplAgent started.
                         The device class of errors refers to 
                         unregistered and unsupported devices."
                ::= { uplAgentErrorStatsSummaryEntry 4 }
 
        uplaKeyErrors OBJECT-TYPE
                SYNTAX     Counter
                ACCESS     read-only
                STATUS     mandatory
                DESCRIPTION
                        "Number of error occurrences for the key
                         class of errors since the uplAgent started.
                         The key class of errors refers to 
                         encryption key mismatch and unsupported
                         encryption algorithms/configurations."
                ::= { uplAgentErrorStatsSummaryEntry 5 }
 
        uplaSessionErrors OBJECT-TYPE
                SYNTAX     Counter
                ACCESS     read-only
                STATUS     mandatory
                DESCRIPTION
                        "Number of error occurrences for the session
                         class of errors since the uplAgent started.
                         The session class of errors refers to 
                         invalid sessions."
                ::= { uplAgentErrorStatsSummaryEntry 6 }
 
        uplaTransactionErrors OBJECT-TYPE
                SYNTAX     Counter
                ACCESS     read-only
                STATUS     mandatory
                DESCRIPTION
                        "Number of error occurrences for the transaction
                         class of errors since the uplAgent started.
                         The transaction class of errors refers to 
                         all errors occurring while the transaction
                         is conducted."
                ::= { uplAgentErrorStatsSummaryEntry 7 }

        uplaOtherErrors OBJECT-TYPE
                SYNTAX     Counter
                ACCESS     read-only
                STATUS     mandatory
                DESCRIPTION
                        "Number of error occurrences for all other 
                         errors since the uplAgent started. It is
                         simply TotalErrors minus all the named 
                         class errors."
                ::= { uplAgentErrorStatsSummaryEntry 8 }

        --
        -- uplAgentErrorStatsDetailTable
        -- This table describes UPLink Agent error statistics details
        --

        uplAgentErrorStatsDetailTable OBJECT-TYPE
                SYNTAX     SEQUENCE OF UplAgentErrorStatsDetailEntry
                ACCESS     not-accessible
                STATUS     mandatory
                DESCRIPTION
                        "The table holding detailed error statistics."
                ::= { uplAgentProxyStats 3 }
 
        uplAgentErrorStatsDetailEntry OBJECT-TYPE
                SYNTAX     UplAgentErrorStatsDetailEntry
                ACCESS     not-accessible
                STATUS     mandatory
                DESCRIPTION
                        "The entry associated with each error code
                         in an uplAgent."
                INDEX { uplaedAgentIdentifier, uplaErrorCode }
                ::= { uplAgentErrorStatsDetailTable 1 }
 
        UplAgentErrorStatsDetailEntry ::= SEQUENCE {
                uplaedAgentIdentifier      INTEGER,
                uplaErrorCode              INTEGER,
                uplaErrorName              DisplayString,
                uplaErrorSeverity          INTEGER,
                uplaErrorClass             INTEGER,
                uplaErrorCount             Counter
        }

        uplaedAgentIdentifier OBJECT-TYPE
                SYNTAX     INTEGER
                ACCESS     read-only
                STATUS     mandatory
                DESCRIPTION
                        "The unique identifier for each uplAgent."
                ::= { uplAgentErrorStatsDetailEntry 1 }
 
        uplaErrorCode OBJECT-TYPE
                SYNTAX     INTEGER
                ACCESS     read-only
                STATUS     mandatory
                DESCRIPTION
                        "The error code as defined in uplAgent."
                ::= { uplAgentErrorStatsDetailEntry 2 }

        uplaErrorName OBJECT-TYPE
                SYNTAX     DisplayString
                ACCESS     read-only
                STATUS     mandatory
                DESCRIPTION
                        "A text string describing the error name."
                ::= { uplAgentErrorStatsDetailEntry 3 }
 
        uplaErrorSeverity OBJECT-TYPE
                SYNTAX     INTEGER
                ACCESS     read-only
                STATUS     optional
                DESCRIPTION
                        "Error severity. 1 is the highest."
                ::= { uplAgentErrorStatsDetailEntry 4 }
 
        uplaErrorClass OBJECT-TYPE
                SYNTAX     INTEGER { silent(1),
                                     device(2),
                                     key(3),
                                     session(4),
                                     transaction(5),
                                     other(6) 
                                    }
                ACCESS     read-only
                STATUS     mandatory
                DESCRIPTION
                        "Error class identifier."
                ::= { uplAgentErrorStatsDetailEntry 5 }
 
        uplaErrorCount OBJECT-TYPE
                SYNTAX     Counter
                ACCESS     read-only
                STATUS     mandatory
                DESCRIPTION
                        "Number of times the error has occurred since
                         the uplAgent started."
                ::= { uplAgentErrorStatsDetailEntry 6 }
 
        --
        -- HDTP statistics that are held in the Agent
        --     

        uplHdtpStats    OBJECT IDENTIFIER ::= { uplAgent 3 }

        --
        -- uplAgentSessionStatsTable
        -- This table describes UPLink Agent session statistics
        --
        uplAgentSessionStatsTable OBJECT-TYPE
                SYNTAX     SEQUENCE OF UplAgentSessionStatsEntry
                ACCESS     not-accessible
                STATUS     mandatory
                DESCRIPTION
                        "The table holding uplAgent session statistics."
                ::= { uplHdtpStats 1 }
 
        uplAgentSessionStatsEntry OBJECT-TYPE
                SYNTAX     UplAgentSessionStatsEntry
                ACCESS     not-accessible
                STATUS     mandatory
                DESCRIPTION
                        "The entry associated with each uplAgent."
                INDEX { uplassAgentIdentifier }
                ::= { uplAgentSessionStatsTable 1 }
 
        UplAgentSessionStatsEntry ::= SEQUENCE {
                uplassAgentIdentifier   INTEGER,
                uplaActiveSessions      Gauge,
                uplaEncryptedSessions   Gauge,
                uplaProtoSessions       Gauge,
                uplaSessionsStarted     Counter,
                uplaSessionsSucceeded   Counter,
                uplaKeyExchanges        Counter
        }

        uplassAgentIdentifier OBJECT-TYPE
                SYNTAX     INTEGER
                ACCESS     read-only
                STATUS     mandatory
                DESCRIPTION
                        "The unique identifier for each uplAgent."
                ::= { uplAgentSessionStatsEntry 1 }
 
        uplaActiveSessions OBJECT-TYPE
                SYNTAX     Gauge
                ACCESS     read-only
                STATUS     mandatory
                DESCRIPTION
                        "Number of active sessions currently in 
                         the uplAgent."
                ::= { uplAgentSessionStatsEntry 2 }

        uplaEncryptedSessions OBJECT-TYPE
                SYNTAX     Gauge
                ACCESS     read-only
                STATUS     mandatory
                DESCRIPTION
                        "Number of sessions that use encryption
                         among all active sessions in the uplAgent."
                ::= { uplAgentSessionStatsEntry 3 }

        uplaProtoSessions OBJECT-TYPE
                SYNTAX     Gauge
                ACCESS     read-only
                STATUS     mandatory
                DESCRIPTION
                        "Number of proto sessions that do not
                         complete the session-creation procedure
                         currently in the uplAgent."
                ::= { uplAgentSessionStatsEntry 4 }

        uplaSessionsStarted OBJECT-TYPE
                SYNTAX     Counter
                ACCESS     read-only
                STATUS     mandatory
                DESCRIPTION
                        "Number of sessions started since
                         the uplAgent started."
                ::= { uplAgentSessionStatsEntry 5 }

        uplaSessionsSucceeded OBJECT-TYPE
                SYNTAX     Counter
                ACCESS     read-only
                STATUS     mandatory
                DESCRIPTION
                        "Number of sessions that have completed the 
                         session-creation procedure among all
                         sessions started since the
                         uplAgent started."
                ::= { uplAgentSessionStatsEntry 6 }

        uplaKeyExchanges OBJECT-TYPE
                SYNTAX     Counter
                ACCESS     read-only
                STATUS     mandatory
                DESCRIPTION
                        "Number of key exchanges that have completed 
                         since the uplAgent started."
                ::= { uplAgentSessionStatsEntry 7 }
        --
        -- uplAgentAirLinkStatsTable
        -- This table describes statistics for the link between 
        -- the mobile device and the UPLink
        --

        uplAgentAirLinkStatsTable OBJECT-TYPE
                SYNTAX     SEQUENCE OF UplAgentAirLinkStatsEntry
                ACCESS     not-accessible
                STATUS     deprecated
                DESCRIPTION
                        "The table holding uplAgent airlink traffic
                         statistics."
                ::= { uplHdtpStats 2 }
 
        uplAgentAirLinkStatsEntry OBJECT-TYPE
                SYNTAX     UplAgentAirLinkStatsEntry
                ACCESS     not-accessible
                STATUS     deprecated
                DESCRIPTION
                        "The entry associated with each uplAgent."
                INDEX { uplaasAgentIdentifier }
                ::= { uplAgentAirLinkStatsTable 1 }
 
        UplAgentAirLinkStatsEntry ::= SEQUENCE {
                uplaasAgentIdentifier    INTEGER,
                uplaRequestsReceived     Counter,
                uplaRequestsDropped      Counter,
                uplaRequestsDuplicated   Counter,
                uplaRequestsNotValid     Counter,
                uplaRepliesDelivered     Counter,
                uplaRepliesTimedOut      Counter
        }

        uplaasAgentIdentifier OBJECT-TYPE
                SYNTAX     INTEGER
                ACCESS     read-only
                STATUS     deprecated
                DESCRIPTION
                        "The unique identifier for each uplAgent."
                ::= { uplAgentAirLinkStatsEntry 1 }
 
        uplaRequestsReceived OBJECT-TYPE
                SYNTAX     Counter
                ACCESS     read-only
                STATUS     deprecated
                DESCRIPTION
                        "Number of requests that have been received by
                         uplAgent since it started. Ack, Cancel,
                         and SessComplete PDU's are not counted."
                ::= { uplAgentAirLinkStatsEntry 2 }

        uplaRequestsDropped OBJECT-TYPE
                SYNTAX     Counter
                ACCESS     read-only
                STATUS     deprecated
                DESCRIPTION
                        "Number of requests that have been dropped
                         since the UPLagent started. Dropped
                         requests include duplicated, invalid,
                         and out of sequence PDU's."
                ::= { uplAgentAirLinkStatsEntry 3 }

        uplaRequestsDuplicated OBJECT-TYPE
                SYNTAX     Counter
                ACCESS     read-only
                STATUS     deprecated
                DESCRIPTION
                        "Number of duplicated requests that have been 
                         received since the uplAgent started."
                ::= { uplAgentAirLinkStatsEntry 4 }
 
        uplaRequestsNotValid OBJECT-TYPE
                SYNTAX     Counter
                ACCESS     read-only
                STATUS     deprecated
                DESCRIPTION
                        "Number of invalid requests that have been received 
                         since the uplAgent started."
                ::= { uplAgentAirLinkStatsEntry 5 }
 
        uplaRepliesDelivered OBJECT-TYPE
                SYNTAX     Counter
                ACCESS     read-only
                STATUS     deprecated
                DESCRIPTION
                        "Number of replies that have been successfully
                         delivered to the browser client since
                         the uplAgent started."
                ::= { uplAgentAirLinkStatsEntry 6 }
 
        uplaRepliesTimedOut OBJECT-TYPE
                SYNTAX     Counter
                ACCESS     read-only
                STATUS     deprecated
                DESCRIPTION
                        "Number of replies not delivered
                         due to timeout since the uplAgent started."
                ::= { uplAgentAirLinkStatsEntry 7 }
 
        --
        -- uplAgentTransactionStatsTable
        -- This table describes UPLink Agent transaction statistics
        --

        uplAgentTransactionStatsTable OBJECT-TYPE
                SYNTAX     SEQUENCE OF UplAgentTransactionStatsEntry
                ACCESS     not-accessible
                STATUS     mandatory
                DESCRIPTION
                        "The table holding uplAgent transaction statistics."
                ::= { uplHdtpStats 3 }
 
        uplAgentTransactionStatsEntry OBJECT-TYPE
                SYNTAX     UplAgentTransactionStatsEntry
                ACCESS     not-accessible
                STATUS     mandatory
                DESCRIPTION
                        "The entry associated with each uplAgent."
                INDEX { uplatsAgentIdentifier }
                ::= { uplAgentTransactionStatsTable 1 }
 
        UplAgentTransactionStatsEntry ::= SEQUENCE {
                uplatsAgentIdentifier           INTEGER,
                uplaTransactionsActive          Gauge,
                uplaTransactionsStarted         Counter,
                uplaTransactionsSucceeded       Counter,
                uplaMeanTransactionLife         INTEGER,
                uplaDeviationOfTransactionLife  INTEGER,
                uplaMeanResponseTime            INTEGER,
                uplaDeviationOfResponseTime     INTEGER,
                uplaMeanRetriesPerThousandTxn   INTEGER,
                uplaDeviationOfRetriesPTTxn     INTEGER
        }

        uplatsAgentIdentifier OBJECT-TYPE
                SYNTAX     INTEGER
                ACCESS     read-only
                STATUS     mandatory
                DESCRIPTION
                        "The unique identifier for each uplAgent."
                ::= { uplAgentTransactionStatsEntry 1 }
 
        uplaTransactionsActive OBJECT-TYPE
                SYNTAX     Gauge
                ACCESS     read-only
                STATUS     mandatory
                DESCRIPTION
                        "Number of active transactions currently 
                         in the uplAgent."
                ::= { uplAgentTransactionStatsEntry 2 }

        uplaTransactionsStarted OBJECT-TYPE
                SYNTAX     Counter
                ACCESS     read-only
                STATUS     mandatory
                DESCRIPTION
                        "Number of transactions that have started since
                         the uplAgent started."
                ::= { uplAgentTransactionStatsEntry 3 }

        uplaTransactionsSucceeded OBJECT-TYPE
                SYNTAX     Counter
                ACCESS     read-only
                STATUS     mandatory
                DESCRIPTION
                        "Number of transactions that have succeeded among
                         all transactions started since the
                         uplAgent started."
                ::= { uplAgentTransactionStatsEntry 4 }

        uplaMeanTransactionLife OBJECT-TYPE
                SYNTAX     INTEGER
                ACCESS     read-only
                STATUS     mandatory
                DESCRIPTION
                        "Mean transaction lifetime measured in milliseconds."
                ::= { uplAgentTransactionStatsEntry 5 }

        uplaDeviationOfTransactionLife OBJECT-TYPE
                SYNTAX     INTEGER
                ACCESS     read-only
                STATUS     mandatory
                DESCRIPTION
                        "Standard deviation of uplaMeanTransactionLife."
                ::= { uplAgentTransactionStatsEntry 6 }
 
        uplaMeanResponseTime OBJECT-TYPE
                SYNTAX     INTEGER
                ACCESS     read-only
                STATUS     mandatory
                DESCRIPTION
                        "Mean transaction response time in milliseconds,as 
                         measured from the browser's point of view."
                ::= { uplAgentTransactionStatsEntry 7 }
 
        uplaDeviationOfResponseTime OBJECT-TYPE
                SYNTAX     INTEGER
                ACCESS     read-only
                STATUS     mandatory
                DESCRIPTION
                        "Standard deviation of uplaMeanResponseTime."
                ::= { uplAgentTransactionStatsEntry 8 }
 
        uplaMeanRetriesPerThousandTxn OBJECT-TYPE
                SYNTAX     INTEGER
                ACCESS     read-only
                STATUS     mandatory
                DESCRIPTION
                        "Number of retransmitted requests for
                         every one thousand completed transactions."
                ::= { uplAgentTransactionStatsEntry 9 }

        uplaDeviationOfRetriesPTTxn OBJECT-TYPE
                SYNTAX     INTEGER
                ACCESS     read-only
                STATUS     mandatory
                DESCRIPTION
                        "Standard deviation of uplaMeanRetriesPerThousandTxn."
                ::= { uplAgentTransactionStatsEntry 10 }

 
        --
        -- uplAgentLimitedResourceTable
        -- This table describes UPLink Agent resource usage 
        --

        uplAgentLimitedResourceTable OBJECT-TYPE
                SYNTAX     SEQUENCE OF UplAgentLimitedResourceEntry
                ACCESS     not-accessible
                STATUS     deprecated
                DESCRIPTION
                        "The table holding information about limited 
                         resource usage."
                ::= { uplHdtpStats 6 }
         
        uplAgentLimitedResourceEntry OBJECT-TYPE
                SYNTAX     UplAgentLimitedResourceEntry
                ACCESS     not-accessible
                STATUS     deprecated
                DESCRIPTION
                        "???"
                ::= { uplAgentLimitedResourceTable 1 }
					 
			-- unknow structure, just created an arbitrary one to make it compile
			UplAgentLimitedResourceEntry ::= SEQUENCE
			{
				integer INTEGER
			}
        --
        -- New WAP statistics that are held in the Agent
        --     

        uplaWapStats OBJECT IDENTIFIER ::= { uplAgent 4 }

        --
        -- WAP Session Statistics
        --
        
        uplAgentWapWSPSessionStatsTable OBJECT-TYPE
                SYNTAX     SEQUENCE OF UplAgentWapSessionStatsEntry
                ACCESS     not-accessible
                STATUS     mandatory
                DESCRIPTION
                        "The table holding uplAgent WAP session statistics."
                ::= { uplaWapStats 1 }
 
        uplAgentWapSessionStatsEntry OBJECT-TYPE
                SYNTAX     UplAgentWapSessionStatsEntry
                ACCESS     not-accessible
                STATUS     mandatory
                DESCRIPTION
                        "The entry associated with each uplAgent."
                INDEX { uplawssAgentIdentifier }
                ::= { uplAgentWapWSPSessionStatsTable 1 }
 
        UplAgentWapSessionStatsEntry ::= SEQUENCE {
                uplawssAgentIdentifier      INTEGER,
                uplaActiveWapSessions      Gauge,
                uplaWapSessionsStarted     Counter
        }

        uplawssAgentIdentifier OBJECT-TYPE
                SYNTAX     INTEGER
                ACCESS     read-only
                STATUS     mandatory
                DESCRIPTION
                        "The unique identifier for each uplAgent."
                ::= { uplAgentWapSessionStatsEntry 1 }
             
        uplaActiveWapSessions OBJECT-TYPE
                SYNTAX     Gauge
                ACCESS     read-only
                STATUS     mandatory
                DESCRIPTION
                        ""
                ::= { uplAgentWapSessionStatsEntry 2 }
                
        uplaWapSessionsStarted OBJECT-TYPE
                SYNTAX     Counter
                ACCESS     read-only
                STATUS     mandatory
                DESCRIPTION
                        ""
                ::= { uplAgentWapSessionStatsEntry 3 }
              
        --
        -- WAP WTP layer Statistics
        --
        
        uplAgentWapWTPTransactionStatsTable OBJECT-TYPE
                SYNTAX     SEQUENCE OF UplAgentWapTransactionStatsEntry
                ACCESS     not-accessible
                STATUS     mandatory
                DESCRIPTION
                        "The table holding uplAgent WAP Transaction layer statistics."
                ::= { uplaWapStats 2 }
 
        uplAgentWapTransactionStatsEntry OBJECT-TYPE
                SYNTAX     UplAgentWapTransactionStatsEntry
                ACCESS     not-accessible
                STATUS     mandatory
                DESCRIPTION
                        "The entry associated with each uplAgent."
                INDEX { uplawtsAgentIdentifier }
                ::= { uplAgentWapWTPTransactionStatsTable 1 }
 
        UplAgentWapTransactionStatsEntry ::= SEQUENCE {
                uplawtsAgentIdentifier          INTEGER,
                uplaWapInvokeTpdus		 Gauge,
                uplaWapResultTpdus		 Counter,
                uplaWapAbortTransaction		 Counter
        }

        uplawtsAgentIdentifier OBJECT-TYPE
                SYNTAX     INTEGER
                ACCESS     read-only
                STATUS     mandatory
                DESCRIPTION
                        "The unique identifier for each uplAgent."
                ::= { uplAgentWapTransactionStatsEntry 1 }
             
        uplaWapInvokeTpdus OBJECT-TYPE
                SYNTAX     Gauge
                ACCESS     read-only
                STATUS     mandatory
                DESCRIPTION
                        ""
                ::= { uplAgentWapTransactionStatsEntry 2 }
                
        uplaWapResultTpdus OBJECT-TYPE
                SYNTAX     Counter
                ACCESS     read-only
                STATUS     mandatory
                DESCRIPTION
                        ""
                ::= { uplAgentWapTransactionStatsEntry 3 }
                
        uplaWapAbortTransaction OBJECT-TYPE
                SYNTAX     Counter
                ACCESS     read-only
                STATUS     mandatory
                DESCRIPTION
                        ""
                ::= { uplAgentWapTransactionStatsEntry 4 }
              
    --
    -- Wap Error Statistics
    --

        -- uplAgentWapErrorStatsSummaryTable
        -- This table describes UPLink Agent WAP errors statistics summary
        --

        uplAgentWapErrorStatsSummaryTable OBJECT-TYPE
                SYNTAX     SEQUENCE OF UplAgentWapErrorStatsSummaryEntry
                ACCESS     not-accessible
                STATUS     mandatory
                DESCRIPTION
                        "The table holding WAP stack related error-summary statistics."
                ::= { uplaWapStats 3 }
 
        uplAgentWapErrorStatsSummaryEntry OBJECT-TYPE
                SYNTAX     UplAgentWapErrorStatsSummaryEntry
                ACCESS     not-accessible
                STATUS     mandatory
                DESCRIPTION
                        "The entry associated with each uplAgent."
                INDEX { uplawesAgentIdentifier }
                ::= { uplAgentWapErrorStatsSummaryTable 1 }
 
        UplAgentWapErrorStatsSummaryEntry ::= SEQUENCE {
                uplawesAgentIdentifier      INTEGER,
                uplaTotalWapErrors          Counter,
                uplaOtherWapErrors          Counter,
                uplaSessionWapErrors        Counter,
                uplaTransactionWapErrors    Counter
        }

        uplawesAgentIdentifier OBJECT-TYPE
                SYNTAX     INTEGER
                ACCESS     read-only
                STATUS     mandatory
                DESCRIPTION
                        "The unique identifier for each uplAgent."
                ::= { uplAgentWapErrorStatsSummaryEntry 1 }
 
        uplaTotalWapErrors OBJECT-TYPE
                SYNTAX     Counter
                ACCESS     read-only
                STATUS     mandatory
                DESCRIPTION
                        "Total number of WAP stack errors that have occurred since
                         the uplAgent started."
                ::= { uplAgentWapErrorStatsSummaryEntry 2 }

        uplaOtherWapErrors OBJECT-TYPE
                SYNTAX     Counter
                ACCESS     read-only
                STATUS     mandatory
                DESCRIPTION
                        "Number of error occurrences for all other 
                         errors since the uplAgent started. It is
                         simply TotalErrors minus all the named 
                         class errors."
                ::= { uplAgentWapErrorStatsSummaryEntry 3 }
                
        uplaSessionWapErrors OBJECT-TYPE
                SYNTAX     Counter
                ACCESS     read-only
                STATUS     mandatory
                DESCRIPTION
                        "Number of error occurrences for the WAP session
                         class of errors since the uplAgent started.
                         The session class of errors refers to 
                         invalid sessions."
                ::= { uplAgentWapErrorStatsSummaryEntry 4 }
 
        uplaTransactionWapErrors OBJECT-TYPE
                SYNTAX     Counter
                ACCESS     read-only
                STATUS     mandatory
                DESCRIPTION
                        "Number of error occurrences for the WAP transaction
                         class of errors since the uplAgent started.
                         The transaction class of errors refers to 
                         all errors occurring while the transaction
                         is conducted."
                ::= { uplAgentWapErrorStatsSummaryEntry 5 }

        --
        -- uplAgentWapErrorStatsDetailTable
        --
        -- This table describes UPLink Agent WAP error statistics details
        --

        uplAgentWapErrorStatsDetailTable OBJECT-TYPE
                SYNTAX     SEQUENCE OF UplAgentWapErrorStatsDetailEntry
                ACCESS     not-accessible
                STATUS     mandatory
                DESCRIPTION
                        "The table holding detailed error statistics."
                ::= { uplaWapStats 4 }
 
        uplAgentWapErrorStatsDetailEntry OBJECT-TYPE
                SYNTAX     UplAgentWapErrorStatsDetailEntry
                ACCESS     not-accessible
                STATUS     mandatory
                DESCRIPTION
                        "The entry associated with each error code
                         in an uplAgent."
                INDEX { uplaweAgentIdentifier, uplaWapErrorCode }
                ::= { uplAgentWapErrorStatsDetailTable 1 }
 
        UplAgentWapErrorStatsDetailEntry ::= SEQUENCE {
                uplaweAgentIdentifier         INTEGER,
                uplaWapErrorCode              INTEGER,
                uplaWapErrorName              DisplayString,
                uplaWapErrorSeverity          INTEGER,
                uplaWapErrorClass             INTEGER,
                uplaWapErrorCount             Counter
        }

        uplaweAgentIdentifier OBJECT-TYPE
                SYNTAX     INTEGER
                ACCESS     read-only
                STATUS     mandatory
                DESCRIPTION
                        "The unique identifier for each uplAgent."
                ::= { uplAgentWapErrorStatsDetailEntry 1 }
 
        uplaWapErrorCode OBJECT-TYPE
                SYNTAX     INTEGER
                ACCESS     read-only
                STATUS     mandatory
                DESCRIPTION
                        "The error code as defined in uplAgent."
                ::= { uplAgentWapErrorStatsDetailEntry 2 }

        uplaWapErrorName OBJECT-TYPE
                SYNTAX     DisplayString
                ACCESS     read-only
                STATUS     mandatory
                DESCRIPTION
                        "A text string describing the error name."
                ::= { uplAgentWapErrorStatsDetailEntry 3 }
 
        uplaWapErrorSeverity OBJECT-TYPE
                SYNTAX     INTEGER
                ACCESS     read-only
                STATUS     optional
                DESCRIPTION
                        "Error severity. 1 is the highest."
                ::= { uplAgentWapErrorStatsDetailEntry 4 }
 
        uplaWapErrorClass OBJECT-TYPE
                SYNTAX     INTEGER { other(1),
                                     session(2),
                                     txn(3)
                                    }
                ACCESS     read-only
                STATUS     mandatory
                DESCRIPTION
                        "Error class identifier."
                ::= { uplAgentWapErrorStatsDetailEntry 5 }
 
        uplaWapErrorCount OBJECT-TYPE
                SYNTAX     Counter
                ACCESS     read-only
                STATUS     mandatory
                DESCRIPTION
                        "Number of times the error has occurred since
                         the uplAgent started."
                ::= { uplAgentWapErrorStatsDetailEntry 6 }


        --- uplAgentStackServiceTable 
        ---     
        --- Table holding enabled stack services.
        --- The table indicates whether an enabled stack service 
        --- has been loaded successfully or not in UPLAgent.
        --- 

        uplaStackServiceStats OBJECT IDENTIFIER ::= { uplAgent 5 }


        uplAgentStackServiceTable OBJECT-TYPE
                SYNTAX     SEQUENCE OF UplAgentStackServiceEntry
                ACCESS     not-accessible
                STATUS     mandatory
                DESCRIPTION
                        "The table holding UP.Link Stack Service data for each Agent.
                         The static information is obtained from the 
                         Oracle database which is configured via the 
                         Admin GUI. The dynamic information is kept
                         up to date by the process."
                ::= { uplaStackServiceStats 1 }
 
        uplAgentStackServiceEntry OBJECT-TYPE
                SYNTAX     UplAgentStackServiceEntry
                ACCESS     not-accessible
                STATUS     mandatory
                DESCRIPTION
                        "The entry associated with Stack Services for each Agent."
                INDEX { uplasstAgentIdentifier, uplAgentStackServiceIdentifier }
                ::= { uplAgentStackServiceTable 1 }
 
        UplAgentStackServiceEntry ::= SEQUENCE {
        		uplasstAgentIdentifier						 INTEGER,
                uplAgentStackServiceIdentifier               INTEGER,
                uplAgentStackServiceAppProtoName             DisplayString,
                uplAgentStackServiceName                     DisplayString,
                uplAgentStackServiceLoaded                   INTEGER,
                uplAgentStackServiceAdaptorThreads  	     INTEGER,
                uplAgentStackServiceWDPPortNumber            INTEGER
        }
        
        uplasstAgentIdentifier OBJECT-TYPE
                SYNTAX     INTEGER
                ACCESS     read-only
                STATUS     mandatory
                DESCRIPTION
                        "The unique identifier for each uplAgent."
                ::= { uplAgentStackServiceEntry 1 }

        uplAgentStackServiceIdentifier OBJECT-TYPE
                SYNTAX     INTEGER
                ACCESS     read-only
                STATUS     mandatory
                DESCRIPTION
                        "The unique identifier for each Stack Service."
                ::= { uplAgentStackServiceEntry 2 }
                
        uplAgentStackServiceAppProtoName OBJECT-TYPE                   
                SYNTAX     DisplayString
                ACCESS     read-only
                STATUS     mandatory
                DESCRIPTION
                        "AppProtName."
                ::= { uplAgentStackServiceEntry 3 } 
                
        uplAgentStackServiceName OBJECT-TYPE                   
                SYNTAX     DisplayString
                ACCESS     read-only
                STATUS     mandatory
                DESCRIPTION
                        "AppProtName + Bearer + Tunnel Proto."
                ::= { uplAgentStackServiceEntry 4 }                  
                
        uplAgentStackServiceLoaded OBJECT-TYPE              
                SYNTAX     INTEGER  { notloaded(1),
                                      loaded(2)
                                     }
                ACCESS     read-only
                STATUS     mandatory
                DESCRIPTION
                        "Has the Stack Service been loaded: (1) No (2) Yes."
                ::= { uplAgentStackServiceEntry 5 }
 
                               
        uplAgentStackServiceAdaptorThreads OBJECT-TYPE
                SYNTAX     INTEGER
                ACCESS     read-only
                STATUS     mandatory
                DESCRIPTION
                        "The number of Adaptor threads for this Stack Service."
                ::= { uplAgentStackServiceEntry 6 }
                                
        uplAgentStackServiceWDPPortNumber OBJECT-TYPE  
                SYNTAX     INTEGER
                ACCESS     read-only
                STATUS     mandatory
                DESCRIPTION
                        "The WDP Port number for this Stack Service."
                ::= { uplAgentStackServiceEntry 7 }             
              
        --
        -- uplAgentTraps
        -- Copy of information from uplagent.mib lines 844-953
        --     
        uplAgentTrapInfo   OBJECT IDENTIFIER ::= { uplAgent 20 }

        uplaTrapInfo OBJECT-TYPE
                SYNTAX     DisplayString
                ACCESS     not-accessible
                STATUS     optional
                DESCRIPTION
                        "Text string that provides additional
                         information about the trap." 
                ::= { uplAgentTrapInfo 1 }

        uplaStartup TRAP-TYPE
                ENTERPRISE { upLink }
                VARIABLES { uplaAgentIdentifier, 
                            uplaHostName,
                            uplaProcessId,
                            uplaTrapInfo 
                          }
                DESCRIPTION
                       "An event that is generated when the uplAgent
                        is started."
                ::= 200
 
        uplaShutdown TRAP-TYPE
                ENTERPRISE { upLink }
                VARIABLES { uplaAgentIdentifier,
                            uplaHostName,
                            uplaProcessId,
                            uplaTrapInfo 
                          }
                DESCRIPTION
                       "An event that is generated when the uplAgent
                        is shut down. uplaTrapInfo gives the reason for 
                        the shutdown."
                ::= 201
 
        uplaDatabaseConnectionDown TRAP-TYPE
                ENTERPRISE { upLink }
                VARIABLES { uplaAgentIdentifier,
                            uplaHostName,
                            uplaProcessId,
                            uplaTrapInfo 
                          }
                DESCRIPTION
                       "An event that is generated when the uplAgent
                        detects that the database connection is down."
                ::= 202
 
        uplaFaxMgrConnectionDown TRAP-TYPE
                ENTERPRISE { upLink }
                VARIABLES { uplaAgentIdentifier,
                            uplaHostName,
                            uplaProcessId,
                            uplaTrapInfo 
                          }
                DESCRIPTION
                       "An event that is generated when the uplAgent
                        detects that the fax manager is down."
                ::= 203
 
        uplaMessengerConnectionDown TRAP-TYPE
                ENTERPRISE { upLink }
                VARIABLES { uplaAgentIdentifier,
                            uplaHostName,
                            uplaProcessId,
                            uplaTrapInfo 
                          }
                DESCRIPTION
                       "An event that is generated when the uplAgent
                        detects that the messenger is down."
                ::= 204
 
        uplaInvalidConfig TRAP-TYPE
                ENTERPRISE { upLink }
                VARIABLES { uplaAgentIdentifier,
                            uplaHostName,
                            uplaProcessId,
                            uplaTrapInfo
                          }
                DESCRIPTION
                       "An event that is generated when the uplAgent
                        detects an invalid configuration. uplaTrapInfo
                        gives the configuration name."
                ::= 205
 
        uplaInternalFatalErrors TRAP-TYPE
                ENTERPRISE { upLink }
                VARIABLES { uplaAgentIdentifier,
                            uplaHostName,
                            uplaProcessId,
                            uplaTrapInfo 
                          }
                DESCRIPTION
                       "An event that is generated when the uplAgent
                        detects an internal fatal error. uplaTrapInfo
                        gives error name."
                ::= 206
 
        uplaOutOfResource TRAP-TYPE
                ENTERPRISE { upLink }
                VARIABLES { uplaAgentIdentifier,
                            uplaHostName,
                            uplaProcessId,
                            uplaTrapInfo 
                          }
                DESCRIPTION
                       "An event that is generated when the uplAgent
                        detects reportable out-of-resource conditions.
                        uplaTrapInfo gives the resource name."
                ::= 207
        
        --
        -- New traps for Agent
        --

        uplaDatabaseConnectionUp TRAP-TYPE
                ENTERPRISE { upLink }
                VARIABLES  { uplaAgentIdentifier,
                            uplaHostName,
                            uplaProcessId,
                            uplaTrapInfo 
                           }
                DESCRIPTION
                       "An event that is generated when the Agent
                        detects that the database is up."
                ::= 208
                    
        --
        -- NBRouter
        --          
        
    uplNbRouter OBJECT IDENTIFIER ::= { upLinkProcesses 3 }

        --
        -- uplNbRouterDescriptionTable
        -- This table describes information identifying UPLink NarrowBand Routers
        --

        uplNbRouterDescriptionTable OBJECT-TYPE
                SYNTAX     SEQUENCE OF UplNbRouterDescriptionEntry
                ACCESS     not-accessible
                STATUS     mandatory
                DESCRIPTION
                        "The table holding UPLNbRouter identifying
information."
                ::= { uplNbRouter 1 }

        uplNbRouterDescriptionEntry OBJECT-TYPE
                SYNTAX     UplNbRouterDescriptionEntry
                ACCESS     not-accessible
                STATUS     mandatory
                DESCRIPTION
                        "The entry associated with each UPLNbRouter."
                INDEX { uplrdIpAddress, uplrdProcessId}
                ::= { uplNbRouterDescriptionTable 1 }

        UplNbRouterDescriptionEntry ::= SEQUENCE {
                uplrdIpAddress          IpAddress,
                uplrdProcessId          INTEGER,
                uplrdHostName           DisplayString,
                uplrdPortNumber         INTEGER,
                uplrdStartUpTime        DisplayString
        }

        uplrdIpAddress  OBJECT-TYPE
                                SYNTAX          IpAddress
                ACCESS          read-only
                STATUS          mandatory
                DESCRIPTION
                        "The ip address of the host running UPLNbRouter."
                ::= { uplNbRouterDescriptionEntry 1 }

        uplrdProcessId OBJECT-TYPE
                SYNTAX     INTEGER
                ACCESS     read-only
                STATUS     mandatory
                DESCRIPTION
                        "The process id of the UPLNbRouter."
                ::= { uplNbRouterDescriptionEntry 2 }

        uplrdHostName OBJECT-TYPE
                SYNTAX     DisplayString
                ACCESS     read-only
                STATUS     mandatory
                DESCRIPTION
                        "The host name of the node running UPLNbRouter."
                ::= { uplNbRouterDescriptionEntry 3 }

        uplrdPortNumber OBJECT-TYPE
                SYNTAX     INTEGER
                ACCESS     read-only
                STATUS     mandatory
                DESCRIPTION
                        "The port number on which the UPLNbRouter listens
                         for incoming requests."
                ::= { uplNbRouterDescriptionEntry 4 }

        uplrdStartUpTime OBJECT-TYPE
                SYNTAX     DisplayString
                ACCESS     read-only
                STATUS     mandatory
                DESCRIPTION
                        "The date and time the UPLNbRouter started."
                ::= { uplNbRouterDescriptionEntry 5 }

        --
        -- HDTP statistics that are held in the UPLNbRouter
        --

        uplrHdtpStats OBJECT IDENTIFIER ::= { uplNbRouter 2 }
        
        uplNbRouterAirlinkTable OBJECT-TYPE
                SYNTAX     SEQUENCE OF UplNbRouterAirlinkEntry
                ACCESS     not-accessible
                STATUS     deprecated
                DESCRIPTION
                       "The table holding airlinks loaded successfully
                                                in UPLNbRouter."
                ::= { uplrHdtpStats 1 }
                
        uplNbRouterAirlinkEntry OBJECT-TYPE
                SYNTAX     UplNbRouterAirlinkEntry
                ACCESS     not-accessible
                STATUS     deprecated
                DESCRIPTION
                       "???"
                ::= { uplNbRouterAirlinkTable 1 }
					 
			-- unknow structure, just created an arbitrary one to make it compile
			UplNbRouterAirlinkEntry ::= SEQUENCE
			{
				integer INTEGER
			}
                
        uplNbRouterAirlinkStatsTable OBJECT-TYPE
                SYNTAX     SEQUENCE OF UplNbRouterAirlinkStatsEntry
                ACCESS     not-accessible
                STATUS     deprecated
                DESCRIPTION
                       "The table holding statistics of mobile-terminated
                                                traffic through airlinks loaded in UPLNbRouter."
                ::= { uplrHdtpStats 2 }

        uplNbRouterAirlinkStatsEntry OBJECT-TYPE
                SYNTAX     UplNbRouterAirlinkStatsEntry
                ACCESS     not-accessible
                STATUS     deprecated
                DESCRIPTION
                       "???"
                ::= { uplNbRouterAirlinkStatsTable 1 }

			-- unknow structure, just created an arbitrary one to make it compile
			UplNbRouterAirlinkStatsEntry ::= SEQUENCE
			{
				integer INTEGER
			}

			--
        -- WAP statistics that are held in the UPLNbRouter
        --

        uplrStackServiceStats OBJECT IDENTIFIER ::= { uplNbRouter 3 }


        --
        -- uplNbRouterTraps
        -- This section describes traps originated by UPLNbRouter
        --

        uplNbRouterTrapInfo   OBJECT IDENTIFIER ::= { uplNbRouter 20 }

        uplrTrapInfo OBJECT-TYPE
                SYNTAX     DisplayString
                ACCESS     not-accessible
                STATUS     optional
                DESCRIPTION
                        "Text string that provides additional
                         information about the trap."
                ::= { uplNbRouterTrapInfo 1 }

        uplrClientIpAddress OBJECT-TYPE
                SYNTAX     IpAddress
                ACCESS     read-only
                STATUS     mandatory
                DESCRIPTION
                        "The ip address of the node running  the client
                                                that is communicating to the UPLNbRouter."
                ::= { uplNbRouterTrapInfo 2 }

        uplrClientHostName OBJECT-TYPE
                SYNTAX     DisplayString
                ACCESS     read-only
                STATUS     mandatory
                DESCRIPTION
                        "The host name of the node running  the client
                                                that is communicating to the UPLNbRouter."
                ::= { uplNbRouterTrapInfo 3 }

        uplrClientProcessId OBJECT-TYPE
                SYNTAX     INTEGER
                ACCESS     read-only
                STATUS     mandatory
                DESCRIPTION
                        "The process id of the client that is
                                                communicating to the UPLNbRouter."
                ::= { uplNbRouterTrapInfo 4 }

        uplrStartup TRAP-TYPE
                ENTERPRISE { upLink }
                VARIABLES { uplrdHostName,
                            uplrdProcessId,
                            uplrTrapInfo
                          }
                DESCRIPTION
                       "An event that is generated when the UPLNbRouter
                        is started."
                ::= 500

        uplrShutdown TRAP-TYPE
                ENTERPRISE { upLink }
                VARIABLES { uplrdHostName,
                            uplrdProcessId,
                            uplrTrapInfo
                          }
                DESCRIPTION
                       "An event that is generated when the UPLNbRouter
                        is shut down. uplrTrapInfo gives the reason for
                        the shutdown."
                ::= 501

        uplrDatabaseConnectionDown TRAP-TYPE
                ENTERPRISE { upLink }
                VARIABLES { uplrdHostName,
                            uplrdProcessId,
                            uplrTrapInfo
                          }
                DESCRIPTION
                       "An event that is generated when the UPLNbRouter
                        detects that the database connection is down."
                ::= 502

        uplrDatabaseConnectionUp TRAP-TYPE
                ENTERPRISE { upLink }
                VARIABLES { uplrdHostName,
                            uplrdProcessId,
                            uplrTrapInfo
                          }
                DESCRIPTION
                       "An event that is generated when the UPLNbRouter
                        detects that the database connection is back up."
                ::= 503

        uplrInvalidConfig TRAP-TYPE
                ENTERPRISE { upLink }
                VARIABLES { uplrdHostName,
                            uplrdProcessId,
                            uplrTrapInfo
                          }
                DESCRIPTION
                       "An event that is generated when the UPLNbRouter
                        detects an invalid configuration. uplrTrapInfo
                        gives the configuration name."
                ::= 504

        uplrInternalError TRAP-TYPE
                ENTERPRISE { upLink }
                VARIABLES { uplrdHostName,
                            uplrdProcessId,
                            uplrTrapInfo
                          }
                DESCRIPTION
                       "An event that is generated when the UPLNbRouter
                        detects an internal error. uplrTrapInfo
                        gives error name."
                ::= 505

        uplrSMSCConnectionDown TRAP-TYPE
                ENTERPRISE { upLink }
                VARIABLES { uplrdHostName,
                            uplrdProcessId,
                            uplrTrapInfo
                          }
                DESCRIPTION
                       "An event that is generated when the UPLNbRouter
                        detects the connection to external SMSC is down"
                ::= 506

        uplrSMSCConnectionUp TRAP-TYPE
                ENTERPRISE { upLink }
                VARIABLES { uplrdHostName,
                            uplrdProcessId,
                            uplrTrapInfo
                          }
                DESCRIPTION
                       "An event that is generated when the UPLNbRouter
                        detects the connection to external SMSC is back up"
                ::= 507

        uplrClientConnectionDown TRAP-TYPE
                ENTERPRISE { upLink }
                VARIABLES { uplrdHostName,
                            uplrdProcessId,
                            uplrTrapInfo
                          }
                DESCRIPTION
                       "An event that is generated when the UPLNbRouter
                        detects the connection to a client is down.
                                                The client can be uplMessenger, uplAgent or
                                                uplDispatcher."
               ::= 508

        uplrClientConnectionUp TRAP-TYPE
                ENTERPRISE { upLink }
                VARIABLES { uplrdHostName,
                            uplrdProcessId,
                            uplrTrapInfo
                          }
                DESCRIPTION
                       "An event that is generated when the UPLNbRouter
                        detects the connection to a client is back up.
                                                The client can be uplMessenger, uplAgent or
                                                uplDispatcher."
               ::= 509

        uplrNbRouterConnectionDown TRAP-TYPE
                ENTERPRISE { upLink }
                VARIABLES { uplrClientIpAddress,
                                        uplrClientHostName,
                            uplrClientProcessId,
                            uplrTrapInfo
                          }
                DESCRIPTION
                       "An event that is generated by a client when the
                                                client detects the connection to an UPLNbRouter
                                                is down."
               ::= 510

        uplrNbRouterConnectionUp TRAP-TYPE
                ENTERPRISE { upLink }
                VARIABLES { uplrClientIpAddress,
                            uplrClientHostName,
                            uplrClientProcessId,
                            uplrTrapInfo
                          }
                DESCRIPTION
                       "An event that is generated by a client when the
                                                client detects the connection to an UPLNbRouter
                                                is back up."
               ::= 511

        uplrProtocolError TRAP-TYPE
                ENTERPRISE { upLink }
                VARIABLES { uplrClientIpAddress,
                            uplrClientHostName,
                            uplrClientProcessId,
                            uplrTrapInfo
                          }
                DESCRIPTION
                       "An event that is generated by a client process
                                                running narrowband airlink adaptor when it detects
                                                a protocol error in the messages exchange with the
                                                UPLNbRouter."
                ::= 512

    --
    -- Messenger   
    --
        
    uplMessenger    OBJECT IDENTIFIER ::= { upLinkProcesses 4 }
 
        --
        -- uplMessengerDescriptionTable
        -- This table describes information identifying UPLMessenger
        --

        uplMessengerDescriptionTable OBJECT-TYPE
                SYNTAX     SEQUENCE OF UplMessengerDescriptionEntry
                ACCESS     not-accessible
                STATUS     mandatory
                DESCRIPTION
                        "The table holding UPLMessenger identifying
                         information."
                ::= { uplMessenger 1 }

        uplMessengerDescriptionEntry OBJECT-TYPE
                SYNTAX     UplMessengerDescriptionEntry
                ACCESS     not-accessible
                STATUS     mandatory
                DESCRIPTION
                        "The entry associated with each UPLMessenger."
                INDEX { uplmdIpAddress, uplmdProcessId}
                ::= { uplMessengerDescriptionTable 1 }

        UplMessengerDescriptionEntry ::= SEQUENCE {
                uplmdIpAddress                          IpAddress,
                uplmdProcessId                          INTEGER,
                uplmdHostName                           DisplayString,
                uplmdMsgServerPortNumber        INTEGER,
                uplmdPublicHTTPPortNumber       INTEGER,
                uplmdPublicHTTPSPortNumber      INTEGER,
                uplmdPrivateHTTPPortNumber      INTEGER,
                uplmdStartupTime                        DisplayString
        }

        uplmdIpAddress  OBJECT-TYPE
                                SYNTAX          IpAddress
                ACCESS          read-only
                STATUS          mandatory
                DESCRIPTION
                        "The ip address of the host running UPLMessenger."
                ::= { uplMessengerDescriptionEntry 1 }

        uplmdProcessId OBJECT-TYPE
                SYNTAX     INTEGER
                ACCESS     read-only
                STATUS     mandatory
                DESCRIPTION
                       "The process id of the UPLMessenger."
                ::= { uplMessengerDescriptionEntry 2 }

        uplmdHostName OBJECT-TYPE
                SYNTAX     DisplayString
                ACCESS     read-only
                STATUS     mandatory
                DESCRIPTION
                        "The host name of the node running UPLMessenger."
                ::= { uplMessengerDescriptionEntry 3 }

        uplmdMsgServerPortNumber OBJECT-TYPE
                SYNTAX     INTEGER
                ACCESS     read-only
                STATUS     mandatory
                DESCRIPTION
                        "The port number on which the UPLMessenger connects
                         to the proxy to deliver notifications."
                ::= { uplMessengerDescriptionEntry 4 }

        uplmdPublicHTTPPortNumber       OBJECT-TYPE
                SYNTAX     INTEGER
                ACCESS     read-only
                STATUS     mandatory
                DESCRIPTION
                        "The port number on which the UPLMessenger listens
                         for nonsecure public notification services."
                ::= { uplMessengerDescriptionEntry 5 }

        uplmdPublicHTTPSPortNumber      OBJECT-TYPE
                SYNTAX     INTEGER
                ACCESS     read-only
                STATUS     mandatory
                DESCRIPTION
                        "The port number on which the UPLMessenger listens
                         for secure public notification services."
                ::= { uplMessengerDescriptionEntry 6 }

        uplmdPrivateHTTPPortNumber      OBJECT-TYPE
                SYNTAX     INTEGER
                ACCESS     read-only
                STATUS     mandatory
                DESCRIPTION
                        "The port number on which the UPLMessenger listens
                         for nonsecure private notification services."
                ::= { uplMessengerDescriptionEntry 7 }

        uplmdStartupTime OBJECT-TYPE
                SYNTAX     DisplayString
                ACCESS     read-only
                STATUS     mandatory
                DESCRIPTION
                        "The date and time the UPLMessenger started."
                ::= { uplMessengerDescriptionEntry 8 }

        --
        -- HDTP statistics that are held in the UPLMessenger
        --

        uplmHdtpStats OBJECT IDENTIFIER ::= { uplMessenger 2 }
        
        uplMessengerAirlinkTable OBJECT-TYPE
                SYNTAX     SEQUENCE OF UplMessengerAirlinkEntry
                ACCESS     not-accessible
                STATUS     deprecated
                DESCRIPTION
                       "The table holding airlinks loaded successfully
                                                in UPLMessenger."
                ::= { uplmHdtpStats 1 }
                
        uplMessengerAirlinkEntry OBJECT-TYPE
                SYNTAX     UplMessengerAirlinkEntry
                ACCESS     not-accessible
                STATUS     deprecated
                DESCRIPTION
                       "???"
                ::= { uplMessengerAirlinkTable 1 }
					 
			-- unknow structure, just created an arbitrary one to make it compile
			UplMessengerAirlinkEntry ::= SEQUENCE
			{
				integer INTEGER
			}
                
                
        uplMessengerAirlinkStatsTable OBJECT-TYPE
                SYNTAX     SEQUENCE OF UplMessengerAirlinkStatsEntry
                ACCESS     not-accessible
                STATUS     deprecated
                DESCRIPTION
                       "The table holding statistics of notifications
                                                sent by the messenger."
                ::= { uplmHdtpStats 2 }

        uplMessengerAirlinkStatsEntry OBJECT-TYPE
                SYNTAX     UplMessengerAirlinkStatsEntry
                ACCESS     not-accessible
                STATUS     deprecated
                DESCRIPTION
                       "???"
                ::= { uplMessengerAirlinkStatsTable 1 }
					 
			-- unknow structure, just created an arbitrary one to make it compile
			UplMessengerAirlinkStatsEntry ::= SEQUENCE
			{
				integer INTEGER
			}


        --
        -- WAP statistics that are held in the UPLMessenger
        --

        uplmStackServiceStats OBJECT IDENTIFIER ::= { uplMessenger 3 }



        --
        -- Notifications statistics that are held in the UPLMessenger
        --

        uplMessengerNtfnStatsTable OBJECT-TYPE
                SYNTAX     SEQUENCE OF UplMessengerNtfnStatsEntry
                ACCESS     not-accessible
                STATUS     mandatory
                DESCRIPTION
                       "The table holding statistics on notification
                                                services provided by UPLMessenger."
                ::= { uplMessenger 4 }

        uplMessengerNtfnStatsEntry OBJECT-TYPE
                SYNTAX     UplMessengerNtfnStatsEntry
                ACCESS     not-accessible
                STATUS     mandatory
                DESCRIPTION
                        "The entry associated with notifications statistics
                                                for each UPLMessenger."
                INDEX { uplmnsIpAddress, uplmnsProcessId }
                ::= { uplMessengerNtfnStatsTable 1 }

        UplMessengerNtfnStatsEntry ::= SEQUENCE {
                uplmnsIpAddress                                         IpAddress,
                uplmnsProcessId                                 INTEGER,
                uplmnsPublicHTTPReqReceived                     Counter,
                uplmnsPrivateHTTPReqReceived            Counter,
                uplmnsPublicHTTPSReqReceived            Counter,
                uplmnsPublicHTTPReqProcessed            Counter,
                uplmnsPrivateHTTPReqProcessed           Counter,
                uplmnsPublicHTTPSReqProcessed           Counter,
                uplmnsAvgNtfnsAddedPerSec                       INTEGER,
                                uplmnsAvgNtfnsDeliveredPerSec           INTEGER,
                uplmnsAvgNtfnsExpiredPerSec                     INTEGER,
                uplmnsAvgNtfnsMarkedUnDelvrPerSec       INTEGER
        }

        uplmnsIpAddress OBJECT-TYPE
                SYNTAX     IpAddress
                ACCESS     read-only
                STATUS     mandatory
                DESCRIPTION
                        "The ip address of the host running UPLMessenger."
                ::= { uplMessengerNtfnStatsEntry 1 }

        uplmnsProcessId OBJECT-TYPE
                SYNTAX     INTEGER
                ACCESS     read-only
                STATUS     mandatory
                DESCRIPTION
                        "The process id of the UPLMessenger."
                ::= { uplMessengerNtfnStatsEntry 2 }

        uplmnsPublicHTTPReqReceived OBJECT-TYPE
                SYNTAX     Counter
                ACCESS     read-only
                STATUS     mandatory
                DESCRIPTION
                        "The number of public HTTP requests the UPLMessenger
                                                 received since it comes up."
                ::= { uplMessengerNtfnStatsEntry 3 }

        uplmnsPrivateHTTPReqReceived OBJECT-TYPE
                SYNTAX     Counter
                ACCESS     read-only
                STATUS     mandatory
                DESCRIPTION
                        "The number of private HTTP requests the
UPLMessenger
                                                 received since it comes up."
                ::= { uplMessengerNtfnStatsEntry 4 }

        uplmnsPublicHTTPSReqReceived OBJECT-TYPE
                SYNTAX     Counter
                ACCESS     read-only
                STATUS     mandatory
                DESCRIPTION
                        "The number of public HTTP requests the UPLMessenger
                                                 received since it comes up."
                ::= { uplMessengerNtfnStatsEntry 5 }

        uplmnsPublicHTTPReqProcessed OBJECT-TYPE
                SYNTAX     Counter
                ACCESS     read-only
                STATUS     mandatory
                DESCRIPTION
                        "The number of public HTTP requests the UPLMessenger
                                                 processed successfully since it comes up."
                ::= { uplMessengerNtfnStatsEntry 6 }

        uplmnsPrivateHTTPReqProcessed OBJECT-TYPE
                SYNTAX     Counter
                ACCESS     read-only
                STATUS     mandatory
                DESCRIPTION
                        "The number of private HTTP requests the
UPLMessenger
                                                 processed successfully since it comes up."
                ::= { uplMessengerNtfnStatsEntry 7 }

        uplmnsPublicHTTPSReqProcessed OBJECT-TYPE
                SYNTAX     Counter
                ACCESS     read-only
                STATUS     mandatory
                DESCRIPTION
                        "The number of public HTTPS requests the
UPLMessenger
                                                 processed successfully since it comes up."
                ::= { uplMessengerNtfnStatsEntry 8 }

        uplmnsAvgNtfnsAddedPerSec OBJECT-TYPE
                SYNTAX     INTEGER
                ACCESS     read-only
                STATUS     mandatory
                DESCRIPTION
                        "The average number of notifications added
                                                 per second by the UPLMessenger."
                ::= { uplMessengerNtfnStatsEntry 9 }

        uplmnsAvgNtfnsDeliveredPerSec OBJECT-TYPE
                SYNTAX     INTEGER
                ACCESS     read-only
                STATUS     mandatory
                DESCRIPTION
                        "The average number of notifications delivered
                                                 per second by the UPLMessenger."
                ::= { uplMessengerNtfnStatsEntry 10 }

        uplmnsAvgNtfnsExpiredPerSec OBJECT-TYPE
                SYNTAX     INTEGER
                ACCESS     read-only
                STATUS     mandatory
                DESCRIPTION
                        "The average number of notifications expired
                                                 per second by the UPLMessenger."
                ::= { uplMessengerNtfnStatsEntry 11 }

        uplmnsAvgNtfnsMarkedUnDelvrPerSec OBJECT-TYPE
                SYNTAX     INTEGER
                ACCESS     read-only
                STATUS     mandatory
                DESCRIPTION
                        "The average number of notifications marked
                                                 undeliverable per second by the UPLMessenger."
                ::= { uplMessengerNtfnStatsEntry 12 }


        --
        -- uplMessengerNtfnCacheTable
        -- This table holds the statistics on pending notifications
                -- that the UPLMessenger maintains as a in-memory cache
        --

        uplMessengerNtfnCacheTable OBJECT-TYPE
                SYNTAX     SEQUENCE OF UplMessengerNtfnCacheEntry
                ACCESS     not-accessible
                STATUS     mandatory
                DESCRIPTION
                       "The table holding statistics on the notification
                                                cache maintained by UPLMessenger."
                ::= { uplMessenger 5 }

        uplMessengerNtfnCacheEntry OBJECT-TYPE
                SYNTAX     UplMessengerNtfnCacheEntry
                ACCESS     not-accessible
                STATUS     mandatory
                DESCRIPTION
                        "The entry associated with the notifications cache
                                                 statistics for each UPLMessenger."
                INDEX { uplmncIpAddress, uplmncProcessId }
                ::= { uplMessengerNtfnCacheTable 1 }

        UplMessengerNtfnCacheEntry ::= SEQUENCE {
                uplmncIpAddress                                         IpAddress,
                uplmncProcessId                                 INTEGER,
                uplmncTotalNumOfPendingNtfns            Counter,
                uplmncAvgNumOfPendingNtfnsPerSub        INTEGER
                }

        uplmncIpAddress OBJECT-TYPE
                SYNTAX     IpAddress
                ACCESS     read-only
                STATUS     mandatory
                DESCRIPTION
                        "The ip address of the host running UPLMessenger."
                ::= { uplMessengerNtfnCacheEntry 1 }

        uplmncProcessId OBJECT-TYPE
                SYNTAX     INTEGER
                ACCESS     read-only
                STATUS     mandatory
                DESCRIPTION
                        "The process id of the UPLMessenger."
                ::= { uplMessengerNtfnCacheEntry 2 }

        uplmncTotalNumOfPendingNtfns OBJECT-TYPE
                SYNTAX     Counter
                ACCESS     read-only
                STATUS     mandatory
                DESCRIPTION
                        "The number of pending notifications
                                                in the cache as maintained by the UPLMessenger."
                ::= { uplMessengerNtfnCacheEntry 3 }

        uplmncAvgNumOfPendingNtfnsPerSub OBJECT-TYPE
                SYNTAX     INTEGER
                                ACCESS     read-only
                STATUS     mandatory
                DESCRIPTION
                        "The average number of pending notifications
                                                per subscriber as maintained by the UPLMessenger."
                ::= { uplMessengerNtfnCacheEntry 4 }


        --
        -- uplMessengerTraps
        -- This section describes traps originated by UPLMessenger
        --

        uplMessengerTrapInfo   OBJECT IDENTIFIER ::= { uplMessenger 20 }

        uplmTrapInfo OBJECT-TYPE
                SYNTAX     DisplayString
                ACCESS     not-accessible
                STATUS     optional
                DESCRIPTION
                        "Text string that provides additional
                         information about the trap."
                ::= { uplMessengerTrapInfo 1 }

        uplmStartup TRAP-TYPE
                ENTERPRISE { upLink }
                VARIABLES { uplmdIpAddress,
                            uplmdHostName,
                            uplmdProcessId,
                            uplmTrapInfo
                          }
                DESCRIPTION
                       "An event that is generated when the UPLMessenger
                        is started."
                ::= 600

        uplmShutdown TRAP-TYPE
                ENTERPRISE { upLink }
                VARIABLES { uplmdIpAddress,
                            uplmdHostName,
                            uplmdProcessId,
                            uplmTrapInfo
                          }
                DESCRIPTION
                       "An event that is generated when the UPLMessenger
                        is shut down. uplmTrapInfo gives the reason for
                        the shutdown."
                ::= 601

        uplmDatabaseConnectionDown TRAP-TYPE
                ENTERPRISE { upLink }
                VARIABLES { uplmdIpAddress,
                            uplmdHostName,
                            uplmdProcessId,
                            uplmTrapInfo
                          }
                DESCRIPTION
                       "An event that is generated when the UPLMessenger
                        detects that the database connection is down."
                ::= 602

        uplmDatabaseConnectionUp TRAP-TYPE
                ENTERPRISE { upLink }
                VARIABLES { uplmdIpAddress,
                            uplmdHostName,
                            uplmdProcessId,
                            uplmTrapInfo
                          }
                DESCRIPTION
                       "An event that is generated when the UPLMessenger
                        detects that the database connection is back up."
                ::= 603

        uplmInvalidConfig TRAP-TYPE
                ENTERPRISE { upLink }
                VARIABLES { uplmdIpAddress,
                            uplmdHostName,
                            uplmdProcessId,
                            uplmTrapInfo
                          }
                DESCRIPTION
                       "An event that is generated when the UPLMessenger
                        detects an invalid configuration. uplmTrapInfo
                        gives the configuration name."
                ::= 604

        uplmInternalErrors TRAP-TYPE
                ENTERPRISE { upLink }
                VARIABLES { uplmdIpAddress,
                            uplmdHostName,
                            uplmdProcessId,
                            uplmTrapInfo
                          }
                DESCRIPTION
                       "An event that is generated when the UPLMessenger
                        detects an internal error. uplmTrapInfo
                        gives error name."
                ::= 605

        uplmAgentConnectionDown TRAP-TYPE
                ENTERPRISE { upLink }
                VARIABLES { uplmdIpAddress,
                            uplmdHostName,
                            uplmdProcessId,
                            uplmTrapInfo
                          }
                DESCRIPTION
                       "An event that is generated when the UPLMesssenger
                        detects the message server serving UPLAgents at a
                                                configured port is down."
                ::= 606

        uplmPublicHTTPServiceStarted TRAP-TYPE
                ENTERPRISE { upLink }
                VARIABLES { uplmdIpAddress,
                            uplmdHostName,
                            uplmdProcessId,
                            uplmTrapInfo
                          }
                DESCRIPTION
                       "An event that is generated when the UPLMessenger
                         is starting the Public HTTP service. This is
                                                 sent as a warning because the service lowers
                                                 the overall security of the system."
                ::= 607

        uplmPublicHTTPServiceDown TRAP-TYPE
                ENTERPRISE { upLink }
                VARIABLES { uplmdIpAddress,
                            uplmdHostName,
                            uplmdProcessId,
                            uplmTrapInfo
                          }
                DESCRIPTION
                       "An event that is generated when the UPLMessenger
                        detects the Public HTTP interface is down."
                ::= 608

        uplmPrivateHTTPServiceDown TRAP-TYPE
                ENTERPRISE { upLink }
                VARIABLES { uplmdIpAddress,
                            uplmdHostName,
                            uplmdProcessId,
                            uplmTrapInfo
                          }
                DESCRIPTION
                       "An event that is generated when the UPLMessenger
                        detects the Private HTTP interface is down."
                ::= 609

        uplmPublicHTTPSServiceDown TRAP-TYPE
                ENTERPRISE { upLink }
                VARIABLES { uplmdIpAddress,
                            uplmdHostName,
                            uplmdProcessId,
                            uplmTrapInfo
                          }
                DESCRIPTION
                       "An event that is generated when the UPLMessenger
                        detects the Public secure HTTP interface is down."
                ::= 610       
        
        --
        -- Logical i.e. a more abstract view of the UP.Link machine
        --
        
    upLinkConfig    OBJECT IDENTIFIER ::= { upLink 2 }
        
    upLinkStaticInfo    OBJECT IDENTIFIER ::= { upLinkConfig 1 }
        
        -- to be supplied
        
 --   upLinkAggregateStats    OBJECT IDENTIFIER ::= { upLink 3 }
        
        -- to be supplied
        
        --
        -- upAdmin (formerly upsService)
        --
        upAdmin OBJECT IDENTIFIER ::= { systems 3 }

        upAdminTrapInfo OBJECT IDENTIFIER ::= { upAdmin 20 }

        upsTrapInfo OBJECT-TYPE
                SYNTAX     DisplayString
                ACCESS     not-accessible
                STATUS     optional
                DESCRIPTION
                        "Text string which provides additional
                         information about the trap."
                ::= {  upAdminTrapInfo 1 }


        upsProxyServiceDown TRAP-TYPE
                ENTERPRISE { upAdmin }
                VARIABLES  { upsTrapInfo }
                DESCRIPTION
                       "An event that is generated when the proxy
                        service is down "
                ::= 400

        upsProxyServiceSlow TRAP-TYPE
                ENTERPRISE { upAdmin }
                VARIABLES  { upsTrapInfo }
                DESCRIPTION
                       "An event that is generated when the proxy
                        service is slow"
                ::= 401

        upsPushServiceDown TRAP-TYPE
                ENTERPRISE { upAdmin }
                VARIABLES  { upsTrapInfo }
                DESCRIPTION
                       "An event that is generated when the  push
                       service is down "
                ::= 402

        upsBookmarksServiceDown TRAP-TYPE
                ENTERPRISE { upAdmin }
                VARIABLES  { upsTrapInfo }
                DESCRIPTION
                       "An event that is generated when the bookmarks
                       service is down "
                ::= 403

        upsBookmarksServiceSlow TRAP-TYPE
                ENTERPRISE { upAdmin }
                VARIABLES  { upsTrapInfo }
                DESCRIPTION
                       "An event that is generated when the bookmarks
                       service is slow "
                ::= 404

        upsHomePageServiceDown TRAP-TYPE
                ENTERPRISE { upAdmin }
                VARIABLES  { upsTrapInfo }
                DESCRIPTION
                       "An event that is generated when the homepage
                       service is down "
                ::= 405

        upsUPWebServiceDown TRAP-TYPE
                ENTERPRISE { upAdmin }
                VARIABLES  { upsTrapInfo }
                DESCRIPTION
                       "An event that is generated when the UP Web
                       service is down "
                ::= 406

        upsUPWebServiceSlow TRAP-TYPE
                ENTERPRISE { upAdmin }
                VARIABLES  { upsTrapInfo }
                DESCRIPTION
                       "An event that is generated when the UP Web
                       service is slow "
                ::= 407

        upsUPAdminServiceDown TRAP-TYPE
                ENTERPRISE { upAdmin }
                VARIABLES  { upsTrapInfo }
                DESCRIPTION
                       "An event that is generated when the UP Admin
                       service is down "
                ::= 408

        upsUPMailServiceDown TRAP-TYPE
                ENTERPRISE { upAdmin }
                VARIABLES  { upsTrapInfo }
                DESCRIPTION
                       "An event that is generated when the UP Mail
                       service is down "
                ::= 409

        upsUPMailServiceSlow TRAP-TYPE
                ENTERPRISE { upAdmin }
                VARIABLES  { upsTrapInfo }
                DESCRIPTION
                       "An event that is generated when the UP Mail
                       service is slow "
                ::= 410

        upsUPPimServiceDown TRAP-TYPE
                ENTERPRISE { upAdmin }
                VARIABLES  { upsTrapInfo }
                DESCRIPTION
                       "An event that is generated when the UP Pim
                       service is down "
                ::= 411

        upsUPPimServiceSlow TRAP-TYPE
                ENTERPRISE { upAdmin }
                VARIABLES  { upsTrapInfo }
                DESCRIPTION
                       "An event that is generated when the UP Pim
                       service is slow"
                ::= 412
 
        upsHomePageServiceSlow TRAP-TYPE
                ENTERPRISE { upAdmin }
                VARIABLES  { upsTrapInfo }
                DESCRIPTION
                       "An event that is generated when the UP Home
                       Page service is slow"
                ::= 413

    --
    -- New traps for services coming up
    -- These will be implemented in TACPAC/'hearbeat monitoring tools
    --
    --
        upsProxyServiceUp TRAP-TYPE
                ENTERPRISE { upAdmin }
                VARIABLES  { upsTrapInfo }
                DESCRIPTION
                       "An event that is generated when the proxy
            service comes back online."
                ::= 414

        upsProxyServiceNormal TRAP-TYPE
                ENTERPRISE { upAdmin }
                VARIABLES  { upsTrapInfo }
                DESCRIPTION
                       "An event that is generated when the proxy
            service returns to normal response time."
                ::= 415

        upsPushServiceUp TRAP-TYPE
                ENTERPRISE { upAdmin }
                VARIABLES  { upsTrapInfo }
                DESCRIPTION
                       "An event that is generated when the  push
            service comes back online."
                ::= 416

        upsBookmarksServiceUp TRAP-TYPE
                ENTERPRISE { upAdmin }
                VARIABLES  { upsTrapInfo }
                DESCRIPTION
                       "An event that is generated when the bookmarks
            service comes back online"
                ::= 417

        upsBookmarksServiceNormal TRAP-TYPE
                ENTERPRISE { upAdmin }
                VARIABLES  { upsTrapInfo }
                DESCRIPTION
                       "An event that is generated when the bookmarks
            service returns to normal response time."
                ::= 418

        upsHomePageServiceUp TRAP-TYPE
                ENTERPRISE { upAdmin }
                VARIABLES  { upsTrapInfo }
                DESCRIPTION
                       "An event that is generated when the homepage
            service comes back online."
                ::= 419

        upsUPWebServiceUp TRAP-TYPE
                ENTERPRISE { upAdmin }
                VARIABLES  { upsTrapInfo }
                DESCRIPTION
                       "An event that is generated when the UP Web
            service comes back online."
                ::= 420

        upsUPWebServiceNormal TRAP-TYPE
                ENTERPRISE { upAdmin }
                VARIABLES  { upsTrapInfo }
                DESCRIPTION
                       "An event that is generated when the UP Web
            service returns to normal response time."
                ::= 421

        upsUPAdminServiceUp TRAP-TYPE
                ENTERPRISE { upAdmin }
                VARIABLES  { upsTrapInfo }
                DESCRIPTION
                       "An event that is generated when the UP Admin
            service comes back online."
                ::= 422

        upsUPMailServiceUp TRAP-TYPE
                ENTERPRISE { upAdmin }
                VARIABLES  { upsTrapInfo }
                DESCRIPTION
                       "An event that is generated when the UP Mail
            service comes back online."
                ::= 423

        upsUPMailServiceNormal TRAP-TYPE
                ENTERPRISE { upAdmin }
                VARIABLES  { upsTrapInfo }
                DESCRIPTION
                       "An event that is generated when the UP Mail
            service returns to normal response time."
                ::= 424

        upsUPPimServiceUp TRAP-TYPE
                ENTERPRISE { upAdmin }
                VARIABLES  { upsTrapInfo }
                DESCRIPTION
                       "An event that is generated when the UP Pim
            service comes back on line."
                ::= 425

        upsUPPimServiceNormal TRAP-TYPE
                ENTERPRISE { upAdmin }
                VARIABLES  { upsTrapInfo }
                DESCRIPTION
                       "An event that is generated when the UP Pim
            service returns to normal response time."
                ::= 426


    --
    -- Services - all non-infrastructure items
    --
                
        services OBJECT IDENTIFIER ::= { phoneDotCom 5 }
       
    --
    -- UP.Mail
    --
    
        upMail      OBJECT IDENTIFIER ::= { services 1 }
        
        -- to be supplied
        
END
