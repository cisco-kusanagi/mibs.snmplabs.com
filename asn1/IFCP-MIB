-- extracted from draft-tseng-ifcpmib-00.txt
-- at Wed Aug 22 06:05:54 2001

   IFCP-MIB DEFINITIONS ::= BEGIN
   --
   --  iFCP.mib: IETF iFCP internet Fibre Channel Protocol
   --  management information base, v1.0
   --
   IMPORTS
       MODULE-IDENTITY,
       OBJECT-TYPE,
       IpAddress,
       Unsigned32,
       Counter32,
       Counter64,
       experimental
            FROM SNMPv2-SMI

       OBJECT-GROUP,
       MODULE-COMPLIANCE
            FROM SNMPv2-CONF

       DateAndTime,
       RowStatus
            FROM SNMPv2-TC

   --  These are from rfc 2851
       InetAddressType,
       InetAddress
            FROM INET-ADDRESS-MIB
         ;

   ifcpModule  MODULE-IDENTITY
         LAST-UPDATED "200107200000Z"
         ORGANIZATION "IETF IPS Working Group"
         CONTACT-INFO "
           Attn: Kevin Gibbons
                 Nishan Systems
                 3850 North First Street
                 San Jose, CA 95134
                 USA
                 Tel : +1 408 519-3700
                 email : snmp@nishansystems.com

                 Josh Tseng
                 Nishan Systems
                 3850 North First Street
                 San Jose, CA 95134
                 USA
                 Tel : +1 408 519-3700

   Tseng                Expires February 2002                       4
   Internet Draft              iFCP MIB                    August 2001

                 email : snmp@nishansystems.com

                 Charles Monia
                 Nishan Systems
                 3850 North First Street
                 San Jose, CA 95134
                 USA
                 Tel : +1 408 519-3700
                 email : snmp@nishansystems.com
                       "

         DESCRIPTION "The MIB for internet Fibre Channel Protocol
                     (iFCP) management."
              ::=  {experimental 4370}

   FCIDtype        ::= OCTET STRING (SIZE (3))
   WWNtype         ::= OCTET STRING (SIZE (8))
   EntIdx          ::= INTEGER (1..4294967295)
   PortalIdx       ::= INTEGER (1..4294967295)
   NodeIdx         ::= INTEGER (1..4294967295)
   EidType         ::= OCTET STRING
   NodeTypeBitmap  ::= OCTET STRING (SIZE (4))
   ScnBitmap       ::= OCTET STRING (SIZE (4))
   EntType         ::= INTEGER {iSCSI(1), iFCP(2)}
   IscsiNameType   ::= OCTET STRING
   DDIDtype        ::= INTEGER (1..4294967295)
   ClockType       ::= INTEGER (0..4294967295)
   VersionType     ::= INTEGER (0..4294967295)
   PortGrpType     ::= INTEGER (0..4294967295)
   PortType        ::= INTEGER (0..131071)
   EsiIntType      ::= INTEGER (0..4294967295)
   TFtype          ::= INTEGER {true(1), false(2)}

   --
   -- Internet Fibre Channel Protocol (iFCP)
   --

   ifcpGatewayObj          OBJECT IDENTIFIER ::= { ifcpModule 1 }
   ifcpGatewayConformance  OBJECT IDENTIFIER ::= { ifcpModule 2 }

   --
   -- ifcp Objects --------------------
   --

   ifcpGatewayObjInfo   OBJECT IDENTIFIER ::= { ifcpGatewayObj 1}

   --      top-level object information here

   ifcpGatewayVendorID            OBJECT-TYPE
       SYNTAX                  OCTET STRING (SIZE (0 .. 256))
       MAX-ACCESS              read-write
       STATUS                  current
       DESCRIPTION
   "The vendor identification of this ifcp gateway instance."

   Tseng                Expires February 2002                       5
   Internet Draft              iFCP MIB                    August 2001

       ::= {ifcpGatewayObjInfo 1}

   ifcpGatewayVendorVersion       OBJECT-TYPE
       SYNTAX                  OCTET STRING (SIZE (0 .. 256))
       MAX-ACCESS              read-write
       STATUS                  current
       DESCRIPTION
   "The vendor version of this ifcp gateway instance."
       ::= {ifcpGatewayObjInfo 2}

   ifcpGatewayMgtAddrType   OBJECT-TYPE
       SYNTAX                   InetAddressType
       MAX-ACCESS               read-only
       STATUS                   current
       DESCRIPTION
   "The type of Inet address in the next object."
       ::= {ifcpGatewayObjInfo 3}

   ifcpGatewayMgtAddr       OBJECT-TYPE
       SYNTAX                   InetAddress
       MAX-ACCESS               read-only
       STATUS                   current
       DESCRIPTION
   "The Inet management address of the ifcp instance. This
    is the in-band Inet Address that is used for SNMP."
       ::= {ifcpGatewayObjInfo 4}

   ifcpGatewayIsnsPrimaryAddrType      OBJECT-TYPE
       SYNTAX                   InetAddressType
       MAX-ACCESS               read-only
       STATUS                   current
       DESCRIPTION
   "The type of Inet address in the next object."
       ::= {ifcpGatewayObjInfo 5}

   ifcpGatewayIsnsPrimaryAddr          OBJECT-TYPE
       SYNTAX                   InetAddress
       MAX-ACCESS               read-only
       STATUS                   current
       DESCRIPTION
   "The in-band Inet address of the primary ifcp instance
    in the network.  This is the in-band Inet Address that
    is used for ifcpP messages."
       ::= {ifcpGatewayObjInfo 6}

   ifcpGatewayIsnsPort          OBJECT-TYPE
       SYNTAX                   INTEGER (0..65535)
       MAX-ACCESS               read-only
       STATUS                   current
       DESCRIPTION
   "Indicates the UDP/TCP port that the ifcp gateway is
    currently using for iSNS communication."
       ::= {ifcpGatewayObjInfo 7}


   Tseng                Expires February 2002                       6
   Internet Draft              iFCP MIB                    August 2001

   ifcpGatewayIsnsMcastGrp      OBJECT-TYPE
       SYNTAX                   IpAddress
       MAX-ACCESS               read-only
       STATUS                   current
       DESCRIPTION
   "The multicast group being used for iSNS
    communication.  This group is only valid if multicast
    communication has been set."
       ::= {ifcpGatewayObjInfo 8}

   ifcpGatewayIsnsMcastEnabled          OBJECT-TYPE
       SYNTAX                   TFtype
       MAX-ACCESS               read-only
       STATUS                   current
       DESCRIPTION
   "If this is true the gateway is enabled to communicate
    with the iSNS using multicast."
       ::= {ifcpGatewayObjInfo 9}

   ifcpNumEntities       OBJECT-TYPE
       SYNTAX            EntIdx
       MAX-ACCESS        read-only
       STATUS            current
       DESCRIPTION
   "The current total number of Entities in the gateway."
       ::= {ifcpGatewayObjInfo 10}

   ifcpNumPortals        OBJECT-TYPE
       SYNTAX            PortalIdx
       MAX-ACCESS        read-only
       STATUS            current
       DESCRIPTION
   "The current total number of Portals in the gatway."
       ::= {ifcpGatewayObjInfo 11}

   ifcpNumNodes      OBJECT-TYPE
       SYNTAX            NodeIdx
       MAX-ACCESS        read-only
       STATUS            current
       DESCRIPTION
   "The current total number of iFCP nodes in the gateway."
       ::= {ifcpGatewayObjInfo 12}

   ifcpNumFcNodes        OBJECT-TYPE
       SYNTAX            NodeIdx
       MAX-ACCESS        read-only
       STATUS            current
       DESCRIPTION
   "The current total number of FC nodes in the gateway."
       ::= {ifcpGatewayObjInfo 13}

   --
   -- ifcp Gateway Entities
   --

   Tseng                Expires February 2002                       7
   Internet Draft              iFCP MIB                    August 2001


   ifcpGatewayEntityInfo     OBJECT IDENTIFIER ::= { ifcpGatewayObj 2}

   --
   -- ifcp Gateway Entities Table
   --

   ifcpGatewayEntityTable            OBJECT-TYPE
       SYNTAX                    SEQUENCE OF IfcpGatewayEntityEntry
       MAX-ACCESS                not-accessible
       STATUS                    current
       DESCRIPTION
   "A table containing the entities in the Gateway ."
       ::= {ifcpGatewayEntityInfo 1}

   ifcpGatewayEntityEntry            OBJECT-TYPE
       SYNTAX                    IfcpGatewayEntityEntry
       MAX-ACCESS                not-accessible
       STATUS                    current
       DESCRIPTION
   "Information on Gateway entities in the ifcp."
       INDEX   {ifcpGatewayEntityEIdx}
       ::= {ifcpGatewayEntityTable 1}

   IfcpGatewayEntityEntry ::=
       SEQUENCE {
          ifcpGatewayEntityEIdx         EntIdx,
          ifcpGatewayEntityEID          EidType,
          ifcpGatewayEntityVersionRange VersionType
                 }

   ifcpGatewayEntityEIdx               OBJECT-TYPE
       SYNTAX                      EntIdx
       MAX-ACCESS                  read-only
       STATUS                      current
       DESCRIPTION
   "The Entity Index for this entity.  The index is
    derived for mapping between objects."
       ::= {ifcpGatewayEntityEntry 1}

   ifcpGatewayEntityEID                OBJECT-TYPE
       SYNTAX                      EidType
       MAX-ACCESS                  read-only
       STATUS                      current
       DESCRIPTION
   "The Entity Identifier for this entity as defined in
    the ifcp Specification."
       ::= {ifcpGatewayEntityEntry 2}

   ifcpGatewayEntityVersionRange       OBJECT-TYPE
       SYNTAX                      VersionType
       MAX-ACCESS                  read-only
       STATUS                      current
       DESCRIPTION

   Tseng                Expires February 2002                       8
   Internet Draft              iFCP MIB                    August 2001

   "The Protocol Version minimum and maximum as defined
    in the ifcp Specification."
       ::= {ifcpGatewayEntityEntry 3}

   --
   -- ifcp Gateway Portal Information
   --

   ifcpGatewayPortalInfo     OBJECT IDENTIFIER ::= { ifcpGatewayObj 3}

   --
   -- ifcp Gateway Portal Table
   --

   ifcpGatewayPortalTable    OBJECT-TYPE
       SYNTAX            SEQUENCE OF IfcpGatewayPortalEntry
       MAX-ACCESS        not-accessible
       STATUS            current
       DESCRIPTION
   "A table containing the Gateway portals in the ifcp."
       ::= {ifcpGatewayPortalInfo 1}

   ifcpGatewayPortalEntry    OBJECT-TYPE
       SYNTAX            IfcpGatewayPortalEntry
       MAX-ACCESS        not-accessible
       STATUS            current
       DESCRIPTION
   "Information on Gateway entity portals in the ifcp."
       INDEX   {ifcpGatewayPortalPrtlIdx, ifcpGatewayPortalEIdx}
       ::= {ifcpGatewayPortalTable 1}

   IfcpGatewayPortalEntry ::=
       SEQUENCE {
          ifcpGatewayPortalPrtlIdx        PortalIdx,
          ifcpGatewayPortalEIdx           EntIdx,
          ifcpGatewayPortalAddrType       InetAddressType,
          ifcpGatewayPortalAddr           InetAddress,
          ifcpGatewayPortalPort           PortType,
          ifcpGatewayPortalSymName        OCTET STRING,
          ifcpGatewayPortalEsiInterval    EsiIntType,
          ifcpGatewayPortalEsiScnUdpPort  PortType,
          ifcpGatewayPortalGroup          PortGrpType,
          ifcpGatewayPortalUptime         ClockType
                 }

   ifcpGatewayPortalPrtlIdx        OBJECT-TYPE
       SYNTAX                  PortalIdx
       MAX-ACCESS              read-only
       STATUS                  current
       DESCRIPTION
   "The Portal Index for this node.  The index is derived for
    mapping between objects."
       ::= {ifcpGatewayPortalEntry 1}


   Tseng                Expires February 2002                       9
   Internet Draft              iFCP MIB                    August 2001

   ifcpGatewayPortalEIdx           OBJECT-TYPE
       SYNTAX                  EntIdx
       MAX-ACCESS              read-only
       STATUS                  current
       DESCRIPTION
   "The Entity Index of the entity associated with this portal.
    The index is derived for mapping between objects."
       ::= {ifcpGatewayPortalEntry 2}

   ifcpGatewayPortalAddrType       OBJECT-TYPE
       SYNTAX                  InetAddressType
       MAX-ACCESS              read-only
       STATUS                  current
       DESCRIPTION
   "The type of Inet address in the next object."
       ::= {ifcpGatewayPortalEntry 3 }

   ifcpGatewayPortalAddr           OBJECT-TYPE
       SYNTAX                  InetAddress
       MAX-ACCESS              read-only
       STATUS                  current
       DESCRIPTION
   "The Inet Address for this portal as defined in the ifcp
    Specification."
       ::= {ifcpGatewayPortalEntry 4}

   ifcpGatewayPortalPort           OBJECT-TYPE
       SYNTAX                  PortType
       MAX-ACCESS              read-only
       STATUS                  current
       DESCRIPTION
   "The TCP/UDP port for this portal as defined in the ifcp
    Specification."
       ::= {ifcpGatewayPortalEntry 5}

   ifcpGatewayPortalSymName        OBJECT-TYPE
       SYNTAX                  OCTET STRING(SIZE(0..256))
       MAX-ACCESS              read-only
       STATUS                  current
       DESCRIPTION
   "The Symbolic Name for this portal as defined in the ifcp
    Specification."
       ::= {ifcpGatewayPortalEntry 6}

   ifcpGatewayPortalEsiInterval    OBJECT-TYPE
       SYNTAX                  EsiIntType
       MAX-ACCESS              read-only
       STATUS                  current
       DESCRIPTION
   "The ESI Interval for this portal as defined in the ifcp
    Specification."
       ::= {ifcpGatewayPortalEntry 7}

   ifcpGatewayPortalEsiScnUdpPort  OBJECT-TYPE

   Tseng                Expires February 2002                      10
   Internet Draft              iFCP MIB                    August 2001

       SYNTAX                  PortType
       MAX-ACCESS              read-only
       STATUS                  current
       DESCRIPTION
   "The ESI/SCN UDP port for this portal as defined in the ifcp
    Specification."
       ::= {ifcpGatewayPortalEntry 8}

   ifcpGatewayPortalGroup          OBJECT-TYPE
       SYNTAX                  PortGrpType
       MAX-ACCESS              read-only
       STATUS                  current
       DESCRIPTION
   "The Portal Group for this portal as defined in the ifcp
    Specification."
       ::= {ifcpGatewayPortalEntry 9}

   ifcpGatewayPortalUptime         OBJECT-TYPE
       SYNTAX                  ClockType
       MAX-ACCESS              read-only
       STATUS                  current
       DESCRIPTION
   "The uptime, in seconds, for this portal."
       ::= {ifcpGatewayPortalEntry 10}

   --
   -- ifcp Gateway iFCP Node Information
   --

   ifcpGatewayNodeInfo       OBJECT IDENTIFIER ::= { ifcpGatewayObj 4}

   --
   -- ifcp Gateway iFCP Node Table
   --

   ifcpGatewayNodeTable    OBJECT-TYPE
       SYNTAX              SEQUENCE OF IfcpGatewayNodeEntry
       MAX-ACCESS          not-accessible
       STATUS              current
       DESCRIPTION
   "Information on iFCP Nodes in the Gateway."
       ::= {ifcpGatewayNodeInfo 1}

   ifcpGatewayNodeEntry OBJECT-TYPE
       SYNTAX               IfcpGatewayNodeEntry
       MAX-ACCESS          not-accessible
       STATUS              current
       DESCRIPTION
   "Information on iFCP Node Entries in the Gateway ."
       INDEX {ifcpGatewayNodeWwpn}
       ::= {ifcpGatewayNodeTable 1}

   IfcpGatewayNodeEntry ::= SEQUENCE {
       ifcpGatewayNodeWwpn              WWNtype,

   Tseng                Expires February 2002                      11
   Internet Draft              iFCP MIB                    August 2001

       ifcpGatewayNodeEidx              EntIdx,
       ifcpGatewayNodePortID            FCIDtype,
       ifcpGatewayNodePortType          INTEGER,
       ifcpGatewayNodeSymName           OCTET STRING,
       ifcpGatewayNodeFcNodeWwn         WWNtype,
       ifcpGatewayNodeFabricPortWwn     WWNtype,
       ifcpGatewayNodeHA                FCIDtype,
       ifcpGatewayNodePortAddrType      InetAddressType,
       ifcpGatewayNodePortAddr          InetAddress,
       ifcpGatewayNodeFcCos             INTEGER,
       ifcpGatewayNodeFc4Types          OCTET STRING,
       ifcpGatewayNodeFc4Descr          OCTET STRING,
       ifcpGatewayNodeFc4Features       OCTET STRING,
       ifcpGatewayNodeScnBitmap         ScnBitmap
                                 }

   ifcpGatewayNodeWwpn            OBJECT-TYPE
       SYNTAX                     WWNtype
       MAX-ACCESS                 read-only
       STATUS                     current
       DESCRIPTION
   "The iFCP Node World Wide Port Name as defined in the ifcp
   Specification."
       ::= {ifcpGatewayNodeEntry 1}

   ifcpGatewayNodeEidx            OBJECT-TYPE
       SYNTAX                     EntIdx
       MAX-ACCESS                 read-only
       STATUS                     current
       DESCRIPTION
   "The Entity Index of the Entity associated with this node.  The
    index is derived for mapping between objects."
       ::= {ifcpGatewayNodeEntry 2}

   ifcpGatewayNodePortID         OBJECT-TYPE
       SYNTAX                    FCIDtype
       MAX-ACCESS                read-only
       STATUS                    current
       DESCRIPTION
   "The iFCP Node Port ID as defined in the ifcp Specification."
       ::= {ifcpGatewayNodeEntry 3}

   ifcpGatewayNodePortType        OBJECT-TYPE
       SYNTAX           INTEGER {
           unknown      (0),
           nPort        (1),
           nlPort       (2),
           fNlPort      (3),
           fPort        (129),     -- x'81'
           flPort       (130),     -- x'82'
           ePort        (132),     -- x'84'
           bPort        (133),     -- x'85'
           mFcpPort     (65297),   -- x'FF11'
           iFcpPort     (65298),   -- x'FF12'

   Tseng                Expires February 2002                      12
   Internet Draft              iFCP MIB                    August 2001

           unknownEnd   (65535)
                }
       MAX-ACCESS      read-only
       STATUS          current
       DESCRIPTION
   "The iFCP Node Port Type as defined in the ifcp Specification."
       ::= {ifcpGatewayNodeEntry 4}

   ifcpGatewayNodeSymName    OBJECT-TYPE
       SYNTAX                OCTET STRING(SIZE(0..256))
       MAX-ACCESS            read-only
       STATUS                current
       DESCRIPTION
   "The iFCP Node Port Symbolic Name as defined in the ifcp
   Specification."
       ::= {ifcpGatewayNodeEntry 5}

   ifcpGatewayNodeFcNodeWwn       OBJECT-TYPE
       SYNTAX                     WWNtype
       MAX-ACCESS                 read-only
       STATUS                     current
       DESCRIPTION
   "The FC Node WWN associated with this iFCP Node as defined in the
   ifcp
    Specification."
       ::= {ifcpGatewayNodeEntry 6}

   ifcpGatewayNodeFabricPortWwn   OBJECT-TYPE
       SYNTAX                     WWNtype
       MAX-ACCESS                 read-only
       STATUS                     current
       DESCRIPTION
   "The Fabric Port WWN associated with this Port as defined in the
   ifcp
    Specification."
       ::= {ifcpGatewayNodeEntry 7}

   ifcpGatewayNodeHA              OBJECT-TYPE
       SYNTAX                     FCIDtype
       MAX-ACCESS                 read-only
       STATUS                     current
       DESCRIPTION
   "The FC Hard Address as defined in the ifcp Specification."
       ::= {ifcpGatewayNodeEntry 8}

   ifcpGatewayNodePortAddrType     OBJECT-TYPE
       SYNTAX                      InetAddressType
       MAX-ACCESS                  read-only
       STATUS                      current
       DESCRIPTION
   "The type of Inet address in the next object."
       ::= {ifcpGatewayNodeEntry 9 }

   ifcpGatewayNodePortAddr          OBJECT-TYPE

   Tseng                Expires February 2002                      13
   Internet Draft              iFCP MIB                    August 2001

       SYNTAX                       InetAddress
       MAX-ACCESS                   read-only
       STATUS                       current
       DESCRIPTION
   "The iFCP Node Port Inet Address as defined in the ifcp
   Specification."
       ::= {ifcpGatewayNodeEntry 10}

   ifcpGatewayNodeFcCos         OBJECT-TYPE
       SYNTAX          INTEGER {
                --        class-unknown (0),
                          classF (1),
                          class1 (2),
                          classF1 (3),
                          class2 (4),
                          classF2 (5),
                          class12 (6),
                          classF1_2 (7),
                          class3 (8),
                          classF3 (9),
                          class13 (10),
                          classF1_3 (11),
                          class23 (12),
                          classF2_3 (13),
                          class12_3 (14),
                          classF1_2_3 (15)
                        }
       MAX-ACCESS     read-only
       STATUS         current
       DESCRIPTION
   "The iFCP Node Class of Service as defined in the ifcp
   Specification."
       ::= {ifcpGatewayNodeEntry 11}

   ifcpGatewayNodeFc4Types       OBJECT-TYPE
       SYNTAX                    OCTET STRING (SIZE (32))
       MAX-ACCESS                read-only
       STATUS                    current
       DESCRIPTION
   "The iFCP Node FC-4 Types as defined in the ifcp Specification."
       ::= {ifcpGatewayNodeEntry 12}

   ifcpGatewayNodeFc4Descr       OBJECT-TYPE
       SYNTAX                    OCTET STRING(SIZE(0..256))
       MAX-ACCESS                read-only
       STATUS                    current
       DESCRIPTION
   "The iFCP Node FC-4 Descriptors as defined in the ifcp
   Specification."
       ::= {ifcpGatewayNodeEntry 13}

   ifcpGatewayNodeFc4Features    OBJECT-TYPE
       SYNTAX                    OCTET STRING (SIZE (128))
       MAX-ACCESS                read-only

   Tseng                Expires February 2002                      14
   Internet Draft              iFCP MIB                    August 2001

       STATUS                    current
       DESCRIPTION
   "The iFCP Node FC-4 Features as defined in the ifcp Specification."
       ::= {ifcpGatewayNodeEntry 14}

   ifcpGatewayNodeScnBitmap      OBJECT-TYPE
       SYNTAX                    ScnBitmap
       MAX-ACCESS                read-only
       STATUS                    current
       DESCRIPTION
   "The iFCP Node SCN bitmap for this node as defined in the ifcp
    Specification."
       ::= {ifcpGatewayNodeEntry 15}

   --
   -- ifcp Gateway FC Node Information
   --

   ifcpGatewayFcNodeInfo     OBJECT IDENTIFIER ::= { ifcpGatewayObj 5}

   --
   -- ifcp Gateway FC Node Table
   --

   ifcpGatewayFcNodeTable    OBJECT-TYPE
       SYNTAX            SEQUENCE OF IfcpGatewayFcNodeEntry
       MAX-ACCESS        not-accessible
       STATUS            current
       DESCRIPTION
   "A table containing the FC Nodes in the Gateway."
       ::= {ifcpGatewayFcNodeInfo 1}

   ifcpGatewayFcNodeEntry    OBJECT-TYPE
       SYNTAX            IfcpGatewayFcNodeEntry
       MAX-ACCESS        not-accessible
       STATUS            current
       DESCRIPTION
   "Information on FC nodes in the Gateway."
       INDEX          {ifcpGatewayFcNodeWwn}
       ::= {ifcpGatewayFcNodeTable 1}

   IfcpGatewayFcNodeEntry ::= SEQUENCE {
       ifcpGatewayFcNodeWwn           WWNtype,
       ifcpGatewayFcNodeSymName       OCTET STRING,
       ifcpGatewayFcNodeAddrType      InetAddressType,
       ifcpGatewayFcNodeAddr          InetAddress,
       ifcpGatewayFcNodeIPA           OCTET STRING
                                   }

   ifcpGatewayFcNodeWwn             OBJECT-TYPE
       SYNTAX                   WWNtype
       MAX-ACCESS               read-only
       STATUS                   current
       DESCRIPTION

   Tseng                Expires February 2002                      15
   Internet Draft              iFCP MIB                    August 2001

   "The FC Node WorldWideName as defined in the ifcp Specification."
       ::= {ifcpGatewayFcNodeEntry 1}

   ifcpGatewayFcNodeSymName         OBJECT-TYPE
       SYNTAX                   OCTET STRING (SIZE(0..256))
       MAX-ACCESS               read-only
       STATUS                   current
       DESCRIPTION
   "The FC Node Symbolic Name of the node as defined in the
    ifcp Specification.  This is a variable-length text-based
    description of up to 256 bytes."
       ::= {ifcpGatewayFcNodeEntry 2}

   ifcpGatewayFcNodeAddrType        OBJECT-TYPE
       SYNTAX                   InetAddressType
       MAX-ACCESS               read-only
       STATUS                   current
       DESCRIPTION
   "The type of Inet address in the next object."
       ::= {ifcpGatewayFcNodeEntry 3 }

   ifcpGatewayFcNodeAddr            OBJECT-TYPE
       SYNTAX                   InetAddress
       MAX-ACCESS               read-only
       STATUS                   current
       DESCRIPTION
   "The FC Node Inet address of the node as defined in the
    ifcp Specification."
       ::= {ifcpGatewayFcNodeEntry 4}

   ifcpGatewayFcNodeIPA             OBJECT-TYPE
       SYNTAX                   OCTET STRING (SIZE(8))
       MAX-ACCESS               read-only
       STATUS                   current
       DESCRIPTION
   "The object identifies the FC Initial Process Associator
    of the node as defined in the ifcp Specification."
       ::= {ifcpGatewayFcNodeEntry 5}


   --
   -- ifcp session information --------------------------------------
   --


   ifcpGatewaySessionInfo     OBJECT IDENTIFIER ::= { ifcpGatewayObj 6}

   -- Session Attributes Table

   ifcpSessionAttributesTable OBJECT-TYPE
       SYNTAX                         SEQUENCE OF
   IfcpSessionAttributesEntry
       MAX-ACCESS                     not-accessible
       STATUS                         current

   Tseng                Expires February 2002                      16
   Internet Draft              iFCP MIB                    August 2001

       DESCRIPTION
           "."
   ::= { ifcpGatewaySessionInfo 1 }

   ifcpSessionAttributesEntry OBJECT-TYPE
       SYNTAX                         IfcpSessionAttributesEntry
       MAX-ACCESS                     not-accessible
       STATUS                         current
       DESCRIPTION
           "."
       INDEX { ifcpSsnIndex }
   ::= { ifcpSessionAttributesTable 1 }

   IfcpSessionAttributesEntry ::= SEQUENCE {
       ifcpSessionIndex              Unsigned32,
       ifcpSessionLocalNode          WWNtype,
       ifcpSessionRemoteNode         WWNtype
   }

   ifcpSessionIndex OBJECT-TYPE
       SYNTAX                         Unsigned32 (1..4294967295)
       MAX-ACCESS                     not-accessible
       STATUS                         current
       DESCRIPTION
           "The session index."
   ::= { ifcpSessionAttributesEntry 1 }

   ifcpSessionLocalNode    OBJECT-TYPE
       SYNTAX                         WWNtype
       MAX-ACCESS                     read-only
       STATUS                         current
       DESCRIPTION
           "World Wide Name of the local node."
   ::= { ifcpSessionAttributesEntry 2 }

   ifcpSessionRemoteNode    OBJECT-TYPE
       SYNTAX                         WWNtype
       MAX-ACCESS                     read-only
       STATUS                         current
       DESCRIPTION
           "World Wide Name of the remote node."
   ::= { ifcpSessionAttributesEntry 3 }

   --
   -- Statistics
   --

   ifcpSessionStatsTable OBJECT-TYPE
       SYNTAX                         SEQUENCE OF IfcpSessionStatsEntry
       MAX-ACCESS                     not-accessible
       STATUS                         current
       DESCRIPTION
           "."
   ::= { ifcpGatewaySessionInfo 2 }

   Tseng                Expires February 2002                      17
   Internet Draft              iFCP MIB                    August 2001


   ifcpSessionStatsEntry OBJECT-TYPE
       SYNTAX                         IfcpSessionStatsEntry
       MAX-ACCESS                     not-accessible
       STATUS                         current
       DESCRIPTION
           "."
       AUGMENTS { ifcpSessionAttributesEntry }
   ::= { ifcpSessionStatsTable 1 }

   IfcpSessionStatsEntry ::= SEQUENCE {
       ifcpSessionCmdPdus                Counter32,
       ifcpSessionRspPdus                Counter32,
       ifcpSessionTxDataOctets           Counter64,
       ifcpSessionRxDataOctets           Counter64,
       ifcpSessionCRCErrors              Counter32,
       ifcpSessionCxnTimeoutErrors       Counter32
   }

   ifcpSessionCmdPdus OBJECT-TYPE
       SYNTAX                         Counter32
       MAX-ACCESS                     read-only
       STATUS                         current
       DESCRIPTION
           "."
   ::= { ifcpSessionStatsEntry 1 }

   ifcpSessionRspPdus OBJECT-TYPE
       SYNTAX                         Counter32
       MAX-ACCESS                     read-only
       STATUS                         current
       DESCRIPTION
           "."
   ::= { ifcpSessionStatsEntry 2 }

   ifcpSessionTxDataOctets OBJECT-TYPE
       SYNTAX                         Counter64
       MAX-ACCESS                     read-only
       STATUS                         current
       DESCRIPTION
           "."
   ::= { ifcpSessionStatsEntry 3 }

   ifcpSessionRxDataOctets OBJECT-TYPE
       SYNTAX                         Counter64
       MAX-ACCESS                     read-only
       STATUS                         current
       DESCRIPTION
           "."
   ::= { ifcpSessionStatsEntry 4 }

   ifcpSessionCRCErrors OBJECT-TYPE
       SYNTAX                         Counter32
       MAX-ACCESS                     read-only

   Tseng                Expires February 2002                      18
   Internet Draft              iFCP MIB                    August 2001

       STATUS                         current
       DESCRIPTION
           "."
   ::= { ifcpSessionStatsEntry 5 }

   ifcpSessionCxnTimeoutErrors OBJECT-TYPE
       SYNTAX                         Counter32
       MAX-ACCESS                     read-only
       STATUS                         current
       DESCRIPTION
           "."
   ::= { ifcpSessionStatsEntry 6 }


   ------------------------------------------------------------

   ifcpGroups OBJECT IDENTIFIER ::= { ifcpGatewayConformance 1 }

   END

-- 
--       "Copyright (C) The Internet Society 2001. All Rights Reserved.
--       This document and translations of it may be copied and furnished
--       to others, and derivative works that comment on or otherwise
--       explain it or assist in its implementation may be prepared,
--       copied, published and distributed, in whole or in part, without
--       restriction of any kind, provided that the above copyright notice
--       and this paragraph are included on all such copies and derivative
--       works. However, this document itself may not be modified in any
--       way, such as by removing the copyright notice or references to
--       the Internet Society or other Internet organizations, except as
--       needed for the purpose of developing Internet standards in which
--       case the procedures for copyrights defined in the Internet
--       Standards process must be followed, or as required to translate
--       it into languages other than English.
-- 
--       The limited permissions granted above are perpetual and will not
--       be revoked by the Internet Society or its successors or assigns.
-- 
--       This document and the information contained herein is provided on
--       An "AS IS" basis and THE INTERNET SOCIETY AND THE INTERNET
--       ENGINEERING TASK FORCE DISCLAIMS ALL WARRANTIES, EXPRESS OR
--       IMPLIED, INCLUDING BUT NOT LIMITED TO ANY WARRANTY THAT THE USE
--       OF THE INFORMATION HEREIN WILL NOT INFRINGE ANY RIGHTS OR ANY
--       IMPLIED WARRANTIES OF MERCHANTABILITY OR FITNESS FOR A PARTICULAR
--       PURPOSE."
-- 
-- 
-- 
-- 
-- 
-- 
-- 
-- 
-- 
--    Tseng                Expires February 2002                      21
