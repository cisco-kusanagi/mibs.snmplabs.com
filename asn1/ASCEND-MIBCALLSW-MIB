--			Ascend mibcallsw MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBCALLSW-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibcallSwitchingProfile  OBJECT IDENTIFIER ::= { configuration 65}

	-- The mibcallSwitchingProfile table
	--
	-- This table contains parameters for the mibcallSwitchingProfile profile
	--

    mibcallSwitchingProfileTable	OBJECT-TYPE
	SYNTAX		SEQUENCE OF MibcallSwitchingProfileEntry
	ACCESS		not-accessible
	STATUS		mandatory
	DESCRIPTION	"A list of mibcallSwitchingProfile profile entries."
	::= { mibcallSwitchingProfile 1 }

    mibcallSwitchingProfileEntry	OBJECT-TYPE
	SYNTAX		MibcallSwitchingProfileEntry
	ACCESS		not-accessible
	STATUS		mandatory
	DESCRIPTION	"A mibcallSwitchingProfile entry containing objects that
			 maps to the parameters of mibcallSwitchingProfile profile."
	INDEX		{ callSwitchingProfile-Index-o }
	::= { mibcallSwitchingProfileTable 1 }

    MibcallSwitchingProfileEntry ::=
	SEQUENCE {
	    callSwitchingProfile-Index-o
		INTEGER,
	    callSwitchingProfile-Enabled
		INTEGER,
	    callSwitchingProfile-ComparisonRule-CallRouteEmptyPhoneNumberAcceptable
		INTEGER,
	    callSwitchingProfile-Action-o
		INTEGER
	}

    callSwitchingProfile-Index-o	OBJECT-TYPE
	SYNTAX	INTEGER
	ACCESS	read-only
	STATUS	mandatory
	DESCRIPTION	""
	::= { mibcallSwitchingProfileEntry 1 }

    callSwitchingProfile-Enabled	OBJECT-TYPE
	SYNTAX	INTEGER {
		    no (1),
		    yes (2)
		}
	ACCESS	read-write
	STATUS	mandatory
	DESCRIPTION	"This flag controls whether to search CALL-ROUTE profiles to detect if an incoming call needs to be passed through or routed to network side. When the flag is set to 'no', such procedure will not be used."
	::= { mibcallSwitchingProfileEntry 2 }

    callSwitchingProfile-ComparisonRule-CallRouteEmptyPhoneNumberAcceptable	OBJECT-TYPE
	SYNTAX	INTEGER {
		    no (1),
		    yes (2)
		}
	ACCESS	read-write
	STATUS	mandatory
	DESCRIPTION	"This flag tells whether CALL-ROUTE profiles with empty phone numbers should be used in comparison. If the flag is set to 'yes', empty phone number in a CALL-ROUTE profile will match any dialed number."
	::= { mibcallSwitchingProfileEntry 3 }

    callSwitchingProfile-Action-o	OBJECT-TYPE
	SYNTAX	INTEGER {
		    noAction (1),
		    createProfile (2),
		    deleteProfile (3)
		}
	ACCESS	read-write
	STATUS	mandatory
	DESCRIPTION	""
	::= { mibcallSwitchingProfileEntry 4 }

END
