TUBS-LINUX-MIB DEFINITIONS ::= BEGIN

IMPORTS
    MODULE-IDENTITY, OBJECT-TYPE, 
    Gauge32, enterprises, Counter32, Integer32, TimeTicks, Unsigned32
    	FROM SNMPv2-SMI
    DisplayString, RowStatus, DateAndTime, TruthValue, TimeStamp, TAddress
        FROM SNMPv2-TC
		AGENT-CAPABILITIES FROM SNMPv2-CONF;

linuxMIB MODULE-IDENTITY
     LAST-UPDATED "9607152024Z"
     ORGANIZATION "TU Braunschweig"
     CONTACT-INFO
              "        Juergen Schoenwaelder

               Postal: TU Braunschweig
                       Bueltenweg 74/75
                       D-38108 Braunschweig
                       GERMANY

                  Tel: +49 531 391 3249
                  Fax: +49 531 391 5936

               E-mail: schoenw@ibr.cs.tu-bs.de"
     DESCRIPTION
             "Experimental MIB modules for the linux operating system."
     ::= { enterprises tubs(1575) ibr(1) 5 }

linuxAgents OBJECT IDENTIFIER ::= { linuxMIB 1 }

linuxAgent3dot1 AGENT-CAPABILITIES
    PRODUCT-RELEASE	"cmu-snmp-linux-3.1"
    STATUS		current
    DESCRIPTION		"CMU SNMP v1.1b + SNMPv2 USEC + LINUX"

    SUPPORTS		SNMPv2-MIB
	INCLUDES	{ snmpGroup, snmpSetGroup, systemGroup,
		          snmpBasicNotificationsGroup,
			  snmpCommunityGroup }

    SUPPORTS		SNMPv2-USEC-MIB
	INCLUDES	{ usecBasicGroup, usecStatsGroup }

    SUPPORTS            IF-MIB
	INCLUDES	{ ifGeneralGroup, ifPacketGroup }
	VARIATION	ifLinkUpDownTrapEnable
	    ACCESS	not-implemented
	    DESCRIPTION	""
	VARIATION	ifConnectorPresent
	    ACCESS	not-implemented
	    DESCRIPTION	""
	VARIATION	ifName
	    ACCESS	not-implemented
	    DESCRIPTION	""
	VARIATION	ifHighSpeed
	    ACCESS	not-implemented
	    DESCRIPTION	""

	VARIATION	ifInMulticastPkts
	    ACCESS	not-implemented
	    DESCRIPTION	""
	VARIATION	ifInBroadcastPkts
	    ACCESS	not-implemented
	    DESCRIPTION	""
	VARIATION	ifOutMulticastPkts
	    ACCESS	not-implemented
	    DESCRIPTION	""
	VARIATION	ifOutBroadcastPkts
	    ACCESS	not-implemented
	    DESCRIPTION	""
	VARIATION	ifPromiscuousMode
	    ACCESS	not-implemented
	    DESCRIPTION	""

    SUPPORTS		IP-MIB
	INCLUDES	{ ipGroup,
			  icmpGroup }
	VARIATION	ipAdEntReasmMaxSize
	    ACCESS	not-implemented
	    DESCRIPTION	""
	VARIATION	ipNetToMediaIfIndex
	    ACCESS	not-implemented
	    DESCRIPTION	""
	VARIATION	ipNetToMediaPhysAddress
	    ACCESS	not-implemented
	    DESCRIPTION	""
	VARIATION	ipNetToMediaNetAddress
	    ACCESS	not-implemented
	    DESCRIPTION	""
	VARIATION	ipNetToMediaType
	    ACCESS	not-implemented
	    DESCRIPTION	""
	VARIATION	ipRoutingDiscards
	    ACCESS	not-implemented
	    DESCRIPTION	""

    SUPPORTS		TCP-MIB
	INCLUDES	{ tcpGroup }
	VARIATION	tcpInErrs
	    ACCESS	not-implemented
	    DESCRIPTION	""
	VARIATION	tcpOutRsts
	    ACCESS	not-implemented
	    DESCRIPTION	""

    SUPPORTS		UDP-MIB
	INCLUDES	{ udpGroup }
	VARIATION	udpLocalAddress
	    ACCESS	not-implemented
	    DESCRIPTION	""
	VARIATION	udpLocalPort
	    ACCESS	not-implemented
	    DESCRIPTION	""

    ::= { linuxAgents 1 }

linuxMIBObjects OBJECT IDENTIFIER ::= { linuxMIB 2 }

linuxCPU OBJECT-TYPE
	SYNTAX      DisplayString
	MAX-ACCESS  read-only
	STATUS      current
	DESCRIPTION
		"The identification of the linux CPU."
	::= { linuxMIBObjects 1 }

linuxBogo OBJECT-TYPE
	SYNTAX      Gauge32
	MAX-ACCESS  read-only
	STATUS      current
	DESCRIPTION
		"The number of BOGO MIPS of the linux system."
	::= { linuxMIBObjects 2 }

-- conformance information

linuxMIBConformance
               OBJECT IDENTIFIER ::= { linuxMIB 3 }

linuxMIBCompliances
               OBJECT IDENTIFIER ::= { linuxMIBConformance 1 }
linuxMIBGroups OBJECT IDENTIFIER ::= { linuxMIBConformance 2 }

END
