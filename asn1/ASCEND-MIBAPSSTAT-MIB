--			Ascend mibapsstat MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBAPSSTAT-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibapsStat  OBJECT IDENTIFIER ::= { configuration 149}

	-- The mibapsStat table
	--
	-- This table contains parameters for the mibapsStat profile
	--

    mibapsStatTable	OBJECT-TYPE
	SYNTAX		SEQUENCE OF MibapsStatEntry
	ACCESS		not-accessible
	STATUS		mandatory
	DESCRIPTION	"A list of mibapsStat profile entries."
	::= { mibapsStat 1 }

    mibapsStatEntry	OBJECT-TYPE
	SYNTAX		MibapsStatEntry
	ACCESS		not-accessible
	STATUS		mandatory
	DESCRIPTION	"A mibapsStat entry containing objects that
			 maps to the parameters of mibapsStat profile."
	INDEX		{ apsStat-Name }
	::= { mibapsStatTable 1 }

    MibapsStatEntry ::=
	SEQUENCE {
	    apsStat-Name
		DisplayString,
	    apsStat-ProtectionChannel-Shelf
		INTEGER,
	    apsStat-ProtectionChannel-Slot
		INTEGER,
	    apsStat-ProtectionChannel-ItemNumber
		INTEGER,
	    apsStat-WorkingChannel-Shelf
		INTEGER,
	    apsStat-WorkingChannel-Slot
		INTEGER,
	    apsStat-WorkingChannel-ItemNumber
		INTEGER,
	    apsStat-ApsState
		INTEGER,
	    apsStat-BridgeStatus
		INTEGER,
	    apsStat-LastSwitchTime
		INTEGER,
	    apsStat-SwitchCount
		INTEGER,
	    apsStat-ApsCfgCreationTime
		INTEGER,
	    apsStat-NumberOfChannels
		INTEGER,
	    apsStat-PsbfFailure
		INTEGER,
	    apsStat-ChannelMismatchFailure
		INTEGER,
	    apsStat-ModeMismatchFailure
		INTEGER,
	    apsStat-FeplFailure
		INTEGER,
	    apsStat-RecvPsbfCount
		INTEGER,
	    apsStat-RecvModeMismatchCount
		INTEGER,
	    apsStat-RecvChannelMismatchCount
		INTEGER,
	    apsStat-RecvFeplCount
		INTEGER,
	    apsStat-ExtraTrafficFlag
		INTEGER,
	    apsStat-ProtectionMode
		INTEGER,
	    apsStat-DirectionMode
		INTEGER,
	    apsStat-RevertiveMode
		INTEGER,
	    apsStat-RxK1ByteValue
		DisplayString,
	    apsStat-RxK2ByteValue
		DisplayString,
	    apsStat-TxK1ByteValue
		DisplayString,
	    apsStat-TxK2ByteValue
		DisplayString,
	    apsStat-Action-o
		INTEGER
	}

    apsStat-Name	OBJECT-TYPE
	SYNTAX	DisplayString
	ACCESS	read-only
	STATUS	mandatory
	DESCRIPTION	"Name of APS protection group (aps-config profile)."
	::= { mibapsStatEntry 1 }

    apsStat-ProtectionChannel-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibapsStatEntry 2 }

    apsStat-ProtectionChannel-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibapsStatEntry 3 }

    apsStat-ProtectionChannel-ItemNumber	OBJECT-TYPE
	SYNTAX	INTEGER
	ACCESS	read-write
	STATUS	mandatory
	DESCRIPTION	"A number that specifies an addressable entity within the context of shelf and slot."
	::= { mibapsStatEntry 4 }

    apsStat-WorkingChannel-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibapsStatEntry 43 }

    apsStat-WorkingChannel-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibapsStatEntry 44 }

    apsStat-WorkingChannel-ItemNumber	OBJECT-TYPE
	SYNTAX	INTEGER
	ACCESS	read-write
	STATUS	mandatory
	DESCRIPTION	"A number that specifies an addressable entity within the context of shelf and slot."
	::= { mibapsStatEntry 45 }

    apsStat-ApsState	OBJECT-TYPE
	SYNTAX	INTEGER {
		    unknown (1),
		    onProtection (2),
		    onWorking (3)
		}
	ACCESS	read-only
	STATUS	mandatory
	DESCRIPTION	"Current status of the protection switching."
	::= { mibapsStatEntry 8 }

    apsStat-BridgeStatus	OBJECT-TYPE
	SYNTAX	INTEGER {
		    false (1),
		    true (2)
		}
	ACCESS	read-only
	STATUS	mandatory
	DESCRIPTION	"Status of the bridge. True if bridging is on (always on for 1+1)."
	::= { mibapsStatEntry 47 }

    apsStat-LastSwitchTime	OBJECT-TYPE
	SYNTAX	INTEGER
	ACCESS	read-only
	STATUS	mandatory
	DESCRIPTION	"Time of last switch."
	::= { mibapsStatEntry 48 }

    apsStat-SwitchCount	OBJECT-TYPE
	SYNTAX	INTEGER
	ACCESS	read-only
	STATUS	mandatory
	DESCRIPTION	"Number of times switch over to protection channel occured."
	::= { mibapsStatEntry 49 }

    apsStat-ApsCfgCreationTime	OBJECT-TYPE
	SYNTAX	INTEGER
	ACCESS	read-only
	STATUS	mandatory
	DESCRIPTION	"Time the protection group was created."
	::= { mibapsStatEntry 50 }

    apsStat-NumberOfChannels	OBJECT-TYPE
	SYNTAX	INTEGER
	ACCESS	read-only
	STATUS	mandatory
	DESCRIPTION	"Number of channels in this protection group."
	::= { mibapsStatEntry 51 }

    apsStat-PsbfFailure	OBJECT-TYPE
	SYNTAX	INTEGER {
		    false (1),
		    true (2)
		}
	ACCESS	read-only
	STATUS	mandatory
	DESCRIPTION	"PSBF state."
	::= { mibapsStatEntry 52 }

    apsStat-ChannelMismatchFailure	OBJECT-TYPE
	SYNTAX	INTEGER {
		    false (1),
		    true (2)
		}
	ACCESS	read-only
	STATUS	mandatory
	DESCRIPTION	"Channel mismatch state."
	::= { mibapsStatEntry 53 }

    apsStat-ModeMismatchFailure	OBJECT-TYPE
	SYNTAX	INTEGER {
		    false (1),
		    true (2)
		}
	ACCESS	read-only
	STATUS	mandatory
	DESCRIPTION	"Mode mismatch state."
	::= { mibapsStatEntry 54 }

    apsStat-FeplFailure	OBJECT-TYPE
	SYNTAX	INTEGER {
		    false (1),
		    true (2)
		}
	ACCESS	read-only
	STATUS	mandatory
	DESCRIPTION	"FEPL state."
	::= { mibapsStatEntry 55 }

    apsStat-RecvPsbfCount	OBJECT-TYPE
	SYNTAX	INTEGER
	ACCESS	read-only
	STATUS	mandatory
	DESCRIPTION	"Count of PSBF events received."
	::= { mibapsStatEntry 29 }

    apsStat-RecvModeMismatchCount	OBJECT-TYPE
	SYNTAX	INTEGER
	ACCESS	read-only
	STATUS	mandatory
	DESCRIPTION	"Count of mode-mismatch events received."
	::= { mibapsStatEntry 30 }

    apsStat-RecvChannelMismatchCount	OBJECT-TYPE
	SYNTAX	INTEGER
	ACCESS	read-only
	STATUS	mandatory
	DESCRIPTION	"Count of channel-mismatch events received."
	::= { mibapsStatEntry 31 }

    apsStat-RecvFeplCount	OBJECT-TYPE
	SYNTAX	INTEGER
	ACCESS	read-only
	STATUS	mandatory
	DESCRIPTION	"Count of FEPL events received."
	::= { mibapsStatEntry 32 }

    apsStat-ExtraTrafficFlag	OBJECT-TYPE
	SYNTAX	INTEGER {
		    false (1),
		    true (2)
		}
	ACCESS	read-only
	STATUS	mandatory
	DESCRIPTION	"Indicates whether extra traffic is being carried on protection channel (1:n only)."
	::= { mibapsStatEntry 33 }

    apsStat-ProtectionMode	OBJECT-TYPE
	SYNTAX	INTEGER {
		    n-1-plus-1 (1),
		    n-1-divide-n (2)
		}
	ACCESS	read-only
	STATUS	mandatory
	DESCRIPTION	"The linear APS protection mode (1+1, 1:n)."
	::= { mibapsStatEntry 5 }

    apsStat-DirectionMode	OBJECT-TYPE
	SYNTAX	INTEGER {
		    unidirectional (1),
		    bidirectional (2)
		}
	ACCESS	read-only
	STATUS	mandatory
	DESCRIPTION	"The protection group mode (direction) of operation."
	::= { mibapsStatEntry 6 }

    apsStat-RevertiveMode	OBJECT-TYPE
	SYNTAX	INTEGER {
		    nonRevertive (2),
		    revertive (1)
		}
	ACCESS	read-only
	STATUS	mandatory
	DESCRIPTION	"The protection group revertive mode of operation."
	::= { mibapsStatEntry 7 }

    apsStat-RxK1ByteValue	OBJECT-TYPE
	SYNTAX	DisplayString
	ACCESS	read-only
	STATUS	mandatory
	DESCRIPTION	"Current value of K1 byte received on protection channel"
	::= { mibapsStatEntry 34 }

    apsStat-RxK2ByteValue	OBJECT-TYPE
	SYNTAX	DisplayString
	ACCESS	read-only
	STATUS	mandatory
	DESCRIPTION	"Current value of K2 byte received on protection channel"
	::= { mibapsStatEntry 35 }

    apsStat-TxK1ByteValue	OBJECT-TYPE
	SYNTAX	DisplayString
	ACCESS	read-only
	STATUS	mandatory
	DESCRIPTION	"Last value of K1 byte transmitted on protection channel"
	::= { mibapsStatEntry 36 }

    apsStat-TxK2ByteValue	OBJECT-TYPE
	SYNTAX	DisplayString
	ACCESS	read-only
	STATUS	mandatory
	DESCRIPTION	"Last value of K2 byte transmitted on protection channel"
	::= { mibapsStatEntry 37 }

    apsStat-Action-o	OBJECT-TYPE
	SYNTAX	INTEGER {
		    noAction (1),
		    createProfile (2),
		    deleteProfile (3)
		}
	ACCESS	read-write
	STATUS	mandatory
	DESCRIPTION	""
	::= { mibapsStatEntry 42 }

END
