ELTEX-MES-QOS-TAIL-DROP-MIB DEFINITIONS ::= BEGIN

-- Title:      Eltex MES QoS Tail-Drop Configuration
-- Version:    1.2
-- Date:       11-Feb-2016

IMPORTS
    MODULE-IDENTITY, OBJECT-TYPE                FROM SNMPv2-SMI
    TruthValue                                  FROM SNMPv2-TC
    ifIndex                                     FROM IF-MIB
    eltMes, eltMesQosTailDropMib                FROM ELTEX-MES;

--
-- MIB Groups
--
eltMesQosTailDropMibMIBObjects OBJECT IDENTIFIER ::=
                                { eltMesQosTailDropMib 1 }

eltMesQosTailDropConfig        OBJECT IDENTIFIER ::=
                                { eltMesQosTailDropMibMIBObjects 1 }

eltMesQosTailDropStatus        OBJECT IDENTIFIER ::=
                                { eltMesQosTailDropMibMIBObjects 2 }

--
-- Configuration - Profile Queue table
--

eltQosTailDropProfileQueueTable OBJECT-TYPE
    SYNTAX SEQUENCE OF EltQosTailDropProfileQueueEntry
    MAX-ACCESS not-accessible
    STATUS current
    DESCRIPTION
        "The table lists queues configuration in QoS Tail-Drop Profiles."
    ::= { eltMesQosTailDropConfig 1 }

eltQosTailDropProfileQueueEntry OBJECT-TYPE
    SYNTAX      EltQosTailDropProfileQueueEntry
    MAX-ACCESS  not-accessible
    STATUS      current
    DESCRIPTION
        "An entry containing queues configuration in QoS Tail-Drop Profile."
    INDEX { eltQosTailDropProfileIndex, eltQosTailDropProfileQueueIndex }
    ::= { eltQosTailDropProfileQueueTable 1 }

EltQosTailDropProfileQueueEntry ::= SEQUENCE {
    eltQosTailDropProfileIndex                          INTEGER,
    eltQosTailDropProfileQueueIndex                     INTEGER,
    eltQosTailDropProfileQueueSharedPoolUsage           TruthValue,
    eltQosTailDropProfileQueueLimit                     INTEGER
}

eltQosTailDropProfileIndex OBJECT-TYPE
    SYNTAX INTEGER
    MAX-ACCESS not-accessible
    STATUS current
    DESCRIPTION
        "Profile index."
    ::= { eltQosTailDropProfileQueueEntry 1 }

eltQosTailDropProfileQueueIndex OBJECT-TYPE
    SYNTAX INTEGER
    MAX-ACCESS not-accessible
    STATUS current
    DESCRIPTION
        "Queue index."
    ::= { eltQosTailDropProfileQueueEntry 2 }

eltQosTailDropProfileQueueSharedPoolUsage OBJECT-TYPE
    SYNTAX TruthValue
    MAX-ACCESS read-write
    STATUS current
    DESCRIPTION
        "Enable/Disable shared pool usage."
    DEFVAL  { true }
    ::= { eltQosTailDropProfileQueueEntry 3 }

eltQosTailDropProfileQueueLimit OBJECT-TYPE
    SYNTAX INTEGER
    MAX-ACCESS read-write
    STATUS current
    DESCRIPTION
        "Limit in packets per queue."
    ::= { eltQosTailDropProfileQueueEntry 4 }

--
-- Configuration - Interface profile table
--

eltQosTailDropIfConfigTable OBJECT-TYPE
    SYNTAX SEQUENCE OF EltQosTailDropIfConfigEntry
    MAX-ACCESS not-accessible
    STATUS current
    DESCRIPTION
        "This table specifies for each interface
         the QoS Tail-Drop Profile attached to it."
    ::= { eltMesQosTailDropConfig 2 }

eltQosTailDropIfConfigEntry OBJECT-TYPE
    SYNTAX EltQosTailDropIfConfigEntry
    MAX-ACCESS not-accessible
    STATUS current
    DESCRIPTION
        "Each entry in this table describes what QoS Tail-Drop Profile
         attached to a specific interface."
    INDEX { ifIndex }
    ::= { eltQosTailDropIfConfigTable 1 }

EltQosTailDropIfConfigEntry ::= SEQUENCE {
    eltQosTailDropIfProfileIndex                INTEGER
}

eltQosTailDropIfProfileIndex OBJECT-TYPE
    SYNTAX INTEGER
    MAX-ACCESS read-write
    STATUS current
    DESCRIPTION
        "Index of the QoS Tail-Drop Profile attached to this port.
         Value of 0 means that no user profile is attached to port."
    DEFVAL { 0 }
    ::= { eltQosTailDropIfConfigEntry 1 }

--
-- Configuration - buffers and descriptors table
--

eltQosTailDropConfigTable OBJECT-TYPE
    SYNTAX SEQUENCE OF EltQosTailDropConfigEntry
    MAX-ACCESS not-accessible
    STATUS current
    DESCRIPTION
        "This table contains configuration of buffers and descriptors limits for system."
    ::= { eltMesQosTailDropConfig 3 }


eltQosTailDropConfigEntry OBJECT-TYPE
    SYNTAX EltQosTailDropConfigEntry
    MAX-ACCESS not-accessible
    STATUS current
    DESCRIPTION
        "Qos TailDrop Configuration Table entry."
    INDEX { eltQosTailDropConfigUnitId }
    ::= { eltQosTailDropConfigTable 1 }

EltQosTailDropConfigEntry ::= SEQUENCE {
    eltQosTailDropConfigUnitId                          INTEGER,
    eltQosTailDropConfigPhysicalBuffersLimit            INTEGER,
    eltQosTailDropConfigTotalDescriptorsLimit           INTEGER,
    eltQosTailDropConfigTotalBuffersLimit               INTEGER,
    eltQosTailDropConfigMCDescriptorsLimit              INTEGER,
    eltQosTailDropConfigMCBuffersLimit                  INTEGER,
    eltQosTailDropConfigSharedDescriptorsLimit          INTEGER,
    eltQosTailDropConfigSharedBuffersLimit              INTEGER
}

eltQosTailDropConfigUnitId OBJECT-TYPE
    SYNTAX      INTEGER
    MAX-ACCESS  read-only
    STATUS      current
    DESCRIPTION
        "The stack unit described by this entry."
    ::= { eltQosTailDropConfigEntry 1 }

eltQosTailDropConfigPhysicalBuffersLimit OBJECT-TYPE
    SYNTAX      INTEGER
    MAX-ACCESS  read-only
    STATUS      current
    DESCRIPTION
        "Maximum number of physical buffers."
    ::= { eltQosTailDropConfigEntry 2 }

eltQosTailDropConfigTotalDescriptorsLimit OBJECT-TYPE
    SYNTAX      INTEGER
    MAX-ACCESS  read-only
    STATUS      current
    DESCRIPTION
        "Maximum number of mc, shared and others descriptors
         that may be enqueued to all transmit queues."
    ::= { eltQosTailDropConfigEntry 3 }

eltQosTailDropConfigTotalBuffersLimit OBJECT-TYPE
    SYNTAX      INTEGER
    MAX-ACCESS  read-only
    STATUS      current
    DESCRIPTION
        "Maximum number of mc, shared and others buffers
         that may be enqueued to all transmit queues."
    ::= { eltQosTailDropConfigEntry 4 }

eltQosTailDropConfigMCDescriptorsLimit OBJECT-TYPE
    SYNTAX      INTEGER
    MAX-ACCESS  read-only
    STATUS      current
    DESCRIPTION
        "Maximum number of descriptors that may be allocated
         for multicast packets."
    ::= { eltQosTailDropConfigEntry 5 }

eltQosTailDropConfigMCBuffersLimit OBJECT-TYPE
    SYNTAX      INTEGER
    MAX-ACCESS  read-only
    STATUS      current
    DESCRIPTION
        "Maximum number of buffers that may be used
         for multicast packets."
    ::= { eltQosTailDropConfigEntry 6 }

eltQosTailDropConfigSharedDescriptorsLimit OBJECT-TYPE
    SYNTAX      INTEGER
    MAX-ACCESS  read-only
    STATUS      current
    DESCRIPTION
        "Maximum number of descriptors in shared pool that
        may be used by all ports and queues."
    ::= { eltQosTailDropConfigEntry 7 }

eltQosTailDropConfigSharedBuffersLimit OBJECT-TYPE
    SYNTAX      INTEGER
    MAX-ACCESS  read-only
    STATUS      current
    DESCRIPTION
        "Maximum number of buffers in shared pool that
        may be used by all ports and queues."
    ::= { eltQosTailDropConfigEntry 8 }

--
-- Configuration - Profile table
--

eltQosTailDropProfileTable OBJECT-TYPE
	SYNTAX SEQUENCE OF EltQosTailDropProfileEntry
	MAX-ACCESS not-accessible
    STATUS current
    DESCRIPTION
        "The table lists the QoS Tail-Drop Profiles."
    ::= { eltMesQosTailDropConfig 4 }

eltQosTailDropProfileEntry OBJECT-TYPE
    SYNTAX      EltQosTailDropProfileEntry
    MAX-ACCESS  not-accessible
    STATUS      current
    DESCRIPTION
        "An entry containing QoS Tail-Drop Profile information."
    INDEX { eltQosTailDropProfile }
    ::= { eltQosTailDropProfileTable 1 }

EltQosTailDropProfileEntry ::= SEQUENCE {
    eltQosTailDropProfile              INTEGER,
    eltQosTailDropProfilePortLimit     INTEGER
}

eltQosTailDropProfile OBJECT-TYPE
	SYNTAX      INTEGER
    MAX-ACCESS  not-accessible
    STATUS      current
	DESCRIPTION "Profile index."
    ::= { eltQosTailDropProfileEntry 1 }

eltQosTailDropProfilePortLimit OBJECT-TYPE
	SYNTAX      INTEGER
    MAX-ACCESS  read-write
    STATUS      current
	DESCRIPTION "Port limit in packets."
    ::= { eltQosTailDropProfileEntry 2 }

--
-- Status - global buffers and descriptors table
--

eltQosTailDropStatusTable OBJECT-TYPE
    SYNTAX SEQUENCE OF EltQosTailDropStatusEntry
    MAX-ACCESS not-accessible
    STATUS current
    DESCRIPTION
        "This table contains information about buffers and
         descriptors currently enqueued in the system."
    ::= { eltMesQosTailDropStatus 1 }


eltQosTailDropStatusEntry OBJECT-TYPE
    SYNTAX EltQosTailDropStatusEntry
    MAX-ACCESS not-accessible
    STATUS current
    DESCRIPTION
        "Qos TailDrop Status Table entry."
    INDEX { eltQosTailDropStatusUnitId }
    ::= { eltQosTailDropStatusTable 1 }

EltQosTailDropStatusEntry ::= SEQUENCE {
    eltQosTailDropStatusUnitId                             INTEGER,
    eltQosTailDropStatusPhysicalBuffersEnqueuedCounter     INTEGER,
    eltQosTailDropStatusTotalDescriptorsEnqueuedCounter    INTEGER,
    eltQosTailDropStatusTotalBuffersEnqueuedCounter        INTEGER,
    eltQosTailDropStatusTotalMCDescriptorsEnqueuedCounter  INTEGER,
    eltQosTailDropStatusTotalMCBuffersEnqueuedCounter      INTEGER,
    eltQosTailDropStatusSharedDescriptorsEnqueuedCounter   INTEGER,
    eltQosTailDropStatusSharedBuffersEnqueuedCounter       INTEGER
}

eltQosTailDropStatusUnitId OBJECT-TYPE
    SYNTAX      INTEGER
    MAX-ACCESS  read-only
    STATUS      current
    DESCRIPTION
        "The stack unit described by this entry."
    ::= { eltQosTailDropStatusEntry 1 }

eltQosTailDropStatusPhysicalBuffersEnqueuedCounter OBJECT-TYPE
    SYNTAX      INTEGER
    MAX-ACCESS  read-only
    STATUS      current
    DESCRIPTION
        "Total number of physical buffers currently allocated in a system."
    ::= { eltQosTailDropStatusEntry 2 }

eltQosTailDropStatusTotalDescriptorsEnqueuedCounter OBJECT-TYPE
    SYNTAX      INTEGER
    MAX-ACCESS  read-only
    STATUS      current
    DESCRIPTION
        "Total number of mc, shared and others descriptors enqueued."
    ::= { eltQosTailDropStatusEntry 3 }

eltQosTailDropStatusTotalBuffersEnqueuedCounter OBJECT-TYPE
    SYNTAX      INTEGER
    MAX-ACCESS  read-only
    STATUS      current
    DESCRIPTION
        "Total number of buffers enqueued."
    ::= { eltQosTailDropStatusEntry 4 }

eltQosTailDropStatusTotalMCDescriptorsEnqueuedCounter OBJECT-TYPE
    SYNTAX      INTEGER
    MAX-ACCESS  read-only
    STATUS      current
    DESCRIPTION
        "Total number of multicast packets descriptors currently enqueued."
    ::= { eltQosTailDropStatusEntry 5 }

eltQosTailDropStatusTotalMCBuffersEnqueuedCounter OBJECT-TYPE
    SYNTAX      INTEGER
    MAX-ACCESS  read-only
    STATUS      current
    DESCRIPTION
        "Total number of multicast buffers enqueued."
    ::= { eltQosTailDropStatusEntry 6 }

eltQosTailDropStatusSharedDescriptorsEnqueuedCounter OBJECT-TYPE
    SYNTAX      INTEGER
    MAX-ACCESS  read-only
    STATUS      current
    DESCRIPTION
        "Total shared pool usage."
    ::= { eltQosTailDropStatusEntry 7 }

eltQosTailDropStatusSharedBuffersEnqueuedCounter OBJECT-TYPE
    SYNTAX      INTEGER
    MAX-ACCESS  read-only
    STATUS      current
    DESCRIPTION
        "Total shared pool usage."
    ::= { eltQosTailDropStatusEntry 8 }

--
-- Status - interface buffers and descriptors usage table
--

eltQosTailDropIfStatusTable OBJECT-TYPE
    SYNTAX SEQUENCE OF EltQosIfTailDropStatusEntry
    MAX-ACCESS not-accessible
    STATUS current
    DESCRIPTION
        "This table contains information about buffers and
         descriptors usage per interface."
    ::= { eltMesQosTailDropStatus 2 }

eltQosTailDropIfStatusEntry OBJECT-TYPE
    SYNTAX EltQosIfTailDropStatusEntry
    MAX-ACCESS not-accessible
    STATUS current
    DESCRIPTION
        "Qos TailDrop Interface Counters Table entry."
    INDEX { ifIndex }
    ::= { eltQosTailDropIfStatusTable 1 }

EltQosIfTailDropStatusEntry ::= SEQUENCE {
    eltQosTailDropIfStatusEnqueuedDescriptorsCounter  INTEGER,
    eltQosTailDropIfStatusEnqueuedBuffersCounter      INTEGER,
    eltQosTailDropIfStatusDescriptorsLimit            INTEGER,
    eltQosTailDropIfStatusBuffersLimit                INTEGER
}

eltQosTailDropIfStatusEnqueuedDescriptorsCounter OBJECT-TYPE
    SYNTAX      INTEGER
    MAX-ACCESS  read-only
    STATUS      current
    DESCRIPTION
        "Total number of descriptors enqueued to all the port's queues."
    ::= { eltQosTailDropIfStatusEntry 1 }

eltQosTailDropIfStatusEnqueuedBuffersCounter OBJECT-TYPE
    SYNTAX      INTEGER
    MAX-ACCESS  read-only
    STATUS      current
    DESCRIPTION
        "Total number of buffers enqueued to all the port's queues."
    ::= { eltQosTailDropIfStatusEntry 2 }

eltQosTailDropIfStatusDescriptorsLimit OBJECT-TYPE
    SYNTAX      INTEGER
    MAX-ACCESS  read-only
    STATUS      current
    DESCRIPTION
        "Shared pool usage limit by the port."
    ::= { eltQosTailDropIfStatusEntry 3 }

eltQosTailDropIfStatusBuffersLimit OBJECT-TYPE
    SYNTAX      INTEGER
    MAX-ACCESS  read-only
    STATUS      current
    DESCRIPTION
        "Shared pool usage limit by the port."
    ::= { eltQosTailDropIfStatusEntry 4 }

--
-- Status - interface/queue buffers and descriptors usage table
--

eltQosTailDropIfQueueStatusTable OBJECT-TYPE
    SYNTAX SEQUENCE OF EltQosIfTailDropQueueStatusEntry
    MAX-ACCESS not-accessible
    STATUS current
    DESCRIPTION
        "This table contains information about buffers and descriptors enqueued
         per interface and queue."
    ::= { eltMesQosTailDropStatus 3 }

eltQosTailDropIfQueueStatusEntry OBJECT-TYPE
    SYNTAX EltQosIfTailDropQueueStatusEntry
    MAX-ACCESS not-accessible
    STATUS current
    DESCRIPTION
        "Qos TailDrop Interface/Queue Counters Table entry."
    INDEX { ifIndex, eltQosTailDropIfQueueStatusQueueIndex }
    ::= { eltQosTailDropIfQueueStatusTable 1 }

EltQosIfTailDropQueueStatusEntry ::= SEQUENCE {
    eltQosTailDropIfQueueStatusQueueIndex                       INTEGER,
    eltQosTailDropIfQueueStatusTotalDescriptorsEnqueuedCounter  INTEGER,
    eltQosTailDropIfQueueStatusTotalBuffersEnqueuedCounter      INTEGER,
    eltQosTailDropIfQueueStatusDP0BuffersLimit                  INTEGER,
    eltQosTailDropIfQueueStatusDP1BuffersLimit                  INTEGER,
    eltQosTailDropIfQueueStatusDP2BuffersLimit                  INTEGER,
    eltQosTailDropIfQueueStatusDP0DescriptorsLimit              INTEGER,
    eltQosTailDropIfQueueStatusDP1DescriptorsLimit              INTEGER,
    eltQosTailDropIfQueueStatusDP2DescriptorsLimit              INTEGER
}

eltQosTailDropIfQueueStatusQueueIndex OBJECT-TYPE
    SYNTAX      INTEGER
    MAX-ACCESS  read-write
    STATUS      current
    DESCRIPTION
        "Queue index."
    ::= { eltQosTailDropIfQueueStatusEntry 1 }

eltQosTailDropIfQueueStatusTotalDescriptorsEnqueuedCounter OBJECT-TYPE
    SYNTAX      INTEGER
    MAX-ACCESS  read-only
    STATUS      current
    DESCRIPTION
        "Total number of descriptors enqueued to port's queue."
    ::= { eltQosTailDropIfQueueStatusEntry 2 }

eltQosTailDropIfQueueStatusTotalBuffersEnqueuedCounter OBJECT-TYPE
    SYNTAX      INTEGER
    MAX-ACCESS  read-only
    STATUS      current
    DESCRIPTION
        "Total number of buffers enqueued to port's queue."
    ::= { eltQosTailDropIfQueueStatusEntry 3 }

eltQosTailDropIfQueueStatusDP0BuffersLimit OBJECT-TYPE
    SYNTAX      INTEGER
    MAX-ACCESS  read-only
    STATUS      current
    DESCRIPTION
        "Number of GREEN packets buffers that may be enqueued to port's queue."
    ::= { eltQosTailDropIfQueueStatusEntry 4 }

eltQosTailDropIfQueueStatusDP1BuffersLimit OBJECT-TYPE
    SYNTAX      INTEGER
    MAX-ACCESS  read-only
    STATUS      current
    DESCRIPTION
        "Number of YELLOW packets buffers that may be enqueued to port's queue."
    ::= { eltQosTailDropIfQueueStatusEntry 5 }

eltQosTailDropIfQueueStatusDP2BuffersLimit OBJECT-TYPE
    SYNTAX      INTEGER
    MAX-ACCESS  read-only
    STATUS      current
    DESCRIPTION
        "Number of RED packets buffers that may be enqueued to port's queue."
    ::= { eltQosTailDropIfQueueStatusEntry 6 }

eltQosTailDropIfQueueStatusDP0DescriptorsLimit OBJECT-TYPE
    SYNTAX      INTEGER
    MAX-ACCESS  read-only
    STATUS      current
    DESCRIPTION
        "Number of GREEN packets descriptors that may be enqueued to port's queue."
    ::= { eltQosTailDropIfQueueStatusEntry 7 }

eltQosTailDropIfQueueStatusDP1DescriptorsLimit OBJECT-TYPE
    SYNTAX      INTEGER
    MAX-ACCESS  read-only
    STATUS      current
    DESCRIPTION
        "Number of YELLOW packets descriptors that may be enqueued to port's queue."
    ::= { eltQosTailDropIfQueueStatusEntry 8 }

eltQosTailDropIfQueueStatusDP2DescriptorsLimit OBJECT-TYPE
    SYNTAX      INTEGER
    MAX-ACCESS  read-only
    STATUS      current
    DESCRIPTION
        "Number of RED packets descriptors that may be enqueued to port's queue."
    ::= { eltQosTailDropIfQueueStatusEntry 9 }


END
