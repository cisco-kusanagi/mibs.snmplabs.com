BAS-PBRF-OSPF-MIB DEFINITIONS ::= BEGIN

IMPORTS
    MODULE-IDENTITY, OBJECT-TYPE, IpAddress, Integer32  FROM SNMPv2-SMI
    RowStatus                                           FROM SNMPv2-TC
    BasChassisId, BasSlotId, BasInterfaceId,
    BasLogicalPortId, basPbrfOSPF                       FROM BAS-MIB;

basPbrfOSPFMIB MODULE-IDENTITY
    LAST-UPDATED "9812220800Z"
    ORGANIZATION "Broadband Access Systems, Inc."
    CONTACT-INFO
        " Tech Support
          Broadband Access Systems, Inc.
          201 Forest Street
          Marlborough, MA 01752
          USA

          508-485-8200
          support@basystems.com"
    DESCRIPTION
        "The MIB module defines the configuration MIB objects
         for Broadband Access Systems, Inc. OSPF Export
	 policy based routing filters."
    ::= { basPbrfOSPF 1 }

basPbrfOSPFImport  OBJECT IDENTIFIER ::= { basPbrfOSPFMIB 1 }
basPbrfOSPFExport  OBJECT IDENTIFIER ::= { basPbrfOSPFMIB 2 }

-- the BAS OSPF Import PBRF filter table

-- The BAS OSPF Import PBRF filter table contains BAS proprietary
-- information of a BAS OSPF Import PBRF filter.

basPbrfOSPFImportTable OBJECT-TYPE
    SYNTAX      SEQUENCE OF BasPbrfOSPFImportEntry
    MAX-ACCESS  not-accessible
    STATUS      current
    DESCRIPTION
        "A table of OSPF import PBRF test filter entries."
    ::= { basPbrfOSPFImport 1 }

basPbrfOSPFImportEntry OBJECT-TYPE
    SYNTAX      BasPbrfOSPFImportEntry
    MAX-ACCESS  not-accessible
    STATUS      current
    DESCRIPTION
        "An entry containing management information applicable
        to an OSPF import PBRF filter used for testing the
        filter."
    INDEX { basPbrfOSPFImportChassis,
            basPbrfOSPFImportSlot,
            basPbrfOSPFImportIf,
            basPbrfOSPFImportLPort,
            basPbrfOSPFImportIndex }
    ::= { basPbrfOSPFImportTable 1 }

BasPbrfOSPFImportEntry ::=
    SEQUENCE {
        basPbrfOSPFImportChassis         BasChassisId,
        basPbrfOSPFImportSlot            BasSlotId,
        basPbrfOSPFImportIf              BasInterfaceId,
        basPbrfOSPFImportLPort           BasLogicalPortId,
        basPbrfOSPFImportIndex           Integer32,
        -- basPbrfOSPFImportTestStatus      INTEGER,
        basPbrfOSPFImportTemplateCount   Integer32,
        basPbrfOSPFImportRowStatus       RowStatus,
	basPbrfOSPFImportDescr           OCTET STRING
    }

basPbrfOSPFImportChassis OBJECT-TYPE
    SYNTAX      BasChassisId
    MAX-ACCESS  not-accessible
    STATUS      current
    DESCRIPTION
        "The chassis identifier of this chassis."
    ::= { basPbrfOSPFImportEntry 1 }

basPbrfOSPFImportSlot OBJECT-TYPE
    SYNTAX      BasSlotId
    MAX-ACCESS  not-accessible
    STATUS      current
    DESCRIPTION
        "The BAS slot ID of this card."
    ::= { basPbrfOSPFImportEntry 2 }

basPbrfOSPFImportIf OBJECT-TYPE
    SYNTAX      BasInterfaceId
    MAX-ACCESS  not-accessible
    STATUS      current
    DESCRIPTION
        "The BAS interface ID of this card."
    ::= { basPbrfOSPFImportEntry 3 }

basPbrfOSPFImportLPort OBJECT-TYPE
    SYNTAX      BasLogicalPortId
    MAX-ACCESS  not-accessible
    STATUS      current
    DESCRIPTION
        "The BAS logical port ID of this card."
    ::= { basPbrfOSPFImportEntry 4 }

basPbrfOSPFImportIndex OBJECT-TYPE
    SYNTAX      Integer32
    MAX-ACCESS  not-accessible
    STATUS      current
    DESCRIPTION
        "The index of the filter."
    ::= { basPbrfOSPFImportEntry 5 }

-- basPbrfOSPFImportTestStatus OBJECT-TYPE
--    SYNTAX      INTEGER {
--                        startTest(1),
--                        testing(2),
--                        testSucceed(3),
--                        testFail(4),
--                        notTested(5)
--                }
--    MAX-ACCESS  read-create
--    STATUS      current
--    DESCRIPTION
--        "The status of validating the filter. The value
--        startTest(1) is the only value that my be specified
--        in a write operation. The values testing(2),
--        testSucceed(3), testFail(4), and notTested(5) may be
--        returned by a read operation."
--    DEFVAL { notTested }
--    ::= { basPbrfOSPFImportEntry 6 }

basPbrfOSPFImportTemplateCount OBJECT-TYPE
    SYNTAX      Integer32
    MAX-ACCESS  read-only
    STATUS      current
    DESCRIPTION
        "The number of templates assigned to this filter."
    ::= { basPbrfOSPFImportEntry 7 }

basPbrfOSPFImportRowStatus OBJECT-TYPE
    SYNTAX      RowStatus
    MAX-ACCESS  read-create
    STATUS      current
    DESCRIPTION
        "The row status of the filter."
    ::= { basPbrfOSPFImportEntry 8 }

basPbrfOSPFImportDescr OBJECT-TYPE
    SYNTAX      OCTET STRING(SIZE(0..64))
    MAX-ACCESS  read-create
    STATUS      current
    DESCRIPTION
        "The descr of the OSPF Import."
    ::= { basPbrfOSPFImportEntry 9 }


-- the BAS OSPF Import PBRF filter template table

-- The BAS OSPF Import PBRF filter template table contains BAS
-- proprietary information on policy based route filtering filter
-- structure for OSPF Import filtering.

basPbrfOSPFImportFilterTempTable OBJECT-TYPE
    SYNTAX      SEQUENCE OF BasPbrfOSPFImportFilterTempEntry
    MAX-ACCESS  not-accessible
    STATUS      current
    DESCRIPTION
        "A table of OSPF import PBRF filters."
    ::= { basPbrfOSPFImport 2 }

basPbrfOSPFImportFilterTempEntry OBJECT-TYPE
    SYNTAX      BasPbrfOSPFImportFilterTempEntry
    MAX-ACCESS  not-accessible
    STATUS      current
    DESCRIPTION
        "An entry containing management information applicable
        to an OSPF import PBRF filter."
    INDEX { basPbrfOSPFImportFilterTempChassis,
            basPbrfOSPFImportFilterTempSlot,
            basPbrfOSPFImportFilterTempIf,
            basPbrfOSPFImportFilterTempLPort,
            basPbrfOSPFImportFilterTempIndex,
            basPbrfOSPFImportFilterTempTemplate }
    ::= { basPbrfOSPFImportFilterTempTable 1 }

BasPbrfOSPFImportFilterTempEntry ::=
    SEQUENCE {
        basPbrfOSPFImportFilterTempChassis         BasChassisId,
        basPbrfOSPFImportFilterTempSlot            BasSlotId,
        basPbrfOSPFImportFilterTempIf              BasInterfaceId,
        basPbrfOSPFImportFilterTempLPort           BasLogicalPortId,
        basPbrfOSPFImportFilterTempIndex           Integer32,
        basPbrfOSPFImportFilterTempTemplate        Integer32,
        basPbrfOSPFImportFilterTempOrder           Integer32,
        basPbrfOSPFImportFilterTempRowStatus       RowStatus
    }

basPbrfOSPFImportFilterTempChassis OBJECT-TYPE
    SYNTAX      BasChassisId
    MAX-ACCESS  not-accessible
    STATUS      current
    DESCRIPTION
        "The chassis identifier of this chassis."
    ::= { basPbrfOSPFImportFilterTempEntry 1 }

basPbrfOSPFImportFilterTempSlot OBJECT-TYPE
    SYNTAX      BasSlotId
    MAX-ACCESS  not-accessible
    STATUS      current
    DESCRIPTION
        "The BAS slot ID of this card."
    ::= { basPbrfOSPFImportFilterTempEntry 2 }

basPbrfOSPFImportFilterTempIf OBJECT-TYPE
    SYNTAX      BasInterfaceId
    MAX-ACCESS  not-accessible
    STATUS      current
    DESCRIPTION
        "The BAS interface ID of this card."
    ::= { basPbrfOSPFImportFilterTempEntry 3 }

basPbrfOSPFImportFilterTempLPort OBJECT-TYPE
    SYNTAX      BasLogicalPortId
    MAX-ACCESS  not-accessible
    STATUS      current
    DESCRIPTION
        "The BAS logical port ID of this card."
    ::= { basPbrfOSPFImportFilterTempEntry 4 }

basPbrfOSPFImportFilterTempIndex OBJECT-TYPE
    SYNTAX      Integer32
    MAX-ACCESS  not-accessible
    STATUS      current
    DESCRIPTION
        "The index of the filter."
    ::= { basPbrfOSPFImportFilterTempEntry 5 }

basPbrfOSPFImportFilterTempTemplate OBJECT-TYPE
    SYNTAX      Integer32
    MAX-ACCESS  not-accessible
    STATUS      current
    DESCRIPTION
        "The index for the specific template."
    ::= { basPbrfOSPFImportFilterTempEntry 6 }

basPbrfOSPFImportFilterTempOrder OBJECT-TYPE
    SYNTAX      Integer32
    MAX-ACCESS  read-create
    STATUS      current
    DESCRIPTION
        "The order in which the template is applied."
    ::= { basPbrfOSPFImportFilterTempEntry 7 }

basPbrfOSPFImportFilterTempRowStatus OBJECT-TYPE
    SYNTAX      RowStatus
    MAX-ACCESS  read-create
    STATUS      current
    DESCRIPTION
        "The row status of the filter."
    ::= { basPbrfOSPFImportFilterTempEntry 8 }


-- the BAS OSPF IMPORT PBRF template table

-- The BAS OSPF IMPORT TEMPLATE PBRF table contains BAS proprietary
-- information on OSPF Import policy based route filtering template structure.

basPbrfOSPFImportTemplateTable OBJECT-TYPE
    SYNTAX      SEQUENCE OF BasPbrfOSPFImportTemplateEntry
    MAX-ACCESS  not-accessible
    STATUS      current
    DESCRIPTION
        "A list of OSPF Import template entries."
    ::= { basPbrfOSPFImport 3 }

basPbrfOSPFImportTemplateEntry OBJECT-TYPE
    SYNTAX      BasPbrfOSPFImportTemplateEntry
    MAX-ACCESS  not-accessible
    STATUS      current
    DESCRIPTION
        "An entry containing management information applicable
        to an OSPF Import PBRF template."
    INDEX { basPbrfOSPFImportTemplateChassis,
            basPbrfOSPFImportTemplateSlot,
            basPbrfOSPFImportTemplateIf,
            basPbrfOSPFImportTemplateLPort,
            basPbrfOSPFImportTemplateIndex }
    ::= { basPbrfOSPFImportTemplateTable 1 }

BasPbrfOSPFImportTemplateEntry ::=
    SEQUENCE {
        basPbrfOSPFImportTemplateChassis        BasChassisId,
        basPbrfOSPFImportTemplateSlot           BasSlotId,
        basPbrfOSPFImportTemplateIf             BasInterfaceId,
        basPbrfOSPFImportTemplateLPort          BasLogicalPortId,
        basPbrfOSPFImportTemplateIndex          Integer32,
        basPbrfOSPFImportTemplateRouteAddr      IpAddress,
        basPbrfOSPFImportTemplateRouteMask      IpAddress,
        basPbrfOSPFImportTemplatePeerAddr       IpAddress,
        basPbrfOSPFImportTemplatePeerMask       IpAddress,
        basPbrfOSPFImportTemplateTag	        Integer32,
        basPbrfOSPFImportTemplateKeyBits        Integer32,
        basPbrfOSPFImportTemplatePref	        Integer32,
        basPbrfOSPFImportTemplateFlags	        Integer32,
	basPbrfOSPFImportTemplateRowStatus      RowStatus,
	basPbrfOSPFImportTemplateDescr          OCTET STRING
   }

basPbrfOSPFImportTemplateChassis OBJECT-TYPE
    SYNTAX      BasChassisId
    MAX-ACCESS  not-accessible
    STATUS      current
    DESCRIPTION
        "The BAS chassis identifier of this chassis."
    ::= { basPbrfOSPFImportTemplateEntry 1 }

basPbrfOSPFImportTemplateSlot OBJECT-TYPE
    SYNTAX      BasSlotId
    MAX-ACCESS  not-accessible
    STATUS      current
    DESCRIPTION
        "The BAS slot ID of this card."
    ::= { basPbrfOSPFImportTemplateEntry 2 }

basPbrfOSPFImportTemplateIf OBJECT-TYPE
    SYNTAX      BasInterfaceId
    MAX-ACCESS  not-accessible
    STATUS      current
    DESCRIPTION
        "The BAS interface ID of this card."
    ::= { basPbrfOSPFImportTemplateEntry 3 }

basPbrfOSPFImportTemplateLPort OBJECT-TYPE
    SYNTAX      BasLogicalPortId
    MAX-ACCESS  not-accessible
    STATUS      current
    DESCRIPTION
        "The BAS logical port ID of this card."
    ::= { basPbrfOSPFImportTemplateEntry 4 }

basPbrfOSPFImportTemplateIndex OBJECT-TYPE
    SYNTAX      Integer32
    MAX-ACCESS  not-accessible
    STATUS      current
    DESCRIPTION
        "The Route Address key of of the template."
    ::= { basPbrfOSPFImportTemplateEntry 5 }

basPbrfOSPFImportTemplateRouteAddr OBJECT-TYPE
    SYNTAX      IpAddress
    MAX-ACCESS  read-create
    STATUS      current
    DESCRIPTION
        "The Route Address key of of the template."
    ::= { basPbrfOSPFImportTemplateEntry 6 }

basPbrfOSPFImportTemplateRouteMask OBJECT-TYPE
    SYNTAX      IpAddress
    MAX-ACCESS  read-create
    STATUS      current
    DESCRIPTION
        "The Route Mask key of of the template."
    ::= { basPbrfOSPFImportTemplateEntry 7 }

basPbrfOSPFImportTemplatePeerAddr OBJECT-TYPE
    SYNTAX      IpAddress
    MAX-ACCESS  read-create
    STATUS      current
    DESCRIPTION
        "The PeerAddr key of the template."
    ::= { basPbrfOSPFImportTemplateEntry 8 }

basPbrfOSPFImportTemplatePeerMask OBJECT-TYPE
    SYNTAX      IpAddress
    MAX-ACCESS  read-create
    STATUS      current
    DESCRIPTION
        "The PeerMask key of the template."
    ::= { basPbrfOSPFImportTemplateEntry 9 }

basPbrfOSPFImportTemplateTag OBJECT-TYPE
    SYNTAX      Integer32
    MAX-ACCESS  read-create
    STATUS      current
    DESCRIPTION
        "The tag key of the template."
    ::= { basPbrfOSPFImportTemplateEntry 10 }

basPbrfOSPFImportTemplateKeyBits OBJECT-TYPE
    SYNTAX      Integer32
    MAX-ACCESS  read-create
    STATUS      current
    DESCRIPTION
        "The key bits key mask of the template."
    ::= { basPbrfOSPFImportTemplateEntry 11 }

basPbrfOSPFImportTemplatePref OBJECT-TYPE
    SYNTAX      Integer32
    MAX-ACCESS  read-create
    STATUS      current
    DESCRIPTION
        "The preference of the template action."
    ::= { basPbrfOSPFImportTemplateEntry 12 }

basPbrfOSPFImportTemplateFlags OBJECT-TYPE
    SYNTAX      Integer32
    MAX-ACCESS  read-create
    STATUS      current
    DESCRIPTION
        "The flags of the template action."
    ::= { basPbrfOSPFImportTemplateEntry 13 }

basPbrfOSPFImportTemplateRowStatus OBJECT-TYPE
    SYNTAX      RowStatus
    MAX-ACCESS  read-create
    STATUS      current
    DESCRIPTION
        "The row status of the template."
    ::= { basPbrfOSPFImportTemplateEntry 14 }

basPbrfOSPFImportTemplateDescr OBJECT-TYPE
    SYNTAX      OCTET STRING(SIZE(0..64))
    MAX-ACCESS  read-create
    STATUS      current
    DESCRIPTION
        "The descr of the OSPF Import template."
    ::= { basPbrfOSPFImportTemplateEntry 15 }


-- the BAS OSPF Export PBRF filter table

-- The BAS OSPF Export PBRF filter table contains BAS proprietary
-- information of a BAS OSPF Export PBRF filter.

basPbrfOSPFExportTable OBJECT-TYPE
    SYNTAX      SEQUENCE OF BasPbrfOSPFExportEntry
    MAX-ACCESS  not-accessible
    STATUS      current
    DESCRIPTION
        "A table of OSPF import PBRF test filter entries."
    ::= { basPbrfOSPFExport 1 }

basPbrfOSPFExportEntry OBJECT-TYPE
    SYNTAX      BasPbrfOSPFExportEntry
    MAX-ACCESS  not-accessible
    STATUS      current
    DESCRIPTION
        "An entry containing management information applicable
        to an OSPF import PBRF filter used for testing the
        filter."
    INDEX { basPbrfOSPFExportChassis,
            basPbrfOSPFExportSlot,
            basPbrfOSPFExportIf,
            basPbrfOSPFExportLPort,
            basPbrfOSPFExportIndex }
    ::= { basPbrfOSPFExportTable 1 }

BasPbrfOSPFExportEntry ::=
    SEQUENCE {
        basPbrfOSPFExportChassis         BasChassisId,
        basPbrfOSPFExportSlot            BasSlotId,
        basPbrfOSPFExportIf              BasInterfaceId,
        basPbrfOSPFExportLPort           BasLogicalPortId,
        basPbrfOSPFExportIndex           Integer32,
        -- basPbrfOSPFExportTestStatus      INTEGER,
        basPbrfOSPFExportTemplateCount   Integer32,
        basPbrfOSPFExportRowStatus       RowStatus,
	basPbrfOSPFExportDescr		 OCTET STRING
    }

basPbrfOSPFExportChassis OBJECT-TYPE
    SYNTAX      BasChassisId
    MAX-ACCESS  not-accessible
    STATUS      current
    DESCRIPTION
        "The chassis identifier of this chassis."
    ::= { basPbrfOSPFExportEntry 1 }

basPbrfOSPFExportSlot OBJECT-TYPE
    SYNTAX      BasSlotId
    MAX-ACCESS  not-accessible
    STATUS      current
    DESCRIPTION
        "The BAS slot ID of this card."
    ::= { basPbrfOSPFExportEntry 2 }

basPbrfOSPFExportIf OBJECT-TYPE
    SYNTAX      BasInterfaceId
    MAX-ACCESS  not-accessible
    STATUS      current
    DESCRIPTION
        "The BAS interface ID of this card."
    ::= { basPbrfOSPFExportEntry 3 }

basPbrfOSPFExportLPort OBJECT-TYPE
    SYNTAX      BasLogicalPortId
    MAX-ACCESS  not-accessible
    STATUS      current
    DESCRIPTION
        "The BAS logical port ID of this card."
    ::= { basPbrfOSPFExportEntry 4 }

basPbrfOSPFExportIndex OBJECT-TYPE
    SYNTAX      Integer32
    MAX-ACCESS  not-accessible
    STATUS      current
    DESCRIPTION
        "The index of the filter."
    ::= { basPbrfOSPFExportEntry 5 }

-- basPbrfOSPFExportTestStatus OBJECT-TYPE
--    SYNTAX      INTEGER {
--                        startTest(1),
--                        testing(2),
--                        testSucceed(3),
--                        testFail(4),
--                        notTested(5)
--                }
--    MAX-ACCESS  read-create
--    STATUS      current
--    DESCRIPTION
--        "The status of validating the filter. The value
--        startTest(1) is the only value that my be specified
--        in a write operation. The values testing(2),
--        testSucceed(3), testFail(4), and notTested(5) may be
--        returned by a read operation."
--    DEFVAL { notTested }
--    ::= { basPbrfOSPFExportEntry 6 }

basPbrfOSPFExportTemplateCount OBJECT-TYPE
    SYNTAX      Integer32
    MAX-ACCESS  read-only
    STATUS      current
    DESCRIPTION
        "The number of templates assigned to this filter."
    ::= { basPbrfOSPFExportEntry 7 }

basPbrfOSPFExportRowStatus OBJECT-TYPE
    SYNTAX      RowStatus
    MAX-ACCESS  read-create
    STATUS      current
    DESCRIPTION
        "The row status of the filter."
    ::= { basPbrfOSPFExportEntry 8 }

basPbrfOSPFExportDescr OBJECT-TYPE
    SYNTAX      OCTET STRING(SIZE(0..64))
    MAX-ACCESS  read-create
    STATUS      current
    DESCRIPTION
        "The descr of the OSPF Export."
    ::= { basPbrfOSPFExportEntry 9 }


-- the BAS OSPF Export PBRF filter template table

-- The BAS OSPF Export PBRF filter template table contains BAS
-- proprietary information on policy based route filtering filter
-- structure for OSPF Export filtering.

basPbrfOSPFExportFilterTempTable OBJECT-TYPE
    SYNTAX      SEQUENCE OF BasPbrfOSPFExportFilterTempEntry
    MAX-ACCESS  not-accessible
    STATUS      current
    DESCRIPTION
        "A table of OSPf Export PBRF filter/template bindings."
    ::= { basPbrfOSPFExport 2 }

basPbrfOSPFExportFilterTempEntry OBJECT-TYPE
    SYNTAX      BasPbrfOSPFExportFilterTempEntry
    MAX-ACCESS  not-accessible
    STATUS      current
    DESCRIPTION
        "An entry containing management information applicable
        to an OSPF import PBRF filter."
    INDEX { basPbrfOSPFExportFilterTempChassis,
            basPbrfOSPFExportFilterTempSlot,
            basPbrfOSPFExportFilterTempIf,
            basPbrfOSPFExportFilterTempLPort,
            basPbrfOSPFExportFilterTempIndex,
            basPbrfOSPFExportFilterTempTemplate }
    ::= { basPbrfOSPFExportFilterTempTable 1 }

BasPbrfOSPFExportFilterTempEntry ::=
    SEQUENCE {
        basPbrfOSPFExportFilterTempChassis         BasChassisId,
        basPbrfOSPFExportFilterTempSlot            BasSlotId,
        basPbrfOSPFExportFilterTempIf              BasInterfaceId,
        basPbrfOSPFExportFilterTempLPort           BasLogicalPortId,
        basPbrfOSPFExportFilterTempIndex           Integer32,
        basPbrfOSPFExportFilterTempTemplate        Integer32,
        basPbrfOSPFExportFilterTempOrder           Integer32,
        basPbrfOSPFExportFilterTempRowStatus       RowStatus
    }

basPbrfOSPFExportFilterTempChassis OBJECT-TYPE
    SYNTAX      BasChassisId
    MAX-ACCESS  not-accessible
    STATUS      current
    DESCRIPTION
        "The BAS chassis identifier of this chassis."
    ::= { basPbrfOSPFExportFilterTempEntry 1 }

basPbrfOSPFExportFilterTempSlot OBJECT-TYPE
    SYNTAX      BasSlotId
    MAX-ACCESS  not-accessible
    STATUS      current
    DESCRIPTION
        "The BAS slot ID of this card."
    ::= { basPbrfOSPFExportFilterTempEntry 2 }

basPbrfOSPFExportFilterTempIf OBJECT-TYPE
    SYNTAX      BasInterfaceId
    MAX-ACCESS  not-accessible
    STATUS      current
    DESCRIPTION
        "The BAS interface ID of this card."
    ::= { basPbrfOSPFExportFilterTempEntry 3 }

basPbrfOSPFExportFilterTempLPort OBJECT-TYPE
    SYNTAX      BasLogicalPortId
    MAX-ACCESS  not-accessible
    STATUS      current
    DESCRIPTION
        "The BAS logical port ID of this card."
    ::= { basPbrfOSPFExportFilterTempEntry 4 }

basPbrfOSPFExportFilterTempIndex OBJECT-TYPE
    SYNTAX      Integer32
    MAX-ACCESS  not-accessible
    STATUS      current
    DESCRIPTION
        "The index of the filter."
    ::= { basPbrfOSPFExportFilterTempEntry 5 }

basPbrfOSPFExportFilterTempTemplate OBJECT-TYPE
    SYNTAX      Integer32
    MAX-ACCESS  not-accessible
    STATUS      current
    DESCRIPTION
        "The index for the specific template."
    ::= { basPbrfOSPFExportFilterTempEntry 6 }

basPbrfOSPFExportFilterTempOrder OBJECT-TYPE
    SYNTAX      Integer32
    MAX-ACCESS  read-create
    STATUS      current
    DESCRIPTION
        "The order in which the template is applied."
    ::= { basPbrfOSPFExportFilterTempEntry 7 }

basPbrfOSPFExportFilterTempRowStatus OBJECT-TYPE
    SYNTAX      RowStatus
    MAX-ACCESS  read-create
    STATUS      current
    DESCRIPTION
        "The row status of the filter."
    ::= { basPbrfOSPFExportFilterTempEntry 8 }


-- the BAS OSPF EXPORT PBRF template table

-- The BAS OSPF EXPORT TEMPLATE PBRF table contains BAS proprietary
-- information on OSPF Export policy based route filtering template structure.

basPbrfOSPFExportTemplateTable OBJECT-TYPE
    SYNTAX      SEQUENCE OF BasPbrfOSPFExportTemplateEntry
    MAX-ACCESS  not-accessible
    STATUS      current
    DESCRIPTION
        "A list of OSPF Export template entries."
    ::= { basPbrfOSPFExport 3 }

basPbrfOSPFExportTemplateEntry OBJECT-TYPE
    SYNTAX      BasPbrfOSPFExportTemplateEntry
    MAX-ACCESS  not-accessible
    STATUS      current
    DESCRIPTION
        "An entry containing management information applicable
        to an OSPF Export PBRF template."
    INDEX { basPbrfOSPFExportTemplateChassis,
            basPbrfOSPFExportTemplateSlot,
            basPbrfOSPFExportTemplateIf,
            basPbrfOSPFExportTemplateLPort,
            basPbrfOSPFExportTemplateIndex }
    ::= { basPbrfOSPFExportTemplateTable 1 }

BasPbrfOSPFExportTemplateEntry ::=
    SEQUENCE {
        basPbrfOSPFExportTemplateChassis        BasChassisId,
        basPbrfOSPFExportTemplateSlot           BasSlotId,
        basPbrfOSPFExportTemplateIf             BasInterfaceId,
        basPbrfOSPFExportTemplateLPort          BasLogicalPortId,
        basPbrfOSPFExportTemplateIndex          Integer32,
        basPbrfOSPFExportTemplateRouteAddr      IpAddress,
        basPbrfOSPFExportTemplateRouteMask      IpAddress,
        basPbrfOSPFExportTemplateProtocol       Integer32,
        basPbrfOSPFExportTemplateSpecific1      IpAddress,
        basPbrfOSPFExportTemplateSpecific2      IpAddress,
        basPbrfOSPFExportTemplateTag	        Integer32,
        basPbrfOSPFExportTemplateKeyBits        Integer32,
        basPbrfOSPFExportTemplateMetric	        Integer32,
        basPbrfOSPFExportTemplateFlags	        Integer32,
	basPbrfOSPFExportTemplateActionTag      Integer32,
	basPbrfOSPFExportTemplateRowStatus      RowStatus,
	basPbrfOSPFExportTemplateDescr          OCTET STRING	
   }

basPbrfOSPFExportTemplateChassis OBJECT-TYPE
    SYNTAX      BasChassisId
    MAX-ACCESS  not-accessible
    STATUS      current
    DESCRIPTION
        "The BAS chassis identifier of this chassis."
    ::= { basPbrfOSPFExportTemplateEntry 1 }

basPbrfOSPFExportTemplateSlot OBJECT-TYPE
    SYNTAX      BasSlotId
    MAX-ACCESS  not-accessible
    STATUS      current
    DESCRIPTION
        "The BAS slot ID of this card."
    ::= { basPbrfOSPFExportTemplateEntry 2 }

basPbrfOSPFExportTemplateIf OBJECT-TYPE
    SYNTAX      BasInterfaceId
    MAX-ACCESS  not-accessible
    STATUS      current
    DESCRIPTION
        "The BAS interface ID of this card."
    ::= { basPbrfOSPFExportTemplateEntry 3 }

basPbrfOSPFExportTemplateLPort OBJECT-TYPE
    SYNTAX      BasLogicalPortId
    MAX-ACCESS  not-accessible
    STATUS      current
    DESCRIPTION
        "The BAS logical port ID of this card."
    ::= { basPbrfOSPFExportTemplateEntry 4 }

basPbrfOSPFExportTemplateIndex OBJECT-TYPE
    SYNTAX      Integer32
    MAX-ACCESS  not-accessible
    STATUS      current
    DESCRIPTION
        "The index of the template"
    ::= { basPbrfOSPFExportTemplateEntry 5 }

basPbrfOSPFExportTemplateRouteAddr OBJECT-TYPE
    SYNTAX      IpAddress
    MAX-ACCESS  read-create
    STATUS      current
    DESCRIPTION
        "The Route Address key of of the template."
    ::= { basPbrfOSPFExportTemplateEntry 6 }

basPbrfOSPFExportTemplateRouteMask OBJECT-TYPE
    SYNTAX      IpAddress
    MAX-ACCESS  read-create
    STATUS      current
    DESCRIPTION
        "The Route Mask key of of the template."
    ::= { basPbrfOSPFExportTemplateEntry 7 }

basPbrfOSPFExportTemplateProtocol OBJECT-TYPE
    SYNTAX      Integer32
    MAX-ACCESS  read-create
    STATUS      current
    DESCRIPTION
        "The protocol key of the template."
    ::= { basPbrfOSPFExportTemplateEntry 8 }

basPbrfOSPFExportTemplateSpecific1 OBJECT-TYPE
    SYNTAX      IpAddress
    MAX-ACCESS  read-create
    STATUS      current
    DESCRIPTION
        "The specific1 key of the template."
    ::= { basPbrfOSPFExportTemplateEntry 9 }

basPbrfOSPFExportTemplateSpecific2 OBJECT-TYPE
    SYNTAX      IpAddress
    MAX-ACCESS  read-create
    STATUS      current
    DESCRIPTION
        "The specific2 key of the template."
    ::= { basPbrfOSPFExportTemplateEntry 10 }

basPbrfOSPFExportTemplateTag OBJECT-TYPE
    SYNTAX      Integer32
    MAX-ACCESS  read-create
    STATUS      current
    DESCRIPTION
        "The tag key of the template."
    ::= { basPbrfOSPFExportTemplateEntry 11 }

basPbrfOSPFExportTemplateKeyBits OBJECT-TYPE
    SYNTAX      Integer32
    MAX-ACCESS  read-create
    STATUS      current
    DESCRIPTION
        "The key bits key mask of the template."
    ::= { basPbrfOSPFExportTemplateEntry 12 }

basPbrfOSPFExportTemplateMetric OBJECT-TYPE
    SYNTAX      Integer32
    MAX-ACCESS  read-create
    STATUS      current
    DESCRIPTION
        "The metric of the template action."
    ::= { basPbrfOSPFExportTemplateEntry 13 }

basPbrfOSPFExportTemplateFlags OBJECT-TYPE
    SYNTAX      Integer32
    MAX-ACCESS  read-create
    STATUS      current
    DESCRIPTION
        "The flags of the template action."
    ::= { basPbrfOSPFExportTemplateEntry 14 }

basPbrfOSPFExportTemplateActionTag OBJECT-TYPE
    SYNTAX      Integer32
    MAX-ACCESS  read-create
    STATUS      current
    DESCRIPTION
        "The tag of the template action."
    ::= { basPbrfOSPFExportTemplateEntry 15 }

basPbrfOSPFExportTemplateRowStatus OBJECT-TYPE
    SYNTAX      RowStatus
    MAX-ACCESS  read-create
    STATUS      current
    DESCRIPTION
        "The row status of the template."
    ::= { basPbrfOSPFExportTemplateEntry 16 }

basPbrfOSPFExportTemplateDescr OBJECT-TYPE
    SYNTAX      OCTET STRING(SIZE(0..64))
    MAX-ACCESS  read-create
    STATUS      current
    DESCRIPTION
        "The descr of the OSPF Export template."
    ::= { basPbrfOSPFExportTemplateEntry 17 }

END
