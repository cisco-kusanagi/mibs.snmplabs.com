BAS-TCP-MIB DEFINITIONS ::= BEGIN

IMPORTS
    MODULE-IDENTITY, OBJECT-TYPE, Integer32, Gauge32,
    Counter32, IpAddress  FROM SNMPv2-SMI
    basAliasTcp, BasChassisId,
    BasSlotId, BasInterfaceId,
    BasLogicalPortId			FROM BAS-MIB;



basAliasTcpMib MODULE-IDENTITY
	LAST-UPDATED "9810071415Z"
	ORGANIZATION "Broadband Access Systems"
	CONTACT-INFO
		" Tech Support
		  Broadband Access Systems
		  201 Forest Street
		  Marlboro, MA  01752
		  U.S.A.

		  508-485-8200
		  support@basystems.com"
	DESCRIPTION
		"This module defines the MIB objects
		 for a Broadband Access System IP Forwarding component."
	::= { basAliasTcp  1 }

basTcpObjects		OBJECT IDENTIFIER ::= { basAliasTcpMib 1 }

basTcpTable OBJECT-TYPE
	SYNTAX		SEQUENCE OF BasTcpEntry
	MAX-ACCESS	not-accessible
	STATUS		current
	DESCRIPTION
		"A list of TCP stats"
	::= { basTcpObjects 1 }

basTcpEntry OBJECT-TYPE
	SYNTAX		BasTcpEntry
	MAX-ACCESS	not-accessible
	STATUS		current
	DESCRIPTION
		"Objects for the TCP mib."
	INDEX   { basTcpChassis, basTcpSlot, basTcpIf, basTcpLPort }
	::= { basTcpTable 1 }

BasTcpEntry ::=
	SEQUENCE {
		basTcpRtoAlgorithm						INTEGER,
		basTcpRtoMin							Integer32,
		basTcpRtoMax							Integer32,
		basTcpMaxConn							Integer32,
		basTcpActiveOpens						Counter32,
		basTcpPassiveOpens						Counter32,
		basTcpAttemptFails						Counter32,
		basTcpEstabResets						Counter32,
		basTcpCurrEstab							Gauge32,
		basTcpInSegs							Counter32,
		basTcpOutSegs							Counter32,
		basTcpRetransSegs						Counter32,
		basTcpChassis						BasChassisId,
		basTcpSlot							BasSlotId,
		basTcpIf							BasInterfaceId,
		basTcpLPort							BasLogicalPortId

	}


basTcpRtoAlgorithm OBJECT-TYPE
    SYNTAX      INTEGER {
                    other(1),    -- none of the following
                    constant(2), -- a constant rto
                    rsre(3),     -- MIL-STD-1778, Appendix B
                    vanj(4)      -- Van Jacobson's algorithm [5]
                }
    MAX-ACCESS  read-only
    STATUS      current
    DESCRIPTION
            "The algorithm used to determine the timeout value used for
            retransmitting unacknowledged octets."
    ::= { basTcpEntry 1 }

basTcpRtoMin OBJECT-TYPE
    SYNTAX      Integer32
    UNITS       "milliseconds"
    MAX-ACCESS  read-only
    STATUS      current
    DESCRIPTION
            "The minimum value permitted by a TCP implementation for the
            retransmission timeout, measured in milliseconds.  More
            refined semantics for objects of this type depend upon the
            algorithm used to determine the retransmission timeout.  In
            particular, when the timeout algorithm is rsre(3), an object
            of this type has the semantics of the LBOUND quantity
            described in RFC 793."
    ::= {  basTcpEntry 2 }

basTcpRtoMax OBJECT-TYPE
    SYNTAX      Integer32
    UNITS       "milliseconds"
    MAX-ACCESS  read-only
    STATUS      current
    DESCRIPTION
            "The maximum value permitted by a TCP implementation for the


            retransmission timeout, measured in milliseconds.  More
            refined semantics for objects of this type depend upon the
            algorithm used to determine the retransmission timeout.  In
            particular, when the timeout algorithm is rsre(3), an object
            of this type has the semantics of the UBOUND quantity
            described in RFC 793."
    ::= { basTcpEntry 3 }

basTcpMaxConn OBJECT-TYPE
    SYNTAX      Integer32
    MAX-ACCESS  read-only
    STATUS      current
    DESCRIPTION
            "The limit on the total number of TCP connections the entity
            can support.  In entities where the maximum number of
            connections is dynamic, this object should contain the value
            -1."
    ::= { basTcpEntry 4 }

basTcpActiveOpens OBJECT-TYPE
    SYNTAX      Counter32
    MAX-ACCESS  read-only
    STATUS      current
    DESCRIPTION
            "The number of times TCP connections have made a direct
            transition to the SYN-SENT state from the CLOSED state."
    ::= { basTcpEntry 5 }

basTcpPassiveOpens OBJECT-TYPE
    SYNTAX      Counter32
    MAX-ACCESS  read-only
    STATUS      current
    DESCRIPTION
            "The number of times TCP connections have made a direct
            transition to the SYN-RCVD state from the LISTEN state."
    ::= { basTcpEntry 6 }

basTcpAttemptFails OBJECT-TYPE
    SYNTAX      Counter32
    MAX-ACCESS  read-only
    STATUS      current
    DESCRIPTION
            "The number of times TCP connections have made a direct
            transition to the CLOSED state from either the SYN-SENT
            state or the SYN-RCVD state, plus the number of times TCP
            connections have made a direct transition to the LISTEN
            state from the SYN-RCVD state."
    ::= { basTcpEntry 7 }


basTcpEstabResets OBJECT-TYPE
    SYNTAX      Counter32
    MAX-ACCESS  read-only
    STATUS      current
    DESCRIPTION
            "The number of times TCP connections have made a direct
            transition to the CLOSED state from either the ESTABLISHED
            state or the CLOSE-WAIT state."
    ::= { basTcpEntry 8 }

basTcpCurrEstab OBJECT-TYPE
    SYNTAX      Gauge32
    MAX-ACCESS  read-only
    STATUS      current
    DESCRIPTION
            "The number of TCP connections for which the current state
            is either ESTABLISHED or CLOSE- WAIT."
    ::= { basTcpEntry 9 }

basTcpInSegs OBJECT-TYPE
    SYNTAX      Counter32
    MAX-ACCESS  read-only
    STATUS      current
    DESCRIPTION
            "The total number of segments received, including those
            received in error.  This count includes segments received on
            currently established connections."
    ::= { basTcpEntry 10 }

basTcpOutSegs OBJECT-TYPE
    SYNTAX      Counter32
    MAX-ACCESS  read-only
    STATUS      current
    DESCRIPTION
            "The total number of segments sent, including those on
            current connections but excluding those containing only
            retransmitted octets."
    ::= { basTcpEntry 11 }

basTcpRetransSegs OBJECT-TYPE
    SYNTAX      Counter32
    MAX-ACCESS  read-only
    STATUS      current
    DESCRIPTION
            "The total number of segments retransmitted - that is, the
            number of TCP segments transmitted containing one or more
            previously transmitted octets."


    ::= { basTcpEntry 12 }

basTcpChassis OBJECT-TYPE
	SYNTAX		BasChassisId
	MAX-ACCESS	not-accessible
	STATUS		current
	DESCRIPTION
		"The BAS Chassis ID of the Route Server."
	::= { basTcpEntry 13 }

basTcpSlot OBJECT-TYPE
	SYNTAX		BasSlotId
	MAX-ACCESS	not-accessible
	STATUS		current
	DESCRIPTION
		"The BAS Slot ID of the Route Server."
	::= { basTcpEntry 14 }

basTcpIf OBJECT-TYPE
	SYNTAX		BasInterfaceId
	MAX-ACCESS	not-accessible
	STATUS		current
	DESCRIPTION
		"The BAS interface ID of the Route Server."
	::= { basTcpEntry 15 }

basTcpLPort OBJECT-TYPE
	SYNTAX		BasLogicalPortId
	MAX-ACCESS	not-accessible
	STATUS		current
	DESCRIPTION
		"The BAS logical port ID of the Route Server."
	::= { basTcpEntry 16 }

-- the TCP Connection table

-- The TCP connection table contains information about this
-- entity's existing TCP connections.

basTcpConnTable OBJECT-TYPE
    SYNTAX      SEQUENCE OF BasTcpConnEntry
    MAX-ACCESS  not-accessible
    STATUS      current
    DESCRIPTION
            "A table containing TCP connection-specific information."
    ::= { basTcpObjects 2 }

basTcpConnEntry OBJECT-TYPE
    SYNTAX      BasTcpConnEntry
    MAX-ACCESS  not-accessible
    STATUS      current
    DESCRIPTION
            "A conceptual row of the tcpConnTable containing information
            about a particular current TCP connection.  Each row of this
            table is transient, in that it ceases to exist when (or soon
            after) the connection makes the transition to the CLOSED
            state."
    INDEX   { basTcpConnChassis, 
 	      basTcpConnSlot, 
	      basTcpConnIf, 
	      basTcpConnLPort,
	      basTcpConnLocalAddress,
              basTcpConnLocalPort,
              basTcpConnRemAddress,
              basTcpConnRemPort }
    ::= { basTcpConnTable 1 }

BasTcpConnEntry ::= SEQUENCE {
        basTcpConnState          INTEGER,
        basTcpConnLocalAddress   IpAddress,
        basTcpConnLocalPort      INTEGER,
        basTcpConnRemAddress     IpAddress,
        basTcpConnRemPort        INTEGER,
	basTcpConnChassis						BasChassisId,
	basTcpConnSlot							BasSlotId,
	basTcpConnIf							BasInterfaceId,
	basTcpConnLPort							BasLogicalPortId
    }

basTcpConnState OBJECT-TYPE
    SYNTAX      INTEGER {
                    closed(1),
                    listen(2),
                    synSent(3),
                    synReceived(4),
                    established(5),
                    finWait1(6),
                    finWait2(7),
                    closeWait(8),
                    lastAck(9),
                    closing(10),
                    timeWait(11),
                    deleteTCB(12)
                }
    MAX-ACCESS  read-write
    STATUS      current
    DESCRIPTION
            "The state of this TCP connection.

            The only value which may be set by a management station is
            deleteTCB(12).  Accordingly, it is appropriate for an agent
            to return a `badValue' response if a management station
            attempts to set this object to any other value.

            If a management station sets this object to the value
            deleteTCB(12), then this has the effect of deleting the TCB
            (as defined in RFC 793) of the corresponding connection on
            the managed node, resulting in immediate termination of the
            connection.

            As an implementation-specific option, a RST segment may be
            sent from the managed node to the other TCP endpoint (note
            however that RST segments are not sent reliably)."
    ::= { basTcpConnEntry 1 }

basTcpConnLocalAddress OBJECT-TYPE
    SYNTAX      IpAddress
    MAX-ACCESS  read-only
    STATUS      current
    DESCRIPTION
            "The local IP address for this TCP connection.  In the case
            of a connection in the listen state which is willing to
            accept connections for any IP interface associated with the
            node, the value 0.0.0.0 is used."
    ::= { basTcpConnEntry 2 }

basTcpConnLocalPort OBJECT-TYPE
    SYNTAX      INTEGER (0..65535)
    MAX-ACCESS  read-only
    STATUS      current
    DESCRIPTION
            "The local port number for this TCP connection."
    ::= { basTcpConnEntry 3 }

basTcpConnRemAddress OBJECT-TYPE


    SYNTAX      IpAddress
    MAX-ACCESS  read-only
    STATUS      current
    DESCRIPTION
            "The remote IP address for this TCP connection."
    ::= { basTcpConnEntry 4 }

basTcpConnRemPort OBJECT-TYPE
    SYNTAX      INTEGER (0..65535)
    MAX-ACCESS  read-only
    STATUS      current
    DESCRIPTION
            "The remote port number for this TCP connection."
    ::= { basTcpConnEntry 5 }

basTcpConnChassis OBJECT-TYPE
	SYNTAX		BasChassisId
	MAX-ACCESS	not-accessible
	STATUS		current
	DESCRIPTION
		"The BAS Chassis ID of the Route Server."
	::= { basTcpConnEntry 6 }

basTcpConnSlot OBJECT-TYPE
	SYNTAX		BasSlotId
	MAX-ACCESS	not-accessible
	STATUS		current
	DESCRIPTION
		"The BAS Slot ID of the Route Server."
	::= { basTcpConnEntry 7 }

basTcpConnIf OBJECT-TYPE
	SYNTAX		BasInterfaceId
	MAX-ACCESS	not-accessible
	STATUS		current
	DESCRIPTION
		"The BAS interface ID of the Route Server."
	::= { basTcpConnEntry 8 }

basTcpConnLPort OBJECT-TYPE
	SYNTAX		BasLogicalPortId
	MAX-ACCESS	not-accessible
	STATUS		current
	DESCRIPTION
		"The BAS logical port ID of the Route Server."
	::= { basTcpConnEntry 9 }





basTcpStatsTable OBJECT-TYPE
	SYNTAX		SEQUENCE OF BasTcpStatsEntry
	MAX-ACCESS	not-accessible
	STATUS		current
	DESCRIPTION
		"A list of Route Server forwarding table 
		distribution mechanism statistics."
	::= { basTcpObjects 3 }

basTcpStatsEntry OBJECT-TYPE
	SYNTAX		BasTcpStatsEntry
	MAX-ACCESS	not-accessible
	STATUS		current
	DESCRIPTION
		"Objects for the TCP mib."
	INDEX   { basTcpStatsChassis, basTcpStatsSlot, basTcpStatsIf, basTcpStatsLPort }
	::= { basTcpStatsTable 1 }

BasTcpStatsEntry ::=
	SEQUENCE {
		basTcpInErrs							Counter32,
		basTcpOutRsts							Counter32,
		basTcpStatsChassis						BasChassisId,
		basTcpStatsSlot							BasSlotId,
		basTcpStatsIf							BasInterfaceId,
		basTcpStatsLPort						BasLogicalPortId

	}



basTcpInErrs OBJECT-TYPE
    SYNTAX      Counter32
    MAX-ACCESS  read-only
    STATUS      current
    DESCRIPTION
            "The total number of segments received in error (e.g., bad
            TCP checksums)."
    ::= { basTcpStatsEntry 1 }

basTcpOutRsts OBJECT-TYPE
    SYNTAX      Counter32
    MAX-ACCESS  read-only
    STATUS      current
    DESCRIPTION
            "The number of TCP segments sent containing the RST flag."
    ::= { basTcpStatsEntry 2 }

basTcpStatsChassis OBJECT-TYPE
	SYNTAX		BasChassisId
	MAX-ACCESS	not-accessible
	STATUS		current
	DESCRIPTION
		"The BAS Chassis ID of the Route Server."
	::= { basTcpStatsEntry 3 }

basTcpStatsSlot OBJECT-TYPE
	SYNTAX		BasSlotId
	MAX-ACCESS	not-accessible
	STATUS		current
	DESCRIPTION
		"The BAS Slot ID of the Route Server."
	::= { basTcpStatsEntry 4 }

basTcpStatsIf OBJECT-TYPE
	SYNTAX		BasInterfaceId
	MAX-ACCESS	not-accessible
	STATUS		current
	DESCRIPTION
		"The BAS interface ID of the Route Server."
	::= { basTcpStatsEntry 5}

basTcpStatsLPort OBJECT-TYPE
	SYNTAX		BasLogicalPortId
	MAX-ACCESS	not-accessible
	STATUS		current
	DESCRIPTION
		"The BAS logical port ID of the Route Server."
	::= { basTcpStatsEntry 6 }

END
