NWSD-MIB DEFINITIONS ::= BEGIN

-- Title:      RADWARE
--             This Private MIB supports the Vgate
-- Version:    2.9
-- Date:       27 Oct 1995
-- By:         Rina Nethaniel.
-- E-mail:         rina@rnd-gate.rad.co.il
--
IMPORTS
       NetworkAddress,
       IpAddress,
       Counter,
       Gauge,
       enterprises
              FROM RFC1155-SMI
      OBJECT-TYPE
              FROM RFC-1212
       DisplayString,
       PhysAddress,
       ipAddrEntry
              FROM RFC1213-MIB
       TRAP-TYPE
                    FROM RFC-1215
       rsServerDispatcher,
       rndErrorDesc,
       rndErrorSeverity
                    FROM RND-MIB
       rsNWSD
                    FROM RADWARE-MIB;

    TruthValue ::= INTEGER {
         true (1),
         false (2)
        }
    RowStatus ::= INTEGER {
        active(1),
        notInService(2),
        notReady(3),
        createAndGo(4),
        createAndWait(5),
        destroy(6)
        }
    NetNumber ::=  OCTET STRING (SIZE(4))

-- Some MIB compilers require that the following 7 lines which define the path
-- to RND MIB are commented out:

-- mib            OBJECT IDENTIFIER ::= { mgmt 1  }
-- directory      OBJECT IDENTIFIER ::= { internet 1  }
-- experimental   OBJECT IDENTIFIER ::= { internet 3  }
-- private        OBJECT IDENTIFIER ::= { internet 4  }
-- enterprises    OBJECT IDENTIFIER ::= { private 1  }

rsNWSDProximity  OBJECT IDENTIFIER ::= { rsNWSD 1 }

rsWSDProximityHopsWeight  OBJECT-TYPE
   SYNTAX INTEGER (1..100)
   ACCESS  read-write
   STATUS  mandatory
   DESCRIPTION
       "The weight given to the clients hops distance in the dispatching decision"
-- DEFVAL { 50 }
   ::=  {rsNWSDProximity 1}

rsWSDProximityLatencyWeight  OBJECT-TYPE
   SYNTAX INTEGER (1..100)
   ACCESS  read-write
   STATUS  mandatory
   DESCRIPTION
       "The weight given to the clients latency in the dispatching decision"
-- DEFVAL { 50 }
   ::=  {rsNWSDProximity 2}

rsWSDProximityLoadWeight  OBJECT-TYPE
   SYNTAX INTEGER (1..100)
   ACCESS  read-write
   STATUS  mandatory
   DESCRIPTION
       "The weight given to the site load in the dispatching decision"
-- DEFVAL { 50 }
   ::=  {rsNWSDProximity 3}

rsWSDDNSttl  OBJECT-TYPE
   SYNTAX INTEGER
   ACCESS  read-write
   STATUS  mandatory
   DESCRIPTION
        "TTL for DNS replies."
-- DEFVAL { 0 }
   ::=  {rsNWSD 2}

rsWSDURLSuperFarmTable OBJECT-TYPE
   SYNTAX SEQUENCE OF RsWSDURLSuperFarmEntry
   ACCESS not-accessible
   STATUS mandatory
   DESCRIPTION
       "A table for managing the farm decision according to the incoming URL."
   ::= {rsNWSD 3}

rsWSDURLSuperFarmEntry OBJECT-TYPE
   SYNTAX RsWSDURLSuperFarmEntry
   ACCESS not-accessible
   STATUS mandatory
   DESCRIPTION
       " The row definition for this table."
   INDEX  {rsWSDURL}
   ::= {rsWSDURLSuperFarmTable 1}

RsWSDURLSuperFarmEntry  ::= SEQUENCE {
  rsWSDURLFarmAddress IpAddress,
  rsWSDURL            DisplayString,
  rsWSDURLStatus      RowStatus
}

rsWSDURLFarmAddress OBJECT-TYPE
    	SYNTAX IpAddress
    	ACCESS read-write
   	STATUS mandatory
   	DESCRIPTION
     	 "IP address of the farm to use with the URL."
	::=  {rsWSDURLSuperFarmEntry 1}

rsWSDURL  OBJECT-TYPE
        SYNTAX DisplayString (SIZE (1..63))
    	ACCESS read-write
   	STATUS mandatory
   	DESCRIPTION
     	 "The URL representing the farm."
	::=  {rsWSDURLSuperFarmEntry 2}

rsWSDURLStatus OBJECT-TYPE
    	SYNTAX RowStatus
    	ACCESS read-write
   	STATUS mandatory
   	DESCRIPTION
     	 "Row status for the URL."
	::=  {rsWSDURLSuperFarmEntry 3}

rsWSDClientGroupingMask OBJECT-TYPE
        SYNTAX IpAddress
        ACCESS read-write
        STATUS mandatory
        DESCRIPTION
        "Client IP address mask."
        ::=  {rsNWSD 26}


END
