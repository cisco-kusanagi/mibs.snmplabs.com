--			Ascend mibslot MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBSLOT-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibtcpModemProfile  OBJECT IDENTIFIER ::= { configuration 112}
    mibdhcpServerProfile  OBJECT IDENTIFIER ::= { configuration 111}
    mibappOptionsProfile  OBJECT IDENTIFIER ::= { configuration 109}
    mibdnisProfile  OBJECT IDENTIFIER ::= { configuration 113}
    mibwanOptionsProfile  OBJECT IDENTIFIER ::= { configuration 110}

	-- The mibtcpModemProfile table
	--
	-- This table contains parameters for the mibtcpModemProfile profile
	--

    mibtcpModemProfileTable	OBJECT-TYPE
	SYNTAX		SEQUENCE OF MibtcpModemProfileEntry
	ACCESS		not-accessible
	STATUS		mandatory
	DESCRIPTION	"A list of mibtcpModemProfile profile entries."
	::= { mibtcpModemProfile 1 }

    mibtcpModemProfileEntry	OBJECT-TYPE
	SYNTAX		MibtcpModemProfileEntry
	ACCESS		not-accessible
	STATUS		mandatory
	DESCRIPTION	"A mibtcpModemProfile entry containing objects that
			 maps to the parameters of mibtcpModemProfile profile."
	INDEX		{ tcpModemProfile-Index-o }
	::= { mibtcpModemProfileTable 1 }

    MibtcpModemProfileEntry ::=
	SEQUENCE {
	    tcpModemProfile-Index-o
		INTEGER,
	    tcpModemProfile-Enabled
		INTEGER,
	    tcpModemProfile-Port
		INTEGER,
	    tcpModemProfile-Action-o
		INTEGER
	}

    tcpModemProfile-Index-o	OBJECT-TYPE
	SYNTAX	INTEGER
	ACCESS	read-only
	STATUS	mandatory
	DESCRIPTION	""
	::= { mibtcpModemProfileEntry 1 }

    tcpModemProfile-Enabled	OBJECT-TYPE
	SYNTAX	INTEGER {
		    no (1),
		    yes (2)
		}
	ACCESS	read-write
	STATUS	mandatory
	DESCRIPTION	"Enable TCP MODEM connections."
	::= { mibtcpModemProfileEntry 2 }

    tcpModemProfile-Port	OBJECT-TYPE
	SYNTAX	INTEGER
	ACCESS	read-write
	STATUS	mandatory
	DESCRIPTION	"Port number to accept TCP MODEM connections on."
	::= { mibtcpModemProfileEntry 3 }

    tcpModemProfile-Action-o	OBJECT-TYPE
	SYNTAX	INTEGER {
		    noAction (1),
		    createProfile (2),
		    deleteProfile (3)
		}
	ACCESS	read-write
	STATUS	mandatory
	DESCRIPTION	""
	::= { mibtcpModemProfileEntry 4 }


	-- The mibdhcpServerProfile table
	--
	-- This table contains parameters for the mibdhcpServerProfile profile
	--

    mibdhcpServerProfileTable	OBJECT-TYPE
	SYNTAX		SEQUENCE OF MibdhcpServerProfileEntry
	ACCESS		not-accessible
	STATUS		mandatory
	DESCRIPTION	"A list of mibdhcpServerProfile profile entries."
	::= { mibdhcpServerProfile 1 }

    mibdhcpServerProfileEntry	OBJECT-TYPE
	SYNTAX		MibdhcpServerProfileEntry
	ACCESS		not-accessible
	STATUS		mandatory
	DESCRIPTION	"A mibdhcpServerProfile entry containing objects that
			 maps to the parameters of mibdhcpServerProfile profile."
	INDEX		{ dhcpServerProfile-Index-o }
	::= { mibdhcpServerProfileTable 1 }

    MibdhcpServerProfileEntry ::=
	SEQUENCE {
	    dhcpServerProfile-Index-o
		INTEGER,
	    dhcpServerProfile-Enabled
		INTEGER,
	    dhcpServerProfile-PnpEnabled
		INTEGER,
	    dhcpServerProfile-IpAddress
		IpAddress,
	    dhcpServerProfile-Netmask
		IpAddress,
	    dhcpServerProfile-RenewalTime
		INTEGER,
	    dhcpServerProfile-BecomeDefRouter
		INTEGER,
	    dhcpServerProfile-DialIfLinkDown
		INTEGER,
	    dhcpServerProfile-AlwaysSpoof
		INTEGER,
	    dhcpServerProfile-ValidateIp
		INTEGER,
	    dhcpServerProfile-MaxNoReplyWait
		INTEGER,
	    dhcpServerProfile-GroupOneCount
		INTEGER,
	    dhcpServerProfile-IpGroupTwo
		IpAddress,
	    dhcpServerProfile-GroupTwoCount
		INTEGER,
	    dhcpServerProfile-IpGroupTwoNetmask
		IpAddress,
	    dhcpServerProfile-TftpHost
		DisplayString,
	    dhcpServerProfile-BootpPath
		DisplayString,
	    dhcpServerProfile-Action-o
		INTEGER
	}

    dhcpServerProfile-Index-o	OBJECT-TYPE
	SYNTAX	INTEGER
	ACCESS	read-only
	STATUS	mandatory
	DESCRIPTION	""
	::= { mibdhcpServerProfileEntry 1 }

    dhcpServerProfile-Enabled	OBJECT-TYPE
	SYNTAX	INTEGER {
		    no (1),
		    yes (2)
		}
	ACCESS	read-write
	STATUS	mandatory
	DESCRIPTION	""
	::= { mibdhcpServerProfileEntry 2 }

    dhcpServerProfile-PnpEnabled	OBJECT-TYPE
	SYNTAX	INTEGER {
		    no (1),
		    yes (2)
		}
	ACCESS	read-write
	STATUS	mandatory
	DESCRIPTION	""
	::= { mibdhcpServerProfileEntry 3 }

    dhcpServerProfile-IpAddress	OBJECT-TYPE
	SYNTAX	IpAddress
	ACCESS	read-write
	STATUS	mandatory
	DESCRIPTION	""
	::= { mibdhcpServerProfileEntry 4 }

    dhcpServerProfile-Netmask	OBJECT-TYPE
	SYNTAX	IpAddress
	ACCESS	read-write
	STATUS	mandatory
	DESCRIPTION	""
	::= { mibdhcpServerProfileEntry 5 }

    dhcpServerProfile-RenewalTime	OBJECT-TYPE
	SYNTAX	INTEGER
	ACCESS	read-write
	STATUS	mandatory
	DESCRIPTION	""
	::= { mibdhcpServerProfileEntry 6 }

    dhcpServerProfile-BecomeDefRouter	OBJECT-TYPE
	SYNTAX	INTEGER {
		    no (1),
		    yes (2)
		}
	ACCESS	read-write
	STATUS	mandatory
	DESCRIPTION	"If set to Yes, then we will advertise ourself as the Default Route in the DHCP reply messages."
	::= { mibdhcpServerProfileEntry 7 }

    dhcpServerProfile-DialIfLinkDown	OBJECT-TYPE
	SYNTAX	INTEGER {
		    no (1),
		    yes (2)
		}
	ACCESS	read-write
	STATUS	mandatory
	DESCRIPTION	"When DHCP Request is spoofed, dial the first connection profile"
	::= { mibdhcpServerProfileEntry 8 }

    dhcpServerProfile-AlwaysSpoof	OBJECT-TYPE
	SYNTAX	INTEGER {
		    no (1),
		    yes (2)
		}
	ACCESS	read-write
	STATUS	mandatory
	DESCRIPTION	"When PnP is enabled, offer choice to always spoof or not"
	::= { mibdhcpServerProfileEntry 9 }

    dhcpServerProfile-ValidateIp	OBJECT-TYPE
	SYNTAX	INTEGER {
		    no (1),
		    yes (2)
		}
	ACCESS	read-write
	STATUS	mandatory
	DESCRIPTION	"If TRUE, we will validate the address."
	::= { mibdhcpServerProfileEntry 10 }

    dhcpServerProfile-MaxNoReplyWait	OBJECT-TYPE
	SYNTAX	INTEGER
	ACCESS	read-write
	STATUS	mandatory
	DESCRIPTION	"How long to wait for reply to our ICMP echo request."
	::= { mibdhcpServerProfileEntry 11 }

    dhcpServerProfile-GroupOneCount	OBJECT-TYPE
	SYNTAX	INTEGER
	ACCESS	read-write
	STATUS	mandatory
	DESCRIPTION	"Number of IP addresses in this group."
	::= { mibdhcpServerProfileEntry 12 }

    dhcpServerProfile-IpGroupTwo	OBJECT-TYPE
	SYNTAX	IpAddress
	ACCESS	read-write
	STATUS	mandatory
	DESCRIPTION	"Begining IP address in this group."
	::= { mibdhcpServerProfileEntry 13 }

    dhcpServerProfile-GroupTwoCount	OBJECT-TYPE
	SYNTAX	INTEGER
	ACCESS	read-write
	STATUS	mandatory
	DESCRIPTION	"Number of IP addresses in this group."
	::= { mibdhcpServerProfileEntry 14 }

    dhcpServerProfile-IpGroupTwoNetmask	OBJECT-TYPE
	SYNTAX	IpAddress
	ACCESS	read-write
	STATUS	mandatory
	DESCRIPTION	"Netmask for this group of IP addresses."
	::= { mibdhcpServerProfileEntry 15 }

    dhcpServerProfile-TftpHost	OBJECT-TYPE
	SYNTAX	DisplayString
	ACCESS	read-write
	STATUS	mandatory
	DESCRIPTION	"The TFTP host name used for obtaining config data."
	::= { mibdhcpServerProfileEntry 16 }

    dhcpServerProfile-BootpPath	OBJECT-TYPE
	SYNTAX	DisplayString
	ACCESS	read-write
	STATUS	mandatory
	DESCRIPTION	"Complete file path to where configuration file may be found."
	::= { mibdhcpServerProfileEntry 17 }

    dhcpServerProfile-Action-o	OBJECT-TYPE
	SYNTAX	INTEGER {
		    noAction (1),
		    createProfile (2),
		    deleteProfile (3)
		}
	ACCESS	read-write
	STATUS	mandatory
	DESCRIPTION	""
	::= { mibdhcpServerProfileEntry 18 }


	-- The mibdhcpServerProfile__host_addr table
	--
	-- This table contains parameters for the mibdhcpServerProfile__host_addr profile
	--

    mibdhcpServerProfile-HostAddrTable	OBJECT-TYPE
	SYNTAX		SEQUENCE OF MibdhcpServerProfile-HostAddrEntry
	ACCESS		not-accessible
	STATUS		mandatory
	DESCRIPTION	"A list of mibdhcpServerProfile__host_addr profile entries."
	::= { mibdhcpServerProfile 2 }

    mibdhcpServerProfile-HostAddrEntry	OBJECT-TYPE
	SYNTAX		MibdhcpServerProfile-HostAddrEntry
	ACCESS		not-accessible
	STATUS		mandatory
	DESCRIPTION	"A mibdhcpServerProfile__host_addr entry containing objects that
			 maps to the parameters of mibdhcpServerProfile__host_addr profile."
	INDEX		{ dhcpServerProfile-HostAddr-Index-o, dhcpServerProfile-HostAddr-Index1-o }
	::= { mibdhcpServerProfile-HostAddrTable 1 }

    MibdhcpServerProfile-HostAddrEntry ::=
	SEQUENCE {
	    dhcpServerProfile-HostAddr-Index-o
		INTEGER,
	    dhcpServerProfile-HostAddr-Index1-o
		INTEGER,
	    dhcpServerProfile-HostAddr
		DisplayString
	}

    dhcpServerProfile-HostAddr-Index-o	OBJECT-TYPE
	SYNTAX	INTEGER
	ACCESS	read-only
	STATUS	mandatory
	DESCRIPTION	""
	::= { mibdhcpServerProfile-HostAddrEntry 1 }

    dhcpServerProfile-HostAddr-Index1-o	OBJECT-TYPE
	SYNTAX	INTEGER
	ACCESS	read-only
	STATUS	mandatory
	DESCRIPTION	""
	::= { mibdhcpServerProfile-HostAddrEntry 2 }

    dhcpServerProfile-HostAddr	OBJECT-TYPE
	SYNTAX	DisplayString
	ACCESS	read-write
	STATUS	mandatory
	DESCRIPTION	"Ethernet address (MAC) for host with above IP address."
	::= { mibdhcpServerProfile-HostAddrEntry 3 }


	-- The mibdhcpServerProfile__host_netmask table
	--
	-- This table contains parameters for the mibdhcpServerProfile__host_netmask profile
	--

    mibdhcpServerProfile-HostNetmaskTable	OBJECT-TYPE
	SYNTAX		SEQUENCE OF MibdhcpServerProfile-HostNetmaskEntry
	ACCESS		not-accessible
	STATUS		mandatory
	DESCRIPTION	"A list of mibdhcpServerProfile__host_netmask profile entries."
	::= { mibdhcpServerProfile 3 }

    mibdhcpServerProfile-HostNetmaskEntry	OBJECT-TYPE
	SYNTAX		MibdhcpServerProfile-HostNetmaskEntry
	ACCESS		not-accessible
	STATUS		mandatory
	DESCRIPTION	"A mibdhcpServerProfile__host_netmask entry containing objects that
			 maps to the parameters of mibdhcpServerProfile__host_netmask profile."
	INDEX		{ dhcpServerProfile-HostNetmask-Index-o, dhcpServerProfile-HostNetmask-Index1-o }
	::= { mibdhcpServerProfile-HostNetmaskTable 1 }

    MibdhcpServerProfile-HostNetmaskEntry ::=
	SEQUENCE {
	    dhcpServerProfile-HostNetmask-Index-o
		INTEGER,
	    dhcpServerProfile-HostNetmask-Index1-o
		INTEGER,
	    dhcpServerProfile-HostNetmask
		IpAddress
	}

    dhcpServerProfile-HostNetmask-Index-o	OBJECT-TYPE
	SYNTAX	INTEGER
	ACCESS	read-only
	STATUS	mandatory
	DESCRIPTION	""
	::= { mibdhcpServerProfile-HostNetmaskEntry 1 }

    dhcpServerProfile-HostNetmask-Index1-o	OBJECT-TYPE
	SYNTAX	INTEGER
	ACCESS	read-only
	STATUS	mandatory
	DESCRIPTION	""
	::= { mibdhcpServerProfile-HostNetmaskEntry 2 }

    dhcpServerProfile-HostNetmask	OBJECT-TYPE
	SYNTAX	IpAddress
	ACCESS	read-write
	STATUS	mandatory
	DESCRIPTION	"Netmask for the specific host address."
	::= { mibdhcpServerProfile-HostNetmaskEntry 3 }


	-- The mibdhcpServerProfile__host_ip table
	--
	-- This table contains parameters for the mibdhcpServerProfile__host_ip profile
	--

    mibdhcpServerProfile-HostIpTable	OBJECT-TYPE
	SYNTAX		SEQUENCE OF MibdhcpServerProfile-HostIpEntry
	ACCESS		not-accessible
	STATUS		mandatory
	DESCRIPTION	"A list of mibdhcpServerProfile__host_ip profile entries."
	::= { mibdhcpServerProfile 4 }

    mibdhcpServerProfile-HostIpEntry	OBJECT-TYPE
	SYNTAX		MibdhcpServerProfile-HostIpEntry
	ACCESS		not-accessible
	STATUS		mandatory
	DESCRIPTION	"A mibdhcpServerProfile__host_ip entry containing objects that
			 maps to the parameters of mibdhcpServerProfile__host_ip profile."
	INDEX		{ dhcpServerProfile-HostIp-Index-o, dhcpServerProfile-HostIp-Index1-o }
	::= { mibdhcpServerProfile-HostIpTable 1 }

    MibdhcpServerProfile-HostIpEntry ::=
	SEQUENCE {
	    dhcpServerProfile-HostIp-Index-o
		INTEGER,
	    dhcpServerProfile-HostIp-Index1-o
		INTEGER,
	    dhcpServerProfile-HostIp
		IpAddress
	}

    dhcpServerProfile-HostIp-Index-o	OBJECT-TYPE
	SYNTAX	INTEGER
	ACCESS	read-only
	STATUS	mandatory
	DESCRIPTION	""
	::= { mibdhcpServerProfile-HostIpEntry 1 }

    dhcpServerProfile-HostIp-Index1-o	OBJECT-TYPE
	SYNTAX	INTEGER
	ACCESS	read-only
	STATUS	mandatory
	DESCRIPTION	""
	::= { mibdhcpServerProfile-HostIpEntry 2 }

    dhcpServerProfile-HostIp	OBJECT-TYPE
	SYNTAX	IpAddress
	ACCESS	read-write
	STATUS	mandatory
	DESCRIPTION	"A specific IP address for a specific host."
	::= { mibdhcpServerProfile-HostIpEntry 3 }


	-- The mibappOptionsProfile table
	--
	-- This table contains parameters for the mibappOptionsProfile profile
	--

    mibappOptionsProfileTable	OBJECT-TYPE
	SYNTAX		SEQUENCE OF MibappOptionsProfileEntry
	ACCESS		not-accessible
	STATUS		mandatory
	DESCRIPTION	"A list of mibappOptionsProfile profile entries."
	::= { mibappOptionsProfile 1 }

    mibappOptionsProfileEntry	OBJECT-TYPE
	SYNTAX		MibappOptionsProfileEntry
	ACCESS		not-accessible
	STATUS		mandatory
	DESCRIPTION	"A mibappOptionsProfile entry containing objects that
			 maps to the parameters of mibappOptionsProfile profile."
	INDEX		{ appOptionsProfile-Index-o }
	::= { mibappOptionsProfileTable 1 }

    MibappOptionsProfileEntry ::=
	SEQUENCE {
	    appOptionsProfile-Index-o
		INTEGER,
	    appOptionsProfile-PwsEnabled
		INTEGER,
	    appOptionsProfile-PwsHost
		IpAddress,
	    appOptionsProfile-PwsPort
		INTEGER,
	    appOptionsProfile-Action-o
		INTEGER
	}

    appOptionsProfile-Index-o	OBJECT-TYPE
	SYNTAX	INTEGER
	ACCESS	read-only
	STATUS	mandatory
	DESCRIPTION	""
	::= { mibappOptionsProfileEntry 1 }

    appOptionsProfile-PwsEnabled	OBJECT-TYPE
	SYNTAX	INTEGER {
		    no (1),
		    yes (2)
		}
	ACCESS	read-write
	STATUS	mandatory
	DESCRIPTION	""
	::= { mibappOptionsProfileEntry 2 }

    appOptionsProfile-PwsHost	OBJECT-TYPE
	SYNTAX	IpAddress
	ACCESS	read-write
	STATUS	mandatory
	DESCRIPTION	""
	::= { mibappOptionsProfileEntry 3 }

    appOptionsProfile-PwsPort	OBJECT-TYPE
	SYNTAX	INTEGER
	ACCESS	read-write
	STATUS	mandatory
	DESCRIPTION	""
	::= { mibappOptionsProfileEntry 4 }

    appOptionsProfile-Action-o	OBJECT-TYPE
	SYNTAX	INTEGER {
		    noAction (1),
		    createProfile (2),
		    deleteProfile (3)
		}
	ACCESS	read-write
	STATUS	mandatory
	DESCRIPTION	""
	::= { mibappOptionsProfileEntry 5 }


	-- The mibdnisProfile table
	--
	-- This table contains parameters for the mibdnisProfile profile
	--

    mibdnisProfileTable	OBJECT-TYPE
	SYNTAX		SEQUENCE OF MibdnisProfileEntry
	ACCESS		not-accessible
	STATUS		mandatory
	DESCRIPTION	"A list of mibdnisProfile profile entries."
	::= { mibdnisProfile 1 }

    mibdnisProfileEntry	OBJECT-TYPE
	SYNTAX		MibdnisProfileEntry
	ACCESS		not-accessible
	STATUS		mandatory
	DESCRIPTION	"A mibdnisProfile entry containing objects that
			 maps to the parameters of mibdnisProfile profile."
	INDEX		{ dnisProfile-Index-o }
	::= { mibdnisProfileTable 1 }

    MibdnisProfileEntry ::=
	SEQUENCE {
	    dnisProfile-Index-o
		INTEGER,
	    dnisProfile-Enabled
		INTEGER,
	    dnisProfile-Action-o
		INTEGER
	}

    dnisProfile-Index-o	OBJECT-TYPE
	SYNTAX	INTEGER
	ACCESS	read-only
	STATUS	mandatory
	DESCRIPTION	""
	::= { mibdnisProfileEntry 1 }

    dnisProfile-Enabled	OBJECT-TYPE
	SYNTAX	INTEGER {
		    no (1),
		    yes (2)
		}
	ACCESS	read-write
	STATUS	mandatory
	DESCRIPTION	"Is Dnis selection enabled ?"
	::= { mibdnisProfileEntry 2 }

    dnisProfile-Action-o	OBJECT-TYPE
	SYNTAX	INTEGER {
		    noAction (1),
		    createProfile (2),
		    deleteProfile (3)
		}
	ACCESS	read-write
	STATUS	mandatory
	DESCRIPTION	""
	::= { mibdnisProfileEntry 3 }


	-- The mibdnisProfile__dnis_tab table
	--
	-- This table contains parameters for the mibdnisProfile__dnis_tab profile
	--

    mibdnisProfile-DnisTabTable	OBJECT-TYPE
	SYNTAX		SEQUENCE OF MibdnisProfile-DnisTabEntry
	ACCESS		not-accessible
	STATUS		mandatory
	DESCRIPTION	"A list of mibdnisProfile__dnis_tab profile entries."
	::= { mibdnisProfile 2 }

    mibdnisProfile-DnisTabEntry	OBJECT-TYPE
	SYNTAX		MibdnisProfile-DnisTabEntry
	ACCESS		not-accessible
	STATUS		mandatory
	DESCRIPTION	"A mibdnisProfile__dnis_tab entry containing objects that
			 maps to the parameters of mibdnisProfile__dnis_tab profile."
	INDEX		{ dnisProfile-DnisTab-Index-o, dnisProfile-DnisTab-Index1-o }
	::= { mibdnisProfile-DnisTabTable 1 }

    MibdnisProfile-DnisTabEntry ::=
	SEQUENCE {
	    dnisProfile-DnisTab-Index-o
		INTEGER,
	    dnisProfile-DnisTab-Index1-o
		INTEGER,
	    dnisProfile-DnisTab-DnisNumber
		DisplayString,
	    dnisProfile-DnisTab-DnisMaxCalls
		INTEGER,
	    dnisProfile-DnisTab-DnisMaxCallsModem
		INTEGER,
	    dnisProfile-DnisTab-DnisMaxCallsHdlc
		INTEGER,
	    dnisProfile-DnisTab-DnisMaxCallsV110
		INTEGER
	}

    dnisProfile-DnisTab-Index-o	OBJECT-TYPE
	SYNTAX	INTEGER
	ACCESS	read-only
	STATUS	mandatory
	DESCRIPTION	""
	::= { mibdnisProfile-DnisTabEntry 1 }

    dnisProfile-DnisTab-Index1-o	OBJECT-TYPE
	SYNTAX	INTEGER
	ACCESS	read-only
	STATUS	mandatory
	DESCRIPTION	""
	::= { mibdnisProfile-DnisTabEntry 2 }

    dnisProfile-DnisTab-DnisNumber	OBJECT-TYPE
	SYNTAX	DisplayString
	ACCESS	read-write
	STATUS	mandatory
	DESCRIPTION	"Dnis number entry"
	::= { mibdnisProfile-DnisTabEntry 3 }

    dnisProfile-DnisTab-DnisMaxCalls	OBJECT-TYPE
	SYNTAX	INTEGER
	ACCESS	read-write
	STATUS	mandatory
	DESCRIPTION	"Max calls allowed"
	::= { mibdnisProfile-DnisTabEntry 4 }

    dnisProfile-DnisTab-DnisMaxCallsModem	OBJECT-TYPE
	SYNTAX	INTEGER
	ACCESS	read-write
	STATUS	mandatory
	DESCRIPTION	"Max modem calls allowed"
	::= { mibdnisProfile-DnisTabEntry 5 }

    dnisProfile-DnisTab-DnisMaxCallsHdlc	OBJECT-TYPE
	SYNTAX	INTEGER
	ACCESS	read-write
	STATUS	mandatory
	DESCRIPTION	"Max hdlc calls allowed"
	::= { mibdnisProfile-DnisTabEntry 6 }

    dnisProfile-DnisTab-DnisMaxCallsV110	OBJECT-TYPE
	SYNTAX	INTEGER
	ACCESS	read-write
	STATUS	mandatory
	DESCRIPTION	"Max V110 calls allowed"
	::= { mibdnisProfile-DnisTabEntry 7 }


	-- The mibwanOptionsProfile table
	--
	-- This table contains parameters for the mibwanOptionsProfile profile
	--

    mibwanOptionsProfileTable	OBJECT-TYPE
	SYNTAX		SEQUENCE OF MibwanOptionsProfileEntry
	ACCESS		not-accessible
	STATUS		mandatory
	DESCRIPTION	"A list of mibwanOptionsProfile profile entries."
	::= { mibwanOptionsProfile 1 }

    mibwanOptionsProfileEntry	OBJECT-TYPE
	SYNTAX		MibwanOptionsProfileEntry
	ACCESS		not-accessible
	STATUS		mandatory
	DESCRIPTION	"A mibwanOptionsProfile entry containing objects that
			 maps to the parameters of mibwanOptionsProfile profile."
	INDEX		{ wanOptionsProfile-Index-o }
	::= { mibwanOptionsProfileTable 1 }

    MibwanOptionsProfileEntry ::=
	SEQUENCE {
	    wanOptionsProfile-Index-o
		INTEGER,
	    wanOptionsProfile-DialPlan
		INTEGER,
	    wanOptionsProfile-TrunkGroupsNa
		INTEGER,
	    wanOptionsProfile-RingBack
		INTEGER,
	    wanOptionsProfile-Action-o
		INTEGER
	}

    wanOptionsProfile-Index-o	OBJECT-TYPE
	SYNTAX	INTEGER
	ACCESS	read-only
	STATUS	mandatory
	DESCRIPTION	""
	::= { mibwanOptionsProfileEntry 1 }

    wanOptionsProfile-DialPlan	OBJECT-TYPE
	SYNTAX	INTEGER
	ACCESS	read-write
	STATUS	mandatory
	DESCRIPTION	""
	::= { mibwanOptionsProfileEntry 2 }

    wanOptionsProfile-TrunkGroupsNa	OBJECT-TYPE
	SYNTAX	INTEGER {
		    no (1),
		    yes (2)
		}
	ACCESS	read-write
	STATUS	mandatory
	DESCRIPTION	""
	::= { mibwanOptionsProfileEntry 3 }

    wanOptionsProfile-RingBack	OBJECT-TYPE
	SYNTAX	INTEGER {
		    no (1),
		    yes (2)
		}
	ACCESS	read-write
	STATUS	mandatory
	DESCRIPTION	"When FALSE modem ringback tones will not be generated for digital modem calls. Required for some intl locations."
	::= { mibwanOptionsProfileEntry 4 }

    wanOptionsProfile-Action-o	OBJECT-TYPE
	SYNTAX	INTEGER {
		    noAction (1),
		    createProfile (2),
		    deleteProfile (3)
		}
	ACCESS	read-write
	STATUS	mandatory
	DESCRIPTION	""
	::= { mibwanOptionsProfileEntry 5 }


	-- The mibwanOptionsProfile__ether_ans_number table
	--
	-- This table contains parameters for the mibwanOptionsProfile__ether_ans_number profile
	--

    mibwanOptionsProfile-EtherAnsNumberTable	OBJECT-TYPE
	SYNTAX		SEQUENCE OF MibwanOptionsProfile-EtherAnsNumberEntry
	ACCESS		not-accessible
	STATUS		mandatory
	DESCRIPTION	"A list of mibwanOptionsProfile__ether_ans_number profile entries."
	::= { mibwanOptionsProfile 2 }

    mibwanOptionsProfile-EtherAnsNumberEntry	OBJECT-TYPE
	SYNTAX		MibwanOptionsProfile-EtherAnsNumberEntry
	ACCESS		not-accessible
	STATUS		mandatory
	DESCRIPTION	"A mibwanOptionsProfile__ether_ans_number entry containing objects that
			 maps to the parameters of mibwanOptionsProfile__ether_ans_number profile."
	INDEX		{ wanOptionsProfile-EtherAnsNumber-Index-o, wanOptionsProfile-EtherAnsNumber-Index1-o }
	::= { mibwanOptionsProfile-EtherAnsNumberTable 1 }

    MibwanOptionsProfile-EtherAnsNumberEntry ::=
	SEQUENCE {
	    wanOptionsProfile-EtherAnsNumber-Index-o
		INTEGER,
	    wanOptionsProfile-EtherAnsNumber-Index1-o
		INTEGER,
	    wanOptionsProfile-EtherAnsNumber
		DisplayString
	}

    wanOptionsProfile-EtherAnsNumber-Index-o	OBJECT-TYPE
	SYNTAX	INTEGER
	ACCESS	read-only
	STATUS	mandatory
	DESCRIPTION	""
	::= { mibwanOptionsProfile-EtherAnsNumberEntry 1 }

    wanOptionsProfile-EtherAnsNumber-Index1-o	OBJECT-TYPE
	SYNTAX	INTEGER
	ACCESS	read-only
	STATUS	mandatory
	DESCRIPTION	""
	::= { mibwanOptionsProfile-EtherAnsNumberEntry 2 }

    wanOptionsProfile-EtherAnsNumber	OBJECT-TYPE
	SYNTAX	DisplayString
	ACCESS	read-write
	STATUS	mandatory
	DESCRIPTION	"Incoming calls directed to these numbers are assumed to be LAN connections."
	::= { mibwanOptionsProfile-EtherAnsNumberEntry 3 }

END
