Wellfleet-RADIUS-MIB DEFINITIONS ::= BEGIN


    IMPORTS

      IpAddress, Counter
        FROM RFC1155-SMI
      OBJECT-TYPE
        FROM RFC-1212
      DisplayString
        FROM RFC1213-MIB
      wfRadiusGroup
        FROM Wellfleet-COMMON-MIB;


    wfRadiusTable OBJECT-TYPE
        SYNTAX	SEQUENCE OF WfRadiusEntry
        ACCESS	not-accessible
        STATUS	mandatory
        DESCRIPTION
                "Radius slot information by the Radius Client."
        ::= { wfRadiusGroup 1 }

    wfRadiusEntry OBJECT-TYPE
        SYNTAX	WfRadiusEntry
        ACCESS	not-accessible
        STATUS	mandatory
        DESCRIPTION
                "An entry defining RADIUS on specified slot"
        INDEX	{ wfRadiusSlot }
        ::= { wfRadiusTable 1 }

    WfRadiusEntry ::= SEQUENCE {
            wfRadiusDelete
                INTEGER,
            wfRadiusAuthDisable
                INTEGER,                
            wfRadiusAcctDisable
                INTEGER, 
      	    wfRadiusSlot
    		INTEGER,
	    wfRadiusClientIpAddress
		IpAddress,
            wfRadiusAcctDirection
                INTEGER,                
            wfRadiusDebugMsgLevel
                INTEGER,
            wfRadiusCfgMask
                INTEGER
        }

    wfRadiusDelete OBJECT-TYPE
        SYNTAX	INTEGER {
    		    created(1),
    		    deleted(2)
    		}
        ACCESS	read-write
        STATUS	mandatory
        DESCRIPTION
                "`This value specifies if RADIUS is configured on this
	 	router. '"
        DEFVAL	{ created }
        ::= { wfRadiusEntry 1 }

    wfRadiusAuthDisable OBJECT-TYPE
        SYNTAX	INTEGER {
    		    enabled(1),
    		    disabled(2)
    		}
        ACCESS	read-write
        STATUS	mandatory
        DESCRIPTION
                "`The value enabled specifies that RADIUS authentication
		is active on the router. The value disabled specifies it is
		configured, but has been deactivated."
	DEFVAL	{ disabled }
        ::= { wfRadiusEntry 2 }

    wfRadiusAcctDisable OBJECT-TYPE
        SYNTAX	INTEGER {
    		    enabled(1),
    		    disabled(2)
    		}
        ACCESS	read-write
        STATUS	mandatory
        DESCRIPTION
                "`The value enabled specifies that RADIUS accounting
		is active on the router. The value disabled specifies it is
		configured, but has been deactivated."
	DEFVAL	{ disabled }
        ::= { wfRadiusEntry 3 }

    wfRadiusSlot OBJECT-TYPE
        SYNTAX	INTEGER
        ACCESS	read-only
        STATUS	mandatory
        DESCRIPTION
                "The slots number configured for RADIUS authentication"
	::= { wfRadiusEntry 4 }

    wfRadiusClientIpAddress OBJECT-TYPE
	SYNTAX  IpAddress
	ACCESS 	read-write
        STATUS	mandatory
        DESCRIPTION
                "A 32-bit integer specifying the IP address associated with
		 Radius Client."
	::= { wfRadiusEntry 5 }

    wfRadiusAcctDirection OBJECT-TYPE
        SYNTAX	INTEGER {
    		    all(1),
    		    incoming(2),
		    outgoing(3)
    		}
        ACCESS	read-write
        STATUS	mandatory
        DESCRIPTION
                "The value specifies whether a session should generate accounting 
	         request based o n the direction of the call.
	         all- means sessions established by  incoming as well as outgoing 
	              calls  ma generate accounting requests.
	         incoming- only sessions established by incoming calls may generate 
		           accounting requests.
		 outgoing- only sessions established by outgoing calls may generate 
		           accounting requests."
	DEFVAL	{ all }
        ::= { wfRadiusEntry 6 }

    wfRadiusDebugMsgLevel OBJECT-TYPE
        SYNTAX	INTEGER {
    		    one(1),
    		    two(2),
    		    three(3),
    		    nodebug(4)
    		}
        ACCESS	read-write
        STATUS	mandatory
        DESCRIPTION
                "This attribute is used to assign the level of RADIUS Debug
                messages logged by the RADIUS client."
        DEFVAL	{ nodebug }
        ::= { wfRadiusEntry 7 }

    wfRadiusCfgMask OBJECT-TYPE
        SYNTAX  INTEGER
        ACCESS  read-write
        STATUS  mandatory
        DESCRIPTION
                "Used by SM to indicate the Radius being configured by L2TP or by Switch Service."
        DEFVAL  { 0 }
        ::= { wfRadiusEntry 8 }

    wfRadiusServerTable OBJECT-TYPE
        SYNTAX	SEQUENCE OF WfRadiusServerEntry
        ACCESS	not-accessible
        STATUS	mandatory
        DESCRIPTION
                "Table of servers accessible for this router."
        ::= { wfRadiusGroup 2 }

    wfRadiusServerEntry OBJECT-TYPE
        SYNTAX	WfRadiusServerEntry
        ACCESS	not-accessible
        STATUS	mandatory
        DESCRIPTION
                ""
        INDEX	{ wfRadiusServerIpAddress }
        ::= { wfRadiusServerTable 1 }

    WfRadiusServerEntry ::= SEQUENCE {
        wfRadiusServerDelete
                INTEGER,
        wfRadiusServerDisable
                INTEGER,
        wfRadiusServerIpAddress
                IpAddress,
 	wfRadiusServerMode
		INTEGER,
	wfRadiusServerAuthState
		INTEGER,
        wfRadiusServerAuthUdpPort 
                INTEGER,
        wfRadiusServerAuthType
                INTEGER,
	wfRadiusServerAcctState
		INTEGER,
	wfRadiusServerAcctUdpPort
		INTEGER,
 	wfRadiusServerAcctType
	       INTEGER,	
        wfRadiusPrimarySecret
                DisplayString,
        wfRadiusServerResponseTimeout
                INTEGER,
        wfRadiusServerRetryMax
                INTEGER,
        wfRadiusServerResetTimer
                INTEGER,
	wfRadiusServerAutomaticReset
		INTEGER
        }

    wfRadiusServerDelete OBJECT-TYPE
        SYNTAX	INTEGER {
    		    created(1),
    		    deleted(2)
    		}
        ACCESS	read-write
        STATUS	mandatory
        DESCRIPTION
                ""
        DEFVAL	{ created }
        ::= { wfRadiusServerEntry 1 }

    wfRadiusServerDisable OBJECT-TYPE
        SYNTAX	INTEGER {
    		    enabled(1),
    		    disabled(2)
    		}
        ACCESS	read-write
        STATUS	mandatory
        DESCRIPTION
                " "
	DEFVAL	{ enabled }
        ::= { wfRadiusServerEntry 2 }

    wfRadiusServerIpAddress OBJECT-TYPE
        SYNTAX 	IpAddress
        ACCESS 	read-only
        STATUS	mandatory
        DESCRIPTION
                "`A 32-bit integer specifying the IP address of the primary
		RADIUS server"
	::= { wfRadiusServerEntry 3}
  
    wfRadiusServerMode OBJECT-TYPE
	SYNTAX INTEGER {
    		 authonly(1),
    		 acctonly(2),
		 both(3)
		}
	ACCESS	 read-write
        STATUS	 mandatory
        DESCRIPTION
                "The server supports both authentication and accounting"
	DEFVAL	{both}
        ::= { wfRadiusServerEntry 4}

    wfRadiusServerAuthState OBJECT-TYPE
	SYNTAX  INTEGER {
		up(1),
		down(2)
		}
	ACCESS  read-only
	STATUS  mandatory
	DESCRIPTION
		"Displays the state of the Radius Server as seen by the
		Radius Client"
	DEFVAL  { up }
	::= { wfRadiusServerEntry 5 }

    wfRadiusServerAuthUdpPort OBJECT-TYPE
        SYNTAX	 INTEGER
        ACCESS	 read-write
        STATUS	 mandatory
        DESCRIPTION
                "The UDP port of the RADIUS server"
	DEFVAL	{1645}
        ::= { wfRadiusServerEntry 6}

    wfRadiusServerAuthType OBJECT-TYPE
	SYNTAX INTEGER {
    		 primary(1),
    		 alternate(2)
		}
	ACCESS	 read-write
        STATUS	 mandatory
        DESCRIPTION
                "The server type either primary or alternate"
	DEFVAL	{primary}
        ::= { wfRadiusServerEntry 7}

    wfRadiusServerAcctState OBJECT-TYPE
	SYNTAX  INTEGER {
		up(1),
		down(2)
		}
	ACCESS  read-only
	STATUS  mandatory
	DESCRIPTION
		"Displays the state of the Radius Server as seen by the
		Radius Client"
	DEFVAL  { up }
	::= { wfRadiusServerEntry 8 }


    wfRadiusServerAcctUdpPort OBJECT-TYPE
        SYNTAX	 INTEGER
        ACCESS	 read-write
        STATUS	 mandatory
        DESCRIPTION
                "The UDP port of the RADIUS  accounting server"
	DEFVAL	{1646}
        ::= { wfRadiusServerEntry 9}

    wfRadiusServerAcctType OBJECT-TYPE
	SYNTAX INTEGER {
    		 primary(1),
    		 alternate(2)
		}
	ACCESS	 read-write
        STATUS	 mandatory
        DESCRIPTION
                "The accounting server type either primary or alternate"
	DEFVAL	{primary}
        ::= { wfRadiusServerEntry 10}

    wfRadiusPrimarySecret OBJECT-TYPE
        SYNTAX	 DisplayString
        ACCESS 	 read-write
        STATUS	 mandatory
        DESCRIPTION
                "`The secret used to communicate with the primary
		RADIUS server"
	::= { wfRadiusServerEntry 11}

    wfRadiusServerResponseTimeout OBJECT-TYPE
        SYNTAX	 INTEGER(1..60)
        ACCESS	 read-write
        STATUS	 mandatory
        DESCRIPTION
                "The number of seconds to wait before retransmitting
		the request to the server"
	DEFVAL	{ 3 }
        ::= { wfRadiusServerEntry 12}

    wfRadiusServerRetryMax OBJECT-TYPE
        SYNTAX	 INTEGER(1..10)
        ACCESS	 read-write
        STATUS	 mandatory
        DESCRIPTION
                "The maximum number of times a request is retransmitted
		before determining the RADIUS server is unreachable"
	DEFVAL	{ 2 }
	::= { wfRadiusServerEntry 13}

    wfRadiusServerResetTimer OBJECT-TYPE
        SYNTAX	 INTEGER(1..60)
        ACCESS	 read-write
        STATUS	 mandatory
        DESCRIPTION
                "The number of minutes to wait before retrying the
		primary RADIUS sever after a failure."
	DEFVAL	{ 10 }
        ::= { wfRadiusServerEntry 14}

    wfRadiusServerAutomaticReset OBJECT-TYPE
	SYNTAX	INTEGER {
		enabled (1),
		disabled (2)
		}
	ACCESS	read-write
	STATUS	mandatory
	DESCRIPTION
		" If enabled, automatically resets the state of the failed server to be
		available. Sends a test access request to the failed server at intervals
		configured in wfRadiusServerResetTimer and marks it available if a reply 
		is received.
		  If disabled, reset the state of the failed server to available after the
		timeout configured in wfRadiusServerResetTimer. No test access requests are
		sent."
	DEFVAL	{disabled}
	::= { wfRadiusServerEntry 15 }



    wfRadiusStatsTable OBJECT-TYPE
        SYNTAX	SEQUENCE OF WfRadiusStatsEntry
        ACCESS	not-accessible
        STATUS	mandatory
        DESCRIPTION
                "Table of RADIUS server statistic record."
        ::= { wfRadiusGroup 3 }

    wfRadiusStatsEntry OBJECT-TYPE
        SYNTAX	WfRadiusStatsEntry
        ACCESS	not-accessible
        STATUS	mandatory
        DESCRIPTION
                ""
        INDEX	{ wfRadiusStatsSlot,
                  wfRadiusStatsIpAddress }
        ::= { wfRadiusStatsTable 1 }

    WfRadiusStatsEntry ::= SEQUENCE {
        wfRadiusStatsIpAddress
                IpAddress,
	wfRadiusStatsSlot
		INTEGER,
	wfRadiusStatsAuthReqCount
		INTEGER,
        wfRadiusStatsAuthReqOutstanding
                INTEGER,
	wfRadiusStatsAuthRespSucc
		INTEGER,
        wfRadiusStatsAuthRespFail
                INTEGER,
        wfRadiusStatsAuthNoResp
                INTEGER,        
        wfRadiusStatsAuthRespInvalid
                INTEGER,
        wfRadiusStatsAuthRespTimeouts
                INTEGER,
	wfRadiusStatsAuthAltServerRetries
		INTEGER,
	wfRadiusStatsAcctReqStart
		Counter,
	wfRadiusStatsAcctReqStop
		Counter,
	wfRadiusStatsAcctRespTimeouts
		Counter,
	wfRadiusStatsAcctRespFailed
		Counter,
	wfRadiusStatsAcctAltServerRetries
		Counter,
	wfRadiusStatsAcctResponse
		Counter
        }

    wfRadiusStatsIpAddress OBJECT-TYPE
        SYNTAX 	IpAddress
        ACCESS 	read-only
        STATUS	mandatory
        DESCRIPTION
                "`A 32-bit integer specifying the IP address of the 
		RADIUS server"
	::= { wfRadiusStatsEntry 1}

    wfRadiusStatsSlot OBJECT-TYPE
        SYNTAX	INTEGER
        ACCESS 	read-only
        STATUS	mandatory
        DESCRIPTION
                "RADIUS server statistics per slot"
	::= { wfRadiusStatsEntry 2}
    wfRadiusStatsAuthReqCount OBJECT-TYPE
        SYNTAX	INTEGER
        ACCESS 	read-only
        STATUS	mandatory
        DESCRIPTION
                "Successful RADIUS Authentication request maded to this
                RADIUS server from this slot"
	::= { wfRadiusStatsEntry 3}

    wfRadiusStatsAuthReqOutstanding OBJECT-TYPE
        SYNTAX	INTEGER
        ACCESS 	read-only
        STATUS	mandatory
        DESCRIPTION
                "Outstanding RADIUS Authentication request made to this
                RADIUS server from this slot"
	::= { wfRadiusStatsEntry 4}

    wfRadiusStatsAuthRespSucc OBJECT-TYPE
        SYNTAX	INTEGER
        ACCESS 	read-only
        STATUS	mandatory
        DESCRIPTION
                "Successful RADIUS Authentication request maded to this
                RADIUS server from this slot"
	::= { wfRadiusStatsEntry 5}
    wfRadiusStatsAuthRespFail OBJECT-TYPE
        SYNTAX	INTEGER
        ACCESS 	read-only
        STATUS	mandatory
        DESCRIPTION
                "Failed RADIUS Authentication request maded to this
                RADIUS server from this slot"
	::= { wfRadiusStatsEntry 6}
    wfRadiusStatsAuthNoResp OBJECT-TYPE
        SYNTAX	INTEGER
        ACCESS 	read-only
        STATUS	mandatory
        DESCRIPTION
                "No valid RADIUS Authentication response received from
                RADIUS server or No server available."
	::= { wfRadiusStatsEntry 7}
    wfRadiusStatsAuthRespInvalid OBJECT-TYPE
        SYNTAX	INTEGER
        ACCESS 	read-only
        STATUS	mandatory
        DESCRIPTION
                "Invalid RADIUS Authentication response received from
                RADIUS server on this slot"
	::= { wfRadiusStatsEntry 8}
    wfRadiusStatsAuthRespTimeouts OBJECT-TYPE
        SYNTAX	INTEGER
        ACCESS 	read-only
        STATUS	mandatory
        DESCRIPTION
                "Number of Timeouts occuring to this
                RADIUS server from this slot"
	::= { wfRadiusStatsEntry 9}
    wfRadiusStatsAuthAltServerRetries OBJECT-TYPE
        SYNTAX	INTEGER
        ACCESS 	read-only
        STATUS	mandatory
        DESCRIPTION
                "Number of requests for alternate RADIUS serverfrom this 
                 slot based on failure to communicate with this server"
	::= { wfRadiusStatsEntry 10}

    wfRadiusStatsAcctReqStart OBJECT-TYPE
	SYNTAX Counter
	ACCESS read-only
	STATUS mandatory
	DESCRIPTION
		"Number of Accounting requests indicating Start of
		a call"
	::= { wfRadiusStatsEntry 11 }

    wfRadiusStatsAcctReqStop OBJECT-TYPE
	SYNTAX Counter
	ACCESS read-only
	STATUS mandatory
	DESCRIPTION
		"Number of Accounting requests indicating Stop of
		a call"
	::= { wfRadiusStatsEntry 12}

   wfRadiusStatsAcctRespTimeouts OBJECT-TYPE
	SYNTAX Counter
	ACCESS read-only
	STATUS mandatory
	DESCRIPTION
		"Number of Accounting requests timed out waiting for
		response from the Accounting Server"
	::= { wfRadiusStatsEntry 13 }

   wfRadiusStatsAcctRespFailed OBJECT-TYPE
	SYNTAX Counter
	ACCESS read-only
	STATUS mandatory
	DESCRIPTION
		"Number of Accounting requests that did not get a response"
	::= { wfRadiusStatsEntry 14 }

   wfRadiusStatsAcctAltServerRetries OBJECT-TYPE
	SYNTAX Counter
	ACCESS read-only
	STATUS mandatory
	DESCRIPTION
		"Number of retries expiring causing alternate server to be used.
		This statistic indicates the server used as an alternate server."
	::= { wfRadiusStatsEntry 15 }

   wfRadiusStatsAcctResponse OBJECT-TYPE
	SYNTAX Counter
	ACCESS read-only
	STATUS mandatory
	DESCRIPTION
		"Number of Accounting Responses from the Accounting server"
	::= { wfRadiusStatsEntry 16 }

    END  -- Wellfleet-RADIUS-MIB
