TR-STNASSIGN-MIB DEFINITIONS ::= BEGIN

	--  TR-StnAssign-mib.txt
	--  Revision: 01.00.01
	--  Part Number:  
	--  Date: August 11, 1995

	--  Cabletron Systems, Inc.
	--  35 Industrial Way, P.O. Box 5005
	--  Rochester, NH 03867-0505
	--  (603) 332-9400
	--  support@ctron.com

	--  This module provides authoritative definitions for Cabletron's
	--  enterprise-specific physical chassis management MIB
	--  for Token Ring devices.
	--
	--  This module will be extended, as required.
	--

	--  Cabletron Systems reserves the right to make changes in 
	--  specification and other information contained in this document 
	--  without prior notice.  The reader should consult Cabletron Systems
	--  to determine whether any such changes have been made.
	--
	--  In no event shall Cabletron Systems be liable for any incidental, 
	--  indirect, special, or consequential damages whatsoever (including 
	--  but not limited to lost profits) arising out of or related to this
	--  document or the information contained in it, even if Cabletron
	--  Systems has been advised of, known, or should have known, the 
	--  possibility of such damages.
	--
	--  Cabletron grants vendors, end-users, and other interested parties
	--  a non-exclusive license to use this Specification in connection
	--  with the management of Cabletron products.

	--  Copyright (c)1995 Cabletron Systems

--
IMPORTS
	ctTRStnAssign
		FROM CTRON-MIB-NAMES
	OBJECT-TYPE
		FROM RFC-1212;

-- Formal definitions for Cabletron's Dot5 Physical MIB

--
-- ============================================================
--
-- Managed Objects in Support of Dot5 Physical Management for Token Ring Devices
--
-- ============================================================
--
-- Implementation of this group of objects is optional.
--
-- ============================================================

stnInterfaceCount       OBJECT-TYPE
SYNTAX                  INTEGER
ACCESS                  read-only
STATUS                  mandatory
DESCRIPTION
    "Returns the number of station interfaces stored in table
     stnAssignTable."
 ::= { ctTRStnAssign 1 }

stnAssignTable                  OBJECT-TYPE
SYNTAX          SEQUENCE OF StnAssignTableEntry
ACCESS          not-accessible
STATUS          mandatory
DESCRIPTION
    "A list of managed objects which pertains to a collection of token
     ring interfaces physically residing in the managing device."
 ::= { ctTRStnAssign 2 }

stnAssignTableEntry     OBJECT-TYPE
SYNTAX                  StnAssignTableEntry
ACCESS                  not-accessible
STATUS                  mandatory
DESCRIPTION
    "A list of managed objects which pertains to a single instance of a
     token ring interface physically residing in the managing device."
INDEX   { stnAssignIndex }
 ::= { stnAssignTable 1 }

StnAssignTableEntry ::=
  SEQUENCE {
        stnAssignIndex
                INTEGER,
        stnAssignPortAssociation
                OBJECT IDENTIFIER,
        stnAssignPortRing
                INTEGER
}

stnAssignIndex                  OBJECT-TYPE
SYNTAX  INTEGER
ACCESS  read-only
STATUS  mandatory
DESCRIPTION
    "Returns an index to a stnAssignTable for which the information in
     this table pertains"
 ::= { stnAssignTableEntry 1 }

stnAssignPortAssociation        OBJECT-TYPE
SYNTAX  OBJECT IDENTIFIER
ACCESS  read-write
STATUS  mandatory
DESCRIPTION
    "This object, when read, would return an OID indicating the board and
     port to which the eagle port has been inserted. When written, this
     object will update the board and port data stored in this object.  The
     OID to be passed for reading and writing is:
     dot5PhysMgmtPortCommonPortId."
 ::= { stnAssignTableEntry 2 }

stnAssignPortRing               OBJECT-TYPE
SYNTAX  INTEGER ( 1..255 )
ACCESS  read-only
STATUS  mandatory
DESCRIPTION
    "This object will return the physical fnb ring into which the station
     eagle port is inserted. Return values are defined as:
          1..200 - Fnb ring 1 to Fnb ring 200
        201..254 - AUX ring 1 to AUX ring 54
     Non multi-fnb mim boards will always return 1"
 ::= { stnAssignTableEntry 3 }

--
-- Revision History
--
-- Rev 0.00.01
-- Date: July 18, 1994
--
--  Initial working document.
--

END
