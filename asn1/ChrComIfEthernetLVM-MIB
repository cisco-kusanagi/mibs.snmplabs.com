ChrComIfEthernetLVM-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComIfEthernet			FROM  Chromatis-MIB
	DisplayString			FROM  RFC1213-MIB
	QoSTypeMappingEnum			FROM  EthernetTypes-MIB
	RowStatusEnum				FROM  EthernetTypes-MIB;

-- chrComIfEthernetLVM Table

chrComIfEthernetLVMTable		OBJECT-TYPE
	SYNTAX		SEQUENCE OF ChrComIfEthernetLVMEntry
	MAX-ACCESS	not-accessible
	STATUS		current
	DESCRIPTION
	"This table lists all LVMs and their associated configuration parameters (e.g. QoS Mapping Table)"
	::= { chrComIfEthernet 1}

chrComIfEthernetLVMEntry		OBJECT-TYPE
	SYNTAX		ChrComIfEthernetLVMEntry
	MAX-ACCESS	not-accessible
	STATUS		current
	DESCRIPTION
	""
	INDEX  {  chrComIfEthernetEquipIndex, chrComIfEthernetLocalElmIndex, chrComIfEthernetLvmID }

--DEFAULT  get-function-async  MNIL_GetRoutine
--DEFAULT  set-function-async  MNIL_SetRoutine
--DEFAULT  next-function-async MNIL_NextRoutine
--DEFAULT  test-function-async MNIL_TestRoutine
--DEFAULT  cookie "LVM"
	::= { chrComIfEthernetLVMTable  1 }

ChrComIfEthernetLVMEntry  ::=
	SEQUENCE  {
	chrComIfEthernetEquipIndex		Integer32	(0..65535),
	chrComIfEthernetLocalElmIndex		Integer32	(0..1),
	chrComIfEthernetLvmID			Integer32	(0..7),
	chrComIfEthernetvlanName		DisplayString	(SIZE (0..32)),
	chrComIfEthernetGlobaVlanID		Unsigned32	(0..4294967295),
	chrComIfEthernetMemberID		Unsigned32	(0..27),
	chrComIfEthernetQoSMappingType		QoSTypeMappingEnum,
	chrComIfEthernetDefaultLQC		Unsigned32	(0..2),
	chrComIfEthernetQoSMappingTable		Integer32	(0..65535),
	chrComIfEthernetRowStatus		RowStatusEnum
}

chrComIfEthernetEquipIndex 	OBJECT-TYPE
	SYNTAX		Integer32	(0..65535)
	MAX-ACCESS 	read-write
	STATUS 		current
	DESCRIPTION
	""
	::= { chrComIfEthernetLVMEntry  1 }

chrComIfEthernetLocalElmIndex 	OBJECT-TYPE
	SYNTAX		Integer32	(0..1)
	MAX-ACCESS 	read-write
	STATUS 		current
	DESCRIPTION
	"ELM index within card (up to 2 ELMs per card; current card has only 1)"
	::= { chrComIfEthernetLVMEntry  2 }

chrComIfEthernetLvmID 	OBJECT-TYPE
	SYNTAX		Integer32	(0..7)
	MAX-ACCESS 	read-write
	STATUS 		current
	DESCRIPTION
	"ID of LVM within this ELM"
	::= { chrComIfEthernetLVMEntry  3 }

chrComIfEthernetvlanName 	OBJECT-TYPE
	SYNTAX		DisplayString	(SIZE (0..32))
	MAX-ACCESS 	read-write
	STATUS 		current
	DESCRIPTION
	"Global name of VLAN, assigned by NMS. Used only for display"
	::= { chrComIfEthernetLVMEntry  4 }

chrComIfEthernetGlobaVlanID 	OBJECT-TYPE
	SYNTAX		Unsigned32	(0..4294967295)
	MAX-ACCESS 	read-write
	STATUS 		current
	DESCRIPTION
	"Global ID of VLAN assigned by NMS. Used only by NMS"
	::= { chrComIfEthernetLVMEntry  5 }

chrComIfEthernetMemberID 	OBJECT-TYPE
	SYNTAX		Unsigned32	(0..27)
	MAX-ACCESS 	read-write
	STATUS 		current
	DESCRIPTION
	"Member-ID of this LVM within its Global VLAN"
	::= { chrComIfEthernetLVMEntry  6 }

chrComIfEthernetQoSMappingType 	OBJECT-TYPE
	SYNTAX		QoSTypeMappingEnum
	MAX-ACCESS 	read-write
	STATUS 		current
	DESCRIPTION
	"Defines what type of QoS Mapping is used for this LVM"
	::= { chrComIfEthernetLVMEntry  7 }

chrComIfEthernetDefaultLQC 	OBJECT-TYPE
	SYNTAX		Unsigned32	(0..2)
	MAX-ACCESS 	read-write
	STATUS 		current
	DESCRIPTION
	"Default LQC, to be used if mapping cannot be done or configured to None"
	::= { chrComIfEthernetLVMEntry  8 }

chrComIfEthernetQoSMappingTable 	OBJECT-TYPE
	SYNTAX		Integer32	(0..65535)
	MAX-ACCESS 	read-write
	STATUS 		current
	DESCRIPTION
	"Mapping Table for QoS codes"
	::= { chrComIfEthernetLVMEntry  9 }

chrComIfEthernetRowStatus 	OBJECT-TYPE
	SYNTAX		RowStatusEnum
	MAX-ACCESS 	read-write
	STATUS 		current
	DESCRIPTION
	"This object is used to create a new row or modify or delete an existing row in this table"
	::= { chrComIfEthernetLVMEntry  10 }


END
