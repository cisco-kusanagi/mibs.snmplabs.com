--  HLS Bridge MIB Object Definitions         June 1991

          -- This MIB module contains definitions of all MIB objects 
          -- supported by the various models of HLS bridges.  No single
          -- HLS bridge supports all of the MIB objects defined in this 
          -- MIB module.

          -- HLS-MIB   { iso org(3) dod(6) internet(1) private(4)
          --                     enterprises(1) 26 }

          HLS-MIB   DEFINITIONS ::= BEGIN

          IMPORTS
                   enterprises, IpAddress, Counter, TimeTicks
                      FROM RFC1155-SMI
                   DisplayString
                      FROM RFC1213-MIB;

          --  This MIB Module uses the extended OBJECT-TYPE macro as
          --  defined in RFC-1212.

          hls             OBJECT IDENTIFIER ::= { enterprises 26 }

          hlsBridges      OBJECT IDENTIFIER ::= { hls 2 }
          hlsSystem       OBJECT IDENTIFIER ::= { hls 20 }
          ethernetBridge  OBJECT IDENTIFIER ::= { hlsBridges 1 }
          remoteEthernetBridge
                          OBJECT IDENTIFIER ::= { hlsBridges 2 }
          tokenBusBridge  OBJECT IDENTIFIER ::= { hlsBridges 3 }
          tokenRingBridge OBJECT IDENTIFIER ::= { hlsBridges 23 }


          hlsTemporary    OBJECT IDENTIFIER ::= { hls 21 }
          hlsDot1dBridge  OBJECT IDENTIFIER ::= { hlsTemporary 1 }
          hlsDot1dBase    OBJECT IDENTIFIER ::= { hlsDot1dBridge 1 }
          hlsDot1dStp     OBJECT IDENTIFIER ::= { hlsDot1dBridge 2 }


          MacAddress ::= OCTET STRING (SIZE (6))


          --  common to all/most HLS devices

          sysType OBJECT-TYPE
                  SYNTAX INTEGER {
                             bridge(1),
                             terminalServer(3)
                          }
                  ACCESS read-only
                  STATUS  mandatory
                  DESCRIPTION
                          "The type of system in which the agent is
                          running"
                  ::= { hls 3 }

          serialNumber OBJECT-TYPE
                  SYNTAX  INTEGER
                  ACCESS  read-only
                  STATUS  mandatory
                  DESCRIPTION
                          "The serial number of the system being managed."
                  ::= { hls 4 }

          bootPromVersion OBJECT-TYPE
                  SYNTAX  DisplayString
                  ACCESS  read-only
                  STATUS  mandatory
                  DESCRIPTION
                         "The version number of the boot prom in the
                         system.  The value is an ASCII string."
                  ::= { hls 5 }

          sysAdmAccess OBJECT-TYPE
                  SYNTAX  INTEGER {
                              none(1),
                              password(2),
                              pfx(3)
                          }
                  ACCESS  read-write
                  STATUS  mandatory
                  DESCRIPTION
                         "The method being used to authenticate a user
                         of the system's console/administrative port."
                  ::= {  hls 6 }

          appSwVersion OBJECT-TYPE
                  SYNTAX  DisplayString
                  ACCESS  read-only
                  STATUS  mandatory
                  DESCRIPTION
                         "The version number of the application-software
                         the system is executing.  This value is an ASCII
                         string."
                  ::= {  hls 7 }

          userProfile OBJECT-TYPE
                  SYNTAX  OCTET STRING
                  ACCESS  read-only
                  STATUS  obsolete
                  ::= { hls 8 }

          hlsMibVersion OBJECT-TYPE
                  SYNTAX  INTEGER {
                              versionA(1),
                              versionB(2)
                          }
                  ACCESS  read-only
                  STATUS  mandatory
                  DESCRIPTION
                         "The version number of the HLS-defined MIB
                         extensions supported by the agent.  The version
                         of the HLS MIB defined in this document is
                         versionB(2)."
                  ::= { hls 9 }

          myManager OBJECT-TYPE
                  SYNTAX IpAddress
                  ACCESS read-only
                  STATUS  deprecated
                  DESCRIPTION
                         "The manager to which the agent sends traps."
                  ::= { hls 10 }

          sysReset OBJECT-TYPE
                  SYNTAX  INTEGER {
                              level1(1),
                              level2(2),
                              level3(3),
                              level4(4),
                              level5(5)
                          }
                  ACCESS  write-only
                  STATUS  mandatory
                  DESCRIPTION
                         "Writing to this object causes the agent to
                         reset its system.  The value written to the
                         object determines the reset-level."
                  ::= {  hls 11 }

          clearCounters OBJECT-TYPE
                  SYNTAX  INTEGER
                  ACCESS  write-only
                  STATUS  mandatory
                  DESCRIPTION
                     "Writing any value to this object causes the agent
                     to clear (i.e. set to zero) the values of all
                     instances of object-types having the syntax: Counter."
                  ::= {  hls 12 }

          systemDate OBJECT-TYPE
                  SYNTAX  DisplayString (SIZE (8))
                  ACCESS  read-write
                  STATUS  mandatory
                  DESCRIPTION
                     "The current system date as known by the agent,
                     formatted as an ASCII string: MM-DD-YY."
                  ::= {  hls 13 }

          systemTime OBJECT-TYPE
                  SYNTAX  DisplayString (SIZE (8))
                  ACCESS  read-write
                  STATUS  mandatory
                  DESCRIPTION
                     "The current system time as known by the agent,
                     formatted as an ASCII string: HH:MM:SS."
                  ::= {  hls 14 }

          alarmOption OBJECT-TYPE
                  SYNTAX OCTET STRING
                  ACCESS read-write
                  STATUS  obsolete
                  ::= { hls 15 }

          snmpAccess OBJECT-TYPE
                  SYNTAX INTEGER {
                             password(1),
                             pfx(2),
                             community(3)
                          }
                  ACCESS read-only
                  STATUS  obsolete
                  ::= { hls 16 }

          myIpAddress OBJECT-TYPE
                  SYNTAX  IpAddress
                  ACCESS  read-write
                  STATUS  mandatory
                  DESCRIPTION
                     "The agent's IP Address.  When a new value is
                     written to this object, the system's IP Address is
                     changed immediately after responding to the request."
                  ::= {  hls 17 }

          defaultGateway OBJECT-TYPE
                  SYNTAX  IpAddress
                  ACCESS  read-write
                  STATUS  mandatory
                  DESCRIPTION
                     "The IP gateway, to which IP datagrams destined
                     for a remote network will be sent unless and until
                     directed otherwise by an ICMP Redirect."
                  ::= {  hls 18 }

          netMask OBJECT-TYPE
                  SYNTAX  IpAddress
                  ACCESS  read-write
                  STATUS  mandatory
                  DESCRIPTION
                     "The network mask associated with myIpAddress.
                     The value of the mask is an IP Address with all
                     network bits set to 1, and all host bits set to 0."
                  ::= {  hls 19 }

          snmpAuth OBJECT-TYPE
                  SYNTAX  INTEGER {
                              --  none(0),
                              hlsPassword(1),
                              hlsPfx(2),
                              snmpCommunity(3)
                          }
                  ACCESS  read-write
                  STATUS  mandatory
                  DESCRIPTION
                     "The method by which the agent is to authenticate
                     the SNMP requests it receives.  Both the
                     hlsPassword(1) and the hlsPfx(2) methods require
                     that the use of an 'association' set-up via an
                     HLS-defined extension to the SNMP protocol.  The
                     value of snmpCommunity(3) specifies the SNMP
                     standard use of a community-name.  The value none(0)
                     specifies that no authentication checking is done."
                  ::= {  hlsSystem 1 }

          trapTable OBJECT-TYPE
                  SYNTAX  SEQUENCE OF TrapEntry
                  ACCESS  not-accessible
                  STATUS  mandatory
                  DESCRIPTION
                        "The table which identifies the parameters
                        associated with the agent's generation of
                        SNMP traps."
                  ::= { hlsSystem 5 }

          trapEntry OBJECT-TYPE
                  SYNTAX  TrapEntry
                  ACCESS  not-accessible
                  STATUS  mandatory
                  DESCRIPTION
                        "There is one entry of this table for each
                        destination to which the agent sends SNMP traps."
                  INDEX   { trapEntryNumber }
                  ::= { trapTable 1 }

          TrapEntry ::= SEQUENCE {
                            trapDestination
                                IpAddress,
                            genericTrapSwitches
                                OCTET STRING,
                            specificTrapSwitches
                                OCTET STRING,
                            trapEntryNumber
                                INTEGER
                        }

          trapDestination OBJECT-TYPE
                  SYNTAX  IpAddress
                  ACCESS  read-write
                  STATUS  mandatory
                  DESCRIPTION
                        "The destination IP Address to which traps
                        enabled in this entry's switches are sent.
                        Writing to an instance of this object-type
                        which does not currently exist, causes a new
                        entry in the table to be created with default
                        settings for the trap switches, except when the
                        table already contains entries for the maximum
                        number of trap destinations the agent supports."
                  ::= { trapEntry 1 }

          genericTrapSwitches OBJECT-TYPE
                  SYNTAX  OCTET STRING
                  ACCESS  read-write
                  STATUS  mandatory
                  DESCRIPTION
                        "This object's value contains one octet for each
                        type of SNMP-standard generic trap. If the agent
                        is enabled to send a particular type of trap to
                        this entry's destination, the corresponding octet
                        contains a non-zero value; otherwise, if the
                        corresponding octet has a zero value, the agent
                        is disabled from sending that type of trap to
                        this entry's destination. Writing to an instance
                        of this object-type which does not currently
                        exist is an error.
                            The octets for specific traps are positioned
                        in the OCTET STRING, according to their values in
                        the 'generic-trap' field of an SNMP trap message:

                                     octet  generic-trap field
                                      1st    coldStart(0)
                                      2nd    warmStart(1)
                                      3rd    linkDown(2)
                                         etc."
                  ::= { trapEntry 2 }

          specificTrapSwitches OBJECT-TYPE
                  SYNTAX  OCTET STRING
                  ACCESS  read-write
                  STATUS  mandatory
                  DESCRIPTION
                        "This object's value contains one octet for each
                        type of enterprise-specific trap. If the agent is
                        enabled to send a particular type of trap to this
                        entry's destination, the corresponding octet
                        contains a non-zero value; otherwise, if the
                        corresponding octet has a zero value, the agent
                        is disabled from sending that type of trap to this
                        entry's destination. Writing to an instance of
                        this object-type which does not currently exist
                        is an error.

                            The octets for specific traps are positioned
                        in the OCTET STRING, according to their values in
                        the 'specific-trap' field of an SNMP trap message:

                                   octet     value of specific-trap
                                    1st             0
                                    2nd             1
                                    3rd             2
                                          etc.
                        Note that enterprise-specific traps must be
                        enabled by the setting of the appropriate octet
                        of genericTrapSwitches, before the value of this
                        object takes effect."
                  ::= { trapEntry 3 }

          trapEntryNumber OBJECT-TYPE
                  SYNTAX  INTEGER
                  ACCESS  not-accessible
                  STATUS  mandatory
                  DESCRIPTION
                          "An integer in the range 1 <= i <= N, where N
                          is the maximum number of trap destinations for
                          this agent."
                  ::= { trapEntry 4 }


          --  Objects common to all HLS bridges


          bridgeModel OBJECT-TYPE
                  SYNTAX  INTEGER {
                              hls8080(1),
                              hls8050(2),
                              hls8011(3),
                              hls8200(4),
                              hls8220(5),
                              hls8500(6),
                              hls8033(7),
                              hls8032(8),
                              hls8133(9),
                              hls8233(10),
                              hls8235(12)
                          }
                  ACCESS  read-only
                  STATUS  mandatory
                  DESCRIPTION
                        "The HLS model number of the bridge."
                  ::= {  hlsBridges 4 }

          bridgeMode OBJECT-TYPE
                  SYNTAX  INTEGER {
                              backup(1),
                              active(2),
                              offline(3),
                              spanningTree(4)
                          }
                  ACCESS  read-write
                  STATUS  mandatory
                  DESCRIPTION
                        "The current mode of the bridge."
                  ::= { hlsBridges 15 }

          ageingOption OBJECT-TYPE
                  SYNTAX  INTEGER {
                              notAgeing(1),
                              ageing(2)
                          }
                  ACCESS  read-write
                  STATUS  mandatory
                  DESCRIPTION
                        "The status of the Ageing option in the bridge."
                  ::= {  hlsBridges 16 }


          --    The Channel Table

          --    One entry per port on the bridge.  Ports on the bridge
          --    are mapped one-to-one with entries in the standard MIB's
          --    ifTable [4,6].  For channel-0, ifIndex has the value 1.
          --    For channel-1, ifIndex has the value 2.

          channelTable OBJECT-TYPE
                  SYNTAX  SEQUENCE OF ChannelEntry
                  ACCESS  not-accessible
                  STATUS  mandatory
                  DESCRIPTION
                        "The table of per-channel attributes."
                  ::= {  hlsBridges 17 }

          channelEntry OBJECT-TYPE
                  SYNTAX  ChannelEntry
                  ACCESS  not-accessible
                  STATUS  mandatory
                  DESCRIPTION
                        "A channel entry containing attributes
                        applicable to a particular channel."
                  INDEX   { channelNumber }
                  ::= {  channelTable 1 }

          ChannelEntry ::= SEQUENCE {
                               chLearnMode
                                   INTEGER,
                               chRestrictMode
                                   INTEGER,
                               chOriginMode
                                   INTEGER,
                               chGroupFwdMode
                                   INTEGER,
                               chIndFwdMode
                                   INTEGER,
                               chDefRestrictFlag
                                   INTEGER,
                               chDefStaticFlag
                                   INTEGER,
                               chDefOriginFlag
                                   INTEGER,
                               chInCRCs
                                   Counter,
                               chInOverruns
                                   Counter,
                               chOutColls
                                   Counter,
                               chWhos
                                   Counter,
                               chInRunts
                                   Counter,
                               chInGiants
                                   Counter,
                               chInLenErrors
                                   Counter,
                               chInLocks
                                   Counter,
                               chOutLocks
                                   Counter,
                               chNoBuffers
                                   Counter,
                               channelNumber
                                   INTEGER
                           }

          chLearnMode OBJECT-TYPE
                  SYNTAX  INTEGER {
                              disabled(1),
                              enabled(2)
                          }
                  ACCESS  read-write
                  STATUS  mandatory
                  DESCRIPTION
                        "The status of learning mode for this channel."
                  ::= {  channelEntry 1 }

          chRestrictMode OBJECT-TYPE
                  SYNTAX  INTEGER {
                              disabled(1),
                              enabled(2)
                          }
                  ACCESS  read-only
                  STATUS  mandatory
                  DESCRIPTION
                        "The status of Restrict mode for this channel.
                        A channel's Restrict mode must be enabled in
                        order for the channel to have filtering by
                        destination address enabled for any address."
                  ::= {  channelEntry 2 }

          chOriginMode OBJECT-TYPE
                  SYNTAX  INTEGER {
                              disabled(1),
                              enabled(2)
                          }
                  ACCESS  read-write
                  STATUS  mandatory
                  DESCRIPTION
                        "The status of the Origin mode for this channel.
                        A channel's Origin mode must be enabled in order
                        for the channel to have filtering of non-unicast
                        destination addresses enabled for any individual
                        source addresses."
                  ::= {  channelEntry 3 }

          chGroupFwdMode OBJECT-TYPE
                  SYNTAX  INTEGER {
                              disabled(1),
                              enabled(2)
                          }
                  ACCESS  read-write
                  STATUS  mandatory
                  DESCRIPTION
                        "The value of this object determines whether
                        frames destined for unknown group addresses
                        (i.e. multicast addresses which have not been
                        statically configured) are to be forwarded on
                        this channel."
                  ::= {  channelEntry 4 }

          chIndFwdMode OBJECT-TYPE
                  SYNTAX  INTEGER {
                              disabled(1),
                              enabled(2)
                          }
                  ACCESS  read-write
                  STATUS  mandatory
                  DESCRIPTION
                        "The value of this object determines whether
                        frames destined for unknown individual addresses
                        (i.e. unicast addresses which are not present
                        in the bridge's forwarding tables) are to be
                        forwarded on this channel."
                  ::= {  channelEntry 5 }

          chDefRestrictFlag OBJECT-TYPE
                  SYNTAX  INTEGER {
                              disabled(1),
                              enabled(2)
                          }
                  ACCESS  read-write
                  STATUS  mandatory
                  DESCRIPTION
                        "The value to which the Restrict flag is set for
                        subsequently (re-)learnt addresses on this
                        channel.  When Restrict mode is enabled, frames
                        to adestination address which has the Restrict
                        flag set are not forwarded."
                  ::= {  channelEntry 6 }

          chDefStaticFlag OBJECT-TYPE
                  SYNTAX  INTEGER {
                              disabled(1),
                              enabled(2)
                          }
                  ACCESS  read-write
                  STATUS  mandatory
                  DESCRIPTION
                        "The value to which the Static flag is set for
                        subsequently learnt addresses on this channel.
                        Addresses with the Static flag set do not age."
                  ::= {  channelEntry 7 }

          chDefOriginFlag OBJECT-TYPE
                  SYNTAX  INTEGER {
                              disabled(1),
                              enabled(2)
                          }
                  ACCESS  read-write
                  STATUS  mandatory
                  DESCRIPTION
                        "The value to which the Origin flag is set for
                        subsequently (re-)learnt addresses on this
                        channel.  When Origin mode is enabled, frames
                        destined for non-unicast addresses are not
                        forwarded if their source address has the
                        Origin flag set."
                  ::= {  channelEntry 8 }

          chInCRCs OBJECT-TYPE
                  SYNTAX  Counter
                  ACCESS  read-only
                  STATUS  mandatory
                  DESCRIPTION
                        "The number of packets for which a CRC error has
                        been detected.  For channels on which CRC errors
                        can not occur, this object always has a value
                        of 0."
                  ::= {  channelEntry 9 }

          chInOverruns OBJECT-TYPE
                  SYNTAX  Counter
                  ACCESS  read-only
                  STATUS  mandatory
                  DESCRIPTION
                        "The number of received packets for which an
                        overrun error occurred.  For channels on which
                        overruns can not occur, this object always has
                        a value of 0."
                  ::= { channelEntry 10 }

          chOutColls OBJECT-TYPE
                  SYNTAX  Counter
                  ACCESS  read-only
                  STATUS  mandatory
                  DESCRIPTION
                        "On a CSMA/CD interface, the number of packets
                        for which a collision occurred during
                        transmission.  On any other type of interface,
                        this counter is always zero."
                  ::= { channelEntry 11 }

          chWhos OBJECT-TYPE
                  SYNTAX  Counter
                  ACCESS  read-only
                  STATUS  mandatory
                  DESCRIPTION
                        "On a token-bus interface, the number of times
                        the bridge had to ask who its successor is.  On
                        any other type of interface, the value of this
                        counter is always zero."
                  ::= { channelEntry 12 }

          chInRunts OBJECT-TYPE
                  SYNTAX  Counter
                  ACCESS  read-only
                  STATUS  mandatory
                  DESCRIPTION
                        "The number of undersize packets received on
                        this channel."
                  ::= { channelEntry 13 }

          chInGiants OBJECT-TYPE
                  SYNTAX  Counter
                  ACCESS  read-only
                  STATUS  mandatory
                  DESCRIPTION
                        "The number of oversize packets received on
                        this channel."
                  ::= { channelEntry 14 }

          chInLenErrors OBJECT-TYPE
                  SYNTAX  Counter
                  ACCESS  read-only
                  STATUS  mandatory
                  DESCRIPTION
                        "The number of packets received on this channel,
                        for which the number of bytes received was less
                        than the value in the length field of the
                        packet's header."
                  ::= { channelEntry 15 }

          chInLocks OBJECT-TYPE
                  SYNTAX  Counter
                  ACCESS  read-only
                  STATUS  mandatory
                  DESCRIPTION
                        "The number of times an interface was reset
                        because the interface's receive deadman timer
                        expired."
                  ::= { channelEntry 16 }

          chOutLocks OBJECT-TYPE
                  SYNTAX  Counter
                  ACCESS  read-only
                  STATUS  mandatory
                  DESCRIPTION
                        "The number of times an interface was reset
                        because the interface's transmit deadman timer
                        expired."
                  ::= { channelEntry 17 }

          chNoBuffers OBJECT-TYPE
                  SYNTAX    Counter
                  ACCESS    read-only
                  STATUS    mandatory
                  DESCRIPTION
                        "The number of packets not received because the
                        system was temporarily out of buffers, and so
                        could not transfer the data into memory."
                  ::= { channelEntry 18 }

          channelNumber  OBJECT-TYPE
                  SYNTAX  INTEGER 
                  ACCESS  not-accessible
                  STATUS  mandatory
                  DESCRIPTION
                        "The channel number"
                  ::= { channelEntry 19 }


          --   Deprecated object for Protocol Filtering

          protocolBlocking OBJECT-TYPE
                  SYNTAX  OCTET STRING  (SIZE (12))
                  ACCESS  read-only
                  STATUS  deprecated   -- replaced by protocolFilterTable
                  DESCRIPTION
                        "The set of protocols for which the bridge will
                        not forward any packets.  Each octet contains a
                        non-zero value if the corresponding protocol is
                        to be blocked.  The octets correspond to the
                        protocols, as follows:

                               1st octet:   IP
                               2nd octet:   ARP
                               3rd octet:   RARP
                               4th octet:   reserved (must be zero)
                               5th octet:   DECNET
                               6th octet:   IPX
                               7th octet:   V2
                               8th octet:   XNS
                               9th octet:   TOPS
                               10th octet:  BridgeID (3Com T/Servers)
                               11th octet:  LAT
                               12th octet:  AppleTalk"
                  ::= { hlsBridges 18 }


          --   Table of reasons and times for most recent resets/reboots
          --   of the bridge

          resetLogTable OBJECT-TYPE
                  SYNTAX  SEQUENCE OF ResetLogEntry
                  ACCESS  not-accessible
                  STATUS  mandatory
                  DESCRIPTION
                        "Entries in this table record the reasons and
                        times of the most recent resets of the bridge."
                  ::= { hlsBridges 19 }

          resetLogEntry OBJECT-TYPE
                  SYNTAX  ResetLogEntry
                  ACCESS  not-accessible
                  STATUS  mandatory
                  DESCRIPTION
                        "The reason why the bridge was reset, and of how
                        long it was up prior to the reset recorded by
                        this entry."
                  INDEX   { entryNumber }
                  ::= { resetLogTable 1 }

          ResetLogEntry ::= SEQUENCE {
                                reason
                                    INTEGER,
                                uptime
                                    INTEGER,
                                entryNumber
                                    INTEGER
                          }

          reason OBJECT-TYPE
                  SYNTAX  INTEGER {
                              softwareReset(1),
                              buttonPressReset(2),
                              softwareCrash(3),
                              powerFail(4),
                              selfTestFail(5),
                              parityError(6),
                              selfTestReset(7),
                              unknown(8)
                          }
                  ACCESS  read-only
                  STATUS  mandatory
                  DESCRIPTION
                        "The reason for the reset."
                  ::= { resetLogEntry 1 }

          uptime OBJECT-TYPE
                  SYNTAX  OCTET STRING
                  ACCESS  read-only
                  STATUS  mandatory
                  DESCRIPTION
                        "The length of time, in seconds, the bridge had
                        been up prior to the reset represented by this
                        entry."
                  ::= { resetLogEntry 2 }

          entryNumber OBJECT-TYPE
                  SYNTAX  INTEGER
                  ACCESS  not-accessible
                  STATUS  mandatory
                  DESCRIPTION
                          "The number of this entry where the most recent
                          is entry number 1, the second most recent is
                          entry number 2, etc."
                  ::= { resetLogEntry 3 }

          packetSize OBJECT-TYPE
                  SYNTAX  INTEGER {
                              standard(1),
                              extended(2)
                          }
                  ACCESS  read-write
                  STATUS  mandatory
                  DESCRIPTION
                        "The range of frame sizes to be forwarded onto an
                        Ethernet/802.3 network by this bridge.  The value
                        standard(1) represents the standard range of 60
                        through 1536 bytes. The value extended(2)
                        represents the (non-standard) range of 16 through
                        2100 bytes."
                  ::= { hlsBridges 20 }

          transmitDeadmanTimer OBJECT-TYPE
                  SYNTAX  INTEGER
                  ACCESS  read-write
                  STATUS  mandatory
                  DESCRIPTION
                        "The deadman timer for frame transmission on an
                        interface.  The value is the maximum length of
                        time, in units of 160 milliseconds, that a frame
                        will await transmission before the interface is
                        reset."
                  ::= { hlsBridges 21 }

          receiveDeadmanTimer OBJECT-TYPE
                  SYNTAX  INTEGER
                  ACCESS  read-write
                  STATUS  mandatory
                  DESCRIPTION
                        "The deadman timer for frame reception on an
                        interface.  The value is not given in units of
                        time, but rather as a count of frames transmitted
                        on the interface.  If no frames are received on
                        the interface during the interval taken to transmit
                        this count of frames, then the interface is reset."
                  ::= { hlsBridges 22 }


          -- Ethernet Bridge Objects
          --
          -- This group of MIB objects is used for Ethernet bridges


          ramAddrTab8000Tab  OBJECT-TYPE
                  SYNTAX  RamAddrTab8000Tab
                  ACCESS  not-accessible
                  STATUS  mandatory
                  DESCRIPTION
                          "The RAM-resident Address Table in an
                          HLS non-Token-Bus Bridge."
                  INDEX   { ramAddrTab8000Address }
                  ::= { ethernetBridge 1 }

          RamAddrTab8000Tab ::=
              SEQUENCE {
                  ramAddrTab8000Entry
                      OCTET STRING,
                  ramAddrTab8000Address
                      MacAddress
              }

          ramAddrTab8000Entry OBJECT-TYPE
                  SYNTAX  OCTET STRING  (SIZE (4))
                  ACCESS  read-write
                  STATUS  mandatory
                  DESCRIPTION
                        "An instance of this object-type exists for each
                        entry in the RAM-resident Address Table in a HLS
                        non-Token-Bus Bridge.  The format of the OCTET
                        STRING is:

                          1st octet:  1 = Static flag set
                                      0 = Static flag not set
                          2nd octet:  1 = Restrict flag set
                                      0 = Restrict flag not set
                          3rd octet:  1 = Origin flag set
                                      0 = Origin flag not set
                          4th octet:  0 = Bridge's own address
                                      1 = Address on Channel 0
                                      2 = Address on Channel 1
                                      3 = Address is global (i.e. on
                                                        all Channels)

                        Setting an instance of this object-type to a value
                        of ASN.1 type NULL, causes the identified entry in
                        the RAM-resident Address Table to be deleted."
                  ::= {  ramAddrTab8000Tab 1 }

          ramAddrTab8000Address OBJECT-TYPE
                  SYNTAX  MacAddress
                  ACCESS  not-accessible
                  STATUS  mandatory
                  DESCRIPTION
                          "The MAC address associated with this entry"
                  ::= {  ramAddrTab8000Tab 2 }

          ramAddrTab8000Filter OBJECT-TYPE
                  SYNTAX  OCTET STRING  (SIZE (4))
                  ACCESS  read-write
                  STATUS  mandatory
                  DESCRIPTION
                        "Setting this value causes the re-creation of
                        the filtered subset (see the object
                        ramAddrTab8000FilterEntry) of the RAM-resident
                        Address Table in a HLS 80xx Bridge.  The filtered
                        subset consists of all entries which matched the
                        filter value at the time of the last write to
                        this object.  The format of the OCTET STRING is:

                  1st octet:   0 - must not have Static flag set
                               1 - must have Static flag set
                               2 - don't care whether Static flag set
                  2nd octet:   0 - must not have Restrict flag set
                               1 - must have Restrict flag set
                               2 - don't care whether Restrict flag set
                  3rd octet:   0 - must not have Origin flag set
                               1 - must have Origin flag set
                               2 - don't care whether Origin flag set
                  4th octet:   1 - Address must be on channel 0 (only)
                               2 - Address must be on channel 1 (only)
                               3 - Address must be global (channels 0 AND 1)
                               4 - Address must not be only on channel 0
                               5 - Address must not be only on channel 1
                               6 - Address must not be global
                               7 - Address can be on any channels"
                  ::= {  ethernetBridge 2 }

          ramAddrTab8000FilterNum OBJECT-TYPE
                  SYNTAX  INTEGER
                  ACCESS  read-only
                  STATUS  mandatory
                  DESCRIPTION
                        "The current number of entries in the filtered
                        subset of entries in the RAM-resident Address
                        Table in a HLS 80xx Bridge.  The filtered subset
                        consists of allentries which matched the filter
                        value at the time ofthe last write to the object:
                        ramAddrTab8000Filter."
                  ::= {  ethernetBridge 3 }


          ramAddrTab8000FilterTab OBJECT-TYPE
                  SYNTAX  RamAddrTab8000FilterTab
                  ACCESS  not-accessible
                  STATUS  mandatory
                  DESCRIPTION
                          "This table contains the filtered subset of the
                          RAM-resident Address Table in a HLS 80xx Bridge.
                          The filtered subset consists of all entries which
                          matched the filter value at the time of the last
                          write to the object: ramAddrTab8000Filter.  Note
                          that the contents of this table are constant
                          between writes to ramAddrTab8000Filter."
                  INDEX   { ramAddrTab8000FilterIndex }
                  ::= {  ethernetBridge 4 }

          RamAddrTab8000FilterTab ::=
              SEQUENCE {
                  ramAddrTab8000FilterEntry
                      OCTET STRING,
                  ramAddrTab8000FilterIndex
                      INTEGER
              }

          ramAddrTab8000FilterEntry OBJECT-TYPE
                  SYNTAX  OCTET STRING  (SIZE (10))
                  ACCESS  read-only
                  STATUS  mandatory
                  DESCRIPTION
                        "An instance of this object-type exists for each
                        entry in the filtered subset of entries in the
                        RAM-resident Address Table in a HLS 80xx Bridge.
                        The filtered subset consists of a copy of those
                        entries in ramAddrTab8000Tab which matched the
                        filter value at the time of the last write to the
                        object: ramAddrTab8000Filter.  The format of the
                        OCTET STRING is:

                          octets 1-6:  the MAC address of this entry
                          7th octet:   1 = Static flag set
                                       0 = Static flag not set
                          8th octet:   1 = Restrict flag set
                                       0 = Restrict flag not set
                          9th octet:   1 = Origin flag set
                                       0 = Origin flag not set
                          10th octet:  0 = Bridge's own address
                                       1 = Address on Channel 0
                                       2 = Address on Channel 1
                                       3 = Address is global (i.e. on
                                                         all Channels)"
                  ::= {  ramAddrTab8000FilterTab 1 }

          ramAddrTab8000FilterIndex OBJECT-TYPE
                  SYNTAX  INTEGER
                  ACCESS  not-accessible
                  STATUS  mandatory
                  DESCRIPTION
                          "For the i-th entry, this object takes the
                          value i."
                  ::= {  ramAddrTab8000FilterTab 2 }

          ramAddrTab8000Delete OBJECT-TYPE
                  SYNTAX  OCTET STRING  (SIZE (4))
                  ACCESS  write-only
                  STATUS  mandatory
                  DESCRIPTION
                        "Setting this object to a value causes the
                        immediate deletion of a subset of the entries in
                        the RAM-resident Address Table in a HLS 80xx
                        Bridge.  The subset of entries to be deleted is
                        selected by using the value (to which this object
                        is set) as a filter against which all entries are
                        matched, with all entries matching the filter
                        being deleted.  The format of the OCTET STRING is:

                1st octet:   0 - must not have Static flag set
                             1 - must have Static flag set
                             2 - don't care whether Static flag set
                2nd octet:   0 - must not have Restrict flag set
                             1 - must have Restrict flag set
                             2 - don't care whether Restrict flag set
                3rd octet:   0 - must not have Origin flag set
                             1 - must have Origin flag set
                             2 - don't care whether Origin flag set
                4th octet:   1 - Address must be on channel 0 (only)
                             2 - Address must be on channel 1 (only)
                             3 - Address must be global (channels 0 AND 1)
                             4 - Address must not be only on channel 0
                             5 - Address must not be only on channel 1
                             6 - Address must not be global
                             7 - Address can be on any channels"
                  ::= {  ethernetBridge 5 }

          nvramAddrTab8000Tab  OBJECT-TYPE
                  SYNTAX  NvramAddrTab8000Tab
                  ACCESS  not-accessible
                  STATUS  mandatory
                  DESCRIPTION
                          "The Address Table stored in Non-Volatile RAM
                          in a HLS 80xx Bridge."
                  INDEX   { nvramAddrTab8000Address }
                  ::= {  ethernetBridge 6 }

          NvramAddrTab8000Tab ::=
              SEQUENCE {
                  nvramAddrTab8000Entry
                      OCTET STRING,
                  nvramAddrTab8000Address
                      MacAddress
              }

          nvramAddrTab8000Entry OBJECT-TYPE
                  SYNTAX  OCTET STRING  (SIZE (4))
                  ACCESS  read-write
                  STATUS  mandatory
                  DESCRIPTION
                        "An instance of this object-type exists for each
                        entry in the Address Table stored in Non-Volatile
                        RAM in a HLS 80xx Bridge.  The format of the
                        OCTET STRING is:
                               1st octet:  1 = Static flag set
                                           0 = Static flag not set
                               2nd octet:  1 = Restrict flag set
                                           0 = Restrict flag not set
                               3rd octet:  1 = Origin flag set
                                           0 = Origin flag not set
                               4th octet:  0 = Bridge's own address
                                           1 = Address on Channel 0
                                           2 = Address on Channel 1
                                           3 = Address is global
                                                  (i.e. on all Channels)

                        Setting an instance of this object-type to a
                        value of ASN.1 type NULL, causes the identified
                        entry in the Address Table in Non-Volatile RAM
                        to be deleted."
                  ::= {  nvramAddrTab8000Tab 1 }

          nvramAddrTab8000Address OBJECT-TYPE
                  SYNTAX  MacAddress
                  ACCESS  not-accessible
                  STATUS  mandatory
                  DESCRIPTION
                          "The MAC address associated with this entry"
                  ::= { nvramAddrTab8000Tab 2 }

          nvramAddrTab8000Filter OBJECT-TYPE
                  SYNTAX  OCTET STRING  (SIZE (4))
                  ACCESS  read-write
                  STATUS  mandatory
                  DESCRIPTION
                        "Setting this value causes the re-creation
                        of the filtered subset (see the object
                        nvramAddrTab8000FilterEntry) of the Address
                        Table stored in Non-Volatile RAM in a HLS
                        Local/Remote Bridge.  The filtered subset
                        consists of all entries which matched the
                        filter value at the time of the last write to
                        this object.  The format of the OCTET STRING is:

                1st octet:   0 - must not have Static flag set
                             1 - must have Static flag set
                             2 - don't care whether Static flag set
                2nd octet:   0 - must not have Restrict flag set
                             1 - must have Restrict flag set
                             2 - don't care whether Restrict flag set
                3rd octet:   0 - must not have Origin flag set
                             1 - must have Origin flag set
                             2 - don't care whether Origin flag set
                4th octet:   1 - Address must be on channel 0 (only)
                             2 - Address must be on channel 1 (only)
                             3 - Address must be global (channels 0 AND 1)
                             4 - Address must not be only on channel 0
                             5 - Address must not be only on channel 1
                             6 - Address must not be global
                             7 - Address can be on any channels"
                  ::= {  ethernetBridge 7 }

          nvramAddrTab8000FilterNum OBJECT-TYPE
                  SYNTAX  INTEGER
                  ACCESS  read-only
                  STATUS  mandatory
                  DESCRIPTION
                        "The current number of entries in the filtered
                        subset of entries in the Address Table in
                        Non-Volatile RAM in a HLS Local/Remote Bridge.
                        The filtered subset consists of all entries
                        which matched the filter value at the time of the
                        last write to the object: nvramAddrTab8000Filter."
                  ::= {  ethernetBridge 8 }


          nvramAddrTab8000FilterTab  OBJECT-TYPE
                  SYNTAX  NvramAddrTab8000FilterTab
                  ACCESS  not-accessible
                  STATUS  mandatory
                  DESCRIPTION
                          "This table contains the filtered subset of the
                          Address Table in Non-Volatile RAM in a HLS
                          Local/Remote Bridge.  The filtered subset
                          consists of all entries which matched the filter
                          value at the time it was last written to the
                          object: nvramAddrTab8000Filter.  Note that the
                          contents of this table are constant between
                          writes to nvramAddrTab8000Filter."
                  INDEX   { nvramAddrTab8000FilterIndex }
                  ::= { ethernetBridge 9 }

          NvramAddrTab8000FilterTab ::=
              SEQUENCE {
                  nvramAddrTab8000FilterEntry
                      OCTET STRING,
                  nvramAddrTab8000FilterIndex
                      INTEGER
              }

          nvramAddrTab8000FilterEntry OBJECT-TYPE
                  SYNTAX  OCTET STRING (SIZE (10))
                  ACCESS  read-only
                  STATUS  mandatory
                  DESCRIPTION
                        "An instance of this object-type exists for each
                        entry within the filtered subset of the Address
                        Table in Non-Volatile RAM in a HLS Local/Remote
                        Bridge.  The filtered subset consists of all
                        entries which matched the filter value at the
                        time of the last write to the object:
                        nvramAddrTab8000Filter.  The format of the OCTET
                        STRING is:
                            octets 1-6:  the MAC address of this entry
                            7th octet:   1 = Static flag set
                                         0 = Static flag not set
                            8th octet:   1 = Restrict flag set
                                         0 = Restrict flag not set
                            9th octet:   1 = Origin flag set
                                         0 = Origin flag not set
                            10th octet:  0 = Bridge's own address
                                         1 = Address on Channel 0
                                         2 = Address on Channel 1
                                         3 = Address is global
                                               (i.e. on all Channels)"
                  ::= {  nvramAddrTab8000FilterTab 1 }

          nvramAddrTab8000FilterIndex OBJECT-TYPE
                  SYNTAX  INTEGER
                  ACCESS  not-accessible
                  STATUS  mandatory
                  DESCRIPTION
                          "For the i-th entry, this object has
                          the value i."
                  ::= { nvramAddrTab8000FilterTab 2 }

          nvramAddrTab8000Delete OBJECT-TYPE
                  SYNTAX  OCTET STRING  (SIZE (4))
                  ACCESS  write-only
                  STATUS  mandatory
                  DESCRIPTION
                          "Setting this object to a value causes the
                          immediate deletion of a subset of the entries
                          in the Address Table in Non-Volatile RAM in a
                          HLS Local/Remote Bridge.  The subset of entries
                          to be deleted is selected by using the value
                          (to which this object is set) as a filter
                          against which all entries are matched, with
                          all entries matching the filter being deleted.
                          The format of the OCTET STRING is:

                   1st octet:   0 - must not have Static flag set
                                1 - must have Static flag set
                                2 - don't care whether Static flag set
                   2nd octet:   0 - must not have Restrict flag set
                                1 - must have Restrict flag set
                                2 - don't care whether Restrict flag set
                   3rd octet:   0 - must not have Origin flag set
                                1 - must have Origin flag set
                                2 - don't care whether Origin flag set
                   4th octet:   1 - Address must be on channel 0 (only)
                                2 - Address must be on channel 1 (only)
                                3 - Address must be global (channels 0 AND 1)
                                4 - Address must not be only on channel 0
                                5 - Address must not be only on channel 1
                                6 - Address must not be global
                                7 - Address can be on any channels"
                  ::= {  ethernetBridge 10 }

          nvramAddrTab8000Update OBJECT-TYPE
                  SYNTAX  OCTET STRING  (SIZE (4))
                  ACCESS  write-only
                  STATUS  mandatory
                  DESCRIPTION
                          "Setting this object to a value causes an update
                          of the Address Table in Non-Volatile RAM in a
                          HLS Local/Remote Bridge.  This update is the
                          combination of the deletion of all existing
                          entries in Non-Volatile RAM table, followed by
                          the addition of a set of new entries.  The set
                          of new entries is a subset of the current
                          entries in the bridge's RAM-resident Address
                          Table.  That subset is selected by using the
                          value (to which this object is set) as a filter
                          against which all entries in the RAM-resident
                          Address Table are matched.  After the update
                          is completed, the Address Table in Non-Volatile
                          RAM consists of exactly those entries in the
                          RAM-resident Address Table which match with the
                          filter value.  The format of the OCTET STRING
                          is:
                  1st octet:   0 - must not have Static flag set
                               1 - must have Static flag set
                               2 - don't care whether Static flag set
                  2nd octet:   0 - must not have Restrict flag set
                               1 - must have Restrict flag set
                               2 - don't care whether Restrict flag set
                  3rd octet:   0 - must not have Origin flag set
                               1 - must have Origin flag set
                               2 - don't care whether Origin flag set
                  4th octet:   1 - Address must be on channel 0 (only)
                               2 - Address must be on channel 1 (only)
                               3 - Address must be global (channels 0 AND 1)
                               4 - Address must not be only on channel 0
                               5 - Address must not be only on channel 1
                               6 - Address must not be global
                               7 - Address can be on any channels"
                  ::= {  ethernetBridge 11 }



          --   Remote Ethernet Bridge Objects

          segmentBlocking OBJECT-TYPE
                  SYNTAX  INTEGER (0..15)
                  ACCESS  read-write
                  STATUS  mandatory
                  DESCRIPTION
                          "The value of this object is a single octet
                          specifying which address space segments are to
                          be blocked/passed by the bridge (for the purpose
                          of load-sharing between bridges).  Each address
                          space segment corresponds to one bit in the
                          octet; the first segment corresponds to the
                          least significant bit, the second segment with
                          the second leastsignificant bit; etc.  A bit
                          is set to 1 if the corresponding segment is to
                          be blocked."
                  ::= {  remoteEthernetBridge 1 }

          linktype OBJECT-TYPE
                  SYNTAX  INTEGER {
                              rs232Dte(1),
                              v35Dte(2),
                              rs449Dte(3),
                              rs232Dce(4),
                              v35Dce(5),
                              rs449Dce(6)
                          }
                  ACCESS  read-only
                  STATUS  mandatory
                  DESCRIPTION
                          "The type of physical interface being used on
                          the serial interface to the remote bridge."
                  ::= {  remoteEthernetBridge 2 }

          linkSaver OBJECT-TYPE
                  SYNTAX  INTEGER {
                              removePadding(1),
                              leavePadding(2)
                          }
                  ACCESS  read-write
                  STATUS  mandatory
                  DESCRIPTION
                          "The setting of this object controls the use of
                          data compression over the serial link between
                          two bridges.  If set to removePadding(1), then
                          any padding for LAN transmission is not
                          transmitted over the serial link.  Such padding
                          is required on a LAN when a packet is shorter
                          than a minimum-sized frame."
                  ::= { remoteEthernetBridge 3 }

          crcType OBJECT-TYPE
                  SYNTAX  INTEGER {
                              crc16(1),
                              crc32(2)
                          }
                  ACCESS  read-write
                  STATUS  mandatory
                  DESCRIPTION
                          "The type of CRC used on the serial link
                          between two bridges.
                             Setting this object does not take effect
                          until the next reset of the bridge.  When
                          read, the object retruns the last value
                          written to it (which is not necessarily the
                          value of the CRC type being used)."
                  ::= { remoteEthernetBridge 4 }

          linkEncoding OBJECT-TYPE
                  SYNTAX  INTEGER {
                              nrz(1),
                              nrzi(2)
                          }
                  ACCESS  read-write
                  STATUS  mandatory
                  DESCRIPTION
                          "The encoding scheme used on the serial link
                          between two bridges.
                             Setting this object does not take effect
                          until the next reset of the bridge.  When
                          read, the object retruns the last value
                          written to it (which is not necessarily the
                          value of the link encoding being used)."
                  ::= { remoteEthernetBridge 5 }


          --  Token Bus Bridge Objects

          tbTransmitLevel OBJECT-TYPE
                  SYNTAX  INTEGER (0..15)
                  ACCESS  read-write
                  STATUS  mandatory
                  DESCRIPTION
                          "The transmit level used on the bridge's token
                          bus interface.  There are sixteen valid transmit
                          levels which occur at 1.5 dBmV intervals in the
                          range 30.5 dBmV through 53.0 dBmV.  The value of
                          this object is the number of 1.5 dBmV intervals
                          greater than 30.5 dBmV.  Use of the new transmit
                          level after a write, occurs after the next reset."
                  ::= {  tokenBusBridge 2 }

          tbSlotTime OBJECT-TYPE
                  SYNTAX  INTEGER (1..8191)
                  ACCESS  read-write
                  STATUS  mandatory
                  DESCRIPTION
                          "The slot time for the bridge's token bus
                          interface, in octet-time (i.e. 0.8
                          microsecond) units."
                  ::= {  tokenBusBridge 3 }

          tbHoldtime OBJECT-TYPE
                  SYNTAX  INTEGER (64..65535)
                  ACCESS  read-write
                  STATUS  mandatory
                  DESCRIPTION
                          "The high priority token hold time,
                          in octet-time (i.e. 0.8 microsecond) units."
                  ::= {  tokenBusBridge 4 }

          tbRotationTime OBJECT-TYPE
                  SYNTAX  INTEGER  (64..2097151)
                  ACCESS  read-write
                  STATUS  mandatory
                  DESCRIPTION
                          "The maximum ring maintenance rotation time,
                          in octet-time (i.e. 0.8 microsecond) units."
                  ::= {  tokenBusBridge 5 }

          tbRingTimerInitialValue OBJECT-TYPE
                  SYNTAX  INTEGER  (64..2097151)
                  ACCESS  read-only
                  STATUS  mandatory
                  DESCRIPTION
                          "The initial value to be assigned to the ring
                          maintenance timer, in octet-time
                          (i.e. 0.8 microsecond) units."
                  ::= {  tokenBusBridge 6 }

          tbSolicitCount OBJECT-TYPE
                  SYNTAX  INTEGER  (16..255)
                  ACCESS  read-write
                  STATUS  mandatory
                  DESCRIPTION
                          "The maximum inter-solicit interval, in units
                          of token possessions (i.e. token rotations)."
                  ::= {  tokenBusBridge 7 }

          tbResetDefault OBJECT-TYPE
                  SYNTAX  INTEGER {
                              resetParms(1)
                          }
                  ACCESS  write-only
                  STATUS  mandatory
                  DESCRIPTION
                          "Writing a value of resetParms(1) to this
                          object causes the token bus interface
                          parameters to be reset to their default
                          values."
                  ::= {  tokenBusBridge 8 }

          tbFrequency OBJECT-TYPE
                  SYNTAX  INTEGER {
                             range1(1),    -- Rx: 252-264 Mhz;
                                           -- Tx: 59.75-71.75 Mhz
                             range2(2),    -- Rx: 258-270 Mhz;
                                           -- Tx: 65.75-77.75 Mhz
                             range3(3),    -- Rx: 264-276 Mhz;
                                           -- Tx: 71.75-83.75 Mhz
                             range4(4),    -- Rx: 270-282 Mhz;
                                           -- Tx: 77.75-89.75 Mhz
                             range5(5)     -- Rx: 276-288 Mhz;
                                           -- Tx: 83.75-95.75 Mhz
                          }
                  ACCESS  read-write
                  STATUS  mandatory
                  DESCRIPTION
                          "The frequency ranges used by the interface.
                          Use of the new frequency after a write,
                          occurs after the next reset."
                  ::= {  tokenBusBridge 9 }

          ramAddrTab8200Tab  OBJECT-TYPE
                  SYNTAX  RamAddrTab8200Tab
                  ACCESS  not-accessible
                  STATUS  mandatory
                  DESCRIPTION
                          "The RAM-resident Address Table in an
                          HLS Backbone Bridge."
                  INDEX   { ramAddrTab8200Address }
                  ::= {  tokenBusBridge 10 }

          RamAddrTab8200Tab ::=
              SEQUENCE {
                  ramAddrTab8200Entry
                      OCTET STRING,
                  ramAddrTab8200Address
                      MacAddress
              }

          ramAddrTab8200Entry OBJECT-TYPE
                  SYNTAX  OCTET STRING  (SIZE (10))
                  ACCESS  read-write
                  STATUS  mandatory
                  DESCRIPTION
                          "An instance of this object-type exists for
                          each entry in the RAM-resident Address Table
                          in a HLS Backbone Bridge.  The format of the
                          OCTET STRING is:

                     1st octet:   1 = a Static entry
                                  0 = not a Static entry
                     2nd octet:   1 = a Restrict entry
                                  0 = not a Restrict entry
                     3rd octet:   1 = an Origin entry
                                  0 = not an Origin entry
                     4th octet:   0 = Bridge's own address
                                  1 = Address on Channel 0
                                  2 = Address on Channel 1
                                  3 = Address is global (i.e. on all
                                                             Channels)
                     octets 5-10: the MAC address of the 8200 bridge to
                                  which packets for the entry's MAC
                                  address should be forwarded.

                          Setting an instance of this object-type to a
                          value of ASN.1 type NULL, causes the identified
                          entry in the RAM-resident Address Table to be
                          deleted."
                  ::= {  ramAddrTab8200Tab 1 }

          ramAddrTab8200Address OBJECT-TYPE
                  SYNTAX  MacAddress
                  ACCESS  not-accessible
                  STATUS  mandatory
                  DESCRIPTION
                          "The MAC address associated with this entry"
                  ::= {  ramAddrTab8200Tab 2 }

          ramAddrTab8200Filter OBJECT-TYPE
                  SYNTAX  OCTET STRING  (SIZE (10))
                  ACCESS  read-write
                  STATUS  mandatory
                  DESCRIPTION
                          "Setting this value causes the re-creation of the
                          filtered subset (see the object
                          ramAddrTab8200FilterEntry) of the RAM-resident
                          Address Table in a HLS Backbone Bridge.  The
                          filtered subset consists of all entries which
                          matched the filter value at the time of the
                          last write to this object.  The format of the
                          OCTET STRING is:

                  1st octet:   0 - must not be a Static entry
                               1 - must be a Static entry
                               2 - don't care whether Static entry or not
                  2nd octet:   0 - must not be a Restrict entry
                               1 - must be a Restrict entry
                               2 - don't care whether Restrict entry or not
                  3rd octet:   0 - must not be an Origin entry
                               1 - must be an Origin entry
                               2 - don't care whether Origin entry or not
                  4th octet:   1 - Address must be on channel 0 (only)
                               2 - Address must be on channel 1 (only)
                               3 - Address must be global (channels 0 AND 1)
                               4 - Address must not be only on channel 0
                               5 - Address must not be only on channel 1
                               6 - Address must not be global
                               7 - Address can be on any channels
                  octets 5-10: If these octets contain all-ones, then
                               theymatch any entry; otherwise, an entry
                               matchesonly if the value of these 6 octets
                               equalsthe MAC address of the 8200 bridge
                               to which packets for the entry's MAC
                               address should be forwarded."
                  ::= {  tokenBusBridge 11 }

          ramAddrTab8200FilterNum OBJECT-TYPE
                  SYNTAX  INTEGER
                  ACCESS  read-only
                  STATUS  mandatory
                  DESCRIPTION
                          "The current number of entries in the filtered
                          subset of entries in the RAM-resident Address
                          Table in a HLS Backbone Bridge.  The filtered
                          subset consists of all entries which matched
                          the filter value at the time of the last write
                          to the object: ramAddrTab8200Filter."
                  ::= {  tokenBusBridge 12 }


          ramAddrTab8200FilterTab  OBJECT-TYPE
                  SYNTAX  RamAddrTab8200FilterTab
                  ACCESS  not-accessible
                  STATUS  mandatory
                  DESCRIPTION
                          "This table contains the filtered subset of the
                          RAM-resident Address Table in a HLS Backbone
                          Bridge.  The filtered subset consists of all
                          entries which matched the filter value at the
                          time of the last write to the object:
                          ramAddrTab8200Filter.  Note that the contents
                          of this table are constant between writes to
                          ramAddrTab8200Filter."
                  INDEX   { ramAddrTab8200FilterIndex }
                  ::= {  tokenBusBridge 13 }

          RamAddrTab8200FilterTab ::=
              SEQUENCE {
                  ramAddrTab8200FilterEntry
                      OCTET STRING,
                  ramAddrTab8200FilterIndex
                      INTEGER
              }

          ramAddrTab8200FilterEntry OBJECT-TYPE
                  SYNTAX  OCTET STRING (SIZE (16))
                  ACCESS  read-only
                  STATUS  mandatory
                  DESCRIPTION
                          "An instance of this object-type exists for
                          each entry in the filtered subset of entries
                          in the RAM-resident Address Table in a HLS
                          Backbone Bridge.  The filtered subset consists
                          of a copy of those entries in ramAddrTab8200Tab
                          which matched the filter value at the time of
                          the last write to the object:
                          ramAddrTab8200Filter.  The format of the OCTET
                          STRING is:
                     octets 1-6:   the MAC address of this entry
                     7th octet:    1 = a Static entry
                                   0 = not a Static entry
                     8th octet:    1 = a Restrict entry
                                   0 = not a Restrict entry
                     9th octet:    1 = an Origin entry
                                   0 = not an Origin entry
                     10th octet:   0 = Bridge's own address
                                   1 = Address on Channel 0
                                   2 = Address on Channel 1
                                   3 = Address is global (i.e. on all
                                                               Channels)
                     octets 11-16: the MAC address of the 8200 bridge
                                   to which packets for the entry's MAC
                                   address should be forwarded."
                  ::= {  ramAddrTab8200FilterTab 1 }

          ramAddrTab8200FilterIndex OBJECT-TYPE
                  SYNTAX  INTEGER
                  ACCESS  not-accessible
                  STATUS  mandatory
                  DESCRIPTION
                          "For the i-th entry, this object has
                          the value i."
                  ::= { ramAddrTab8200FilterTab 2 }

          ramAddrTab8200Delete OBJECT-TYPE
                  SYNTAX  OCTET STRING  (SIZE (10))
                  ACCESS  write-only
                  STATUS  mandatory
                  DESCRIPTION
                          "Setting this object to a value causes the
                          immediate deletion of a subset of the entries
                          in the RAM-resident Address Table in a HLS
                          Backbone Bridge.  The subset of entries to be
                          deleted is selected by using the value (to which
                          this object is set) as a filter against which
                          all entries are matched, with all entries
                          matching the filter being deleted.  The format
                          of the OCTET STRING is:

                   1st octet:   0 - must not be a Static entry
                                1 - must be a Static entry
                                2 - don't care whether Static entry or not
                   2nd octet:   0 - must not be a Restrict entry
                                1 - must be a Restrict entry
                                2 - don't care whether Restrict entry or not
                   3rd octet:   0 - must not be an Origin entry
                                1 - must be an Origin entry
                                2 - don't care whether Origin entry or not
                   4th octet:   1 - Address must be on channel 0 (only)
                                2 - Address must be on channel 1 (only)
                                3 - Address must be global (channels 0 AND 1)
                                4 - Address must not be only on channel 0
                                5 - Address must not be only on channel 1
                                6 - Address must not be global
                                7 - Address can be on any channels
                   octets 5-10: If these octets contain all-ones, then they
                                match any entry; otherwise, an entry matches
                                only if the value of these 6 octets equals
                                the MAC address of the 8200 bridge to which
                                packets for the entry's MAC address should
                                be forwarded."
                  ::= {  tokenBusBridge 14 }

          nvramAddrTab8200Tab  OBJECT-TYPE
                  SYNTAX  NvramAddrTab8200Tab
                  ACCESS  not-accessible
                  STATUS  mandatory
                  DESCRIPTION
                          "The Address Table in Non-Volatile RAM in a
                          HLS Backbone Bridge."
                  INDEX   { nvramAddrTab8200Address }
                  ::= {  tokenBusBridge 15 }

          NvramAddrTab8200Tab ::=
              SEQUENCE {
                  nvramAddrTab8200Entry
                      OCTET STRING,
                  nvramAddrTab8200Address
                      MacAddress
              }

          nvramAddrTab8200Entry OBJECT-TYPE
                  SYNTAX  OCTET STRING  (SIZE (10))
                  ACCESS  read-write
                  STATUS  mandatory
                  DESCRIPTION
                          "An instance of this object-type exists for each
                          entry in the Address Table in Non-Volatile RAM
                          in a HLS Backbone Bridge.  The format of the
                          OCTET STRING is:

                     1st octet:   1 = a Static entry
                                  0 = not a Static entry
                     2nd octet:   1 = a Restrict entry
                                  0 = not a Restrict entry
                     3rd octet:   1 = an Origin entry
                                  0 = not an Origin entry
                     4th octet:   0 = Bridge's own address
                                  1 = Address on Channel 0
                                  2 = Address on Channel 1
                                  3 = Address is global (i.e. on all
                                                              Channels)
                     octets 5-10: the MAC address of the 8200 bridge
                                  to which packets for the entry's MAC
                                  address should be forwarded.

                           Setting an instance of this object-type to a
                           value of ASN.1 type NULL, causes the
                           identified entry in the Address Table in
                           Non-Volatile RAM to be deleted."
                  ::= {  nvramAddrTab8200Tab 1 }

          nvramAddrTab8200Address OBJECT-TYPE
                  SYNTAX  MacAddress
                  ACCESS  not-accessible
                  STATUS  mandatory
                  DESCRIPTION
                          "The MAC address associated with this entry"
                  ::= { nvramAddrTab8200Tab 2 }

          nvramAddrTab8200Filter OBJECT-TYPE
                  SYNTAX  OCTET STRING  (SIZE (10))
                  ACCESS  read-write
                  STATUS  mandatory
                  DESCRIPTION
                          "Setting this value causes the re-creation of
                          the filtered subset (see the object
                          nvramAddrTab8200FilterEntry) of the Address
                          Table in Non-Volatile RAM in a HLS Backbone
                          Bridge.  The filtered subset consists of all
                          entries which matched the filter value at the
                          time of the last write to this object.  The
                          format of the OCTET STRING is:

                   1st octet:   0 - must not be a Static entry
                                1 - must be a Static entry
                                2 - don't care whether Static entry or not
                   2nd octet:   0 - must not be a Restrict entry
                                1 - must be a Restrict entry
                                2 - don't care whether Restrict entry or not
                   3rd octet:   0 - must not be an Origin entry
                                1 - must be an Origin entry
                                2 - don't care whether Origin entry or not
                   4th octet:   1 - Address must be on channel 0 (only)
                                2 - Address must be on channel 1 (only)
                                3 - Address must be global (channels 0 AND 1)
                                4 - Address must not be only on channel 0
                                5 - Address must not be only on channel 1
                                6 - Address must not be global
                                7 - Address can be on any channels
                   octets 5-10: If these octets contain all-ones, then they
                                match any entry; otherwise, an entry matches
                                only if the value of these 6 octets equals
                                the MAC address of the 8200 bridge to which
                                packets for the entry's MAC address should
                                be forwarded."
                  ::= {  tokenBusBridge 16 }

          nvramAddrTab8200FilterNum OBJECT-TYPE
                  SYNTAX  INTEGER
                  ACCESS  read-only
                  STATUS  mandatory
                  DESCRIPTION
                          "The current number of entries in the filtered
                          subset of entries in the Address Table in
                          Non-Volatile RAM in a HLS Backbone Bridge.
                          The filtered subset consists of all entries
                          which matched the filter value at the time of
                          the last write to the object:
                          nvramAddrTab8200Filter."
                  ::= {  tokenBusBridge 17 }

          nvramAddrTab8200FilterTab  OBJECT-TYPE
                  SYNTAX  NvramAddrTab8200FilterTab
                  ACCESS  not-accessible
                  STATUS  mandatory
                  DESCRIPTION
                          "This table contains the filtered subset of
                          entries in the Address Table in Non-Volatile
                          RAM in a HLS Backbone Bridge.  The filtered
                          subset consists of all entries which matched
                          the filter value at the time it was last
                          written to the object: nvramAddrTab8200Filter.
                          Note that the contents of this table are
                          constant between writes to
                          nvramAddrTab8200Filter."
                  INDEX   { nvramAddrTab8200FilterIndex }
                  ::= { tokenBusBridge 18 }

          NvramAddrTab8200FilterTab ::=
              SEQUENCE {
                  nvramAddrTab8200FilterEntry
                      OCTET STRING,
                  nvramAddrTab8200FilterIndex
                      INTEGER
              }

          nvramAddrTab8200FilterEntry OBJECT-TYPE
                  SYNTAX  OCTET STRING (SIZE (16))
                  ACCESS  read-only
                  STATUS  mandatory
                  DESCRIPTION
                          "An instance of this object-type exists for
                          each entry within the filtered subset of the
                          Address Table in Non-Volatile RAM in a HLS
                          Backbone Bridge.  The filtered subset consists
                          of all entries which matched the filter value
                          at the time of the last write to the object:
                          nvramAddrTab8200Filter.  The format of the
                          OCTET STRING is:

                     octets 1-6:   the MAC address of this entry
                     7th octet:    1 = a Static entry
                                   0 = not a Static entry
                     8th octet:    1 = a Restrict entry
                                   0 = not a Restrict entry
                     9th octet:    1 = an Origin entry
                                   0 = not an Origin entry
                     10th octet:   0 = Bridge's own address
                                   1 = Address on Channel 0
                                   2 = Address on Channel 1
                                   3 = Address is global (i.e. on all
                                                               Channels)
                     octets 11-16: the MAC address of the 8200 bridge
                                   to which packets for the entry's MAC
                                   address should be forwarded."
                  ::= {  nvramAddrTab8200FilterTab 1 }

          nvramAddrTab8200FilterIndex OBJECT-TYPE
                  SYNTAX  INTEGER
                  ACCESS  not-accessible
                  STATUS  mandatory
                  DESCRIPTION
                          "For the i-th entry, this object has
                          the value i."
                  ::= { nvramAddrTab8200FilterTab 2 }

          nvramAddrTab8200Delete OBJECT-TYPE
                  SYNTAX  OCTET STRING  (SIZE (10))
                  ACCESS  write-only
                  STATUS  mandatory
                  DESCRIPTION
                          "Setting this object to a value causes the
                          immediate deletion of a subset of the entries
                          in the Address Table in Non-Volatile RAM in a
                          HLS 8200 Bridge.  The subset of entries to be
                          deleted is selected by using the value (to
                          which this object is set) as a filter against
                          which all entries are matched, with all entries
                          matching the filter being deleted.  The format
                          of the OCTET STRING is:

                   1st octet:   0 - must not be a Static entry
                                1 - must be a Static entry
                                2 - don't care whether Static entry or not
                   2nd octet:   0 - must not be a Restrict entry
                                1 - must be a Restrict entry
                                2 - don't care whether Restrict entry or not
                   3rd octet:   0 - must not be an Origin entry
                                1 - must be an Origin entry
                                2 - don't care whether Origin entry or not
                   4th octet:   1 - Address must be on channel 0 (only)
                                2 - Address must be on channel 1 (only)
                                3 - Address must be global (channels 0 AND 1)
                                4 - Address must not be only on channel 0
                                5 - Address must not be only on channel 1
                                6 - Address must not be global
                                7 - Address can be on any channels
                   octets 5-10: If these octets contain all-ones, then they
                                match any entry; otherwise, an entry matches
                                only if the value of these 6 octets equals
                                the MAC address of the 8200 bridge to which
                                packets for the entry's MAC address should
                                be forwarded."
                   ::= {  tokenBusBridge 19 }

          nvramAddrTab8200Update OBJECT-TYPE
                  SYNTAX  OCTET STRING  (SIZE (10))
                  ACCESS  write-only
                  STATUS  mandatory
                  DESCRIPTION
                          "Setting this object to a value causes an
                          update of the Address Table in Non-Volatile
                          RAM in a HLS Backbone Bridge.  This update is
                          the combination of the deletion of all
                          existing entries in Non-Volatile RAM table,
                          followed by the addition of a set of new
                          entries.  The set of new entries is a subset
                          of the current entries in the bridge's
                          RAM-resident Address Table.  That subset is
                          selected by using the value (to which this
                          object is set) as a filter against which all
                          entries in the RAM-resident Address Table are
                          matched.  After the update is completed, the
                          Address Table in Non-Volatile RAM consists of
                          exactly those entries in the RAM-resident
                          Address Table which match with the filter
                          value.  The format of the OCTET STRING is:

                   1st octet:   0 - must not be a Static entry
                                1 - must be a Static entry
                                2 - don't care whether Static entry or not
                   2nd octet:   0 - must not be a Restrict entry
                                1 - must be a Restrict entry
                                2 - don't care whether Restrict entry or not
                   3rd octet:   0 - must not be an Origin entry
                                1 - must be an Origin entry
                                2 - don't care whether Origin entry or not
                   4th octet:   1 - Address must be on channel 0 (only)
                                2 - Address must be on channel 1 (only)
                                3 - Address must be global (channels 0 AND 1)
                                4 - Address must not be only on channel 0
                                5 - Address must not be only on channel 1
                                6 - Address must not be global
                                7 - Address can be on any channels
                   octets 5-10: If these octets contain all-ones, then
                                they match any entry; otherwise, an entry
                                matches only if the value of these 6 octets
                                equalsthe MAC address of the 8200 bridge
                                to which packets for the entry's MAC
                                address should be forwarded."
                   ::= {  tokenBusBridge 20 }

          tbEbitErrors OBJECT-TYPE
                  SYNTAX  Counter
                  ACCESS  read-only
                  STATUS  mandatory
                  DESCRIPTION
                          "The number of 802.4 frames received which
                          had the Error-bit set in the trailer."
                  ::= { tokenBusBridge 21 }

          tbFrameFrags OBJECT-TYPE
                  SYNTAX  Counter
                  ACCESS  read-only
                  STATUS  mandatory
                  DESCRIPTION
                          "The number of 802.4 frames received which
                          did not have a valid End delimiter."
                  ::= {  tokenBusBridge 22 }

          tbTokenPassFails OBJECT-TYPE
                  SYNTAX  Counter
                  ACCESS  read-only
                  STATUS  mandatory
                  DESCRIPTION
                          "The number of times this station
                          re-transmitted the token to its neighbor
                          because the neighbor failed to transmit
                          within the required time interval."
                  ::= { tokenBusBridge 23 }



          --    Token Ring objects

          trBridgeNumber OBJECT-TYPE
                  SYNTAX  INTEGER (1..15)
                  ACCESS  read-write
                  STATUS  mandatory
                  DESCRIPTION
                          "The number of this bridge as used in the
                          802.5 source routing scheme."
                  ::= {  tokenRingBridge 1 }

          trChannelTable OBJECT-TYPE
                  SYNTAX  SEQUENCE OF TrChannelEntry
                  ACCESS  not-accessible
                  STATUS  mandatory
                  DESCRIPTION
                          "The table which contains an entry per
                          Token-Ring channel on this bridge.  Note that
                          entries exist for 'virtual token-ring' channels
                          as well as real token-ring channels."
                  ::= { tokenRingBridge 2 }

          trChannelEntry OBJECT-TYPE
                  SYNTAX  TrChannelEntry
                  ACCESS  not-accessible
                  STATUS  mandatory
                  DESCRIPTION
                          "The set of attributes applicable to each of
                          the bridge's Token-Ring channels."
                  INDEX   { channelNumber }
                  ::= { trChannelTable 1 }

          TrChannelEntry ::= SEQUENCE {
                                 trRingNumber
                                     INTEGER,
                                 trSRAstate
                                     INTEGER
                             }

          trRingNumber OBJECT-TYPE
                  SYNTAX  INTEGER (1..4095)
                  ACCESS  read-write
                  STATUS  mandatory
                  DESCRIPTION
                          "The ring number of this channel as used in
                          the 802.5 source routing"
                  ::= { trChannelEntry 1 }

          trSRAstate OBJECT-TYPE
                  SYNTAX  INTEGER {
                              enabled(1),
                              disabled(2)
                          }
                  ACCESS  read-write
                  STATUS  mandatory
                  DESCRIPTION
                          "This object affects the Source Routing
                          Accelerator (SRA) chip of the TMS-380 chip
                          set interfacing to this channel.  When this
                          object has the value of enabled(1), the SRA
                          chip is used in performing the 802.5 source
                          routing; with the value disabled(2), the SRA
                          chip is not used."
                  ::= {  trChannelEntry 2 }



          -- the hlsDot1dBase group

          -- [Note this set of objects are a subset of an early
          --  version of the Bridge-MIB being worked on by the IETF's
          --  Bridge-MIB working group.  As a result, there is some
          --  correspondence to managementinformation defined by 802.1d].

          hlsDot1dBaseBridgeAddress OBJECT-TYPE
              SYNTAX  MacAddress
              ACCESS  read-only
              STATUS  mandatory
              DESCRIPTION
                      "The MAC address used by this bridge when it must
                      be referred to in a unique fashion.   It is
                      recommended that this be the numerically smallest
                      MAC address of all ports that belong to this
                      bridge.  However it is only required to be unique.
                      When concatenated with hlsDot1dStpPriority a unique
                      BridgeIdentifier is formed which is used in the
                      Spanning Tree Protocol."
              REFERENCE
                      "P802.1d/D9, July 14, 1989: Sections 6.4.1.1.3
                      and 3.12.5"
              ::= { hlsDot1dBase 1 }

          hlsDot1dBaseNumPorts OBJECT-TYPE
              SYNTAX  INTEGER
              ACCESS  read-only
              STATUS  mandatory
              DESCRIPTION
                      "The number of ports controlled by this bridging
                      entity. The value can also be determined by
                      examining the number of entries in the port-
                      specific table in the appropriate group.  Thus,
                      this object is a candidate for removal."
              REFERENCE
                      "P802.1d/D9, July 14, 1989: Section 6.4.1.1.3"
              ::= { hlsDot1dBase 2 }

          hlsDot1dBaseBridgeUpTime OBJECT-TYPE
              SYNTAX  TimeTicks
              ACCESS  read-only
              STATUS  mandatory
              DESCRIPTION
                      "The time (in hundredths of a second) since the
                      bridging entity was last reset or initialized."
              REFERENCE
                      "P802.1d/D9, July 14, 1989: Section 6.4.1.1.3"
              ::= { hlsDot1dBase 3 }

          hlsDot1dBaseType OBJECT-TYPE
              SYNTAX  INTEGER {
                          unknown(1),
                          transparent-only(2),
                          sourceroute-only(3),
                          srt(4)
                      }
              ACCESS  read-only
              STATUS  mandatory
              DESCRIPTION
                      "Indicates what type of bridging this bridge can
                      perform.  If a bridge is actually performing a
                      certain type of bridging this will be indicated
                      by entries in the port table for the given type."
              ::= { hlsDot1dBase 4 }


          hlsDot1dBasePortTable OBJECT-TYPE
              SYNTAX  SEQUENCE OF Dot1dBasePortEntry
              ACCESS  not-accessible
              STATUS  mandatory
              DESCRIPTION
                      "A table that contains generic information about
                      every port that is associated with this bridge.
                      Transparent, source-route, and srt ports are
                      included."
              ::= { hlsDot1dBase 5 }

          hlsDot1dBasePortEntry OBJECT-TYPE
              SYNTAX  Dot1dBasePortEntry
              ACCESS  not-accessible
              STATUS  mandatory
              DESCRIPTION
                      "A list of information for each port of the
                      bridge."
              REFERENCE
                      "P802.1d/D9, July 14, 1989: Section 6.4.2, 6.6.1"
              INDEX  { hlsDot1dBasePortIfIndex }
              ::= { hlsDot1dBasePortTable 1 }


          Dot1dBasePortEntry ::= SEQUENCE {
                  hlsDot1dBasePortIfIndex
                      INTEGER,
                  hlsDot1dBasePortNoBufferDiscards
                      Counter,
                  hlsDot1dBasePortDelayExceededDiscards
                      Counter,
                  hlsDot1dBasePortMtuExceededDiscards
                      Counter
              }

          hlsDot1dBasePortIfIndex OBJECT-TYPE
              SYNTAX  INTEGER
              ACCESS  read-only
              STATUS  mandatory
              DESCRIPTION
                      "Identifies the port for which this entry contains
                      bridge management information.  The value of this
                      object for a particular port has the same value as
                      the ifIndex object, defined in [4,6], for the
                      corresponding interface."
              ::= { hlsDot1dBasePortEntry 1 }

          hlsDot1dBasePortNoBufferDiscards OBJECT-TYPE
              SYNTAX  Counter
              ACCESS  read-only
              STATUS  mandatory
              DESCRIPTION
                      "The number of frames discarded by this port due
                      to insufficient internal buffering.  It is
                      incremented by both transparent and source route
                      bridges."
              REFERENCE
                      "P802.1d/D9, July 14, 1989: Section 6.6.1.1.3"
              ::= { hlsDot1dBasePortEntry 2 }

          hlsDot1dBasePortDelayExceededDiscards OBJECT-TYPE
              SYNTAX  Counter
              ACCESS  read-only
              STATUS  mandatory
              DESCRIPTION
                      "The number of frames discarded by this port due
                      to excessive transit delay through the bridge.
                      It is incremented by both transparent and source
                      route bridges."
              REFERENCE
                       "P802.1d/D9, July 14, 1989: Section 6.6.1.1.3"
              ::= { hlsDot1dBasePortEntry 3 }


          hlsDot1dBasePortMtuExceededDiscards OBJECT-TYPE
              SYNTAX  Counter
              ACCESS  read-only
              STATUS  mandatory
              DESCRIPTION
                      "The number of frames discarded by this port due
                      to an excessive size.  It is incremented by both
                      transparent and source route bridges."
              REFERENCE
                      "P802.1d/D9, July 14, 1989: Section 6.6.1.1.3"
              ::= { hlsDot1dBasePortEntry 4 }



          -- the hlsDot1dStp group

          -- Implementation of the hlsDot1dStp group is optional.  It is
          -- implemented by those bridges that support the Spanning Tree
          -- Protocol.  


          hlsDot1dStpProtocolSpecification OBJECT-TYPE
              SYNTAX  INTEGER {
                          unknown(1),
                          decprotocol(2),
                          ieee8021d(3)
                      }
              ACCESS  read-only
              STATUS  mandatory
              DESCRIPTION
                      "An indication of what version of the Spanning
                      Tree Protocol is being run.  Early DEC Spanning
                      Tree implementations will return 'decprotocol(2)'.
                      IEEE 802.1d implementations will return
                      'ieee8021d(3)'.  If future versions of the IEEE
                      Spanning Tree Protocol are released that are
                      incompatible with the current version a new value
                      will be defined."
              ::= { hlsDot1dStp 1 }


          hlsDot1dStpPriority OBJECT-TYPE
              SYNTAX  INTEGER (0..65535)
              ACCESS  read-write
              STATUS  mandatory
              DESCRIPTION
                      "In a Spanning Tree Protocol PDU, this bridge is
                      identified by an 8 octet string composed of
                      hlsDot1dStpPriority concatenated with
                      hlsDot1dBaseId.  One of the uses of this 8 octet
                      string is to determine the root of the spanning
                      tree."
              REFERENCE
                      "P802.1d/D9, July 14, 1989: Section 4.5.3.7"
              ::= { hlsDot1dStp 2 }

          hlsDot1dStpLastTopChange OBJECT-TYPE
              SYNTAX  TimeTicks
              ACCESS  read-only
              STATUS  mandatory
              DESCRIPTION
                      "The value of sysUptIme on the occurrence of
                      last time a topology change was detected by the
                      bridge entity."
              REFERENCE
                      "P802.1d/D9, July 14, 1989: Section 6.8.1.1.3"
              ::= { hlsDot1dStp 3 }


          hlsDot1dStpTopChanges OBJECT-TYPE
              SYNTAX  Counter
              ACCESS  read-only
              STATUS  mandatory
              DESCRIPTION
                      "The total number of topology changes detected by
                      this bridge since the management entity was last
                      reset or initialized."
              REFERENCE
                      "P802.1d/D9, July 14, 1989: Section 6.8.1.1.3"
              ::= { hlsDot1dStp 4 }


          hlsDot1dStpDesignatedRoot OBJECT-TYPE
              SYNTAX  OCTET STRING (SIZE (8))
              ACCESS  read-only
              STATUS  mandatory
              DESCRIPTION
                      "The bridge identifier of the root of the spanning
                      tree as determined by the Spanning Tree Protocol
                      as executed by this node.  This value is used as
                      the Root Identifier parameter in all Configuration
                      Bridge PDUs originated by this node."
              REFERENCE
                      "P802.1d/D9, July 14, 1989: Section 4.5.3.1"
              ::= { hlsDot1dStp 5 }

          hlsDot1dStpRootCost OBJECT-TYPE
              SYNTAX  INTEGER
              ACCESS  read-only
              STATUS  mandatory
              DESCRIPTION
                      "The cost of the path to the root as seen from
                      this bridge."
              REFERENCE
                      "P802.1d/D9, July 14, 1989: Section 4.5.3.2"
              ::= { hlsDot1dStp 6 }

          hlsDot1dStpRootPort OBJECT-TYPE
              SYNTAX  INTEGER
              ACCESS  read-only
              STATUS  mandatory
              DESCRIPTION
                      "Identifies the port which offers the lowest cost
                      path from this bridge to the root bridge.  The
                      value of this object indicates the port for which
                      the ifIndex object, defined in [4,6], of the
                      corresponding interface has the same value."
              REFERENCE
                      "P802.1d/D9, July 14, 1989: Section 4.5.3.2"
              ::= { hlsDot1dStp 7 }

          hlsDot1dStpMaxAge OBJECT-TYPE
              SYNTAX  TimeTicks
              ACCESS  read-only
              STATUS  mandatory
              DESCRIPTION
                      "The maximum age of Spanning Tree Protocol
                      information learned from the network on any port
                      before it is discarded, in units of hundredths of
                      a second.  This is the actual value that this
                      bridge is currently using."
              REFERENCE
                      "P802.1d/D9, July 14, 1989: Section 4.5.3.4"
              ::= { hlsDot1dStp 8 }

          hlsDot1dStpHelloTime OBJECT-TYPE
              SYNTAX  TimeTicks
              ACCESS  read-only
              STATUS  mandatory
              DESCRIPTION
                      "The amount of time between the transmission of
                      Configuration bridge PDUs by this node on any port
                      when it is the root of the spanning tree or trying
                      to become so, in units of hundredths of a second.
                      This is the actual value that this bridge is
                      currently using."
              REFERENCE
                      "P802.1d/D9, July 14, 1989: Section 4.5.3.5"
              ::= { hlsDot1dStp 9 }

          hlsDot1dStpForwardDelay OBJECT-TYPE
              SYNTAX TimeTicks
              ACCESS  read-only
              STATUS  mandatory
              DESCRIPTION
                      "This time value is measured in units of
                      hundredths of a second.  It is used for two
                      purposes.  Firstly, it controls how fast a port
                      changes its spanning state when moving towards the
                      Forwarding state.  In this case, the value
                      determines how long the port stays in a particular
                      state before moving to the next state.  For
                      example, how long a port stays in the Listening
                      state when moving from Blocking to Learning.
                      Secondly, when a topology change has been detected
                      and is underway, this time value is used to age
                      all dynamic entries in the Forwarding Database.
                      This is the actual value that this bridge is
                      currently using."
              REFERENCE
                      "P802.1d/D9, July 14, 1989: Section 4.5.3.6"
              ::= { hlsDot1dStp 10 }

          hlsDot1dStpHoldTime OBJECT-TYPE
              SYNTAX  TimeTicks
              ACCESS  read-only
              STATUS  mandatory
              DESCRIPTION
                      "This time value determines the interval length
                      during which no more than two Configuration bridge
                      PDUs shall be transmitted by this node, in units
                      of hundredths of a second."
              REFERENCE
                      "P802.1d/D9, July 14, 1989: Section 4.5.3.14"
              ::= { hlsDot1dStp 11 }

          hlsDot1dStpPortTable OBJECT-TYPE
              SYNTAX  SEQUENCE OF Dot1dStpPortEntry
              ACCESS  not-accessible
              STATUS  mandatory
              DESCRIPTION
                      "A table that contains port-specific information
                      for the Spanning Tree Protocol."
              ::= { hlsDot1dStp 12 }

          hlsDot1dStpPortEntry OBJECT-TYPE
              SYNTAX  Dot1dStpPortEntry
              ACCESS  not-accessible
              STATUS  mandatory
              DESCRIPTION
                      "A list of information maintained by every port
                      about the Spanning Tree Protocol state for that
                      port."
              INDEX   { hlsDot1dStpPortIfIndex }
              ::= { hlsDot1dStpPortTable 1 }

          Dot1dStpPortEntry ::= SEQUENCE {
                  hlsDot1dStpPortIfIndex
                      INTEGER,
                  hlsDot1dStpPortPriority
                      OCTET STRING,
                  hlsDot1dStpPortPortNum
                      INTEGER,
                  hlsDot1dStpPortState
                      INTEGER,
                  hlsDot1dStpPortMultiCastAddr
                      MacAddress,
                  hlsDot1dStpPortPathCost
                      INTEGER,
                  hlsDot1dStpPortDesignatedRoot
                      OCTET STRING,
                  hlsDot1dStpPortDesignatedCost
                      INTEGER,
                  hlsDot1dStpPortDesignatedBridge
                      OCTET STRING,
                  hlsDot1dStpPortDesignatedPort
                      OCTET STRING,
                  hlsDot1dStpPortInBPDUs
                      Counter,
                  hlsDot1dStpPortOutBPDUs
                      Counter
              }

          hlsDot1dStpPortIfIndex OBJECT-TYPE
              SYNTAX  INTEGER
              ACCESS  read-only
              STATUS  mandatory
              DESCRIPTION
                      "Identifies the port for which this entry contains
                      Spanning Tree Protocol management information.
                      The value of this object for a particular port has
                      the same value as the ifIndex object, defined in
                      [4,6], for the corresponding interface."
              REFERENCE
                      "P802.1d/D9, July 14, 1989: Section 6.8.2.1.2"
              ::= { hlsDot1dStpPortEntry 1 }


          hlsDot1dStpPortPriority OBJECT-TYPE
              SYNTAX  OCTET STRING (SIZE (1))
              ACCESS  read-write
              STATUS  mandatory
              DESCRIPTION
                      "The concatenation of hlsDot1dStpPortPriority and
                      hlsDot1dStpPortNum make up the Port Identifier
                      parameter in all Configuration bridge PDUs output
                      by this port."
              REFERENCE
                      "P802.1d/D9, July 14, 1989: Section 4.5.5.1"
              ::= { hlsDot1dStpPortEntry 2 }

          hlsDot1dStpPortPortNum OBJECT-TYPE
              SYNTAX  INTEGER
              ACCESS  read-only
              STATUS  mandatory
              DESCRIPTION
                      "This object when concatentated with
                      hlsDot1dStpPortPriority make up the Port Identifier
                      included in all bridge PDUs generated by this bridge.
                      The value of this object is always the same as
                      hlsDot1dStpPortIfIndex for the same port."
              REFERENCE
                      "P802.1d/D9, July 14, 1989: Section 4.5.5.1"
              ::= { hlsDot1dStpPortEntry 3 }

          hlsDot1dStpPortState OBJECT-TYPE
              SYNTAX  INTEGER {
                          disabled(1),
                          enabled(2),
                          blocking(3),
                          listening(4),
                          learning(5),
                          forwarding(6)
                      }
              ACCESS  read-only
              STATUS  mandatory
              DESCRIPTION
                      "The port's current state as defined by
                      application of the Spanning Tree Protocol.  This
                      state controls what action a port takes on
                      reception of a frame.  If the bridge has detected
                      a port that is malfunctioning it will place that
                      port into the broken(7) state.  Implementations
                      that permit remote administratinve control of a
                      port may permit writing of the values disabled(1)
                      and enabled(2).  When a port is writen with the
                      value enabled(2) the implementation will take the
                      port to the appropriate state."
              REFERENCE
                      "P802.1d/D9, July 14, 1989: Section 4.5.5.2"
              ::= { hlsDot1dStpPortEntry 4 }


          hlsDot1dStpPortMultiCastAddr OBJECT-TYPE
              SYNTAX  MacAddress
              ACCESS  read-only
              STATUS  mandatory
              DESCRIPTION
                      "The MAC address used as the destination for all
                      Spanning Tree Protocol PDU generated out this
                      port."
              ::= { hlsDot1dStpPortEntry 5 }


          hlsDot1dStpPortPathCost OBJECT-TYPE
              SYNTAX  INTEGER
              ACCESS  read-write
              STATUS  mandatory
              DESCRIPTION
                      "The contribution of this port to the path cost of
                      paths towards the spanning tree root which include
                      this port."
              REFERENCE
                      "P802.1d/D9, July 14, 1989: Section 4.5.5.3"
              ::= { hlsDot1dStpPortEntry 6 }

          hlsDot1dStpPortDesignatedRoot OBJECT-TYPE
              SYNTAX  OCTET STRING (SIZE (8))
              ACCESS  read-only
              STATUS  mandatory
              DESCRIPTION
                      "The value of the Bridge Identifier that should be
                      seen in bridge PDUs received on this port."
              REFERENCE
                      "P802.1d/D9, July 14, 1989: Section 4.5.5.4"
              ::= { hlsDot1dStpPortEntry 7 }


          hlsDot1dStpPortDesignatedCost OBJECT-TYPE
              SYNTAX  INTEGER
              ACCESS  read-only
              STATUS  mandatory
              DESCRIPTION
                      "The path cost of the Designated Port of the
                      segment connected to this port.  This value is
                      compared to the Root Path Cost field in received
                      bridge PDUs."
              REFERENCE
                      "P802.1d/D9, July 14, 1989: Section 4.5.5.5"
              ::= { hlsDot1dStpPortEntry 8 }


          hlsDot1dStpPortDesignatedBridge OBJECT-TYPE
              SYNTAX  OCTET STRING (SIZE (8))
              ACCESS  read-only
              STATUS  mandatory
              DESCRIPTION
                      "The Bridge Identifier of the bridge which this
                      port considers to be the Designated Bridge for
                      this port's segment."
              REFERENCE
                      "P802.1d/D9, July 14, 1989: Section 4.5.5.6"
              ::= { hlsDot1dStpPortEntry 9 }

          hlsDot1dStpPortDesignatedPort OBJECT-TYPE
              SYNTAX  OCTET STRING (SIZE (2))
              ACCESS  read-only
              STATUS  mandatory
              DESCRIPTION
                      "The Port Identifier of the port on the Designated
                      Bridge for this port's segment."
              REFERENCE
                      "P802.1d/D9, July 14, 1989: Section 4.5.5.7"
              ::= { hlsDot1dStpPortEntry 10 }

          hlsDot1dStpPortInBPDUs  OBJECT-TYPE
              SYNTAX  Counter
              ACCESS  read-only
              STATUS  mandatory
              DESCRIPTION
                      "The number of Spanning Tree Protocol BPDUs
                      received on this port."
              ::= { hlsDot1dStpPortEntry 11 }

          hlsDot1dStpPortOutBPDUs OBJECT-TYPE
              SYNTAX  Counter
              ACCESS  read-only
              STATUS  mandatory
              DESCRIPTION
                      "The number of Spanning Tree Protocol BPDUs
                      transmitted on this port."
              ::= { hlsDot1dStpPortEntry 12 }


          --    Protocol Filtering Objects

          protocolFilterTable OBJECT-TYPE
              SYNTAX    SEQUENCE OF ProtocolFilterEntry
              ACCESS    not-accessible
              STATUS    mandatory
              DESCRIPTION
                        "The table which identifies which protocols
                        are being forwarded by the bridge and which
                        are being blocked."
              ::= { hlsBridges 24 }

          protocolFilterEntry OBJECT-TYPE
              SYNTAX    ProtocolFilterEntry
              ACCESS    not-accessible
              STATUS    mandatory
              DESCRIPTION
                        "There is one entry in this table for each
                        protocol specifically forwarded or filtered.
                        The first entry is special in that it specifies
                        the handling of all protocols which do not have
                        their own entry."
              INDEX     { protocolFilterType }
              ::= { protocolFilterTable 1 }

          ProtocolFilterEntry ::= SEQUENCE {
                      protocolFilterStatus
                          INTEGER,
                      protocolFilterType
                          INTEGER
                  }

          protocolFilterStatus OBJECT-TYPE
              SYNTAX    INTEGER {
                            forward(1),
                            block(2),
                            invalid(3)
                        }
              ACCESS    read-write
              STATUS    mandatory
              DESCRIPTION
                        "Identifies whether the protocol referenced by
                        this entry is being forwarded or blocked by the
                        bridge.  Writing a value of invalid(3) to an
                        instance of this object removes the corresponding
                        entry from the table (thereby causing it to be
                        forwarded/blocked according to the 'others' entry).
                           Setting the 'others' entry has the special
                        effect of removing all other entries.  Setting
                        the 'others' entry to invalid(3) is not valid."
              ::= { protocolFilterEntry 1 }

          protocolFilterType OBJECT-TYPE
              SYNTAX    INTEGER  (1..65535)
              ACCESS    read-write
              STATUS    mandatory
              DESCRIPTION
                        "Identifies the protocol to which this entry
                        refers. This object takes the value 1 for the
                        first entry in the table which has the special
                        meaning of 'others' in that all protocols which
                        do not have their own entry, are forwarded or
                        blocked as are 'others'. The following values
                        for this object are also defined:

                                2 - IP
                                3 - ARP
                                4 - RARP
                                5 - DECNET
                                6 - IPX
                                7 - V2
                                8 - XNS
                                9 - TOPS
                               10 - BridgeID (3Com T/Servers)
                               11 - LAT
                               12 - Appletalk

                        All values greater than 1518, identify the
                        protocolwhich has that value as its 'Ether-type'."
              ::= { protocolFilterEntry 2 }

          END
