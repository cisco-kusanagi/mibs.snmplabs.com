SIP-TC DEFINITIONS ::= BEGIN

   IMPORTS 
        MODULE-IDENTITY 
             FROM SNMPv2-SMI 

        TEXTUAL-CONVENTION 
             FROM SNMPv2-TC 

        sipMIB 
             FROM SIP-MIB-SMI; 

   sipTC MODULE-IDENTITY 
        LAST-UPDATED   "200007080000Z" 
        ORGANIZATION   "IETF SIP Working Group, SIP MIB Team" 
        CONTACT-INFO 
                "SIP MIB Team email: sip-mib@egroups.com 

                 Co-editor  Kevin Lingle 
                            Cisco Systems, Inc. 
                 postal:    7025 Kit Creek Road 
                            P.O. Box 14987 
                            Research Triangle Park, NC 27709 

Lingle/Maeng/Walker                                                  6 
Internet Draft            SIP-MIB                          July, 2000 

                            USA 
                 email:     klingle@cisco.com 
                 phone:     +1-919-392-2029 

                 Co-editor  Joon Maeng 
                            VTEL Corporation 
                 postal:    108 Wild Basin Rd. 
                            Austin, TX 78746 
                            USA 
                 email:     joon_maeng@vtel.com 
                 phone:     +1-512-437-4567 

                 Co-editor  Dave Walker 
                            SS8 Networks, Inc. 
                 postal:    80 Hines Road 
                            Kanata, ON  K2K 2T8 
                            Canada 
                 email:     drwalker@ss8networks.com 
                 phone:     +1 613 592 2100" 
        DESCRIPTION 
                "Initial version of Session Initiation Protocol (SIP) 
                 MIB Textual Conventions module used by other 
                 SIP-related MIB Modules." 
        ::= { sipMIB 1 } 

   -- 
   -- Textual Conventions 
   -- 
   SipServerActions ::= TEXTUAL-CONVENTION 
           STATUS current 
           DESCRIPTION 
                "Lists the possible actions of a SIP network server. 
                 A specific action may be requested by a user agent 
                 as a Contact parameter in a REGISTER." 
           SYNTAX INTEGER { 
                          redirect(1), 
                          proxy(2) 
           } 

END
