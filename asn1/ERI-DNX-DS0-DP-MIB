ERI-DNX-DS0-DP-MIB DEFINITIONS ::= BEGIN

IMPORTS
	MODULE-IDENTITY, OBJECT-IDENTITY, OBJECT-TYPE, Integer32,
	Counter32, NOTIFICATION-TYPE
		FROM SNMPv2-SMI
    DisplayString
        FROM SNMPv2-TC
    eriMibs
        FROM ERI-ROOT-SMI
    devices, PortStatus, FunctionSwitch, LinkPortAddress, 
    trapSequence
        FROM ERI-DNX-SMC-MIB;

eriDNXDs0dpMIB MODULE-IDENTITY 
      LAST-UPDATED    "200210300000Z"
      ORGANIZATION    "Eastern Research, Inc."
      CONTACT-INFO
                      "Customer Service
                Postal: Eastern Research, Inc.
                        225 Executive Drive
                        Moorestown, NJ 08057
                Phone:  +1-800-337-4374
                Email:  support@erinc.com"
      DESCRIPTION
              "The ERI Enterprise MIB Module for the DNX DS0DP Device."

      REVISION        "200210300000Z"
      DESCRIPTION
              "Nevio Poljak - eri_DnxNest MIB Rev 01.1
               Added new Tables for DS0DP Port Diagnostics."

      REVISION        "200205210000Z"
      DESCRIPTION
              "Nevio Poljak - eri_DnxNest MIB Rev 01.0
               Corrected errors in definition of ds0DpCfgCmdStatus."

      REVISION        "200204110000Z"
      DESCRIPTION
              "Converted to SMIv2 format. - Nevio Poljak - Release 14.2"

      REVISION        "200108010000Z"
      DESCRIPTION
              "Initial Release of this MIB. - Barry L. Bengel"
  	::= { eriMibs 10 }

-- *************************************************************************
-- The enterprise OID will be { iso(1) org(3) dod(6) internet(1) private(4)
--                              enterprises(1) virent(644) eri(2) dnx (4) 
--                              devices(2), dnxDSO-DP(6) }

-- *************************************************************************
-- The DS0-DP card is currently controlled via the Config or Diag groups.
-- The Configuration branch is used to perform all DS0-DP Port Configuration 
-- functions and the Diagnostic branch is used to run Port tests and view 
-- associated Port Statistics. 
-- *************************************************************************

dnxDS0DP      OBJECT IDENTIFIER      ::= { devices 6}
ds0DpConfig   OBJECT IDENTIFIER 	::= { dnxDS0DP 1 }
ds0DpDiag     OBJECT IDENTIFIER 	::= { dnxDS0DP 2 }

-- *************************************************************************
-- This table is the DS0-DP Port configuration table
-- *************************************************************************

ds0DpPortConfigTable OBJECT-TYPE
        SYNTAX SEQUENCE OF DS0dpPortConfigEntry
        MAX-ACCESS not-accessible
        STATUS current
        DESCRIPTION
            "This is the DS0-DP Configuration table which consists of an
            entry for each of the DS0-DP card's 8 links (ports).  The total
            number of entries depends on the number of DS0-DP cards in the
            nest. Changes to the Port Configuration must be made on a record
            or row by row basis.  This means that any use of the Set command
            on writable fields must include the ds0DPCfgCmdStatus field with
            a value of 'update' as the last variable in the SET PDU."
        ::= { ds0DpConfig 1 }

ds0DpPortConfigEntry OBJECT-TYPE
        SYNTAX DS0dpPortConfigEntry
        MAX-ACCESS not-accessible
        STATUS current
        DESCRIPTION
            "The conceptual row of the DS0-DP Port Configuration table. A row in
            this table cannot be added or deleted, only modified using the 
            ds0DpCfgCmdStatus field with a value of 'update' as the last
            variable in the SET PDU. The ds0DpCfgCmdStatus field must be
            included as the last variable in a SET PDU for the action to 
            take effect. If the ds0DpCfgCmdStatus is missing from the SET PDU, 
            the GET RESPONSE will contain the SNMP error status of 'genErr' 
            for and an error index equal to the last variable."
        INDEX { ds0DpCfgPortAddr }
        ::= { ds0DpPortConfigTable 1 }

DS0dpPortConfigEntry ::=
        SEQUENCE {
                ds0DpCfgPortAddr       LinkPortAddress,   -- RO
                ds0DpCfgResource       Integer32,         -- RO
                ds0DpCfgPortName       DisplayString,
                ds0DpCfgStatus         PortStatus,
                ds0DpCfgRate           INTEGER,
                ds0DpCfgZeroCodeEnf    FunctionSwitch,
                ds0DpCfgLoopDetect     FunctionSwitch,
                ds0DpCfgCmdStatus      INTEGER
                }

ds0DpCfgPortAddr OBJECT-TYPE
        SYNTAX LinkPortAddress
        MAX-ACCESS read-only
        STATUS current
        DESCRIPTION
           "This number uniquely identifies a DS0-Dp Port resource. 
           This number will be used throughout the system to identify 
           a unique port. The format is represented using an IP address 
           syntax (4 byte string). Note that the maximum valid port 
           number will vary depending on the specified device. 
            
               The 1st byte represents the Nest Number (0-7)
               The 2nd byte represents the Slot Number (1-11)            
               The 3rd byte represents the Port Number (1-32)
               The 4th byte is reserved for future use."
        ::= { ds0DpPortConfigEntry 1 }

ds0DpCfgResource OBJECT-TYPE
        SYNTAX Integer32
        MAX-ACCESS read-only
        STATUS current
        DESCRIPTION
           "Uniquely identifies a DS0-DP port in the system.  This
           number is provided as key to allow the manager to map this
           entry to a corresponding Resource Table entry."
        ::= { ds0DpPortConfigEntry 2 }

ds0DpCfgPortName OBJECT-TYPE
        SYNTAX DisplayString (SIZE(0..20))
        MAX-ACCESS read-write
        STATUS current
        DESCRIPTION
           "This is the user-defined text name to identify the port."
        ::= { ds0DpPortConfigEntry 3 }

ds0DpCfgStatus OBJECT-TYPE
        SYNTAX PortStatus
        MAX-ACCESS read-write
        STATUS current
        DESCRIPTION
           "Dictates the current status of the port, in-service or 
           out-of-service."
        ::= { ds0DpPortConfigEntry 4 }

ds0DpCfgRate OBJECT-TYPE
        SYNTAX INTEGER {
            r64K(0),
            r56K(1)
             }
        MAX-ACCESS read-write
        STATUS current
        DESCRIPTION
           "The DS0-DP port's configured transfer rate." 
        ::= { ds0DpPortConfigEntry 5 }

ds0DpCfgZeroCodeEnf OBJECT-TYPE
        SYNTAX FunctionSwitch
        MAX-ACCESS read-write
        STATUS current
        DESCRIPTION
           "Determines the Zero Code Signal enforcement setting."
        ::= { ds0DpPortConfigEntry 6 }

ds0DpCfgLoopDetect OBJECT-TYPE
        SYNTAX FunctionSwitch
        MAX-ACCESS read-write
        STATUS current
        DESCRIPTION
           "Determines current Loop detection setting. A channel bank can 
           turn certain loopback codes into a dropside loop or network loop, 
           depending upon direction (local, remote DS0, remote CSU, or
           remote OCU). If disabled, the DS0-DP device is transparent to loop 
           commands and does not respond."
        ::= { ds0DpPortConfigEntry 7 }

ds0DpCfgCmdStatus OBJECT-TYPE
        SYNTAX INTEGER {
    -- Initial default status for a row
            ready-for-command (0),
    -- DS0DP Port Commands used in SET Command (1..99)
            update (1),
            inServiceAll (7),
            copyToAll (9),
            outOfServiceAll (12),
                            		
    -- Response States used in GET RESPONSE Command (100..199)
            update-successful (101),
            insvc-successful (107),
            copy-successful (109),
            oos-successful (112),
                            		
    -- DS0DP Port Config Error Codes used in GET RESPONSE Command (200..799)
            err-general-config-error (400),
            err-invalid-port-status (401),
            err-invalid-port-command (403),
            err-invalid-zero-code (406),
            err-invalid-port-rate (407),
            err-invalid-network-loop (410),
            err-data-locked-by-another-user (450),
            err-snmp-parse-failed (500),
            err-invalid-snmp-type (501),
            err-invalid-snmp-var-size (502)
            }        
        MAX-ACCESS read-write
        STATUS current
        DESCRIPTION
           "The command status for this port configuration row/record.
           The value used in a SET will be replaced by a response
           value in the GET RESPONSE indicating success or failure.
           		
            Default Response State used in GET RESPONSE Command
                ready-for-command (0)
                    initial default status for a row           
                    
            DS0-DP Port Commands used in SET Command (1..99)            
                update(1)
                    Change existing Port Configuration
                inServiceAll (7)
                    Change Link Status to in-service for all 8 ports.
                copyToAll (9)
                    Copy DS0-DP Port configuration to all other ports 
                    within the same device
                outOfServiceAll (12)
                    Change Link Status to out-of-service for all 8 ports.
               		              		
            Response States used in GET RESPONSE Command (100..199)
                update-successful (101)
                    DS0-DP Port data has been successfully changed
                insvc-successful (107)
                    All Ports have been successfully placed In Service
                copy-successful (109)
                    DS0-DP Port data has been successfully copied to 
                    other ports
                oos-successful (112)
                    All Ports have been successfully placed Out of Service
               		
            DS0DP Port Error Codes used in GET RESPONSE Command (200..699)
                err-general-config-error (400)
                    Unknown DS0-DP port configuration error occurred
                err-invalid-port-status (401)
                    Unrecognized DS0-DP port status setting
                err-invalid-port-command (403)
                    Unrecognized DS0-DP port command-action
                err-invalid-zero-code (406)
                    Unrecognized zero code enforcement setting
                err-invalid-port-rate (407)
                	Unrecognized DS0-DP Rate
                err-invalid-network-loop (410)
                    Unrecognized loop detect setting setting
                err-data-locked-by-another-user (450)
                    Another administrative user is making changes to this
                    part of the system via a terminal session. Check Event
                    Log for user name
                err-snmp-parse-failed (500)
                    Agent could not parse variable
                err-invalid-snmp-type (501)
                    Variable ASN type does not match Agent defined type 
                err-invalid-snmp-var-size (502)
                    Variable size is too big"                 		
         ::= { ds0DpPortConfigEntry 8 }


-- *************************************************************************
-- This table is the DS0-DP Composite Clock configuration table
-- *************************************************************************

ds0DpClockConfigTable OBJECT-TYPE
        SYNTAX SEQUENCE OF DS0dpClockConfigEntry
        MAX-ACCESS not-accessible
        STATUS current
        DESCRIPTION
            "This is the DS0-DP Composite Clock Configuration table which 
            consists of an entry for each DS0-DP card in the node.  The total
            number of entries depends on the number of DS0-DP cards in the
            node. Changes to the Clock Configuration must be made on a record
            or row by row basis.  This means that any use of the Set command
            on writable fields must include the ds0DpCompClockCmdStatus field with
            a value of 'update' as the last variable in the SET PDU."
        ::= { ds0DpConfig 2 }

ds0DpClockConfigEntry OBJECT-TYPE
        SYNTAX DS0dpClockConfigEntry
        MAX-ACCESS not-accessible
        STATUS current
        DESCRIPTION
            "The conceptual row of the DS0-DP Composite Clock Configuration table. 
            A row in this table cannot be added or deleted, only modified using the 
            ds0DpCompClockCmdStatus field with a value of 'update' as the last
            variable in the SET PDU. The ds0DpCompClockCmdStatus field must be
            included as the last variable in a SET PDU for the action to 
            take effect. If the ds0DpCompClockCmdStatus is missing from the SET PDU, 
            the GET RESPONSE will contain the SNMP error status of 'genErr' 
            for and an error index equal to the last variable."
        INDEX { ds0DpCompClockAddr }
        ::= { ds0DpClockConfigTable 1 }

DS0dpClockConfigEntry ::=
        SEQUENCE {
                ds0DpCompClockAddr         LinkPortAddress,   -- RO
                ds0DpCompClockResource     Integer32,         -- RO
                ds0DpCompClockStatus       FunctionSwitch,
                ds0DpCompClockCmdStatus    INTEGER
                }

ds0DpCompClockAddr OBJECT-TYPE
        SYNTAX LinkPortAddress
        MAX-ACCESS read-only
        STATUS current
        DESCRIPTION
           "This number uniquely identifies a DS0-DP Clock resource. 
           This number will be used throughout the system to identify 
           a unique port. The format is represented using an IP address 
           syntax (4 byte string). Note that the maximum valid port 
           number will vary depending on the specified device. 
            
               The 1st byte represents the Nest Number (0-7)
               The 2nd byte represents the Slot Number (1-11)            
               The 3rd byte represents the Clock Port Number (9)
               The 4th byte is reserved for future use."
        ::= { ds0DpClockConfigEntry 1 }

ds0DpCompClockResource OBJECT-TYPE
        SYNTAX Integer32
        MAX-ACCESS read-only
        STATUS current
        DESCRIPTION
           "Uniquely identifies a DS0-DP composite clock port in the 
           system.  This number is provided as key to allow the 
           manager to map this entry to a corresponding Resource Table 
           entry."
        ::= { ds0DpClockConfigEntry 2 }

ds0DpCompClockStatus OBJECT-TYPE
        SYNTAX FunctionSwitch
        MAX-ACCESS read-write
        STATUS current
        DESCRIPTION
           "Displays current Composite Clock setting and allows user to
           enable or disable it."
        ::= { ds0DpClockConfigEntry 3 }

ds0DpCompClockCmdStatus OBJECT-TYPE
        SYNTAX INTEGER {
    -- Initial default status for a row
            ready-for-command (0),
    -- Action States used in SET Command (1..99)
            update (1),
                		
    -- Response States used in GET RESPONSE Command (100..199)
            update-successful (101),
                		
    -- DS0DP Clock Error Codes used in GET RESPONSE Command (200..799)
            err-general-clock-config-error (400),
            err-invalid-clock-status(401),
            err-invalid-clock-command(403),            
            err-data-locked-by-another-user(450),
            err-snmp-parse-failed (500),
            err-invalid-snmp-type (501),
            err-invalid-snmp-var-size (502)
            }
        MAX-ACCESS read-write
        STATUS current
        DESCRIPTION
           "The command status for this port configuration row/record.
           The value used in a SET will be replaced by a response
           value in the GET RESPONSE indicating success or failure.
           		
            Default Response State used in GET RESPONSE Command
                ready-for-command (0)
                    initial default status for a row           
                    
            DS0-DP Clock Commands used in SET Command (1..99)            
                update (1)
                    Change existing Composite Clock setting
               		              		
            Response States used in GET RESPONSE Command (100..199)
                update-successful (101)
                    DS0-DP Composite Clock data has been successfully changed
               		
            DS0DP Clock Error Codes used in GET RESPONSE Command (200..699)
                err-general-clock-config-error (400)
                    Unknown DS0-DP port configuration error occurred
                err-invalid-clock-status (401)
                    Unrecognized DS0-DP composite clock setting
                err-invalid-clock-command (403)
                    Unrecognized DS0-DP clock command-action
                err-data-locked-by-another-user (450)
                    Another administrative user is making changes to this
                    part of the system via a terminal session. Check Event
                    Log for user name
                err-snmp-parse-failed (500)
                    Agent could not parse variable
                err-invalid-snmp-type (501)
                    Variable ASN type does not match Agent defined type 
                err-invalid-snmp-var-size (502)
                    Variable size is too big"                 		
         ::= { ds0DpClockConfigEntry 4 }

-- *************************************************************************
-- This is the DS0DP Port Diagnostic Status table

ds0dpPortDiagTable OBJECT-TYPE
        SYNTAX SEQUENCE OF DS0dpPortDiagEntry
        MAX-ACCESS not-accessible
        STATUS current
        DESCRIPTION
            "This is the DS0DP Port Diagnostic table which consists of a single
            entry for each card's Framer Display.  The total number of
            entries depends on the number of DS0DP cards in the nest."
        ::= { ds0DpDiag 1 }

ds0dpPortDiagEntry OBJECT-TYPE
        SYNTAX DS0dpPortDiagEntry
        MAX-ACCESS not-accessible
        STATUS current
        DESCRIPTION
            "The conceptual row of the DS0DP Port table. 
            A row in this table cannot be added or deleted, only modified."
        INDEX { ds0dpDiagAddr }
        ::= { ds0dpPortDiagTable 1 }

DS0dpPortDiagEntry ::=
        SEQUENCE {
                ds0dpDiagAddr             LinkPortAddress,  -- RO
                ds0dpDiagResource         Integer32,        -- RO
                ds0dpDiagState            INTEGER,
                ds0dpDiagErrSecs          Counter32,
                ds0dpDiagDropLoop         INTEGER,        -- RW
                ds0dpDiagNetLoop          INTEGER,        -- RW
                ds0dpDiagBertState        INTEGER,        -- RW
                ds0dpDiagTestDuration     Counter32,
                ds0dpDiagBertErrSecs      Counter32,
                ds0dpDiagBpvErrSecs       Counter32,
                ds0dpDiagInsErrMode       INTEGER,        -- RW              
                ds0dpDiagCmdStatus        INTEGER         -- RW              
              	}

ds0dpDiagAddr OBJECT-TYPE
        SYNTAX LinkPortAddress
        MAX-ACCESS read-only
        STATUS current
        DESCRIPTION
           "This number uniquely identifies a DS0-Dp Port resource. 
           This number will be used throughout the system to identify 
           a unique port. The format is represented using an IP address 
           syntax (4 byte string). Note that the maximum valid port 
           number will vary depending on the specified device. 
            
               The 1st byte represents the Nest Number (0-7)
               The 2nd byte represents the Slot Number (1-11)            
               The 3rd byte represents the Port Number (1-32)
               The 4th byte is reserved for future use."
        ::= { ds0dpPortDiagEntry 1 }

ds0dpDiagResource OBJECT-TYPE 
        SYNTAX Integer32
        MAX-ACCESS read-only
        STATUS current
        DESCRIPTION
            "This number uniquely identifies a DS0DP Port resource. 
            This number is provided as key to allow the manager to map this
            entry to a corresponding Resource Table Entry."
        ::= { ds0dpPortDiagEntry 2 }

ds0dpDiagState OBJECT-TYPE
        SYNTAX INTEGER {
                ok  (0), 
                net-loop (8),         -- bit 3
                drop-loop (16),       -- bit 4
                los (64),             -- bit 6
                oos (65535),          -- bit 16
                errors(2147483647)    -- all
                }
        MAX-ACCESS read-only
        STATUS current
        DESCRIPTION
           "Determines the current line condition status of the Port.
                ok       	(0)         - No Alarm
                net-loop 	(8),        - loopback code on the network side
                drop-loop 	(16),       - loopback code on the STP drop side
                los 		(64),       - Loss of Signal
                oos 		(65535),    - Inactive
                errors		(2147483647)- Multiple Errors displays raw bit field value
           "
        ::= { ds0dpPortDiagEntry 3 }

ds0dpDiagErrSecs OBJECT-TYPE
        SYNTAX Counter32
        MAX-ACCESS read-only
        STATUS current
        DESCRIPTION
            "This is the total number of errored seconds that have
            occurred since the port has been activated."
        ::= { ds0dpPortDiagEntry 4 } 
     
ds0dpDiagDropLoop OBJECT-TYPE
        SYNTAX INTEGER {
        	off (0),
        	ocu (40), 
        	csu (41),
        	ds0ToDrop (42),
        	local(43),
        	ds0FromDrop (49)
        	}
        MAX-ACCESS read-write
        STATUS current
        DESCRIPTION
           "Determines the current latching DS0 Dataport loopback code
            on the STP drop side (4 wire anolog side) for this port.
           In order to turn on a loop, the port must be configured In Service
           with a Connection.
            off         (0)  - indicates drop side loopback is disabled
        	ocu         (40) - triggers the DS0DP to send a standard DDS OCU 
        	                   loop code towards the drop side.
        	csu         (41) - triggers the DS0DP to send a standard DDS CSU 
        	                   loop code towards the drop side.
        	ds0ToDrop   (42) - loops the DS0 data towards the drop side.
        	local       (43) - the STP/PATCH PANEL output data enters the DS0DP 
        	                   and is looped back toward the four-wire drop. Also, 
        	                   the DS0-DP sends the DDS Mux-Out-Of-Sync-Code in place 
        	                   of the four-wire loop data towards the network.
        	ds0FromDrop (49) - loops the DS0 data from the drop side."
        ::= { ds0dpPortDiagEntry 5 }

ds0dpDiagNetLoop OBJECT-TYPE
        SYNTAX INTEGER {
        	off (5),
        	local(44),
        	ocu (45),
        	csu (46),
        	ds0ToNet (47),
        	ds0FromNet (48)
        	}
        MAX-ACCESS read-write
        STATUS current
        DESCRIPTION
           "Determines the current latching DS0 Dataport loopback code
            on the network side (T1 digital line side) for this port. 
            In order to turn on a loop, the port must be configured In Service 
            with a Connection.
             off        (0) - indicates network loopback is disabled
        	 local      (5) - the incoming DS0 data from the far end enters the DS0DP 
        	                  and is looped back towards the far end. Also, the DS0DP 
        	                  sends the DDS Mux-Out-Of-Sync-Code in place of the DS0 
        	                  data from the network towards the drop.
         	 ocu        (45)- triggers the DS0DP to send a standard DDS OCU loop code 
        	                   towards the far end.
         	 csu        (46)- triggers the DS0DP to send a standard DDS CSU loop code 
        	                  towards the far end.
        	 ds0ToNet  (47) - loops the DS0 data towards the network side.
        	 ds0FromNet(48) - loops the DS0 data from the network side.
        	 "
        ::= { ds0dpPortDiagEntry 6 } 

ds0dpDiagBertState OBJECT-TYPE
        SYNTAX INTEGER {
        	bertOff (51),
            dropAllOnes (93),         
            drop511 (94),       
            drop2047 (95),        
            dropQRSS (96),
            netAllOnes (97),        
            net511 (98),       
            net2047 (99),        
            netQRSS (100)
            }
        MAX-ACCESS read-write
        STATUS current
        DESCRIPTION
            "This indicates the current BERT test running and can be used to
            start and stop a desired Test Period. In order to turn on a bert, 
            the port must be configured In Service.
             	bertOff     (51)  - indicates BERT test is not running
        	 	dropAllOnes (93)  - sends All Ones Bert pattern to Drop        
             	drop511 	(94)  - sends 511 Bert pattern to Drop        
             	drop2047 	(95)  - sends 2047 Bert pattern to Drop         
             	dropQRSS 	(96)  - sends QRSS Bert pattern to Drop
             	netAllOnes 	(97)  - sends All Ones Bert pattern to Network        
             	net511 		(98)  - sends 511 Bert pattern to Network        
             	net2047 	(99)  - sends 2047 Bert pattern to Network         
             	netQRSS 	(100) - sends QRSS Bert pattern to Network
            "
        ::= { ds0dpPortDiagEntry 7 } 
        
ds0dpDiagTestDuration OBJECT-TYPE
        SYNTAX Counter32
        MAX-ACCESS read-only
        STATUS current
        DESCRIPTION
            "This the total number of seconds the test data has been collected."
        ::= { ds0dpPortDiagEntry 8 }     
        
ds0dpDiagBertErrSecs OBJECT-TYPE   
        SYNTAX Counter32
        MAX-ACCESS read-only
        STATUS current
        DESCRIPTION
            "This is the total number of errored seconds that have
            occurred on the local port since the Test has been turned on.
            
            This Errored Second is defined as a one second period in which 
            one or more bits are in error."
        ::= { ds0dpPortDiagEntry 9 } 
        
ds0dpDiagBpvErrSecs OBJECT-TYPE
        SYNTAX Counter32
        MAX-ACCESS read-only
        STATUS current
        DESCRIPTION
            "This is the number of seconds a Bi-polar violation was detected."
        ::= { ds0dpPortDiagEntry 10 } 

ds0dpDiagInsErrMode OBJECT-TYPE
        SYNTAX INTEGER {
                bert-error (1),
                bpv (2)     
                }
        MAX-ACCESS read-write
        STATUS current
        DESCRIPTION
           "Determines the status of the current Insert Error mode associated 
           with the framer. In order to insert an error, the ds0dpPortDiagCmdStatus 
           must be sent in a SET PDU with a value of 'insertError'."
        ::= { ds0dpPortDiagEntry 11 }

ds0dpDiagCmdStatus OBJECT-TYPE
        SYNTAX INTEGER {
    -- Initial default status for a row
            ready-for-command (0),
    -- Action States used in SET Command (1..99)
            update (1),
            clearErrors (14),
            insertError (16),
                                
    -- Response States used in GET RESPONSE Command (100..199)
            update-successful (101),
            clear-successful (114),
            insert-successful (116),
                                
    -- Error Codes used in GET RESPONSE Command (200..799)
            err-general-diag-error (200),
            err-link-out-of-service (201),
            err-invalid-loop (202),
            err-invalid-bert (203),
            err-test-in-progress (205),
            err-field-cannot-be-set (206),
            err-invalid-command (208),
            err-snmp-parse-failed(500),
            err-invalid-snmp-type(501),
            err-invalid-snmp-var-size(502) 
            }
        MAX-ACCESS read-write
        STATUS current
        DESCRIPTION
            "This is the command status for the DS0DP Port Row.
           The value used in a SET will be replaced by a response
           value in the GET RESPONSE indicating success or failure.

            Default Response State used in GET RESPONSE Command
                ready-for-command (0)
                    initial default status for a row           
                    
            DS0DP Action Commands used in SET Command (1..99)            
                update (1)
                    Can be used optionally when inserting errors
                    in order to get status code back in response
                clearErrors (14)
                    Resets all error counters and bert test time to zero
                insertError (16)
                    Inserts the current invalid bit pattern as indicated
                    by the value of ds0dpPortDiagInsErrMode. 
                                
            Response States used in GET RESPONSE Command (100..199)
                update-successful (101)
                    Action has been successfully performed
                clear-successful (114)
                    Error counts have been successfully cleared
                insert-successful (116)
                    Errored bits have been successfully inserted
                                
            The Error Codes used in GET RESPONSE Command (200..799)
                err-general-diag-error (200)
                    Unknown request error occurred.
                err-invalid-loop (202)
                	Unrecognized loop Command requested                    
            	err-invalid-bert (203)
                    Unrecognized Bert Command requested                    
                err-test-in-progress (205)
                    Requested action cannot be performed during bert
                err-field-cannot-be-set (206)
                    Read-only field was included in SET request
                err-invalid-command (208)
                    Unrecognized framer Command requested                    
                err-snmp-parse-failed (500)
                    Agent could not parse variable
                err-invalid-snmp-type (501)
                    Variable ASN type does not match Agent defined type 
                err-invalid-snmp-var-size (502)
                    Variable size is too big" 
        ::= { ds0dpPortDiagEntry 12 } 

-- *************************************************************************
--   This is the Trap Definitions section for the DS0-DP MIB. 
-- *************************************************************************
                
dnxDS0DPEnterprise OBJECT-IDENTITY
      STATUS current
      DESCRIPTION "ERI DNX DS0DP Enterprise for Alarms/Events"
    ::= { dnxDS0DP 0 }

ds0DpPortConfigTrap NOTIFICATION-TYPE
        OBJECTS {
            trapSequence,
            ds0DpCfgPortAddr,
            ds0DpCfgCmdStatus
            }
        STATUS current
        DESCRIPTION
              	"This trap is used to notify a NMS that a user has updated 
              	the Port configuration for a given DS0-DP Port entry."
        ::= { dnxDS0DPEnterprise 1 }

ds0DpClockConfigTrap NOTIFICATION-TYPE
        OBJECTS {
            trapSequence,
            ds0DpCompClockAddr,
            ds0DpCompClockCmdStatus
            }
        STATUS current
        DESCRIPTION
              	"This trap is used to notify a NMS that a user has updated 
              	the Clock configuration for the specified DS0-DP Device."
        ::= { dnxDS0DPEnterprise 2 }

END

-- *************************************************************************
--
--  MIB:    ERI-DNX-E3-MIB
--
--  Purpose:
--          This will be the MIB for the DNX E3 Interface 
--          Module. This will provide for Configuration and Diagnostics
--          on any E3 card in the nest.
--
--  Contact: Eastern Research Inc. 1-800-337-4374  Email: support@erinc.com
--
--  Revised: Dec. 14, 2001 - Nevio Poljak  - Release 14.0 
--           Initial Release
--
--           Jan. 2, 2002 - Nevio Poljak - Release 14.1 
--           Added new E1 InterNational Bit field.
--
--           April 8, 2002 - Nevio Poljak for Release 14.2
--           Converted to SMIv2 format and remove old E3 Framer Insert Error
--           that are not supported.
-- *************************************************************************
