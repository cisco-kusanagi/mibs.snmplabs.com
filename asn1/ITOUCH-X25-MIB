-- $Id: it-x25-mib.mib,v 1.2 2000/07/24 19:34:11 sse Exp $
        ITOUCH-X25-MIB DEFINITIONS ::= BEGIN

               IMPORTS
                       IpAddress
                               FROM RFC1155-SMI
                       X121Address
                               FROM RFC1382-MIB
                       OBJECT-TYPE
                               FROM RFC-1212
                       iTouch
                               FROM ITOUCH-MIB;

       xX25            OBJECT IDENTIFIER ::= { iTouch 20 }


            -- This is a MIB module for all iTouch Communications systems that
            -- implement X25.

            -- Copyright 2000 iTouch Communications, Inc. All Rights Reserved.
            -- Reproduction of this document is authorized on
            -- condition that this copyright notice is included.
            -- This MIB document embodies iTouch Communications, Inc.'s 
            -- proprietary intellectual property.  iTouch Communications, Inc.
            -- retains all title and ownership in this MIB, including any
            -- revisions.
            --
            -- It is iTouch Communications, Inc.'s intent to encourage the
            -- widespread use of this MIB in connection with the management of
            -- iTouch Communications, Inc. products. iTouch Communications,
            -- Inc. grants vendors,end-users, and other interested parties a
            -- non-exclusive license to use this MIB in connection with the
            -- management of iTouch Communications, Inc. products.
            --
            -- This MIB document is supplied "AS IS," and iTouch 
            -- Communications, Inc. makes no warranty, either express or
            -- implied, as to the use operation, condition, or performance of
            -- the MIB.
	
	
       -- X.25 Channel Table

       xX25ChannelTable OBJECT-TYPE
           SYNTAX SEQUENCE OF XX25ChannelEntry
           ACCESS not-accessible
           STATUS mandatory
           DESCRIPTION
               "Entries of xX25Channel Table."
           ::= { xX25 4 }

       xX25ChannelEntry OBJECT-TYPE
           SYNTAX XX25ChannelEntry
           ACCESS not-accessible
           STATUS mandatory
           DESCRIPTION
               "Entries of xX25ChannelTable."
           INDEX { xX25ChannelIndex }
           ::= { xX25ChannelTable 1 }

       XX25ChannelEntry ::=
           SEQUENCE {
               xX25ChannelIndex
                       INTEGER,
               xX25ChannelLowPVC
                       INTEGER,
               xX25ChannelHighPVC
                       INTEGER,
			   xX25ChannelNetwork
					   INTEGER,
			   xX25ChannelMaxPrecedence
					   INTEGER,
			   xX25ChannelStdVersion
					   INTEGER
           }

       xX25ChannelIndex OBJECT-TYPE
           SYNTAX INTEGER
           ACCESS read-only
           STATUS mandatory
           DESCRIPTION
               "The ifIndex value for the X.25 physical link."
           ::= { xX25ChannelEntry 1 }

       xX25ChannelLowPVC OBJECT-TYPE
           SYNTAX INTEGER (0..4095)
           ACCESS read-write
           STATUS mandatory
           DESCRIPTION
               "Lowest PVC channel.  Setting it to zero indicates 
               'none', and will also set the xX25ChannelHighPVC to 
               zero.  If set to a non-zero value and 
               xX25ChannelHighPVC is zero, xX25ChannelHighPVC will 
               be set to the same value.  Otherwise, 
               xX25ChannelLowPVC must be less than or equal to 
               xX25ChannelHighPVC."
           ::= { xX25ChannelEntry 2 }

       xX25ChannelHighPVC OBJECT-TYPE
           SYNTAX INTEGER (0..4095)
           ACCESS read-write
           STATUS mandatory
           DESCRIPTION
               "Highest PVC channel.  Setting it to 0 indicates 
               none, and will also set the xX25ChannelLowPVC to 0.  
               If set to a non-zero value and xX25ChannelLowPVC is 
               zero, xX25ChannelLowPVC will be set to the same 
               value.  Otherwise, xX25ChannelHighPVC must be less 
               than or equal to xX25ChannelLowPVC."
           ::= { xX25ChannelEntry 3 }

       xX25ChannelNetwork OBJECT-TYPE
           SYNTAX INTEGER { ccitt(1), ddnStandard(2) }
           ACCESS read-write
           STATUS mandatory
           DESCRIPTION
               "The type of network being run."
           ::= { xX25ChannelEntry 4 }

       xX25ChannelMaxPrecedence OBJECT-TYPE
           SYNTAX INTEGER ( 0..3 )
           ACCESS read-write
           STATUS mandatory
           DESCRIPTION
               "The maximum level of IP precedence supported."
           ::= { xX25ChannelEntry 5 }

       xX25ChannelStdVersion OBJECT-TYPE
           SYNTAX INTEGER
           ACCESS read-write
           STATUS mandatory
           DESCRIPTION
               "The standard year supported by x25.  Values are usually
			   1980 or 1984 (the default)."
           ::= { xX25ChannelEntry 6 }

       -- X.25 Virtual Circuit Configuration Table

       xX25VcCfgTable OBJECT-TYPE
           SYNTAX SEQUENCE OF XX25VcCfgEntry
           ACCESS not-accessible
           STATUS mandatory
           DESCRIPTION
               "These objects contain information about the virtual 
               circuit configuration in an X.25 PLE.  These values 
               are the configured values for circuits that  may or 
               may not be connected.  Unconfigured calls may be 
               added to this table as calls are accepted."
           ::= { xX25 6 }

       xX25VcCfgEntry OBJECT-TYPE
           SYNTAX XX25VcCfgEntry
           ACCESS not-accessible
           STATUS mandatory
           DESCRIPTION
               "Entries of the xX25VcCfgTable."
           INDEX { xX25VcCfgIndex }
           ::= { xX25VcCfgTable 1 }

       XX25VcCfgEntry ::=
           SEQUENCE {
               xX25VcCfgIndex
                   INTEGER,
               xX25VcCfgPartnerAddr
                   X121Address,
               xX25VcCfgInterfaceIndex
                   INTEGER,
               xX25VcCfgLinkIndex
                   INTEGER,
               xX25VcCfgProtocol
                   INTEGER,
               xX25VcCfgEncapsulation
                   INTEGER,
               xX25VcCfgPvc
                   INTEGER,
               xX25VcCfgPartnerIpAddress
                   IpAddress,
               xX25VcCfgClearFacilities
                   INTEGER,
               xX25VcCfgStatus
                   INTEGER
           }

       xX25VcCfgIndex OBJECT-TYPE
           SYNTAX INTEGER
           ACCESS read-only
           STATUS mandatory
           DESCRIPTION
               "An arbitrary index value for the virtual circuit."
           ::= { xX25VcCfgEntry 1 }

       xX25VcCfgPartnerAddr OBJECT-TYPE
           SYNTAX X121Address
           ACCESS read-write
           STATUS mandatory
           DESCRIPTION
               "Partner's X.121 Address."
           DEFVAL { "" }
           ::= { xX25VcCfgEntry 2 }

       xX25VcCfgInterfaceIndex OBJECT-TYPE
           SYNTAX INTEGER
           ACCESS read-write
           STATUS mandatory
           DESCRIPTION
               "ifIndex of ITouch logical interface associated with 
               this VC."
           DEFVAL { 0 } -- Actually lowest numbered WAN link
           ::= { xX25VcCfgEntry 3 }

       xX25VcCfgLinkIndex OBJECT-TYPE
           SYNTAX INTEGER
           ACCESS read-write
           STATUS mandatory
           DESCRIPTION
               "ifIndex of physical link on which this VC 
               resides."
           DEFVAL { 0 }  -- Actually lowest numbered WAN link
           ::= { xX25VcCfgEntry 4 }

       xX25VcCfgProtocol OBJECT-TYPE
           SYNTAX INTEGER { appleTalk(1),
                            bridged(2),
                            decnet(3),
                            ip(4),
                            ipx(5),
                            multiProtocol(6),
                            osi(7) }
           ACCESS read-write
           STATUS mandatory
           DESCRIPTION
               "Protocol which is being encapsulated by this VC."
           DEFVAL { ip }
           ::= { xX25VcCfgEntry 5 }

       xX25VcCfgEncapsulation OBJECT-TYPE
           SYNTAX INTEGER { null(1),
                            dedicated(2),
                            snap(3) }
           ACCESS read-write
           STATUS mandatory
           DESCRIPTION
               "Encapsulation method used by this VC."
           DEFVAL { dedicated }
           ::= { xX25VcCfgEntry 6 }

       xX25VcCfgPvc OBJECT-TYPE
           SYNTAX INTEGER (0..4095)
           ACCESS read-write
           STATUS mandatory
           DESCRIPTION
               "Channel number if VC is a PVC, else 0.  The value 
               must be in the range of xX25ChannelLowPVC to 
               xX25ChannelHighPVC"
           DEFVAL { 0 }
           ::= { xX25VcCfgEntry 7 }

       xX25VcCfgPartnerIpAddress OBJECT-TYPE
           SYNTAX IpAddress
           ACCESS read-write
           STATUS mandatory
           DESCRIPTION
               "IP address of the partner over this VC.  This must 
               be configured if IP packets will not be 
               MAC-encapsulated."
           DEFVAL { 0 }
           ::= { xX25VcCfgEntry 8 }

       xX25VcCfgClearFacilities OBJECT-TYPE
           SYNTAX INTEGER { ready(1), execute(2) }
           ACCESS read-write
           STATUS mandatory
           DESCRIPTION
               "Control to clear the VC call facilities string.  In 
               response to a get-request or get-next-request, the 
               agent always returns 'ready' for this value.  
               Setting the value to 'ready' has no effect.  Setting 
               it to 'execute' causes the string to be cleared."
           DEFVAL { ready }
           ::= { xX25VcCfgEntry 9 }

       xX25VcCfgStatus OBJECT-TYPE
           SYNTAX INTEGER { invalid(1), valid(2) }
           ACCESS read-write
           STATUS mandatory
           DESCRIPTION
               "Setting to 'invalid' removes this VC from the 
               table.  If 'valid', setting to 'valid' has no 
               effect, otherwise it creates an entry."
           DEFVAL { valid }
           ::= { xX25VcCfgEntry 10 }

       -- X.25 Physical Link Table

       xX25LinkTable OBJECT-TYPE
           SYNTAX SEQUENCE OF XX25LinkEntry
           ACCESS not-accessible
           STATUS mandatory
           DESCRIPTION
               "These objects contain information about the 
               configuration of the X.25 physical links necessary 
               for the ITouch Bridge/Router.  Unless otherwise 
               noted, changes to these objects require that the 
               X.25 physical link be restarted in order for the 
               changes to take effect."
           ::= { xX25 7 }

       xX25LinkEntry OBJECT-TYPE
           SYNTAX XX25LinkEntry
           ACCESS not-accessible
           STATUS mandatory
           DESCRIPTION
               "Entries of the xX25LinkTable."
           INDEX { xX25LinkIndex }
           ::= { xX25LinkTable 1 }

       XX25LinkEntry ::=
           SEQUENCE {
               xX25LinkIndex
                   INTEGER,
               xX25LinkRRDelay
                   INTEGER,
               xX25LinkIdleTimeout
                   INTEGER,
               xX25LinkHoldDownTimer
                   INTEGER,
               xX25LinkAccUncfgCalls
                   INTEGER,
               xX25LinkDefWindSize
                   INTEGER,
               xX25LinkMaxWindSize
                   INTEGER,
               xX25LinkDefPktSize
                   INTEGER,
               xX25LinkDefThrptClassIn
                   INTEGER,
               xX25LinkDefThrptClassOut
                   INTEGER,
               xX25LinkDefThrptClassInMsk
                   INTEGER,
               xX25LinkDefThrptClassOutMsk
                   INTEGER,
               xX25LinkFlowCtrlNeg
                   INTEGER,
               xX25LinkThrptClassNeg
                   INTEGER,
               xX25LinkICallBarred
                   INTEGER,
               xX25LinkOCallBarred
                   INTEGER,
               xX25LinkOneOut
                   INTEGER,
               xX25LinkOneIn
                   INTEGER,
               xX25LinkRevChargeAcc
                   INTEGER,
               xX25LinkLocalChargePrevent
                   INTEGER,
               xX25LinkRpoa
                   INTEGER,
               xX25LinkNui
                   INTEGER,
               xX25LinkMaxPacketSize
                   INTEGER,
               xX25LinkInsertCallingAddr
                   INTEGER,
               xX25LinkDefaultInterface
                   INTEGER
           }

       xX25LinkIndex OBJECT-TYPE
           SYNTAX INTEGER
           ACCESS read-only
           STATUS mandatory
           DESCRIPTION
               "The ifIndex value for a ITouch physical link."
           ::= { xX25LinkEntry 1 }

       xX25LinkRRDelay OBJECT-TYPE
           SYNTAX INTEGER (0..127)
           ACCESS read-write
           STATUS mandatory
           DESCRIPTION
               "Number of packets received before an RR will be 
               sent. The value must be less than the 
               xX25CallParmInWindowSize. Modifying this object does 
               not require the X.25 physical link to be 
               restarted. 0 indicates that RR will not be sent."
           ::= { xX25LinkEntry 2 }

       xX25LinkIdleTimeout OBJECT-TYPE
           SYNTAX INTEGER (0..255)
           ACCESS read-write
           STATUS mandatory
           DESCRIPTION
               "Length of time in minutes that a virtual circuit 
               may be idle before the circuit will be cleared.  
               Modifying this object does not require the X.25 
               physical link to be restarted."
           ::= { xX25LinkEntry 3 }

       xX25LinkHoldDownTimer OBJECT-TYPE
           SYNTAX INTEGER (0..255)
           ACCESS read-write
           STATUS mandatory
           DESCRIPTION
               "Length of time in minutes after a virtual circuit 
               has been cleared before it may make a call again.  
               Modifying this object does not require the X.25 
               physical link to be restarted."
           ::= { xX25LinkEntry 4 }

       xX25LinkAccUncfgCalls OBJECT-TYPE
           SYNTAX INTEGER { enabled(1), disabled(2) }
           ACCESS read-write
           STATUS mandatory
           DESCRIPTION
               "Indicates whether unconfigured, non-reverse charged 
               calls will be accepted.  Modifying this object does 
               not require the X.25 physical link to be 
               restarted."
           ::= { xX25LinkEntry 5 }

       xX25LinkDefWindSize OBJECT-TYPE
           SYNTAX INTEGER (1..127)
           ACCESS read-write
           STATUS mandatory
           DESCRIPTION
               "Default packet level window size for this link."
           ::= { xX25LinkEntry 6 }

       xX25LinkMaxWindSize OBJECT-TYPE
           SYNTAX INTEGER (1..127)
           ACCESS read-write
           STATUS mandatory
           DESCRIPTION
               "Maximum packet level window size for this link."
           ::= { xX25LinkEntry 7 }

       xX25LinkDefPktSize OBJECT-TYPE
           SYNTAX INTEGER { bytes16(16),
                            bytes32(32),
                            bytes64(64),
                            bytes128(128),
                            bytes256(256),
                            bytes512(512),
                            bytes1024(1024),
                            bytes2048(2048),
                            bytes4096(4096) }
           ACCESS read-write
           STATUS mandatory
           DESCRIPTION
               "Default packet size for this link."
           ::= { xX25LinkEntry 8 }

       xX25LinkDefThrptClassIn OBJECT-TYPE
           SYNTAX INTEGER { bps75(75),
                            bps150(150),
                            bps300(300),
                            bps600(600),
                            bps1200(1200),
                            bps2400(2400),
                            bps4800(4800),
                            bps9600(9600),
                            bps19200(19200),
                            bps48000(48000) }
           ACCESS read-write
           STATUS mandatory
           DESCRIPTION
               "Default input throughput class for this link."
           ::= { xX25LinkEntry 9 }

       xX25LinkDefThrptClassOut OBJECT-TYPE
           SYNTAX INTEGER { bps75(75),
                            bps150(150),
                            bps300(300),
                            bps600(600),
                            bps1200(1200),
                            bps2400(2400),
                            bps4800(4800),
                            bps9600(9600),
                            bps19200(19200),
                            bps48000(48000) }
           ACCESS read-write
           STATUS mandatory
           DESCRIPTION
               "Default output throughput class for this link."
           ::= { xX25LinkEntry 10 }

       xX25LinkDefThrptClassInMsk OBJECT-TYPE
           SYNTAX INTEGER { bps75(75),
                            bps150(150),
                            bps300(300),
                            bps600(600),
                            bps1200(1200),
                            bps2400(2400),
                            bps4800(4800),
                            bps9600(9600),
                            bps19200(19200),
                            bps48000(48000) }
           ACCESS read-write
           STATUS deprecated
           DESCRIPTION
               "Default incoming throughput class mask for this 
               link."
           ::= { xX25LinkEntry 11 }

       xX25LinkDefThrptClassOutMsk OBJECT-TYPE
           SYNTAX INTEGER { bps75(75),
                            bps150(150),
                            bps300(300),
                            bps600(600),
                            bps1200(1200),
                            bps2400(2400),
                            bps4800(4800),
                            bps9600(9600),
                            bps19200(19200),
                            bps48000(48000) }
           ACCESS read-write
           STATUS deprecated
           DESCRIPTION
               "Default outgoing throughput class mask for this 
               link."
           ::= { xX25LinkEntry 12 }

       xX25LinkFlowCtrlNeg OBJECT-TYPE
           SYNTAX INTEGER { enabled(1), disabled(2) }
           ACCESS read-write
           STATUS mandatory
           DESCRIPTION
               "Indicates whether flow control negotiation will be 
               performed on this link."
           ::= { xX25LinkEntry 13 }

       xX25LinkThrptClassNeg OBJECT-TYPE
           SYNTAX INTEGER { enabled(1), disabled(2) }
           ACCESS read-write
           STATUS mandatory
           DESCRIPTION
               "Indicates whether throughput class negotiation will 
               be performed on this link."
           ::= { xX25LinkEntry 14 }

       xX25LinkICallBarred OBJECT-TYPE
           SYNTAX INTEGER { enabled(1), disabled(2) }
           ACCESS read-write
           STATUS mandatory
           DESCRIPTION
               "Indicates whether incoming calls are barred on this 
               link."
           ::= { xX25LinkEntry 15 }

       xX25LinkOCallBarred OBJECT-TYPE
           SYNTAX INTEGER { enabled(1), disabled(2) }
           ACCESS read-write
           STATUS mandatory
           DESCRIPTION
               "Indicates whether outgoing calls are barred on this 
               link."
           ::= { xX25LinkEntry 16 }

       xX25LinkOneOut OBJECT-TYPE
           SYNTAX INTEGER { enabled(1), disabled(2) }
           ACCESS read-write
           STATUS mandatory
           DESCRIPTION
               "Indicates whether the link supports one way 
               outgoing channels."
           ::= { xX25LinkEntry 17 }

       xX25LinkOneIn OBJECT-TYPE
           SYNTAX INTEGER { enabled(1), disabled(2) }
           ACCESS read-write
           STATUS mandatory
           DESCRIPTION
               "Indicates whether the link supports one way 
               incoming channels."
           ::= { xX25LinkEntry 18 }

       xX25LinkRevChargeAcc OBJECT-TYPE
           SYNTAX INTEGER { enabled(1), disabled(2) }
           ACCESS read-write
           STATUS mandatory
           DESCRIPTION
               "Indicates whether reverse charge acceptance may be 
               configured on this link."
           ::= { xX25LinkEntry 19 }

       xX25LinkLocalChargePrevent OBJECT-TYPE
           SYNTAX INTEGER { enabled(1), disabled(2) }
           ACCESS read-write
           STATUS mandatory
           DESCRIPTION
               "Indicates whether local charge prevention may be 
               configured on the link."
           ::= { xX25LinkEntry 20 }

       xX25LinkRpoa OBJECT-TYPE
           SYNTAX INTEGER { enabled(1), disabled(2) }
           ACCESS read-write
           STATUS mandatory
           DESCRIPTION
               "Indicates whether RPOA may be configured on the 
               link."
           ::= { xX25LinkEntry 21 }

       xX25LinkNui OBJECT-TYPE
           SYNTAX INTEGER { enabled(1), disabled(2) }
           ACCESS read-write
           STATUS mandatory
           DESCRIPTION
               "Indicates whether NUI may be configured on the 
               link."
           ::= { xX25LinkEntry 22 }

       xX25LinkMaxPacketSize OBJECT-TYPE
           SYNTAX INTEGER { bytes16(16),
                            bytes32(32),
                            bytes64(64),
                            bytes128(128),
                            bytes256(256),
                            bytes512(512),
                            bytes1024(1024) }
           ACCESS read-write
           STATUS mandatory
           DESCRIPTION
               "Maximum size of packets on the link."
           ::= { xX25LinkEntry 23 }

       xX25LinkInsertCallingAddr OBJECT-TYPE
           SYNTAX INTEGER { enabled(1), disabled(2) }
           ACCESS read-write
           STATUS mandatory
           DESCRIPTION
               "Indicates whether the caller's X.121 address should 
               be inserted into the the call request packet."
           ::= { xX25LinkEntry 24 }

       xX25LinkDefaultInterface OBJECT-TYPE
           SYNTAX INTEGER
           ACCESS read-write
           STATUS mandatory
           DESCRIPTION
               "The ITouch logical ifIndex to which new SVCs should 
               be attached, when 'accept unconfigured calls' is 
               enabled.  A value of zero means 'create a new 
               interface'."
           ::= { xX25LinkEntry 25 }

END
