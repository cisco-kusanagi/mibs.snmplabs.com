-- Copyright 1993 General DataComm Ind., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive licence to use
-- this Specification in connection with the management of GDC's products.
--
-- This Specification is supplied "AS IS," and GDC makes no warranty,
-- either expressed or implied, as to the use operation, condition, or
-- performance of the Specification.

-- Revision History
-- Version   Date	Name		Description
-- 1.00A     08-May-96  J. Beaujour	initial version of snmp553 alarm mib for text based traps 

SNMP553-ALARM-MIB DEFINITIONS	::= 	BEGIN

IMPORTS
	DisplayString				FROM RFC1213-MIB
	OBJECT-TYPE				FROM RFC-1212
	TRAP-TYPE				FROM RFC-1215
	snmp553s				FROM SNMP553S-MGMT-MIB;

snmp553sTextAlarm        OBJECT IDENTIFIER ::= { snmp553s 9}


-- The Version Group. This group identifies the version information
-- for the MIB.
-- 

snmp553sTextAlarmMIBversion OBJECT-TYPE
    SYNTAX DisplayString (SIZE (5))
    ACCESS read-only
    STATUS mandatory
    DESCRIPTION
        "Identifies the version of the MIB. The format
         of the version is x.yzT, where 'x' identifies
         the major revision number, 'y'identifies the
         minor revision number, 'z' identifies the
         typographical revision, and T identifies the
         test revision.  Acceptable values for the
         individual revision components are
         as follows

                x: 1 - 9
                y: 0 - 9
                z: 0 - 9
                T: A - Z

        Upon formal release, no designation for the test
        revision will be present."
    ::= { snmp553sTextAlarm 1 }

snmp553sTextAlarmGlobal OBJECT-TYPE
     SYNTAX  INTEGER {
     disable(1),
     enable(2)
     }
     ACCESS  read-write
     STATUS  mandatory
     DESCRIPTION
         "This globally enables and disables all text based TRAPs from an
          agent."
    ::= { snmp553sTextAlarm 2 }



snmp553sTextAlarmTable OBJECT-TYPE
    SYNTAX SEQUENCE OF Snmp553sTextAlarmEntry
    ACCESS not-accessible
    STATUS mandatory
    DESCRIPTION
    	"The  snmp553AlarmTable contains entries that report the
	status of alarms.  The status of an alarm indicates whether the
	alarm is currently active or inactive.  This information will
	be determined by the network element depending on the alarm threshold
	configuration.

        The structure of the table is such that alarm status is
        supported on a unit or interface basis, and then on an alarm
        type basis within the interface.  For simplicity sake and to
        support the reporting of status of all alarms, a unit is
        treated as an interface in this table."
    ::= { snmp553sTextAlarm 3 }

snmp553sTextAlarmEntry OBJECT-TYPE
    SYNTAX Snmp553sTextAlarmEntry
    ACCESS not-accessible
    STATUS mandatory
    DESCRIPTION
    	"An entry in the Alarm table."
    INDEX { alarmNumber }
    ::= { snmp553sTextAlarmTable 1 }

Snmp553sTextAlarmEntry ::=
    SEQUENCE {
        alarmNumber	
    	    INTEGER,
        description	
            DisplayString,
    	status
    	    INTEGER
    }

alarmNumber OBJECT-TYPE
    SYNTAX INTEGER
    ACCESS read-only
    STATUS mandatory
    DESCRIPTION
    	"The index value which uniquely identifies the interface to
    	which this entry is applicable."
    ::= { snmp553sTextAlarmEntry 1 }


description  OBJECT-TYPE
        SYNTAX  DisplayString (SIZE (1..32))
        ACCESS  read-only
        STATUS  mandatory
        DESCRIPTION
        "The  Description of the alarm generated."
        ::= { snmp553sTextAlarmEntry 2 }

status OBJECT-TYPE
    SYNTAX INTEGER {
    	inactive(1),
    	active(2)	
    }
    ACCESS read-only
    STATUS mandatory
    DESCRIPTION
    	"The current status of the alarm.  The value inactive(1)
    	indicates that this alarm is currently inactive.  The value
    	active(2) indicates that this alarm is currently active."
    ::= { snmp553sTextAlarmEntry 3 }

-- Alarm Management Related Traps

snmp553sTextAlarmTrap TRAP-TYPE
    ENTERPRISE snmp553s
    VARIABLES { description, status }
    DESCRIPTION    
        "The snmp553 alarm trap.  This trap is set whenever an alarm
        status change occurs to report an alarm.  The variable
        bindings contain the description and status for each alarm that
	changes state.
        Note that the OBJECT IDENTIFIER of the variable contains the
        interface, family type, and alarm type of the alarm encoded
        within.    

        More than one alarm can be sent in the trap, if the network
        element indicates that more than one has changed at the same
        time."
    ::= 1

END
