AVICI-SONET-MIB DEFINITIONS ::= BEGIN

IMPORTS
   MODULE-IDENTITY, OBJECT-TYPE, NOTIFICATION-TYPE,
   Integer32, Unsigned32
      FROM SNMPv2-SMI
   DisplayString
      FROM SNMPv2-TC
   MODULE-COMPLIANCE, OBJECT-GROUP, NOTIFICATION-GROUP
      FROM SNMPv2-CONF
   ifIndex
      FROM IF-MIB
   aviciMibs
      FROM AVICI-SMI
   aviciSysTrapDescr
      FROM AVICI-SYSTEM-MIB;   

aviciSonetMIB MODULE-IDENTITY
   LAST-UPDATED   "000830011500Z"
   ORGANIZATION   "Avici Systems, Inc."
   CONTACT-INFO   "
                  Avici Systems, Inc.
                  101 Billerica Avenue
                  North Billerica, MA 01862-1256
 
                  (978) 964-2000
                  (978) 964-2100 (fax)
 
                  snmp@avici.com"
   DESCRIPTION
      ""
   REVISION      "990330095500Z" 
   DESCRIPTION
      "Created MIB module."
   ::= { aviciMibs 3 }

aviciSonetObjects       OBJECT IDENTIFIER ::= { aviciSonetMIB 1 }

aviciSonetNotifications OBJECT IDENTIFIER ::= { aviciSonetMIB 2 }

aviciSonetNotificationPrefix OBJECT IDENTIFIER ::=
                                  { aviciSonetNotifications 0 }

--******************************************************************************
--* aviciSonetMediumTable                                                      *
--*                                                                            *
--* This table contains extensions to the SONET/SDH medium table defined by    *
--* RFC-1595; Definitions of Managed Objects for the SONET/SDH Interface Type. *
--* The managed objects contained by this table provide additional control of  *
--* the electrical or fiber physical layer of a SONET/SDH interface.           *
--*                                                                            *
--* Observe that this table also serves as a "catch all" for managed objects   *
--* that apply to the medium, section, line, and path entities comprising a    *
--* SONET/SDH interface.                                                       *
--******************************************************************************

aviciSonetMediumTable OBJECT-TYPE
   SYNTAX         SEQUENCE OF AviciSonetMediumEntry
   MAX-ACCESS     not-accessible
   STATUS         current
   DESCRIPTION
      "The Avici SONET/SDH medium table."
   ::= { aviciSonetObjects 1 }

aviciSonetMediumEntry OBJECT-TYPE
   SYNTAX         AviciSonetMediumEntry
   MAX-ACCESS     not-accessible
   STATUS         current
   DESCRIPTION
      "An entry in the Avici SONET/SDH medium table."
   INDEX          { ifIndex }
   ::= { aviciSonetMediumTable 1 }

AviciSonetMediumEntry ::=
   SEQUENCE {
      aviciSonetMediumFramingType           INTEGER,
      aviciSonetMediumLoopbackMode          INTEGER,
      aviciSonetMediumClockSource           INTEGER
   }

aviciSonetMediumFramingType OBJECT-TYPE
   SYNTAX         INTEGER
                     {
                     sonet(1),
                     sdh(2)
                     }
   MAX-ACCESS     read-write
   STATUS         current
   DESCRIPTION    
      "This variable specifies the type of framing used by the interface."
   DEFVAL { sonet }
   ::= { aviciSonetMediumEntry 1 }

aviciSonetMediumLoopbackMode OBJECT-TYPE
   SYNTAX         INTEGER
                     {
                     none(1),
                     line (2),
                     internal(3)
                     }
   MAX-ACCESS     read-write
   STATUS         current
   DESCRIPTION    
      "This variable specifies whether the interface is in a loopback mode
      of operation.  Furthermore, if the interface is in a loopback mode of
      operation, then this variable specifies the type of loopback being
      applied to the interface.  A line loopback is an externally applied
      loopback.  For example, the SONET/SDH MUX can provide a loopback for the
      interface.  This type of loopback is a line loopback.  An internal 
      loopback is an internally applied loopback.  Typically the interface's
      PHY controller provides an interface's internal loopback."
   DEFVAL { none }
   ::= { aviciSonetMediumEntry 2 }

aviciSonetMediumClockSource OBJECT-TYPE
   SYNTAX         INTEGER
                     {
                     line(1),
                     interface(2)
                     }
   MAX-ACCESS     read-write
   STATUS         current
   DESCRIPTION    
      "This variable specifies the origin of the clock being used by the
      interface's PHY controller.  If the interface is using the line as its
      clock source, then it derives the clock from the inbound signal.  If the
      interface is using the interface as its clock source, then it derives
      the clock internally."
   DEFVAL { interface }
   ::= { aviciSonetMediumEntry 3 }

--******************************************************************************
--* aviciSonetSectionTable                                                     *
--*                                                                            *
--* This table contains extensions to the SONET/SDH medium table defined by    *
--* RFC-1595, Definitions of Managed Objects for the SONET/SDH Interface Type. *
--* The managed objects contained by this table provide additional control of  *
--* the section entity associated with a SONET/SDH interface.                  *
--*                                                                            *
--* 3/26/01 achung                                                             *
--*    (1) Change aviciSonetSectionJ0 to aviciSonetTxSectionJ0 and Integer32   *
--*        to DisplayString                                                    *
--*    (2) Added aviciSonetRxSectionJ0 display string                          *
--******************************************************************************

aviciSonetSectionTable OBJECT-TYPE
   SYNTAX         SEQUENCE OF AviciSonetSectionEntry
   MAX-ACCESS     not-accessible
   STATUS         current
   DESCRIPTION
      "The Avici SONET/SDH section table."
   ::= { aviciSonetObjects 2 }

aviciSonetSectionEntry OBJECT-TYPE
   SYNTAX         AviciSonetSectionEntry
   MAX-ACCESS     not-accessible
   STATUS         current
   DESCRIPTION
      "An entry in the Avici SONET/SDH section table."
   INDEX          { ifIndex }
   ::= { aviciSonetSectionTable 1 }

AviciSonetSectionEntry ::=
   SEQUENCE {
      aviciSonetTxSectionJ0                 DisplayString,
      aviciSonetSectionThresholdES          Unsigned32,
      aviciSonetSectionThresholdSES         Unsigned32,
      aviciSonetSectionThresholdSEFS        Unsigned32,
      aviciSonetSectionThresholdCV          Unsigned32,
      aviciSonetSectionEventEnable          Integer32,
      aviciSonetSectionEventStatus          Integer32,
      aviciSonetSectionEventIndex           Integer32,
      aviciSonetSectionCurrentFailures      Integer32, 
      aviciSonetRxSectionJ0                 DisplayString
   }

aviciSonetTxSectionJ0 OBJECT-TYPE
   SYNTAX         DisplayString (SIZE(0..16))
   MAX-ACCESS     read-create
   STATUS         current
   DESCRIPTION
      "This variable specifies the value to which the section entity sets the
      J0 byte of the SONET/SDH section overhead for all outbound frames."
   ::= { aviciSonetSectionEntry 1 }

aviciSonetSectionThresholdES OBJECT-TYPE
   SYNTAX         Unsigned32 (1..900)
   MAX-ACCESS     read-create
   STATUS         current
   DESCRIPTION    
      "This variable specifies a threshold for the number of Errored Seconds
      encountered by the SONET/SDH section entity in the current fifteen
      minute interval.  If the value of sonetSectionCurrentESs becomes greater
      than or equal to this value in the current fifteen minute interval, then
      a single aviciSonetSectionEvent notification will be generated."
   DEFVAL { 1 }
   ::= { aviciSonetSectionEntry 2 }

aviciSonetSectionThresholdSES OBJECT-TYPE
   SYNTAX         Unsigned32 (1..900)
   MAX-ACCESS     read-create
   STATUS         current
   DESCRIPTION    
      "This variable specifies a threshold for the number of Severely Errored
      Seconds encountered by the SONET/SDH section entity in the current
      fifteen minute interval.  If the value of sonetSectionCurrentSESs becomes
      greater than or equal to this value in the current fifteen minute interval,
      then a single aviciSonetSectionEvent notification will be generated."
   DEFVAL { 1 }
   ::= { aviciSonetSectionEntry 3 }

aviciSonetSectionThresholdSEFS OBJECT-TYPE
   SYNTAX         Unsigned32 (1..900)
   MAX-ACCESS     read-create
   STATUS         current
   DESCRIPTION    
      "This variable specifies a threshold for the number of Severely Errored
      Framing Seconds encountered by the SONET/SDH section entity in the current
      fifteen minute interval.  If the value of sonetSectionCurrentSEFSs becomes
      greater than or equal to this value in the current fifteen minute
      interval, then a single aviciSonetSectionEvent notification will be
      generated."
   DEFVAL { 1 }
   ::= { aviciSonetSectionEntry 4 }

aviciSonetSectionThresholdCV OBJECT-TYPE
   SYNTAX         Unsigned32 (1..4294967295)
   MAX-ACCESS     read-create
   STATUS         current
   DESCRIPTION    
      "This variable specifies a threshold for the number of Coding Violations
      encountered by the SONET/SDH section entity in the current fifteen minute
      interval.  If the value of sonetSectionCurrentCVs becomes greater
      than or equal to this value in the current fifteen minute interval, then
      a single aviciSonetSectionEvent notification will be generated."
   DEFVAL { 1 }
   ::= { aviciSonetSectionEntry 5 }

aviciSonetSectionEventEnable OBJECT-TYPE
   SYNTAX         Integer32 (0..511)
   MAX-ACCESS     read-create
   STATUS         current
   DESCRIPTION    
      "This variable specifies the type of events that will be generated for
      this corresponding SONET/SDH section entity.  The value represents a
      vector of bits, each controlling a unique event:

         - Bit 0   Rising threshold alarm, sonetSectionCurrentESs.
         - Bit 1   Rising threshold alarm, sonetSectionCurrentSESs.
         - Bit 2   Rising threshold alarm, sonetSectionCurrentSEFSs.
         - Bit 3   Rising threshold alarm, sonetSectionCurrentCVs.
         - Bit 4   Reserved.
         - Bit 5   LOS failure indication.
         - Bit 6   LOS failure cleared.
         - Bit 7   LOF failure indication.
         - Bit 8   LOF failure cleared.
      "
   DEFVAL { 0 }
   ::= { aviciSonetSectionEntry 6 }

aviciSonetSectionEventStatus OBJECT-TYPE
   SYNTAX         Integer32 (0..511)
   MAX-ACCESS     accessible-for-notify
   STATUS         current
   DESCRIPTION    
      "This variable specifies which events have occurred in the current 15
      minute interval.  The value represents a vector of bits, each specifying
      a unique event:

         - Bit 0   Rising threshold alarm, sonetSectionCurrentESs.
         - Bit 1   Rising threshold alarm, sonetSectionCurrentSESs.
         - Bit 2   Rising threshold alarm, sonetSectionCurrentSEFSs.
         - Bit 3   Rising threshold alarm, sonetSectionCurrentCVs.
         - Bit 4   Reserved.
         - Bit 5   LOS failure indication.
         - Bit 6   LOS failure cleared.
         - Bit 7   LOF failure indication.
         - Bit 8   LOF failure cleared.
      "
   ::= { aviciSonetSectionEntry 7 }

aviciSonetSectionEventIndex OBJECT-TYPE
   SYNTAX         Integer32 (0..65535)
   MAX-ACCESS     read-create
   STATUS         current
   DESCRIPTION    
      "The index of the eventEntry that is used when one of the following
      events concerning the section entity has occurred:

         -  The value sonetSectionCurrentESs has crossed the threshold
            specified by aviciSonetSectionThresholdES.

         -  The value sonetSectionCurrentSESs has crossed the threshold
            specified by aviciSonetSectionThresholdSES.

         -  The value sonetSectionCurrentSEFSs has crossed the threshold
            specified by aviciSonetSectionThresholdSEFS.

         -  The value sonetSectionCurrentCVs has crossed the threshold
            specified by aviciSonetSectionThresholdCV.

         -  The SONET/SDH section entity has experienced a loss of signal
            (LOS) failure.

         -  The SONET/SDH section entity has cleared the LOS failure
            condition.

         -  The SONET/SDH section entity has experienced a loss of frame
            (LOF) failure.

         -  The SONET/SDH section entity has cleared the LOF failure
            condition.

      The eventEntry identified by a particular value of this index is the
      same as identified by the same value of the eventindex object.  If 
      there is no corresponding entry in the eventTable, then no association
      exists.  In particular, if this value is zero, no associated event will
      be generated, as zero is not a valid event index."
   DEFVAL { 0 }
   ::= { aviciSonetSectionEntry 8 }

aviciSonetSectionCurrentFailures OBJECT-TYPE
   SYNTAX         Integer32 (0..511)       
   MAX-ACCESS     read-only
   STATUS         current
   DESCRIPTION    
      "This variable specifies which failures have occurred. A value of zero
       means no failures have occurred. The value represents a vector of bits, 
       each specifying a unique failure:

         - Bit 0   No Failure
         - Bit 1   LOS failure.
         - Bit 2   LOF failure indication.
      "
   ::= { aviciSonetSectionEntry 9 }

aviciSonetRxSectionJ0 OBJECT-TYPE
   SYNTAX         DisplayString (SIZE(0..16))
   MAX-ACCESS     read-only
   STATUS         current
   DESCRIPTION
      "This variable specifies the value to which the section entity sets the
      J0 byte of the SONET/SDH section overhead for the last frame received 
      by this interface."
   ::= { aviciSonetSectionEntry 10 }


--******************************************************************************
--* aviciSonetLineTable                                                        *
--******************************************************************************

aviciSonetLineTable OBJECT-TYPE
   SYNTAX         SEQUENCE OF AviciSonetLineEntry
   MAX-ACCESS     not-accessible
   STATUS         current
   DESCRIPTION
      "The Avici SONET/SDH line table."
   ::= { aviciSonetObjects 3 }

aviciSonetLineEntry OBJECT-TYPE
   SYNTAX         AviciSonetLineEntry
   MAX-ACCESS     not-accessible
   STATUS         current
   DESCRIPTION
      "An entry in the Avici SONET/SDH line table."
   INDEX          { ifIndex }
   ::= { aviciSonetLineTable 1 }

AviciSonetLineEntry ::=
   SEQUENCE {
      aviciSonetLineS1                      Integer32,
      aviciSonetLineAPS                     Integer32,
      aviciSonetLineThresholdES             Unsigned32,
      aviciSonetLineThresholdSES            Unsigned32,
      aviciSonetLineThresholdCV             Unsigned32,
      aviciSonetLineThresholdUAS            Unsigned32,
      aviciSonetLineEventEnable             Integer32,
      aviciSonetLineEventStatus             Integer32,
      aviciSonetLineEventIndex              Integer32,
      aviciSonetLineCurrentFailures         Integer32
   }

aviciSonetLineS1 OBJECT-TYPE
   SYNTAX         Integer32 (0..255)
   MAX-ACCESS     read-create
   STATUS         current
   DESCRIPTION    
      "This variable specifies the value to which the line entity sets the
      S1 byte of the SONET/SDH line overhead for all outbound frames."
   DEFVAL { 0 }
   ::= { aviciSonetLineEntry 1 }

aviciSonetLineAPS OBJECT-TYPE
   SYNTAX         Integer32 (0..65535)
   MAX-ACCESS     read-create
   STATUS         current
   DESCRIPTION    
      "This variable specifies the value to which the line entity sets the
      K1 and K2 bytes of the SONET/SDH line overhead for all outbound frames."
   DEFVAL { 0 }
   ::= { aviciSonetLineEntry 2 }

aviciSonetLineThresholdES OBJECT-TYPE
   SYNTAX         Unsigned32 (1..900)
   MAX-ACCESS     read-create
   STATUS         current
   DESCRIPTION    
      "This variable specifies a threshold for the number of Errored Seconds
      encountered by the SONET/SDH line entity in the current fifteen minute
      interval.  If the value of sonetLineCurrentESs becomes greater
      than or equal to this value in the current fifteen minute interval, then
      a single aviciSonetLineEvent notification will be generated."
   DEFVAL { 1 }
   ::= { aviciSonetLineEntry 3 }

aviciSonetLineThresholdSES OBJECT-TYPE
   SYNTAX         Unsigned32 (1..900)
   MAX-ACCESS     read-create
   STATUS         current
   DESCRIPTION    
      "This variable specifies a threshold for the number of Severely Errored
      Seconds encountered by the SONET/SDH line entity in the current fifteen
      minute interval.  If the value of sonetLineCurrentSESs becomes greater
      than or equal to this value in the current fifteen minute interval, then
      a single aviciSonetLineEvent notification will be generated."
   DEFVAL { 1 }
   ::= { aviciSonetLineEntry 4 }

aviciSonetLineThresholdCV OBJECT-TYPE
   SYNTAX         Unsigned32 (1..4294967295)
   MAX-ACCESS     read-create
   STATUS         current
   DESCRIPTION    
      "This variable specifies a threshold for the number of Coding Violations
      encountered by the SONET/SDH line entity in the current fifteen minute
      interval.  If the value of sonetLineCurrentCVs becomes greater
      than or equal to this value in the current fifteen minute interval, then
      a single aviciSonetLineEvent notification will be generated."
   DEFVAL { 1 }
   ::= { aviciSonetLineEntry 5 }

aviciSonetLineThresholdUAS OBJECT-TYPE
   SYNTAX         Unsigned32 (1..900)
   MAX-ACCESS     read-create
   STATUS         current
   DESCRIPTION    
      "This variable specifies a threshold for the number of Unavailable
      Seconds encountered by a SONET/SDH line entity in the current fifteen
      minute interval.  If the value of sonetLineCurrentUASs becomes greater
      than or equal to this value in the current fifteen minute interval, then
      a single aviciSonetLineEvent notification will be generated."
   DEFVAL { 1 }
   ::= { aviciSonetLineEntry 6 }

aviciSonetLineEventEnable OBJECT-TYPE
   SYNTAX         Integer32 (0..511)
   MAX-ACCESS     read-create
   STATUS         current
   DESCRIPTION    
      "This variable specifies the type of events that will be generated for
      this corresponding SONET/SDH line entity.  The value represents a
      vector of bits, each controlling a unique event:

         - Bit 0   Rising threshold alarm, sonetSectionCurrentESs.
         - Bit 1   Rising threshold alarm, sonetSectionCurrentSESs.
         - Bit 2   Reserved.
         - Bit 3   Rising threshold alarm, sonetSectionCurrentCVs.
         - Bit 4   Rising threshold alarm, sonetSectionCurrentUASs.
         - Bit 5   AIS failure indication.
         - Bit 6   AIS failure cleared.
         - Bit 7   RFI indication.
         - Bit 8   RFI cleared.
      "
   DEFVAL { 0 }
   ::= { aviciSonetLineEntry 7 }

aviciSonetLineEventStatus OBJECT-TYPE
   SYNTAX         Integer32 (0..511)
   MAX-ACCESS     accessible-for-notify
   STATUS         current
   DESCRIPTION    
      "This variable specifies which events have occurred in the current 15
      minute interval.  The value represents a vector of bits, each specifying
      a unique event:

         - Bit 0   Rising threshold alarm, sonetLineCurrentESs.
         - Bit 1   Rising threshold alarm, sonetLineCurrentSESs.
         - Bit 2   Reserved.
         - Bit 3   Rising threshold alarm, sonetLineCurrentCVs.
         - Bit 4   Rising threshold alarm, sonetLineCurrentUASs.
         - Bit 5   AIS failure indication.
         - Bit 6   AIS failure cleared.
         - Bit 7   RFI indication.
         - Bit 8   RFI cleared.
      "
   ::= { aviciSonetLineEntry 8 }

aviciSonetLineEventIndex OBJECT-TYPE
   SYNTAX         Integer32 (0..65535)
   MAX-ACCESS     read-create
   STATUS         current
   DESCRIPTION    
      "The index of the eventEntry that is used when one of the following
      events concerning the line entity has occurred:

         -  The value sonetLineCurrentESs has crossed the threshold
            specified by aviciSonetLineThresholdES.

         -  The value sonetLineCurrentSESs has crossed the threshold
            specified by aviciSonetLineThresholdSES.

         -  The value sonetLineCurrentCVs has crossed the threshold
            specified by aviciSonetLineThresholdCV.

         -  The value sonetLineCurrentUASs has crossed the threshold
            specified by aviciSonetLineThresholdUAS.

         -  The SONET/SDH line entity has experienced an alarm indication
            signal (AIS) failure.

         -  The SONET/SDH line entity has cleared the AIS failure condition.

         -  The SONET/SDH line entity has experienced a remote failure
            indication (RFI).

         -  The SONET/SDH line entity has cleared the RFI condition.

      The eventEntry identified by a particular value of this index is the
      same as identified by the same value of the eventindex object.  If 
      there is no corresponding entry in the eventTable, then no association
      exists.  In particular, if this value is zero, no associated event will
      be generated, as zero is not a valid event index."
   DEFVAL { 0 }
   ::= { aviciSonetLineEntry 9 }

aviciSonetLineCurrentFailures OBJECT-TYPE
   SYNTAX         Integer32 (0..511) 
   MAX-ACCESS     read-only
   STATUS         current
   DESCRIPTION    
      "This variable specifies which failures have occurred. A value of zero
       means no failures have occurred. The value represents a vector of bits, 
       each specifying a unique failure:

         - Bit 0   No Failures
         - Bit 1   AIS failure indication.
         - Bit 2   RFI indication.
      "
   ::= { aviciSonetLineEntry 10 }

--******************************************************************************
--* aviciSonetFarEndLineTable                                                  *
--******************************************************************************

aviciSonetFarEndLineTable OBJECT-TYPE
   SYNTAX         SEQUENCE OF AviciSonetFarEndLineEntry
   MAX-ACCESS     not-accessible
   STATUS         current
   DESCRIPTION
      "The Avici SONET/SDH far end line table."
   ::= { aviciSonetObjects 4 }

aviciSonetFarEndLineEntry OBJECT-TYPE
   SYNTAX         AviciSonetFarEndLineEntry
   MAX-ACCESS     not-accessible
   STATUS         current
   DESCRIPTION
      "An entry in the Avici SONET/SDH far end line table."
   INDEX          { ifIndex }
   ::= { aviciSonetFarEndLineTable 1 }

AviciSonetFarEndLineEntry ::=
   SEQUENCE {
      aviciSonetFarEndLineThresholdES       Unsigned32,
      aviciSonetFarEndLineThresholdSES      Unsigned32,
      aviciSonetFarEndLineThresholdCV       Unsigned32,
      aviciSonetFarEndLineThresholdUAS      Unsigned32,
      aviciSonetFarEndLineEventEnable       Integer32,
      aviciSonetFarEndLineEventStatus       Integer32,
      aviciSonetFarEndLineEventIndex        Integer32
   }

aviciSonetFarEndLineThresholdES OBJECT-TYPE
   SYNTAX         Unsigned32 (1..900)
   MAX-ACCESS     read-create
   STATUS         current
   DESCRIPTION    
      "This variable specifies a threshold for the number of Far End Errored
      Seconds encountered by the SONET/SDH line entity in the current fifteen 
      minute interval.  If the value of sonetFarEndLineCurrentESs becomes
      greater than or equal to this value in the current fifteen minute
      interval, then a single aviciSonetFarEndLineEvent notification will
      be generated."
   DEFVAL { 1 }
   ::= { aviciSonetFarEndLineEntry 1 }

aviciSonetFarEndLineThresholdSES OBJECT-TYPE
   SYNTAX         Unsigned32 (1..900)
   MAX-ACCESS     read-create
   STATUS         current
   DESCRIPTION    
      "This variable specifies a threshold for the number of Far End Severely
      Errored Seconds encountered by the SONET/SDH line entity in the current
      fifteen minute interval.  If the value of sonetFarEndLineCurrentSESs
      becomes greater than or equal to this value in the current fifteen minute
      interval, then a single aviciSonetFarEndLineEvent notification will
      be generated."
   DEFVAL { 1 }
   ::= { aviciSonetFarEndLineEntry 2 }

aviciSonetFarEndLineThresholdCV OBJECT-TYPE
   SYNTAX         Unsigned32 (1..4294967295)
   MAX-ACCESS     read-create
   STATUS         current
   DESCRIPTION    
      "This variable specifies a threshold for the number of Far End Coding
      Violations encountered by the SONET/SDH line entity in the current
      fifteen minute interval.  If the value of sonetFarEndLineCurrentCVs
      becomes greater than or equal to this value in the current fifteen
      minute interval, then a single aviciSonetFarEndLineEvent notification
      will be generated."
   DEFVAL { 1 }
   ::= { aviciSonetFarEndLineEntry 3 }

aviciSonetFarEndLineThresholdUAS OBJECT-TYPE
   SYNTAX         Unsigned32 (1..900)
   MAX-ACCESS     read-create
   STATUS         current
   DESCRIPTION    
      "This variable specifies a threshold for the number of Far End
      Unavailable Seconds encountered by a SONET/SDH line entity in the
      current fifteen minute interval.  If the value of
      sonetFarEndLineCurrentUASs becomes greater than or equal to this
      value in the current fifteen minute interval, then a single
      aviciSonetFarEndLineEvent notification will be generated."
   DEFVAL { 1 }
   ::= { aviciSonetFarEndLineEntry 4 }

aviciSonetFarEndLineEventEnable OBJECT-TYPE
   SYNTAX         Integer32 (0..32)
   MAX-ACCESS     read-create
   STATUS         current
   DESCRIPTION    
      "This variable specifies the type of events that will be generated for
      this corresponding SONET/SDH far-end line entity.  The value represents
      a vector of bits, each controlling a unique event:

         - Bit 0   Rising threshold alarm, sonetSectionCurrentESs.
         - Bit 1   Rising threshold alarm, sonetSectionCurrentSESs.
         - Bit 2   Reserved.
         - Bit 3   Rising threshold alarm, sonetSectionCurrentCVs.
         - Bit 4   Rising threshold alarm, sonetSectionCurrentUASs.
      "
   DEFVAL { 0 }
   ::= { aviciSonetFarEndLineEntry 5 }

aviciSonetFarEndLineEventStatus OBJECT-TYPE
   SYNTAX         Integer32 (0..32)
   MAX-ACCESS     accessible-for-notify
   STATUS         current
   DESCRIPTION    
      "This variable specifies which events have occurred in the current 15
      minute interval.  The value represents a vector of bits, each specifying
      a unique event:

         - Bit 0   Rising threshold alarm, sonetFarEndLineCurrentESs.
         - Bit 1   Rising threshold alarm, sonetFarEndLineCurrentSESs.
         - Bit 2   Reserved.
         - Bit 3   Rising threshold alarm, sonetFarEndLineCurrentCVs.
         - Bit 4   Rising threshold alarm, sonetFarEndLineCurrentUASs.
      "
   ::= { aviciSonetFarEndLineEntry 6 }

aviciSonetFarEndLineEventIndex OBJECT-TYPE
   SYNTAX         Integer32 (0..65535)
   MAX-ACCESS     read-create
   STATUS         current
   DESCRIPTION    
      "The index of the eventEntry that is used when one of the following
      events concerning the far-end line entity has occurred:

         -  The value sonetFarEndLineCurrentESs has crossed the threshold
            specified by aviciSonetFarEndLineThresholdES.

         -  The value sonetFarEndLineCurrentSESs has crossed the threshold
            specified by aviciSonetFarEndLineThresholdSES.

         -  The value sonetFarEndLineCurrentCVs has crossed the threshold
            specified by aviciSonetFarEndLineThresholdCV.

         -  The value sonetFarEndLineCurrentUASs has crossed the threshold
            specified by aviciSonetFarEndLineThresholdUAS.

      The eventEntry identified by a particular value of this index is the
      same as identified by the same value of the eventindex object.  If 
      there is no corresponding entry in the eventTable, then no association
      exists.  In particular, if this value is zero, no associated event will
      be generated, as zero is not a valid event index."
   DEFVAL { 0 }
   ::= { aviciSonetFarEndLineEntry 7 }

--******************************************************************************
--* aviciSonetPathTable                                                        *
--******************************************************************************

aviciSonetPathTable OBJECT-TYPE
   SYNTAX         SEQUENCE OF AviciSonetPathEntry
   MAX-ACCESS     not-accessible
   STATUS         current
   DESCRIPTION
      "The Avici SONET/SDH path table."
   ::= { aviciSonetObjects 5 }

aviciSonetPathEntry OBJECT-TYPE
   SYNTAX         AviciSonetPathEntry
   MAX-ACCESS     not-accessible
   STATUS         current
   DESCRIPTION
      "An entry in the Avici SONET/SDH path table."
   INDEX          { ifIndex }
   ::= { aviciSonetPathTable 1 }

AviciSonetPathEntry ::=
   SEQUENCE {
      aviciSonetPathC2                      Integer32,
      aviciSonetPathTxTrace                 DisplayString,
      aviciSonetPathRxTrace                 DisplayString,
      aviciSonetPathThresholdES             Unsigned32,
      aviciSonetPathThresholdSES            Unsigned32,
      aviciSonetPathThresholdCV             Unsigned32,
      aviciSonetPathThresholdUAS            Unsigned32,
      aviciSonetPathEventEnable             Integer32,
      aviciSonetPathEventStatus             Integer32,
      aviciSonetPathEventIndex              Integer32,
      aviciSonetPathCurrentFailures         Integer32
   }

aviciSonetPathC2 OBJECT-TYPE
   SYNTAX         Integer32 (0..255)
   MAX-ACCESS     read-create
   STATUS         current
   DESCRIPTION    
      "This variable specifies the value to which the path entity sets the
      C2 byte of the SONET/SDH path overhead for all outbound frames."
   DEFVAL { 0 }
   ::= { aviciSonetPathEntry 1 }

aviciSonetPathTxTrace OBJECT-TYPE
   SYNTAX         DisplayString (SIZE (64))
   MAX-ACCESS     read-create
   STATUS         current
   DESCRIPTION    
      "This variable specifies the value to which the path entity sets the
      trace field of the SONET/SDH path overhead for all outbound frames."
   ::= { aviciSonetPathEntry 2 }

aviciSonetPathRxTrace OBJECT-TYPE
   SYNTAX         DisplayString (SIZE (64))
   MAX-ACCESS     read-only
   STATUS         current
   DESCRIPTION    
      "This variable specifies the value of the trace field of the SONET/SDH
      path overhead for the last frame received by this interface."
   ::= { aviciSonetPathEntry 3 }


aviciSonetPathThresholdES OBJECT-TYPE
   SYNTAX         Unsigned32 (1..900)
   MAX-ACCESS     read-create
   STATUS         current
   DESCRIPTION    
      "This variable specifies a threshold for the number of Errored Seconds
      encountered by the SONET/SDH path entity in the current fifteen minute
      interval.  If the value of sonetPathCurrentESs becomes greater
      than or equal to this value in the current fifteen minute interval, then
      a single aviciSonetPathEvent notification will be generated."
   DEFVAL { 1 }
   ::= { aviciSonetPathEntry 4 }

aviciSonetPathThresholdSES OBJECT-TYPE
   SYNTAX         Unsigned32 (1..900)
   MAX-ACCESS     read-create
   STATUS         current
   DESCRIPTION    
      "This variable specifies a threshold for the number of Severely Errored
      Seconds encountered by the SONET/SDH path entity in the current fifteen
      minute interval.  If the value of sonetPathCurrentSESs becomes greater
      than or equal to this value in the current fifteen minute interval, then
      a single aviciSonetPathEvent notification will be generated."
   DEFVAL { 1 }
   ::= { aviciSonetPathEntry 5 }

aviciSonetPathThresholdCV OBJECT-TYPE
   SYNTAX         Unsigned32 (1..4294967295)
   MAX-ACCESS     read-create
   STATUS         current
   DESCRIPTION    
      "This variable specifies a threshold for the number of Coding Violations
      encountered by the SONET/SDH path entity in the current fifteen minute
      interval.  If the value of sonetPathCurrentCVs becomes greater
      than or equal to this value in the current fifteen minute interval, then
      a single aviciSonetPathEvent notification will be generated."
   DEFVAL { 1 }
   ::= { aviciSonetPathEntry 6 }

aviciSonetPathThresholdUAS OBJECT-TYPE
   SYNTAX         Unsigned32 (1..900)
   MAX-ACCESS     read-create
   STATUS         current
   DESCRIPTION    
      "This variable specifies a threshold for the number of Unavailable
      Seconds encountered by a SONET/SDH path entity in the current fifteen
      minute interval.  If the value of sonetPathCurrentUASs becomes greater
      than or equal to this value in the current fifteen minute interval, then
      a single aviciSonetPathEvent notification will be generated."
   DEFVAL { 1 }
   ::= { aviciSonetPathEntry 7 }

aviciSonetPathEventEnable OBJECT-TYPE
   SYNTAX         Integer32 (0..32767)
   MAX-ACCESS     read-create
   STATUS         current
   DESCRIPTION    
      "This variable specifies the type of events that will be generated for
      this corresponding SONET/SDH path entity.  The value represents a
      vector of bits, each controlling a unique event:

         - Bit 0   Rising threshold alarm, sonetSectionCurrentESs.
         - Bit 1   Rising threshold alarm, sonetSectionCurrentSESs.
         - Bit 2   Reserved.
         - Bit 3   Rising threshold alarm, sonetSectionCurrentCVs.
         - Bit 4   Rising threshold alarm, sonetSectionCurrentUASs.
         - Bit 5   LOP failure indication.
         - Bit 6   LOP failure cleared.
         - Bit 7   AIS failure indication.
         - Bit 8   AIS failure cleared.
         - Bit 9   RFI indication.
         - Bit 10  RFI cleared.
         - Bit 11  UNEQ failure indication.
         - Bit 12  UNEQ failure cleared.
         - Bit 13  PLM failure indication.
         - Bit 14  PLM failure cleared.
      "
   DEFVAL { 0 }
   ::= { aviciSonetPathEntry 8 }

aviciSonetPathEventStatus OBJECT-TYPE
   SYNTAX         Integer32 (0..32767)
   MAX-ACCESS     accessible-for-notify
   STATUS         current
   DESCRIPTION    
      "This variable specifies which events have occurred in the current 15
      minute interval.  The value represents a vector of bits, each specifying
      a unique event:

         - Bit 0   Rising threshold alarm, sonetPathCurrentESs.
         - Bit 1   Rising threshold alarm, sonetPathCurrentSESs.
         - Bit 2   Reserved.
         - Bit 3   Rising threshold alarm, sonetPathCurrentCVs.
         - Bit 4   Rising threshold alarm, sonetPathCurrentUASs.
         - Bit 5   LOP failure indication.
         - Bit 6   LOP failure cleared.
         - Bit 7   AIS failure indication.
         - Bit 8   AIS failure cleared.
         - Bit 9   RFI indication.
         - Bit 10  RFI cleared.
         - Bit 11  UNEQ failure indication.
         - Bit 12  UNEQ failure cleared.
         - Bit 13  PLM failure indication.
         - Bit 14  PLM failure cleared.
      "
   ::= { aviciSonetPathEntry 9 }

aviciSonetPathEventIndex OBJECT-TYPE
   SYNTAX         Integer32 (0..65535)
   MAX-ACCESS     read-create
   STATUS         current
   DESCRIPTION    
      "The index of the eventEntry that is used when one of the following
      events concerning the path entity has occurred:

         -  The value sonetPathCurrentESs has crossed the threshold
            specified by aviciSonetPathThresholdES.

         -  The value sonetPathCurrentSESs has crossed the threshold
            specified by aviciSonetPathThresholdSES.

         -  The value sonetPathCurrentCVs has crossed the threshold
            specified by aviciSonetPathThresholdCV.

         -  The value sonetPathCurrentUASs has crossed the threshold
            specified by aviciSonetPathThresholdUAS.

         -  The SONET/SDH path entity has experienced a loss of pointer
            (LOP) failure.

         -  The SONET/SDH path entity has cleared the LOP failure condition.

         -  The SONET/SDH path entity has experienced an alarm indication signal
            (AIS) failure.

         -  The SONET/SDH path entity has cleared the AIS failure condition.

         -  The SONET/SDH path entity has experienced a remote defect indication
            (RFI).

         -  The SONET/SDH path entity has cleared the RFI condition.

         -  The SONET/SDH path entity has experienced an unequipped failure
            (UNEQ) failure.

         -  The SONET/SDH path entity has cleared the UNEQ failure condition.

         -  The SONET/SDH path entity has experienced a path label mismatch
            (PLM) failure.

         -  The SONET/SDH path entity has cleared the PLM failure condition.

      The eventEntry identified by a particular value of this index is the
      same as identified by the same value of the eventindex object.  If 
      there is no corresponding entry in the eventTable, then no association
      exists.  In particular, if this value is zero, no associated event will
      be generated, as zero is not a valid event index."
   DEFVAL { 0 }
   ::= { aviciSonetPathEntry 10 }

aviciSonetPathCurrentFailures OBJECT-TYPE
   SYNTAX         Integer32 (0..511) 
   MAX-ACCESS     read-only
   STATUS         current
   DESCRIPTION    
      "This variable specifies which failures have occurred. A value of zero
       means no failures have occurred. The value represents a vector of bits, 
       each specifying a unique failure:

         - Bit 0   No Failures    
         - Bit 1   LOP failure indication.
         - Bit 2   AIS failure indication.
         - Bit 3   RFI indication.
         - Bit 4   UNEQ failure indication.
         - Bit 5   PLM failure indication.
      "
   ::= { aviciSonetPathEntry 11 }

--******************************************************************************
--* aviciSonetFarEndPathTable                                                  *
--******************************************************************************

aviciSonetFarEndPathTable OBJECT-TYPE
   SYNTAX         SEQUENCE OF AviciSonetFarEndPathEntry
   MAX-ACCESS     not-accessible
   STATUS         current
   DESCRIPTION
      "The Avici SONET/SDH far end path table."
   ::= { aviciSonetObjects 6 }

aviciSonetFarEndPathEntry OBJECT-TYPE
   SYNTAX         AviciSonetFarEndPathEntry
   MAX-ACCESS     not-accessible
   STATUS         current
   DESCRIPTION
      "An entry in the Avici SONET/SDH far end path table."
   INDEX          { ifIndex }
   ::= { aviciSonetFarEndPathTable 1 }

AviciSonetFarEndPathEntry ::=
   SEQUENCE {
      aviciSonetFarEndPathThresholdES       Unsigned32,
      aviciSonetFarEndPathThresholdSES      Unsigned32,
      aviciSonetFarEndPathThresholdCV       Unsigned32,
      aviciSonetFarEndPathThresholdUAS      Unsigned32,
      aviciSonetFarEndPathEventEnable       Integer32,
      aviciSonetFarEndPathEventStatus       Integer32,
      aviciSonetFarEndPathEventIndex        Integer32
   }

aviciSonetFarEndPathThresholdES OBJECT-TYPE
   SYNTAX         Unsigned32 (1..900)
   MAX-ACCESS     read-create
   STATUS         current
   DESCRIPTION    
      "This variable specifies a threshold for the number of Far End Errored
      Seconds encountered by the SONET/SDH path entity in the current 15 minute
      interval.  If the value of sonetFarEndPathCurrentESs becomes greater
      than or equal to this value in the current fifteen minute interval, then
      a single aviciSonetFarEndPathEvent notification will be generated."
   DEFVAL { 1 }
   ::= { aviciSonetFarEndPathEntry 1 }

aviciSonetFarEndPathThresholdSES OBJECT-TYPE
   SYNTAX         Unsigned32 (1..900)
   MAX-ACCESS     read-create
   STATUS         current
   DESCRIPTION    
      "This variable specifies a threshold for the number of Far End Severely
      Errored Seconds encountered by the SONET/SDH path entity in the current
      fifteen minute interval.  If the value of sonetFarEndPathCurrentSESs
      becomes greater than or equal to this value in the current fifteen minute
      interval, then a single aviciSonetFarEndPathEvent notification will be
      generated."
   DEFVAL { 1 }
   ::= { aviciSonetFarEndPathEntry 2 }

aviciSonetFarEndPathThresholdCV OBJECT-TYPE
   SYNTAX         Unsigned32 (1..4294967295)
   MAX-ACCESS     read-create
   STATUS         current
   DESCRIPTION    
      "This variable specifies a threshold for the number of Far End Coding
      Violations encountered by the SONET/SDH path entity in the current
      fifteen minute interval.  If the value of sonetFarEndPathCurrentCVs
      becomes greater than or equal to this value in the current fifteen
      minute interval, then a single aviciSonetFarEndPathEvent notification
      will be generated."
   DEFVAL { 1 }
   ::= { aviciSonetFarEndPathEntry 3 }

aviciSonetFarEndPathThresholdUAS OBJECT-TYPE
   SYNTAX         Unsigned32 (1..900)
   MAX-ACCESS     read-create
   STATUS         current
   DESCRIPTION    
      "This variable specifies a threshold for the number of Far End
      Unavailable Seconds encountered by a SONET/SDH path entity in the
      current fifteen minute interval.  If the value of
      sonetFarEndPathCurrentUASs becomes greater than or equal to this
      value in the current fifteen minute interval, then a single
      aviciSonetFarEndPathEvent notification will be generated."
   DEFVAL { 1 }
   ::= { aviciSonetFarEndPathEntry 4 }

aviciSonetFarEndPathEventEnable OBJECT-TYPE
   SYNTAX         Integer32 (0..32)
   MAX-ACCESS     read-create
   STATUS         current
   DESCRIPTION    
      "This variable specifies the type of events that will be generated for
      this corresponding SONET/SDH far-end path entity.  The value represents a
      vector of bits, each controlling a unique event:

         - Bit 0   Rising threshold alarm, sonetSectionCurrentESs.
         - Bit 1   Rising threshold alarm, sonetSectionCurrentSESs.
         - Bit 2   Reserved.
         - Bit 3   Rising threshold alarm, sonetSectionCurrentCVs.
         - Bit 4   Rising threshold alarm, sonetSectionCurrentUASs.
      "
   DEFVAL { 0 }
   ::= { aviciSonetFarEndPathEntry 5 }

aviciSonetFarEndPathEventStatus OBJECT-TYPE
   SYNTAX         Integer32 (0..32)
   MAX-ACCESS     accessible-for-notify
   STATUS         current
   DESCRIPTION    
      "This variable specifies which events have occurred in the current 15
      minute interval.  The value represents a vector of bits, each specifying
      a unique event:

         - Bit 0   Rising threshold alarm, sonetFarEndPathCurrentESs.
         - Bit 1   Rising threshold alarm, sonetFarEndPathCurrentSESs.
         - Bit 2   Reserved.
         - Bit 3   Rising threshold alarm, sonetFarEndPathCurrentCVs.
         - Bit 4   Rising threshold alarm, sonetFarEndPathCurrentUASs.
      "
   ::= { aviciSonetFarEndPathEntry 6 }

aviciSonetFarEndPathEventIndex OBJECT-TYPE
   SYNTAX         Integer32 (0..65535)
   MAX-ACCESS     read-create
   STATUS         current
   DESCRIPTION    
      "The index of the eventEntry that is used when one of the following
      events concerning the far-end path entity has occurred:

         -  The value sonetPathCurrentESs has crossed the threshold
            specified by aviciSonetPathThresholdES.

         -  The value sonetPathCurrentSESs has crossed the threshold
            specified by aviciSonetPathThresholdSES.

         -  The value sonetPathCurrentCVs has crossed the threshold
            specified by aviciSonetPathThresholdCV.

         -  The value sonetPathCurrentUASs has crossed the threshold
            specified by aviciSonetPathThresholdUAS.

      The eventEntry identified by a particular value of this index is the
      same as identified by the same value of the eventindex object.  If 
      there is no corresponding entry in the eventTable, then no association
      exists.  In particular, if this value is zero, no associated event will
      be generated, as zero is not a valid event index."
   DEFVAL { 0 }
   ::= { aviciSonetFarEndPathEntry 7 }

--******************************************************************************
--* Notifications                                                              *
--******************************************************************************

aviciSonetSectionEvent NOTIFICATION-TYPE
   OBJECTS        {
                  ifIndex,
                  aviciSonetSectionEventStatus,
                  aviciSonetSectionEventIndex,
                  aviciSysTrapDescr
                  }
   STATUS         current
   DESCRIPTION    
      "An interfaces generates this notification when one of the
      following events occur:

      1)  One of the performance counters maintained by the section entity
          associated with a SONET/SDH interface has crossed an established
          threshold.
          
      2)  The section entity associated with a SONET/SDH interface
          experiences a failure.

      3)  The section entity associated with a SONET/SDH interface
          clears a failure condition.

      The interface only generates a notification for one of these events
      if the corresponding enable bit is set to one in the instance of
      aviciSonetSectionEventEnable associated with the interface.  "
   ::= { aviciSonetNotificationPrefix 1 }

aviciSonetLineEvent NOTIFICATION-TYPE
   OBJECTS        {
                  ifIndex,
                  aviciSonetLineEventStatus,
                  aviciSonetLineEventIndex,
                  aviciSysTrapDescr
                  }
   STATUS         current
   DESCRIPTION    
      "An interfaces generates this notification when one of the
      following events occur:

      1)  One of the performance counters maintained by the line entity
          associated with a SONET/SDH interface has crossed an established
          threshold.
          
      2)  The line entity associated with a SONET/SDH interface
          experiences a failure.

      3)  The line entity associated with a SONET/SDH interface
          clears a failure condition.

      The interface only generates a notification for one of these events
      if the corresponding enable bit is set to one in the instance of
      aviciSonetLineEventEnable associated with the interface."
   ::= { aviciSonetNotificationPrefix 2 }

aviciSonetFarEndLineEvent NOTIFICATION-TYPE
   OBJECTS        {
                  ifIndex,
                  aviciSonetFarEndLineEventStatus,
                  aviciSonetFarEndLineEventIndex,
                  aviciSysTrapDescr
                  }
   STATUS         current
   DESCRIPTION    
      "An interfaces generates this notification when one of the
      following events occur:

      1)  One of the performance counters maintained by the far-end line
          entity associated with a SONET/SDH interface has crossed an
          established threshold.
          
      2)  The far-end line entity associated with a SONET/SDH interface
          experiences a failure.

      3)  The far-end line entity associated with a SONET/SDH interface
          clears a failure condition.

      The interface only generates a notification for one of these events
      if the corresponding enable bit is set to one in the instance of
      aviciSonetFarEndLineEventEnable associated with the interface."
   ::= { aviciSonetNotificationPrefix 3 }

aviciSonetPathEvent NOTIFICATION-TYPE
   OBJECTS        {
                  ifIndex,
                  aviciSonetPathEventStatus,
                  aviciSonetPathEventIndex,
                  aviciSysTrapDescr
                  }
   STATUS         current
   DESCRIPTION    
      "An interfaces generates this notification when one of the
      following events occur:

      1)  One of the performance counters maintained by the path entity
          associated with a SONET/SDH interface has crossed an established
          threshold.
          
      2)  The path entity associated with a SONET/SDH interface
          experiences a failure.

      3)  The path entity associated with a SONET/SDH interface
          clears a failure condition.

      The interface only generates a notification for one of these events
      if the corresponding enable bit is set to one in the instance of
      aviciSonetPathEventEnable associated with the interface."
   ::= { aviciSonetNotificationPrefix 4 }

aviciSonetFarEndPathEvent NOTIFICATION-TYPE
   OBJECTS        {
                  ifIndex,
                  aviciSonetFarEndPathEventStatus,
                  aviciSonetFarEndPathEventIndex,
                  aviciSysTrapDescr
                  }
   STATUS         current
   DESCRIPTION    
      "An interfaces generates this notification when one of the
      following events occur:

      1)  One of the performance counters maintained by the far-end path
          entity associated with a SONET/SDH interface has crossed an
          established threshold.
          
      2)  The far-end path entity associated with a SONET/SDH interface
          experiences a failure.

      3)  The far-end path entity associated with a SONET/SDH interface
          clears a failure condition.

      The interface only generates a notification for one of these events
      if the corresponding enable bit is set to one in the instance of
      aviciSonetFarEndPathEventEnable associated with the interface."
   ::= { aviciSonetNotificationPrefix 5 }

--
-- Conformance Information
--    

aviciSonetMIBConformance OBJECT IDENTIFIER ::= { aviciSonetMIB 3 }
aviciSonetMIBCompliances OBJECT IDENTIFIER ::= { aviciSonetMIBConformance 1 }
aviciSonetMIBGroups OBJECT IDENTIFIER ::= { aviciSonetMIBConformance 2 }

aviciSonetMIBCompliance MODULE-COMPLIANCE
        STATUS current
        DESCRIPTION
            "The compliance statement for aviciSonet."
        MODULE
        MANDATORY-GROUPS {
            aviciSonetGroup,
            aviciSonetPathGroup,
            aviciSonetNotificationGroup,
            aviciSonetPathNotificationGroup
        }
        ::= { aviciSonetMIBCompliances 1 }

aviciSonetGroup OBJECT-GROUP
        OBJECTS {
            aviciSonetMediumFramingType,
            aviciSonetMediumLoopbackMode,
            aviciSonetMediumClockSource,
            aviciSonetTxSectionJ0,
            aviciSonetRxSectionJ0,
            aviciSonetSectionThresholdES,
            aviciSonetSectionThresholdSES,
            aviciSonetSectionThresholdSEFS,
            aviciSonetSectionThresholdCV,
            aviciSonetSectionEventEnable,
            aviciSonetSectionEventStatus,
            aviciSonetSectionEventIndex,
            aviciSonetLineS1,
            aviciSonetLineAPS,
            aviciSonetLineThresholdES,
            aviciSonetLineThresholdSES,
            aviciSonetLineThresholdCV,
            aviciSonetLineThresholdUAS,
            aviciSonetLineEventEnable,
            aviciSonetLineEventStatus,
            aviciSonetLineEventIndex,
            aviciSonetFarEndLineThresholdES,
            aviciSonetFarEndLineThresholdSES,
            aviciSonetFarEndLineThresholdCV,
            aviciSonetFarEndLineThresholdUAS,
            aviciSonetFarEndLineEventEnable,
            aviciSonetFarEndLineEventStatus,
            aviciSonetFarEndLineEventIndex           
        }           
        STATUS     current
        DESCRIPTION
            "Objects for the SONET layer."
        ::= { aviciSonetMIBGroups 1 }

aviciSonetPathGroup OBJECT-GROUP
        OBJECTS {
           aviciSonetPathC2,
           aviciSonetPathTxTrace,
           aviciSonetPathRxTrace,
           aviciSonetPathThresholdES,
           aviciSonetPathThresholdSES,
           aviciSonetPathThresholdCV,
           aviciSonetPathThresholdUAS,
           aviciSonetPathEventEnable,
           aviciSonetPathEventStatus,
           aviciSonetPathEventIndex,
           aviciSonetFarEndPathThresholdES,
           aviciSonetFarEndPathThresholdSES,
           aviciSonetFarEndPathThresholdCV,
           aviciSonetFarEndPathThresholdUAS,
           aviciSonetFarEndPathEventEnable,
           aviciSonetFarEndPathEventStatus,
           aviciSonetFarEndPathEventIndex
        }           
        STATUS     current
        DESCRIPTION
            "Objects for the SONET Path layer."
        ::= { aviciSonetMIBGroups 2 }
           
aviciSonetNotificationGroup NOTIFICATION-GROUP
        NOTIFICATIONS {
             aviciSonetSectionEvent,
             aviciSonetLineEvent,
             aviciSonetFarEndLineEvent
        }
        STATUS     current
        DESCRIPTION
            "Notifications for SONET events."
        ::= { aviciSonetMIBGroups 3 }

aviciSonetPathNotificationGroup NOTIFICATION-GROUP
        NOTIFICATIONS {
             aviciSonetPathEvent,
             aviciSonetFarEndPathEvent
        }
        STATUS     current
        DESCRIPTION
            "Notifications for SONET Path events."
        ::= { aviciSonetMIBGroups 4 }

END
