--	Quantum Bridge QBSONET Management Information Base
--	Version 1.0.0
--	October 15, 2000
--
--	Quantum Bridge Corporation
--	One High Street
--	North Andover, MA 01845
--	(978) 688-9100
--
----------------------------------------------------------------------------------------
----------------------------------------------------------------------------------------
--
	QB-SONET-MIB DEFINITIONS ::= BEGIN

	IMPORTS 
	MODULE-IDENTITY, OBJECT-TYPE, Counter32, Gauge32, Counter64
		FROM SNMPv2-SMI
	TEXTUAL-CONVENTION
		FROM SNMPv2-TC
	sonetMediumEntry
		FROM SONET-MIB 
	MODULE-COMPLIANCE, OBJECT-GROUP
		FROM SNMPv2-CONF
	qbMibs
		FROM QUANTUMBRIDGE-REG
	ifIndex
		FROM IF-MIB
    ;    

    qbSonetMIB MODULE-IDENTITY
    LAST-UPDATED "0011141434Z" -- May 22, 2000
    ORGANIZATION "Quantum Bridge Inc."
    CONTACT-INFO
	    "mvaysman@quantumbridge.com"
    DESCRIPTION
        "This module defines additional objects for management of SONET 
        links in Quantum Bridge devices, above and beyond what is defined in the
        standard SONET mib."
    ::= { qbMibs 6 }

 QbSonetType ::= TEXTUAL-CONVENTION
        STATUS        current
	DESCRIPTION
            "Defines whether SONET, SDH/VC12, SDHDS1/VC11, SONET/M13 signal
		is used across the chassis/slot."
	SYNTAX      INTEGER {
		    sonetVT15(1),
		    sdhVC12(2),
		    sdhVC11(3),
		    sonetM13(4),
		    unknown(5)
	}

    -- Top-level organization of the MIB


    qbSonetObjects          OBJECT IDENTIFIER ::= { qbSonetMIB 1 }
    qbSonetTables	    OBJECT IDENTIFIER ::= { qbSonetMIB 2 }
    qbSonetConformance      OBJECT IDENTIFIER ::= { qbSonetMIB 3 }

  qbSonetAlarmMode        OBJECT-TYPE
        SYNTAX      INTEGER {
		    enabled(1),
		    disabled(2),
		    unknown(3)
	}
        MAX-ACCESS  read-write
        STATUS      current
        DESCRIPTION
            "Setting this object causes enabling or disabling 
	    optical ports alarms(LOS, LF, SD or SF). At initial start
	    up time all optical ports are enabled. The user can
	    change the port state to 'disabled' if there are not connections 
	    configured on the port.
	    Upon configuring the first active connection
        to the optical port, the system automatically enables the port 
	    alarms. This object is used in conjunction with
	    qbSonetSlot object which defines a scope of the configuration parameter: 
	    chassis wide or slot wide.
	    enabled(1) - enables alarms on the selected slot or
		       chassis.
	    disabled(2) - disables alarms on the dormant optical ports
	    of the selected slot or chassis.
	   When read, the value of the object is always 'unknown(3)'
	   This parameter is applied to WAN622, S622, and Q155 cards."	       
	DEFVAL       { enabled }     
    ::= { qbSonetObjects 1 }

   qbSonetScramblingMode        OBJECT-TYPE
        SYNTAX      INTEGER {
		    enabled(1),
		    disabled(2),
		    unknown(3)
	}
        MAX-ACCESS  read-write
        STATUS      current
        DESCRIPTION
		"Setting this object defines whether ATM cell payload 
		is enabled or disabled. 
		At initial start up time scrambling is set to 'enabled(1)'
		This object is used in conjunction with
		qbSonetSlot object which defines a scope of the configuration 
		parameter:  chassis wide or slot wide.
		enabled(1) - enables alarms on the selected slot or
			     chassis.
		disabled(2) - disables alarms on the dormant optical ports
			      of the selected slot or chassis.
		When read, the value of the object is alwayd  'unknown(3)'
		This parameter is applied to WAN622, S622, and Q155 cards."
	DEFVAL       { enabled }    
    ::= { qbSonetObjects 2 }

  qbSonetMediumType  OBJECT-TYPE
        SYNTAX      QbSonetType
        MAX-ACCESS  read-write
        STATUS      current
        DESCRIPTION
		"Setting this object defines whether SONET, SDH,
		SDHDS1, or SONETM13 signal
		is used across the chassis/slot.
		At initial start up the object is set to 'sonet(1)'
		This object is used in conjunction with
		qbSonetSlot object which defines a scope of the configuration parameter: 
		chassis wide or slot wide.
		sonet(1) - sets signal format to 'sonet'.
		sdh(2) -   sets signal format to 'sdh/VC12'
		sdhDs1(2) - sets signal format to 'sdh/VC11'
		sonetM13(2) - sets signal format to 'sonet/M13 payload'
			When read, the value of the object is always 'unknown(3)'
			This parameter is applied to D155VT/VC-T."
	DEFVAL       { sonetVT15 }    
    ::= { qbSonetObjects 3 }

   qbSonetSlot      OBJECT-TYPE
        SYNTAX      INTEGER(0..14)
        MAX-ACCESS  read-write
        STATUS      current
        DESCRIPTION
            "This object defines a scope of the applied configuration
	    parameter. If the object is set to non-zero value all 
	    ports of the defined slot are configured. When object is
	    set to 0, this setting is applied to all applicable
	    optical cards."  
	DEFVAL { 0 }    
    ::= { qbSonetObjects 4 }

   -- *************************************** 
   -- Extensions to the SONET 'Medium' Table
   -- ***************************************

    qbSonetMediumTable        OBJECT-TYPE
        SYNTAX      SEQUENCE OF QbSonetMediumEntry
        MAX-ACCESS  not-accessible
        STATUS      current
        DESCRIPTION
            "The Quantum Bridge SONET Medium table contains extensions to
             the SONET Medium table."
    ::= { qbSonetTables 1 }

    qbSonetMediumEntry        OBJECT-TYPE
       SYNTAX      QbSonetMediumEntry
       MAX-ACCESS  not-accessible
       STATUS      current
       DESCRIPTION
            "An entry in the Quantum Bridge SONET Medium table."
       AUGMENTS    { sonetMediumEntry }
       ::= { qbSonetMediumTable 1 }

    QbSonetMediumEntry ::=
       SEQUENCE {
		qbSonetPortTxClockSource      INTEGER,
		qbSonetPortScramblingMode     INTEGER,
		qbSonetPortAlarmMode          INTEGER,
		qbSonetPortMediumType         QbSonetType
     }

     qbSonetPortTxClockSource OBJECT-TYPE
          SYNTAX  INTEGER {
                     local(1),
                     recovered(2)
                 }
          MAX-ACCESS  read-write
          STATUS  deprecated
          DESCRIPTION
                 "The source of Transmit Clock.

                 recovered indicates that the recovered receive clock
                 is used as the transmit clock.

                 local indicates that a local clock source is
                 used."
               DEFVAL { local }
               ::= { qbSonetMediumEntry 1 }

    qbSonetPortScramblingMode OBJECT-TYPE
        SYNTAX      INTEGER {  
                    enabled(1),
                    disabled(2)
            }
    MAX-ACCESS  read-write
    STATUS      current
    DESCRIPTION
        "The scrambling mode of the sonet interface."
    ::= { qbSonetMediumEntry 2 }

  qbSonetPortAlarmMode OBJECT-TYPE
        SYNTAX      INTEGER {  
                    enabled(1),
                    disabled(2)
            }
    MAX-ACCESS  read-write
    STATUS      current
    DESCRIPTION
        "The alarm mode of the sonet interface."
    ::= { qbSonetMediumEntry 3 }

    qbSonetPortMediumType OBJECT-TYPE
        SYNTAX      QbSonetType
        MAX-ACCESS  read-write
        STATUS      current
        DESCRIPTION
		"Setting this object defines whether SONET, SDH,
		SDHDS1, or SONETM13 signal
		is used across the chassis/slot.
		At initial start up the object is set to 'sonet(1)'
		This object is used in conjunction with
		qbSonetSlot object which defines a scope of the configuration parameter: 
		chassis wide or slot wide.
		sonet(1) - sets signal format to 'sonet'.
		sdh(2) -   sets signal format to 'sdh/VC12'
		sdhDs1(2) - sets signal format to 'sdh/VC11'
		sonetM13(2) - sets signal format to 'sonet/M13 payload'
			When read, the value of the object is always 'unknown(3)'
			This parameter is applied to D155VT/VC-T."
	DEFVAL       { sonetVT15 }    
    ::= { qbSonetMediumEntry 4 }

   -- *************************************** 
   -- SONET Statistics Table
   -- ***************************************

    qbSonetStatTable        OBJECT-TYPE
        SYNTAX      SEQUENCE OF QbSonetStatEntry
        MAX-ACCESS  not-accessible
        STATUS      current
        DESCRIPTION
            "The Quantum Bridge SONET Stat table contains SONET statistics."
    ::= { qbSonetTables 2 }

    qbSonetStatEntry        OBJECT-TYPE
       SYNTAX      QbSonetStatEntry
       MAX-ACCESS  not-accessible
       STATUS      current
       DESCRIPTION
            "An entry in the Quantum Bridge SONET Stat table."
       INDEX   { ifIndex }
       ::= { qbSonetStatTable 1 }

    QbSonetStatEntry ::=
       SEQUENCE {
		qbSonetSectionBIP		Counter32,
		qbSonetLineBIP			Counter32,
		qbSonetPathBIP			Counter32
     }

  qbSonetSectionBIP OBJECT-TYPE
    SYNTAX      Counter32  
    MAX-ACCESS  read-only
    STATUS      current
    DESCRIPTION
        "This object gives the number of section bit
        interleaved parity erorrs."
    ::= { qbSonetStatEntry 1 }
 
   qbSonetLineBIP OBJECT-TYPE
    SYNTAX      Counter32  
    MAX-ACCESS  read-only
    STATUS      current
    DESCRIPTION
        "This object gives the number of line bit
        interleaved parity erorrs."
    ::= { qbSonetStatEntry 2 }

  qbSonetPathBIP OBJECT-TYPE
    SYNTAX      Counter32  
    MAX-ACCESS  read-only
    STATUS      current
    DESCRIPTION
        "This object gives the number of path bit
        interleaved parity erorrs."
    ::= { qbSonetStatEntry 3 }
 
-- ****************************************************************
-- Conformance Information
-- ****************************************************************

qbSonetCompliances OBJECT IDENTIFIER ::= { qbSonetConformance 1 }
qbSonetGroups      OBJECT IDENTIFIER ::= { qbSonetConformance 2 }

--
-- Compliance Statements
--

qbSonetCompliance MODULE-COMPLIANCE
    STATUS      current
    DESCRIPTION
        "The compliance statement for all agents that support this
        MIB. A compliant agent implements all objects defined in this
        MIB."
    MODULE  -- this module
    MANDATORY-GROUPS {
        qbSonetAllGroup
    }
    ::= { qbSonetCompliances 1 }

--
-- All Object Groups
--
qbSonetAllGroup OBJECT-GROUP
    OBJECTS { 
      qbSonetAlarmMode,  
  	  qbSonetScramblingMode,
  	  qbSonetMediumType,
  	  qbSonetSlot,
      qbSonetPortTxClockSource,
      qbSonetPortScramblingMode,
      qbSonetPortAlarmMode
    }
    STATUS      current
    DESCRIPTION
        "The set of all accessible objects in this MIB."
    ::= { qbSonetGroups 1 }

END
