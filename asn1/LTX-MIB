------------------------------------------------------------------------------
------------------------------------------------------------------------------
--
-- File         : ltx.mib
-- Description  : Private MIB for Lantronix Products
-- By           : Robert Winter, Xact Inc.
-- Version      : 1.0/1     
-- Date         : May 3, 1996    
-- 
--
-- Copyright (c) 1996 Lantronix.  All Rights Reserved.
--
-- Reproduction of this document is authorized on condition that this
-- copyright notice is included.  This Lantronix SNMP MIB Specification
-- embodies Lantronix's proprietary intellectual property.  Lantronix
-- retains all title and ownership in the specification, including any
-- revisions.
--
-- It is Lantronix's intent to encourage the widespread use of this
-- specification in connection with the management of Lantronix's
-- products.  Lantronix grants vendor, end-users, and other interested
-- parties a non-exclusive license to use this specification in
-- connection with the management of Lantronix's products.
--
-- This specification is supplied "AS IS", and Lantronix makes no
-- warranty, either express or implied, as to the use, operations,
-- condition, or performance of this specification.
--
-- Copyright text courtesy of S. Rotenstein.
--
-- If you have any questions about this MIB, please call Lantronix
-- Technical Support Center at 1-714-453-3990 or email to 
-- ts@lantronix.com.  Additional information is available from
-- Lantronix's WWW site, www.lantronix.com and their FTP server at
-- ftp.lantronix.com.
--
-- Products (Agents) supporting this MIB:
--     LRP (Lantronix RMON Probe), version B1.1/1 or higher.
--
------------------------------------------------------------------------------
-- Groups in the LTXMIB
--
-- The following groups are supported for the LRP:
--
-- Active....
--    ltxLRPCommInfo     Permits the user to configure the communities
--    ltxLRPHostInfo     Permits the user to configure the hosts
--    ltxLRPGroupInfo    Permits the user to configure groups by port
--    ltxLRPMaxInfo      Permits the user to configure maximum parameters
--    ltxLRPRoverInfo	 Permits the user to configure the Rover thresholds
--    ltxLRPMiscInfo     Permits the user to configure miscellaneous stuff
--
-- Planned...
--    ltxLRPBadPkt       Bad packet source identifier group
--    ltxLRPEnetIPMap    Ethernet to IP address mapping group
--    ltxLRPTopNProt     TopN protocols group
--    ltxLRPDupIPDet     Duplicate IP detection group
--    ltxLRPNewIPDet     New IP detection group
--    ltxLRPIPChgDet     IP change detection group
--
--
------------------------------------------------------------------------------
------------------------------------------------------------------------------
        LTX-MIB DEFINITIONS ::= BEGIN

        IMPORTS                
            OBJECT-TYPE                          FROM RFC-1212
            enterprises,
            Counter, TimeTicks, IpAddress        FROM RFC1155-SMI
            mib-2,
            DisplayString                        FROM RFC1213-MIB;


        --  Lantronix MIBs for their devices
        --     LNA (Lantronix Network Analyzer - LNA2/LNA6)
        --     LRP (Lantronix RMON Probe - LRP2/LRP6)
        --     LSW (Lantronix SWitch - LSW10/18)
      
        ltx         OBJECT IDENTIFIER ::= { enterprises 244 }  

        ltxlna      OBJECT IDENTIFIER ::= { ltx 10 }  
        ltxlrp      OBJECT IDENTIFIER ::= { ltx 11 }  
        ltxlsw      OBJECT IDENTIFIER ::= { ltx 12 }  

        -- textual conventions

        OwnerString ::= DisplayString
        -- This data type is used to model an administratively
        -- assigned name of the owner of a resource. This
        -- information is taken from the NVT ASCII character set.
        -- It is suggested that this name contain one or more
        -- of the following:
        -- IP address, management station name, network manager's
        -- name, location, or phone number.
        -- In some cases the agent itself will be the owner of
        -- an entry.  In these cases, this string shall be set
        -- to a string starting with 'monitor'.
        --
        -- SNMP access control is articulated entirely in terms of
        -- the contents of MIB views; access to a particular SNMP
        -- object instance depends only upon its presence or
        -- absence in a particular MIB view and never upon its
        -- value or the value of related object instances. Thus,
        -- objects of this type afford resolution of resource
        -- contention only among cooperating managers; they
        -- realize no access control function with respect
        -- to uncooperative parties.
        --
        -- By convention, objects with this syntax are declared
        -- as having
        --
        --      SIZE (0..127)


        --
        -- LTX (Lantronix) Enterprise MIB Extensions
        -- Robert L. Winter, Xact Inc.
        --

        ltxLRPCommInfo      OBJECT IDENTIFIER ::= { ltxlrp 1 }  
        ltxLRPHostInfo      OBJECT IDENTIFIER ::= { ltxlrp 2 }  
        ltxLRPGroupInfo     OBJECT IDENTIFIER ::= { ltxlrp 3 }  
        ltxLRPMaxInfo       OBJECT IDENTIFIER ::= { ltxlrp 4 }  
        ltxLRPRoverInfo     OBJECT IDENTIFIER ::= { ltxlrp 5 }  
		ltxLRPMiscInfo		OBJECT IDENTIFIER ::= { ltxlrp 6 }

		ltxLRPBadPkt		OBJECT IDENTIFIER ::= { ltxlrp 7 }
		ltxLRPEnetIPMap		OBJECT IDENTIFIER ::= { ltxlrp 8 }
		ltxLRPTopNProt		OBJECT IDENTIFIER ::= { ltxlrp 9 }
		ltxLRPDupIPDet		OBJECT IDENTIFIER ::= { ltxlrp 10 }
		ltxLRPNewIPDet		OBJECT IDENTIFIER ::= { ltxlrp 11 }
		ltxLRPIPChgDet		OBJECT IDENTIFIER ::= { ltxlrp 12 }
      

        --
        -- Lantronix LTX LRP Extension MIB, Communtiy Information             
        -- Robert Winter, Xact Inc., March 15, 1996    
        --
        
        
        commInfoTable OBJECT-TYPE
            SYNTAX SEQUENCE OF CommInfoEntry
            ACCESS not-accessible
            STATUS mandatory
            DESCRIPTION
                "A list of LTX Configuration Community Entries "
            ::= { ltxLRPCommInfo 1 }
            
        commInfoEntry OBJECT-TYPE
            SYNTAX CommInfoEntry
            ACCESS not-accessible
            STATUS mandatory
            DESCRIPTION
                "A list of Community properties for the LTX LRP"
            INDEX { commInfoIndex }
            ::= { commInfoTable 1 }
            
        CommInfoEntry ::= SEQUENCE {
            commInfoIndex                 INTEGER (1..65535),
            commInfoName                  DisplayString,
            commInfoGet                   INTEGER,
            commInfoSet                   INTEGER,
            commInfoTrap                  INTEGER
        }
        
        commInfoIndex OBJECT-TYPE
            SYNTAX INTEGER (1..65535)
            ACCESS read-write
            STATUS mandatory
            DESCRIPTION
                "An index that uniquely identifies an entry in the
            LTX LRP Community Info Table."
            ::= { commInfoEntry 1 }
            
        commInfoName OBJECT-TYPE
            SYNTAX DisplayString
            ACCESS read-write
            STATUS mandatory
            DESCRIPTION
                "The name of this LTX LRP Community Entry."
            ::= { commInfoEntry 2 }
            
        commInfoGet OBJECT-TYPE
            SYNTAX INTEGER
            ACCESS read-write
            STATUS mandatory
            DESCRIPTION
                "The GET permission for the community."
            ::= { commInfoEntry 3 }
            
        commInfoSet OBJECT-TYPE
            SYNTAX INTEGER
            ACCESS read-write
            STATUS mandatory
            DESCRIPTION
                "The SET permission for the community."
            ::= { commInfoEntry 4 }
            
        commInfoTrap OBJECT-TYPE
            SYNTAX INTEGER
            ACCESS read-write
            STATUS mandatory
            DESCRIPTION
                "The TRAP permission for the community."
            ::= { commInfoEntry 5 }
            

        --
        -- Lantronix LTX LRP Extension MIB, Host Information             
        -- Robert Winter, Xact Inc., March 15, 1996    
        --
        
        
        hostInfoTable OBJECT-TYPE
            SYNTAX SEQUENCE OF HostInfoEntry
            ACCESS not-accessible
            STATUS mandatory
            DESCRIPTION
                "A list of LTX Configuration Host Entries "
            ::= { ltxLRPHostInfo 1 }
            
        hostInfoEntry OBJECT-TYPE
            SYNTAX HostInfoEntry
            ACCESS not-accessible
            STATUS mandatory
            DESCRIPTION
                "A list of Host properties for the LTX LRP"
            INDEX { hostInfoIndex }
            ::= { hostInfoTable 1 }
            
        HostInfoEntry ::= SEQUENCE {
            hostInfoIndex                 INTEGER (1..65535),
            hostInfoName                  DisplayString,
            hostInfoIP                    IpAddress,
            hostInfoComm                  DisplayString
        }
        
        hostInfoIndex OBJECT-TYPE
            SYNTAX INTEGER (1..65535)
            ACCESS read-write
            STATUS mandatory
            DESCRIPTION
                "An index that uniquely identifies an entry in the
            LTX LRP Host Info Table."
            ::= { hostInfoEntry 1 }
            
        hostInfoName OBJECT-TYPE
            SYNTAX DisplayString
            ACCESS read-write
            STATUS mandatory
            DESCRIPTION
                "The name of this LTX LRP Host Entry."
            ::= { hostInfoEntry 2 }
            
        hostInfoIP OBJECT-TYPE
            SYNTAX IpAddress
            ACCESS read-write
            STATUS mandatory
            DESCRIPTION
                "The IP Address for the host."
            ::= { hostInfoEntry 3 }
            
        hostInfoComm OBJECT-TYPE
            SYNTAX DisplayString
            ACCESS read-write
            STATUS mandatory
            DESCRIPTION
                "The name of the community this host belongs to."
            ::= { hostInfoEntry 4 }
            

        --
        -- Lantronix LTX LRP Extension MIB, MIB Group Information             
        -- Robert Winter, Xact Inc., March 15, 1996    
        --
        
        
        groupInfoTable OBJECT-TYPE
            SYNTAX SEQUENCE OF GroupInfoEntry
            ACCESS not-accessible
            STATUS mandatory
            DESCRIPTION
                "A list of LTX Configuration Group Entries "
            ::= { ltxLRPGroupInfo 1 }
            
        groupInfoEntry OBJECT-TYPE
            SYNTAX GroupInfoEntry
            ACCESS not-accessible
            STATUS mandatory
            DESCRIPTION
                "A list of Group properties for the LTX LRP"
            INDEX { groupInfoIndex }
            ::= { groupInfoTable 1 }
            
        GroupInfoEntry ::= SEQUENCE {
            groupInfoIndex                INTEGER (1..65535),
            groupInfoCapFilt              INTEGER,      
            groupInfoHostTopN             INTEGER,                    
            groupInfoMatrix               INTEGER
        }
        
        groupInfoIndex OBJECT-TYPE
            SYNTAX INTEGER (1..65535)
            ACCESS read-write
            STATUS mandatory
            DESCRIPTION
                "An index that uniquely identifies an entry in the
            LTX LRP MIB Group Info Table."
            ::= { groupInfoEntry 1 }
            
        groupInfoCapFilt OBJECT-TYPE
            SYNTAX INTEGER
            ACCESS read-write
            STATUS mandatory
            DESCRIPTION
                "The toggle for the LTX LRP Group Capture/Filter Entry."
            ::= { groupInfoEntry 2 }

        groupInfoHostTopN OBJECT-TYPE
            SYNTAX INTEGER
            ACCESS read-write
            STATUS mandatory
            DESCRIPTION
                "The toggle for the LTX LRP Group Host/HostTopN Entry."
            ::= { groupInfoEntry 3 }

        groupInfoMatrix OBJECT-TYPE
            SYNTAX INTEGER
            ACCESS read-write
            STATUS mandatory
            DESCRIPTION
                "The toggle for the LTX LRP Group Matrix Entry."
            ::= { groupInfoEntry 4 }
            
            
        --
        -- Lantronix LTX LRP Extension MIB, RMON Maximum Information         
        -- Robert Winter, Xact Inc., March 15, 1996    
        --

        maxHTS OBJECT-TYPE
            SYNTAX  INTEGER (1..8192)
            ACCESS  read-write
            STATUS  mandatory
            DESCRIPTION
                    "The maximum number of Host Table entries."
            ::= { ltxLRPMaxInfo 1 }
  
        maxMTS OBJECT-TYPE
            SYNTAX  INTEGER (1..8192)
            ACCESS  read-write
            STATUS  mandatory
            DESCRIPTION
                    "The maximum number of Matrix Table entries."
            ::= { ltxLRPMaxInfo 2 }

        maxBuckets OBJECT-TYPE
            SYNTAX  INTEGER (1..8192)
            ACCESS  read-write
            STATUS  mandatory
            DESCRIPTION
                    "The maximum number of History buckets."
            ::= { ltxLRPMaxInfo 3 }

        maxLogs OBJECT-TYPE
            SYNTAX  INTEGER (1..10)
            ACCESS  read-write
            STATUS  mandatory
            DESCRIPTION
                    "The maximum number of Event Logs."
            ::= { ltxLRPMaxInfo 4 }

        maxTopN OBJECT-TYPE
            SYNTAX  INTEGER (1..8192)
            ACCESS  read-write
            STATUS  mandatory
            DESCRIPTION
                    "The maximum number of HostTopN entries."
            ::= { ltxLRPMaxInfo 5 }

        maxBuff OBJECT-TYPE
            SYNTAX  INTEGER (1..256)
            ACCESS  read-write
            STATUS  mandatory
            DESCRIPTION
                    "The maximum size of the Capture Buffer (in KBytes)."
            ::= { ltxLRPMaxInfo 6 }


        --
        -- Lantronix LTX LRP Extension MIB, RMON Rover Information         
        -- Robert Winter, Xact Inc., March 15, 1996    
        --

        roverControl OBJECT-TYPE
            SYNTAX  INTEGER
            ACCESS  read-write
            STATUS  mandatory
            DESCRIPTION
                    "The control to switch the Rover on and off."
            ::= { ltxLRPRoverInfo 1 }
  
        roverSeconds OBJECT-TYPE
            SYNTAX  Counter
            ACCESS  read-write
            STATUS  mandatory
            DESCRIPTION
                    "The Rover decision-point interval in seconds."
            ::= { ltxLRPRoverInfo 2 }

        roverTErrs OBJECT-TYPE
            SYNTAX  Counter
            ACCESS  read-write
            STATUS  mandatory
            DESCRIPTION
                    "The maximum value for the Total Errors threshold."
            ::= { ltxLRPRoverInfo 3 }

        roverBPS OBJECT-TYPE
            SYNTAX  Counter
            ACCESS  read-write
            STATUS  mandatory
            DESCRIPTION
                    "The maximum value for the Bytes Per Second threshold."
            ::= { ltxLRPRoverInfo 4 }

        roverEPS OBJECT-TYPE
            SYNTAX  Counter
            ACCESS  read-write
            STATUS  mandatory
            DESCRIPTION
                    "The maximum value for the Errors Per Second threshold."
            ::= { ltxLRPRoverInfo 5 }

        roverPPS OBJECT-TYPE
            SYNTAX  Counter
            ACCESS  read-write
            STATUS  mandatory
            DESCRIPTION
                    "The maximum value for the Packets Per Second threshold."
            ::= { ltxLRPRoverInfo 6 }

        roverUtil OBJECT-TYPE
            SYNTAX  Counter
            ACCESS  read-write
            STATUS  mandatory
            DESCRIPTION
                    "The maximum value for the Utilization (%) threshold."
            ::= { ltxLRPRoverInfo 7 }

        roverTCRC OBJECT-TYPE
            SYNTAX  Counter
            ACCESS  read-write
            STATUS  mandatory
            DESCRIPTION
                    "The maximum value for the Total CRC Error threshold."
            ::= { ltxLRPRoverInfo 8 }

        roverTRunt OBJECT-TYPE
            SYNTAX  Counter
            ACCESS  read-write
            STATUS  mandatory
            DESCRIPTION
                    "The maximum value for the Total Runts threshold."
            ::= { ltxLRPRoverInfo 9 }

        roverTGiant OBJECT-TYPE
            SYNTAX  Counter
            ACCESS  read-write
            STATUS  mandatory
            DESCRIPTION
                    "The maximum value for the Total Giants threshold."
            ::= { ltxLRPRoverInfo 10 }

        roverTColl OBJECT-TYPE
            SYNTAX  Counter
            ACCESS  read-write
            STATUS  mandatory
            DESCRIPTION
                    "The maximum value for the Total Collisions threshold."
            ::= { ltxLRPRoverInfo 11 }

        roverTJabb OBJECT-TYPE
            SYNTAX  Counter
            ACCESS  read-write
            STATUS  mandatory
            DESCRIPTION
                    "The maximum value for the Total Jabbers threshold."
            ::= { ltxLRPRoverInfo 12 }


        --
        -- Lantronix LTX LRP Extension MIB, Miscellaneous Information         
        -- Robert Winter, Xact Inc., March 15, 1996    
        --
        
        
        miscInfoPortTable OBJECT-TYPE
            SYNTAX SEQUENCE OF MiscInfoPortEntry
            ACCESS not-accessible
            STATUS mandatory
            DESCRIPTION
                "A list of LTX Configuration Port Entries "
            ::= { ltxLRPMiscInfo 1 }
            
        miscInfoPortEntry OBJECT-TYPE
            SYNTAX MiscInfoPortEntry
            ACCESS not-accessible
            STATUS mandatory
            DESCRIPTION
                "A list of Port properties for the LTX LRP"
            INDEX { miscInfoPortIndex }
            ::= { miscInfoPortTable 1 }
            
        MiscInfoPortEntry ::= SEQUENCE {
            miscInfoPortIndex             INTEGER (1..6),
            miscInfoPortName              DisplayString,
            miscInfoPortIP                IpAddress,
            miscInfoPortMask              IpAddress
        }
        
        miscInfoPortIndex OBJECT-TYPE
            SYNTAX INTEGER (1..6)
            ACCESS read-write
            STATUS mandatory
            DESCRIPTION
                "An index that uniquely identifies a LTX LRP port."
            ::= { miscInfoPortEntry 1 }
            
        miscInfoPortName OBJECT-TYPE
            SYNTAX DisplayString
            ACCESS read-write
            STATUS mandatory
            DESCRIPTION
                "The name of this LTX LRP Port Entry."
            ::= { miscInfoPortEntry 2 }
            
        miscInfoPortIP OBJECT-TYPE
            SYNTAX IpAddress
            ACCESS read-write
            STATUS mandatory
            DESCRIPTION
                "The IP Address for the LTX LRP Port."
            ::= { miscInfoPortEntry 3 }
            
        miscInfoPortMask OBJECT-TYPE
            SYNTAX IpAddress
            ACCESS read-write
            STATUS mandatory
            DESCRIPTION
                "The netmask for the LTX LRP Port."
            ::= { miscInfoPortEntry 4 }

        miscInfoDate OBJECT-TYPE
            SYNTAX DisplayString
            ACCESS read-write
            STATUS mandatory
            DESCRIPTION
                "The time and date on the LTX LRP."
            ::= { ltxLRPMiscInfo 2 }

        miscInfoTMO OBJECT-TYPE
            SYNTAX INTEGER
            ACCESS read-write
            STATUS mandatory
            DESCRIPTION
                "The Terminal and Modem timeout value in seconds."
            ::= { ltxLRPMiscInfo 3 }

        miscInfoRefresh OBJECT-TYPE
            SYNTAX INTEGER
            ACCESS read-write
            STATUS mandatory
            DESCRIPTION
                "The ASCII Screen refresh interval value in seconds."
            ::= { ltxLRPMiscInfo 4 }

        miscInfoBaud OBJECT-TYPE
            SYNTAX INTEGER
            ACCESS read-write
            STATUS mandatory
            DESCRIPTION
                "The ASCII Screen BAUD Rate."
            ::= { ltxLRPMiscInfo 5 }

        miscInfoTelnetControl OBJECT-TYPE
            SYNTAX INTEGER
            ACCESS read-write
            STATUS mandatory
            DESCRIPTION
                "Enables or disables the Telnet daemon."
            ::= { ltxLRPMiscInfo 6 }

        miscInfoSNMPPort OBJECT-TYPE
            SYNTAX INTEGER
            ACCESS read-write
            STATUS mandatory
            DESCRIPTION
                "Sets the SNMP Port number."
            ::= { ltxLRPMiscInfo 7 }

        miscInfoAuthenTrap OBJECT-TYPE
            SYNTAX INTEGER
            ACCESS read-write
            STATUS mandatory
            DESCRIPTION
                "Enables or disables the Authentication TRAP."
            ::= { ltxLRPMiscInfo 8 }

        miscInfoColdstartTrap OBJECT-TYPE
            SYNTAX INTEGER
            ACCESS read-write
            STATUS mandatory
            DESCRIPTION
                "Enables or disables the ColdStart TRAP."
            ::= { ltxLRPMiscInfo 9 }

        miscInfoLRPName OBJECT-TYPE
            SYNTAX DisplayString
            ACCESS read-write
            STATUS mandatory
            DESCRIPTION
                "Names the LRP device."
            ::= { ltxLRPMiscInfo 10 }

        miscInfoGateway OBJECT-TYPE
            SYNTAX IpAddress
            ACCESS read-write
            STATUS mandatory
            DESCRIPTION
                "Sets the Default Gateway for the LTX LRP."
            ::= { ltxLRPMiscInfo 11 }

        miscInfoRoverPort OBJECT-TYPE
            SYNTAX INTEGER
            ACCESS read-only
            STATUS mandatory
            DESCRIPTION
                "Identifies the port Rover is active on, if any."
            ::= { ltxLRPMiscInfo 12 }

        miscInfoReset OBJECT-TYPE
            SYNTAX INTEGER
            ACCESS read-write
            STATUS mandatory
            DESCRIPTION
                "Physically resets the LTX LRP - use with care."
            ::= { ltxLRPMiscInfo 13 }


        END
