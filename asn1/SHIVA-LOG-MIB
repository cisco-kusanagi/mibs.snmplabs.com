--
-- 	Copyright 1992, 1993, 1995, 1996 Shiva Corporation
--

SHIVA-LOG-MIB DEFINITIONS ::= BEGIN

IMPORTS
      	TimeTicks
  		FROM RFC1155-SMI
    	DisplayString
    		FROM RFC1213-MIB
    	OBJECT-TYPE
    		FROM RFC-1212		-- Concise MIB Definitions
	TRAP-TYPE
		FROM RFC-1215		-- TRAPs
    	log, lanrover
    		FROM SHIVA-MIB;


--	The message log holds a list of ASCII strings which correspond
--	to the last N diagnostic messages generated by the device.

    logCount	OBJECT-TYPE
	SYNTAX	INTEGER
	ACCESS  read-only
	STATUS  mandatory
	DESCRIPTION
		"The number of entries currently in the message log buffer."
	::= { log 1 }

    logTrapPriority OBJECT-TYPE
	SYNTAX	INTEGER {
		disabled(1),
		emerg(2),	-- system is unusable
		alert(3),	-- action must be taken immediately
		crit(4),	-- critical conditions
		err(5),		-- error conditions
		warning(6),	-- warning conditions
		notice(7),	-- normal but significant condition
		info(8),	-- informational
		debug(9)	-- debug-level messages
	}
	ACCESS  read-write
	STATUS  mandatory
	DESCRIPTION
		"Enables or disables the generation of logNewMessage Traps
		 of a priority numerically equal or lower than the value of 
		 this variable."
	DEFVAL { disabled }
	::= { log 2 }

    logBufferTable OBJECT-TYPE
	SYNTAX	SEQUENCE OF LogBufferEntry
	ACCESS  not-accessible
	STATUS  mandatory
	DESCRIPTION
		"A list of message log entries."
	::= { log 3 }

    logBufferEntry OBJECT-TYPE
	SYNTAX	LogBufferEntry
	ACCESS  not-accessible
	STATUS  mandatory
	DESCRIPTION
		"An entry in the message log.  Entries are indexed by
		counting integers.  Since the earliest messages are dropped
		from the log when it overflows, the first row in the table
		is not necessarily row 1.  Therefore, a Get-Next request
		should be issued to determine the index of the first row."
	INDEX	{ logBufferSequence }
	::= { logBufferTable 1 }

    LogBufferEntry ::= SEQUENCE {
	logBufferSequence	INTEGER,
	logBufferPriority	INTEGER,
	logBufferFacility	INTEGER,
	logBufferTimeOfDay	INTEGER,
	logBufferTimeStamp	TimeTicks,
	logBufferText		DisplayString,
	logBufferPort		DisplayString,
	logBufferUser		DisplayString
    }

    logBufferSequence OBJECT-TYPE
	SYNTAX	INTEGER
	ACCESS  read-only
	STATUS  mandatory
	DESCRIPTION
		"Ordinal position in the Log Buffer."
	::= { logBufferEntry 1 }

    logBufferPriority OBJECT-TYPE
	SYNTAX	INTEGER {
		not-possible(1),
		emerg(2),	-- system is unusable
		alert(3),	-- action must be taken immediately
		crit(4),	-- critical conditions
		err(5),		-- error conditions
		warning(6),	-- warning conditions
		notice(7),	-- normal but significant condition
		info(8),	-- informational
		debug(9)	-- debug-level messages
	}
	ACCESS  read-only
	STATUS  mandatory
	DESCRIPTION
		"The priority of the log message."
	::= { logBufferEntry 2 }

    logBufferFacility OBJECT-TYPE
	SYNTAX	INTEGER {
		default(1),	-- prom
		init(8),	-- initialization
		inet(9),	-- Internet Protocol (IP)
		atalk(10),	-- AppleTalk
		dnet(11),	-- DECnet (FastPath only)
		nw(12),		-- NetWare IPX
		audit(13),	-- accounting
		system(16),	-- from here on down not on FastPath
		config(17),
		serial(18),	-- also known as dialin
		dialout(19),
		ltl(20),	-- LAN-to-LAN
		callControl(21),
		fileIO(22)	-- file transfer to/from/within system
	}
	ACCESS  read-only
	STATUS  mandatory
	DESCRIPTION
		"The Facility which generated the log message."
	::= { logBufferEntry 3 }

    logBufferTimeOfDay OBJECT-TYPE
	SYNTAX	INTEGER
	ACCESS  read-only
	STATUS  mandatory
	DESCRIPTION
		"The time of day at which the message is logged.  This is
		expressed in seconds."
	::= { logBufferEntry 4 }

    logBufferTimeStamp OBJECT-TYPE
	SYNTAX	TimeTicks
	ACCESS  read-only
	STATUS  mandatory
	DESCRIPTION
		"The time the message was generated, measured in number of
		ticks since the device started."
	::= { logBufferEntry 5 }

    logBufferText OBJECT-TYPE
	SYNTAX	DisplayString
	ACCESS  read-only
	STATUS  mandatory
	DESCRIPTION
		"The text of the log message."
	::= { logBufferEntry 6 }

    logBufferPort OBJECT-TYPE
	SYNTAX	DisplayString
	ACCESS  read-only
	STATUS  mandatory
	DESCRIPTION
		"The Serial Port associated the log message.
		Only valid when logBufferFacility is audit(13)."
	::= { logBufferEntry 7 }

    logBufferUser OBJECT-TYPE
	SYNTAX	DisplayString
	ACCESS  read-only
	STATUS  mandatory
	DESCRIPTION
		"The User associated the log message.
		Only valid when logBufferFacility is audit(13)."
	::= { logBufferEntry 8 }

    -- logSavePriority accidentally not implemented until release 4.3.
    logSavePriority OBJECT-TYPE
	SYNTAX	INTEGER {
		none(1),
		emerg(2),	-- system is unusable
		alert(3),	-- action must be taken immediately
		crit(4),	-- critical conditions
		err(5),		-- error conditions
		warning(6),	-- warning conditions
		notice(7),	-- normal but significant condition
		info(8),	-- informational
		debug(9)	-- debug-level messages
	}
	ACCESS  read-write
	STATUS  mandatory
	DESCRIPTION
		"This variable indicates the lowest (numerically
		highest) priority message (as indicated by
		logBufferPriority) which will be save in the
		logBufferTable."
	DEFVAL { debug }
	::= { log 4 }

    logClear OBJECT-TYPE
	SYNTAX	INTEGER { notClear(1), clear(2) }
	ACCESS  read-write
	STATUS  mandatory
	DESCRIPTION
		"Indicates whether the log buffer is non-empty.
		Clears the log buffer when written with clear(2)."
	::= { log 5 }

    -- While logNewMessage has not been documented until release 4.0,
    -- it was present in several prior releases.
    logNewMessage TRAP-TYPE
	ENTERPRISE	lanrover	-- or as appropriate for this
					-- device, whatever the value
					-- of sysObjectID is.
					-- One of the values in products,
					-- per the original SNMP
					-- enterprise naming scheme.
	VARIABLES {
		logBufferSequence,
		logBufferPriority,
		logBufferFacility,
		logBufferTimeOfDay,
		logBufferTimeStamp,
		logBufferText,
		logBufferPort,
		logBufferUser
	}
	DESCRIPTION
		"This trap is generated when an new message of priority
		at or higher than logTrapPriority is generated, and SNMP
		trapping is enabled."
	::= 1 

END
