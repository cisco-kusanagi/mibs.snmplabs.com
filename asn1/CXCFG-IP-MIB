-- LAN system configuration group for the IP router.
-- It assignes IP addresses to IP interfaces and the binging of these 
-- interfaces to the real subnetworks such as device drivers or 
-- convergence elements.

CXCFG-IP-MIB DEFINITIONS ::= BEGIN

--#CURRENT_VERSION 5

   IMPORTS
      Counter
    FROM RFC1155-SMI
      IpAddress
    FROM RFC1155-SMI
      OBJECT-TYPE                     
    FROM RFC-1212
      Alias, cxCfgIpSap, cxIcmp, cxCfgIp               
    FROM CXProduct-SMI;


     cxCfgIpAddrTable OBJECT-TYPE
      SYNTAX  SEQUENCE OF CxCfgIpAddrEntry
      ACCESS  not-accessible
      STATUS  mandatory
      DESCRIPTION
"Provides the configuration and addressing information for eachIP port.
This information is used when a port binds to a physical port or a
convergence port.

The table contains one default entry (row) which can be modified.
If more than one IP port is required, additional entries can be added."

    ::= { cxCfgIpSap 1 }


     cxCfgIpAddrEntry OBJECT-TYPE
    SYNTAX  CxCfgIpAddrEntry
    ACCESS  not-accessible
    STATUS  mandatory
    DESCRIPTION
"Identifies the configuration and addressing information for a particular
IP port.  This information is used when the port binds to a physical
port or a convergence port."

    INDEX   { cxCfgIpAdEntAddr }
    ::= { cxCfgIpAddrTable 1 }

     CxCfgIpAddrEntry ::=
    SEQUENCE {
   cxCfgIpAdEntAddr
       IpAddress,
   cxCfgIpAdEntIfIndex
       INTEGER,
   cxCfgIpAdEntNetMask
       IpAddress,
   cxCfgIpAdEntBcastAddr
       INTEGER,
   cxCfgIpAdEntSubnetworkSAPAlias 
       Alias,
   cxCfgIpAdEntRowStatus
       INTEGER,
   cxCfgIpAdEntState 
       INTEGER,
   cxCfgIpAdEntPeerAddr 
       IpAddress,
   cxCfgIpAdEntRtProto 
       INTEGER,
   cxCfgIpAdEntMtu
       INTEGER,
   cxCfgIpAdEntReplyToRARP
       INTEGER,  
   cxCfgIpAdEntSRSupport
       INTEGER   
    }

     cxCfgIpAdEntAddr OBJECT-TYPE
    SYNTAX  IpAddress
    ACCESS  read-only
    STATUS  mandatory
    DESCRIPTION
"Determines the IP address assigned to a particular IP Port. The value of 
this address is used to index this row of the table.

Range of Values: 4 integers, each one ranging from 0 to 255.

Default Value: 00.00.00.00

Configuration Changed: Administrative. "

    ::= { cxCfgIpAddrEntry 1 }

     cxCfgIpAdEntIfIndex OBJECT-TYPE
    SYNTAX  INTEGER
    ACCESS  read-write
    STATUS  mandatory
    DESCRIPTION
"Identifies the table row that contains configuration or monitoring objects
for a specific type of physical interface.

Range of Values: From 1 to the number of entries in the interface table.  

Default Value: None "

    ::= { cxCfgIpAddrEntry 2 }

     cxCfgIpAdEntNetMask OBJECT-TYPE
    SYNTAX  IpAddress
    ACCESS  read-write
    STATUS  mandatory
    DESCRIPTION
"Determines the subnet mask associated with this IP address. The mask
defines which part of the IP address is the network and which part is
the host. 

Range of Values: 4 integers, with the parts identifying the network set to 
255 and the parts identifying the host set to 0.

Default Value: 00.00.00.00.

Configuration Changed: Administrative. "

    ::= { cxCfgIpAddrEntry 3 }

     cxCfgIpAdEntBcastAddr OBJECT-TYPE
    SYNTAX  INTEGER
    ACCESS  read-write
    STATUS  mandatory
    DESCRIPTION
"The value of the least-significant bit in the IP broadcast address used
for sending datagrams on the (logical) interface associated with the IP
address of this entry.  For example, when the Internet standard all-ones
broadcast address is used, the value will be 1.  This value applies to
both the subnet and network broadcasts addresses used by the entity on
this (logical) interface."

    ::= { cxCfgIpAddrEntry 4 }

     cxCfgIpAdEntSubnetworkSAPAlias OBJECT-TYPE
    SYNTAX  Alias
    ACCESS  read-write
    STATUS  mandatory
    DESCRIPTION
"Determines the name which uniquely identifies the
cxCfgIpAdEntSubnetworkSAP.

Range of Values: 0 to 16 alphanumeric characters. (Note that the 
first character must be a letter, spaces are not allowed).

Default Value: LAN_PORT1

Related Parameters:
If the IP port binds to a physical port, then the alias must match the
alias defined in cxLanIoPortAlias of the cxLanIoPortTable; if the IP port
binds to a convergence port, then the alias must match the port's alias
defined in cxConvPortAlias of the cxConvTable.

Configuration Changed: Administrative"

    ::= { cxCfgIpAddrEntry 5 }

     cxCfgIpAdEntRowStatus  OBJECT-TYPE
    SYNTAX  INTEGER {
       invalid (1),
       valid (2)
          }
    ACCESS  read-write
    STATUS  mandatory
    DESCRIPTION 
"Determines the status of the objects in a table row.

Options:
invalid (1): Row is flagged. After next reset the values will be disabled
and the row will be deleted from the table.

valid (2): Values are enabled.

Default Value: (2)

Configuration Changed: Administrative"

    ::= { cxCfgIpAddrEntry 6 }

     cxCfgIpAdEntState OBJECT-TYPE
    SYNTAX  INTEGER {
        on (1),
        off (2),  
        onether (3),
        ontoken (4)
          }
    ACCESS  read-write
    STATUS  mandatory
    
    DESCRIPTION
"Determines whether the IP port is active or inactive. 

Options:
On (1): The port is active, transmission is possible.

Off (2): The port is inactive, transmission is not possible.  

OnEther (3): The Ethernet STP port will bind to this IP port.

OnToken (4): The Token Ring STP port will bind to this IP port.

Default Value: (1)

Configuration Changed: Administrative"

   DEFVAL { on }
   ::= { cxCfgIpAddrEntry 7 }
        
     cxCfgIpAdEntPeerAddr OBJECT-TYPE
    SYNTAX  IpAddress
    ACCESS  read-write
    STATUS  mandatory
    DESCRIPTION
"Determines the IP address of the port's closest neighbor (the port that is
one hop away).  The object is only applicable if the IP port binds to a 
convergence port.  On broadcast networks, this value can be void,
i.e. 00.00.00.00.

Range of Values: 4 integers, each one ranging from 0 to 255.

Default Values: 00.00.00.00

Configuration Changed: Administrative"

    ::= { cxCfgIpAddrEntry 8 }

     cxCfgIpAdEntRtProto OBJECT-TYPE
    SYNTAX  INTEGER {
            none (1),
            rip  (2),
            ospf (3)
          }
    ACCESS  read-write
    STATUS  mandatory
    
    DESCRIPTION
"Determines which routing protocol the IP port is associated with. 

Options:                 
none (1): No routing protocol is used

rip (2): Routing Information Protocol (RIP).  A distance vector routing
protocol popular for routing IP.

ospf (3): Open Shortest Path First (OSPF). A link state routing protocol
used for routing IP.

Default Value: rip (2)

Configuration Changed:  administrative"
   DEFVAL { rip }
   --#STARTING_VERSION 1
   ::= { cxCfgIpAddrEntry 9 }

     cxCfgIpAdEntMtu OBJECT-TYPE
    SYNTAX  INTEGER (64..4096)
    ACCESS  read-write
    STATUS  mandatory

    DESCRIPTION
"Determines the size, in bytes, of the largest IP packet that can be sent 
or received at the IP layer. Packets that exceed this size are fragmented.

This value should always be less than or equal to the sub-layer 
packet size. 

Range of Values: 64-4096

Default Value: 1600

Configuration Changed:  administrative"
   DEFVAL { 1600 }
   --#STARTING_VERSION 2
         ::= { cxCfgIpAddrEntry 10 }

   cxCfgIpAdEntReplyToRARP OBJECT-TYPE
    SYNTAX  INTEGER {
               enabled  (1),
               disabled (2)
            }              
    ACCESS  read-write
    STATUS  mandatory

    DESCRIPTION
"Determines whether the port should reply a RARP request.

Default Value: disabled (2)

Configuration Changed:  administrative"
   DEFVAL { disabled }
   --#STARTING_VERSION 3
         ::= { cxCfgIpAddrEntry 11 }

   cxCfgIpAdEntSRSupport OBJECT-TYPE
    SYNTAX  INTEGER {
               enabled  (1),
               disabled (2)
            }              
    ACCESS  read-write
    STATUS  mandatory

    DESCRIPTION
"Determines whether the port should support Source Routing
packet. If it is enabled, the physical infterface of the port
must be Token-Ring. If it is disabled, any Source Routing
packet will be discarded.

Default Value: disabled (2)

Configuration Changed:  administrative"
   DEFVAL { disabled }
   --#STARTING_VERSION 5
         ::= { cxCfgIpAddrEntry 12 }

--
-- Ping  Table
--

     cxCfgIpPingTable OBJECT-TYPE
      SYNTAX  SEQUENCE OF CxCfgIpPingEntry
      ACCESS  not-accessible
      STATUS  mandatory
      DESCRIPTION
"Provides the configuration to perform an IP Ping.

The table contains one default entry (row) which can be modified."
   --#STARTING_VERSION 1
    ::= { cxIcmp 1 }


     cxCfgIpPingEntry OBJECT-TYPE
    SYNTAX  CxCfgIpPingEntry
    ACCESS  not-accessible
    STATUS  mandatory
    DESCRIPTION
"Identifies the configuration of a Ping table."

    INDEX   { cxCfgIpPingDestAddr }
    ::= { cxCfgIpPingTable 1 }

     CxCfgIpPingEntry ::=
    SEQUENCE {
-- Parameters
   cxCfgIpPingIndex
       INTEGER,        
   cxCfgIpPingDestAddr
       IpAddress,
   cxCfgIpPingGapsInMs
       INTEGER,
   cxCfgIpPingNbOfPings
       INTEGER,
   cxCfgIpPingDataSize
       INTEGER,
-- Control
   cxCfgIpPingRowStatus
       INTEGER,
   cxCfgIpPingTriggerSend
       INTEGER,
-- Statistics
   cxCfgIpPingNbTx
       Counter,
   cxCfgIpPingNbReplyRx
       Counter,
   cxCfgIpPingNbErrorRx
       Counter,
   cxCfgIpPingLastSeqNumRx
       Counter,
   cxCfgIpPingLastRoundTripInMs
       Counter,
   cxCfgIpPingAvgRoundTripInMs
       Counter,
   cxCfgIpPingMinRoundTripInMs
       Counter,
   cxCfgIpPingMaxRoundTripInMs
       Counter,
   cxCfgIpPingLastNumHopsTraveled
       Counter
    }

      cxCfgIpPingIndex  OBJECT-TYPE
     SYNTAX  INTEGER (1..32)
     ACCESS  read-write
     STATUS  mandatory
     DESCRIPTION 
"Determines the number used to index the Ping entry table. 

Range of Values: From 1 - 32

Default Value: None

Configuration Changed: Administrative"

    ::= { cxCfgIpPingEntry 1 }


     cxCfgIpPingDestAddr OBJECT-TYPE
    SYNTAX  IpAddress
    ACCESS  read-write
    STATUS  mandatory
    DESCRIPTION
"The Destination IP Address, a unique IP number.

Default Value: None "
    ::= { cxCfgIpPingEntry 2 }

     cxCfgIpPingGapsInMs OBJECT-TYPE
    SYNTAX  INTEGER (1..1000)
    ACCESS  read-write
    STATUS  mandatory
    DESCRIPTION
"Gaps in Tenths of a second between ping frames.

Range of Values: From 1 to 1000

Default Value: 10"

    DEFVAL { 10 }
    ::= { cxCfgIpPingEntry 3 }

     cxCfgIpPingNbOfPings OBJECT-TYPE
    SYNTAX  INTEGER (0..4000000)
    ACCESS  read-write
    STATUS  mandatory
    DESCRIPTION
"Number of Ping frames to send. A value of 0, means run infinitely.

Range of Values: From 0 to 4,000,000

Default Value: 1"

    DEFVAL { 1 }
    ::= { cxCfgIpPingEntry 4 }

     cxCfgIpPingDataSize OBJECT-TYPE
    SYNTAX  INTEGER (1..300)
    ACCESS  read-write
    STATUS  mandatory
    DESCRIPTION
"Size of data packet to send in the IP Ping frame.

Range of Values: From 1 to 300

Default Value: 64"

    DEFVAL { 64 }
    ::= { cxCfgIpPingEntry 5 }

     cxCfgIpPingRowStatus  OBJECT-TYPE
    SYNTAX  INTEGER {
       invalid (1),
       valid (2)
          }
    ACCESS  read-write
    STATUS  mandatory
    DESCRIPTION 
"Determines the status of the objects in a table row.

Options:
invalid (1): Row is flagged. After next reset the values will be disabled
and the row will be deleted from the table.

valid (2): Values are enabled.

Default Value: (2)

Configuration Changed: Administrative"

    ::= { cxCfgIpPingEntry 10 }

     cxCfgIpPingTriggerSend OBJECT-TYPE
    SYNTAX  INTEGER { ipIdle (1),
            ipSend (2)
          }
    ACCESS  read-write
    STATUS  mandatory
    DESCRIPTION
"The parameter that triggers whether Pings are sent out.

Options:
ipIdle (1): No Pings are sent

ipSend (2): The counter is set to zero and Pings are sent

Default Value: ipIdle (1)"
    DEFVAL { ipIdle }
    ::= { cxCfgIpPingEntry 11 }

     cxCfgIpPingNbTx OBJECT-TYPE
    SYNTAX  Counter
    ACCESS  read-only
    STATUS  mandatory
    DESCRIPTION
"The number of Ping frames transmitted."
    ::= { cxCfgIpPingEntry 20 }

     cxCfgIpPingNbReplyRx OBJECT-TYPE
    SYNTAX  Counter
    ACCESS  read-only
    STATUS  mandatory
    DESCRIPTION
"The number of positive Ping replies received."
    ::= { cxCfgIpPingEntry 21 }

     cxCfgIpPingNbErrorRx OBJECT-TYPE
    SYNTAX  Counter
    ACCESS  read-only
    STATUS  mandatory
    DESCRIPTION
"The number of error replies received."
    ::= { cxCfgIpPingEntry 22 }

     cxCfgIpPingLastSeqNumRx OBJECT-TYPE
    SYNTAX  Counter
    ACCESS  read-only
    STATUS  mandatory
    DESCRIPTION
"The sequence of the last Ping frame received."
    ::= { cxCfgIpPingEntry 23 }

     cxCfgIpPingLastRoundTripInMs OBJECT-TYPE
    SYNTAX  Counter
    ACCESS  read-only
    STATUS  mandatory
    DESCRIPTION
"The time elapsed in milliseconds for the round trip of the last Ping frame."
    ::= { cxCfgIpPingEntry 24 }

     cxCfgIpPingAvgRoundTripInMs OBJECT-TYPE
    SYNTAX  Counter
    ACCESS  read-only
    STATUS  mandatory
    DESCRIPTION
"The average time spent in ms for the round trips of the each Ping frame."
    ::= { cxCfgIpPingEntry 25 }

     cxCfgIpPingMinRoundTripInMs OBJECT-TYPE
    SYNTAX  Counter
    ACCESS  read-only
    STATUS  mandatory
    DESCRIPTION
"The minimum time spent in ms for a round trips of a Ping frame."
    ::= { cxCfgIpPingEntry 26 }

     cxCfgIpPingMaxRoundTripInMs OBJECT-TYPE
    SYNTAX  Counter
    ACCESS  read-only
    STATUS  mandatory
    DESCRIPTION
"The maximum time spent in ms for a round trips of a Ping frame."
    ::= { cxCfgIpPingEntry 27 }

     cxCfgIpPingLastNumHopsTraveled OBJECT-TYPE
    SYNTAX  Counter
    ACCESS  read-only
    STATUS  mandatory
    DESCRIPTION
"The number of hops traveled counter for the last Ping frame."
    ::= { cxCfgIpPingEntry 28 }



-- Routing Control information for IP router.

cxCfgIpRIP   OBJECT-TYPE
      SYNTAX  INTEGER{
    on(1),  -- RIP enabled
    off(2)   -- RIP disabled
    }
      ACCESS  read-write
      STATUS  mandatory
      DESCRIPTION 
"Determines whether RIP is enabled or disabled on this router. 

Options:
on (1): RIP enabled

off (2): RIP disabled

Default Value: on

Configuration Changed: administrative"
    ::= { cxCfgIp 1 }



cxCfgRIPII   OBJECT-TYPE
      SYNTAX  INTEGER{
    on(1),  -- RIPII enabled
    off(2)   -- RIPII disabled
    }
      ACCESS  read-write
      STATUS  mandatory
      DESCRIPTION 
"Determines whether RIP-2 is enabled or disabled on this router. RIP-2 can 
only be enabled, if RIP is also enabled.

Options:
on (1): RIP-2 enabled

off (2): RIP-2 disabled

Default Value: on (1)

Configuration Changed: Administrative"

    ::= { cxCfgIp 2 }

cxCfgIpMibLevel OBJECT-TYPE
   SYNTAX   INTEGER
   ACCESS   read-only
   STATUS   mandatory
   DESCRIPTION
"Used to determine current MIB module release supported
by the agent. Object is in decimal."
   DEFVAL { 0 }
   --#STARTING_VERSION 1
   ::= { cxCfgIp 3 }


END
