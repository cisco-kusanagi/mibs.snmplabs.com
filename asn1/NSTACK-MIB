--  =======================================================================
--  File        : nbstack.mib
--  Description : Private MIB for NBase Stackable Device
--  By          : Vaisman Yakov
--  Version     : $Revision:   1.1
--  Date        : $Date:   October 27, 1998
--  =======================================================================
--
--
-- Copyright (c) 1998 NBase Switch Communications.  All Rights Reserved.
--
-- Reproduction of this document is authorized on condition that this
-- copyright notice is included.  This NBase SNMP MIB Specification
-- embodies NBase's proprietary intellectual property.  NBase
-- retains all title and ownership in the specification, including any
-- revisions.
--
-- It is NBase's intent to encourage the widespread use of this
-- specification in connection with the management of NBase's
-- p223roducts. NBase grants vendor, end-users, and other interested
-- parties a non-exclusive license to use this specification in
-- connection with the management of NBase's products.
--
-- This specification is supplied "AS IS," and NBase makes no
-- warranty, either express or implied, as to the use, operation,
-- condition, or performance of the specification.
--
-- NBase retains the right to change this MIB without notification.
--
NSTACK-MIB DEFINITIONS ::= BEGIN

	 IMPORTS
		enterprises,
                IpAddress                     FROM RFC1155-SMI

		OBJECT-TYPE                   FROM RFC-1212
        DisplayString                 FROM RFC1213-MIB;

		PortsBitmap ::= OCTET STRING
	--          		 Set of ports. Each octet
	--                 within the value of this object specifies a set of
	--                 eight ports, with the first octet specifying ports
	--                 1 through 8, the second octet specifying ports 9
	--                 through 16, etc.  Within each octet, the least
	--                 significant bit represents the lowest numbered
	--                 port, and the most significant bit represents the
	--                 highest numbered port.  Thus, each port of the
	--                 switch is represented by a single bit within the
	--                 value of this object.  If that bit has a value of
	--                 <1> then that port is included in the set of
	--                 ports; the port is not included if its bit has a
	--                 value of <0>.  (Note that the setting of the bit
	--                 corresponding to the port from which a frame is
	--                 received is irrelevant.)  The default value of
	--                 this object is a string of ones of appropriate
	--                 length."

-- ************************************************************
-- NBase Object Identifier Definition
-- ************************************************************

nbase              OBJECT IDENTIFIER ::= { enterprises 629 }
nbSwitchG1         OBJECT IDENTIFIER ::= { nbase 1 }
nbSwitchG1Il       OBJECT IDENTIFIER ::= { nbSwitchG1 50}
nbsStackInfo       OBJECT IDENTIFIER ::= { nbSwitchG1Il 4}

-- ************************************************************

-- ************************************************************
-- Objects in the Stack Information Group
-- *************************************************************

	 nbsStackSlotCapacity  OBJECT-TYPE
	 SYNTAX    INTEGER
         ACCESS    read-only
         STATUS    mandatory
         DESCRIPTION
                 "Max quantity of Slots possible in the Stack."
		 ::= { nbsStackInfo 1 }

	 nbsStackSlotsTableSize    OBJECT-TYPE
	 SYNTAX    INTEGER
         ACCESS    read-only
         STATUS    mandatory
         DESCRIPTION
                 "Real size of Slots Table in the Stack."
		 ::= { nbsStackInfo 2 }

	 nbsStackPortsCapacity		OBJECT-TYPE
	 SYNTAX    INTEGER
         ACCESS    read-only
         STATUS    mandatory
         DESCRIPTION
                 "Max quantity of Ports possible in the Stack ."
	 ::= { nbsStackInfo 3 }

	 nbsStackSlotPortsCapacity	OBJECT-TYPE
	 SYNTAX    INTEGER
         ACCESS    read-only
         STATUS    mandatory
         DESCRIPTION
                 "Max quantity of Ports possible in the Slot ."
	 ::= { nbsStackInfo 4 }

-- *************************************************************
-- Objects in the Slot Information Group
-- *************************************************************
        
	 nbsStackSlotTable OBJECT-TYPE
	 SYNTAX    SEQUENCE OF NbsStackSlotEntry
         ACCESS    not-accessible
         STATUS    mandatory
         DESCRIPTION
                 "Table of descriptive and status information about
	          the Slots."
		 ::= { nbsStackInfo 5 }

	 nbsStackSlotEntry OBJECT-TYPE
	 SYNTAX    NbsStackSlotEntry
         ACCESS    not-accessible
         STATUS    mandatory
         DESCRIPTION
                 "An entry in the table, containing information
                  about a single Slot."
	 INDEX   { nbsStackSlotIndex }
		 ::= { nbsStackSlotTable 1 }

	 NbsStackSlotEntry ::=
	 SEQUENCE   {
		     nbsStackSlotIndex
                          INTEGER,
		     nbsStackSlotType
                          INTEGER,                         
		     nbsStackSlotMgmtStatus
                          INTEGER,
		     nbsStackSlotPortsMaxNumber
                          INTEGER,
		     nbsStackSlotPortsNumber
                          INTEGER,
		     nbsStackSlotFirstPort
                          INTEGER,
		     nbsStackSlotOperStatus
                          INTEGER,
		     nbsStackSlotAdminStatus
                          INTEGER,
		     nbsStackSlotRedundantPSMode
                          INTEGER,
		     nbsStackSlotUplinkModulesNumber
			  INTEGER,
		     nbsStackSlotReset
                          INTEGER,
-- ykfix27 - 15.05.99 - begin
		     nbsStackSlotIp
                          IpAddress,
		     nbsStackSlotHwVers
			  INTEGER,
		     nbsStackSlotSwVers
			  INTEGER
-- ykfix27 - 15.05.99 - end
		    }

	 nbsStackSlotIndex	 OBJECT-TYPE
         SYNTAX    INTEGER
         ACCESS    read-only
         STATUS    mandatory
         DESCRIPTION
		 "This object identifies the Slot#
		  for which this entry contains information."
		 ::= { nbsStackSlotEntry 1 }
       
-- ykfix27 - 5.04.99 - begin
	 nbsStackSlotType          OBJECT-TYPE
         SYNTAX    INTEGER {
                       empty(1),
		       unknown(2),
		       standAlone(3),
		       universal(4),
		       eth20Ports10or100TP(5),
		       eth40Ports10TP(6),
		       eth10Ports100FO(7),
		       eth16Ports10or100TP(8),
		       eth4Ports1000FO(9),
		       agentSlot(10),
		       routingEngine(11),
		       eth8Ports10or100TP(12),
		       eth2Ports100FOMM(13),
		       eth2Ports100FOSM(14),
		       eth1Ports1000FOMM(15),
		       eth1Ports1000FOSM(16),
		       eth2Ports1000FOMM(17),
		       eth2Ports1000FOSM(18),
		       stackableSlotNoLink(19),
		       stackableSlotNH2025(20),
		       stackableSlotReserve1(21),
		       stackableSlotReserve2(22),          -- ykfix30 - 14.07.99
		       eth2Ports100FO(23),                 -- ykfix30 - 14.07.99
		       eth2Ports1000FO(24),                -- ykfix30 - 14.07.99
		       eth4Ports100FOMM(25),               -- ykfix30 - 14.07.99
		       eth4Ports100FOSM(26),               -- ykfix30 - 14.07.99
		       eth4Ports100FO(27),                 -- ykfix30 - 14.07.99
		       eth4Ports10or100TP(28),             -- ykfix31 - 9.08.99
		       eth4Ports100MTRJ(29),               -- ykfix31 - 9.08.99
		       eth8Ports100MTRJ(30),               -- ykfix31 - 9.08.99
		       eth4Ports100VF(31),                 -- ykfix31 - 9.08.99
		       eth8Ports100VF(32),                 -- ykfix31 - 27.10.99
		       ethGigaBitService(33),              -- ykfix33 - 1.03.00
		       eth4Ports100LC(34),                 -- ykfix33 - 1.03.00
		       eth8Ports100LC(35),                 -- ykfix33 - 1.03.00
		       eth2Ports10FL(36),                  -- ykfix33 - 1.03.00
		       eth4Ports10FL(37),                  -- ykfix33 - 1.03.00
		       eth1Port100or1000TP(38),            -- ykfix39 - 21.09.00
		       eth1Port1000FORED(39),              -- ykfix39 - 21.09.00
		       eth4Ports100TPand2Ports100FO(40),   -- ykfix39 - 21.09.00
		       eth4Ports100TPand1Port100FO(41),    -- ykfix39 - 21.09.00
		       eth0Ports100TPand2Ports100FO(42),   -- ykfix39 - 21.09.00
		       eth4Ports100TPand0Ports100FO(43),   -- ykfix39 - 21.09.00
		       eth1Ports1000MTRJ(44),              -- ykfix39 - 21.09.00
		       eth1StackPorts100or1000TP(45)       -- ykfix39 - 21.09.00
		      }
         ACCESS    read-only
         STATUS    mandatory
         DESCRIPTION
         "Slot Types:
	  empty              - Slot is Empty;
	  unknown            - Slot is of the Unknown type;
	  standAlone         - Stand Alone Device;
	  universal          - Slot including Uplink Modules of the different types;
	  eth20Ports10or100TP- Slot including 20 fast   copper 10/100 MBps Ports;
	  eth40Ports10TP     - Slot including 40 normal copper 10 MBps Ports;
	  eth10Ports100FO    - Slot including 10 fast fibre optic 100 MBps Ports(Multi Mode);
	  eth16Ports10or100TP- Slot including 16 fast   copper 10/100 MBps Ports;
	  eth4Ports1000FO    - Slot including  4 GigaBit 1000 MBps Ports(Multi Mode);
	  agentSlot          - Slot including  CPU  Card;
	  routingEngine      - Slot including  Routing Engine Card;
	  eth8Ports10or100TP - Slot including  8 fast   copper 10/100 MBps Ports;
	  eth2Ports100FOMM   - Slot including  2 fast fibre optic 100 MBps Ports(MM=Multi  Mode);
	  eth2Ports100FOSM   - Slot including  2 fast fibre optic 100 MBps Ports(SM=Single Mode);
	  eth1Ports1000FOMM  - Slot including  1 GigaBit 1000 MBps Ports(MM=Multi  Mode);
	  eth1Ports1000FOSM  - Slot including  1 GigaBit 1000 MBps Ports(SM=Single Mode);
	  eth2Ports1000FOMM  - Slot including  2 GigaBit 1000 MBps Ports(MM=Multi  Mode);
	  eth2Ports1000FOSM  - Slot including  2 GigaBit 1000 MBps Ports(SM=Single Mode);
	  stackableSlotNoLink- Slot including special Stackable Card with no Link;
	  stackableSlotNH2025- Slot including special Stackable Card Linked with the NH2025 Device;
	stackableSlotReserve1- Slot including special Stackable Card (Reserve1 for the future purposes);
-- ykfix30 - 14.07.99 - begin
	stackableSlotReserve2- Slot including special Stackable Card (Reserve2 for the future purposes);
	  eth2Ports100FO     - Slot including  2 fast fibre optic 100 MBps Ports(different configuration of the Multi Mode and/or Single Mode Ports);
	  eth2Ports1000FO    - Slot including  2 GigaBit 1000 MBps Ports(different configuration of the Multi Mode and/or Single Mode Ports);
	  eth4Ports100FOMM   - Slot including  4 fast fibre optic 100 MBps Ports(MM=Multi  Mode);
	  eth4Ports100FOSM   - Slot including  4 fast fibre optic 100 MBps Ports(SS=Single Mode);
	  eth4Ports100FO     - Slot including  4 fast fibre optic 100 MBps Ports(different configuration of the Multi Mode and/or Single Mode Ports);
-- ykfix31 - 9.08.99  - begin
	  eth4Ports10or100TP - Slot including  4 fast copper   10/100 MBps Ports;
	  eth4Ports100MTRJ   - Slot including  4 fast fibre optic 100 MBps MTRJ Ports;
	  eth8Ports100MTRJ   - Slot including  8 fast fibre optic 100 MBps MTRJ Ports;
	  eth4Ports100VF     - Slot including  4 fast fibre optic 100 MBps VF Ports;
	  eth8Ports100VF     - Slot including  8 fast fibre optic 100 MBps VF Ports;
-- ykfix33 - 1.03.00 - begin
	  ethGigaBitService  - Slot including special Giga Bit Service Card (for using Modules with >= 2 GigaBit Ports);
	  eth4Ports100LC     - Slot including  4 fast fibre optic 100 MBps LC Ports;
	  eth8Ports100LC     - Slot including  8 fast fibre optic 100 MBps LC Ports;
          eth2Ports10FL      - Slot including  2 slow fibre optic 10  MBps FL Ports;
          eth4Ports10FL      - Slot including  4 slow fibre optic 10  MBps FL Ports;
-- ykfix39 - 21.09.00 - begin
	  eth1Port100or1000TP- Slot including  1 GigaBit copper   100/1000 MBps TP Ports;
	  eth1Port1000FORED             - Slot including 1 GigaBit fibre optic Redundant Port;
	  eth4Ports100TPand2Ports100FO  - Slot including 4 copper 100/1000 MBps TP + 2 fast FO 100 MBps Ports;
	  eth4Ports100TPand1Port100FO   - Slot including 4 copper 100/1000 MBps TP + 1 fast FO 100 MBps Ports;
	  eth0Ports100TPand2Ports100FO  - Slot including 0 copper 100/1000 MBps TP + 2 fast FO 100 MBps Ports;
	  eth4Ports100TPand0Ports100FO  - Slot including 4 copper 100/1000 MBps TP + 0 fast FO 100 MBps Ports;
	  eth1Ports1000MTRJ             - Slot including 1 GigaBit MTRJ fibre optic     1000 MBps Port;
	  eth1StackPorts100or1000TP     - Slot including 1 GigaBit TP copper 100/1000 MBps Port for Low Distances(<= 5m);"
-- ykfix39 - 21.09.00 - end
-- ykfix33 - 1.03.00 - end
-- ykfix31 - 9.08.99  - end
-- ykfix30 - 14.07.99 - end
		 ::= { nbsStackSlotEntry 2 }
-- ykfix27 - 5.04.99 - end

	 nbsStackSlotMgmtStatus        OBJECT-TYPE
         SYNTAX    INTEGER {
		       master(1),
		       slave(2)
                      }
	 ACCESS    read-only
	 STATUS    mandatory
         DESCRIPTION
                 "Slot Module Management Status:
				  master            - Master Slot Module;
				  slave             - Slave  Slot Module."
		 ::= { nbsStackSlotEntry 3 }

	 nbsStackSlotPortsMaxNumber  OBJECT-TYPE
         SYNTAX    INTEGER 
         ACCESS    read-only
         STATUS    mandatory
         DESCRIPTION
		 "This object identifies the Maximum possible Ports Number in the Slot."
		 ::= { nbsStackSlotEntry 4 }
       
	 nbsStackSlotPortsNumber   OBJECT-TYPE
         SYNTAX    INTEGER 
         ACCESS    read-only
         STATUS    mandatory
         DESCRIPTION
		 "This object identifies the Real Ports Number in the Slot."
		 ::= { nbsStackSlotEntry 5 }
       
	 nbsStackSlotFirstPort     OBJECT-TYPE
         SYNTAX    INTEGER
         ACCESS    read-only
         STATUS    mandatory
         DESCRIPTION
		 "This object identifies the number of the First Port
		  in the Slot, according to the Stack Ports Numeration."
		 ::= { nbsStackSlotEntry 6 }
       
	 nbsStackSlotOperStatus    OBJECT-TYPE
         SYNTAX    INTEGER {
		       switchedOff(1),
		       enabled(2),
		       disabled(3),
		       changing(4)
                      }
         ACCESS    read-only
         STATUS    mandatory
         DESCRIPTION
                 "Slot Oper Status:
				  switchedOff      - Slot is Switched-off;
				  enabled          - Slot is enabled;
				  disabled         - Slot is disabled;
				  changing         - Slot is changing."
		 ::= { nbsStackSlotEntry 7 }

	 nbsStackSlotAdminStatus   OBJECT-TYPE
         SYNTAX    INTEGER {
		       enabled(1),
		       disabled(2)
                      }
         ACCESS    read-write
         STATUS    mandatory
         DESCRIPTION
                 "Slot Admin Status:
				  enabled           - Slot is enabled;
				  disabled          - Slot is disabled."
		 ::= { nbsStackSlotEntry 8 }

	 nbsStackSlotRedundantPSMode OBJECT-TYPE
         SYNTAX    INTEGER {
		       notConnected(1),
		       connected(2)
		      }
         ACCESS    read-only
         STATUS    mandatory
         DESCRIPTION
				 "Slot Redundant Power Supply Module Status:
				  notConnected     - Redundant Power Supply is not Existing;
				  connected        - Redundant Power Supply is Existing."
		 ::= { nbsStackSlotEntry 9 }

	 nbsStackSlotUplinkModulesNumber OBJECT-TYPE
	 SYNTAX    INTEGER
         ACCESS    read-only
         STATUS    mandatory
         DESCRIPTION
				 "This object identifies the number of the Uplink Modules
                  in the Slot."
		 ::= { nbsStackSlotEntry 10 }
       
	 nbsStackSlotReset         OBJECT-TYPE
	 SYNTAX    INTEGER {
	       running(1),
               reset(2)
		      }
         ACCESS    read-write
         STATUS    mandatory
         DESCRIPTION
		 "This object is used to reset the corresponding Slot Module."
		 ::= { nbsStackSlotEntry 11 }

	 nbsStackSlotIp         OBJECT-TYPE
	 SYNTAX    IpAddress
		ACCESS    read-only
		STATUS    mandatory
		DESCRIPTION
		 "Ip address of the slot (if it has it; if it hasn't - 0.0.0.0)."
		 ::= { nbsStackSlotEntry 12 }

-- ykfix27 - 15.05.99 - begin
	 nbsStackSlotHwVers     OBJECT-TYPE
	 SYNTAX  INTEGER
	 ACCESS  read-only
         STATUS  mandatory
		DESCRIPTION
		"This object holds the Software Version of the Slot Module."
		 ::= { nbsStackSlotEntry 13 }

	 nbsStackSlotSwVers     OBJECT-TYPE
	 SYNTAX  INTEGER
	 ACCESS  read-only
         STATUS  mandatory
		DESCRIPTION
		"This object holds the Hardware Version of the Slot Module."
		 ::= { nbsStackSlotEntry 14 }
-- ykfix27 - 15.05.99 - end

-- *************************************************************
-- Objects in the Uplink Information Group
-- *************************************************************
        
	 nbsStackSlotUplTable   OBJECT-TYPE
	 SYNTAX  SEQUENCE OF NbsStackSlotUplEntry
         ACCESS  not-accessible
         STATUS  mandatory
         DESCRIPTION
                 "A table of Uplink Modules mounted on the corresponding Slot of the Switch."		
		 ::= { nbsStackInfo 6 }

	 nbsStackSlotUplEntry   OBJECT-TYPE
	 SYNTAX  NbsStackSlotUplEntry
         ACCESS  not-accessible
         STATUS  mandatory
         DESCRIPTION
		"Contains the information needed to identify the Uplink Module of the Slot."
	 INDEX { nbsStackSlotNumber,
		 nbsStackSlotUplNumber }
		::= { nbsStackSlotUplTable 1 }

	 NbsStackSlotUplEntry ::=
	 SEQUENCE   {
		     nbsStackSlotNumber
                          INTEGER,
		     nbsStackSlotUplNumber
			  INTEGER,
		     nbsStackSlotUplType
                          INTEGER,
		     nbsStackSlotUplSwVers
                          INTEGER,
		     nbsStackSlotUplHwVers
                          INTEGER,
		     nbsStackSlotUplNPorts
                          INTEGER,
		     nbsStackSlotUplFirstPort
                          INTEGER,
		     nbsStackSlotUplPortsMask
			  PortsBitmap,
		     nbsStackSlotUplStatus
                          INTEGER,
-- ykfix22 - 18.03.99 - begin
		     nbsStackSlotUplHwDescr
	         	  DisplayString,
		     nbsStackSlotUplSwDescr
    	     		  DisplayString
-- ykfix22 - 18.03.99 - begin
		    }

	 nbsStackSlotNumber        OBJECT-TYPE
	 SYNTAX  INTEGER
         ACCESS  read-only
         STATUS  mandatory
         DESCRIPTION
		 "The Slot # in the Device."
		 ::= { nbsStackSlotUplEntry 1 }

	 nbsStackSlotUplNumber     OBJECT-TYPE
	 SYNTAX  INTEGER
         ACCESS  read-only
         STATUS  mandatory
         DESCRIPTION
		 "The Uplink Module # in the
		  corresponding Slot in the Device."
		 ::= { nbsStackSlotUplEntry 2 }

-- ykfix27 - 5.04.99 - begin
	 nbsStackSlotUplType       OBJECT-TYPE
         SYNTAX    INTEGER {
                     uplAbsent(1),
		     uplUnknown(2),
		     upl1GigaMM(3),
		     upl1GigaSM(4),
		     upl2GigaMM(5),
		     upl2GigaSM(6),
		     upl1FO(7),
		     upl1TP(8),
		     upl2FOMM(9),
		     upl2FOSM(10),
		     upl4FOMM(11),
		     upl4FOSM(12),
		     upl8TP(13),
		     upl1ATM(14),
                     upl1FDDI(15),
		     uplStackModuleNoLink(16),
		     uplStackModuleNH2025(17),
		     uplStackModuleReserve1(18),
		     uplStackModuleReserve2(19),           -- ykfix30 - 14.07.99
		     upl4TP(20),                           -- ykfix30 - 27.07.99
		     upl2FO(21),                           -- ykfix30 - 14.07.99
		     upl2Giga(22),                         -- ykfix30 - 14.07.99
		     upl4FO(23),                           -- ykfix31 - 9.08.99
		     upl4MTRJ(24),                         -- ykfix31 - 9.08.99
		     upl8MTRJ(25),                         -- ykfix31 - 9.08.99
		     upl4VF(26),                           -- ykfix31 - 9.08.99
		     upl8VF(27),                           -- ykfix33 - 1.03.00
		     upl4LC(28),                           -- ykfix33 - 1.03.00
		     upl8LC(29),                           -- ykfix33 - 1.03.00
		     upl2FL(30),                           -- ykfix33 - 1.03.00
		     upl4FL(31),                           -- ykfix33 - 1.03.00
		     upl1GigaTP(32),                       -- ykfix39 - 21.09.00
		     upl1GER(33),                          -- ykfix39 - 21.09.00
		     upl4TP2FO(34),                        -- ykfix39 - 21.09.00
		     upl4TP1FO(35),                        -- ykfix39 - 21.09.00
		     upl0TP2FO(36),                        -- ykfix39 - 21.09.00
		     upl4TP0FO(37),                        -- ykfix39 - 21.09.00
		     upl1GigaMTRJ(38),                     -- ykfix39 - 21.09.00
		     upl1GigaStackTP(39)                   -- ykfix39 - 21.09.00
		    }
         ACCESS    read-only
	 STATUS    mandatory
         DESCRIPTION
                 "Uplink Module Types:
		  uplAbsent  - Uplink Module is Absent;
                  uplUnknown - Uplink Module of the Unknown type;
		  upl1GigaMM - Uplink Module including 1 GigaBit 1000 MBps Ports(MM=Multi  Mode);
		  upl1GigaSM - Uplink Module including 1 GigaBit 1000 MBps Ports(SM=Single Mode);
		  upl2GigaMM - Uplink Module including 2 GigaBit 1000 MBps Ports(MM=Multi  Mode);
		  upl2GigaSM - Uplink Module including 2 GigaBit 1000 MBps Ports(SM=Single Mode);
		  upl1FO     - Uplink Module including 1 fast fibre optic 100 MBps Ports;
		  upl1TP     - Uplink Module including 1 fast copper   10/100 MBps Ports;
		  upl2FOMM   - Uplink Module including 2 fast fibre optic 100 MBps Ports(MM=Multi  Mode);
		  upl2FOSM   - Uplink Module including 2 fast fibre optic 100 MBps Ports(SM=Single Mode);
		  upl4FOMM   - Uplink Module including 4 fast fibre optic 100 MBps Ports(MM=Multi  Mode);
		  upl4FOSM   - Uplink Module including 4 fast fibre optic 100 MBps Ports(SM=Single Mode);
		  upl8TP     - Uplink Module including 8 fast copper   10/100 MBps Ports;
		  upl1ATM    - Uplink Module including 1 ATM Port;
		  upl1FDDI   - Uplink Module including 1 FDDI Port;
	uplStackModuleNoLink - special Stacking Module with no Link;
	uplStackModuleNH2025 - special Stacking Module Linked with the NH2025 Device;
      uplStackModuleReserve1 - special Stacking Module (Reserve1 for the future purposes);
-- ykfix30 - 14.07.99 - begin
      uplStackModuleReserve2 - special Stacking Module (Reserve2 for the future purposes);
		  upl4TP     - Uplink Module including 4 fast copper   10/100 MBps Ports;
		  upl2FO     - Uplink Module including 2 fast fibre optic 100 MBps Ports(different configuration of the Multi Mode and/or Single Mode Ports);
		  upl2Giga   - Uplink Module including 2 GigaBit 1000 MBps Ports(different configuration of the Multi Mode and/or Single Mode Ports);
-- ykfix31 - 9.08.99  - begin
		  upl4FO     - Uplink Module including 4 fast fibre optic 100 MBps Ports(different configuration of the Multi Mode and/or Single Mode Ports);
		  upl4MTRJ   - Uplink Module including 4 fast fibre optic 100 MBps MTRJ Ports;
		  upl8MTRJ   - Uplink Module including 8 fast fibre optic 100 MBps MTRJ Ports;
		  upl4VF     - Uplink Module including 4 fast fibre optic 100 MBps VF Ports;
-- ykfix33 - 1.03.00 - begin
		  upl8VF     - Uplink Module including 8 fast fibre optic 100 MBps VF Ports;
		  upl4LC     - Uplink Module including 4 fast fibre optic 100 MBps LC Ports;
		  upl8LC     - Uplink Module including 8 fast fibre optic 100 MBps LC Ports;
	  	  upl2FL     - Uplink Module including 2 slow fibre optic 10  MBps FL Ports;
		  upl4FL     - Uplink Module including 4 slow fibre optic 10  MBps FL Ports;
-- ykfix39 - 21.09.00 - begin
		  upl1GigaTP - Uplink Module including 1 GigaBit copper   100/1000 MBps TP Ports;
		  upl1GER    - Uplink Module including 1 GigaBit fibre optic Redundant Port;
		  upl4TP2FO  - Uplink Module including 4 copper 10/100 MBps TP + 2 fast FO 100 MBps Ports;
		  upl4TP1FO  - Uplink Module including 4 copper 10/100 MBps TP + 1 fast FO 100 MBps Ports;
		  upl0TP2FO  - Uplink Module including 0 copper 10/100 MBps TP + 2 fast FO 100 MBps Ports;
		  upl4TP0FO  - Uplink Module including 4 copper 10/100 MBps TP + 0 fast FO 100 MBps Ports;
		 upl1GigaMTRJ- Uplink Module including 1 GigaBit MTRJ fibre optic     1000 MBps Port;
	      upl1GigaStackTP- Uplink Module including 1 GigaBit TP copper 1000 MBps Port for Low Distances(<= 5m);"
-- ykfix39 - 21.09.00 - end
-- ykfix33 - 1.03.00  - end
-- ykfix31 - 9.08.99  - end
-- ykfix30 - 14.07.99 - end
		 ::= { nbsStackSlotUplEntry 3 }
-- ykfix27 - 5.04.99 - end

	 nbsStackSlotUplSwVers     OBJECT-TYPE
	 SYNTAX  INTEGER
	 ACCESS  read-only
         STATUS  mandatory
         DESCRIPTION
		 "This object holds the Software Version of the Uplink Module."
		 ::= { nbsStackSlotUplEntry 4 }

	 nbsStackSlotUplHwVers     OBJECT-TYPE
	 SYNTAX  INTEGER
         ACCESS  read-only
         STATUS  mandatory
         DESCRIPTION
		 "This object holds the Hardware Version of the Uplink Module."
		 ::= { nbsStackSlotUplEntry 5 }

	 nbsStackSlotUplNPorts     OBJECT-TYPE
	 SYNTAX  INTEGER
         ACCESS  read-only
         STATUS  mandatory
         DESCRIPTION
		 "Number of Ports in the current UpLink Module."
		 ::= { nbsStackSlotUplEntry 6 }

	 nbsStackSlotUplFirstPort  OBJECT-TYPE
         SYNTAX    INTEGER
         ACCESS    read-only
         STATUS    mandatory
         DESCRIPTION
		 "This object identifies the number of the First Port
                  in the Uplink Module, according to the Stack Ports Numeration."
		 ::= { nbsStackSlotUplEntry 7 }
       

	 nbsStackSlotUplPortsMask  OBJECT-TYPE
	 SYNTAX  PortsBitmap
	 ACCESS  read-only
         STATUS  mandatory
         DESCRIPTION
		 "Contains the list of the ports in the Uplink Module.
                  The representation is a bit map.
                  Each octet within the value of this object specifies
                  a set of eight ports, with the first octet specifying
                  ports 1 through 8, the second octet specifying ports 9
                  through 16, etc.  Within each octet, the least
                  significant bit represents the lowest numbered
				  port, and the most significant bit represents the
                  highest numbered port.  Thus, each port of the
				  Uplink Module is represented by a single bit within the
                  value of this object.  If that bit has a value of
				  <1> then that port is exists in the Uplink Module.
				  The port is not exists if its bit has a value of <0>."

		 ::= { nbsStackSlotUplEntry 8 }

	 nbsStackSlotUplStatus     OBJECT-TYPE
	 SYNTAX    INTEGER {             
		       up(1),
                       down(2)
		      }
         ACCESS    read-only
         STATUS    mandatory
         DESCRIPTION
		 "Current status of the Uplink Module"
		 ::= { nbsStackSlotUplEntry 9 }

-- ykfix22 - 18.03.99 - begin
	 nbsStackSlotUplHwDescr     OBJECT-TYPE
        SYNTAX  DisplayString
        ACCESS  read-only
        STATUS  mandatory
		DESCRIPTION
		"A description of the Hardware Version of the Uplink Module."
		 ::= { nbsStackSlotUplEntry 10 }

	 nbsStackSlotUplSwDescr     OBJECT-TYPE
        SYNTAX  DisplayString
        ACCESS  read-only
        STATUS  mandatory
		DESCRIPTION
		"A description of the Software Version of the Uplink Module."
		 ::= { nbsStackSlotUplEntry 11 }
-- ykfix22 - 18.03.99 - end

-- ykfix39 - 25.09.00 - begin
	 nbsStackSpecSlotTable OBJECT-TYPE
	 SYNTAX    SEQUENCE OF NbsStackSpecSlotEntry
         ACCESS    not-accessible
         STATUS    mandatory
         DESCRIPTION
                 "Table of descriptive and status information about
	          the Special Slots."
		 ::= { nbsStackInfo 7 }

	 nbsStackSpecSlotEntry OBJECT-TYPE
	 SYNTAX    NbsStackSpecSlotEntry
         ACCESS    not-accessible
         STATUS    mandatory
         DESCRIPTION
                 "An entry in the table, containing information
                  about a single Special Slot."
	 INDEX   { nbsStackSlotSpecNumber,
		   nbsStackSlotSpecUplNumber }
		 ::= { nbsStackSpecSlotTable 1 }

	 NbsStackSpecSlotEntry ::=
	 SEQUENCE   {
		     nbsStackSlotSpecNumber
                          INTEGER,
		     nbsStackSlotSpecUplNumber
                          INTEGER,
		     nbsStackSlotSpecUplRedundantMode
			  INTEGER,
		     nbsStackSlotSpecUplLeftLinkLed
			  INTEGER,
		     nbsStackSlotSpecUplLeftActivityLed
                          INTEGER,
		     nbsStackSlotSpecUplRightLinkLed
			  INTEGER,
		     nbsStackSlotSpecUplRightActivityLed
			  INTEGER
		    }

	 nbsStackSlotSpecNumber	OBJECT-TYPE
         SYNTAX    INTEGER
         ACCESS    read-only
         STATUS    mandatory
         DESCRIPTION
		 "The Special Slot # in the Device."
		 ::= { nbsStackSpecSlotEntry 1 }
       
	 nbsStackSlotSpecUplNumber	OBJECT-TYPE
         SYNTAX    INTEGER
         ACCESS    read-only
         STATUS    mandatory
         DESCRIPTION
		 "The Uplink Module # in the
		  corresponding Special Slot in the Device."
		 ::= { nbsStackSpecSlotEntry 2 }
       
	 nbsStackSlotSpecUplRedundantMode	OBJECT-TYPE
         SYNTAX    INTEGER {
		       other                (1),
		       specialRedundant     (2),
		       autoRedundant        (3),
		       manualLeftRedundant  (4),
		       manualRightRedundant (5)
		      }
	 ACCESS    read-write
         STATUS    mandatory
         DESCRIPTION
		 "Special Slot Additional Status:
		  other=(1)                - unknown Status or Module is not Valid;
		  specialRedundant=(2)     - Both connectors of the GigaBit Redundant Module
		  are connected to the same 2 connectors of the other GigaBit Redundant
		  Module. Module provides automatic quick Redundancy;
		  autoRedundant=(3)        - Each connector of the GigaBit Redundant Module
		  is connected to the Single GigaBit Ethernet Module.
		  Module provides automatic quick Redundancy;
		  manualLeftRedundant =(4),
		  manualRightRedundant=(5) - Each connector of the GigaBit Redundant Module
		  is connected to the Single GigaBit Ethernet Module.
		  Module will force the Link in its Left  Connector as a primary Link, in case of (4).
		  Module will force the Link in its Right Connector as a primary Link, in case of (5)"
		 ::= { nbsStackSpecSlotEntry 3 }

	 nbsStackSlotSpecUplLeftLinkLed	OBJECT-TYPE
	 SYNTAX    INTEGER {
		       other (1),
		       up    (2),
		       down  (3)
		      }
         ACCESS    read-only
	 STATUS    mandatory
         DESCRIPTION
		 "Rx Activity ower Left Connector in the Module."
		 ::= { nbsStackSpecSlotEntry 4 }

	 nbsStackSlotSpecUplLeftActivityLed	OBJECT-TYPE
	 SYNTAX    INTEGER {
		       other (1),
		       up    (2),
		       down  (3)
		      }
         ACCESS    read-only
	 STATUS    mandatory
         DESCRIPTION
		 "Tx Activity ower Left Connector in the Module."
		 ::= { nbsStackSpecSlotEntry 5 }

	 nbsStackSlotSpecUplRightLinkLed	OBJECT-TYPE
	 SYNTAX    INTEGER {
		       other (1),
		       up    (2),
		       down  (3)
		      }
         ACCESS    read-only
	 STATUS    mandatory
         DESCRIPTION
		 "Rx Activity ower Right Connector in the Module."
		 ::= { nbsStackSpecSlotEntry 6 }

	 nbsStackSlotSpecUplRightActivityLed	OBJECT-TYPE
	 SYNTAX    INTEGER {
		       other (1),
		       up    (2),
		       down  (3)
		      }
         ACCESS    read-only
	 STATUS    mandatory
         DESCRIPTION
		 "Tx Activity ower Right Connector in the Module."
		 ::= { nbsStackSpecSlotEntry 7 }
-- ykfix39 - 25.09.00 - end

-- *************************************************************

END
