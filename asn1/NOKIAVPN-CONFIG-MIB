NOKIAVPN-CONFIG-MIB DEFINITIONS ::= BEGIN

IMPORTS  nokiaVPNModules, config
             FROM NOKIAVPN-MIB
         MODULE-IDENTITY, OBJECT-TYPE, NOTIFICATION-TYPE, IpAddress, Integer32
             FROM SNMPv2-SMI;

nokiaVPNConfigMIB MODULE-IDENTITY
    LAST-UPDATED "200101180000Z"
    ORGANIZATION "Nokia Internet Communications."
    CONTACT-INFO 
		 "	Nokia, Inc.
			Customer Support

		  Postal: 100 Enterprise Way, Module B
			Scotts Valley, CA 95066
			USA
                  E-Mail: snmp-contact@cips.nokia.com"

    DESCRIPTION "NokiaVPN Configuration MIB module."
    REVISION "200101180000Z"
    DESCRIPTION "Cleanup."
    ::= { nokiaVPNModules 6 }

configDirtyBit OBJECT-TYPE
    SYNTAX        INTEGER { no(0), yes(1) }
    MAX-ACCESS    read-only
    STATUS        current
    DESCRIPTION   "Says whether the configuration has been changed via a set
		  on any of the writable SNMP variables."
    ::= { config 1 }

configCommit OBJECT-TYPE
    SYNTAX      INTEGER { no(0), yes(1) }
    MAX-ACCESS	read-write
    STATUS	current
    DESCRIPTION "When an SNMP management station sets (changes) a configuration
                 parameter via an SNMP set operation, the SNMP agent code will
                 set a dirty bit.
                 The management station can then submit a set operation on
                 this configCommit variable to write the configuration to flash,
                 thereby committing the change.
                 Performing a read on this variable will return the value
                 of the config dirty bit."
    ::= { config 2 }

configPollrate OBJECT-TYPE
    SYNTAX        Integer32
    MAX-ACCESS    read-only
    STATUS        current
    DESCRIPTION   "Defines how often in seconds SNMP Agent checks system
                   resources for capasity-limit-exceeded -trap
                   sending purposes."
    ::= { config 3 }
	     
configTrapDelay  OBJECT-TYPE
    SYNTAX        Integer32
    MAX-ACCESS    read-only
    STATUS        current
    DESCRIPTION   "Defines how often (at most) one type of trap is sent
                   in seconds."
    ::= { config 4 }
	     

configTresholdCPUUsage  OBJECT-TYPE
    SYNTAX        Integer32
    MAX-ACCESS    read-only
    STATUS        current
    DESCRIPTION   "Defines the treshold (percentage) of CPU utilisation
                   after which a trap is sent."
    ::= { config 5 }
	     
configTresholdIOLoad  OBJECT-TYPE
    SYNTAX        Integer32
    MAX-ACCESS    read-only
    STATUS        current
    DESCRIPTION   "Defines the treshold (pkts/sec divided by
                   system performance rating) of I/O load
                   after which a trap is sent."
    ::= { config 6 }
	     
configTresholdUDPDrop  OBJECT-TYPE
    SYNTAX        Integer32
    MAX-ACCESS    read-only
    STATUS        current
    DESCRIPTION   "Defines the UDP packet drop rate treshold (percentage) after
                   which a trap is sent."
    ::= { config 7 }
	     
configTresholdIPDrop  OBJECT-TYPE
    SYNTAX        Integer32
    MAX-ACCESS    read-only
    STATUS        current
    DESCRIPTION   "Defines the IP packet drop rate treshold (percentage) after
                   which a trap is sent."
    ::= { config 8 }
	     
configTresholdMemUsage  OBJECT-TYPE
    SYNTAX        Integer32
    MAX-ACCESS    read-only
    STATUS        current
    DESCRIPTION   "Defines the memory usage treshold (percentage) after which
                   a trap is sent."
    ::= { config 9 }
	     

configValCPUUsage  OBJECT-TYPE
    SYNTAX        Integer32
    MAX-ACCESS    read-only
    STATUS        current
    DESCRIPTION   "The current CPU (the most loaded CPU) usage (percentage)."
    ::= { config 10 }
	     
configValIOLoad  OBJECT-TYPE
    SYNTAX        Integer32
    MAX-ACCESS    read-only
    STATUS        current
    DESCRIPTION   "The current I/O load (pkts/sec divided by
                   system performance rating) ."
    ::= { config 11 }
	     
configValUDPDrop  OBJECT-TYPE
    SYNTAX        Integer32
    MAX-ACCESS    read-only
    STATUS        current
    DESCRIPTION   "The current UDP packet drop rate (percentage)."
    ::= { config 12 }
	     
configValIPDrop  OBJECT-TYPE
    SYNTAX        Integer32
    MAX-ACCESS    read-only
    STATUS        current
    DESCRIPTION   "The current IP packet drop rate (percentage)."
    ::= { config 13 }
	     
configValMemUsage  OBJECT-TYPE
    SYNTAX        Integer32
    MAX-ACCESS    read-only
    STATUS        current
    DESCRIPTION   "The current memory usage (percentage)."
    ::= { config 14 }
	     

END
