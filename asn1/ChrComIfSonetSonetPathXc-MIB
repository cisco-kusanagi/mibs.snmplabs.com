ChrComIfSonetSonetPathXc-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComIfSonet				FROM  Chromatis-MIB
	TimeTicks			FROM  RFC1155-SMI
	RowStatus				FROM  SonetTypes-MIB;

-- chrComIfSonetSonetPathXc Table

chrComIfSonetSonetPathXcTable		OBJECT-TYPE
	SYNTAX		SEQUENCE OF ChrComIfSonetSonetPathXcEntry
	MAX-ACCESS	not-accessible
	STATUS		current
	DESCRIPTION
	"sonet path cross connect table"
	::= { chrComIfSonet 7}

chrComIfSonetSonetPathXcEntry		OBJECT-TYPE
	SYNTAX		ChrComIfSonetSonetPathXcEntry
	MAX-ACCESS	not-accessible
	STATUS		current
	DESCRIPTION
	""
	INDEX  {  chrComIfSonetSonetPathCrossConnectID, chrComIfSonetSonetPathCrossConnectLowIfindex, chrComIfSonetSonetPathCrossConnectHighIfindex }

--DEFAULT  get-function-async  MNIL_GetRoutine
--DEFAULT  set-function-async  MNIL_SetRoutine
--DEFAULT  next-function-async MNIL_NextRoutine
--DEFAULT  test-function-async MNIL_TestRoutine
--DEFAULT  cookie "SonetPathXc"
	::= { chrComIfSonetSonetPathXcTable  1 }

ChrComIfSonetSonetPathXcEntry  ::=
	SEQUENCE  {
	chrComIfSonetSonetPathCrossConnectID	Unsigned32	(0..4294967295),
	chrComIfSonetSonetPathCrossConnectLowIfindex Unsigned32	(0..4294967295),
	chrComIfSonetSonetPathCrossConnectHighIfindex Unsigned32	(0..4294967295),
	chrComIfSonetSonetPathCrossConnectAdminStatus Unsigned32	(0..4294967295),
	chrComIfSonetSonetPathCrossConnectL2HoperStatus Unsigned32	(0..4294967295),
	chrComIfSonetSonetPathCrossConnectH2LoperStatus Unsigned32	(0..4294967295),
	chrComIfSonetSonetPathCrossConnectL2HlastChange TimeTicks		(0..255),
	chrComIfSonetSonetPathCrossConnectH2LlastChange TimeTicks		(0..255),
	chrComIfSonetrowStatus		RowStatus
}

chrComIfSonetSonetPathCrossConnectID 	OBJECT-TYPE
	SYNTAX		Unsigned32	(0..4294967295)
	MAX-ACCESS 	read-write
	STATUS 		current
	DESCRIPTION
	""
	::= { chrComIfSonetSonetPathXcEntry  1 }

chrComIfSonetSonetPathCrossConnectLowIfindex 	OBJECT-TYPE
	SYNTAX		Unsigned32	(0..4294967295)
	MAX-ACCESS 	read-write
	STATUS 		current
	DESCRIPTION
	""
	::= { chrComIfSonetSonetPathXcEntry  2 }

chrComIfSonetSonetPathCrossConnectHighIfindex 	OBJECT-TYPE
	SYNTAX		Unsigned32	(0..4294967295)
	MAX-ACCESS 	read-write
	STATUS 		current
	DESCRIPTION
	""
	::= { chrComIfSonetSonetPathXcEntry  3 }

chrComIfSonetSonetPathCrossConnectAdminStatus 	OBJECT-TYPE
	SYNTAX		Unsigned32	(0..4294967295)
	MAX-ACCESS 	read-write
	STATUS 		current
	DESCRIPTION
	""
	::= { chrComIfSonetSonetPathXcEntry  4 }

chrComIfSonetSonetPathCrossConnectL2HoperStatus 	OBJECT-TYPE
	SYNTAX		Unsigned32	(0..4294967295)
	MAX-ACCESS 	read-only
	STATUS 		current
	DESCRIPTION
	""
	::= { chrComIfSonetSonetPathXcEntry  5 }

chrComIfSonetSonetPathCrossConnectH2LoperStatus 	OBJECT-TYPE
	SYNTAX		Unsigned32	(0..4294967295)
	MAX-ACCESS 	read-only
	STATUS 		current
	DESCRIPTION
	""
	::= { chrComIfSonetSonetPathXcEntry  6 }

chrComIfSonetSonetPathCrossConnectL2HlastChange 	OBJECT-TYPE
	SYNTAX		TimeTicks		(0..255)
	MAX-ACCESS 	read-only
	STATUS 		current
	DESCRIPTION
	""
	::= { chrComIfSonetSonetPathXcEntry  7 }

chrComIfSonetSonetPathCrossConnectH2LlastChange 	OBJECT-TYPE
	SYNTAX		TimeTicks		(0..255)
	MAX-ACCESS 	read-only
	STATUS 		current
	DESCRIPTION
	""
	::= { chrComIfSonetSonetPathXcEntry  8 }

chrComIfSonetrowStatus 	OBJECT-TYPE
	SYNTAX		RowStatus
	MAX-ACCESS 	read-write
	STATUS 		current
	DESCRIPTION
	""
	::= { chrComIfSonetSonetPathXcEntry  9 }


END
