NRC-HUB1-MIB	DEFINITIONS ::= BEGIN

IMPORTS
		Counter FROM RFC1155-SMI
		DisplayString		FROM RFC1213-MIB
		OBJECT-TYPE		FROM RFC-1212;

enterprises	OBJECT IDENTIFIER ::= { 1 3 6 1 4 1 }
nrc		OBJECT IDENTIFIER ::= { enterprises 315 }
hub1		OBJECT IDENTIFIER ::= { nrc 1 }

--
-- NRC HUB 1 Group
--

hub1AutoPartition	OBJECT-TYPE
		SYNTAX	INTEGER { enabled(1), disabled(2) }
		ACCESS	read-write
		STATUS	mandatory
		DESCRIPTION	"The value 'enabled' indicates that
				the HUB should auto partition ports.

				The value 'disabled' will disable
				this feature."
		::= { hub1 1 }

hub1ReconnectOnTransmission
				OBJECT-TYPE
		SYNTAX	INTEGER { enabled(1), disabled(2) }
		ACCESS	read-write
		STATUS	mandatory
		DESCRIPTION	"The value 'enabled' indicates that
				the HUB will reconnect an auto 
				partitioned port if the HUB receives
				a packet from a partitioned port.

				The value 'disabled' indicates that  
				the HUB will reconnect a partitioned 
				port if there is any traffic to or 
				from the port."
		::= { hub1 2 }

hub1IncludeOutOfWinColl
				OBJECT-TYPE
		SYNTAX	INTEGER { enabled(1), disabled(2) }
		ACCESS	read-write
		STATUS	mandatory
		DESCRIPTION	"A value of 'enabled' will cause Out Of
				Window Collisions to be counted along
				with In Window Collisions (as defined by
				IEEE 802.3)  when determining if the
				collision count has exceeded
				hub1CollisionLimit and a port should be
				auto partitioned.

				A value of 'disabled' indicates that Out
				Of Window Collisions should NOT be counted
				when determining if the collision count
				has exceeded hub1CollisionLimit and a 
				and a port should be auto partitioned."

		::= { hub1 3 }

hub1LoopbackPartition
				OBJECT-TYPE
		SYNTAX	INTEGER { enabled(1), disabled(2) }
		ACCESS	read-write
		STATUS	mandatory
		DESCRIPTION	"A value of 'enabled' will cause the
				HUB to automatically partition a 
				port where a lack of loopback from
				the transeiver is detected.

				A value of 'disabled' will disable 
				this feature.

				Note: Setting this variable will only
				effect HUB operation when hub1PortType
				value	equals 'thinNet-10Base2'. For all
				other hub1PortType values, a value of
				'enabled' will have no effect."
		::= { hub1 4 }

hub1CollisionLimit	OBJECT-TYPE
		SYNTAX	INTEGER { low(31), high(63) }
		ACCESS	read-write
		STATUS	mandatory
		DESCRIPTION	"If consecutive collisions exceeding the
				value of this variable are detected on
				a port, the port will be auto partitioned
				31 is the IEEE 802.3 consecutive collision
				limit."
		::= { hub1 5 }

hub1CarrierRecoverTime
				OBJECT-TYPE
		SYNTAX	INTEGER { short(3), long(5) }
		ACCESS	read-write
		STATUS	mandatory
		DESCRIPTION	"Time to recover carrier.  A value 
				of 'short' will use 3 bit times (IEEE 802.3
				specification). A value of 'long' will use
				5 bit times."
		::= { hub1 6 }

hub1EventCounterFlags
				OBJECT-TYPE
		SYNTAX	OCTET STRING (SIZE (2))
		ACCESS	read-write
		STATUS	mandatory
		DESCRIPTION	"A bit mask indicating which error types
				will cause an increment in the 
				hub1PortEventCount Counter.

				Each bit has the following significance 
				where each bit is listed from most
				significant bit of the first octet, to
				least significant bit of the second octet.

				High (first) Octet
				  bit

				  8	- not used -
				  7	- not used -
				  6	Out Of Window Collision Count Enable
				  5	Receive Collision Count Enable
				  4	Transmit Collision Count Enable
				  3	- not used -
				  2	- not used -
				  1	- not used -

				Low (second) Octet
				  bit

				  8	Bad Link Count Enable
				  7	Partition Count Enable
				  6	Receive Count Enable
				  5	Pygmy Packet Enable
				  4	Non SFD Enable
				  3	Phase Lock Error Enable
				  2	Elasticity Buffer Error Enable
				  1	Jabber Enable

				When setting the value of this variable,
				the entire bit mask must be specified and
				the '-not used-' bits must not be set."
		::= { hub1 7 }

hub1EventRecordFlags	OBJECT-TYPE
		SYNTAX	OCTET STRING (SIZE (1))
		ACCESS	read-write
		STATUS	mandatory
		DESCRIPTION	"A bit mask indicating which error types
				will cause corresponding bits in 
				hub1PortEventRecordValue to be set when
				an error is detected.

				Each bit has the following significance 
				where bits are listed from most
				significant bit to least significant bit.

				  bit

				  8	Bad Link Enable
				  7	Partition Enable
				  6	Out Of Window Collision Enable
				  5	Pygmy Packet Enable
				  4	Non SFD Enable
				  3	Phase Lock Error Enable
				  2	Elasticity Buffer Error Enable
				  1	Jabber Enable

				When a particular bit is set, all ports 
				will start to log the specified error in 
				the hub1PortEventRecordValue column of the
				port's row of the hub1PortTable.

				For example, if bit 1 (Jabber Enable) is
				set, then for every port, a detected
				Jabber Error would cause bit 1 of 
				hub1PortEventRecordValue to be set.
	
				When setting the value of this variable,
				the entire bit mask must be specified.
				When this mask is set, hub1PortRecordValue
				for all ports is cleared."
		::= { hub1 8 }

hub1BridgingMode	OBJECT-TYPE
		SYNTAX	INTEGER {
					bridging (1),
					bypass (2)
				}
		ACCESS	read-write
		STATUS	mandatory
		DESCRIPTION	"Operational mode of the bridge:

				    bridging	Packets are being
							selectively forwarded 
							according to the internal 
							dynamically built tables.

				    bypass		All packets are being 
							repeated between the
							backbone and the repeater
							ports.  The bridge logic
							is disabled.

				After setting this variable the HUB 
				must be reset for the new value to take
				effect.

				NOTE: FOIRL Hubs can only have the
					value 'bypass' for this variable.
					Attempts to set this variable to
					'bridging' on FOIRL hubs will be
					rejected."
		::= { hub1 9 }

hub1ProtocolFilterMode	
				OBJECT-TYPE
		SYNTAX	INTEGER {
					off (1),
					filter (2),
					pass (3)
				}
		ACCESS	read-write
		STATUS	mandatory
		DESCRIPTION	"Filtering Mode of the Hub:

					off		The protocol filtering
							logic is disabled. 
							
					filter	The protocol filtering
							logic is enabled and
							packets with the 
							protocol types indicated
							in hubFilterProtocols
							will not be forwarded by
							the bridge.

					pass		The packet filtering
							logic is enabled and
							packets with the 
							protocol types indicated
							in hubFilterProtocols
							will be the ONLY packets
							that the bridge will
							forward."
		::= { hub1 10 }

hub1FilterProtocols	OBJECT-TYPE
		SYNTAX	OCTET STRING (SIZE (0..32))			
		ACCESS	read-write
		STATUS	mandatory
		DESCRIPTION	"Protocol types to be filtered or passed
				by the bridging logic.  This is a variable
				length array of between 0 and 16 2-byte
				entries, each entry containing the 2-byte
				protocol identifier as seen in the Ethernet
				header.

				Attempts to configure this variable with
				an OCTET STRING of odd length will be
				rejected."
		::= { hub1 11 }

hub1ConsoleBaudRate	OBJECT-TYPE
		SYNTAX	INTEGER
		ACCESS	read-write
		STATUS	mandatory
		DESCRIPTION	"The baud rate of the console port.  Legal
				values are 9600, 4800, 2400, and 1200."
		::= { hub1 12 }

hub1Reset	OBJECT-TYPE
		SYNTAX	INTEGER {
					no-reset (1),
					reset (2)
				}
		ACCESS	read-write
		STATUS	mandatory
		DESCRIPTION	"Setting this object to 'reset' will
				cause the Hub1 to perform a hardware
				reset within approximately 5 seconds.

				Setting this object to 'no-reset will
				have no effect.  The value 'no-reset
				will be returned whenever this object
				is retrieved.

				The primary purpose for including this
				variable in the Hub1 MIB is to allow
				SNMP managers to modify the operational
				mode of the Hub1.  Changing the variable
				hub1BridgingMode has no effect on the
				Hub until the Hub is reset."
		::= { hub1 13 }

hub1SoftwareVersion	OBJECT-TYPE
		SYNTAX	DisplayString (SIZE (0..15))
		ACCESS	read-write
		STATUS	mandatory
		DESCRIPTION	"The version of software running on the
				Hub.  On versions of the Hub that support
				dynamic download, this variable may be
				set to cause a new version of the 
				software to be loaded the next time
				the Hub is reset (as in setting the 
				variable hub1Reset or power cycling the
				unit).  The version should be specified in
				the following format:

					'MM.mm.rr'

				Where MM is the major number, mm is the
				minor number, and rr is the revision level
				(for example 2.0.16).

				On versions of the Hub that do not support
				dynamic download, setting this variable 
				will result in an error."
		::= { hub1 14 }

--
-- HUB 1 Ports Table
--

hub1PortTable		OBJECT-TYPE
		SYNTAX	SEQUENCE OF Hub1PortEntry
		ACCESS	not-accessible
		STATUS	mandatory
		DESCRIPTION	"A table of port specific information
				for the NRC HUB 1 product.  This table
				supplements the Repeater MIB Ports Table."
		::= { hub1 15 }

hub1PortEntry		OBJECT-TYPE
		SYNTAX	Hub1PortEntry
		ACCESS	not-accessible
		STATUS	mandatory
		DESCRIPTION	"A list of information for every port."
		INDEX		{ hub1PortIndex }
		::= { hub1PortTable 1 }

Hub1PortEntry ::= SEQUENCE {
		hub1PortIndex			INTEGER,
		hub1PortForceReconnect		INTEGER,
		hub1PortPartitionReason		INTEGER,
		hub1PortLinkState			INTEGER,
		hub1PortLinkEnable		INTEGER,
		hub1PortPolarityStatus		INTEGER,
		hub1PortName			DisplayString,
		hub1PortEventCount		INTEGER,
		hub1PortEventRecordValue	OCTET STRING,
		hub1PortType			INTEGER
}

hub1PortIndex		OBJECT-TYPE
		SYNTAX	INTEGER (1..24)
		ACCESS	read-only
		STATUS	mandatory
		DESCRIPTION	"Port number that corresponds to the index
				value in the Repeater MIB variable
				rptrPortIndex."
		::= { hub1PortEntry 1 }

hub1PortForceReconnect		
				OBJECT-TYPE
		SYNTAX	INTEGER { idle(1), force-reconnect(2) }
		ACCESS	read-write
		STATUS	mandatory
		DESCRIPTION	"Setting this variable to the value 'force-
				reconnect' will cause the port to be
				reconnected assuming that it is currently
				in the 'Partition' state. If the port is
				not in a 'Partition' state, setting
				variable to the value 'force-reconnect'
				will not have any effect. Setting this
				variable to anything other than 'force-
				reconnect will and an undefined effect.

				When retrieving this variable, the value
				'idle' will always be returned."

		::= { hub1PortEntry 2 }

hub1PortPartitionReason		
				OBJECT-TYPE
		SYNTAX	INTEGER {
					not-partitioned (1),
					other (2),
					consecutive-collision-limit (3),
					excessive-len-of-collision-limit (4),
					data-loopback-failure (5),
					process-forced-reconnection (6)
				}
		ACCESS	read-only
		STATUS	mandatory
		DESCRIPTION	"Reason for port being in the partitioned
				state.  If the port is currently not
				partitioned, this variable will have the
				value 'not-partitioned'."
		::= { hub1PortEntry 3 }	

hub1PortLinkState	OBJECT-TYPE
		SYNTAX	INTEGER { unknown(1), up(2), down(3) }
		ACCESS	read-only 
		STATUS	mandatory
		DESCRIPTION	"This variable's meaning varies depending
				on the type of HUB:

				10Base2	Not Applicable.  A value of
						'unknown' will always be 
						returned.

				10BaseT	Link Test is being received
						('up') or not being received
						('down').

				Fiber		Light Monitoring (LMON) is 
						being detected ('up') or not 
						being detected ('down')."
		::= { hub1PortEntry 4 }

hub1PortLinkEnable	OBJECT-TYPE
		SYNTAX	INTEGER { enabled(1), disabled(2) }
		ACCESS	read-write
		STATUS	mandatory
		DESCRIPTION	"Enabling this variable has the following
				effect depending on the type of HUB:

				10Base2	No Effect

				10BaseT	Link Test Enabled

				Fiber		LMON Test Enabled"
		::= { hub1PortEntry 5 }

hub1PortPolarityStatus	
				OBJECT-TYPE
		SYNTAX	INTEGER { ok(1), reversed(2) }
		ACCESS	read-only
		STATUS	mandatory
		DESCRIPTION	"Current port Polarity status. 

				NOTE: a value of 'ok' will always
					be returned for 10Base2 and FOIRL
					HUBs"
		::= { hub1PortEntry 6 }

hub1PortName		OBJECT-TYPE
		SYNTAX	DisplayString (SIZE (0..32))
		ACCESS	read-write
		STATUS	mandatory
		DESCRIPTION	"Administrator assigned ASCII port name."
		::= { hub1PortEntry 7 }

hub1PortEventCount	OBJECT-TYPE
		SYNTAX	INTEGER
		ACCESS	read-only
		STATUS	mandatory
		DESCRIPTION	"Counter of all error events that were
				detected on this port and at the same 
				time were marked for collection in the
				hub1EventCounterFlags variable.

				This is a 16 bit wrapping counter."
		::= { hub1PortEntry 8 }

hub1PortRecordValue	OBJECT-TYPE
		SYNTAX	OCTET STRING (SIZE (1))
		ACCESS	read-only
		STATUS	mandatory
		DESCRIPTION	"Bit Mask that has bits set for each error
				event that was detected on this port and at
				the same time was marked for collection in
				the hub1EventRecordFlags variable.

				Each bit has the following meaning, where
				the bits are listed from most significant
				to least significant:

				  bit

				  8	Bad Link Count Error
				  7	Partition Count Error
				  6	Receive Count Error
				  5	Pygmy Packet Error
				  4	Non SFD Error
				  3	Phase Lock Error
				  2	Elasticity Buffer Error
				  1	Jabber Error

				Each read of this variable causes the
				variable to be cleared."
		::= { hub1PortEntry 9 }

hub1PortType		OBJECT-TYPE
		SYNTAX	INTEGER {
					other				(1),
					twistedPair-10BaseT	(2),
					thinNet-10Base2		(3),
					fiber-FOIRL			(4)
				}
		ACCESS	read-only
		STATUS	mandatory
		DESCRIPTION	"The type of port"
		::= { hub1PortEntry 10 }


--
-- HUB 1 Interfaces 
--

hub1IFTable		OBJECT-TYPE
		SYNTAX	SEQUENCE OF Hub1IFEntry
		ACCESS	not-accessible
		STATUS	mandatory
		DESCRIPTION	"A table that contains HUB 1 specific
				supplements to the MIB-II interfaces 
				table."
	::= { hub1 16 }

hub1IFEntry		OBJECT-TYPE
		SYNTAX	Hub1IFEntry
		ACCESS	not-accessible
		STATUS	mandatory
		DESCRIPTION	"Entries in the HUB 1 supplement table."
		INDEX		{ hub1IFIndex }
		::= { hub1IFTable 1 }

Hub1IFEntry ::= SEQUENCE {
		hub1IFIndex				INTEGER,
		hub1IFInAlignmentErrors		Counter,
		hub1IFInCrcErrors			Counter,
		hub1IFInCollisions		Counter,
		hub1IFInMtuExceededDiscards	Counter,
		hub1IFInShortErrors		Counter,
		hub1IFInOverrunDiscards		Counter,
		hub1IFOutUnderruns		Counter,
		hub1IFOutLostCts			Counter,
		hub1IFOutLostCrs			Counter,
		hub1IFOutMtuExceededDiscards	Counter,
		hub1IFOutCollisions		Counter,
		hub1IFChannelUtilization	OCTET STRING
}

hub1IFIndex		OBJECT-TYPE
		SYNTAX	INTEGER
		ACCESS	read-only
		STATUS	mandatory
		DESCRIPTION	"Interface index that corresponds to
				ifIndex in the interfaces table from
				MIB II."
		::= { hub1IFEntry 1 }

hub1IFInAlignmentErrors	
				OBJECT-TYPE
		SYNTAX	Counter
		ACCESS	read-only
		STATUS	mandatory
		DESCRIPTION	"The number of alignment errors detected
				by this interface."
		::= { hub1IFEntry 2 }

hub1IFInCrcErrors	OBJECT-TYPE
		SYNTAX	Counter
		ACCESS	read-only
		STATUS	mandatory
		DESCRIPTION	"The number of CRC errors detected by
				this interface."
		::= { hub1IFEntry 3 }

hub1IFInCollisions	OBJECT-TYPE
		SYNTAX	Counter
		ACCESS	read-only
		STATUS	mandatory
		DESCRIPTION	"The number of collisions detected by this
				interface."
		::= { hub1IFEntry 4 }

hub1IFInMtuExceededDiscards	
				OBJECT-TYPE
		SYNTAX	Counter
		ACCESS	read-only
		STATUS	mandatory
		DESCRIPTION	"The number of frames discarded by this
				interface on receive due to an excessive
				size."
		::= { hub1IFEntry 5 }

hub1IFInShortErrors	OBJECT-TYPE
		SYNTAX	Counter
		ACCESS	read-only
		STATUS	mandatory
		DESCRIPTION	"The number of frames discarded by this
				interface because they were less than the
				Ethernet minumum frame size of 64 bytes."
		::= { hub1IFEntry 6 }

hub1IFInOverrunDiscards	
				OBJECT-TYPE
		SYNTAX	Counter
		ACCESS	read-only
		STATUS	mandatory
		DESCRIPTION	"The number of frames discarded by this
				interface due to a LAN Controller FIFO
				overflow on receive."
		::= { hub1IFEntry 7 }

hub1IFOutUnderruns	OBJECT-TYPE
		SYNTAX	Counter
		ACCESS	read-only
		STATUS	mandatory
		DESCRIPTION	"The number of frames which had to be
				retransmitted by this interface due to a
				LAN Controller FIFO underrun error on
				transmit." 
		::= { hub1IFEntry 8 }

hub1IFOutLostCts	OBJECT-TYPE
		SYNTAX	Counter
		ACCESS	read-only
		STATUS	mandatory
		DESCRIPTION	"The number of times Carrier Transmit Sense
				(CTS) was lost on this interface during
				frame transmission. The hub will attempt to
				retransmit frames when transmission fails
				due to lost CTS."
		::= { hub1IFEntry 9 }

hub1IFOutLostCrs	OBJECT-TYPE
		SYNTAX	Counter
		ACCESS	read-only
		STATUS	mandatory
		DESCRIPTION	"The number of times Carrier Receive Sense
				(CRS) was lost on this interface during
				frame transmission. The hub will attempt to
				retransmit frames when transmission fails
				due to lost CRS."
		::= { hub1IFEntry 10 }

hub1IFOutMtuExceededDiscards	
				OBJECT-TYPE
		SYNTAX	Counter
		ACCESS	read-only
		STATUS	mandatory
		DESCRIPTION	"The number of frames discarded by this
				interface on transmit due to an excessive
				size."
		::= { hub1IFEntry 11 }

hub1IFOutCollisions	OBJECT-TYPE
		SYNTAX	Counter
		ACCESS	read-only
		STATUS	mandatory
		DESCRIPTION	"The number of collisions detected by this
				interface while attempting to transmit a
				packet."
		::= { hub1IFEntry 12 }

hub1IFChannelUtilization
				OBJECT-TYPE
		SYNTAX	OCTET STRING (SIZE (90))
		ACCESS	read-only
		STATUS	mandatory
		DESCRIPTION	"Utilization statistics for the last 60
				seconds of operation of the bridging
				logic associated with this interface.  The
				OCTET STRING is a series of 45 16-bit
				words, each word representing the
				percentage utilization for a 1.33 second
				sample period.  The first 16 bit word
				in this series represents the oldest
				sample.

				Percentages are calculated by passing each
				16 bit sample through the following
				equation:

					((Sample) * 100) / 0xffff

				to yield the percent channel utilization
				(a number ranging from 0 to 100)."
		::= { hub1IFEntry 13 }

--
--	This is a continuation of the Hub1 Group
--
hub1LastFailureReason
				OBJECT-TYPE
		SYNTAX	INTEGER
		ACCESS	read-only
		STATUS	mandatory
		DESCRIPTION	"The last error that caused a Hub failure.

				A value of zero (0) indicates that there
				has not been a Hub failure since the novram
				was last erased.

				A non-zero value indicates the reason for 
				the last Hub failure.  A normal Hub reset 
				or power cycle will not change the value 
				of this variable (it will still indicate 
				the reason for the last known failure."
		::= { hub1 17 } 


END
