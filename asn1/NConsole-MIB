NConsole-MIB DEFINITIONS ::= BEGIN
 
IMPORTS
		DisplayString FROM SNMPv2-TC
	TimeTicks, OBJECT-TYPE, enterprises FROM RFC1155-SMI;

avanti			OBJECT IDENTIFIER ::= { enterprises 1117 }
nconsolemib		OBJECT IDENTIFIER ::= { avanti 1 }
serverinfo		OBJECT IDENTIFIER ::= { nconsolemib 1 }
configinfo		OBJECT IDENTIFIER ::= { nconsolemib 2 }
memoryinfo		OBJECT IDENTIFIER ::= { nconsolemib 3 }
moduleinfo		OBJECT IDENTIFIER ::= { nconsolemib 4 }
netinfo			OBJECT IDENTIFIER ::= { nconsolemib 5 }
nicstats		OBJECT IDENTIFIER ::= { nconsolemib 6 }
setparminfo		OBJECT IDENTIFIER ::= { nconsolemib 7 }
serverstats		OBJECT IDENTIFIER ::= { nconsolemib 8 }
servertrends		OBJECT IDENTIFIER ::= { nconsolemib 9 }
volinfo			OBJECT IDENTIFIER ::= { nconsolemib 10 }
voltrends		OBJECT IDENTIFIER ::= { nconsolemib 11 }
driveinfo		OBJECT IDENTIFIER ::= { nconsolemib 12 }
drivetrends		OBJECT IDENTIFIER ::= { nconsolemib 13 }
nictrends		OBJECT IDENTIFIER ::= { nconsolemib 14 }
protocolinfo		OBJECT IDENTIFIER ::= { nconsolemib 15 }
protocoltrends		OBJECT IDENTIFIER ::= { nconsolemib 16 }
sftserverinfo		OBJECT IDENTIFIER ::= { nconsolemib 17 }
sftmemoryinfo		OBJECT IDENTIFIER ::= { nconsolemib 18 }
sftmoduleinfo		OBJECT IDENTIFIER ::= { nconsolemib 19 }
sftnetinfo		OBJECT IDENTIFIER ::= { nconsolemib 20 }
sftsetparminfo		OBJECT IDENTIFIER ::= { nconsolemib 21 }
sftservertrends		OBJECT IDENTIFIER ::= { nconsolemib 22 }
smpinfo			OBJECT IDENTIFIER ::= { nconsolemib 23 }
smptrends		OBJECT IDENTIFIER ::= { nconsolemib 24 }



	serverName OBJECT-TYPE
	    SYNTAX DisplayString (SIZE (0..64))
	    ACCESS read-only
	    STATUS mandatory
	    DESCRIPTION
		"Name"
	::= { serverinfo 1 }

	serverNwRevInfo OBJECT-TYPE
	    SYNTAX DisplayString (SIZE (0..128))
	    ACCESS read-only
	    STATUS mandatory
	    DESCRIPTION
		"NOS Revision Info"
	::= { serverinfo 2 }

	serverNwSerialNumber OBJECT-TYPE
	    SYNTAX INTEGER
	    ACCESS read-only
	    STATUS mandatory
	    DESCRIPTION
		"NOS Serial Number"
	::= { serverinfo 3 }

	serverTimeLocal OBJECT-TYPE
	    SYNTAX DisplayString (SIZE (0..32))
	    ACCESS read-only
	    STATUS mandatory
	    DESCRIPTION
		"Time Local (string)"
	::= { serverinfo 4 }

	serverTimeUTC OBJECT-TYPE
	    SYNTAX INTEGER
	    ACCESS read-only
	    STATUS mandatory
	    DESCRIPTION
		"Time GMT (UTC secs)"
	::= { serverinfo 5 }

	serverUpTime OBJECT-TYPE
	    SYNTAX TimeTicks
	    ACCESS read-only
	    STATUS mandatory
	    DESCRIPTION
		"Up-Time (Ticks)"
	::= { serverinfo 6 }

	serverCpuUtil OBJECT-TYPE
	    SYNTAX INTEGER
	    ACCESS read-only
	    STATUS mandatory
	    DESCRIPTION
		"Utilization"
	::= { serverinfo 7 }

	serverCpuCount OBJECT-TYPE
	    SYNTAX INTEGER
	    ACCESS read-only
	    STATUS mandatory
	    DESCRIPTION
		"Installed CPU Count"
	::= { serverinfo 8 }

	serverCpuSpeed OBJECT-TYPE
	    SYNTAX INTEGER
	    ACCESS read-only
	    STATUS mandatory
	    DESCRIPTION
		"CPU Speed (per NetWare)"
	::= { serverinfo 9 }

	serverCacheHits OBJECT-TYPE
	    SYNTAX INTEGER
	    ACCESS read-only
	    STATUS mandatory
	    DESCRIPTION
		"Cache Hit Ratio (%)"
	::= { serverinfo 10 }

	serverCacheLRU OBJECT-TYPE
	    SYNTAX TimeTicks
	    ACCESS read-only
	    STATUS mandatory
	    DESCRIPTION
		"Cache LRU (secs)"
	::= { serverinfo 11 }

	serverCacheRatio OBJECT-TYPE
	    SYNTAX INTEGER
	    ACCESS read-only
	    STATUS mandatory
	    DESCRIPTION
		"Cache Buffer Ratio (%)"
	::= { serverinfo 12 }

	serverLicenses OBJECT-TYPE
	    SYNTAX INTEGER
	    ACCESS read-only
	    STATUS mandatory
	    DESCRIPTION
		"Installed License Count"
	::= { serverinfo 13 }

	serverConns OBJECT-TYPE
	    SYNTAX INTEGER
	    ACCESS read-only
	    STATUS mandatory
	    DESCRIPTION
		"Active Connections"
	::= { serverinfo 14 }

	serverUsers OBJECT-TYPE
	    SYNTAX INTEGER
	    ACCESS read-only
	    STATUS mandatory
	    DESCRIPTION
		"Logged-in Users"
	::= { serverinfo 15 }

	serverAllowUnencryptedPwds OBJECT-TYPE
	    SYNTAX DisplayString (SIZE (0..4))
	    ACCESS read-only
	    STATUS mandatory
	    DESCRIPTION
		"Unencrypted Passwords Allowed (ON/OFF)"
	::= { serverinfo 16 }

	serverDOSPresent OBJECT-TYPE
	    SYNTAX DisplayString (SIZE (0..8))
	    ACCESS read-only
	    STATUS mandatory
	    DESCRIPTION
		"DOS Status (Present/Removed)"
	::= { serverinfo 17 }

	serverLoginStatus OBJECT-TYPE
	    SYNTAX DisplayString (SIZE (0..10))
	    ACCESS read-only
	    STATUS mandatory
	    DESCRIPTION
		"Login Status (Enabled/Disabled)"
	::= { serverinfo 18 }

	serverRemoteStatus OBJECT-TYPE
	    SYNTAX DisplayString (SIZE (0..12))
	    ACCESS read-only
	    STATUS mandatory
	    DESCRIPTION
		"REMOTE.NLM Status (Loaded/Not Loaded)"
	::= { serverinfo 19 }

	serverSecurityRestrictionLevel OBJECT-TYPE
	    SYNTAX INTEGER
	    ACCESS read-only
	    STATUS mandatory
	    DESCRIPTION
		"Security Restriction Level"
	::= { serverinfo 20 }

	serverNumOfActiveDrives OBJECT-TYPE
	    SYNTAX INTEGER
	    ACCESS read-only
	    STATUS mandatory
	    DESCRIPTION
		"# of Active Drives"
	::= { serverinfo 21 }

	serverNumOfMountedVols OBJECT-TYPE
	    SYNTAX INTEGER
	    ACCESS read-only
	    STATUS mandatory
	    DESCRIPTION
		"# of Mounted Volumes"
	::= { serverinfo 22 }

	serverStartupFilePath OBJECT-TYPE
	    SYNTAX DisplayString (SIZE (0..256))
	    ACCESS read-only
	    STATUS mandatory
	    DESCRIPTION
		"STARTUP.NCF full path"
	::= { serverinfo 23 }

	serverAutoexecFilePath OBJECT-TYPE
	    SYNTAX DisplayString (SIZE (0..256))
	    ACCESS read-only
	    STATUS mandatory
	    DESCRIPTION
		"AUTOEXEC.NCF full path"
	::= { serverinfo 24 }



	configVersion OBJECT-TYPE
	    SYNTAX DisplayString (SIZE (0..7))
	    ACCESS read-only
	    STATUS mandatory
	    DESCRIPTION
		"NConsole Version Info"
	::= { configinfo 1 }

	configCycleLength OBJECT-TYPE
	    SYNTAX INTEGER
	    ACCESS read-only
	    STATUS mandatory
	    DESCRIPTION
		"NConsole Cycle Length (mins.)"
	::= { configinfo 2 }

	configStartTime OBJECT-TYPE
	    SYNTAX DisplayString (SIZE (0..6))
	    ACCESS read-only
	    STATUS mandatory
	    DESCRIPTION
		"NConsole Cycle Start Time (NULL = N/A else hh:mm)"
	::= { configinfo 3 }

	configStopTime OBJECT-TYPE
	    SYNTAX DisplayString (SIZE (0..6))
	    ACCESS read-only
	    STATUS mandatory
	    DESCRIPTION
		"NConsole Cycle Stop Time (NULL = N/A else hh:mm)"
	::= { configinfo 4 }

	configKeyboardStatus OBJECT-TYPE
	    SYNTAX DisplayString (SIZE (0..9))
	    ACCESS read-only
	    STATUS mandatory
	    DESCRIPTION
		"NConsole Keyboard Lock Status (Locked/Unlocked)"
	::= { configinfo 5 }

	configKeyboardAutoLock OBJECT-TYPE
	    SYNTAX DisplayString (SIZE (0..4))
	    ACCESS read-only
	    STATUS mandatory
	    DESCRIPTION
		"NConsole Keyboard Auto Lock Status (On/Off)"
	::= { configinfo 6 }

	configScreenSaverTimeout OBJECT-TYPE
	    SYNTAX INTEGER
	    ACCESS read-only
	    STATUS mandatory
	    DESCRIPTION
		"NConsole Screen Saver Timeout (mins.)"
	::= { configinfo 7 }

	configArchiveStatus OBJECT-TYPE
	    SYNTAX DisplayString (SIZE (0..9))
	    ACCESS read-only
	    STATUS mandatory
	    DESCRIPTION
		"NConsole Log File Archive Status (Enabled/Disabled)"
	::= { configinfo 8 }

	configArchiveMaxDays OBJECT-TYPE
	    SYNTAX INTEGER
	    ACCESS read-only
	    STATUS mandatory
	    DESCRIPTION
		"NConsole Log File Max Archive Period (Days, if Enabled)"
	::= { configinfo 9 }

	configDataFileName OBJECT-TYPE
	    SYNTAX DisplayString (SIZE (0..256))
	    ACCESS read-only
	    STATUS mandatory
	    DESCRIPTION
		"NConsole ASCII Delimited Log File (NULL, if Disabled)"
	::= { configinfo 10 }

	configDataFileFormat OBJECT-TYPE
	    SYNTAX DisplayString (SIZE (0..64))
	    ACCESS read-only
	    STATUS mandatory
	    DESCRIPTION
		"NConsole ASCII Delimited Log File Format"
	::= { configinfo 11 }

	configLogFileName OBJECT-TYPE
	    SYNTAX DisplayString (SIZE (0..256))
	    ACCESS read-only
	    STATUS mandatory
	    DESCRIPTION
		"NConsole ASCII Print Log File (NULL, if Disabled)"
	::= { configinfo 12 }

	configTrendFileName OBJECT-TYPE
	    SYNTAX DisplayString (SIZE (0..256))
	    ACCESS read-only
	    STATUS mandatory
	    DESCRIPTION
		"NConsole Trend File (NULL, if Disabled)"
	::= { configinfo 13 }

	configTrendMaxDays OBJECT-TYPE
	    SYNTAX INTEGER
	    ACCESS read-only
	    STATUS mandatory
	    DESCRIPTION
		"NConsole Max Trend Period (Days, if Enabled)"
	::= { configinfo 14 }



	memoryTotalRAM OBJECT-TYPE
	    SYNTAX INTEGER
	    ACCESS read-only
	    STATUS mandatory
	    DESCRIPTION
		"Total Configured RAM"
	::= { memoryinfo 1 }

	memoryServerWorkRAM OBJECT-TYPE
	    SYNTAX INTEGER
	    ACCESS read-only
	    STATUS mandatory
	    DESCRIPTION
		"Total Work RAM"
	::= { memoryinfo 2 }

	memoryDOS OBJECT-TYPE
	    SYNTAX INTEGER
	    ACCESS read-only
	    STATUS mandatory
	    DESCRIPTION
		"Conventional Memory Used by DOS"
	::= { memoryinfo 3 }

	memoryBaseRAM OBJECT-TYPE
	    SYNTAX INTEGER
	    ACCESS read-only
	    STATUS mandatory
	    DESCRIPTION
		"Conventional Memory Available to NetWare"
	::= { memoryinfo 4 }

	memoryAllocPoolTotal OBJECT-TYPE
	    SYNTAX INTEGER
	    ACCESS read-only
	    STATUS mandatory
	    DESCRIPTION
		"Work Dynamic Memory Pool Allocated"
	::= { memoryinfo 5 }

	memoryAllocPoolInUse OBJECT-TYPE
	    SYNTAX INTEGER
	    ACCESS read-only
	    STATUS mandatory
	    DESCRIPTION
		"Work Dynamic Memory Pool In Use"
	::= { memoryinfo 6 }

	memoryCacheBufferPool OBJECT-TYPE
	    SYNTAX INTEGER
	    ACCESS read-only
	    STATUS mandatory
	    DESCRIPTION
		"Cache Buffer Pool"
	::= { memoryinfo 7 }

	memoryCacheMovablePool OBJECT-TYPE
	    SYNTAX INTEGER
	    ACCESS read-only
	    STATUS mandatory
	    DESCRIPTION
		"Cache Movable Pool"
	::= { memoryinfo 8 }

	memoryCacheNonMovablePool OBJECT-TYPE
	    SYNTAX INTEGER
	    ACCESS read-only
	    STATUS mandatory
	    DESCRIPTION
		"Cache Non-Movable Pool"
	::= { memoryinfo 9 }

	memoryNw3PermMemoryPoolTotal OBJECT-TYPE
	    SYNTAX INTEGER
	    ACCESS read-only
	    STATUS mandatory
	    DESCRIPTION
		"Permanent Memory Pool Total (NetWare v3 only)"
	::= { memoryinfo 10 }

	memoryNw3PermMemoryPoolInUse OBJECT-TYPE
	    SYNTAX INTEGER
	    ACCESS read-only
	    STATUS mandatory
	    DESCRIPTION
		"Permanent Memory Pool In Use (NetWare v3 only)"
	::= { memoryinfo 11 }

	memoryNw4CodeDataPool OBJECT-TYPE
	    SYNTAX INTEGER
	    ACCESS read-only
	    STATUS mandatory
	    DESCRIPTION
		"Code And Data Memory Pool (NetWare v4 only)"
	::= { memoryinfo 12 }



	moduleCount OBJECT-TYPE
	    SYNTAX INTEGER
	    ACCESS read-only
	    STATUS mandatory
	    DESCRIPTION
		"Loaded Modules"
	::= { moduleinfo 1 }

	moduleTable OBJECT-TYPE
	    SYNTAX SEQUENCE OF ModuleEntry
	    ACCESS not-accessible
	    STATUS mandatory
	    DESCRIPTION
		"Loaded Module Entry Table"
	::= { moduleinfo 2 }

	moduleEntry OBJECT-TYPE
	    SYNTAX ModuleEntry
	    ACCESS not-accessible
	    STATUS mandatory
	    DESCRIPTION
		"Loaded Module Entry"
	    INDEX  { moduleIndex }
	::= { moduleTable 1 }

	ModuleEntry ::=
	    SEQUENCE {
			moduleIndex
				INTEGER,
			moduleName
				DisplayString,
			moduleDesc
				DisplayString,
			moduleCopyright
				DisplayString,
			moduleVersion
				DisplayString,
			moduleCompileDate
				DisplayString,
			moduleCodeSize
				INTEGER,
			moduleDataSize
				INTEGER,
			moduleSmallMemoryAlloc
				INTEGER,
			moduleMediumMemoryAlloc
				INTEGER,
			moduleLargeMemoryAlloc
				INTEGER,
			moduleActiveProcesses
				INTEGER,
			moduleActiveScreens
				INTEGER
		    }

	moduleIndex OBJECT-TYPE
	    SYNTAX INTEGER
	    ACCESS read-only
	    STATUS mandatory
	    DESCRIPTION
		"Loaded Module Index Pointer"
	::= { moduleEntry 1 }

	moduleName OBJECT-TYPE
	    SYNTAX DisplayString (SIZE (0..36))
	    ACCESS read-only
	    STATUS mandatory
	    DESCRIPTION
		"Loaded Module Name"
	::= { moduleEntry 2 }

	moduleDesc OBJECT-TYPE
	    SYNTAX DisplayString (SIZE (0..128))
	    ACCESS read-only
	    STATUS mandatory
	    DESCRIPTION
		"Loaded Module Description"
	::= { moduleEntry 3 }

	moduleCopyright OBJECT-TYPE
	    SYNTAX DisplayString (SIZE (0..256))
	    ACCESS read-only
	    STATUS mandatory
	    DESCRIPTION
		"Loaded Module Copyright Information"
	::= { moduleEntry 4 }

	moduleVersion OBJECT-TYPE
	    SYNTAX DisplayString (SIZE (0..8))
	    ACCESS read-only
	    STATUS mandatory
	    DESCRIPTION
		"Loaded Module Version Information"
	::= { moduleEntry 5 }

	moduleCompileDate OBJECT-TYPE
	    SYNTAX DisplayString (SIZE (0..8))
	    ACCESS read-only
	    STATUS mandatory
	    DESCRIPTION
		"Loaded Module Compile Date"
	::= { moduleEntry 6 }

	moduleCodeSize OBJECT-TYPE
	    SYNTAX INTEGER
	    ACCESS read-only
	    STATUS mandatory
	    DESCRIPTION
		"Loaded Module Static Code Size"
	::= { moduleEntry 7 }

	moduleDataSize OBJECT-TYPE
	    SYNTAX INTEGER
	    ACCESS read-only
	    STATUS mandatory
	    DESCRIPTION
		"Loaded Module Static Data Size"
	::= { moduleEntry 8 }

	moduleSmallMemoryAlloc OBJECT-TYPE
	    SYNTAX INTEGER
	    ACCESS read-only
	    STATUS mandatory
	    DESCRIPTION
		"Loaded Module Small Memory Allocations"
	::= { moduleEntry 9 }

	moduleMediumMemoryAlloc OBJECT-TYPE
	    SYNTAX INTEGER
	    ACCESS read-only
	    STATUS mandatory
	    DESCRIPTION
		"Loaded Module Medium Memory Allocations"
	::= { moduleEntry 10 }

	moduleLargeMemoryAlloc OBJECT-TYPE
	    SYNTAX INTEGER
	    ACCESS read-only
	    STATUS mandatory
	    DESCRIPTION
		"Loaded Module Large Memory Allocations"
	::= { moduleEntry 11 }

	moduleActiveProcesses OBJECT-TYPE
	    SYNTAX INTEGER
	    ACCESS read-only
	    STATUS mandatory
	    DESCRIPTION
		"Loaded Module Active Processes"
	::= { moduleEntry 12 }

	moduleActiveScreens OBJECT-TYPE
	    SYNTAX INTEGER
	    ACCESS read-only
	    STATUS mandatory
	    DESCRIPTION
		"Loaded Module Active Screens"
	::= { moduleEntry 13 }



	netCount OBJECT-TYPE
	    SYNTAX INTEGER
	    ACCESS read-only
	    STATUS mandatory
	    DESCRIPTION
		"Configured Networks"
	::= { netinfo 1 }

	netTable OBJECT-TYPE
	    SYNTAX SEQUENCE OF NetEntry
	    ACCESS not-accessible
	    STATUS mandatory
	    DESCRIPTION
		"Configured Network Entry Table"
	::= { netinfo 2 }

	netEntry OBJECT-TYPE
	    SYNTAX NetEntry
	    ACCESS not-accessible
	    STATUS mandatory
	    DESCRIPTION
		"Configured Network Entry"
	    INDEX  { netIndex }
	::= { netTable 1 }

	NetEntry ::=
	    SEQUENCE {
			netIndex
				INTEGER,
			netDriverName
				DisplayString,
			netDriverDesc
				DisplayString,
			netFrameDesc
				DisplayString,
			netLogicalName
				DisplayString,
			netProtocolDesc
				DisplayString,
			netNodeID
				OCTET STRING,
			netLineSpeed
				INTEGER,
			netMaxPacketSize
				INTEGER,
			netMaxRecvSize
				INTEGER,
			netMaxProtocolSize
				INTEGER,
			netPrimaryIOPort
				DisplayString,
			netPrimaryMemoryDecode
				DisplayString,
			netPrimaryInterrupt
				DisplayString,
			netPrimaryDMA
				DisplayString,
			netSecondaryIOPort
				DisplayString,
			netSecondaryMemoryDecode
				DisplayString,
			netSecondaryInterrupt
				DisplayString,
			netSecondaryDMA
				DisplayString,
			netTotalRxPacketCount
				INTEGER,
			netPacketRxOverflowCount
				INTEGER,
			netPacketRxTooBigCount
				INTEGER,
			netPacketRxTooSmallCount
				INTEGER,
			netPacketRxMiscErrorCount
				INTEGER,
			netChecksumErrorCount
				INTEGER,
			netHardwareRxMismatchCount
				INTEGER,
			netTotalTxPacketCount
				INTEGER,
			netNoECBAvailableCount
				INTEGER,
			netPacketTxTooBigCount
				INTEGER,
			netPacketTxTooSmallCount
				INTEGER,
			netPacketTxMiscErrorCount
				INTEGER,
			netRetryTxCount
				INTEGER
		    }

	netIndex OBJECT-TYPE
	    SYNTAX INTEGER
	    ACCESS read-only
	    STATUS mandatory
	    DESCRIPTION
		"Network Index Pointer"
	::= { netEntry 1 }

	netDriverName OBJECT-TYPE
	    SYNTAX DisplayString (SIZE (0..10))
	    ACCESS read-only
	    STATUS mandatory
	    DESCRIPTION
		"Network Driver Name"
	::= { netEntry 2 }

	netDriverDesc OBJECT-TYPE
	    SYNTAX DisplayString (SIZE (0..128))
	    ACCESS read-only
	    STATUS mandatory
	    DESCRIPTION
		"Network Driver Description"
	::= { netEntry 3 }

	netFrameDesc OBJECT-TYPE
	    SYNTAX DisplayString (SIZE (0..32))
	    ACCESS read-only
	    STATUS mandatory
	    DESCRIPTION
		"Network Frame Description"
	::= { netEntry 4 }

	netLogicalName OBJECT-TYPE
	    SYNTAX DisplayString (SIZE (0..18))
	    ACCESS read-only
	    STATUS mandatory
	    DESCRIPTION
		"Network Logical Name"
	::= { netEntry 5 }

	netProtocolDesc OBJECT-TYPE
	    SYNTAX DisplayString (SIZE (0..128))
	    ACCESS read-only
	    STATUS mandatory
	    DESCRIPTION
		"Network Protocol Description"
	::= { netEntry 6 }

	netNodeID OBJECT-TYPE
	    SYNTAX OCTET STRING (SIZE (6))
	    ACCESS read-only
	    STATUS mandatory
	    DESCRIPTION
		"Network Node ID"
	::= { netEntry 7 }

	netLineSpeed OBJECT-TYPE
	    SYNTAX INTEGER
	    ACCESS read-only
	    STATUS mandatory
	    DESCRIPTION
		"Network Line Speed (Kbps)"
	::= { netEntry 8 }

	netMaxPacketSize OBJECT-TYPE
	    SYNTAX INTEGER
	    ACCESS read-only
	    STATUS mandatory
	    DESCRIPTION
		"Network Maximum Packet Size"
	::= { netEntry 9 }

	netMaxRecvSize OBJECT-TYPE
	    SYNTAX INTEGER
	    ACCESS read-only
	    STATUS mandatory
	    DESCRIPTION
		"Network Maximum Rx Size"
	::= { netEntry 10 }

	netMaxProtocolSize OBJECT-TYPE
	    SYNTAX INTEGER
	    ACCESS read-only
	    STATUS mandatory
	    DESCRIPTION
		"Network Maximum Protocol Size"
	::= { netEntry 11 }

	netPrimaryIOPort OBJECT-TYPE
	    SYNTAX DisplayString (SIZE (0..10))
	    ACCESS read-only
	    STATUS mandatory
	    DESCRIPTION
		"Network Primary I/O Port Address"
	::= { netEntry 12 }

	netPrimaryMemoryDecode OBJECT-TYPE
	    SYNTAX DisplayString (SIZE (0..12))
	    ACCESS read-only
	    STATUS mandatory
	    DESCRIPTION
		"Network Primary Memory Address"
	::= { netEntry 13 }

	netPrimaryInterrupt OBJECT-TYPE
	    SYNTAX DisplayString (SIZE (0..3))
	    ACCESS read-only
	    STATUS mandatory
	    DESCRIPTION
		"Network Primary IRQ"
	::= { netEntry 14 }

	netPrimaryDMA OBJECT-TYPE
	    SYNTAX DisplayString (SIZE (0..3))
	    ACCESS read-only
	    STATUS mandatory
	    DESCRIPTION
		"Network Primary DMA Channel"
	::= { netEntry 15 }

	netSecondaryIOPort OBJECT-TYPE
	    SYNTAX DisplayString (SIZE (0..10))
	    ACCESS read-only
	    STATUS mandatory
	    DESCRIPTION
		"Network Secondary I/O Port Address"
	::= { netEntry 16 }

	netSecondaryMemoryDecode OBJECT-TYPE
	    SYNTAX DisplayString (SIZE (0..12))
	    ACCESS read-only
	    STATUS mandatory
	    DESCRIPTION
		"Network Secondary Memory Address"
	::= { netEntry 17 }

	netSecondaryInterrupt OBJECT-TYPE
	    SYNTAX DisplayString (SIZE (0..3))
	    ACCESS read-only
	    STATUS mandatory
	    DESCRIPTION
		"Network Secondary IRQ"
	::= { netEntry 18 }

	netSecondaryDMA OBJECT-TYPE
	    SYNTAX DisplayString (SIZE (0..3))
	    ACCESS read-only
	    STATUS mandatory
	    DESCRIPTION
		"Network Secondary DMA Channel"
	::= { netEntry 19 }

	netTotalRxPacketCount OBJECT-TYPE
	    SYNTAX INTEGER
	    ACCESS read-only
	    STATUS mandatory
	    DESCRIPTION
		"Network Total Rx Packets"
	::= { netEntry 20 }

	netPacketRxOverflowCount OBJECT-TYPE
	    SYNTAX INTEGER
	    ACCESS read-only
	    STATUS mandatory
	    DESCRIPTION
		"Network Total Rx Packet Overflow Count"
	::= { netEntry 21 }

	netPacketRxTooBigCount OBJECT-TYPE
	    SYNTAX INTEGER
	    ACCESS read-only
	    STATUS mandatory
	    DESCRIPTION
		"Network Total Rx Packet Too Big Count"
	::= { netEntry 22 }

	netPacketRxTooSmallCount OBJECT-TYPE
	    SYNTAX INTEGER
	    ACCESS read-only
	    STATUS mandatory
	    DESCRIPTION
		"Network Total Rx Packet Too Small Count"
	::= { netEntry 23 }

	netPacketRxMiscErrorCount OBJECT-TYPE
	    SYNTAX INTEGER
	    ACCESS read-only
	    STATUS mandatory
	    DESCRIPTION
		"Network Total Rx Misc. Errors"
	::= { netEntry 24 }

	netChecksumErrorCount OBJECT-TYPE
	    SYNTAX INTEGER
	    ACCESS read-only
	    STATUS mandatory
	    DESCRIPTION
		"Network Total Rx Checksum Errors"
	::= { netEntry 25 }

	netHardwareRxMismatchCount OBJECT-TYPE
	    SYNTAX INTEGER
	    ACCESS read-only
	    STATUS mandatory
	    DESCRIPTION
		"Network Total Rx Mismatch Errors"
	::= { netEntry 26 }

	netTotalTxPacketCount OBJECT-TYPE
	    SYNTAX INTEGER
	    ACCESS read-only
	    STATUS mandatory
	    DESCRIPTION
		"Network Total Tx Packets"
	::= { netEntry 27 }

	netNoECBAvailableCount OBJECT-TYPE
	    SYNTAX INTEGER
	    ACCESS read-only
	    STATUS mandatory
	    DESCRIPTION
		"Network Total Tx No ECB Available Count"
	::= { netEntry 28 }

	netPacketTxTooBigCount OBJECT-TYPE
	    SYNTAX INTEGER
	    ACCESS read-only
	    STATUS mandatory
	    DESCRIPTION
		"Network Total Tx Packet Too Big Count"
	::= { netEntry 29 }

	netPacketTxTooSmallCount OBJECT-TYPE
	    SYNTAX INTEGER
	    ACCESS read-only
	    STATUS mandatory
	    DESCRIPTION
		"Network Total Tx Packet Too Small Count"
	::= { netEntry 30 }

	netPacketTxMiscErrorCount OBJECT-TYPE
	    SYNTAX INTEGER
	    ACCESS read-only
	    STATUS mandatory
	    DESCRIPTION
		"Network Total Tx Misc. Errors"
	::= { netEntry 31 }

	netRetryTxCount OBJECT-TYPE
	    SYNTAX INTEGER
	    ACCESS read-only
	    STATUS mandatory
	    DESCRIPTION
		"Network Total Tx Retry Count"
	::= { netEntry 32 }



	nicCount OBJECT-TYPE
	    SYNTAX INTEGER
	    ACCESS read-only
	    STATUS mandatory
	    DESCRIPTION
		"Configured NICs (Network Interface Cards)"
	::= { nicstats 1 }

	nicTable OBJECT-TYPE
	    SYNTAX SEQUENCE OF NicEntry
	    ACCESS not-accessible
	    STATUS mandatory
	    DESCRIPTION
		"Configured NIC Entry Table"
	::= { nicstats 2 }

	nicEntry OBJECT-TYPE
	    SYNTAX NicEntry
	    ACCESS not-accessible
	    STATUS mandatory
	    DESCRIPTION
		"Configured NIC Entry"
	    INDEX  { nicIndex }
	::= { nicTable 1 }

	NicEntry ::=
	    SEQUENCE {
			nicIndex
				INTEGER,
			nicNodeID
				OCTET STRING,
			nicCurrRxPacketCount
				INTEGER,
			nicAvgRxPacketCount
				INTEGER,
			nicPeakRxPacketCount
				INTEGER,
			nicCumlRxPacketCount
				INTEGER,
			nicCurrTxPacketCount
				INTEGER,
			nicAvgTxPacketCount
				INTEGER,
			nicPeakTxPacketCount
				INTEGER,
			nicCumlTxPacketCount
				INTEGER
		    }

	nicIndex OBJECT-TYPE
	    SYNTAX INTEGER
	    ACCESS read-only
	    STATUS mandatory
	    DESCRIPTION
		"NIC Index Pointer"
	::= { nicEntry 1 }

	nicNodeID OBJECT-TYPE
	    SYNTAX OCTET STRING (SIZE (6))
	    ACCESS read-only
	    STATUS mandatory
	    DESCRIPTION
		"NIC Node ID"
	::= { nicEntry 2 }

	nicCurrRxPacketCount OBJECT-TYPE
	    SYNTAX INTEGER
	    ACCESS read-only
	    STATUS mandatory
	    DESCRIPTION
		"NIC Current Rx Packets"
	::= { nicEntry 3 }

	nicAvgRxPacketCount OBJECT-TYPE
	    SYNTAX INTEGER
	    ACCESS read-only
	    STATUS mandatory
	    DESCRIPTION
		"NIC Average Rx Packets"
	::= { nicEntry 4 }

	nicPeakRxPacketCount OBJECT-TYPE
	    SYNTAX INTEGER
	    ACCESS read-only
	    STATUS mandatory
	    DESCRIPTION
		"NIC Peak Rx Packets"
	::= { nicEntry 5 }

	nicCumlRxPacketCount OBJECT-TYPE
	    SYNTAX INTEGER
	    ACCESS read-only
	    STATUS mandatory
	    DESCRIPTION
		"NIC Cumulative Rx Packets"
	::= { nicEntry 6 }

	nicCurrTxPacketCount OBJECT-TYPE
	    SYNTAX INTEGER
	    ACCESS read-only
	    STATUS mandatory
	    DESCRIPTION
		"NIC Current Tx Packets"
	::= { nicEntry 7 }

	nicAvgTxPacketCount OBJECT-TYPE
	    SYNTAX INTEGER
	    ACCESS read-only
	    STATUS mandatory
	    DESCRIPTION
		"NIC Average Tx Packets"
	::= { nicEntry 8 }

	nicPeakTxPacketCount OBJECT-TYPE
	    SYNTAX INTEGER
	    ACCESS read-only
	    STATUS mandatory
	    DESCRIPTION
		"NIC Peak Tx Packets"
	::= { nicEntry 9 }

	nicCumlTxPacketCount OBJECT-TYPE
	    SYNTAX INTEGER
	    ACCESS read-only
	    STATUS mandatory
	    DESCRIPTION
		"NIC Cumulative Tx Packets"
	::= { nicEntry 10 }



	setparmTable OBJECT-TYPE
	    SYNTAX SEQUENCE OF SetparmEntry
	    ACCESS not-accessible
	    STATUS mandatory
	    DESCRIPTION
		"SET Parameter Entry Table"
	::= { setparminfo 1 }

	setparmEntry OBJECT-TYPE
	    SYNTAX SetparmEntry
	    ACCESS not-accessible
	    STATUS mandatory
	    DESCRIPTION
		"SET Parameter Entry"
	    INDEX  { setparmIndex }
	::= { setparmTable 1 }

	SetparmEntry ::=
	    SEQUENCE {
			setparmIndex
				INTEGER,
			setparmName
				DisplayString,
			setparmDesc
				DisplayString,
			setparmCategory
				DisplayString,
			setparmFlags
				DisplayString,
			setparmCurrent
				DisplayString,
			setparmMinimum
				DisplayString,
			setparmMaximum
				DisplayString
		    }

	setparmIndex OBJECT-TYPE
	    SYNTAX INTEGER
	    ACCESS read-only
	    STATUS mandatory
	    DESCRIPTION
		"SET Parameter Index Pointer"
	::= { setparmEntry 1 }

	setparmName OBJECT-TYPE
	    SYNTAX DisplayString (SIZE (0..80))
	    ACCESS read-only
	    STATUS mandatory
	    DESCRIPTION
		"SET Parameter Name"
	::= { setparmEntry 2 }

	setparmDesc OBJECT-TYPE
	    SYNTAX DisplayString (SIZE (0..576))
	    ACCESS read-only
	    STATUS mandatory
	    DESCRIPTION
		"SET Parameter Description"
	::= { setparmEntry 3 }

	setparmCategory OBJECT-TYPE
	    SYNTAX DisplayString (SIZE (0..24))
	    ACCESS read-only
	    STATUS mandatory
	    DESCRIPTION
		"SET Parameter Category"
	::= { setparmEntry 4 }

	setparmFlags OBJECT-TYPE
	    SYNTAX DisplayString (SIZE (0..80))
	    ACCESS read-only
	    STATUS mandatory
	    DESCRIPTION
		"SET Parameter Flags"
	::= { setparmEntry 5 }

	setparmCurrent OBJECT-TYPE
	    SYNTAX DisplayString (SIZE (0..80))
	    ACCESS read-only
	    STATUS mandatory
	    DESCRIPTION
		"SET Parameter Current Value"
	::= { setparmEntry 6 }

	setparmMinimum OBJECT-TYPE
	    SYNTAX DisplayString (SIZE (0..80))
	    ACCESS read-only
	    STATUS mandatory
	    DESCRIPTION
		"SET Parameter Minimum Value"
	::= { setparmEntry 7 }

	setparmMaximum OBJECT-TYPE
	    SYNTAX DisplayString (SIZE (0..80))
	    ACCESS read-only
	    STATUS mandatory
	    DESCRIPTION
		"SET Parameter Maximum Value"
	::= { setparmEntry 8 }



	serverCycleStartTime OBJECT-TYPE
	    SYNTAX DisplayString (SIZE (0..32))
	    ACCESS read-only
	    STATUS mandatory
	    DESCRIPTION
		"Current Cycle Start Time (string)"
	::= { serverstats 1 }

	serverCycleStartUTC OBJECT-TYPE
	    SYNTAX INTEGER
	    ACCESS read-only
	    STATUS mandatory
	    DESCRIPTION
		"Current Cycle Start Time GMT (UTC secs)"
	::= { serverstats 2 }

	serverCycleElapsedTicks OBJECT-TYPE
	    SYNTAX TimeTicks
	    ACCESS read-only
	    STATUS mandatory
	    DESCRIPTION
		"Current Cycle Elapsed Time (Ticks)"
	::= { serverstats 3 }

	serverCycleLengthTicks OBJECT-TYPE
	    SYNTAX TimeTicks
	    ACCESS read-only
	    STATUS mandatory
	    DESCRIPTION
		"Current Cycle Length (Ticks)"
	::= { serverstats 4 }

	serverCurrUtil OBJECT-TYPE
	    SYNTAX INTEGER
	    ACCESS read-only
	    STATUS mandatory
	    DESCRIPTION
		"Current CPU Utilization"
	::= { serverstats 5 }

	serverAvgUtil OBJECT-TYPE
	    SYNTAX INTEGER
	    ACCESS read-only
	    STATUS mandatory
	    DESCRIPTION
		"Average CPU Utilization"
	::= { serverstats 6 }

	serverPeakUtil OBJECT-TYPE
	    SYNTAX INTEGER
	    ACCESS read-only
	    STATUS mandatory
	    DESCRIPTION
		"Peak CPU Utilization"
	::= { serverstats 7 }

	serverCurrCacheRatio OBJECT-TYPE
	    SYNTAX INTEGER
	    ACCESS read-only
	    STATUS mandatory
	    DESCRIPTION
		"Current Cache Buffer Ratio (%)"
	::= { serverstats 8 }

	serverAvgCacheRatio OBJECT-TYPE
	    SYNTAX INTEGER
	    ACCESS read-only
	    STATUS mandatory
	    DESCRIPTION
		"Average Cache Buffer Ratio (%)"
	::= { serverstats 9 }

	serverMinCacheRatio OBJECT-TYPE
	    SYNTAX INTEGER
	    ACCESS read-only
	    STATUS mandatory
	    DESCRIPTION
		"Minimum Cache Buffer Ratio (%)"
	::= { serverstats 10 }

	serverCurrCacheHits OBJECT-TYPE
	    SYNTAX INTEGER
	    ACCESS read-only
	    STATUS mandatory
	    DESCRIPTION
		"Current Cache Hit Ratio (%)"
	::= { serverstats 11 }

	serverAvgCacheHits OBJECT-TYPE
	    SYNTAX INTEGER
	    ACCESS read-only
	    STATUS mandatory
	    DESCRIPTION
		"Average Cache Hit Ratio (%)"
	::= { serverstats 12 }

	serverMinCacheHits OBJECT-TYPE
	    SYNTAX INTEGER
	    ACCESS read-only
	    STATUS mandatory
	    DESCRIPTION
		"Minimum Cache Hit Ratio (%)"
	::= { serverstats 13 }

	serverCurrFSPs OBJECT-TYPE
	    SYNTAX INTEGER
	    ACCESS read-only
	    STATUS mandatory
	    DESCRIPTION
		"Current File Service Processes (FSPs)"
	::= { serverstats 14 }

	serverAvgFSPs OBJECT-TYPE
	    SYNTAX INTEGER
	    ACCESS read-only
	    STATUS mandatory
	    DESCRIPTION
		"Average File Service Processes (FSPs)"
	::= { serverstats 15 }

	serverPeakFSPs OBJECT-TYPE
	    SYNTAX INTEGER
	    ACCESS read-only
	    STATUS mandatory
	    DESCRIPTION
		"Peak File Service Processes (FSPs)"
	::= { serverstats 16 }

	serverCurrProcs OBJECT-TYPE
	    SYNTAX INTEGER
	    ACCESS read-only
	    STATUS mandatory
	    DESCRIPTION
		"Current Processes (non-FSPs)"
	::= { serverstats 17 }

	serverAvgProcs OBJECT-TYPE
	    SYNTAX INTEGER
	    ACCESS read-only
	    STATUS mandatory
	    DESCRIPTION
		"Average Processes (non-FSPs)"
	::= { serverstats 18 }

	serverPeakProcs OBJECT-TYPE
	    SYNTAX INTEGER
	    ACCESS read-only
	    STATUS mandatory
	    DESCRIPTION
		"Peak Processes (non-FSPs)"
	::= { serverstats 19 }

	serverCurrConns OBJECT-TYPE
	    SYNTAX INTEGER
	    ACCESS read-only
	    STATUS mandatory
	    DESCRIPTION
		"Current Connections In Use"
	::= { serverstats 20 }

	serverAvgConns OBJECT-TYPE
	    SYNTAX INTEGER
	    ACCESS read-only
	    STATUS mandatory
	    DESCRIPTION
		"Average Connections In Use (current cycle)"
	::= { serverstats 21 }

	serverPeakConns OBJECT-TYPE
	    SYNTAX INTEGER
	    ACCESS read-only
	    STATUS mandatory
	    DESCRIPTION
		"Peak Connections In Use (current cycle)"
	::= { serverstats 22 }

	serverCurrUsers OBJECT-TYPE
	    SYNTAX INTEGER
	    ACCESS read-only
	    STATUS mandatory
	    DESCRIPTION
		"Current Connections In Use"
	::= { serverstats 23 }

	serverAvgUsers OBJECT-TYPE
	    SYNTAX INTEGER
	    ACCESS read-only
	    STATUS mandatory
	    DESCRIPTION
		"Average Connections In Use"
	::= { serverstats 24 }

	serverPeakUsers OBJECT-TYPE
	    SYNTAX INTEGER
	    ACCESS read-only
	    STATUS mandatory
	    DESCRIPTION
		"Peak Connections In Use"
	::= { serverstats 25 }

	serverCurrRecvBuffs OBJECT-TYPE
	    SYNTAX INTEGER
	    ACCESS read-only
	    STATUS mandatory
	    DESCRIPTION
		"Current Packet Receive Buffers"
	::= { serverstats 26 }

	serverAvgRecvBuffs OBJECT-TYPE
	    SYNTAX INTEGER
	    ACCESS read-only
	    STATUS mandatory
	    DESCRIPTION
		"Average Packet Receive Buffers"
	::= { serverstats 27 }

	serverPeakRecvBuffs OBJECT-TYPE
	    SYNTAX INTEGER
	    ACCESS read-only
	    STATUS mandatory
	    DESCRIPTION
		"Peak Packet Receive Buffers"
	::= { serverstats 28 }

	serverCurrDirBuffs OBJECT-TYPE
	    SYNTAX INTEGER
	    ACCESS read-only
	    STATUS mandatory
	    DESCRIPTION
		"Current Directory Cache Buffers"
	::= { serverstats 29 }

	serverAvgDirBuffs OBJECT-TYPE
	    SYNTAX INTEGER
	    ACCESS read-only
	    STATUS mandatory
	    DESCRIPTION
		"Average Directory Cache Buffers"
	::= { serverstats 30 }

	serverPeakDirBuffs OBJECT-TYPE
	    SYNTAX INTEGER
	    ACCESS read-only
	    STATUS mandatory
	    DESCRIPTION
		"Peak Directory Cache Buffers"
	::= { serverstats 31 }

	serverCurrOpenFiles OBJECT-TYPE
	    SYNTAX INTEGER
	    ACCESS read-only
	    STATUS mandatory
	    DESCRIPTION
		"Current Open Files"
	::= { serverstats 32 }

	serverAvgOpenFiles OBJECT-TYPE
	    SYNTAX INTEGER
	    ACCESS read-only
	    STATUS mandatory
	    DESCRIPTION
		"Average Open Files"
	::= { serverstats 33 }

	serverPeakOpenFiles OBJECT-TYPE
	    SYNTAX INTEGER
	    ACCESS read-only
	    STATUS mandatory
	    DESCRIPTION
		"Peak Open Files"
	::= { serverstats 34 }

	serverCurrIOsPending OBJECT-TYPE
	    SYNTAX INTEGER
	    ACCESS read-only
	    STATUS mandatory
	    DESCRIPTION
		"Current Disk I/Os Pending"
	::= { serverstats 35 }

	serverAvgIOsPending OBJECT-TYPE
	    SYNTAX INTEGER
	    ACCESS read-only
	    STATUS mandatory
	    DESCRIPTION
		"Average Disk I/Os Pending (current cycle)"
	::= { serverstats 36 }

	serverPeakIOsPending OBJECT-TYPE
	    SYNTAX INTEGER
	    ACCESS read-only
	    STATUS mandatory
	    DESCRIPTION
		"Peak Disk I/Os Pending (current cycle)"
	::= { serverstats 37 }

	serverCumlIOsPending OBJECT-TYPE
	    SYNTAX INTEGER
	    ACCESS read-only
	    STATUS mandatory
	    DESCRIPTION
		"Cumulative Disk I/Os Pending (current cycle)"
	::= { serverstats 38 }

	serverCurrDirtyBlocks OBJECT-TYPE
	    SYNTAX INTEGER
	    ACCESS read-only
	    STATUS mandatory
	    DESCRIPTION
		"Current Dirty Blocks"
	::= { serverstats 39 }

	serverAvgDirtyBlocks OBJECT-TYPE
	    SYNTAX INTEGER
	    ACCESS read-only
	    STATUS mandatory
	    DESCRIPTION
		"Average Dirty Blocks (current cycle)"
	::= { serverstats 40 }

	serverPeakDirtyBlocks OBJECT-TYPE
	    SYNTAX INTEGER
	    ACCESS read-only
	    STATUS mandatory
	    DESCRIPTION
		"Peak Dirty Blocks (current cycle)"
	::= { serverstats 41 }

	serverCumlDirtyBlocks OBJECT-TYPE
	    SYNTAX INTEGER
	    ACCESS read-only
	    STATUS mandatory
	    DESCRIPTION
		"Cumulative Dirty Blocks (current cycle)"
	::= { serverstats 42 }

	serverCurrDiskReads OBJECT-TYPE
	    SYNTAX INTEGER
	    ACCESS read-only
	    STATUS mandatory
	    DESCRIPTION
		"Current Physical Disk Reads"
	::= { serverstats 43 }

	serverAvgDiskReads OBJECT-TYPE
	    SYNTAX INTEGER
	    ACCESS read-only
	    STATUS mandatory
	    DESCRIPTION
		"Average Physical Disk Reads (current cycle)"
	::= { serverstats 44 }

	serverPeakDiskReads OBJECT-TYPE
	    SYNTAX INTEGER
	    ACCESS read-only
	    STATUS mandatory
	    DESCRIPTION
		"Peak Physical Disk Reads (current cycle)"
	::= { serverstats 45 }

	serverCumlDiskReads OBJECT-TYPE
	    SYNTAX INTEGER
	    ACCESS read-only
	    STATUS mandatory
	    DESCRIPTION
		"Cumulative Physical Disk Reads (current cycle)"
	::= { serverstats 46 }

	serverCurrDiskReadBytes OBJECT-TYPE
	    SYNTAX INTEGER
	    ACCESS read-only
	    STATUS mandatory
	    DESCRIPTION
		"Current Physical Disk Read Bytes"
	::= { serverstats 47 }

	serverAvgDiskReadBytes OBJECT-TYPE
	    SYNTAX INTEGER
	    ACCESS read-only
	    STATUS mandatory
	    DESCRIPTION
		"Average Physical Disk Read Bytes (current cycle)"
	::= { serverstats 48 }

	serverPeakDiskReadBytes OBJECT-TYPE
	    SYNTAX INTEGER
	    ACCESS read-only
	    STATUS mandatory
	    DESCRIPTION
		"Peak Physical Disk Read Bytes (current cycle)"
	::= { serverstats 49 }

	serverCumlDiskReadBytes OBJECT-TYPE
	    SYNTAX INTEGER
	    ACCESS read-only
	    STATUS mandatory
	    DESCRIPTION
		"Cumulative Physical Disk Read Bytes (current cycle)"
	::= { serverstats 50 }

	serverCurrDiskWrites OBJECT-TYPE
	    SYNTAX INTEGER
	    ACCESS read-only
	    STATUS mandatory
	    DESCRIPTION
		"Current Physical Disk Writes"
	::= { serverstats 51 }

	serverAvgDiskWrites OBJECT-TYPE
	    SYNTAX INTEGER
	    ACCESS read-only
	    STATUS mandatory
	    DESCRIPTION
		"Average Physical Disk Writes (current cycle)"
	::= { serverstats 52 }

	serverPeakDiskWrites OBJECT-TYPE
	    SYNTAX INTEGER
	    ACCESS read-only
	    STATUS mandatory
	    DESCRIPTION
		"Peak Physical Disk Writes (current cycle)"
	::= { serverstats 53 }

	serverCumlDiskWrites OBJECT-TYPE
	    SYNTAX INTEGER
	    ACCESS read-only
	    STATUS mandatory
	    DESCRIPTION
		"Cumulative Physical Disk Writes (current cycle)"
	::= { serverstats 54 }

	serverCurrDiskWriteBytes OBJECT-TYPE
	    SYNTAX INTEGER
	    ACCESS read-only
	    STATUS mandatory
	    DESCRIPTION
		"Current Physical Disk Write Bytes"
	::= { serverstats 55 }

	serverAvgDiskWriteBytes OBJECT-TYPE
	    SYNTAX INTEGER
	    ACCESS read-only
	    STATUS mandatory
	    DESCRIPTION
		"Average Physical Disk Write Bytes (current cycle)"
	::= { serverstats 56 }

	serverPeakDiskWriteBytes OBJECT-TYPE
	    SYNTAX INTEGER
	    ACCESS read-only
	    STATUS mandatory
	    DESCRIPTION
		"Peak Physical Disk Write Bytes (current cycle)"
	::= { serverstats 57 }

	serverCumlDiskWriteBytes OBJECT-TYPE
	    SYNTAX INTEGER
	    ACCESS read-only
	    STATUS mandatory
	    DESCRIPTION
		"Cumulative Physical Disk Write Bytes (current cycle)"
	::= { serverstats 58 }

	serverCurrRoutedPkts OBJECT-TYPE
	    SYNTAX INTEGER
	    ACCESS read-only
	    STATUS mandatory
	    DESCRIPTION
		"Current LAN Routed Packets"
	::= { serverstats 59 }

	serverAvgRoutedPkts OBJECT-TYPE
	    SYNTAX INTEGER
	    ACCESS read-only
	    STATUS mandatory
	    DESCRIPTION
		"Average LAN Routed Packets (current cycle)"
	::= { serverstats 60 }

	serverPeakRoutedPkts OBJECT-TYPE
	    SYNTAX INTEGER
	    ACCESS read-only
	    STATUS mandatory
	    DESCRIPTION
		"Peak LAN Routed Packets (current cycle)"
	::= { serverstats 61 }

	serverCumlRoutedPkts OBJECT-TYPE
	    SYNTAX INTEGER
	    ACCESS read-only
	    STATUS mandatory
	    DESCRIPTION
		"Cumulative LAN Routed Packets (current cycle)"
	::= { serverstats 62 }

	serverCurrRxPkts OBJECT-TYPE
	    SYNTAX INTEGER
	    ACCESS read-only
	    STATUS mandatory
	    DESCRIPTION
		"Current LAN Rx Packets"
	::= { serverstats 63 }

	serverAvgRxPkts OBJECT-TYPE
	    SYNTAX INTEGER
	    ACCESS read-only
	    STATUS mandatory
	    DESCRIPTION
		"Average LAN Rx Packets (current cycle)"
	::= { serverstats 64 }

	serverPeakRxPkts OBJECT-TYPE
	    SYNTAX INTEGER
	    ACCESS read-only
	    STATUS mandatory
	    DESCRIPTION
		"Peak LAN Rx Packets (current cycle)"
	::= { serverstats 65 }

	serverCumlRxPkts OBJECT-TYPE
	    SYNTAX INTEGER
	    ACCESS read-only
	    STATUS mandatory
	    DESCRIPTION
		"Cumulative LAN Rx Packets (current cycle)"
	::= { serverstats 66 }

	serverCurrRxBytes OBJECT-TYPE
	    SYNTAX INTEGER
	    ACCESS read-only
	    STATUS mandatory
	    DESCRIPTION
		"Current LAN Rx Bytes"
	::= { serverstats 67 }

	serverAvgRxBytes OBJECT-TYPE
	    SYNTAX INTEGER
	    ACCESS read-only
	    STATUS mandatory
	    DESCRIPTION
		"Average LAN Rx Bytes (current cycle)"
	::= { serverstats 68 }

	serverPeakRxBytes OBJECT-TYPE
	    SYNTAX INTEGER
	    ACCESS read-only
	    STATUS mandatory
	    DESCRIPTION
		"Peak LAN Rx Bytes (current cycle)"
	::= { serverstats 69 }

	serverCumlRxBytes OBJECT-TYPE
	    SYNTAX INTEGER
	    ACCESS read-only
	    STATUS mandatory
	    DESCRIPTION
		"Cumulative LAN Rx Bytes (current cycle)"
	::= { serverstats 70 }

	serverCurrTxPkts OBJECT-TYPE
	    SYNTAX INTEGER
	    ACCESS read-only
	    STATUS mandatory
	    DESCRIPTION
		"Current LAN Tx Packets"
	::= { serverstats 71 }

	serverAvgTxPkts OBJECT-TYPE
	    SYNTAX INTEGER
	    ACCESS read-only
	    STATUS mandatory
	    DESCRIPTION
		"Average LAN Tx Packets (current cycle)"
	::= { serverstats 72 }

	serverPeakTxPkts OBJECT-TYPE
	    SYNTAX INTEGER
	    ACCESS read-only
	    STATUS mandatory
	    DESCRIPTION
		"Peak LAN Tx Packets (current cycle)"
	::= { serverstats 73 }

	serverCumlTxPkts OBJECT-TYPE
	    SYNTAX INTEGER
	    ACCESS read-only
	    STATUS mandatory
	    DESCRIPTION
		"Cumulative LAN Tx Packets (current cycle)"
	::= { serverstats 74 }

	serverCurrTxBytes OBJECT-TYPE
	    SYNTAX INTEGER
	    ACCESS read-only
	    STATUS mandatory
	    DESCRIPTION
		"Current LAN Tx Bytes"
	::= { serverstats 75 }

	serverAvgTxBytes OBJECT-TYPE
	    SYNTAX INTEGER
	    ACCESS read-only
	    STATUS mandatory
	    DESCRIPTION
		"Average LAN Tx Bytes (current cycle)"
	::= { serverstats 76 }

	serverPeakTxBytes OBJECT-TYPE
	    SYNTAX INTEGER
	    ACCESS read-only
	    STATUS mandatory
	    DESCRIPTION
		"Peak LAN Tx Bytes (current cycle)"
	::= { serverstats 77 }

	serverCumlTxBytes OBJECT-TYPE
	    SYNTAX INTEGER
	    ACCESS read-only
	    STATUS mandatory
	    DESCRIPTION
		"Cumulative LAN Tx Bytes (current cycle)"
	::= { serverstats 78 }

	serverCurrDirSearch OBJECT-TYPE
	    SYNTAX INTEGER
	    ACCESS read-only
	    STATUS mandatory
	    DESCRIPTION
		"Current Directory Search Requests"
	::= { serverstats 79 }

	serverAvgDirSearch OBJECT-TYPE
	    SYNTAX INTEGER
	    ACCESS read-only
	    STATUS mandatory
	    DESCRIPTION
		"Average Directory Search Requests (current cycle)"
	::= { serverstats 80 }

	serverPeakDirSearch OBJECT-TYPE
	    SYNTAX INTEGER
	    ACCESS read-only
	    STATUS mandatory
	    DESCRIPTION
		"Peak Directory Search Requests (current cycle)"
	::= { serverstats 81 }

	serverCumlDirSearch OBJECT-TYPE
	    SYNTAX INTEGER
	    ACCESS read-only
	    STATUS mandatory
	    DESCRIPTION
		"Cumulative Directory Search Requests (current cycle)"
	::= { serverstats 82 }

	serverCurrFileCreates OBJECT-TYPE
	    SYNTAX INTEGER
	    ACCESS read-only
	    STATUS mandatory
	    DESCRIPTION
		"Current File Create Requests"
	::= { serverstats 83 }

	serverAvgFileCreates OBJECT-TYPE
	    SYNTAX INTEGER
	    ACCESS read-only
	    STATUS mandatory
	    DESCRIPTION
		"Average File Create Requests (current cycle)"
	::= { serverstats 84 }

	serverPeakFileCreates OBJECT-TYPE
	    SYNTAX INTEGER
	    ACCESS read-only
	    STATUS mandatory
	    DESCRIPTION
		"Peak File Create Requests (current cycle)"
	::= { serverstats 85 }

	serverCumlFileCreates OBJECT-TYPE
	    SYNTAX INTEGER
	    ACCESS read-only
	    STATUS mandatory
	    DESCRIPTION
		"Cumulative File Create Requests (current cycle)"
	::= { serverstats 86 }

	serverCurrFileOpens OBJECT-TYPE
	    SYNTAX INTEGER
	    ACCESS read-only
	    STATUS mandatory
	    DESCRIPTION
		"Current File Open Requests"
	::= { serverstats 87 }

	serverAvgFileOpens OBJECT-TYPE
	    SYNTAX INTEGER
	    ACCESS read-only
	    STATUS mandatory
	    DESCRIPTION
		"Average File Open Requests (current cycle)"
	::= { serverstats 88 }

	serverPeakFileOpens OBJECT-TYPE
	    SYNTAX INTEGER
	    ACCESS read-only
	    STATUS mandatory
	    DESCRIPTION
		"Peak File Open Requests (current cycle)"
	::= { serverstats 89 }

	serverCumlFileOpens OBJECT-TYPE
	    SYNTAX INTEGER
	    ACCESS read-only
	    STATUS mandatory
	    DESCRIPTION
		"Cumulative File Open Requests (current cycle)"
	::= { serverstats 90 }

	serverCurrFileDeletes OBJECT-TYPE
	    SYNTAX INTEGER
	    ACCESS read-only
	    STATUS mandatory
	    DESCRIPTION
		"Current File Delete Requests"
	::= { serverstats 91 }

	serverAvgFileDeletes OBJECT-TYPE
	    SYNTAX INTEGER
	    ACCESS read-only
	    STATUS mandatory
	    DESCRIPTION
		"Average File Delete Requests (current cycle)"
	::= { serverstats 92 }

	serverPeakFileDeletes OBJECT-TYPE
	    SYNTAX INTEGER
	    ACCESS read-only
	    STATUS mandatory
	    DESCRIPTION
		"Peak File Delete Requests (current cycle)"
	::= { serverstats 93 }

	serverCumlFileDeletes OBJECT-TYPE
	    SYNTAX INTEGER
	    ACCESS read-only
	    STATUS mandatory
	    DESCRIPTION
		"Cumulative File Delete Requests (current cycle)"
	::= { serverstats 94 }

	serverCurrFileReads OBJECT-TYPE
	    SYNTAX INTEGER
	    ACCESS read-only
	    STATUS mandatory
	    DESCRIPTION
		"Current File Read Requests"
	::= { serverstats 95 }

	serverAvgFileReads OBJECT-TYPE
	    SYNTAX INTEGER
	    ACCESS read-only
	    STATUS mandatory
	    DESCRIPTION
		"Average File Read Requests (current cycle)"
	::= { serverstats 96 }

	serverPeakFileReads OBJECT-TYPE
	    SYNTAX INTEGER
	    ACCESS read-only
	    STATUS mandatory
	    DESCRIPTION
		"Peak File Read Requests (current cycle)"
	::= { serverstats 97 }

	serverCumlFileReads OBJECT-TYPE
	    SYNTAX INTEGER
	    ACCESS read-only
	    STATUS mandatory
	    DESCRIPTION
		"Cumulative File Read Requests (current cycle)"
	::= { serverstats 98 }

	serverCurrFileReadBytes OBJECT-TYPE
	    SYNTAX INTEGER
	    ACCESS read-only
	    STATUS mandatory
	    DESCRIPTION
		"Current File Read Bytes"
	::= { serverstats 99 }

	serverAvgFileReadBytes OBJECT-TYPE
	    SYNTAX INTEGER
	    ACCESS read-only
	    STATUS mandatory
	    DESCRIPTION
		"Average File Read Bytes (current cycle)"
	::= { serverstats 100 }

	serverPeakFileReadBytes OBJECT-TYPE
	    SYNTAX INTEGER
	    ACCESS read-only
	    STATUS mandatory
	    DESCRIPTION
		"Peak File Read Bytes (current cycle)"
	::= { serverstats 101 }

	serverCumlFileReadBytes OBJECT-TYPE
	    SYNTAX INTEGER
	    ACCESS read-only
	    STATUS mandatory
	    DESCRIPTION
		"Cumulative File Read Bytes (current cycle)"
	::= { serverstats 102 }

	serverCurrFileWrites OBJECT-TYPE
	    SYNTAX INTEGER
	    ACCESS read-only
	    STATUS mandatory
	    DESCRIPTION
		"Current File Write Requests"
	::= { serverstats 103 }

	serverAvgFileWrites OBJECT-TYPE
	    SYNTAX INTEGER
	    ACCESS read-only
	    STATUS mandatory
	    DESCRIPTION
		"Average File Write Requests (current cycle)"
	::= { serverstats 104 }

	serverPeakFileWrites OBJECT-TYPE
	    SYNTAX INTEGER
	    ACCESS read-only
	    STATUS mandatory
	    DESCRIPTION
		"Peak File Write Requests (current cycle)"
	::= { serverstats 105 }

	serverCumlFileWrites OBJECT-TYPE
	    SYNTAX INTEGER
	    ACCESS read-only
	    STATUS mandatory
	    DESCRIPTION
		"Cumulative File Write Requests (current cycle)"
	::= { serverstats 106 }

	serverCurrFileWriteBytes OBJECT-TYPE
	    SYNTAX INTEGER
	    ACCESS read-only
	    STATUS mandatory
	    DESCRIPTION
		"Current File Write Bytes"
	::= { serverstats 107 }

	serverAvgFileWriteBytes OBJECT-TYPE
	    SYNTAX INTEGER
	    ACCESS read-only
	    STATUS mandatory
	    DESCRIPTION
		"Average File Write Bytes (current cycle)"
	::= { serverstats 108 }

	serverPeakFileWriteBytes OBJECT-TYPE
	    SYNTAX INTEGER
	    ACCESS read-only
	    STATUS mandatory
	    DESCRIPTION
		"Peak File Write Bytes (current cycle)"
	::= { serverstats 109 }

	serverCumlFileWriteBytes OBJECT-TYPE
	    SYNTAX INTEGER
	    ACCESS read-only
	    STATUS mandatory
	    DESCRIPTION
		"Cumulative File Write Bytes (current cycle)"
	::= { serverstats 110 }



	serverTrendTable OBJECT-TYPE
	    SYNTAX SEQUENCE OF ServerTrendEntry
	    ACCESS not-accessible
	    STATUS mandatory
	    DESCRIPTION
		"Trend Entry Table"
	::= { servertrends 1 }

	serverTrendEntry OBJECT-TYPE
	    SYNTAX ServerTrendEntry
	    ACCESS not-accessible
	    STATUS mandatory
	    DESCRIPTION
		"Trend Entry"
	    INDEX  { serverTrendIndex }
	::= { serverTrendTable 1 }

	ServerTrendEntry ::=
	    SEQUENCE {
			serverTrendIndex
				INTEGER,
			serverTrendStartTime
				DisplayString,
			serverTrendStartUTC
				INTEGER,
			serverTrendStopTime
				DisplayString,
			serverTrendStopUTC
				INTEGER,
			serverTrendUpTime
				TimeTicks,
			serverTrendCacheLRU
				TimeTicks,
			serverTrendAvgUtil
				INTEGER,
			serverTrendPeakUtil
				INTEGER,
			serverTrendAvgConns
				INTEGER,
			serverTrendPeakConns
				INTEGER,
			serverTrendAvgUsers
				INTEGER,
			serverTrendPeakUsers
				INTEGER,
			serverTrendAvgFSPs
				INTEGER,
			serverTrendPeakFSPs
				INTEGER,
			serverTrendAvgProcs
				INTEGER,
			serverTrendPeakProcs
				INTEGER,
			serverTrendAvgCacheRatio
				INTEGER,
			serverTrendMinCacheRatio
				INTEGER,
			serverTrendAvgCacheHits
				INTEGER,
			serverTrendMinCacheHits
				INTEGER,
			serverTrendAvgDirBuffs
				INTEGER,
			serverTrendPeakDirBuffs
				INTEGER,
			serverTrendAvgRecvBuffs
				INTEGER,
			serverTrendPeakRecvBuffs
				INTEGER,
			serverTrendAvgOpenFiles
				INTEGER,
			serverTrendPeakOpenFiles
				INTEGER,
			serverTrendAvgIOsPending
				INTEGER,
			serverTrendPeakIOsPending
				INTEGER,
			serverTrendCumlIOsPending
				INTEGER,
			serverTrendAvgDirtyBlocks
				INTEGER,
			serverTrendPeakDirtyBlocks
				INTEGER,
			serverTrendCumlDirtyBlocks
				INTEGER,
			serverTrendAvgDiskReads
				INTEGER,
			serverTrendPeakDiskReads
				INTEGER,
			serverTrendCumlDiskReads
				INTEGER,
			serverTrendAvgDiskReadBytes
				INTEGER,
			serverTrendPeakDiskReadBytes
				INTEGER,
			serverTrendCumlDiskReadBytes
				INTEGER,
			serverTrendAvgDiskWrites
				INTEGER,
			serverTrendPeakDiskWrites
				INTEGER,
			serverTrendCumlDiskWrites
				INTEGER,
			serverTrendAvgDiskWriteBytes
				INTEGER,
			serverTrendPeakDiskWriteBytes
				INTEGER,
			serverTrendCumlDiskWriteBytes
				INTEGER,
			serverTrendAvgRoutedPkts
				INTEGER,
			serverTrendPeakRoutedPkts
				INTEGER,
			serverTrendCumlRoutedPkts
				INTEGER,
			serverTrendAvgRxPkts
				INTEGER,
			serverTrendPeakRxPkts
				INTEGER,
			serverTrendCumlRxPkts
				INTEGER,
			serverTrendAvgRxBytes
				INTEGER,
			serverTrendPeakRxBytes
				INTEGER,
			serverTrendCumlRxBytes
				INTEGER,
			serverTrendAvgTxPkts
				INTEGER,
			serverTrendPeakTxPkts
				INTEGER,
			serverTrendCumlTxPkts
				INTEGER,
			serverTrendAvgTxBytes
				INTEGER,
			serverTrendPeakTxBytes
				INTEGER,
			serverTrendCumlTxBytes
				INTEGER,
			serverTrendAvgDirSearch
				INTEGER,
			serverTrendPeakDirSearch
				INTEGER,
			serverTrendCumlDirSearch
				INTEGER,
			serverTrendAvgFileCreates
				INTEGER,
			serverTrendPeakFileCreates
				INTEGER,
			serverTrendCumlFileCreates
				INTEGER,
			serverTrendAvgFileOpens
				INTEGER,
			serverTrendPeakFileOpens
				INTEGER,
			serverTrendCumlFileOpens
				INTEGER,
			serverTrendAvgFileDeletes
				INTEGER,
			serverTrendPeakFileDeletes
				INTEGER,
			serverTrendCumlFileDeletes
				INTEGER,
			serverTrendAvgFileReads
				INTEGER,
			serverTrendPeakFileReads
				INTEGER,
			serverTrendCumlFileReads
				INTEGER,
			serverTrendAvgFileReadBytes
				INTEGER,
			serverTrendPeakFileReadBytes
				INTEGER,
			serverTrendCumlFileReadBytes
				INTEGER,
			serverTrendAvgFileWrites
				INTEGER,
			serverTrendPeakFileWrites
				INTEGER,
			serverTrendCumlFileWrites
				INTEGER,
			serverTrendAvgFileWriteBytes
				INTEGER,
			serverTrendPeakFileWriteBytes
				INTEGER,
			serverTrendCumlFileWriteBytes
				INTEGER,
			serverTrendMemoryAllocPoolTotal
				INTEGER,
			serverTrendMemoryAllocPoolInUse
				INTEGER,
			serverTrendMemoryCacheBufferPool
				INTEGER,
			serverTrendMemoryCacheMovablePool
				INTEGER,
			serverTrendMemoryCacheNonMovablePool
				INTEGER,
			serverTrendMemoryNw3PermMemoryPoolTotal
				INTEGER,
			serverTrendMemoryNw3PermMemoryPoolInUse
				INTEGER,
			serverTrendMemoryNw4CodeDataPool
				INTEGER
		    }

	serverTrendIndex OBJECT-TYPE
	    SYNTAX INTEGER
	    ACCESS read-only
	    STATUS mandatory
	    DESCRIPTION
		"Trend Statistics Index Pointer"
	::= { serverTrendEntry 1 }

	serverTrendStartTime OBJECT-TYPE
	    SYNTAX DisplayString (SIZE (0..32))
	    ACCESS read-only
	    STATUS mandatory
	    DESCRIPTION
		"Trend Cycle Start Time (string)"
	::= { serverTrendEntry 2 }

	serverTrendStartUTC OBJECT-TYPE
	    SYNTAX INTEGER
	    ACCESS read-only
	    STATUS mandatory
	    DESCRIPTION
		"Trend Cycle Start Time GMT (UTC secs)"
	::= { serverTrendEntry 3 }

	serverTrendStopTime OBJECT-TYPE
	    SYNTAX DisplayString (SIZE (0..32))
	    ACCESS read-only
	    STATUS mandatory
	    DESCRIPTION
		"Trend Cycle Stop Time (string)"
	::= { serverTrendEntry 4 }

	serverTrendStopUTC OBJECT-TYPE
	    SYNTAX INTEGER
	    ACCESS read-only
	    STATUS mandatory
	    DESCRIPTION
		"Trend Cycle Stop Time GMT (UTC secs)"
	::= { serverTrendEntry 5 }

	serverTrendUpTime OBJECT-TYPE
	    SYNTAX TimeTicks
	    ACCESS read-only
	    STATUS mandatory
	    DESCRIPTION
		"Trend Cycle Up-Time (Ticks)"
	::= { serverTrendEntry 6 }

	serverTrendCacheLRU OBJECT-TYPE
	    SYNTAX TimeTicks
	    ACCESS read-only
	    STATUS mandatory
	    DESCRIPTION
		"Trend Cycle Cache LRU (Ticks)"
	::= { serverTrendEntry 7 }

	serverTrendAvgUtil OBJECT-TYPE
	    SYNTAX INTEGER
	    ACCESS read-only
	    STATUS mandatory
	    DESCRIPTION
		"Trend Average CPU Utilization"
	::= { serverTrendEntry 8 }

	serverTrendPeakUtil OBJECT-TYPE
	    SYNTAX INTEGER
	    ACCESS read-only
	    STATUS mandatory
	    DESCRIPTION
		"Trend Peak CPU Utilization"
	::= { serverTrendEntry 9 }

	serverTrendAvgConns OBJECT-TYPE
	    SYNTAX INTEGER
	    ACCESS read-only
	    STATUS mandatory
	    DESCRIPTION
		"Trend Average Connections In Use"
	::= { serverTrendEntry 10 }

	serverTrendPeakConns OBJECT-TYPE
	    SYNTAX INTEGER
	    ACCESS read-only
	    STATUS mandatory
	    DESCRIPTION
		"Trend Peak Connections In Use"
	::= { serverTrendEntry 11 }

	serverTrendAvgUsers OBJECT-TYPE
	    SYNTAX INTEGER
	    ACCESS read-only
	    STATUS mandatory
	    DESCRIPTION
		"Trend Average Logged-in Users"
	::= { serverTrendEntry 12 }

	serverTrendPeakUsers OBJECT-TYPE
	    SYNTAX INTEGER
	    ACCESS read-only
	    STATUS mandatory
	    DESCRIPTION
		"Trend Peak Logged-in Users"
	::= { serverTrendEntry 13 }

	serverTrendAvgFSPs OBJECT-TYPE
	    SYNTAX INTEGER
	    ACCESS read-only
	    STATUS mandatory
	    DESCRIPTION
		"Trend Average File Service Processes (FSPs)"
	::= { serverTrendEntry 14 }

	serverTrendPeakFSPs OBJECT-TYPE
	    SYNTAX INTEGER
	    ACCESS read-only
	    STATUS mandatory
	    DESCRIPTION
		"Trend Peak File Service Processes (FSPs)"
	::= { serverTrendEntry 15 }

	serverTrendAvgProcs OBJECT-TYPE
	    SYNTAX INTEGER
	    ACCESS read-only
	    STATUS mandatory
	    DESCRIPTION
		"Trend Average Processes (non-FSPs)"
	::= { serverTrendEntry 16 }

	serverTrendPeakProcs OBJECT-TYPE
	    SYNTAX INTEGER
	    ACCESS read-only
	    STATUS mandatory
	    DESCRIPTION
		"Trend Peak Processes (non-FSPs)"
	::= { serverTrendEntry 17 }

	serverTrendAvgCacheRatio OBJECT-TYPE
	    SYNTAX INTEGER
	    ACCESS read-only
	    STATUS mandatory
	    DESCRIPTION
		"Trend Average Cache Buffer Ratio (%)"
	::= { serverTrendEntry 18 }

	serverTrendMinCacheRatio OBJECT-TYPE
	    SYNTAX INTEGER
	    ACCESS read-only
	    STATUS mandatory
	    DESCRIPTION
		"Trend Minimum Cache Buffer Ratio (%)"
	::= { serverTrendEntry 19 }

	serverTrendAvgCacheHits OBJECT-TYPE
	    SYNTAX INTEGER
	    ACCESS read-only
	    STATUS mandatory
	    DESCRIPTION
		"Trend Average Cache Hit Ratio (%)"
	::= { serverTrendEntry 20 }

	serverTrendMinCacheHits OBJECT-TYPE
	    SYNTAX INTEGER
	    ACCESS read-only
	    STATUS mandatory
	    DESCRIPTION
		"Trend Minimum Cache Hit Ratio (%)"
	::= { serverTrendEntry 21 }

	serverTrendAvgDirBuffs OBJECT-TYPE
	    SYNTAX INTEGER
	    ACCESS read-only
	    STATUS mandatory
	    DESCRIPTION
		"Trend Average Directory Cache Buffers"
	::= { serverTrendEntry 22 }

	serverTrendPeakDirBuffs OBJECT-TYPE
	    SYNTAX INTEGER
	    ACCESS read-only
	    STATUS mandatory
	    DESCRIPTION
		"Trend Peak Directory Cache Buffers"
	::= { serverTrendEntry 23 }

	serverTrendAvgRecvBuffs OBJECT-TYPE
	    SYNTAX INTEGER
	    ACCESS read-only
	    STATUS mandatory
	    DESCRIPTION
		"Trend Average Packet Receive Buffers"
	::= { serverTrendEntry 24 }

	serverTrendPeakRecvBuffs OBJECT-TYPE
	    SYNTAX INTEGER
	    ACCESS read-only
	    STATUS mandatory
	    DESCRIPTION
		"Trend Peak Packet Receive Buffers"
	::= { serverTrendEntry 25 }

	serverTrendAvgOpenFiles OBJECT-TYPE
	    SYNTAX INTEGER
	    ACCESS read-only
	    STATUS mandatory
	    DESCRIPTION
		"Trend Average Open Files"
	::= { serverTrendEntry 26 }

	serverTrendPeakOpenFiles OBJECT-TYPE
	    SYNTAX INTEGER
	    ACCESS read-only
	    STATUS mandatory
	    DESCRIPTION
		"Trend Peak Open Files"
	::= { serverTrendEntry 27 }

	serverTrendAvgIOsPending OBJECT-TYPE
	    SYNTAX INTEGER
	    ACCESS read-only
	    STATUS mandatory
	    DESCRIPTION
		"Trend Average Disk I/Os Pending"
	::= { serverTrendEntry 28 }

	serverTrendPeakIOsPending OBJECT-TYPE
	    SYNTAX INTEGER
	    ACCESS read-only
	    STATUS mandatory
	    DESCRIPTION
		"Trend Peak Disk I/Os Pending"
	::= { serverTrendEntry 29 }

	serverTrendCumlIOsPending OBJECT-TYPE
	    SYNTAX INTEGER
	    ACCESS read-only
	    STATUS mandatory
	    DESCRIPTION
		"Trend Cumulative Disk I/Os Pending"
	::= { serverTrendEntry 30 }

	serverTrendAvgDirtyBlocks OBJECT-TYPE
	    SYNTAX INTEGER
	    ACCESS read-only
	    STATUS mandatory
	    DESCRIPTION
		"Trend Average Dirty Blocks"
	::= { serverTrendEntry 31 }

	serverTrendPeakDirtyBlocks OBJECT-TYPE
	    SYNTAX INTEGER
	    ACCESS read-only
	    STATUS mandatory
	    DESCRIPTION
		"Trend Peak Dirty Blocks"
	::= { serverTrendEntry 32 }

	serverTrendCumlDirtyBlocks OBJECT-TYPE
	    SYNTAX INTEGER
	    ACCESS read-only
	    STATUS mandatory
	    DESCRIPTION
		"Trend Cumulative Dirty Blocks"
	::= { serverTrendEntry 33 }

	serverTrendAvgDiskReads OBJECT-TYPE
	    SYNTAX INTEGER
	    ACCESS read-only
	    STATUS mandatory
	    DESCRIPTION
		"Trend Average Physical Disk Reads"
	::= { serverTrendEntry 34 }

	serverTrendPeakDiskReads OBJECT-TYPE
	    SYNTAX INTEGER
	    ACCESS read-only
	    STATUS mandatory
	    DESCRIPTION
		"Trend Peak Physical Disk Reads"
	::= { serverTrendEntry 35 }

	serverTrendCumlDiskReads OBJECT-TYPE
	    SYNTAX INTEGER
	    ACCESS read-only
	    STATUS mandatory
	    DESCRIPTION
		"Trend Cumulative Physical Disk Reads"
	::= { serverTrendEntry 36 }

	serverTrendAvgDiskReadBytes OBJECT-TYPE
	    SYNTAX INTEGER
	    ACCESS read-only
	    STATUS mandatory
	    DESCRIPTION
		"Trend Average Physical Disk Read Bytes"
	::= { serverTrendEntry 37 }

	serverTrendPeakDiskReadBytes OBJECT-TYPE
	    SYNTAX INTEGER
	    ACCESS read-only
	    STATUS mandatory
	    DESCRIPTION
		"Trend Peak Physical Disk Read Bytes"
	::= { serverTrendEntry 38 }

	serverTrendCumlDiskReadBytes OBJECT-TYPE
	    SYNTAX INTEGER
	    ACCESS read-only
	    STATUS mandatory
	    DESCRIPTION
		"Trend Cumulative Physical Disk Read Bytes"
	::= { serverTrendEntry 39 }

	serverTrendAvgDiskWrites OBJECT-TYPE
	    SYNTAX INTEGER
	    ACCESS read-only
	    STATUS mandatory
	    DESCRIPTION
		"Trend Average Physical Disk Writes"
	::= { serverTrendEntry 40 }

	serverTrendPeakDiskWrites OBJECT-TYPE
	    SYNTAX INTEGER
	    ACCESS read-only
	    STATUS mandatory
	    DESCRIPTION
		"Trend Peak Physical Disk Writes"
	::= { serverTrendEntry 41 }

	serverTrendCumlDiskWrites OBJECT-TYPE
	    SYNTAX INTEGER
	    ACCESS read-only
	    STATUS mandatory
	    DESCRIPTION
		"Trend Cumulative Physical Disk Writes"
	::= { serverTrendEntry 42 }

	serverTrendAvgDiskWriteBytes OBJECT-TYPE
	    SYNTAX INTEGER
	    ACCESS read-only
	    STATUS mandatory
	    DESCRIPTION
		"Trend Average Physical Disk Write Bytes"
	::= { serverTrendEntry 43 }

	serverTrendPeakDiskWriteBytes OBJECT-TYPE
	    SYNTAX INTEGER
	    ACCESS read-only
	    STATUS mandatory
	    DESCRIPTION
		"Trend Peak Physical Disk Write Bytes"
	::= { serverTrendEntry 44 }

	serverTrendCumlDiskWriteBytes OBJECT-TYPE
	    SYNTAX INTEGER
	    ACCESS read-only
	    STATUS mandatory
	    DESCRIPTION
		"Trend Cumulative Physical Disk Write Bytes"
	::= { serverTrendEntry 45 }

	serverTrendAvgRoutedPkts OBJECT-TYPE
	    SYNTAX INTEGER
	    ACCESS read-only
	    STATUS mandatory
	    DESCRIPTION
		"Trend Average LAN Routed Packets"
	::= { serverTrendEntry 46 }

	serverTrendPeakRoutedPkts OBJECT-TYPE
	    SYNTAX INTEGER
	    ACCESS read-only
	    STATUS mandatory
	    DESCRIPTION
		"Trend Peak LAN Routed Packets"
	::= { serverTrendEntry 47 }

	serverTrendCumlRoutedPkts OBJECT-TYPE
	    SYNTAX INTEGER
	    ACCESS read-only
	    STATUS mandatory
	    DESCRIPTION
		"Trend Cumulative LAN Routed Packets"
	::= { serverTrendEntry 48 }

	serverTrendAvgRxPkts OBJECT-TYPE
	    SYNTAX INTEGER
	    ACCESS read-only
	    STATUS mandatory
	    DESCRIPTION
		"Trend Average LAN Rx Packets"
	::= { serverTrendEntry 49 }

	serverTrendPeakRxPkts OBJECT-TYPE
	    SYNTAX INTEGER
	    ACCESS read-only
	    STATUS mandatory
	    DESCRIPTION
		"Trend Peak LAN Rx Packets"
	::= { serverTrendEntry 50 }

	serverTrendCumlRxPkts OBJECT-TYPE
	    SYNTAX INTEGER
	    ACCESS read-only
	    STATUS mandatory
	    DESCRIPTION
		"Trend Cumulative LAN Rx Packets"
	::= { serverTrendEntry 51 }

	serverTrendAvgRxBytes OBJECT-TYPE
	    SYNTAX INTEGER
	    ACCESS read-only
	    STATUS mandatory
	    DESCRIPTION
		"Trend Average LAN Rx Bytes"
	::= { serverTrendEntry 52 }

	serverTrendPeakRxBytes OBJECT-TYPE
	    SYNTAX INTEGER
	    ACCESS read-only
	    STATUS mandatory
	    DESCRIPTION
		"Trend Peak LAN Rx Bytes"
	::= { serverTrendEntry 53 }

	serverTrendCumlRxBytes OBJECT-TYPE
	    SYNTAX INTEGER
	    ACCESS read-only
	    STATUS mandatory
	    DESCRIPTION
		"Trend Cumulative LAN Rx Bytes"
	::= { serverTrendEntry 54 }

	serverTrendAvgTxPkts OBJECT-TYPE
	    SYNTAX INTEGER
	    ACCESS read-only
	    STATUS mandatory
	    DESCRIPTION
		"Trend Average LAN Tx Packets"
	::= { serverTrendEntry 55 }

	serverTrendPeakTxPkts OBJECT-TYPE
	    SYNTAX INTEGER
	    ACCESS read-only
	    STATUS mandatory
	    DESCRIPTION
		"Trend Peak LAN Tx Packets"
	::= { serverTrendEntry 56 }

	serverTrendCumlTxPkts OBJECT-TYPE
	    SYNTAX INTEGER
	    ACCESS read-only
	    STATUS mandatory
	    DESCRIPTION
		"Trend Cumulative LAN Tx Packets"
	::= { serverTrendEntry 57 }

	serverTrendAvgTxBytes OBJECT-TYPE
	    SYNTAX INTEGER
	    ACCESS read-only
	    STATUS mandatory
	    DESCRIPTION
		"Trend Average LAN Tx Bytes"
	::= { serverTrendEntry 58 }

	serverTrendPeakTxBytes OBJECT-TYPE
	    SYNTAX INTEGER
	    ACCESS read-only
	    STATUS mandatory
	    DESCRIPTION
		"Trend Peak LAN Tx Bytes"
	::= { serverTrendEntry 59 }

	serverTrendCumlTxBytes OBJECT-TYPE
	    SYNTAX INTEGER
	    ACCESS read-only
	    STATUS mandatory
	    DESCRIPTION
		"Trend Cumulative LAN Tx Bytes"
	::= { serverTrendEntry 60 }

	serverTrendAvgDirSearch OBJECT-TYPE
	    SYNTAX INTEGER
	    ACCESS read-only
	    STATUS mandatory
	    DESCRIPTION
		"Trend Average Directory Search Requests"
	::= { serverTrendEntry 61 }

	serverTrendPeakDirSearch OBJECT-TYPE
	    SYNTAX INTEGER
	    ACCESS read-only
	    STATUS mandatory
	    DESCRIPTION
		"Trend Peak Directory Search Requests"
	::= { serverTrendEntry 62 }

	serverTrendCumlDirSearch OBJECT-TYPE
	    SYNTAX INTEGER
	    ACCESS read-only
	    STATUS mandatory
	    DESCRIPTION
		"Trend Cumulative Directory Search Requests"
	::= { serverTrendEntry 63 }

	serverTrendAvgFileCreates OBJECT-TYPE
	    SYNTAX INTEGER
	    ACCESS read-only
	    STATUS mandatory
	    DESCRIPTION
		"Trend Average File Create Requests"
	::= { serverTrendEntry 64 }

	serverTrendPeakFileCreates OBJECT-TYPE
	    SYNTAX INTEGER
	    ACCESS read-only
	    STATUS mandatory
	    DESCRIPTION
		"Trend Peak File Create Requests"
	::= { serverTrendEntry 65 }

	serverTrendCumlFileCreates OBJECT-TYPE
	    SYNTAX INTEGER
	    ACCESS read-only
	    STATUS mandatory
	    DESCRIPTION
		"Trend Cumulative File Create Requests"
	::= { serverTrendEntry 66 }

	serverTrendAvgFileOpens OBJECT-TYPE
	    SYNTAX INTEGER
	    ACCESS read-only
	    STATUS mandatory
	    DESCRIPTION
		"Trend Average File Open Requests"
	::= { serverTrendEntry 67 }

	serverTrendPeakFileOpens OBJECT-TYPE
	    SYNTAX INTEGER
	    ACCESS read-only
	    STATUS mandatory
	    DESCRIPTION
		"Trend Peak File Open Requests"
	::= { serverTrendEntry 68 }

	serverTrendCumlFileOpens OBJECT-TYPE
	    SYNTAX INTEGER
	    ACCESS read-only
	    STATUS mandatory
	    DESCRIPTION
		"Trend Cumulative File Open Requests"
	::= { serverTrendEntry 69 }

	serverTrendAvgFileDeletes OBJECT-TYPE
	    SYNTAX INTEGER
	    ACCESS read-only
	    STATUS mandatory
	    DESCRIPTION
		"Trend Average File Delete Requests"
	::= { serverTrendEntry 70 }

	serverTrendPeakFileDeletes OBJECT-TYPE
	    SYNTAX INTEGER
	    ACCESS read-only
	    STATUS mandatory
	    DESCRIPTION
		"Trend Peak File Delete Requests"
	::= { serverTrendEntry 71 }

	serverTrendCumlFileDeletes OBJECT-TYPE
	    SYNTAX INTEGER
	    ACCESS read-only
	    STATUS mandatory
	    DESCRIPTION
		"Trend Cumulative File Delete Requests"
	::= { serverTrendEntry 72 }

	serverTrendAvgFileReads OBJECT-TYPE
	    SYNTAX INTEGER
	    ACCESS read-only
	    STATUS mandatory
	    DESCRIPTION
		"Trend Average File Read Requests"
	::= { serverTrendEntry 73 }

	serverTrendPeakFileReads OBJECT-TYPE
	    SYNTAX INTEGER
	    ACCESS read-only
	    STATUS mandatory
	    DESCRIPTION
		"Trend Peak File Read Requests"
	::= { serverTrendEntry 74 }

	serverTrendCumlFileReads OBJECT-TYPE
	    SYNTAX INTEGER
	    ACCESS read-only
	    STATUS mandatory
	    DESCRIPTION
		"Trend Cumulative File Read Requests"
	::= { serverTrendEntry 75 }

	serverTrendAvgFileReadBytes OBJECT-TYPE
	    SYNTAX INTEGER
	    ACCESS read-only
	    STATUS mandatory
	    DESCRIPTION
		"Trend Average File Read Bytes"
	::= { serverTrendEntry 76 }

	serverTrendPeakFileReadBytes OBJECT-TYPE
	    SYNTAX INTEGER
	    ACCESS read-only
	    STATUS mandatory
	    DESCRIPTION
		"Trend Peak File Read Bytes"
	::= { serverTrendEntry 77 }

	serverTrendCumlFileReadBytes OBJECT-TYPE
	    SYNTAX INTEGER
	    ACCESS read-only
	    STATUS mandatory
	    DESCRIPTION
		"Trend Cumulative File Read Bytes"
	::= { serverTrendEntry 78 }

	serverTrendAvgFileWrites OBJECT-TYPE
	    SYNTAX INTEGER
	    ACCESS read-only
	    STATUS mandatory
	    DESCRIPTION
		"Trend Average File Write Requests"
	::= { serverTrendEntry 79 }

	serverTrendPeakFileWrites OBJECT-TYPE
	    SYNTAX INTEGER
	    ACCESS read-only
	    STATUS mandatory
	    DESCRIPTION
		"Trend Peak File Write Requests"
	::= { serverTrendEntry 80 }

	serverTrendCumlFileWrites OBJECT-TYPE
	    SYNTAX INTEGER
	    ACCESS read-only
	    STATUS mandatory
	    DESCRIPTION
		"Trend Cumulative File Write Requests"
	::= { serverTrendEntry 81 }

	serverTrendAvgFileWriteBytes OBJECT-TYPE
	    SYNTAX INTEGER
	    ACCESS read-only
	    STATUS mandatory
	    DESCRIPTION
		"Trend Average File Write Bytes"
	::= { serverTrendEntry 82 }

	serverTrendPeakFileWriteBytes OBJECT-TYPE
	    SYNTAX INTEGER
	    ACCESS read-only
	    STATUS mandatory
	    DESCRIPTION
		"Trend Peak File Write Bytes"
	::= { serverTrendEntry 83 }

	serverTrendCumlFileWriteBytes OBJECT-TYPE
	    SYNTAX INTEGER
	    ACCESS read-only
	    STATUS mandatory
	    DESCRIPTION
		"Trend Cumulative File Write Bytes"
	::= { serverTrendEntry 84 }

	serverTrendMemoryAllocPoolTotal OBJECT-TYPE
	    SYNTAX INTEGER
	    ACCESS read-only
	    STATUS mandatory
	    DESCRIPTION
		"Trend Work Dynamic Memory Pool Allocated"
	::= { serverTrendEntry 85 }

	serverTrendMemoryAllocPoolInUse OBJECT-TYPE
	    SYNTAX INTEGER
	    ACCESS read-only
	    STATUS mandatory
	    DESCRIPTION
		"Trend Work Dynamic Memory Pool In Use"
	::= { serverTrendEntry 86 }

	serverTrendMemoryCacheBufferPool OBJECT-TYPE
	    SYNTAX INTEGER
	    ACCESS read-only
	    STATUS mandatory
	    DESCRIPTION
		"Trend Cache Buffer Pool"
	::= { serverTrendEntry 87 }

	serverTrendMemoryCacheMovablePool OBJECT-TYPE
	    SYNTAX INTEGER
	    ACCESS read-only
	    STATUS mandatory
	    DESCRIPTION
		"Trend Cache Movable Pool"
	::= { serverTrendEntry 88 }

	serverTrendMemoryCacheNonMovablePool OBJECT-TYPE
	    SYNTAX INTEGER
	    ACCESS read-only
	    STATUS mandatory
	    DESCRIPTION
		"Trend Cache Non-Movable Pool"
	::= { serverTrendEntry 89 }

	serverTrendMemoryNw3PermMemoryPoolTotal OBJECT-TYPE
	    SYNTAX INTEGER
	    ACCESS read-only
	    STATUS mandatory
	    DESCRIPTION
		"Trend Permanent Memory Pool Total (NetWare v3 only)"
	::= { serverTrendEntry 90 }

	serverTrendMemoryNw3PermMemoryPoolInUse OBJECT-TYPE
	    SYNTAX INTEGER
	    ACCESS read-only
	    STATUS mandatory
	    DESCRIPTION
		"Trend Permanent Memory Pool In Use (NetWare v3 only)"
	::= { serverTrendEntry 91 }

	serverTrendMemoryNw4CodeDataPool OBJECT-TYPE
	    SYNTAX INTEGER
	    ACCESS read-only
	    STATUS mandatory
	    DESCRIPTION
		"Trend Code And Data Memory Pool (NetWare v4 only)"
	::= { serverTrendEntry 92 }



	volCount OBJECT-TYPE
	    SYNTAX INTEGER
	    ACCESS read-only
	    STATUS mandatory
	    DESCRIPTION
		"Mounted Volumes"
	::= { volinfo 1 }

	volTable OBJECT-TYPE
	    SYNTAX SEQUENCE OF VolEntry
	    ACCESS not-accessible
	    STATUS mandatory
	    DESCRIPTION
		"Mounted Volume Entry Table"
	::= { volinfo 2 }

	volEntry OBJECT-TYPE
	    SYNTAX VolEntry
	    ACCESS not-accessible
	    STATUS mandatory
	    DESCRIPTION
		"Mounted Volume Entry"
	    INDEX  { volIndex }
	::= { volTable 1 }

	VolEntry ::=
	    SEQUENCE {
			volIndex
				INTEGER,
			volName
				DisplayString,
			volDriveNumber
				INTEGER,
			volBlockSize
				INTEGER,
			volDirSlots
				INTEGER,
			volDirSlotsFree
				INTEGER,
			volDiskSpace
				INTEGER,
			volDiskSpaceFree
				INTEGER,
			volDiskSpacePurgable
				INTEGER,
			volDiskSpaceNotYetPurgable
				INTEGER
		    }

	volIndex OBJECT-TYPE
	    SYNTAX INTEGER
	    ACCESS read-only
	    STATUS mandatory
	    DESCRIPTION
		"Mounted Volume Index Pointer"
	::= { volEntry 1 }

	volName OBJECT-TYPE
	    SYNTAX DisplayString (SIZE (0..16))
	    ACCESS read-only
	    STATUS mandatory
	    DESCRIPTION
		"Mounted Volume Name"
	::= { volEntry 2 }

	volDriveNumber OBJECT-TYPE
	    SYNTAX INTEGER
	    ACCESS read-only
	    STATUS mandatory
	    DESCRIPTION
		"Mounted Volume Drive Number"
	::= { volEntry 3 }

	volBlockSize OBJECT-TYPE
	    SYNTAX INTEGER
	    ACCESS read-only
	    STATUS mandatory
	    DESCRIPTION
		"Mounted Volume Block Size (bytes)"
	::= { volEntry 4 }

	volDirSlots OBJECT-TYPE
	    SYNTAX INTEGER
	    ACCESS read-only
	    STATUS mandatory
	    DESCRIPTION
		"Mounted Volume Allocated Directory Slots"
	::= { volEntry 5 }

	volDirSlotsFree OBJECT-TYPE
	    SYNTAX INTEGER
	    ACCESS read-only
	    STATUS mandatory
	    DESCRIPTION
		"Mounted Volume Available Directory Slots"
	::= { volEntry 6 }

	volDiskSpace OBJECT-TYPE
	    SYNTAX INTEGER
	    ACCESS read-only
	    STATUS mandatory
	    DESCRIPTION
		"Mounted Volume Configured Disk Space (Kb)"
	::= { volEntry 7 }

	volDiskSpaceFree OBJECT-TYPE
	    SYNTAX INTEGER
	    ACCESS read-only
	    STATUS mandatory
	    DESCRIPTION
		"Mounted Volume Available Disk Space (Kb)"
	::= { volEntry 8 }

	volDiskSpacePurgable OBJECT-TYPE
	    SYNTAX INTEGER
	    ACCESS read-only
	    STATUS mandatory
	    DESCRIPTION
		"Mounted Volume Purgable Disk Space (Kb)"
	::= { volEntry 9 }

	volDiskSpaceNotYetPurgable OBJECT-TYPE
	    SYNTAX INTEGER
	    ACCESS read-only
	    STATUS mandatory
	    DESCRIPTION
		"Mounted Volume Not Yet Purgable Disk Space(Kb)"
	::= { volEntry 10 }



	volTrendTable OBJECT-TYPE
	    SYNTAX SEQUENCE OF VolTrendEntry
	    ACCESS not-accessible
	    STATUS mandatory
	    DESCRIPTION
		"Volume Trends Entry Table"
	::= { voltrends 1 }

	volTrendEntry OBJECT-TYPE
	    SYNTAX VolTrendEntry
	    ACCESS not-accessible
	    STATUS mandatory
	    DESCRIPTION
		"Volume Trends Entry"
	    INDEX  { volTrendCycleIndex, volTrendVolumeIndex }
	::= { volTrendTable 1 }

	VolTrendEntry ::=
	    SEQUENCE {
			volTrendCycleIndex
				INTEGER,
			volTrendVolumeIndex
				INTEGER,
			volTrendStartTime
				DisplayString,
			volTrendStartUTC
				INTEGER,
			volTrendStopTime
				DisplayString,
			volTrendStopUTC
				INTEGER,
			volTrendName
				DisplayString,
			volTrendDirSlots
				INTEGER,
			volTrendDirSlotsFree
				INTEGER,
			volTrendDiskSpace
				INTEGER,
			volTrendDiskSpaceFree
				INTEGER,
			volTrendDiskSpacePurgable
				INTEGER,
			volTrendDiskSpaceNotYetPurgable
				INTEGER
		    }

	volTrendCycleIndex OBJECT-TYPE
	    SYNTAX INTEGER
	    ACCESS read-only
	    STATUS mandatory
	    DESCRIPTION
		"Volume Trend Cycle Index"
	::= { volTrendEntry 1 }

	volTrendVolumeIndex OBJECT-TYPE
	    SYNTAX INTEGER
	    ACCESS read-only
	    STATUS mandatory
	    DESCRIPTION
		"Volume Trend Volume Index"
	::= { volTrendEntry 2 }

	volTrendStartTime OBJECT-TYPE
	    SYNTAX DisplayString (SIZE (0..32))
	    ACCESS read-only
	    STATUS mandatory
	    DESCRIPTION
		"Volume Trend Start Time"
	::= { volTrendEntry 3 }

	volTrendStartUTC OBJECT-TYPE
	    SYNTAX INTEGER
	    ACCESS read-only
	    STATUS mandatory
	    DESCRIPTION
		"Volume Trend Start Time GMT (UTC secs)"
	::= { volTrendEntry 4 }

	volTrendStopTime OBJECT-TYPE
	    SYNTAX DisplayString (SIZE (0..32))
	    ACCESS read-only
	    STATUS mandatory
	    DESCRIPTION
		"Volume Trend Stop Time"
	::= { volTrendEntry 5 }

	volTrendStopUTC OBJECT-TYPE
	    SYNTAX INTEGER
	    ACCESS read-only
	    STATUS mandatory
	    DESCRIPTION
		"Volume Trend Stop Time GMT (UTC secs)"
	::= { volTrendEntry 6 }

	volTrendName OBJECT-TYPE
	    SYNTAX DisplayString (SIZE (0..16))
	    ACCESS read-only
	    STATUS mandatory
	    DESCRIPTION
		"Volume Trend Volume Name"
	::= { volTrendEntry 7 }

	volTrendDirSlots OBJECT-TYPE
	    SYNTAX INTEGER
	    ACCESS read-only
	    STATUS mandatory
	    DESCRIPTION
		"Volume Trend Allocated Directory Slots"
	::= { volTrendEntry 8 }

	volTrendDirSlotsFree OBJECT-TYPE
	    SYNTAX INTEGER
	    ACCESS read-only
	    STATUS mandatory
	    DESCRIPTION
		"Volume Trend Available Directory Slots"
	::= { volTrendEntry 9 }

	volTrendDiskSpace OBJECT-TYPE
	    SYNTAX INTEGER
	    ACCESS read-only
	    STATUS mandatory
	    DESCRIPTION
		"Volume Trend Configured Disk Space (Kb)"
	::= { volTrendEntry 10 }

	volTrendDiskSpaceFree OBJECT-TYPE
	    SYNTAX INTEGER
	    ACCESS read-only
	    STATUS mandatory
	    DESCRIPTION
		"Volume Trend Available Disk Space (Kb)"
	::= { volTrendEntry 11 }

	volTrendDiskSpacePurgable OBJECT-TYPE
	    SYNTAX INTEGER
	    ACCESS read-only
	    STATUS mandatory
	    DESCRIPTION
		"Volume Trend Purgable Disk Space (Kb)"
	::= { volTrendEntry 12 }

	volTrendDiskSpaceNotYetPurgable OBJECT-TYPE
	    SYNTAX INTEGER
	    ACCESS read-only
	    STATUS mandatory
	    DESCRIPTION
		"Volume Trend Not Yet Purgable Disk Space(Kb)"
	::= { volTrendEntry 13 }



	driveCount OBJECT-TYPE
	    SYNTAX INTEGER
	    ACCESS read-only
	    STATUS mandatory
	    DESCRIPTION
		"Active Drives"
	::= { driveinfo 1 }

	driveTable OBJECT-TYPE
	    SYNTAX SEQUENCE OF DriveEntry
	    ACCESS not-accessible
	    STATUS mandatory
	    DESCRIPTION
		"Active Drive Entry Table"
	::= { driveinfo 2 }

	driveEntry OBJECT-TYPE
	    SYNTAX DriveEntry
	    ACCESS not-accessible
	    STATUS mandatory
	    DESCRIPTION
		"Active Drive Entry"
	    INDEX  { driveIndex }
	::= { driveTable 1 }

	DriveEntry ::=
	    SEQUENCE {
			driveIndex
				INTEGER,
			driveDesc
				DisplayString,
			driveType
				DisplayString,
			driveControllerCardID
				INTEGER,
			driveControllerDeviceID
				INTEGER,
			driveControllerDriveID
				INTEGER,
			driveCylinderCount
				INTEGER,
			driveHeadCount
				INTEGER,
			driveSectorsPerTrack
				INTEGER,
			driveSize
				INTEGER,
			driveNumberOfPartitions
				INTEGER,
			driveNetWarePartitionStatus
				DisplayString,
			driveNetWarePartitionType
				DisplayString,
			driveNetWarePartitionSize
				INTEGER,
			driveMirrorFlag
				DisplayString,
			driveMirrorStatus
				DisplayString,
			driveRemirrorPercentage
				INTEGER,
			driveRedirectionSize
				INTEGER,
			driveRedirectedSize
				INTEGER,
			driveRedirectionReservedSize
				INTEGER
		    }

	driveIndex OBJECT-TYPE
	    SYNTAX INTEGER
	    ACCESS read-only
	    STATUS mandatory
	    DESCRIPTION
		"Active Drive Index Pointer"
	::= { driveEntry 1 }

	driveDesc OBJECT-TYPE
	    SYNTAX DisplayString (SIZE (0..40))
	    ACCESS read-only
	    STATUS mandatory
	    DESCRIPTION
		"Active Drive Description"
	::= { driveEntry 2 }

	driveType OBJECT-TYPE
	    SYNTAX DisplayString (SIZE (0..40))
	    ACCESS read-only
	    STATUS mandatory
	    DESCRIPTION
		"Active Drive Type"
	::= { driveEntry 3 }

	driveControllerCardID OBJECT-TYPE
	    SYNTAX INTEGER
	    ACCESS read-only
	    STATUS mandatory
	    DESCRIPTION
		"Active Drive Controller ID (Physical)"
	::= { driveEntry 4 }

	driveControllerDeviceID OBJECT-TYPE
	    SYNTAX INTEGER
	    ACCESS read-only
	    STATUS mandatory
	    DESCRIPTION
		"Active Drive Controller Device ID (Logical)"
	::= { driveEntry 5 }

	driveControllerDriveID OBJECT-TYPE
	    SYNTAX INTEGER
	    ACCESS read-only
	    STATUS mandatory
	    DESCRIPTION
		"Active Drive Controller Drive ID (Physical)"
	::= { driveEntry 6 }

	driveCylinderCount OBJECT-TYPE
	    SYNTAX INTEGER
	    ACCESS read-only
	    STATUS mandatory
	    DESCRIPTION
		"Active Drive Cylinders"
	::= { driveEntry 7 }

	driveHeadCount OBJECT-TYPE
	    SYNTAX INTEGER
	    ACCESS read-only
	    STATUS mandatory
	    DESCRIPTION
		"Active Drive Heads"
	::= { driveEntry 8 }

	driveSectorsPerTrack OBJECT-TYPE
	    SYNTAX INTEGER
	    ACCESS read-only
	    STATUS mandatory
	    DESCRIPTION
		"Active Drive Sectors Per Track"
	::= { driveEntry 9 }

	driveSize OBJECT-TYPE
	    SYNTAX INTEGER
	    ACCESS read-only
	    STATUS mandatory
	    DESCRIPTION
		"Active Drive Size (KBytes)"
	::= { driveEntry 10 }

	driveNumberOfPartitions OBJECT-TYPE
	    SYNTAX INTEGER
	    ACCESS read-only
	    STATUS mandatory
	    DESCRIPTION
		"Active Drive Number Of Partitions"
	::= { driveEntry 11 }

	driveNetWarePartitionStatus OBJECT-TYPE
	    SYNTAX DisplayString (SIZE (0..8))
	    ACCESS read-only
	    STATUS mandatory
	    DESCRIPTION
		"Active Drive NetWare Partition Status (Present/None)"
	::= { driveEntry 12 }

	driveNetWarePartitionType OBJECT-TYPE
	    SYNTAX DisplayString (SIZE (0..20))
	    ACCESS read-only
	    STATUS mandatory
	    DESCRIPTION
		"Active Drive NetWare Partition Type (NetWare 286/NetWare 386)"
	::= { driveEntry 13 }

	driveNetWarePartitionSize OBJECT-TYPE
	    SYNTAX INTEGER
	    ACCESS read-only
	    STATUS mandatory
	    DESCRIPTION
		"Active Drive NetWare Partition Size (KBytes)"
	::= { driveEntry 14 }

	driveMirrorFlag OBJECT-TYPE
	    SYNTAX DisplayString (SIZE (0..13))
	    ACCESS read-only
	    STATUS mandatory
	    DESCRIPTION
		"Active Drive Mirror Flag (Mirrored/Not-Mirrored)"
	::= { driveEntry 15 }

	driveMirrorStatus OBJECT-TYPE
	    SYNTAX DisplayString (SIZE (0..13))
	    ACCESS read-only
	    STATUS mandatory
	    DESCRIPTION
		"Active Drive Mirror Status (In-Sync/Partial Sync/Remirroring)"
	::= { driveEntry 16 }

	driveRemirrorPercentage OBJECT-TYPE
	    SYNTAX INTEGER
	    ACCESS read-only
	    STATUS mandatory
	    DESCRIPTION
		"Active Drive Remirror Process Status (Percent Complete)"
	::= { driveEntry 17 }

	driveRedirectionSize OBJECT-TYPE
	    SYNTAX INTEGER
	    ACCESS read-only
	    STATUS mandatory
	    DESCRIPTION
		"Active Drive NetWare Partition Redirection Size (HotFix Allocated KBytes)"
	::= { driveEntry 18 }

	driveRedirectedSize OBJECT-TYPE
	    SYNTAX INTEGER
	    ACCESS read-only
	    STATUS mandatory
	    DESCRIPTION
		"Active Drive NetWare Partition Redirected Size (HotFix Used KBytes)"
	::= { driveEntry 19 }

	driveRedirectionReservedSize OBJECT-TYPE
	    SYNTAX INTEGER
	    ACCESS read-only
	    STATUS mandatory
	    DESCRIPTION
		"Active Drive NetWare Partition Reserved Redirection Size (HotFix Reserved KBytes)"
	::= { driveEntry 20 }



	driveTrendsTable OBJECT-TYPE
	    SYNTAX SEQUENCE OF DriveTrendEntry
	    ACCESS not-accessible
	    STATUS mandatory
	    DESCRIPTION
		"Drive Trend Entry Table"
	::= { drivetrends 1 }

	driveTrendEntry OBJECT-TYPE
	    SYNTAX DriveTrendEntry
	    ACCESS not-accessible
	    STATUS mandatory
	    DESCRIPTION
		"Drive Trend Entry"
	    INDEX  { driveTrendCycleIndex, driveTrendDriveIndex }
	::= { driveTrendsTable 1 }

	DriveTrendEntry ::=
	    SEQUENCE {
			driveTrendCycleIndex
				INTEGER,
			driveTrendDriveIndex
				INTEGER,
			driveTrendStartTime
				DisplayString,
			driveTrendStartUTC
				INTEGER,
			driveTrendStopTime
				DisplayString,
			driveTrendStopUTC
				INTEGER,
			driveTrendDesc
				DisplayString,
			driveTrendSize
				INTEGER,
			driveTrendRedirectionSize
				INTEGER,
			driveTrendRedirectedSize
				INTEGER,
			driveTrendRedirectionReservedSize
				INTEGER
		    }

	driveTrendCycleIndex OBJECT-TYPE
	    SYNTAX INTEGER
	    ACCESS read-only
	    STATUS mandatory
	    DESCRIPTION
		"Drive Trend Cycle Index"
	::= { driveTrendEntry 1 }

	driveTrendDriveIndex OBJECT-TYPE
	    SYNTAX INTEGER
	    ACCESS read-only
	    STATUS mandatory
	    DESCRIPTION
		"Drive Trend Drive Index"
	::= { driveTrendEntry 2 }

	driveTrendStartTime OBJECT-TYPE
	    SYNTAX DisplayString (SIZE (0..32))
	    ACCESS read-only
	    STATUS mandatory
	    DESCRIPTION
		"Drive Trend Start Time (string)"
	::= { driveTrendEntry 3 }

	driveTrendStartUTC OBJECT-TYPE
	    SYNTAX INTEGER
	    ACCESS read-only
	    STATUS mandatory
	    DESCRIPTION
		"Drive Trend Start Time GMT (UTC secs)"
	::= { driveTrendEntry 4 }

	driveTrendStopTime OBJECT-TYPE
	    SYNTAX DisplayString (SIZE (0..32))
	    ACCESS read-only
	    STATUS mandatory
	    DESCRIPTION
		"Drive Trend Stop Time"
	::= { driveTrendEntry 5 }

	driveTrendStopUTC OBJECT-TYPE
	    SYNTAX INTEGER
	    ACCESS read-only
	    STATUS mandatory
	    DESCRIPTION
		"Drive Trend Stop Time GMT (UTC secs)"
	::= { driveTrendEntry 6 }

	driveTrendDesc OBJECT-TYPE
	    SYNTAX DisplayString (SIZE (0..40))
	    ACCESS read-only
	    STATUS mandatory
	    DESCRIPTION
		"Drive Trend Description"
	::= { driveTrendEntry 7 }

	driveTrendSize OBJECT-TYPE
	    SYNTAX INTEGER
	    ACCESS read-only
	    STATUS mandatory
	    DESCRIPTION
		"Drive Trend Size (KBytes)"
	::= { driveTrendEntry 8 }

	driveTrendRedirectionSize OBJECT-TYPE
	    SYNTAX INTEGER
	    ACCESS read-only
	    STATUS mandatory
	    DESCRIPTION
		"Drive Trend NetWare Partition Redirection Size (HotFix Allocated KBytes)"
	::= { driveTrendEntry 9 }

	driveTrendRedirectedSize OBJECT-TYPE
	    SYNTAX INTEGER
	    ACCESS read-only
	    STATUS mandatory
	    DESCRIPTION
		"Drive Trend NetWare Partition Redirected Size (HotFix Used KBytes)"
	::= { driveTrendEntry 10 }

	driveTrendRedirectionReservedSize OBJECT-TYPE
	    SYNTAX INTEGER
	    ACCESS read-only
	    STATUS mandatory
	    DESCRIPTION
		"Drive Trend NetWare Partition Reserved Redirection Size (HotFix Reserved KBytes)"
	::= { driveTrendEntry 11 }



	nicTrendsTable OBJECT-TYPE
	    SYNTAX SEQUENCE OF NicTrendEntry
	    ACCESS not-accessible
	    STATUS mandatory
	    DESCRIPTION
		"NIC Trend Entry Table"
	::= { nictrends 1 }

	nicTrendEntry OBJECT-TYPE
	    SYNTAX NicTrendEntry
	    ACCESS not-accessible
	    STATUS mandatory
	    DESCRIPTION
		"NIC Trend Entry"
	    INDEX  { nicTrendCycleIndex, nicTrendNICIndex }
	::= { nicTrendsTable 1 }

	NicTrendEntry ::=
	    SEQUENCE {
			nicTrendCycleIndex
				INTEGER,
			nicTrendNICIndex
				INTEGER,
			nicTrendStartTime
				DisplayString,
			nicTrendStartUTC
				INTEGER,
			nicTrendStopTime
				DisplayString,
			nicTrendStopUTC
				INTEGER,
			nicTrendNodeID
				OCTET STRING,
			nicTrendAvgRxPacketCount
				INTEGER,
			nicTrendPeakRxPacketCount
				INTEGER,
			nicTrendCumlRxPacketCount
				INTEGER,
			nicTrendAvgTxPacketCount
				INTEGER,
			nicTrendPeakTxPacketCount
				INTEGER,
			nicTrendCumlTxPacketCount
				INTEGER
		    }

	nicTrendCycleIndex OBJECT-TYPE
	    SYNTAX INTEGER
	    ACCESS read-only
	    STATUS mandatory
	    DESCRIPTION
		"NIC Trend Cycle Index"
	::= { nicTrendEntry 1 }

	nicTrendNICIndex OBJECT-TYPE
	    SYNTAX INTEGER
	    ACCESS read-only
	    STATUS mandatory
	    DESCRIPTION
		"NIC Trend NIC Index"
	::= { nicTrendEntry 2 }

	nicTrendStartTime OBJECT-TYPE
	    SYNTAX DisplayString (SIZE (0..32))
	    ACCESS read-only
	    STATUS mandatory
	    DESCRIPTION
		"NIC Trend Start Time (string)"
	::= { nicTrendEntry 3 }

	nicTrendStartUTC OBJECT-TYPE
	    SYNTAX INTEGER
	    ACCESS read-only
	    STATUS mandatory
	    DESCRIPTION
		"NIC Trend Start Time GMT (UTC secs)"
	::= { nicTrendEntry 4 }

	nicTrendStopTime OBJECT-TYPE
	    SYNTAX DisplayString (SIZE (0..32))
	    ACCESS read-only
	    STATUS mandatory
	    DESCRIPTION
		"NIC Trend Stop Time"
	::= { nicTrendEntry 5 }

	nicTrendStopUTC OBJECT-TYPE
	    SYNTAX INTEGER
	    ACCESS read-only
	    STATUS mandatory
	    DESCRIPTION
		"NIC Trend Stop Time GMT (UTC secs)"
	::= { nicTrendEntry 6 }

	nicTrendNodeID OBJECT-TYPE
	    SYNTAX OCTET STRING (SIZE (6))
	    ACCESS read-only
	    STATUS mandatory
	    DESCRIPTION
		"NIC Trend Node ID"
	::= { nicTrendEntry 7 }

	nicTrendAvgRxPacketCount OBJECT-TYPE
	    SYNTAX INTEGER
	    ACCESS read-only
	    STATUS mandatory
	    DESCRIPTION
		"NIC Trend Average Rx Packets"
	::= { nicTrendEntry 8 }

	nicTrendPeakRxPacketCount OBJECT-TYPE
	    SYNTAX INTEGER
	    ACCESS read-only
	    STATUS mandatory
	    DESCRIPTION
		"NIC Trend Peak Rx Packets"
	::= { nicTrendEntry 9 }

	nicTrendCumlRxPacketCount OBJECT-TYPE
	    SYNTAX INTEGER
	    ACCESS read-only
	    STATUS mandatory
	    DESCRIPTION
		"NIC Trend Cumulative Rx Packets"
	::= { nicTrendEntry 10 }

	nicTrendAvgTxPacketCount OBJECT-TYPE
	    SYNTAX INTEGER
	    ACCESS read-only
	    STATUS mandatory
	    DESCRIPTION
		"NIC Trend Average Tx Packets"
	::= { nicTrendEntry 11 }

	nicTrendPeakTxPacketCount OBJECT-TYPE
	    SYNTAX INTEGER
	    ACCESS read-only
	    STATUS mandatory
	    DESCRIPTION
		"NIC Trend Peak Tx Packets"
	::= { nicTrendEntry 12 }

	nicTrendCumlTxPacketCount OBJECT-TYPE
	    SYNTAX INTEGER
	    ACCESS read-only
	    STATUS mandatory
	    DESCRIPTION
		"NIC Trend Cumulative Tx Packets"
	::= { nicTrendEntry 13 }



	protocolCount OBJECT-TYPE
	    SYNTAX INTEGER
	    ACCESS read-only
	    STATUS mandatory
	    DESCRIPTION
		"Configured Protocols"
	::= { protocolinfo 1 }

	protocolTable OBJECT-TYPE
	    SYNTAX SEQUENCE OF ProtocolEntry
	    ACCESS not-accessible
	    STATUS mandatory
	    DESCRIPTION
		"Configured Protocol Entry Table"
	::= { protocolinfo 2 }

	protocolEntry OBJECT-TYPE
	    SYNTAX ProtocolEntry
	    ACCESS not-accessible
	    STATUS mandatory
	    DESCRIPTION
		"Configured Protocol Entry"
	    INDEX  { protocolIndex }
	::= { protocolTable 1 }

	ProtocolEntry ::=
	    SEQUENCE {
			protocolIndex
				INTEGER,
			protocolDesc
				DisplayString,
			protocolCurrRxPacketCount
				INTEGER,
			protocolAvgRxPacketCount
				INTEGER,
			protocolPeakRxPacketCount
				INTEGER,
			protocolCumlRxPacketCount
				INTEGER,
			protocolCurrTxPacketCount
				INTEGER,
			protocolAvgTxPacketCount
				INTEGER,
			protocolPeakTxPacketCount
				INTEGER,
			protocolCumlTxPacketCount
				INTEGER
		    }

	protocolIndex OBJECT-TYPE
	    SYNTAX INTEGER
	    ACCESS read-only
	    STATUS mandatory
	    DESCRIPTION
		"Protocol Index Pointer"
	::= { protocolEntry 1 }

	protocolDesc OBJECT-TYPE
	    SYNTAX DisplayString (SIZE (0..32))
	    ACCESS read-only
	    STATUS mandatory
	    DESCRIPTION
		"Protocol Description"
	::= { protocolEntry 2 }

	protocolCurrRxPacketCount OBJECT-TYPE
	    SYNTAX INTEGER
	    ACCESS read-only
	    STATUS mandatory
	    DESCRIPTION
		"Protocol Current Rx Packets"
	::= { protocolEntry 3 }

	protocolAvgRxPacketCount OBJECT-TYPE
	    SYNTAX INTEGER
	    ACCESS read-only
	    STATUS mandatory
	    DESCRIPTION
		"Protocol Average Rx Packets"
	::= { protocolEntry 4 }

	protocolPeakRxPacketCount OBJECT-TYPE
	    SYNTAX INTEGER
	    ACCESS read-only
	    STATUS mandatory
	    DESCRIPTION
		"Protocol Peak Rx Packets"
	::= { protocolEntry 5 }

	protocolCumlRxPacketCount OBJECT-TYPE
	    SYNTAX INTEGER
	    ACCESS read-only
	    STATUS mandatory
	    DESCRIPTION
		"Protocol Cumulative Rx Packets"
	::= { protocolEntry 6 }

	protocolCurrTxPacketCount OBJECT-TYPE
	    SYNTAX INTEGER
	    ACCESS read-only
	    STATUS mandatory
	    DESCRIPTION
		"Protocol Current Tx Packets"
	::= { protocolEntry 7 }

	protocolAvgTxPacketCount OBJECT-TYPE
	    SYNTAX INTEGER
	    ACCESS read-only
	    STATUS mandatory
	    DESCRIPTION
		"Protocol Average Tx Packets"
	::= { protocolEntry 8 }

	protocolPeakTxPacketCount OBJECT-TYPE
	    SYNTAX INTEGER
	    ACCESS read-only
	    STATUS mandatory
	    DESCRIPTION
		"Protocol Peak Tx Packets"
	::= { protocolEntry 9 }

	protocolCumlTxPacketCount OBJECT-TYPE
	    SYNTAX INTEGER
	    ACCESS read-only
	    STATUS mandatory
	    DESCRIPTION
		"Protocol Cumulative Tx Packets"
	::= { protocolEntry 10 }



	protocolTrendsTable OBJECT-TYPE
	    SYNTAX SEQUENCE OF ProtocolTrendEntry
	    ACCESS not-accessible
	    STATUS mandatory
	    DESCRIPTION
		"Protocol Trend Entry Table"
	::= { protocoltrends 1 }

	protocolTrendEntry OBJECT-TYPE
	    SYNTAX ProtocolTrendEntry
	    ACCESS not-accessible
	    STATUS mandatory
	    DESCRIPTION
		"Protocol Trend Entry"
	    INDEX  { protocolTrendCycleIndex, protocolTrendProtocolIndex }
	::= { protocolTrendsTable 1 }

	ProtocolTrendEntry ::=
	    SEQUENCE {
			protocolTrendCycleIndex
				INTEGER,
			protocolTrendProtocolIndex
				INTEGER,
			protocolTrendStartTime
				DisplayString,
			protocolTrendStartUTC
				INTEGER,
			protocolTrendStopTime
				DisplayString,
			protocolTrendStopUTC
				INTEGER,
			protocolTrendDesc
				DisplayString,
			protocolTrendAvgRxPacketCount
				INTEGER,
			protocolTrendPeakRxPacketCount
				INTEGER,
			protocolTrendCumlRxPacketCount
				INTEGER,
			protocolTrendAvgTxPacketCount
				INTEGER,
			protocolTrendPeakTxPacketCount
				INTEGER,
			protocolTrendCumlTxPacketCount
				INTEGER
		    }

	protocolTrendCycleIndex OBJECT-TYPE
	    SYNTAX INTEGER
	    ACCESS read-only
	    STATUS mandatory
	    DESCRIPTION
		"Protocol Trend Cycle Index"
	::= { protocolTrendEntry 1 }

	protocolTrendProtocolIndex OBJECT-TYPE
	    SYNTAX INTEGER
	    ACCESS read-only
	    STATUS mandatory
	    DESCRIPTION
		"Protocol Trend Protocol Index"
	::= { protocolTrendEntry 2 }

	protocolTrendStartTime OBJECT-TYPE
	    SYNTAX DisplayString (SIZE (0..32))
	    ACCESS read-only
	    STATUS mandatory
	    DESCRIPTION
		"Protocol Trend Start Time"
	::= { protocolTrendEntry 3 }

	protocolTrendStartUTC OBJECT-TYPE
	    SYNTAX INTEGER
	    ACCESS read-only
	    STATUS mandatory
	    DESCRIPTION
		"Protocol Trend Start Time GMT (UTC secs)"
	::= { protocolTrendEntry 4 }

	protocolTrendStopTime OBJECT-TYPE
	    SYNTAX DisplayString (SIZE (0..32))
	    ACCESS read-only
	    STATUS mandatory
	    DESCRIPTION
		"Protocol Trend Stop Time"
	::= { protocolTrendEntry 5 }

	protocolTrendStopUTC OBJECT-TYPE
	    SYNTAX INTEGER
	    ACCESS read-only
	    STATUS mandatory
	    DESCRIPTION
		"Protocol Trend Stop Time GMT (UTC secs)"
	::= { protocolTrendEntry 6 }

	protocolTrendDesc OBJECT-TYPE
	    SYNTAX DisplayString (SIZE (0..32))
	    ACCESS read-only
	    STATUS mandatory
	    DESCRIPTION
		"Protocol Trend Description"
	::= { protocolTrendEntry 7 }

	protocolTrendAvgRxPacketCount OBJECT-TYPE
	    SYNTAX INTEGER
	    ACCESS read-only
	    STATUS mandatory
	    DESCRIPTION
		"Protocol Trend Average Rx Packets"
	::= { protocolTrendEntry 8 }

	protocolTrendPeakRxPacketCount OBJECT-TYPE
	    SYNTAX INTEGER
	    ACCESS read-only
	    STATUS mandatory
	    DESCRIPTION
		"Protocol Trend Peak Rx Packets"
	::= { protocolTrendEntry 9 }

	protocolTrendCumlRxPacketCount OBJECT-TYPE
	    SYNTAX INTEGER
	    ACCESS read-only
	    STATUS mandatory
	    DESCRIPTION
		"Protocol Trend Cumulative Rx Packets"
	::= { protocolTrendEntry 10 }

	protocolTrendAvgTxPacketCount OBJECT-TYPE
	    SYNTAX INTEGER
	    ACCESS read-only
	    STATUS mandatory
	    DESCRIPTION
		"Protocol Trend Average Tx Packets"
	::= { protocolTrendEntry 11 }

	protocolTrendPeakTxPacketCount OBJECT-TYPE
	    SYNTAX INTEGER
	    ACCESS read-only
	    STATUS mandatory
	    DESCRIPTION
		"Protocol Trend Peak Tx Packets"
	::= { protocolTrendEntry 12 }

	protocolTrendCumlTxPacketCount OBJECT-TYPE
	    SYNTAX INTEGER
	    ACCESS read-only
	    STATUS mandatory
	    DESCRIPTION
		"Protocol Trend Cumulative Tx Packets"
	::= { protocolTrendEntry 13 }



	smpCount OBJECT-TYPE
	    SYNTAX INTEGER
	    ACCESS read-only
	    STATUS mandatory
	    DESCRIPTION
		"SMP Processors"
	::= { smpinfo 1 }

	smpTable OBJECT-TYPE
	    SYNTAX SEQUENCE OF SmpEntry
	    ACCESS not-accessible
	    STATUS mandatory
	    DESCRIPTION
		"SMP Processor Entry Table"
	::= { smpinfo 2 }

	smpEntry OBJECT-TYPE
	    SYNTAX SmpEntry
	    ACCESS not-accessible
	    STATUS mandatory
	    DESCRIPTION
		"SMP Processor Entry"
	    INDEX  { smpIndex }
	::= { smpTable 1 }

	SmpEntry ::=
	    SEQUENCE {
			smpIndex
				INTEGER,
			smpCurrUtil
				INTEGER,
			smpAvgUtil
				INTEGER,
			smpPeakUtil
				INTEGER
		    }

	smpIndex OBJECT-TYPE
	    SYNTAX INTEGER
	    ACCESS read-only
	    STATUS mandatory
	    DESCRIPTION
		"SMP Processor Index Pointer"
	::= { smpEntry 1 }

	smpCurrUtil OBJECT-TYPE
	    SYNTAX INTEGER
	    ACCESS read-only
	    STATUS mandatory
	    DESCRIPTION
		"SMP Processor Current Utilization"
	::= { smpEntry 2 }

	smpAvgUtil OBJECT-TYPE
	    SYNTAX INTEGER
	    ACCESS read-only
	    STATUS mandatory
	    DESCRIPTION
		"SMP Processor Average Utilization (current cycle)"
	::= { smpEntry 3 }

	smpPeakUtil OBJECT-TYPE
	    SYNTAX INTEGER
	    ACCESS read-only
	    STATUS mandatory
	    DESCRIPTION
		"SMP Processor Peak Utilization (current cycle)"
	::= { smpEntry 4 }



	smpTrendTable OBJECT-TYPE
	    SYNTAX SEQUENCE OF SmpTrendEntry
	    ACCESS not-accessible
	    STATUS mandatory
	    DESCRIPTION
		"SMP Processor Trends Entry Table"
	::= { smptrends 1 }

	smpTrendEntry OBJECT-TYPE
	    SYNTAX SmpTrendEntry
	    ACCESS not-accessible
	    STATUS mandatory
	    DESCRIPTION
		"SMP Processor Trends Entry"
	    INDEX  { smpTrendCycleIndex, smpTrendProcessorIndex }
	::= { smpTrendTable 1 }

	SmpTrendEntry ::=
	    SEQUENCE {
			smpTrendCycleIndex
				INTEGER,
			smpTrendProcessorIndex
				INTEGER,
			smpTrendStartTime
				DisplayString,
			smpTrendStartUTC
				INTEGER,
			smpTrendStopTime
				DisplayString,
			smpTrendStopUTC
				INTEGER,
			smpTrendAvgUtil
				INTEGER,
			smpTrendPeakUtil
				INTEGER
		    }

	smpTrendCycleIndex OBJECT-TYPE
	    SYNTAX INTEGER
	    ACCESS read-only
	    STATUS mandatory
	    DESCRIPTION
		"SMP Trend Cycle Index"
	::= { smpTrendEntry 1 }

	smpTrendProcessorIndex OBJECT-TYPE
	    SYNTAX INTEGER
	    ACCESS read-only
	    STATUS mandatory
	    DESCRIPTION
		"SMP Trend Processor Index"
	::= { smpTrendEntry 2 }

	smpTrendStartTime OBJECT-TYPE
	    SYNTAX DisplayString (SIZE (0..32))
	    ACCESS read-only
	    STATUS mandatory
	    DESCRIPTION
		"SMP Trend Start Time"
	::= { smpTrendEntry 3 }

	smpTrendStartUTC OBJECT-TYPE
	    SYNTAX INTEGER
	    ACCESS read-only
	    STATUS mandatory
	    DESCRIPTION
		"SMP Trend Start Time GMT (UTC secs)"
	::= { smpTrendEntry 4 }

	smpTrendStopTime OBJECT-TYPE
	    SYNTAX DisplayString (SIZE (0..32))
	    ACCESS read-only
	    STATUS mandatory
	    DESCRIPTION
		"SMP Trend Stop Time"
	::= { smpTrendEntry 5 }

	smpTrendStopUTC OBJECT-TYPE
	    SYNTAX INTEGER
	    ACCESS read-only
	    STATUS mandatory
	    DESCRIPTION
		"SMP Trend Stop Time GMT (UTC secs)"
	::= { smpTrendEntry 6 }

	smpTrendAvgUtil OBJECT-TYPE
	    SYNTAX INTEGER
	    ACCESS read-only
	    STATUS mandatory
	    DESCRIPTION
		"SMP Trend Processor Average Utilization"
	::= { smpTrendEntry 7 }

	smpTrendPeakUtil OBJECT-TYPE
	    SYNTAX INTEGER
	    ACCESS read-only
	    STATUS mandatory
	    DESCRIPTION
		"SMP Trend Processor Peak Utilization"
	::= { smpTrendEntry 8 }

END
