PROBERTTEXT-MIB 

   --FORCE-INCLUDE <mib.h>
   --FORCE-INCLUDE <snmpdefs.h>
   --FORCE-INCLUDE <snmpstat.h>
   --FORCE-INCLUDE "mibproto.h"
 
	DEFINITIONS ::= BEGIN

	IMPORTS
		MODULE-IDENTITY, OBJECT-TYPE, Integer32
			FROM SNMPv2-SMI                    
		DisplayString
			FROM SNMPv2-TC
		probeRttExt
			FROM APENT-MIB;

--PROBERTTEXT MIB

    apProbeRttExtMib MODULE-IDENTITY
	   LAST-UPDATED "9707202000Z" -- Wed July 20 20:00:00 EST 1997
	   ORGANIZATION "ArrowPoint Communications Inc."
	   CONTACT-INFO
	   "                Customer Support
	   Postal:          ArrowPoint Communications, Inc.
				  		50 Nagog Park
				  		Acton, Massachusetts 01720
	   Tel:             +1 978 206 3000
	   E-Mail:          mibsupport@arrowpoint.com"
       DESCRIPTION
	  "The MIB module used to describe the ArrowPoint Communications Tiered
	  Proximity Service RTT Probe Module functionality."
      ::= { probeRttExt 1 }


--RTT Probe Module Objects
apProbeRttEnable OBJECT-TYPE
	SYNTAX			INTEGER { 
								disable(0),
								enable(1)
							}
	MAX-ACCESS		read-only
	STATUS			current
	DESCRIPTION
		"This object specifies the state of the Proximity RTT Probe Module.
		 When 'enable' the RTT PM is running on this system.  When 'disable'
         it is not.  This object is valid only if apProximityEnable is 'enable'"
	::= { probeRttExt 2 }

apProbeRttMethod0 OBJECT-TYPE
	SYNTAX			INTEGER { 
								icmp(0),
								tcp(1)
							}
	MAX-ACCESS		read-write
	STATUS			current
	DESCRIPTION
		"This object specifies which probe method is to be tried first.
		 This object is valid only if apProbeRttEnable is 'enable'"
    DEFVAL {0}
	::= { probeRttExt 3 }

apProbeRttMethod1 OBJECT-TYPE
	SYNTAX			INTEGER { 
								icmp(0),
								tcp(1),
                                none(2)
							}
	MAX-ACCESS		read-write
	STATUS			current
	DESCRIPTION
		"This object specifies which probe method is to be tried second.
		 This object is valid only if apProbeRttEnable is 'enable'"
    DEFVAL {1}
	::= { probeRttExt 4 }

apProbeRttIcmpSamples OBJECT-TYPE
	SYNTAX			Integer32 (1 .. 30)
	MAX-ACCESS		read-write
	STATUS			current
	DESCRIPTION
		"This object specifies the number of ICMP probe requests to be
         used to calculate the RTT mean.  This object is valid only if
         apProbeRttEnable is 'enable'"
    DEFVAL {2}
	::= { probeRttExt 5 }

apProbeRttIcmpInterval OBJECT-TYPE
	SYNTAX			Integer32 (1 .. 10)
	MAX-ACCESS		read-write
	STATUS			current
	DESCRIPTION
		"This object specifies the time delay in seconds between
         consecutive ICMP requests to an individual client. This object
         is valid only if apProbeRttEnable is 'enable'"
    DEFVAL {1}
	::= { probeRttExt 6 }

apProbeRttTcpPort0 OBJECT-TYPE
	SYNTAX			Integer32 (0 .. 65535)
	MAX-ACCESS		read-write
	STATUS			current
	DESCRIPTION
		"The first TCP port number to be probed on the client's local name
         server."
    DEFVAL {23}
	::= { probeRttExt 7 }

apProbeRttTcpPort1 OBJECT-TYPE
	SYNTAX			Integer32 (0 .. 65535)
	MAX-ACCESS		read-write
	STATUS			current
	DESCRIPTION
		"The second TCP port number to be probed on the client's local name
         server.  Used only if the first port fails."
    DEFVAL {21}
	::= { probeRttExt 8 }

apProbeRttTcpPort2 OBJECT-TYPE
	SYNTAX			Integer32 (0 .. 65535)
	MAX-ACCESS		read-write
	STATUS			current
	DESCRIPTION
		"The third TCP port number to be probed on the client's local name
         server.  Used only if the first and second ports fail."
    DEFVAL {80}
	::= { probeRttExt 9 }

apProbeRttTcpPort3 OBJECT-TYPE
	SYNTAX			Integer32 (0 .. 65535)
	MAX-ACCESS		read-write
	STATUS			current
	DESCRIPTION
		"The fourth TCP port number to be probed on the client's local name
         server.  Used only if the first, second and third ports fail."
    DEFVAL {0}
	::= { probeRttExt 10 }      
	
apProbeRttLastReset OBJECT-TYPE
	SYNTAX			DisplayString    (SIZE(0..19)) 
	MAX-ACCESS		read-only
	STATUS			current
	DESCRIPTION
		"Elapsed time since the Proximity RTT Probe statistics were reset."
	::= { probeRttExt 11 }  
	
apProbeRttTtlProbes		OBJECT-TYPE
	SYNTAX				Integer32
	MAX-ACCESS  	 	read-only
	STATUS				current
	DESCRIPTION
		"The total number of times that the PDB has probed a client to measure
         the RTT.  This may be more than the total number of unique clients,
         and may be less than the actual number of ICMP or TCP requests."
	::= { probeRttExt 12}

apProbeRttAvgProbes		OBJECT-TYPE
	SYNTAX				Integer32
	MAX-ACCESS   		read-only
	STATUS				current
	DESCRIPTION
		"The cumulative average number of probes per minute since last reset."
	::= { probeRttExt 13}
apProbeRttICMPReqSent		OBJECT-TYPE
	SYNTAX				Integer32
	MAX-ACCESS   		read-only
	STATUS				current
	DESCRIPTION
		"The total number of ICMP requests that have been successfully sent
         from the PDB in order to measure RTT."
	::= { probeRttExt 14}
	
apProbeRttICMPResp		OBJECT-TYPE
	SYNTAX				Integer32
	MAX-ACCESS   		read-only
	STATUS				current
	DESCRIPTION
		"The total number of valid ICMP responses that the PDB has received.
         Valid ICMP responses are used to measure RTT."
	::= { probeRttExt 15}
	
apProbeRttICMPNoResp	OBJECT-TYPE
	SYNTAX				Integer32
	MAX-ACCESS 		  	read-only
	STATUS				current
	DESCRIPTION
		"The total number of ICMP requests that were successfully sent that did
         not receive a reply.  The ICMP requests that do not recieve a response
         are not used to measure RTT."
	::= { probeRttExt 16}
apProbeRttICMPAvgReq	OBJECT-TYPE
	SYNTAX				Integer32
	MAX-ACCESS   		read-only
	STATUS				current
	DESCRIPTION
		"The cumulative average number of ICMP requests per minute that were
         successfully sent during the time period since last reset."
	::= { probeRttExt 17}
apProbeRttICMPSendFail		OBJECT-TYPE
	SYNTAX				Integer32
	MAX-ACCESS   		read-only
	STATUS				current
	DESCRIPTION
		"The total number of ICMP requests that the PDB tried to send, but
         that failed internally, due to a missing route or other problem."
	::= { probeRttExt 18}
apProbeRttTCPReqSent	OBJECT-TYPE
	SYNTAX				Integer32
	MAX-ACCESS   		read-only
	STATUS				current
	DESCRIPTION
		"The total number of TCP requests that have been successfully sent
         from the PDB in order to measure RTT."
	::= { probeRttExt 19}
apProbeRttTCPResp		OBJECT-TYPE
	SYNTAX				Integer32
	MAX-ACCESS   		read-only
	STATUS				current
	DESCRIPTION
		"The total number of valid TCP responses that the PDB has recieved.
         Valid TCP responses are used to measure RTT."
	::= { probeRttExt 20}
apProbeRttTCPNoResp		OBJECT-TYPE
	SYNTAX				Integer32
	MAX-ACCESS   		read-only
	STATUS				current
	DESCRIPTION
		"The total number of TCP request that were successfully sent that did
         not recieve a usable response.  The RCP requests that do not receive
         a response are not used to measure RTT."
	::= { probeRttExt 21}
apProbeRttTCPAvgReq		OBJECT-TYPE
	SYNTAX				Integer32
	MAX-ACCESS   		read-only
	STATUS				current
	DESCRIPTION
		"The cumulative average number of TCP requests per minute that were
         successfully sent during the time period since the last reset."
	::= { probeRttExt 22}
apProbeRttTCPSendFail	OBJECT-TYPE
	SYNTAX				Integer32
	MAX-ACCESS   		read-only
	STATUS				current
	DESCRIPTION
		"The total number of TCP requests that the PDB tried to send, but
         that failed internally, due to a missing route or other problem."
	::= { probeRttExt 23}      
	
apProbeRttPortTable OBJECT-TYPE
	SYNTAX	SEQUENCE OF ApProbeRttPortEntry
	MAX-ACCESS  	not-accessible
	STATUS  		current
	DESCRIPTION
		"Statistics table for the TCP ports that are used for probing clients."
	::= {probeRttExt 24 }
	
apProbeRttPortEntry OBJECT-TYPE
	SYNTAX 		ApProbeRttPortEntry
	MAX-ACCESS	not-accessible
	STATUS		current
	DESCRIPTION 
		"Statistics table entries for TCP ports used for probing clients." 
	INDEX {apProbeRttPortIndex}
	::= {apProbeRttPortTable 1}
	
ApProbeRttPortEntry ::=
	SEQUENCE {
		apProbeRttPortIndex		Integer32,
		apProbeRttPortNumber	Integer32,
		apProbeRttPortRequests  Integer32,
		apProbeRttPortResponses Integer32,
		apProbeRttPortFailures  Integer32     
		}
		
apProbeRttPortIndex OBJECT-TYPE
	SYNTAX 			Integer32(0..3)
	MAX-ACCESS		read-only
	STATUS			current
	DESCRIPTION
		"The index for port information.  Not the actual port number"
	::= {apProbeRttPortEntry 1}
apProbeRttPortNumber OBJECT-TYPE
	SYNTAX			Integer32
	MAX-ACCESS		read-only
	STATUS 			current
	DESCRIPTION
		"The TCP port number used for probing the client's name server."
	::= {apProbeRttPortEntry 2}
apProbeRttPortRequests OBJECT-TYPE
	SYNTAX			Integer32
	MAX-ACCESS		read-only
	STATUS			current
	DESCRIPTION
		"Total number of successful TCP requests to this port on the client's
         name server."
	::= {apProbeRttPortEntry 3} 
apProbeRttPortResponses OBJECT-TYPE
	SYNTAX			Integer32
	MAX-ACCESS		read-only
	STATUS			current
	DESCRIPTION		
		"Total number of respones to TCP requests that were sent to this port
         on the client's local name server."
	::= {apProbeRttPortEntry 4}
	
apProbeRttPortFailures OBJECT-TYPE
	SYNTAX			Integer32
	MAX-ACCESS		read-only
	STATUS			current
	DESCRIPTION
		"Total number of failed TCP requests that were destined for this port
         on the client's local name server."
	::= {apProbeRttPortEntry 5}

END
