-- automatically generated by mosy 7.1 #288 (float-factor), do not edit!

ORANAMES-MIB DEFINITIONS ::= BEGIN


IMPORTS
	DisplayString
		FROM RFC1213-MIB
	OBJECT-TYPE
		FROM RFC-1212
	Counter, TimeTicks, enterprises
		FROM RFC1155-SMI
	applIndex
		FROM NETWORK-SERVICES-MIB;

DateAndTime ::= OCTET STRING (SIZE (8 .. 11))
TruthValue  ::= INTEGER { true(1), false(2) }

oracle OBJECT IDENTIFIER ::= { enterprises 111 }

oraNamesMIB OBJECT IDENTIFIER ::= { oracle  6 }

oraNamesObjects OBJECT IDENTIFIER ::= { oraNamesMIB  1 }

oraNamesTNSTable OBJECT-TYPE
    SYNTAX  SEQUENCE OF OraNamesTNSEntry
    ACCESS  not-accessible
    STATUS  mandatory
    DESCRIPTION
           "Table of standard TNS variables."
    ::= { oraNamesObjects  1 }

oraNamesTNSEntry OBJECT-TYPE
    SYNTAX  OraNamesTNSEntry
    ACCESS  not-accessible
    STATUS  mandatory
    DESCRIPTION
           "Entry contains variables which are generic to TNS applications."
    INDEX   { applIndex }
    ::= { oraNamesTNSTable  1 }

OraNamesTNSEntry ::=
    SEQUENCE {
        oraNamesTNSstartDate
            DateAndTime,

        oraNamesTNStraceLevel
            INTEGER (-2147483648..2147483647),

        oraNamesTNSsecurityLevel
            INTEGER (-2147483648..2147483647),

        oraNamesTNSparameterFile
            DisplayString,

        oraNamesTNSlogFile
            DisplayString,

        oraNamesTNStraceFile
            DisplayString,

        oraNamesTNSstate
            INTEGER (-2147483648..2147483647),

        oraNamesTNScontact
            DisplayString,

        oraNamesTNSlistenAddresses
            DisplayString,

        oraNamesTNSfailedListenAddresses
            DisplayString,

        oraNamesTNSreload
            TimeTicks,

        oraNamesTNSrunningTime
            INTEGER (-2147483648..2147483647)
    }

oraNamesTNSstartDate OBJECT-TYPE
    SYNTAX  DateAndTime
    ACCESS  read-only
    STATUS  mandatory
    DESCRIPTION
           "Date and time when this service was initialized."
    ::= { oraNamesTNSEntry  1 }

oraNamesTNStraceLevel OBJECT-TYPE
    SYNTAX  INTEGER (-2147483648..2147483647)
    ACCESS  read-write
    STATUS  mandatory
    DESCRIPTION
           "The level of tracing in use by this server. The higher the number,
           the more verbose the tracing information."
    ::= { oraNamesTNSEntry  2 }

oraNamesTNSsecurityLevel OBJECT-TYPE
    SYNTAX  INTEGER (-2147483648..2147483647)
    ACCESS  read-only
    STATUS  mandatory
    DESCRIPTION
           "The degree to which access to this server is restricted."
    ::= { oraNamesTNSEntry  3 }

oraNamesTNSparameterFile OBJECT-TYPE
    SYNTAX  DisplayString
    ACCESS  read-write
    STATUS  mandatory
    DESCRIPTION
           "Name of the file containing startup configuration parameters for
           this service."
    ::= { oraNamesTNSEntry  4 }

oraNamesTNSlogFile OBJECT-TYPE
    SYNTAX  DisplayString
    ACCESS  read-write
    STATUS  mandatory
    DESCRIPTION
           "Name of the file which this server writes log information to."
    ::= { oraNamesTNSEntry  5 }

oraNamesTNStraceFile OBJECT-TYPE
    SYNTAX  DisplayString
    ACCESS  read-write
    STATUS  mandatory
    DESCRIPTION
           "Name of the file which tis server writes trace information to if
           tracing is enabled."
    ::= { oraNamesTNSEntry  6 }

oraNamesTNSstate OBJECT-TYPE
    SYNTAX  INTEGER (-2147483648..2147483647)
    ACCESS  read-write
    STATUS  mandatory
    DESCRIPTION
           "Operation status of this server."
    ::= { oraNamesTNSEntry  7 }

oraNamesTNScontact OBJECT-TYPE
    SYNTAX  DisplayString
    ACCESS  read-only
    STATUS  mandatory
    DESCRIPTION
           "Person to contact regarding the operation or administration of this
           server."
    ::= { oraNamesTNSEntry  8 }

oraNamesTNSlistenAddresses OBJECT-TYPE
    SYNTAX  DisplayString
    ACCESS  read-only
    STATUS  mandatory
    DESCRIPTION
           "TNS address on which this service can be called."
    ::= { oraNamesTNSEntry  9 }

oraNamesTNSfailedListenAddresses OBJECT-TYPE
    SYNTAX  DisplayString
    ACCESS  read-only
    STATUS  mandatory
    DESCRIPTION
           "TNS addresses which this server attempted to listen on but failed."
    ::= { oraNamesTNSEntry  10 }

oraNamesTNSreload OBJECT-TYPE
    SYNTAX  TimeTicks
    ACCESS  read-write
    STATUS  mandatory
    DESCRIPTION
           "The amount of time in centiseconds until this server reloads."
    ::= { oraNamesTNSEntry  11 }

oraNamesTNSrunningTime OBJECT-TYPE
    SYNTAX  INTEGER (-2147483648..2147483647)
    ACCESS  read-only
    STATUS  mandatory
    DESCRIPTION
           "The amount of time in seconds that the server has been running."
    ::= { oraNamesTNSEntry  12 }

oraNamesConfigTable OBJECT-TYPE
    SYNTAX  SEQUENCE OF OraNamesConfigEntry
    ACCESS  not-accessible
    STATUS  mandatory
    DESCRIPTION
           "Oracle Names server configuration paramaters."
    ::= { oraNamesObjects  2 }

oraNamesConfigEntry OBJECT-TYPE
    SYNTAX  OraNamesConfigEntry
    ACCESS  not-accessible
    STATUS  mandatory
    DESCRIPTION
           "A set of paramters which can be set (in names.ora) to configure
           or tune a Names server."
    INDEX   { applIndex }
    ::= { oraNamesConfigTable  1 }

OraNamesConfigEntry ::=
    SEQUENCE {
        oraNamesConfigAdminRegion
            DisplayString,

        oraNamesConfigAuthorityRequired
            TruthValue,

        oraNamesConfigAutoRefreshExpire
            TimeTicks,

        oraNamesConfigAutoRefreshRetry
            TimeTicks,

        oraNamesConfigCacheCheckpointFile
            DisplayString,

        oraNamesConfigCacheCheckpointInterval
            TimeTicks,

        oraNamesConfigConfigCheckpointFile
            DisplayString,

        oraNamesConfigDefaultForwarders
            DisplayString,

        oraNamesConfigDefaultForwardersOnly
            TruthValue,

        oraNamesConfigDomainCheckpointFile
            DisplayString,

        oraNamesConfigDomainHints
            DisplayString,

        oraNamesConfigDomains
            DisplayString,

        oraNamesConfigForwardingAvailable
            TruthValue,

        oraNamesConfigForwardingDesired
            TruthValue,

        oraNamesConfigLogDirectory
            DisplayString,

        oraNamesConfigLogStatsInterval
            TimeTicks,

        oraNamesConfigLogUnique
            TruthValue,

        oraNamesConfigMaxOpenConnections
            INTEGER (-2147483648..2147483647),

        oraNamesConfigMaxReforwards
            INTEGER (-2147483648..2147483647),

        oraNamesConfigMessagePoolStartSize
            INTEGER (-2147483648..2147483647),

        oraNamesConfigNoModifyRequests
            TruthValue,

        oraNamesConfigNoRegionDatabase
            TruthValue,

        oraNamesConfigResetStatsInterval
            TimeTicks,

        oraNamesConfigServerName
            DisplayString,

        oraNamesConfigTopologyCheckpointFile
            DisplayString,

        oraNamesConfigTraceDirectory
            DisplayString,

        oraNamesConfigTraceFunc
            DisplayString,

        oraNamesConfigTraceMask
            INTEGER (-2147483648..2147483647),

        oraNamesConfigTraceUnique
            TruthValue
    }

oraNamesConfigAdminRegion OBJECT-TYPE
    SYNTAX  DisplayString
    ACCESS  read-write
    STATUS  mandatory
    DESCRIPTION
           "The name of the Administrative Region which this server serves."
    ::= { oraNamesConfigEntry  1 }

oraNamesConfigAuthorityRequired OBJECT-TYPE
    SYNTAX  TruthValue
    ACCESS  read-write
    STATUS  mandatory
    DESCRIPTION
           "Set to TRUE if this server requires an authoritative answer to
           system query requests that it generates. Requests with Authority
           Required cannot be answered by a non-authoritative server out of
           its cache."
    ::= { oraNamesConfigEntry  2 }

oraNamesConfigAutoRefreshExpire OBJECT-TYPE
    SYNTAX  TimeTicks
    ACCESS  read-write
    STATUS  mandatory
    DESCRIPTION
           "If an auto-refresh system query is issued and repeatedly fails
           after multiple retries, the server will cancel the query after
           this time period has gone by with no response."
    ::= { oraNamesConfigEntry  3 }

oraNamesConfigAutoRefreshRetry OBJECT-TYPE
    SYNTAX  TimeTicks
    ACCESS  read-write
    STATUS  mandatory
    DESCRIPTION
           "If an auto-refresh system query is issued and fails, the server
           will wait for this time period before attempting the query again."
    ::= { oraNamesConfigEntry  4 }

oraNamesConfigCacheCheckpointFile OBJECT-TYPE
    SYNTAX  DisplayString
    ACCESS  read-write
    STATUS  mandatory
    DESCRIPTION
           "Filename where the cache will be periodically be written to disk."
    ::= { oraNamesConfigEntry  5 }

oraNamesConfigCacheCheckpointInterval OBJECT-TYPE
    SYNTAX  TimeTicks
    ACCESS  read-write
    STATUS  mandatory
    DESCRIPTION
           "Amount of time between cache checkpooints."
    ::= { oraNamesConfigEntry  6 }

oraNamesConfigConfigCheckpointFile OBJECT-TYPE
    SYNTAX  DisplayString
    ACCESS  read-write
    STATUS  mandatory
    DESCRIPTION
           "Filename where the Names server configuration will be periodically
           be written to disk."
    ::= { oraNamesConfigEntry  7 }

oraNamesConfigDefaultForwarders OBJECT-TYPE
    SYNTAX  DisplayString
    ACCESS  read-write
    STATUS  mandatory
    DESCRIPTION
           "A list of TNS addresses of servers in foreign regions which should
           always be tried first when searching for other regions."
    ::= { oraNamesConfigEntry  8 }

oraNamesConfigDefaultForwardersOnly OBJECT-TYPE
    SYNTAX  TruthValue
    ACCESS  read-write
    STATUS  mandatory
    DESCRIPTION
           "Set to TRUE if this server is to operate in DEFAULT-FORWARDERS-ONLY
           mode. A server in this mode must have at least one default
           forwarder, and will always forward to its defaults forwarder
           whether or not it has server information that might be more
           accurate."
    ::= { oraNamesConfigEntry  9 }

oraNamesConfigDomainCheckpointFile OBJECT-TYPE
    SYNTAX  DisplayString
    ACCESS  read-write
    STATUS  mandatory
    DESCRIPTION
           "File where the domain data will be periodically written to disk."
    ::= { oraNamesConfigEntry  10 }

oraNamesConfigDomainHints OBJECT-TYPE
    SYNTAX  DisplayString
    ACCESS  read-write
    STATUS  mandatory
    DESCRIPTION
           "A list of foreign domains and their server's TNS addresses. This
           allows administrators to prevent a server from searching for
           servers in other domains which they know will be contacted
           frquently."
    ::= { oraNamesConfigEntry  11 }

oraNamesConfigDomains OBJECT-TYPE
    SYNTAX  DisplayString
    ACCESS  read-write
    STATUS  mandatory
    DESCRIPTION
           "A list of domains which this server is authoritative for, ie this
           server knows about all the services in these domains."
    ::= { oraNamesConfigEntry  12 }

oraNamesConfigForwardingAvailable OBJECT-TYPE
    SYNTAX  TruthValue
    ACCESS  read-write
    STATUS  mandatory
    DESCRIPTION
           "Set to TRUE if this server is willing to forward requests for data
           for which it is not authoritative."
    ::= { oraNamesConfigEntry  13 }

oraNamesConfigForwardingDesired OBJECT-TYPE
    SYNTAX  TruthValue
    ACCESS  read-write
    STATUS  mandatory
    DESCRIPTION
           "Set to TRUE if this server is desires other servers to forward
           requests which this server generates on its own. Requests which
           this server forwards have Forwarding Desired set by the original
           requestor."
    ::= { oraNamesConfigEntry  14 }

oraNamesConfigLogDirectory OBJECT-TYPE
    SYNTAX  DisplayString
    ACCESS  read-write
    STATUS  mandatory
    DESCRIPTION
           "Directory to write log file into."
    ::= { oraNamesConfigEntry  15 }

oraNamesConfigLogStatsInterval OBJECT-TYPE
    SYNTAX  TimeTicks
    ACCESS  read-write
    STATUS  mandatory
    DESCRIPTION
           "The interval in centiseconds at which server statistic counters are
           written to the log file."
    ::= { oraNamesConfigEntry  16 }

oraNamesConfigLogUnique OBJECT-TYPE
    SYNTAX  TruthValue
    ACCESS  read-write
    STATUS  mandatory
    DESCRIPTION
           "When set to 'ON' the log filename will be generated in such a way
           as to insure uniqueness in order to prevent overwriting existing
           log files."
    ::= { oraNamesConfigEntry  17 }

oraNamesConfigMaxOpenConnections OBJECT-TYPE
    SYNTAX  INTEGER (-2147483648..2147483647)
    ACCESS  read-write
    STATUS  mandatory
    DESCRIPTION
           "The number of TNS connections this server will leave open to
           clients and other servers."
    ::= { oraNamesConfigEntry  18 }

oraNamesConfigMaxReforwards OBJECT-TYPE
    SYNTAX  INTEGER (-2147483648..2147483647)
    ACCESS  read-write
    STATUS  mandatory
    DESCRIPTION
           "The server keeps a count of the number of times a given forwarded
           query returns with a referral to a closer name server. When the
           number of referrals exceeds maxReforwards, the query is cancelled
           and an error returned to the requestor."
    ::= { oraNamesConfigEntry  19 }

oraNamesConfigMessagePoolStartSize OBJECT-TYPE
    SYNTAX  INTEGER (-2147483648..2147483647)
    ACCESS  read-write
    STATUS  mandatory
    DESCRIPTION
           "The number of messages that can be kept in the message pool. Larger
           settings save time but take more space."
    ::= { oraNamesConfigEntry  20 }

oraNamesConfigNoModifyRequests OBJECT-TYPE
    SYNTAX  TruthValue
    ACCESS  read-write
    STATUS  mandatory
    DESCRIPTION
           "When set to 'ON' this server will refuse any requests to modify
           its region data."
    ::= { oraNamesConfigEntry  21 }

oraNamesConfigNoRegionDatabase OBJECT-TYPE
    SYNTAX  TruthValue
    ACCESS  read-write
    STATUS  mandatory
    DESCRIPTION
           "If set to 'TRUE' this server will not load any region data; in this
           state the server (typically one in the root region) can only
           forward requests."
    ::= { oraNamesConfigEntry  22 }

oraNamesConfigResetStatsInterval OBJECT-TYPE
    SYNTAX  TimeTicks
    ACCESS  read-write
    STATUS  mandatory
    DESCRIPTION
           "The interval in centiseconds at which all server statistic counters
           are reset back to zero."
    ::= { oraNamesConfigEntry  23 }

oraNamesConfigServerName OBJECT-TYPE
    SYNTAX  DisplayString
    ACCESS  read-write
    STATUS  mandatory
    DESCRIPTION
           "This server's name, as defined in the TNS Network definition."
    ::= { oraNamesConfigEntry  24 }

oraNamesConfigTopologyCheckpointFile OBJECT-TYPE
    SYNTAX  DisplayString
    ACCESS  read-write
    STATUS  mandatory
    DESCRIPTION
           "File where the topology data will be periodically written to disk."
    ::= { oraNamesConfigEntry  25 }

oraNamesConfigTraceDirectory OBJECT-TYPE
    SYNTAX  DisplayString
    ACCESS  read-write
    STATUS  mandatory
    DESCRIPTION
           "Directory to write trace files in when tracing is enabled."
    ::= { oraNamesConfigEntry  26 }

oraNamesConfigTraceFunc OBJECT-TYPE
    SYNTAX  DisplayString
    ACCESS  read-write
    STATUS  mandatory
    DESCRIPTION
           "A list of internal server functions which will record information
 in the trace file whenever tracing is enabled."
    ::= { oraNamesConfigEntry  27 }

oraNamesConfigTraceMask OBJECT-TYPE
    SYNTAX  INTEGER (-2147483648..2147483647)
    ACCESS  read-write
    STATUS  mandatory
    DESCRIPTION
           "A numeric mask which specifys which subsystems of the server are
           to be traced when tracing is enabled."
    ::= { oraNamesConfigEntry  28 }

oraNamesConfigTraceUnique OBJECT-TYPE
    SYNTAX  TruthValue
    ACCESS  read-write
    STATUS  mandatory
    DESCRIPTION
           "When set to 'ON' the trace filename will be generated in such a way
           as to insure uniqueness in order to prevent overwriting existing
           trace files."
    ::= { oraNamesConfigEntry  29 }

oraNamesServerTable OBJECT-TYPE
    SYNTAX  SEQUENCE OF OraNamesServerEntry
    ACCESS  not-accessible
    STATUS  mandatory
    DESCRIPTION
           "General MIB describing the Orale Name Resolution Server."
    ::= { oraNamesObjects  3 }

oraNamesServerEntry OBJECT-TYPE
    SYNTAX  OraNamesServerEntry
    ACCESS  not-accessible
    STATUS  mandatory
    DESCRIPTION
           "A set of variables which generally describe the current state
           of a Names server ."
    INDEX   { applIndex }
    ::= { oraNamesServerTable  1 }

OraNamesServerEntry ::=
    SEQUENCE {
        oraNamesServerQueriesReceived
            Counter,

        oraNamesServerLastNnamesNotFound
            DisplayString,

        oraNamesServerQueriesTotalTime
            TimeTicks,

        oraNamesServerDeletesReceived
            Counter,

        oraNamesServerDeletesRefused
            Counter,

        oraNamesServerDeletesTotalTime
            TimeTicks,

        oraNamesServerRenamesReceived
            Counter,

        oraNamesServerRenamesRefused
            Counter,

        oraNamesServerRenamesTotalTime
            TimeTicks,

        oraNamesServerUpdatesReceived
            Counter,

        oraNamesServerUpdatesRefused
            Counter,

        oraNamesServerUpdatesTotalTime
            TimeTicks,

        oraNamesServerCorruptMessagesReceived
            Counter,

        oraNamesServerResponsesSent
            Counter,

        oraNamesServerErrorResponsesSent
            Counter,

        oraNamesServerAliasLoopsDetected
            Counter,

        oraNamesServerLookupsAttempted
            Counter,

        oraNamesServerCreatedOnLookup
            Counter,

        oraNamesServerLookupFailures
            Counter,

        oraNamesServerExactMatches
            Counter,

        oraNamesServerForwardFailures
            Counter,

        oraNamesServerForwardTimeouts
            Counter,

        oraNamesServerResponsesReceived
            Counter,

        oraNamesServerErrorResponsesReceived
            Counter,

        oraNamesServerRequestsForwarded
            Counter,

        oraNamesServerLastReload
            DateAndTime,

        oraNamesServerReloadCheckFailures
            Counter,

        oraNamesServerLastCheckpoint
            DateAndTime,

        oraNamesServerName
            DisplayString,

        oraNamesServerAdminRegion
            DisplayString
    }

oraNamesServerQueriesReceived OBJECT-TYPE
    SYNTAX  Counter
    ACCESS  read-only
    STATUS  mandatory
    DESCRIPTION
           "Number of query requests received by this server."
    ::= { oraNamesServerEntry  1 }

oraNamesServerLastNnamesNotFound OBJECT-TYPE
    SYNTAX  DisplayString
    ACCESS  read-only
    STATUS  mandatory
    DESCRIPTION
           "List of the last N names queried from this region but not defined."
    ::= { oraNamesServerEntry  2 }

oraNamesServerQueriesTotalTime OBJECT-TYPE
    SYNTAX  TimeTicks
    ACCESS  read-only
    STATUS  mandatory
    DESCRIPTION
           "Total time spent processing query requests, in centiseconds."
    ::= { oraNamesServerEntry  3 }

oraNamesServerDeletesReceived OBJECT-TYPE
    SYNTAX  Counter
    ACCESS  read-only
    STATUS  mandatory
    DESCRIPTION
           "Number of delete requests received by this server."
    ::= { oraNamesServerEntry  4 }

oraNamesServerDeletesRefused OBJECT-TYPE
    SYNTAX  Counter
    ACCESS  read-only
    STATUS  mandatory
    DESCRIPTION
           "Total number of delete requests refused."
    ::= { oraNamesServerEntry  5 }

oraNamesServerDeletesTotalTime OBJECT-TYPE
    SYNTAX  TimeTicks
    ACCESS  read-only
    STATUS  mandatory
    DESCRIPTION
           "Total time spent processing delete requests, in centiseconds."
    ::= { oraNamesServerEntry  6 }

oraNamesServerRenamesReceived OBJECT-TYPE
    SYNTAX  Counter
    ACCESS  read-only
    STATUS  mandatory
    DESCRIPTION
           "Number of rename requests received by this server."
    ::= { oraNamesServerEntry  7 }

oraNamesServerRenamesRefused OBJECT-TYPE
    SYNTAX  Counter
    ACCESS  read-only
    STATUS  mandatory
    DESCRIPTION
           "Total number of rename requests refused."
    ::= { oraNamesServerEntry  8 }

oraNamesServerRenamesTotalTime OBJECT-TYPE
    SYNTAX  TimeTicks
    ACCESS  read-only
    STATUS  mandatory
    DESCRIPTION
           "Total time spent processing rename requests, in centiseconds."
    ::= { oraNamesServerEntry  9 }

oraNamesServerUpdatesReceived OBJECT-TYPE
    SYNTAX  Counter
    ACCESS  read-only
    STATUS  mandatory
    DESCRIPTION
           "Number of update requests received by this server."
    ::= { oraNamesServerEntry  10 }

oraNamesServerUpdatesRefused OBJECT-TYPE
    SYNTAX  Counter
    ACCESS  read-only
    STATUS  mandatory
    DESCRIPTION
           "Total number of update requests refused."
    ::= { oraNamesServerEntry  11 }

oraNamesServerUpdatesTotalTime OBJECT-TYPE
    SYNTAX  TimeTicks
    ACCESS  read-only
    STATUS  mandatory
    DESCRIPTION
           "Total time spent processing update requests, in centiseconds."
    ::= { oraNamesServerEntry  12 }

oraNamesServerCorruptMessagesReceived OBJECT-TYPE
    SYNTAX  Counter
    ACCESS  read-only
    STATUS  mandatory
    DESCRIPTION
           "Number of corrupted messages received by this server."
    ::= { oraNamesServerEntry  13 }

oraNamesServerResponsesSent OBJECT-TYPE
    SYNTAX  Counter
    ACCESS  read-only
    STATUS  mandatory
    DESCRIPTION
           "Number of responses of all sorts sent by this server."
    ::= { oraNamesServerEntry  14 }

oraNamesServerErrorResponsesSent OBJECT-TYPE
    SYNTAX  Counter
    ACCESS  read-only
    STATUS  mandatory
    DESCRIPTION
           "Total number of error responses sent."
    ::= { oraNamesServerEntry  15 }

oraNamesServerAliasLoopsDetected OBJECT-TYPE
    SYNTAX  Counter
    ACCESS  read-only
    STATUS  mandatory
    DESCRIPTION
           "Number of alias loops detected by this server."
    ::= { oraNamesServerEntry  16 }

oraNamesServerLookupsAttempted OBJECT-TYPE
    SYNTAX  Counter
    ACCESS  read-only
    STATUS  mandatory
    DESCRIPTION
           "Number of name lookup operations performed by this server."
    ::= { oraNamesServerEntry  17 }

oraNamesServerCreatedOnLookup OBJECT-TYPE
    SYNTAX  Counter
    ACCESS  read-only
    STATUS  mandatory
    DESCRIPTION
           "Number of names created on lookup because they were not found."
    ::= { oraNamesServerEntry  18 }

oraNamesServerLookupFailures OBJECT-TYPE
    SYNTAX  Counter
    ACCESS  read-only
    STATUS  mandatory
    DESCRIPTION
           "Number of name lookups for a name not known to this server."
    ::= { oraNamesServerEntry  19 }

oraNamesServerExactMatches OBJECT-TYPE
    SYNTAX  Counter
    ACCESS  read-only
    STATUS  mandatory
    DESCRIPTION
           "Number of name lookups which resulted in an exact match with
           information known to this server."
    ::= { oraNamesServerEntry  20 }

oraNamesServerForwardFailures OBJECT-TYPE
    SYNTAX  Counter
    ACCESS  read-only
    STATUS  mandatory
    DESCRIPTION
           "Number of forwarded requests which failed because no servers
           responded to the request."
    ::= { oraNamesServerEntry  21 }

oraNamesServerForwardTimeouts OBJECT-TYPE
    SYNTAX  Counter
    ACCESS  read-only
    STATUS  mandatory
    DESCRIPTION
           "Number of requests forwarded by this server which timed out waiting 
           for a response."
    ::= { oraNamesServerEntry  22 }

oraNamesServerResponsesReceived OBJECT-TYPE
    SYNTAX  Counter
    ACCESS  read-only
    STATUS  mandatory
    DESCRIPTION
           "Number of responses received by this server."
    ::= { oraNamesServerEntry  23 }

oraNamesServerErrorResponsesReceived OBJECT-TYPE
    SYNTAX  Counter
    ACCESS  read-only
    STATUS  mandatory
    DESCRIPTION
           "Total number error responses received."
    ::= { oraNamesServerEntry  24 }

oraNamesServerRequestsForwarded OBJECT-TYPE
    SYNTAX  Counter
    ACCESS  read-only
    STATUS  mandatory
    DESCRIPTION
           "Number of requests that this server has forwarded because it is not 
           authoritative for the requested name."
    ::= { oraNamesServerEntry  25 }

oraNamesServerLastReload OBJECT-TYPE
    SYNTAX  DateAndTime
    ACCESS  read-only
    STATUS  mandatory
    DESCRIPTION
           "Date when this server last reloaded its region data."
    ::= { oraNamesServerEntry  26 }

oraNamesServerReloadCheckFailures OBJECT-TYPE
    SYNTAX  Counter
    ACCESS  read-only
    STATUS  mandatory
    DESCRIPTION
           "Number of times this server has failed in a check to see whether the
           region data changed and needs reloading."
    ::= { oraNamesServerEntry  27 }

oraNamesServerLastCheckpoint OBJECT-TYPE
    SYNTAX  DateAndTime
    ACCESS  read-only
    STATUS  mandatory
    DESCRIPTION
           "Date when this server last cached its non-authoritative data to disk
           ."
    ::= { oraNamesServerEntry  28 }

oraNamesServerName OBJECT-TYPE
    SYNTAX  DisplayString
    ACCESS  read-only
    STATUS  mandatory
    DESCRIPTION
           "This server's name, as printed in its start-up banner."
    ::= { oraNamesServerEntry  29 }

oraNamesServerAdminRegion OBJECT-TYPE
    SYNTAX  DisplayString
    ACCESS  read-only
    STATUS  mandatory
    DESCRIPTION
           "TNS descriptor which defines this server's region; includes the
           region name and location of its network definition."
    ::= { oraNamesServerEntry  30 }

END
