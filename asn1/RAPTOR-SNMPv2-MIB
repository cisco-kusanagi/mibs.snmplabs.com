RAPTOR-SNMPv2-MIB DEFINITIONS ::= BEGIN
 
IMPORTS
    enterprises
        FROM RFC1155-SMI
    MODULE-IDENTITY, OBJECT-TYPE, NOTIFICATION-TYPE
        FROM SNMPv2-SMI;
 
--
-- Assigned by IANA
--

raptorSystems      OBJECT IDENTIFIER ::= { enterprises 1294 }
 
--
-- Raptor Systems subtrees
--

raptorModules OBJECT IDENTIFIER ::= { raptorSystems 1 }
raptorObjects OBJECT IDENTIFIER ::= { raptorSystems 2 }
raptorTraps   OBJECT IDENTIFIER ::= { raptorSystems 3 }
 
--
-- The raptorNotifyModule
--
raptorNotify MODULE-IDENTITY
    LAST-UPDATED "9810271200Z"
    ORGANIZATION "Axent Technologies, Inc. Raptor SBU"
    CONTACT-INFO
        "Ashok Nadkarni
         Axent Technologies/Raptor SBU
         266 Second Avenue
         Waltham, MA  02451
 
         Phone: 617-530-2200
         Email: ashok@raptor.com"
 
    DESCRIPTION
        "MIB for the Raptor Firewall."
 
    REVISION     "9810271200Z"
    DESCRIPTION
        "A skeletal MIB that supports the raptorNotifyTrap."
 
    ::= { raptorModules 1 }
 

--
-- Managed objects follow
--
-- Contents:
--     raptorNotifyMessage      Alert generated by Raptor Firewall
--

raptorNotifyMessage OBJECT-TYPE
    SYNTAX       OCTET STRING
    MAX-ACCESS   not-accessible
    STATUS       current
    DESCRIPTION  "An alert message generated by a Raptor Firewall."
 
    ::= { raptorObjects 1 }
 

--
-- Notifications follow
--
-- Contents:
--     raptorNotifyTrap         Trap containing a single raptorNotifyMessage
--

raptorNotifyTrap NOTIFICATION-TYPE
    OBJECTS      { raptorNotifyMessage }
    STATUS       current
    DESCRIPTION  "An alert generated by a Raptor Firewall."
 
    ::= { raptorTraps 1 }
 
END
