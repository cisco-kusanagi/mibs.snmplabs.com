XYPLEX-SYSTEM-MIB DEFINITIONS ::= BEGIN
            
                    IMPORTS
                            enterprises, Counter, Gauge, TimeTicks,
                            IpAddress
                                    FROM RFC1155-SMI
                            DisplayString
                                    FROM RFC1213-MIB
                            OBJECT-TYPE
                                    FROM RFC1212
                            TRAP-TYPE
                                    FROM RFC1215-DEFINING-TRAPS;
            
            xyplex          OBJECT IDENTIFIER ::= { enterprises 33 }
            xSystem         OBJECT IDENTIFIER ::= { xyplex 1 }
            
            -- This is a MIB module for all Xyplex systems
            
            -- Copyright 1992 Xyplex, Inc..  All Rights Reserved.
            -- Reproduction of this document is authorized on
            -- condition that this copyright notice is included.
            -- This MIB document embodies Xyplex, Inc.'s proprietary
            -- intellectual property.  Xyplex, Inc. retains all
            -- title and ownership in this MIB, including any
            -- revisions.
            --
            -- It is Xyplex, Inc.'s intent to encourage the widespread
            -- use of this MIB in connection with the management of
            -- Xyplex, Inc. products. Xyplex, Inc. grants vendors,
            -- end-users, and other interested parties a non-exclusive
            -- license to use this MIB in connection with the
            -- management of Xyplex, Inc. products.
            --
            -- This MIB document is supplied "AS IS," and Xyplex, Inc.
            -- makes no warranty, either express or implied, as to the
            -- use operation, condition, or performance of the MIB.
            
            
            -- Textual Conventions
            
            DateTime ::=
                OCTET STRING (SIZE (8))
            -- This data type is used throughout the Xyplex private MIB
            -- to model an absolute date and time.

            
            
            
            
            
            
            -- In order, the octets contain the following information:
            -- century, year within century (0..99), month (1..12),
            -- day (1..31), hour (0..23), minute (0..59),
            -- second (0..59), hundredth (0..99).  If the century
            -- value is zero, the date and time are unknown, and the
            -- other values are meaningless.
            
            AddressType ::=
                INTEGER  { unknown(1), other(2), local(3),
                           ip(4), ethernet(5) }
            -- This data type is used throughout the Xyplex private MIB
            -- to indicate the type of an address stored in a related
            -- octet string.

































            
            
            
            
            
            
            -- the System group
            
            -- Implementation of this group is mandatory for all Xyplex
            -- systems.
            
            sysIdent OBJECT-TYPE
                SYNTAX DisplayString (SIZE (0..50))
                ACCESS read-write
                STATUS mandatory
                DESCRIPTION
                    "An identification string for local and remote 
                    displays.  Corresponds directly to SERVER 
                    IDENTIFICATION and the value labeled 
                    'Identification:' on the SERVER CHARACTERISTICS 
                    display."
                ::= { xSystem 1 }
            
            sysDefineMode OBJECT-TYPE
                SYNTAX INTEGER { permOnly(1), operAndPerm(2) }
                ACCESS read-write
                STATUS mandatory
                DESCRIPTION
                    "The system's operation with regard to DEFINE 
                    commands.  'permOnly' indicates that DEFINE commands 
                    modify only the permanent data base.  'operAndPerm' 
                    indicates that DEFINE commands modify both 
                    operational and permanent data bases, unless 
                    specifically documented to the contrary.  
                    Corresponds to SERVER CHANGE and the presence of the 
                    label CHANGE in the SERVER CHARACTERISTICS 
                    display."
                ::= { xSystem 2 }
            
            sysDateTime OBJECT-TYPE
                SYNTAX DateTime
                ACCESS read-write
                STATUS mandatory
                DESCRIPTION
                    "The system's current local date and time.  
                    Corresponds directly to SERVER DATE and SERVER TIME 
                    and the value in various displays."
                ::= { xSystem 3 }
            
            sysTimeZone OBJECT-TYPE
                SYNTAX OCTET STRING (SIZE (2))
                ACCESS read-write

            
            
            
            
            
            
                STATUS mandatory
                DESCRIPTION
                    "The adjustment to apply to a universal (Greenwich) 
                    time received when down-line loaded, comprising two 
                    octets.  The first octet is the number of hours west 
                    of universal, the second is the number of minutes.  
                    Corresponds directly to SERVER TIMEZONE and the 
                    value labeled 'Timezone:' in the SERVER 
                    CHARACTERISTICS display."
                ::= { xSystem 4 }
            
            sysLoadSoftware OBJECT-TYPE
                SYNTAX DisplayString (SIZE (0..15))
                ACCESS read-write
                STATUS mandatory
                DESCRIPTION
                    "The software file name to request for down-line 
                    load of the server.  Corresponds directly to SERVER 
                    SOFTWARE, and the value labeled 'Software:' in the 
                    SERVER CHARACTERISTICS display."
                ::= { xSystem 5 }
            
            sysDump OBJECT-TYPE
                SYNTAX INTEGER { disabled(1), enabled(2) }
                ACCESS read-write
                STATUS mandatory
                DESCRIPTION
                    "Control for dumping the system's memory when the 
                    system crashes.  Corresponds directly to SERVER DUMP 
                    and the presence of 'Dump' under the label 'Enabled 
                    Characteristics' in the SERVER CHARACTERISTICS 
                    display."
                ::= { xSystem 6 }
            
            sysMaintenancePassword OBJECT-TYPE
                SYNTAX OCTET STRING (SIZE (0..8))
                ACCESS read-write
                STATUS mandatory
                DESCRIPTION
                    "The password a management system must supply to 
                    force the system to reboot or use the system's 
                    remote console via the Maintenance Operation 
                    Protocol (MOP).  Corresponds directly to SERVER 
                    MAINTENANCE PASSWORD.
            
                    When setting this value, the management system must 

            
            
            
            
            
            
                            supply eight octets, filling with zeros from the 
                    first octet.  That is, the value '1ab42' would be 
                    expressed as '0.0.0.0.0.1.ab.42'.  Setting the value 
                    to zero disables the password check.
            
                    When returning this value, the agent always returns 
                    a zero length OCTET STRING."
                ::= { xSystem 7 }
            
            sysLocalName OBJECT-TYPE
                SYNTAX DisplayString (SIZE (1..16))
                ACCESS read-write
                STATUS mandatory
                DESCRIPTION
                    "The system's local name.  Corresponds directly to 
                    SERVER NAME and the value labeled 'Name:' in the 
                    SERVER CHARACTERISTICS display."
                ::= { xSystem 8 }
            
            sysSoftwareVersionType OBJECT-TYPE
                SYNTAX INTEGER { alpha(1), beta(2),
                                 production(3), special(4) }
                ACCESS read-only
                STATUS mandatory
                DESCRIPTION
                    "The software version variant running in the system.  
                    Corresponds to the letter in the software version in 
                    the SERVER CHARACTERISTICS display.
            
                    alpha         'A':   alpha test
                    beta          'B':   beta test
                    production    null:  normal, production software
                    special       'S':   special, custom software
                    "
                ::= { xSystem 9 }
            
            sysSoftwareVersion OBJECT-TYPE
                SYNTAX OCTET STRING (SIZE (4))
                ACCESS read-only
                STATUS mandatory
                DESCRIPTION
                    "The software version running in the system.  In 
                    order, the octets contain major version, minor 
                    version, ECO, and pre-release number.  Corresponds 
                    to the numbers in the software version in the SERVER 
                    CHARACTERISTICS display.

            
            
            
            
            
            
            
                    For example, the version display for 
                    sysSoftwareVersionType 'production' and 
                    sysSoftwareVersion '2.2.0.0' is 'V2.2'.
            
                    The version display for sysSoftwareVersionType 
                    'beta' and sysSoftwareVersion '3.1.0.4' is 
                    'V3.1B4'."
                ::= { xSystem 10 }
            
            sysRomVersion OBJECT-TYPE
                SYNTAX INTEGER
                ACCESS read-only
                STATUS mandatory
                DESCRIPTION
                    "The firmware version of the bootstrap ROM installed 
                    in the system.  Corresponds directly to the value 
                    labeled 'Rom' in the SERVER CHARACTERISTICS 
                    display."
                ::= { xSystem 11 }
            
            sysHardwareType OBJECT-TYPE
                SYNTAX INTEGER
                ACCESS read-only
                STATUS mandatory
                DESCRIPTION
                    "The type of hardware on which the system is 
                    running, with values as defined in Xyplex Assigned 
                    Numbers, Xyplex document number 420-0497.  
                    Corresponds directly to the value labeled 'Hardware 
                    Type:' in the UNIT display."
                ::= { xSystem 12 }
            
            sysHardwareVersion OBJECT-TYPE
                SYNTAX INTEGER
                ACCESS read-only
                STATUS mandatory
                DESCRIPTION
                    "This version of hardware on which the system is 
                    running.  Corresponds directly to part of the value 
                    labeled 'HW' in the SERVER CHARACTERISTICS 
                    display."
                ::= { xSystem 13 }
            
            sysChassisType OBJECT-TYPE
                SYNTAX INTEGER { other(1), mx45xx(2), net9000(3) }

            
            
            
            
            
            
                ACCESS read-only
                STATUS mandatory
                DESCRIPTION
                    "The type of chassis in which the system is running.  
                    Corresponds directly to part of the value labeled 
                    'HW' in the SERVER CHARACTERISTICS display."
                ::= { xSystem 14 }
            
            sysChassisVersion OBJECT-TYPE
                SYNTAX INTEGER
                ACCESS read-only
                STATUS mandatory
                DESCRIPTION
                    "This version of chassis in which the system is 
                    running.  Corresponds directly to part of the value 
                    labeled 'HW' in the SERVER CHARACTERISTICS 
                    display."
                ::= { xSystem 15 }
            
            sysCrash OBJECT-TYPE
                SYNTAX INTEGER { ready(1), execute(2) }
                ACCESS read-write
                STATUS mandatory
                DESCRIPTION
                    "Control to cause this system to crash.  In response 
                    to a get-request or get-next-request, the agent 
                    always returns 'ready' for this value.  Setting the 
                    value to 'ready' has no effect.  Setting it to 
                    'execute' causes an immediate crash.  Corresponds to 
                    the CRASH command."
            ::= { xSystem 16 }
            
            sysInitialize OBJECT-TYPE
                SYNTAX INTEGER { ready(1), conditionalExecute(2),
                                 unconditionalExecute(3), cancel(4) }
                ACCESS read-write
                STATUS mandatory
                DESCRIPTION
                    "Control to cause this system to reset its software 
                    to initial load values, typically by reloading.  
                    When executing an initialize command, the system 
                    observes the value of sysInitializeDelay as supplied 
                    anywhere in the same set request with sysInitialize.  
                    If this value is not included in the set request, 
                    the system uses its default value.
            

            
            
            
            
            
            
                    In response to a get-request or get-next-request, 
                    the agent always returns 'ready' for this value.  
                    Setting the value to 'ready' has no effect.  Setting 
                    it to 'conditionalExecute' causes initialization if 
                    the overall system state is acceptible (such as not 
                    needing to store permanent parameters).  Setting it 
                    to 'unconditionalExecute' causes initialization 
                    regardless of the overall system state.  Setting it 
                    to 'cancel' aborts an initialization that has not 
                    yet started.  According to standard SNMP operation, 
                    if the system is not in a proper state to accept a 
                    given set request for this value, it returns the 
                    standard SNMP error 'badValue'.
            
                    Corresponds to the INITIALIZE command."
                ::= { xSystem 17 }
            
            sysInitializeDelay OBJECT-TYPE
                SYNTAX INTEGER (0..32768)
                ACCESS read-write
                STATUS mandatory
                DESCRIPTION
                    "The number of minutes to delay before beginning the 
                    system initialization process as executed with 
                    sysInitialize.
            
                    This value cannot be set outside a set-request that 
                    contains the value 'execute' for sysInitialize.  If 
                    not included in such a set, the default value is 1.
            
                    Corresponds to the INITIALIZE command's DELAY 
                    parameter and to the value labeled 'Minutes to 
                    shutdown:' in the SYSTEM STATUS display."
                ::= { xSystem 18 }
            
            sysZeroAll OBJECT-TYPE
                SYNTAX INTEGER { ready(1), execute(2) }
                ACCESS read-write
                STATUS mandatory
                DESCRIPTION
                    "Control to zero all counters.  In response to a 
                    get-request or get-next-request, the agent always 
                    returns 'ready' for this value.  Setting the value 
                    to 'ready' has no effect.  Setting it to 'execute' 
                    causes all the system's counters to be zeroed.  
                    Corresponds to the ZERO ALL command."

            
            
            
            
            
            
                ::= { xSystem 19 }
            
            sysZeroBase OBJECT-TYPE
                SYNTAX INTEGER { ready(1), execute(2) }
                ACCESS read-write
                STATUS mandatory
                DESCRIPTION
                    "Control to zero all base counters.  In response to 
                    a get-request or get-next-request, the agent always 
                    returns 'ready' for this value.  Setting the value 
                    to 'ready' has no effect.  Setting it to 'execute' 
                    causes all the system's base counters to be zeroed.  
                    Examples of counters that are zeroed are the SNMP 
                    counters or the counters from the SYSTEM COUNTERS 
                    display.  Examples of counters that are not zeroed 
                    are Ethernet interface counters or port counters.  
                    Corresponds to the ZERO SYSTEM command."
                ::= { xSystem 20 }
            
            sysZeroBaseTime OBJECT-TYPE
                SYNTAX TimeTicks
                ACCESS read-only
                STATUS mandatory
                DESCRIPTION
                    "The number hundredths of a second since the most 
                    recent zeroing of the base counters, such as through 
                    execution of sysZeroAll or sysZeroBase.  Corresponds 
                    directly to the value labeled 'Seconds Since 
                    Zeroed:' in the SERVER COUNTERS display."
                ::= { xSystem 21 }
            
            sysLoaderName OBJECT-TYPE
                SYNTAX DisplayString (SIZE (0..40))
                ACCESS read-only
                STATUS mandatory
                DESCRIPTION
                    "The name of the system that provided this system's 
                    running software.  Corresponds directly to the value 
                    labeled 'Primary Host:' in the SERVER STATUS 
                    display."
                ::= { xSystem 22 }
            
            sysLoaderAddressType OBJECT-TYPE
                SYNTAX AddressType
                ACCESS read-only
                STATUS mandatory

            
            
            
            
            
            
                DESCRIPTION
                    "The type of network address contained in 
                    sysLoaderAddress.  'unknown' means no address has 
                    been defined.  'other' means no other type value 
                    applies.  'local' means there is no address and this 
                    system's software was loaded from local storage.  
                    'ip' is an Internet IP address.  'ethernet' is an 
                    802.3 MAC address.  Corresponds indirectly to the 
                    value labeled 'Load Address:' in the SERVER STATUS 
                    display."
                ::= { xSystem 23 }
            
            sysLoaderAddress OBJECT-TYPE
                SYNTAX OCTET STRING
                ACCESS read-only
                STATUS mandatory
                DESCRIPTION
                    "The network address of the system that provided 
                    this system's running software.  Corresponds 
                    directly to the value labeled 'Load Address:' in the 
                    SERVER STATUS display."
                ::= { xSystem 24 }
            
            sysDumperAddressType OBJECT-TYPE
                SYNTAX AddressType
                ACCESS read-only
                STATUS mandatory
                DESCRIPTION
                    "The type of network address contained in 
                    sysDumperAddress.  'unknown' means no address has 
                    been defined.  'other' means no other type value 
                    applies.  'local' means there is no address and this 
                    system's was dumped to local storage.  'ip' is an 
                    Internet IP address.  'ethernet' is an 802.3 MAC 
                    address.  Corresponds indirectly to the value 
                    labeled 'Dump Address:' in the SERVER STATUS 
                    display."
                ::= { xSystem 25 }
            
            sysDumperAddress OBJECT-TYPE
                SYNTAX OCTET STRING
                ACCESS read-only
                STATUS mandatory
                DESCRIPTION
                    "The network address of the system that most 
                    recently accepted a crash dump from this system.  

            
            
            
            
            
            
                            Corresponds directly to the value labeled 'Dump 
                    Address:' in the SERVER STATUS display."
                ::= { xSystem 26 }
            
            sysResourceLacks OBJECT-TYPE
                SYNTAX Counter
                ACCESS read-only
                STATUS mandatory
                DESCRIPTION
                    "The number of times a local resource allocation 
                    failed, for example due to lack of dynamic memory.  
                    Corresponds directly to the value labeled 'Resource 
                    Errors:' in the SERVER STATUS display."
                ::= { xSystem 27 }
            
            sysChassisState OBJECT-TYPE
                SYNTAX INTEGER { notApplicable(1), noFault(2), fault(3),
                                 loop(4) }
                ACCESS read-only
                STATUS mandatory
                DESCRIPTION
                    "For chassis-based systems, the state of the overall 
                    chassis.  'notApplicable' indicates the system is 
                    not chassis based.  'noFault' indicates no current 
                    chassis problem.  'fault' indicates a current 
                    chassis problem such as a card or power supply 
                    failure.  Corresponds directly to the value labeled 
                    'Crate Current State: in the SERVER ALTERNATE STATUS 
                    display."
                ::= { xSystem 28 }
            
            sysChassisFaultTransitions OBJECT-TYPE
                SYNTAX Counter
                ACCESS read-only
                STATUS mandatory
                DESCRIPTION
                    "The number of times this system has seen 
                    sysChassisState switch from 'noFault' to 'fault' or 
                    from 'fault' to 'noFault'.  Corresponds directly to 
                    the value labeled 'Crate Transition Count: in the 
                    SERVER ALTERNATE STATUS display."
                ::= { xSystem 29 }
            
            sysResourceNumber OBJECT-TYPE
                SYNTAX INTEGER
                ACCESS read-only

            
            
            
            
            
            
                STATUS mandatory
                DESCRIPTION
                    "The number of resource entries in the Resource 
                    table."
                ::= { xSystem 30 }
            
            sysFeatureNumber OBJECT-TYPE
                SYNTAX INTEGER
                ACCESS read-only
                STATUS mandatory
                DESCRIPTION
                    "The number of feature entries in the Feature 
                    table."
                ::= { xSystem 31 }
            
            -- more base objects following tables






























            
            
            
            
            
            
            -- the Resource table
            
            resTable OBJECT-TYPE
                SYNTAX SEQUENCE OF ResEntry
                ACCESS not-accessible
                STATUS mandatory
                DESCRIPTION
                    "A list of resource entries.  The number of entries 
                    is given by the value of sysResourceNumber."
                ::= { xSystem 32 }
            
            resEntry OBJECT-TYPE
                SYNTAX ResEntry
                ACCESS not-accessible
                STATUS mandatory
                DESCRIPTION
                    "Status values for a system resource."
                INDEX { resType }
                ::= { resTable 1 }
            
            ResEntry ::=
                SEQUENCE {
                    resType
                        INTEGER,
                    resCurrent
                        Gauge,
                    resWorst
                        Gauge,
                    resAdminMaximum
                        INTEGER,
                    resLacks
                        INTEGER,
                    resLackTime
                        DateTime,
                    resOperMaximum
                        INTEGER
                }
            
            resType OBJECT-TYPE
                SYNTAX INTEGER { cpuPercent(1), memoryPercent(2),
                                 process(3), timer(4), packetBuffer(5),
                                 ipcMessage(6), textPool(7),
                                 freeMemory(8), globalMemoryPercent(9),
                                 phivDecnetRouteCache(10),
                                 ipFilterCache(11), ipRouteCache(12),
                                 ipxRouteCache(13), ipPolicyTable(14),

            
            
            
            
            
            
                                 ipFilterTable(15),
                                 phivDecnetPolicyTable(16),
                                 phivDecnetFilterTable(17),
                                 appleRouteCache(18),
                                 appleFilterTable(19),
                                 repeaterPortAccessTable(20),
                                 repeaterPortNameTable(21),
                                 ipxRipTable(22), ipxSapTable(23) }
                ACCESS read-only
                STATUS mandatory
                DESCRIPTION
                    "Identification of a resource type.  Typically 
                    corresponds directly to a label such as 'Processes:' 
                    in the SERVER ALTERNATE STATUS display."
                ::= { resEntry 1 }
            
            resCurrent OBJECT-TYPE
                SYNTAX Gauge
                ACCESS read-only
                STATUS mandatory
                DESCRIPTION
                    "The number of resources currently in use on the 
                    system.  Typically corresponds directly to a value 
                    labeled 'Cur' in the SERVER ALTERNATE STATUS 
                    display."
                ::= { resEntry 2 }
            
            resWorst OBJECT-TYPE
                SYNTAX Gauge
                ACCESS read-only
                STATUS mandatory
                DESCRIPTION
                    "The highest or lowest value of resCurrent since 
                    system initialization.  Typically corresponds 
                    directly to a value labeled 'High' or 'Low' in the 
                    SERVER ALTERNATE STATUS display."
                ::= { resEntry 3 }
            
            resAdminMaximum OBJECT-TYPE
                SYNTAX INTEGER
                ACCESS read-write
                STATUS mandatory
                DESCRIPTION
                    "The desired maximum possible number of resources in 
                    the system.  In many cases, ACCESS to this object 
                    for a particular resType is read-only.  Typically 

            
            
            
            
            
            
                            corresponds directly to a value labeled 'Max' in the 
                    SERVER ALTERNATE STATUS display for desired, 
                    administrative values.  When the desired change 
                    takes effect is implementation specific, ranging 
                    from immediately to the next system 
                    initialization."
                ::= { resEntry 4 }
            
            resLacks OBJECT-TYPE
                SYNTAX Counter
                ACCESS read-only
                STATUS mandatory
                DESCRIPTION
                    "The number of times since system initialization 
                    that the system could not obtain the resource 
                    because none were available.  Typically corresponds 
                    directly to a value labeled 'Failure' in the SERVER 
                    ALTERNATE STATUS display.
            
                    If such failures do not apply to the particular 
                    resource, such as 'cpuPercent', the agent returns 
                    zero for this object."
                ::= { resEntry 5 }
            
            resLackTime OBJECT-TYPE
                SYNTAX DateTime
                ACCESS read-only
                STATUS mandatory
                DESCRIPTION
                    "The local system date and time when resLack last 
                    increased.  Typically corresponds directly to a 
                    value labeled 'Last Occurred' in the SERVER 
                    ALTERNATE STATUS display.
                        
                    If such failures do not apply to the particular 
                    resource, such as 'cpuPercent', the agent returns 
                    all zeroes (unknown) for this object."
            ::= { resEntry 6 }
            
            resOperMaximum OBJECT-TYPE
                SYNTAX INTEGER
                ACCESS read-only
                STATUS mandatory
                DESCRIPTION
                    "The current maximum possible number of resources in 
                    the system.  Typically corresponds directly to a 

            
            
            
            
            
            
                            value labeled 'Max' in the SERVER ALTERNATE STATUS 
                    display for current operational values.  This value 
                    is based on current or previous value of 
                    resAdminMaximum."
                ::= { resEntry 7 }









































            
            
            
            
            
            
            -- the Feature table
            
            featTable OBJECT-TYPE
                SYNTAX SEQUENCE OF FeatEntry
                ACCESS not-accessible
                STATUS mandatory
                DESCRIPTION
                    "A list of feature entries.  The number of entries 
                    is given by the value of sysFeatureNumber."
                ::= { xSystem 33 }
            
            featEntry OBJECT-TYPE
                SYNTAX FeatEntry
                ACCESS not-accessible
                STATUS mandatory
                DESCRIPTION
                    "Status values for a system feature."
                INDEX { featType }
                ::= { featTable 1 }
            
            FeatEntry ::=
                SEQUENCE {
                    featType
                        INTEGER,
                    featStatus
                        INTEGER
                }
            
            featType OBJECT-TYPE
                SYNTAX INTEGER { help(1), snmp(2), xremote(3),
                                 tn3270(4), menu(5), multisessions(6),
                                 lat(7), eventLog(8),
                                 internetSecurity(9), slip(10),
                                 scriptServer(11), kerberos(12),
                                 telnet(13), rlogin(14), allPorts(15),
                                 xprinter(16) }
                ACCESS read-only
                STATUS mandatory
                DESCRIPTION
                    "Identification of a feature type.  Corresponds to a 
                    SERVER feature keyword."
                ::= { featEntry 1 }
            
            featStatus OBJECT-TYPE
                SYNTAX INTEGER { disabled(1), enabled(2) }
                ACCESS read-write

            
            
            
            
            
            
                STATUS mandatory
                DESCRIPTION
                    "The status of the feature as of the next system 
                    initialization.  Corresponds to the presence of the 
                    feature's lable following the label 'Enabled 
                    Feature(s): in the UNIT display."
                ::= { featEntry 2 }
            






































            
            
            
            
            
            
            -- the Boot Control group
            
            -- The Boot Control group contains parameters to control
            -- how a system loads and dumps its runtime software and
            -- parameters.  Typically these parameters are kept for
            -- and used by system initialization firmware.
            
            -- This group is mandatory for systems that offer runtime
            -- control of these parameters, and omitted in systems
            -- that do not.
            
            bootControl OBJECT IDENTIFIER ::= { xSystem 34 }
            
            bootControlLoadInternetFile OBJECT-TYPE
                SYNTAX DisplayString (SIZE (0..64))
                ACCESS read-write
                STATUS mandatory
                DESCRIPTION
                    "The filename to request when loading an image via 
                    TFTP.  Corresponds directly to SERVER INTERNET LOAD 
                    FILE and the value labeled 'Internet Load File:' in 
                    the SERVER BOOT CHARACTERISTICS display."
                ::= { bootControl 1 }
            
            bootControlLoadInternetServer OBJECT-TYPE
                SYNTAX IpAddress
                ACCESS read-write
                STATUS mandatory
                DESCRIPTION
                    "The internet address of the server to use when 
                    loading an image via TFTP.  Corresponds directly to 
                    SERVER INTERNET LOAD HOST and the value labeled 
                    'Internet Load Host:' in the SERVER BOOT 
                    CHARACTERISTICS display."
                ::= { bootControl 2 }
            
            bootControlLoadInternetGateway OBJECT-TYPE
                SYNTAX IpAddress
                ACCESS read-write
                STATUS mandatory
                DESCRIPTION
                    "The internet address of the gateway to use when 
                    loading an image via TFTP.  Corresponds directly to 
                    SERVER INTERNET LOAD GATEWAY and the value labeled 
                    'Internet Load Gateway:' in the SERVER BOOT 
                    CHARACTERISTICS display."

            
            
            
            
            
            
                ::= { bootControl 3 }
            
            bootControlLoadBootpTftp OBJECT-TYPE
                SYNTAX INTEGER { disabled(1), enabled(2) }
                ACCESS read-write
                STATUS mandatory
                DESCRIPTION
                    "Control for loading via the combination of BOOTP 
                    and TFTP.  Corresponds to SERVER LOAD PROTOCOL 
                    BOOTPTFTP and the presence of 'BOOTP/TFTP/' 
                    following the label 'Load Protocols Enabled:' in the 
                    SERVER BOOT CHARACTERISTICS display."
                ::= { bootControl 4 }
            
            bootControlLoadTftpDirect OBJECT-TYPE
                SYNTAX INTEGER { disabled(1), enabled(2) }
                ACCESS read-write
                STATUS mandatory
                DESCRIPTION
                    "Control for loading via directed TFTP.  Corresponds 
                    to SERVER LOAD PROTOCOL TFTPDIRECT and the presence 
                    of 'TFTPDIRECT' following the label 'Load Protocols 
                    Enabled:' in the SERVER BOOT CHARACTERISTICS 
                    display."
                ::= { bootControl 5 }
            
            bootControlLoadLocal OBJECT-TYPE
                SYNTAX INTEGER { disabled(1), enabled(2) }
                ACCESS read-write
                STATUS mandatory
                DESCRIPTION
                    "Control for loading from a local medium.  
                    Corresponds to SERVER LOAD PROTOCOL LOCAL and the 
                    presence of 'LOCAL' following the label 'Load 
                    Protocols Enabled:' in the SERVER BOOT 
                    CHARACTERISTICS display."
                ::= { bootControl 6 }
            
            bootControlLoadMop OBJECT-TYPE
                SYNTAX INTEGER { disabled(1), enabled(2) }
                ACCESS read-write
                STATUS mandatory
                DESCRIPTION
                    "Control for loading via DEC MOP.  Corresponds to 
                    SERVER LOAD PROTOCOL MOP and the presence of 'MOP' 
                    following the label 'Load Protocols Enabled:' in the 

            
            
            
            
            
            
                            SERVER BOOT CHARACTERISTICS display."
                ::= { bootControl 7 }
            
            bootControlLoadProprietary OBJECT-TYPE
                SYNTAX INTEGER { disabled(1), enabled(2) }
                ACCESS read-write
                STATUS mandatory
                DESCRIPTION
                    "Control for loading via Xyplex-proprietary extended 
                    MOP.  Corresponds to SERVER LOAD PROTOCOL 
                    PROPRIETARY and the presence of 'Proprietary' 
                    following the label 'Load Protocols Enabled:' in the 
                    SERVER BOOT CHARACTERISTICS display."
                ::= { bootControl 8 }
            
            bootControlLoadRarpTftp OBJECT-TYPE
                SYNTAX INTEGER { disabled(1), enabled(2) }
                ACCESS read-write
                STATUS mandatory
                DESCRIPTION
                    "Control for loading via the combination of RARP and 
                    TFTP.  Corresponds to SERVER LOAD PROTOCOL RARPTFTP 
                    and the presence of 'RARP/TFTP' following the label 
                    'Load Protocols Enabled:' in the SERVER BOOT 
                    CHARACTERISTICS display."
                ::= { bootControl 9 }
            
            bootControlDumpBootpTftp OBJECT-TYPE
                SYNTAX INTEGER { disabled(1), enabled(2) }
                ACCESS read-write
                STATUS mandatory
                DESCRIPTION
                    "Control for dumping via the combination of BOOTP 
                    and TFTP.  Corresponds to SERVER DUMP PROTOCOL 
                    BOOTPTFTP and the presence of 'BOOTP/TFTP' following 
                    the label 'Dump Protocols Enabled:' in the SERVER 
                    BOOT CHARACTERISTICS display."
                ::= { bootControl 10 }
            
            bootControlDumpLocal OBJECT-TYPE
                SYNTAX INTEGER { disabled(1), enabled(2) }
                ACCESS read-write
                STATUS mandatory
                DESCRIPTION
                    "Control for dumping to a local medium.  Corresponds 
                    to SERVER DUMP PROTOCOL LOCAL and the presence of 

            
            
            
            
            
            
                            'Local' following the label 'Dump Protocols 
                    Enabled:' in the SERVER BOOT CHARACTERISTICS 
                    display."
                ::= { bootControl 11 }
            
            bootControlDumpMop OBJECT-TYPE
                SYNTAX INTEGER { disabled(1), enabled(2) }
                ACCESS read-write
                STATUS mandatory
                DESCRIPTION
                    "Control for dumping via DEC MOP.  Corresponds to 
                    SERVER DUMP PROTOCOL MOP and the presence of 'MOP' 
                    following the label 'Dump Protocols Enabled:' in the 
                    SERVER BOOT CHARACTERISTICS display."
                ::= { bootControl 12 }
            
            bootControlDumpProprietary OBJECT-TYPE
                SYNTAX INTEGER { disabled(1), enabled(2) }
                ACCESS read-write
                STATUS mandatory
                DESCRIPTION
                    "Control for dumping via Xyplex-proprietary extended 
                    MOP.  Corresponds to SERVER DUMP PROTOCOL 
                    PROPRIETARY and the presence of 'Proprietary' 
                    following the label 'Dump Protocols Enabled:' in the 
                    SERVER BOOT CHARACTERISTICS display."
                ::= { bootControl 13 }
            
            bootControlDumpRarpTftp OBJECT-TYPE
                SYNTAX INTEGER { disabled(1), enabled(2) }
                ACCESS read-write
                STATUS mandatory
                DESCRIPTION
                    "Control for dumping via the combination of RARP and 
                    TFTP.  Corresponds to SERVER DUMP PROTOCOL RARPTFTP 
                    and the presence of 'RARP/TFTP' following the label 
                    'Dump Protocols Enabled:' in the SERVER BOOT 
                    CHARACTERISTICS display."
                ::= { bootControl 14 }
            
            bootControlParamBootpTftp OBJECT-TYPE
                SYNTAX INTEGER { disabled(1), enabled(2) }
                ACCESS read-write
                STATUS mandatory
                DESCRIPTION
                    "Control for loading parameters via the combination 

            
            
            
            
            
            
                            of BOOTP and TFTP.  Corresponds to SERVER PARAMETER 
                    PROTOCOL MOP and the presence of 'BOOTP/TFTP' 
                    following the label 'Parameter Protocols Enabled:' 
                    in the SERVER BOOT CHARACTERISTICS display."
                ::= { bootControl 15 }
            
            bootControlParamLocal OBJECT-TYPE
                SYNTAX INTEGER { disabled(1), enabled(2) }
                ACCESS read-write
                STATUS mandatory
                DESCRIPTION
                    "Control for loading parameters from a local medium.  
                    Corresponds to SERVER PARAMETER PROTOCOL LOCAL and 
                    the presence of 'LOCAL' following the label 
                    'Parameter Protocols Enabled:' in the SERVER BOOT 
                    CHARACTERISTICS display."
                ::= { bootControl 16 }
            
            bootControlParamMop OBJECT-TYPE
                SYNTAX INTEGER { disabled(1), enabled(2) }
                ACCESS read-write
                STATUS mandatory
                DESCRIPTION
                    "Control for loading parameters via DEC MOP.  
                    Corresponds to SERVER PARAMETER PROTOCOL MOP and the 
                    presence of 'MOP' following the label 'Parameter 
                    Protocols Enabled:' in the SERVER BOOT 
                    CHARACTERISTICS display."
                ::= { bootControl 17 }
            
            bootControlParamProprietary OBJECT-TYPE
                SYNTAX INTEGER { disabled(1), enabled(2) }
                ACCESS read-write
                STATUS mandatory
                DESCRIPTION
                    "Control for loading parameters via 
                    Xyplex-proprietary extended MOP.  Corresponds to 
                    SERVER PARAMETER PROTOCOL PROPRIETARY and the 
                    presence of 'Proprietary' following the label 
                    'Parameter Protocols Enabled:' in the SERVER BOOT 
                    CHARACTERISTICS display."
                ::= { bootControl 18 }
            
            bootControlParamRarpTftp OBJECT-TYPE
                SYNTAX INTEGER { disabled(1), enabled(2) }
                ACCESS read-write

            
            
            
            
            
            
                STATUS mandatory
                DESCRIPTION
                    "Control for loading parameters via the combination 
                    of RARP and TFTP.  Corresponds to SERVER PARAMETER 
                    PROTOCOL RARPTFTP and the presence of 'RARP/TFTP' 
                    following the label 'Parameter Protocols Enabled:' 
                    in the SERVER BOOT CHARACTERISTICS display."
                ::= { bootControl 19 }
            





































            
            
            
            
            
            
            -- the System group, basic parameters continued
            
            sysInstalledMemory OBJECT-TYPE
                SYNTAX Gauge
                ACCESS read-only
                STATUS mandatory
                DESCRIPTION
                    "The total number of bytes of main memory installed 
                    in the system.  Corresponds directly to the value 
                    labeled 'Installed' on the SERVER ALTERNATE STATUS 
                    display.  A value of 0 indicates standard memory for 
                    the particular hardware."
                ::= { xSystem 35 }

































            
            
            
            
            
            
            -- System traps
            
            resourceLack TRAP-TYPE
                ENTERPRISE xSystem
                VARIABLES {
                    resType
                    }
                DESCRIPTION
                    "Indication that the system incremented the 
                    corresponding value of resLacks."
                ::= 1
            
END
