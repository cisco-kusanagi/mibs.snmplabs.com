WS-INFRA-CLUSTER-MIB DEFINITIONS ::= BEGIN
 
		IMPORTS
			OBJECT-GROUP, MODULE-COMPLIANCE			
				FROM SNMPv2-CONF			
			IpAddress, Integer32, Unsigned32, OBJECT-TYPE, MODULE-IDENTITY			
				FROM SNMPv2-SMI			
			DateAndTime, DisplayString, RowStatus, TruthValue			
				FROM SNMPv2-TC			
			wsInfraCluster			
				FROM WS-INFRA-SMI-MIB			
			DoActionNow			
				FROM WS-TYPE-MIB;

		-- 1.3.6.1.4.1.388.14.1.8.1
		wsInfraClusterMIB MODULE-IDENTITY 
			LAST-UPDATED "200808080946Z"		-- August 08, 2008 at 09:46 GMT
			ORGANIZATION 
				"Symbol Technologies"
			CONTACT-INFO 
				"Symbol Technologies, Inc.
				Customer Service
				Postal:
				One Symbol Plaza
				Holtsville, NY 11742-1300
				USA
				Tel: +1. 631.738.6213
				E-mail: support@symbol.com
				Web: http://www.symbol.com/support"
			DESCRIPTION 
				"The Cluster module is responsible for providing a minimal 
				interrupted service to the network in the case of a switch 
				failure by making the other standby switch take over the 
				un-adopted Access ports. 
				
				The core functionalities of the Cluster module are as listed 
				below:
				
				- Manage and process automatic port adoption by 
				   switch(es) in the event of network or any switch failure.
				- Manage the cluster license.
				- Act as a tunnel between the application modules of CC 
				   across the switches.
				
				All Cluster related configuration parameters (except of course 
				wsInfraClusterEnable itself) can be modified only if Cluster 
				Protocol is disabled."
			REVISION "200808080946Z"		-- August 08, 2008 at 09:46 GMT
			DESCRIPTION 
				"01a15
				Added scalar wsInfraClusterLicensingAlgorithm."
			REVISION "200806171713Z"		-- June 17, 2008 at 17:13 GMT
			DESCRIPTION 
				"01a14
				Added dynamic AP load balancing objects."
			REVISION "200804291013Z"		-- April 29, 2008 at 10:13 GMT
			DESCRIPTION 
				"01a13
				
				Added notes in the description of the following objects:
				- wsInfraCriticalResourceIp
				- wsInfraClusterMode
				- wsInfraClusterId
				- wsInfraClusterDiscoveryInterval
				- wsInfraClusterHoldInterval
				- wsInfraClusterHBInterval
				- wsInfraClusterAutoRevert
				- wsInfraClusterAutoRevertDelay
				- wsInfraClusterDhcpRedundancy"
			REVISION "200706261326Z"		-- June 26, 2007 at 13:26 GMT
			DESCRIPTION 
				"01a12"
			REVISION "200706261215Z"		-- June 26, 2007 at 12:15 GMT
			DESCRIPTION 
				"01a11"
			REVISION "200605241358Z"		-- May 24, 2006 at 13:58 GMT
			DESCRIPTION 
				"01a10"
			REVISION "200512271405Z"		-- December 27, 2005 at 14:05 GMT
			DESCRIPTION 
				"01a09"
			REVISION "200512161229Z"		-- December 16, 2005 at 12:29 GMT
			DESCRIPTION 
				"01a08"
			REVISION "200509122039Z"		-- September 12, 2005 at 20:39 GMT
			DESCRIPTION 
				"01a07"
			REVISION "200508171325Z"		-- August 17, 2005 at 13:25 GMT
			DESCRIPTION 
				"01a06"
			REVISION "200508151627Z"		-- August 15, 2005 at 16:27 GMT
			DESCRIPTION 
				"01a05"
			REVISION "200508151420Z"		-- August 15, 2005 at 14:20 GMT
			DESCRIPTION 
				"01a04"
			REVISION "200508111853Z"		-- August 11, 2005 at 18:53 GMT
			DESCRIPTION 
				"01a03"
			REVISION "200507071836Z"		-- July 07, 2005 at 18:36 GMT
			DESCRIPTION 
				"01a02"
			REVISION "200507071639Z"		-- July 07, 2005 at 16:39 GMT
			DESCRIPTION 
				"01a01"
			::= { wsInfraCluster 1 }

		-- 1.3.6.1.4.1.388.14.1.8.1.1
		wsInfraClusterSwitchIP OBJECT-TYPE
			SYNTAX IpAddress
			MAX-ACCESS read-write
			STATUS current
			DESCRIPTION
				"The IP Address of the switch in the cluster context."
			::= { wsInfraClusterMIB 1 }

		-- 1.3.6.1.4.1.388.14.1.8.1.2
		wsInfraClusterEnable OBJECT-TYPE
			SYNTAX INTEGER
				{
				enable(1),
				disable(2)
				}
			MAX-ACCESS read-write
			STATUS current
			DESCRIPTION
				"Enable or disable the Cluster feature."
			::= { wsInfraClusterMIB 2 }

		-- 1.3.6.1.4.1.388.14.1.8.1.3
		wsInfraClusterMode OBJECT-TYPE
			SYNTAX INTEGER
				{
				active(1),
				standby(2)
				}
			MAX-ACCESS read-write
			STATUS current
			DESCRIPTION
				"Set the mode to either Active or Standby.
				
				This object can not be set when Cluster feature is enabled.
				Disable the Cluster feature using wsInfraClusterEnable
				before setting this object."
			::= { wsInfraClusterMIB 3 }

		-- 1.3.6.1.4.1.388.14.1.8.1.4
		wsInfraClusterId OBJECT-TYPE
			SYNTAX Unsigned32 (1..65535)
			MAX-ACCESS read-write
			STATUS current
			DESCRIPTION
				"Cluster/Group id.
				
				This object can not be set when Cluster feature is enabled.
				Disable the Cluster feature using wsInfraClusterEnable
				before setting this object."
			::= { wsInfraClusterMIB 4 }

		-- 1.3.6.1.4.1.388.14.1.8.1.5
		wsInfraClusterDiscoveryInterval OBJECT-TYPE
			SYNTAX Unsigned32 (10..60)
			UNITS "seconds"
			MAX-ACCESS read-write
			STATUS current
			DESCRIPTION
				"During this time switches try to discover other switches 
				in the cluster.
				
				This object can not be set when Cluster feature is enabled.
				Disable the Cluster feature using wsInfraClusterEnable
				before setting this object."
			::= { wsInfraClusterMIB 5 }

		-- 1.3.6.1.4.1.388.14.1.8.1.6
		wsInfraClusterHoldInterval OBJECT-TYPE
			SYNTAX Unsigned32 (1..255)
			UNITS "seconds"
			MAX-ACCESS read-write
			STATUS current
			DESCRIPTION
				"Time to announce that the neighbour switch is down if 
				no heartbeats received during this period of time.
				
				This object can not be set when Cluster feature is enabled.
				Disable the Cluster feature using wsInfraClusterEnable
				before setting this object."
			::= { wsInfraClusterMIB 6 }

		-- 1.3.6.1.4.1.388.14.1.8.1.7
		wsInfraClusterHBInterval OBJECT-TYPE
			SYNTAX Unsigned32 (1..255)
			MAX-ACCESS read-write
			STATUS current
			DESCRIPTION
				"The frequency in which heartbeats are sent.
				
				This object can not be set when Cluster feature is enabled.
				Disable the Cluster feature using wsInfraClusterEnable
				before setting this object."
			::= { wsInfraClusterMIB 7 }

		-- 1.3.6.1.4.1.388.14.1.8.1.8
		wsInfraClusterHandleSTP OBJECT-TYPE
			SYNTAX INTEGER
				{
				true(1),
				false(2)
				}
			MAX-ACCESS read-write
			STATUS current
			DESCRIPTION
				"Whether the STP convergence time needs to be handled or not."
			::= { wsInfraClusterMIB 8 }

		-- 1.3.6.1.4.1.388.14.1.8.1.9
		wsInfraClusterSwitchState OBJECT-TYPE
			SYNTAX INTEGER
				{
				disabled(1),
				startup(2),
				discovery(3),
				online(4)
				}
			MAX-ACCESS read-only
			STATUS current
			DESCRIPTION
				"The current state of the switch in the cluster."
			::= { wsInfraClusterMIB 9 }

		-- 1.3.6.1.4.1.388.14.1.8.1.10
		wsInfraClusterLicNum OBJECT-TYPE
			SYNTAX Unsigned32 (0..65535)
			MAX-ACCESS read-only
			STATUS current
			DESCRIPTION
				"The cluster license number."
			::= { wsInfraClusterMIB 10 }

		-- 1.3.6.1.4.1.388.14.1.8.1.11
		wsInfraClusterInstalledLicNum OBJECT-TYPE
			SYNTAX Unsigned32 (0..65535)
			MAX-ACCESS read-only
			STATUS current
			DESCRIPTION
				"Installed license number of the switch."
			::= { wsInfraClusterMIB 11 }

		-- 1.3.6.1.4.1.388.14.1.8.1.12
		wsInfraClusterApCnt OBJECT-TYPE
			SYNTAX Unsigned32
			MAX-ACCESS read-only
			STATUS current
			DESCRIPTION
				"Total number of APs adopted in the cluster by 
				all the switches."
			::= { wsInfraClusterMIB 12 }

		-- 1.3.6.1.4.1.388.14.1.8.1.13
		wsInfraClusterVersion OBJECT-TYPE
			SYNTAX DisplayString
			MAX-ACCESS read-only
			STATUS current
			DESCRIPTION
				"The version of the Cluster Module."
			::= { wsInfraClusterMIB 13 }

		-- 1.3.6.1.4.1.388.14.1.8.1.14
		wsInfraClusterHistory OBJECT IDENTIFIER ::= { wsInfraClusterMIB 14 }

		-- 1.3.6.1.4.1.388.14.1.8.1.14.1
		wsInfraClusterHistoryTable OBJECT-TYPE
			SYNTAX SEQUENCE OF WsInfraClusterHistoryEntry
			MAX-ACCESS not-accessible
			STATUS current
			DESCRIPTION
				"List of history entries for the state changes of the switch."
			::= { wsInfraClusterHistory 1 }

		-- 1.3.6.1.4.1.388.14.1.8.1.14.1.1
		wsInfraClusterHistoryEntry OBJECT-TYPE
			SYNTAX WsInfraClusterHistoryEntry
			MAX-ACCESS not-accessible
			STATUS current
			DESCRIPTION
				"Defines an entry in the wsInfraClusterHistoryTable."
			INDEX { wsInfraClusterHistoryIndex }
			::= { wsInfraClusterHistoryTable 1 }

		WsInfraClusterHistoryEntry ::=
			SEQUENCE { 
				wsInfraClusterHistoryIndex
					Unsigned32,
				wsInfraClusterHistoryState
					INTEGER,
				wsInfraClusterHistoryTime
					DateAndTime,
				wsInfraClusterHistoryEventTrigger
					INTEGER,
				wsInfraClusterHistoryDesc
					DisplayString
			 }

		-- 1.3.6.1.4.1.388.14.1.8.1.14.1.1.1
		wsInfraClusterHistoryIndex OBJECT-TYPE
			SYNTAX Unsigned32 (1..100)
			MAX-ACCESS accessible-for-notify
			STATUS current
			DESCRIPTION
				"Simple Index."
			::= { wsInfraClusterHistoryEntry 1 }

		-- 1.3.6.1.4.1.388.14.1.8.1.14.1.1.2
		wsInfraClusterHistoryState OBJECT-TYPE
			SYNTAX INTEGER
				{
				disabled(1),
				startup(2),
				discovery(3),
				online(4)
				}
			MAX-ACCESS read-only
			STATUS current
			DESCRIPTION
				"Switch states."
			::= { wsInfraClusterHistoryEntry 2 }

		-- 1.3.6.1.4.1.388.14.1.8.1.14.1.1.3
		wsInfraClusterHistoryTime OBJECT-TYPE
			SYNTAX DateAndTime
			MAX-ACCESS read-only
			STATUS current
			DESCRIPTION
				"The time at which state change happened."
			::= { wsInfraClusterHistoryEntry 3 }

		-- 1.3.6.1.4.1.388.14.1.8.1.14.1.1.4
		wsInfraClusterHistoryEventTrigger OBJECT-TYPE
			SYNTAX INTEGER
				{
				enable(1),
				disable(2),
				startupDone(3),
				discoveryDone(4)
				}
			MAX-ACCESS read-only
			STATUS current
			DESCRIPTION
				"The event that triggered the state change."
			::= { wsInfraClusterHistoryEntry 4 }

		-- 1.3.6.1.4.1.388.14.1.8.1.14.1.1.5
		wsInfraClusterHistoryDesc OBJECT-TYPE
			SYNTAX DisplayString
			MAX-ACCESS read-only
			STATUS current
			DESCRIPTION
				"Description of the event and state change reason."
			::= { wsInfraClusterHistoryEntry 5 }

		-- 1.3.6.1.4.1.388.14.1.8.1.15
		wsInfraClusterConfig OBJECT IDENTIFIER ::= { wsInfraClusterMIB 15 }

		-- 1.3.6.1.4.1.388.14.1.8.1.15.1
		wsInfraClusterConfigTable OBJECT-TYPE
			SYNTAX SEQUENCE OF WsInfraClusterConfigEntry
			MAX-ACCESS not-accessible
			STATUS current
			DESCRIPTION
				"This table is used to configure the IP address of the switches
				in the cluster including this switch. It can be modified only if
				Cluster Protocol is disabled i.e. when wsInfraClusterEnable is 
				set to 'disable'."
			::= { wsInfraClusterConfig 1 }

		-- 1.3.6.1.4.1.388.14.1.8.1.15.1.1
		wsInfraClusterConfigEntry OBJECT-TYPE
			SYNTAX WsInfraClusterConfigEntry
			MAX-ACCESS not-accessible
			STATUS current
			DESCRIPTION
				"Defines an entry in the wsInfraClusterConfigTable."
			INDEX { wsInfraClusterConfigIndex, wsInfraClusterMemberIpAddr }
			::= { wsInfraClusterConfigTable 1 }

		WsInfraClusterConfigEntry ::=
			SEQUENCE { 
				wsInfraClusterConfigIndex
					INTEGER,
				wsInfraClusterMemberIpAddr
					IpAddress,
				wsInfraClusterCfgRowStatus
					RowStatus,
				wsInfraClustertNumHBSent
					Unsigned32,
				wsInfraClusterNumHBRcvd
					Unsigned32,
				wsInfraClusterLastSeen
					DateAndTime,
				wsInfraClusterFirstSeen
					DateAndTime,
				wsInfraClusterNumUpdMesgSent
					Unsigned32,
				wsInfraClusterNumUpdMesgRecd
					Unsigned32,
				wsInfraClusterStatus
					INTEGER,
				wsInfraClusterAdoptionCnt
					Unsigned32,
				wsInfraClusterSwitchMode
					INTEGER,
				wsInfraClusterInstalLicValue
					Unsigned32,
				wsInfraClusterUptime
					DateAndTime,
				wsInfraClusterNumMusAdopted
					Unsigned32,
				wsInfraClusterNumRadiosAdopted
					Unsigned32,
				wsInfraClusterNumSelfHealingRadios
					Unsigned32,
				wsInfraClusterNumRogueAps
					Unsigned32,
				wsInfraClusterCfgRunningImgVer
					DisplayString,
				wsInfraClusterCfgPortAdoptionCapacity
					Unsigned32
			 }

		-- 1.3.6.1.4.1.388.14.1.8.1.15.1.1.1
		wsInfraClusterConfigIndex OBJECT-TYPE
			SYNTAX INTEGER (1..12)
			MAX-ACCESS read-only
			STATUS current
			DESCRIPTION
				"Description."
			::= { wsInfraClusterConfigEntry 1 }

		-- 1.3.6.1.4.1.388.14.1.8.1.15.1.1.2
		wsInfraClusterMemberIpAddr OBJECT-TYPE
			SYNTAX IpAddress
			MAX-ACCESS read-only
			STATUS current
			DESCRIPTION
				"Unique IP address of the switch."
			::= { wsInfraClusterConfigEntry 2 }

		-- 1.3.6.1.4.1.388.14.1.8.1.15.1.1.3
		wsInfraClusterCfgRowStatus OBJECT-TYPE
			SYNTAX RowStatus
			MAX-ACCESS read-create
			STATUS current
			DESCRIPTION
				"SNMP row status about the configured object. The row creation 
				fails with error status as 'Bad Value' if the Cluster Config 
				Table already contains the max number of peers specified by 
				the Cluster Protocol Specification."
			::= { wsInfraClusterConfigEntry 3 }

		-- 1.3.6.1.4.1.388.14.1.8.1.15.1.1.4
		wsInfraClustertNumHBSent OBJECT-TYPE
			SYNTAX Unsigned32
			MAX-ACCESS read-only
			STATUS current
			DESCRIPTION
				"The number of HeartBeats sent from this switch to a
				peer switch in the cluster. 
				"
			::= { wsInfraClusterConfigEntry 4 }

		-- 1.3.6.1.4.1.388.14.1.8.1.15.1.1.5
		wsInfraClusterNumHBRcvd OBJECT-TYPE
			SYNTAX Unsigned32
			MAX-ACCESS read-only
			STATUS current
			DESCRIPTION
				"The number of HeartBeats received from the peer switch in the
				cluster."
			::= { wsInfraClusterConfigEntry 5 }

		-- 1.3.6.1.4.1.388.14.1.8.1.15.1.1.6
		wsInfraClusterLastSeen OBJECT-TYPE
			SYNTAX DateAndTime
			MAX-ACCESS read-only
			STATUS current
			DESCRIPTION
				"The time at which the last heartbeat received from the peer 
				switch. 
				
				"
			::= { wsInfraClusterConfigEntry 6 }

		-- 1.3.6.1.4.1.388.14.1.8.1.15.1.1.7
		wsInfraClusterFirstSeen OBJECT-TYPE
			SYNTAX DateAndTime
			MAX-ACCESS read-only
			STATUS current
			DESCRIPTION
				"The time at which the peer switch was first seen."
			::= { wsInfraClusterConfigEntry 7 }

		-- 1.3.6.1.4.1.388.14.1.8.1.15.1.1.8
		wsInfraClusterNumUpdMesgSent OBJECT-TYPE
			SYNTAX Unsigned32
			MAX-ACCESS read-only
			STATUS current
			DESCRIPTION
				"The number of Update Messages sent from this switch to a
				peer switch in the cluster. "
			::= { wsInfraClusterConfigEntry 8 }

		-- 1.3.6.1.4.1.388.14.1.8.1.15.1.1.9
		wsInfraClusterNumUpdMesgRecd OBJECT-TYPE
			SYNTAX Unsigned32
			MAX-ACCESS read-only
			STATUS current
			DESCRIPTION
				"The number of Update Messages received from the peer switch 
				in the cluster."
			::= { wsInfraClusterConfigEntry 9 }

		-- 1.3.6.1.4.1.388.14.1.8.1.15.1.1.10
		wsInfraClusterStatus OBJECT-TYPE
			SYNTAX INTEGER
				{
				peerConfigured(1),
				peerInvalid(2),
				peerSeen(3),
				peerNotSeen(4),
				peerEstablished(5)
				}
			MAX-ACCESS read-only
			STATUS current
			DESCRIPTION
				"The status of the peer switch."
			::= { wsInfraClusterConfigEntry 10 }

		-- 1.3.6.1.4.1.388.14.1.8.1.15.1.1.11
		wsInfraClusterAdoptionCnt OBJECT-TYPE
			SYNTAX Unsigned32
			MAX-ACCESS read-only
			STATUS current
			DESCRIPTION
				"Number of APs adopted by the peer switch in cluster."
			::= { wsInfraClusterConfigEntry 11 }

		-- 1.3.6.1.4.1.388.14.1.8.1.15.1.1.12
		wsInfraClusterSwitchMode OBJECT-TYPE
			SYNTAX INTEGER
				{
				active(1),
				standby(2)
				}
			MAX-ACCESS read-only
			STATUS current
			DESCRIPTION
				"Whether the Peer Switch's mode is primary or standby."
			::= { wsInfraClusterConfigEntry 12 }

		-- 1.3.6.1.4.1.388.14.1.8.1.15.1.1.13
		wsInfraClusterInstalLicValue OBJECT-TYPE
			SYNTAX Unsigned32 (0..65535)
			MAX-ACCESS read-only
			STATUS current
			DESCRIPTION
				"The value of the Installed License of the peer switch."
			::= { wsInfraClusterConfigEntry 13 }

		-- 1.3.6.1.4.1.388.14.1.8.1.15.1.1.14
		wsInfraClusterUptime OBJECT-TYPE
			SYNTAX DateAndTime
			MAX-ACCESS read-only
			STATUS current
			DESCRIPTION
				"Uptime of member switch"
			::= { wsInfraClusterConfigEntry 14 }

		-- 1.3.6.1.4.1.388.14.1.8.1.15.1.1.15
		wsInfraClusterNumMusAdopted OBJECT-TYPE
			SYNTAX Unsigned32
			MAX-ACCESS read-only
			STATUS current
			DESCRIPTION
				"Number of MUs adopted by the member switch"
			::= { wsInfraClusterConfigEntry 15 }

		-- 1.3.6.1.4.1.388.14.1.8.1.15.1.1.16
		wsInfraClusterNumRadiosAdopted OBJECT-TYPE
			SYNTAX Unsigned32
			MAX-ACCESS read-only
			STATUS current
			DESCRIPTION
				"Number of radios adopted by the member switch"
			::= { wsInfraClusterConfigEntry 16 }

		-- 1.3.6.1.4.1.388.14.1.8.1.15.1.1.17
		wsInfraClusterNumSelfHealingRadios OBJECT-TYPE
			SYNTAX Unsigned32
			MAX-ACCESS read-only
			STATUS current
			DESCRIPTION
				"Number of radios in self healing mode in the member switch"
			::= { wsInfraClusterConfigEntry 17 }

		-- 1.3.6.1.4.1.388.14.1.8.1.15.1.1.18
		wsInfraClusterNumRogueAps OBJECT-TYPE
			SYNTAX Unsigned32
			MAX-ACCESS read-only
			STATUS current
			DESCRIPTION
				"Number of rogue APs detected by the member switch"
			::= { wsInfraClusterConfigEntry 18 }

		-- 1.3.6.1.4.1.388.14.1.8.1.15.1.1.19
		wsInfraClusterCfgRunningImgVer OBJECT-TYPE
			SYNTAX DisplayString
			MAX-ACCESS read-only
			STATUS current
			DESCRIPTION
				"Version of the running image on the member switch"
			::= { wsInfraClusterConfigEntry 19 }

		-- 1.3.6.1.4.1.388.14.1.8.1.15.1.1.20
		wsInfraClusterCfgPortAdoptionCapacity OBJECT-TYPE
			SYNTAX Unsigned32
			MAX-ACCESS read-only
			STATUS current
			DESCRIPTION
				"Port adoption capacity of the member switch"
			::= { wsInfraClusterConfigEntry 20 }

		-- 1.3.6.1.4.1.388.14.1.8.1.15.2
		wsInfraClusterPeerStatTable OBJECT-TYPE
			SYNTAX SEQUENCE OF WsInfraClusterPeerStatEntry
			MAX-ACCESS not-accessible
			STATUS obsolete
			DESCRIPTION
				"Statistics about different switches in the cluster."
			::= { wsInfraClusterConfig 2 }

		-- 1.3.6.1.4.1.388.14.1.8.1.15.2.1
		wsInfraClusterPeerStatEntry OBJECT-TYPE
			SYNTAX WsInfraClusterPeerStatEntry
			MAX-ACCESS not-accessible
			STATUS obsolete
			DESCRIPTION
				"Defines an entry in the wsInfraClusterPeerStatTable."
			INDEX { wsInfraClusterConfigIndex, wsInfraClusterMemberIpAddr }
			::= { wsInfraClusterPeerStatTable 1 }

		WsInfraClusterPeerStatEntry ::=
			SEQUENCE { 
				wsInfraClusterStatNumHBSent
					Unsigned32
			 }

		-- 1.3.6.1.4.1.388.14.1.8.1.15.2.1.1
		wsInfraClusterStatNumHBSent OBJECT-TYPE
			SYNTAX Unsigned32
			MAX-ACCESS read-only
			STATUS obsolete
			DESCRIPTION
				"The number of HeartBeats sent from this switch to a
				peer switch in the cluster. 
				"
			::= { wsInfraClusterPeerStatEntry 1 }

		-- 1.3.6.1.4.1.388.14.1.8.1.16
		wsInfraClusterUpAndFullyConnected OBJECT-TYPE
			SYNTAX INTEGER
				{
				no(1),
				yes(2)
				}
			MAX-ACCESS read-only
			STATUS current
			DESCRIPTION
				"Indicates if cluster is up and fully connected"
			::= { wsInfraClusterMIB 16 }

		-- 1.3.6.1.4.1.388.14.1.8.1.17
		wsInfraClusterTotalApsAdopted OBJECT-TYPE
			SYNTAX Integer32
			MAX-ACCESS read-only
			STATUS current
			DESCRIPTION
				"Total number of APs adopted by the cluster"
			::= { wsInfraClusterMIB 17 }

		-- 1.3.6.1.4.1.388.14.1.8.1.18
		wsInfraClusterTotalRadiosAdopted OBJECT-TYPE
			SYNTAX Integer32
			MAX-ACCESS read-only
			STATUS current
			DESCRIPTION
				"Total number of radios adopted by the cluster"
			::= { wsInfraClusterMIB 18 }

		-- 1.3.6.1.4.1.388.14.1.8.1.19
		wsInfraClusterTotalMusAssociated OBJECT-TYPE
			SYNTAX Integer32
			MAX-ACCESS read-only
			STATUS current
			DESCRIPTION
				"Total number of MUs adopted by the cluster"
			::= { wsInfraClusterMIB 19 }

		-- 1.3.6.1.4.1.388.14.1.8.1.20
		wsInfraClusterTotalRogueAps OBJECT-TYPE
			SYNTAX Integer32
			MAX-ACCESS read-only
			STATUS current
			DESCRIPTION
				"Total number of rogue APs detected by the cluster"
			::= { wsInfraClusterMIB 20 }

		-- 1.3.6.1.4.1.388.14.1.8.1.21
		wsInfraClusterTotalPortAdoptionCapacity OBJECT-TYPE
			SYNTAX Integer32
			MAX-ACCESS read-only
			STATUS current
			DESCRIPTION
				"Total port adoption capacity of the cluster"
			::= { wsInfraClusterMIB 21 }

		-- 1.3.6.1.4.1.388.14.1.8.1.22
		wsInfraClusterTotalSelfHealingRadios OBJECT-TYPE
			SYNTAX Integer32
			MAX-ACCESS read-only
			STATUS current
			DESCRIPTION
				"Total number of radios in self healing mode in the cluster"
			::= { wsInfraClusterMIB 22 }

		-- 1.3.6.1.4.1.388.14.1.8.1.23
		wsInfraClusterMusAdoptedCnt OBJECT-TYPE
			SYNTAX Integer32
			MAX-ACCESS read-only
			STATUS current
			DESCRIPTION
				"Number of MUs adopted by the switch"
			::= { wsInfraClusterMIB 23 }

		-- 1.3.6.1.4.1.388.14.1.8.1.24
		wsInfraClusterRadiosAdoptedCnt OBJECT-TYPE
			SYNTAX Integer32
			MAX-ACCESS read-only
			STATUS current
			DESCRIPTION
				"Number of radios adopted by the switch"
			::= { wsInfraClusterMIB 24 }

		-- 1.3.6.1.4.1.388.14.1.8.1.25
		wsInfraClusterSelfHealingRadioCnt OBJECT-TYPE
			SYNTAX Integer32
			MAX-ACCESS read-only
			STATUS current
			DESCRIPTION
				"Number of radios in self healing mode in the switch"
			::= { wsInfraClusterMIB 25 }

		-- 1.3.6.1.4.1.388.14.1.8.1.26
		wsInfraClusterRogueApCnt OBJECT-TYPE
			SYNTAX Integer32
			MAX-ACCESS read-only
			STATUS current
			DESCRIPTION
				"Number of rogue APs detected by the switch"
			::= { wsInfraClusterMIB 26 }

		-- 1.3.6.1.4.1.388.14.1.8.1.27
		wsInfraClusterRunningImgVer OBJECT-TYPE
			SYNTAX DisplayString
			MAX-ACCESS read-only
			STATUS current
			DESCRIPTION
				"Version of the running image on the switch"
			::= { wsInfraClusterMIB 27 }

		-- 1.3.6.1.4.1.388.14.1.8.1.28
		wsInfraClusterPortAdoptionCapacity OBJECT-TYPE
			SYNTAX Integer32
			MAX-ACCESS read-only
			STATUS current
			DESCRIPTION
				"Port adoption capacity of the switch"
			::= { wsInfraClusterMIB 28 }

		-- 1.3.6.1.4.1.388.14.1.8.1.29
		wsInfraClusterAutoRevert OBJECT-TYPE
			SYNTAX INTEGER
				{
				enable(1),
				disable(2)
				}
			MAX-ACCESS read-write
			STATUS current
			DESCRIPTION
				"Enable or disable automatic revert.
				
				This object can not be set when Cluster feature is enabled.
				Disable the Cluster feature using wsInfraClusterEnable
				before setting this object."
			::= { wsInfraClusterMIB 29 }

		-- 1.3.6.1.4.1.388.14.1.8.1.30
		wsInfraClusterAutoRevertDelay OBJECT-TYPE
			SYNTAX Unsigned32 (1..1800)
			UNITS "minutes"
			MAX-ACCESS read-write
			STATUS current
			DESCRIPTION
				"Auto-revert delay (in minutes - ranging from 1 to 1800).
				
				This object can not be set when Cluster feature is enabled.
				Disable the Cluster feature using wsInfraClusterEnable
				before setting this object."
			::= { wsInfraClusterMIB 30 }

		-- 1.3.6.1.4.1.388.14.1.8.1.31
		wsInfraClusterManualRevert OBJECT-TYPE
			SYNTAX INTEGER { manualRevertNow(1) }
			MAX-ACCESS read-write
			STATUS current
			DESCRIPTION
				"Set manual revert"
			::= { wsInfraClusterMIB 31 }

		-- 1.3.6.1.4.1.388.14.1.8.1.32
		wsInfraClusterDhcpRedundancy OBJECT-TYPE
			SYNTAX INTEGER
				{
				enable(1),
				disable(2)
				}
			MAX-ACCESS read-write
			STATUS current
			DESCRIPTION
				"Enable or disable the DHCP redundancy feature.
				
				This object can not be set when Cluster feature is enabled.
				Disable the Cluster feature using wsInfraClusterEnable
				before setting this object."
			::= { wsInfraClusterMIB 32 }

		-- 1.3.6.1.4.1.388.14.1.8.1.33
		wsInfraClusterActiveDhcpServerSwitch OBJECT-TYPE
			SYNTAX DisplayString (SIZE (1..64))
			MAX-ACCESS read-only
			STATUS current
			DESCRIPTION
				"IP address of the switch running the active DHCP server.
				
				Other values this field could take are:
				  NotApplicable - when redundancy is disabled. 
				  Unknown - when at any given time if there is no active DHCP 
				            server switch or the current switch is not participating 
				            in DHCP redundancy."
			::= { wsInfraClusterMIB 33 }

		-- 1.3.6.1.4.1.388.14.1.8.1.34
		wsInfraClusterResetActiveDhcpServer OBJECT-TYPE
			SYNTAX INTEGER { resetActiveDhcpServer(1) }
			MAX-ACCESS read-write
			STATUS current
			DESCRIPTION
				"Reset the active DHCP server.
				
				If the current switch is running active DHCP server, 
				then the DHCP server will be reset. 
				
				Otherwise, this action will be ignored."
			::= { wsInfraClusterMIB 34 }

		-- 1.3.6.1.4.1.388.14.1.8.1.35
		wsInfraCriticalResourceIp OBJECT-TYPE
			SYNTAX IpAddress
			MAX-ACCESS read-write
			STATUS current
			DESCRIPTION
				"IP address of the Critical Resource for the cluster switches.
				
				This object can not be set when Cluster feature is enabled.
				Disable the Cluster feature using wsInfraClusterEnable
				before setting this object."
			::= { wsInfraClusterMIB 35 }

		-- 1.3.6.1.4.1.388.14.1.8.1.36
		wsInfraClusterDynApLoadBal OBJECT IDENTIFIER ::= { wsInfraClusterMIB 36 }

		-- 1.3.6.1.4.1.388.14.1.8.1.36.1
		wsInfraClusterDynApLoadBalEnable OBJECT-TYPE
			SYNTAX TruthValue
			MAX-ACCESS read-write
			STATUS current
			DESCRIPTION
				"Enable or disable dynamic AP load balance feature.
				Default is disabled."
			::= { wsInfraClusterDynApLoadBal 1 }

		-- 1.3.6.1.4.1.388.14.1.8.1.36.2
		wsInfraClusterDynApLoadBalApproach OBJECT-TYPE
			SYNTAX INTEGER
				{
				schedule(1),
				runtime(2)
				}
			MAX-ACCESS read-write
			STATUS current
			DESCRIPTION
				"This determines whether to the trigger dynamic AP 
				load balance on scheduled time or immediately 
				when AP imbalance is detected."
			::= { wsInfraClusterDynApLoadBal 2 }

		-- 1.3.6.1.4.1.388.14.1.8.1.36.3
		wsInfraClusterDynApLoadBalSched OBJECT IDENTIFIER ::= { wsInfraClusterDynApLoadBal 3 }

		-- 1.3.6.1.4.1.388.14.1.8.1.36.3.1
		wsInfraClusterDynApLoadBalSchedStartTime OBJECT-TYPE
			SYNTAX DateAndTime
			MAX-ACCESS read-write
			STATUS current
			DESCRIPTION
				"If trigger for dynamic AP load balance is scheduled time 
				then this configuration parameter determines the start time 
				to initiate dynamic AP load balance."
			::= { wsInfraClusterDynApLoadBalSched 1 }

		-- 1.3.6.1.4.1.388.14.1.8.1.36.3.2
		wsInfraClusterDynApLoadBalSchedInterval OBJECT-TYPE
			SYNTAX Unsigned32 (1..180)
			UNITS "days"
			MAX-ACCESS read-write
			STATUS current
			DESCRIPTION
				"If trigger for dynamic AP load balance is scheduled time 
				then this configuration parameter determines the interval 
				or frequency at which dynamic AP load balance will be 
				triggered. Default value is 1 day."
			::= { wsInfraClusterDynApLoadBalSched 2 }

		-- 1.3.6.1.4.1.388.14.1.8.1.36.4
		wsInfraClusterDynApLoadBalStart OBJECT-TYPE
			SYNTAX DoActionNow
			MAX-ACCESS read-write
			STATUS current
			DESCRIPTION
				"Command to initiate dynamic AP load balance."
			::= { wsInfraClusterDynApLoadBal 4 }

		-- 1.3.6.1.4.1.388.14.1.8.1.36.5
		wsInfraClusterDynApLoadBalMUThrshld OBJECT-TYPE
			SYNTAX INTEGER (1..512)
			UNITS "MUs"
			MAX-ACCESS read-write
			STATUS current
			DESCRIPTION
				"This specifies per AP MU threshold value. 
				If AP associated MU count is equal to or 
				greater than this threshold value then AP 
				will not be reset. It also depends on trigger 
				for dynamic AP load balance. Default value is 32 MUs."
			::= { wsInfraClusterDynApLoadBal 5 }

		-- 1.3.6.1.4.1.388.14.1.8.1.37
		wsInfraClusterLicensingAlgorithm OBJECT-TYPE
			SYNTAX INTEGER
				{
				max(1),
				aggregation(2)
				}
			MAX-ACCESS read-write
			STATUS current
			DESCRIPTION
				"Set the redundancy licensing algorithm to either 
				Max or Aggregation.
				This object can not be set when Redundancy feature 
				is enabled. Disable the Redundancy feature using 
				wsInfraClusterEnable before setting this object."
			::= { wsInfraClusterMIB 37 }

		-- 1.3.6.1.4.1.388.14.1.8.1.100
		wsInfrastructureMIBConformance OBJECT IDENTIFIER ::= { wsInfraClusterMIB 100 }

		-- 1.3.6.1.4.1.388.14.1.8.1.100.1
		wsInfrastructureMIBCompliances OBJECT IDENTIFIER ::= { wsInfrastructureMIBConformance 1 }

		-- 1.3.6.1.4.1.388.14.1.8.1.100.1.1
		wsInfrastructureMIBCompliance MODULE-COMPLIANCE
			STATUS current
			DESCRIPTION 
				"Description."
			MODULE -- this module
				MANDATORY-GROUPS { wsInfrastructureMIBGroup }
			::= { wsInfrastructureMIBCompliances 1 }

		-- 1.3.6.1.4.1.388.14.1.8.1.100.2
		wsInfrastructureMIBGroups OBJECT IDENTIFIER ::= { wsInfrastructureMIBConformance 2 }

		-- 1.3.6.1.4.1.388.14.1.8.1.100.2.1
		wsInfrastructureMIBGroup OBJECT-GROUP
			OBJECTS { wsInfraClusterSwitchIP, wsInfraClusterEnable, wsInfraClusterMode, wsInfraClusterId, wsInfraClusterHBInterval, 
				wsInfraClusterHandleSTP, wsInfraClusterSwitchState, wsInfraClusterLicNum, wsInfraClusterInstalledLicNum, wsInfraClusterApCnt, 
				wsInfraClusterVersion, wsInfraClusterHistoryIndex, wsInfraClusterHistoryState, wsInfraClusterHistoryTime, wsInfraClusterHistoryEventTrigger, 
				wsInfraClusterHistoryDesc, wsInfraClusterCfgRowStatus, wsInfraClusterMemberIpAddr, wsInfraClusterHoldInterval, wsInfraClusterDiscoveryInterval, 
				wsInfraClusterUpAndFullyConnected, wsInfraClusterTotalApsAdopted, wsInfraClusterTotalRadiosAdopted, wsInfraClusterTotalMusAssociated, wsInfraClusterTotalRogueAps, 
				wsInfraClusterTotalPortAdoptionCapacity, wsInfraClusterTotalSelfHealingRadios, wsInfraClusterMusAdoptedCnt, wsInfraClusterRadiosAdoptedCnt, wsInfraClusterSelfHealingRadioCnt, 
				wsInfraClusterRogueApCnt, wsInfraClusterRunningImgVer, wsInfraClusterPortAdoptionCapacity, wsInfraClusterConfigIndex, wsInfraClusterAutoRevert, 
				wsInfraClusterAutoRevertDelay, wsInfraClusterResetActiveDhcpServer, wsInfraClusterActiveDhcpServerSwitch, wsInfraClusterDhcpRedundancy, wsInfraCriticalResourceIp, 
				wsInfraClusterDynApLoadBalEnable, wsInfraClusterDynApLoadBalApproach, wsInfraClusterDynApLoadBalMUThrshld, wsInfraClusterDynApLoadBalStart, wsInfraClusterLicensingAlgorithm, 
				wsInfraClusterManualRevert, wsInfraClustertNumHBSent, wsInfraClusterNumHBRcvd, wsInfraClusterLastSeen, wsInfraClusterFirstSeen, 
				wsInfraClusterNumUpdMesgSent, wsInfraClusterNumUpdMesgRecd, wsInfraClusterStatus, wsInfraClusterAdoptionCnt, wsInfraClusterSwitchMode, 
				wsInfraClusterInstalLicValue, wsInfraClusterUptime, wsInfraClusterNumMusAdopted, wsInfraClusterNumRadiosAdopted, wsInfraClusterNumSelfHealingRadios, 
				wsInfraClusterNumRogueAps, wsInfraClusterCfgRunningImgVer, wsInfraClusterCfgPortAdoptionCapacity, wsInfraClusterDynApLoadBalSchedStartTime, wsInfraClusterDynApLoadBalSchedInterval
				 }
			STATUS current
			DESCRIPTION 
				"Description."
			::= { wsInfrastructureMIBGroups 1 }

		-- 1.3.6.1.4.1.388.14.1.8.1.100.2.2
		wsInfrastructureMIBObsoleteGroup OBJECT-GROUP
			OBJECTS { wsInfraClusterStatNumHBSent }
			STATUS obsolete
			DESCRIPTION 
				"Description."
			::= { wsInfrastructureMIBGroups 2 }
	END
