A3COM-RIP-IPEXTNS-R4-MIB DEFINITIONS ::= BEGIN

      IMPORTS
              enterprises, IpAddress
                  FROM RFC1155-SMI
              OBJECT-TYPE
                      FROM RFC-1212;


      a3Com          OBJECT IDENTIFIER ::= { enterprises 43 }
      brouterMIB     OBJECT IDENTIFIER ::= { a3Com 2 }
      a3ComRipIp     OBJECT IDENTIFIER ::= { brouterMIB 8 }

      RowStatus ::= INTEGER {
                         -- the following two values are states
                         -- these values can be read or written
                         active(1),
                         notInService(2),

                         -- the following value is a state:         
                         -- this value may be read, but not written 
                         notReady(3),                               

                         -- the following three values are actions
                         -- these values can be written, but are never read
                         createAndGo(4),
                         createAndWait(5),
                         destroy(6)
      }

      --This data type, which has the same semantics as the rowStatus
      --textual convention used in SNMPv2, is used to add and 
      --delete entries from a table.
      --
      --The tables in this MIB allow a subset of the functionality
      --provided by the rowStatus textual convention.  In particular
      --row creation is allowed using only the createAndGo method.
      --
      --That is, when adding entries to this table, this object
      --must be set to createAndGo(4).  The instance identifier
      --for this object will define the values of the columns 
      --that make up the index.  
      --
      --In the same PDU, the appropriate remaining columns
      --of that row must be set as well.  The agent
      --will immediately set the value of this object to
      --active(1) if the row is correct.  If not, the agent
      --will refuse the SET request and return an
      --error code.
      --
      --To modify an existing entry, it must be removed
      --and another entry with the desired changes added. 
      --                   
      --To remove an entry, set the value of this object
      --to destroy(6).


      a3RipIpUpdateTime  OBJECT-TYPE
          SYNTAX  INTEGER (5..5400)
          ACCESS  read-write
          STATUS  mandatory
          DESCRIPTION
                  "This parameter specifies the time interval,
                  in seconds, within which RIP-IP sends update
                  packets.  This parameter also determines
                  the length of time a route learned through
                  RIP-IP stays in the IP routing table.  For
                  example, once a route is in the routing table, 
                  the router must receive a RIP update packet
                  indicating the reachability of this route
                  every 6 * a3RipIpUpdateTime.  If no updates
                  are received in that time interval, the entry
                  is removed from the routing table."
          DEFVAL { 30 }
          ::= { a3ComRipIp 1 }


      a3RipIpCtlTable  OBJECT-TYPE
          SYNTAX  SEQUENCE OF A3RipIpCtlEntry
          ACCESS  not-accessible
          STATUS  mandatory
          DESCRIPTION
                  "This table contains parameters that affect the
                  operation of RIP for IP."
          ::= { a3ComRipIp 2 }
        
      a3RipIpCtlEntry  OBJECT-TYPE
          SYNTAX  A3RipIpCtlEntry
          ACCESS  not-accessible
          STATUS  mandatory
          DESCRIPTION
                  "Each entry contains parameters specific to each
                  network port on this system."
          INDEX { a3RipIpPortIndex }
          ::= { a3RipIpCtlTable 1 }

      A3RipIpCtlEntry ::=
          SEQUENCE {
              a3RipIpPortIndex     INTEGER,
              a3RipIpTalkCtl       INTEGER,
              a3RipIpListenCtl     INTEGER,
              a3RipIpTrustedNbrCtl INTEGER,
              a3RipIpPoisonCtl     INTEGER,
              a3RipIpTriggerCtl    INTEGER,
              a3RipIpDefMetric     INTEGER,
              a3RipIpExtPolCtl     INTEGER,
              a3RipIpIntPolCtl     INTEGER,
              a3RipIpNetPolCtl     INTEGER,
              a3RipIpRcvPolCtl     INTEGER,
              a3RipIpStaPolCtl     INTEGER,
              a3RipIpUnnAdvCtl     INTEGER,
              a3RipIpBcastCtl      INTEGER,
              a3RipIpExtPolAllMet  INTEGER,
              a3RipIpIntPolAllMet  INTEGER,
              a3RipIpNetPolAllMet  INTEGER,
              a3RipIpRcvPolAllMet  INTEGER,
              a3RipIpStaPolAllMet  INTEGER,
              a3RipIpDynNbrCtl     INTEGER,
              a3RipIpAggregateCtl  INTEGER,
              a3RipIpDeAggregateCtl INTEGER,
              a3RipIpNBMAmodeCtl   INTEGER
          }

      a3RipIpPortIndex  OBJECT-TYPE
          SYNTAX  INTEGER
          ACCESS  read-only
          STATUS  mandatory
          DESCRIPTION
                  "This provides the port index to which the RIP-IP
                  parameters in this table entry apply."
          ::= { a3RipIpCtlEntry 1 }

      a3RipIpTalkCtl  OBJECT-TYPE
          SYNTAX  INTEGER {
                     talk   (1),
                     noTalk (2)
                  }
          ACCESS  read-write
          STATUS  mandatory
          DESCRIPTION
                  "If talk (1) is specified, RIP-IP sends update and
                  request packets on the specified port.  If noTalk (2)
                  is specified, no updates or requests are sent over
                  this port.

		  If talk(1) is specified, 3RipIpDynNbrCtl has been
		  set to dynamicNbr, and the -PORT owner has been set
		  to FR/X.25, the -RIP Neighbor list is built from
		  the ARP table."
          REFERENCE
                  "NETBuilder II Ref. Guide, RIPIP Service Parameter:
                  CONTol."
          DEFVAL { noTalk }
          ::= { a3RipIpCtlEntry 2 }

      a3RipIpListenCtl  OBJECT-TYPE
          SYNTAX  INTEGER {
                     listen   (1),
                     noListen (2)
                  }
          ACCESS  read-write
          STATUS  mandatory
          DESCRIPTION
                  "If listen (1) is selected, RIP-IP receives and
                  processes incoming update and request packets.  If
                  a3RipIpTalkCtl is set to noTalk (2), this system does
                  not send any response packets for the request
                  packets it receives."
          REFERENCE
                  "NETBuilder II Ref. Guide, RIPIP Service Parameter:
                  CONTol."
          DEFVAL { noListen }
          ::= { a3RipIpCtlEntry 3 }

      a3RipIpTrustedNbrCtl  OBJECT-TYPE
          SYNTAX  INTEGER {
                     include (1),
                     exclude (2)
                  }
          ACCESS  read-write
          STATUS  mandatory
          DESCRIPTION
                  "This object controls how the list of trusted neighbors in
                  a3RipIpTrustedNbrTable is to be interpreted.  If this is
                  set to include (1), RIP-IP will accept routing packets from
                  the set of addresses in a3RipIpTrustedNbrTable.  If this
                  is set to exclude (2), RIP-IP will accept routing packets
                  from all addresses except those listed in that table for
                  this port.  Note, if a3RipIpTrustedNbrTable is empty, RIP-IP
                  will accept routing updates from all neighbors, regardless
                  of the value of this object."
          REFERENCE
                  "NETBuilder II Ref. Guide, RIPIP Service Parameter:
                  TrustedNeighbor."
          ::= { a3RipIpCtlEntry 4 }

      a3RipIpPoisonCtl  OBJECT-TYPE
          SYNTAX  INTEGER {
                     poison   (1),
                     noPoison (2)
                  }
          ACCESS  read-write
          STATUS  mandatory
          DESCRIPTION
                  "This parameter determines how split horizon is
                  performed.  To achieve split horizon, RIP-IP
                  refrains from advertising a route to a port if
                  the gateway for this route can be reached on the 
                  same port.  If poison (1) is selected, RIP-IP
                  advertises the route but it uses infinity (16)
                  for the metric.  If noPoison (2) is selected,
                  the route is not advertised."
          REFERENCE
                  "NETBuilder II Ref. Guide, RIPIP Service Parameter:
                  CONTol."
          DEFVAL { poison }
          ::= { a3RipIpCtlEntry 5 }

      a3RipIpTriggerCtl  OBJECT-TYPE
          SYNTAX  INTEGER {
                     trigger   (1),
                     noTrigger (2)
                  }
          ACCESS  read-write
          STATUS  mandatory
          DESCRIPTION
                  "This parameter determines if RIP-IP sends trigger
                  update packets.  Trigger update packets are
                  sent when a route's metric has changed.  By
                  sending these update packets, RIP does not need to
                  wait for the update interval, allowing earlier
                  notification that a route's metric has changed."
          REFERENCE
                  "NETBuilder II Ref. Guide, RIPIP Service Parameter:
                  CONTol."
          DEFVAL { trigger }
          ::= { a3RipIpCtlEntry 6 }

      a3RipIpDefMetric  OBJECT-TYPE
          SYNTAX  INTEGER (0..15)
          ACCESS  read-write
          STATUS  mandatory
          DESCRIPTION
                  "This parameter specifies whether RIP-IP advertises
                  the default route.  The default route is the
                  network with internet address 0.0.0.0 and is 
                  reported with a metric equal to the value of this
                  parameter.  If this is set to 0, the default
                  route is advertised only if it was learned and if
                  that default route is allowed by the corresponding policies."
          REFERENCE
                  "NETBuilder II Ref. Guide, RIPIP Service Parameter:
                  DefaultMetric."
          DEFVAL { 0 }
          ::= { a3RipIpCtlEntry 7 }
         
--
-- The following objects instrument policies controlling the routes
-- that may be added to the routing table and the routes that may be
-- advertised via routing updates.
--
-- Incoming policies are applied to received routing updates before the
-- routes are entered into the routing table.  The Receive Policy 
-- (mib objects:  a3RipIpRcvPolCtl and a3RipIpRcvPolTable) filters
-- RIP updates before they get into the routing table.  There are
-- corresponding incoming policies for OSPF routing updates and EGP routing 
-- updates. (they will be in separate MIBs).
--
-- Outgoing policies are applied to routing updates before they are
-- sent by the system.  First, the Network Policy (mib objects: 
-- a3RipIpNetPolCtl and a3RipIpNetPolTable) is applied to all routing
-- updates.  Next, those entries learned via an IGP (other than RIP) are
-- filtered against the Interior Policy (mib objects: a3RipIpIntPolCtl and
-- a3RipIpIntPolTable) before they are included in any routing updates.
-- Those entries learned via an EGP are similarly filtered against the
-- Exterior Policy (mib objects: a3RipIpExtPolCtl and a3RipIpExtPolTable) and,
-- static entries are filtered against the Static Policy (mib objects: 
-- a3RipIpStaPolCtl and a3RipIpStaPolTable).
--
-- All routing updates must pass these two layers of policy before they
-- are allowed to be sent.
--

      a3RipIpExtPolCtl  OBJECT-TYPE
          SYNTAX  INTEGER {
                     all      (1),
                     none     (2),
                     include  (3),
                     exclude  (4)
                  }
          ACCESS  read-write
          STATUS  mandatory
          DESCRIPTION
                  "This parameter controls which routes learned
                  by the Exterior Gateway Protocol (EGP) are
                  reported by RIP-IP.  If this is set to all (1),
                  all routes learned from EGP or BGP are reported, provided
                  those routes are allowed to be reported by 
                  the Network Policy (see a3RipIpNetPolCtl).  
                  The metric that will be reported by RIP for all routes 
                  learned via EGP or BGP is specified by a3RipIpExtPolAllMet.

                  If this is set to none (2), none of the routes
                  learned from EGP or BGP are reported.

                  If this is set to include (3), routes to destinations
                  listed in a3RipIpExtPolTable are reported.  If no
                  routes are listed in a3RipIpExtPolTable, all routes
                  are reported.  This applies to the other policy tables
                  as well.

                  If this is set to exclude (4), all routes
                  are reported except those listed in a3RipIpExtPolTable.
                  If no routes are listed in a3RipIpExtPolTable, no routes
                  are reported.  This applies to the other policy tables
                  as well.  The metric reported for routes learned via EGP or BGP
                  in this case is calculated using the formula specified in 
                  a3RipIpImpMetTable (for egp or bgp).

                  (note, in all these cases, Network Policy must be
                  passed before this policy is applied).

                  If this objects gets changed from include to exclude,
                  or from exclude to include, all existing entries will
                  be flushed from the table."
          REFERENCE
                  "NETBuilder II Ref. Guide, RIPIP Service Parameter:
                  ExteriorPolicy."
          DEFVAL { none }
          ::= { a3RipIpCtlEntry 8 }
               
      a3RipIpIntPolCtl  OBJECT-TYPE
          SYNTAX  INTEGER {
                     all      (1),
                     none     (2),
                     include  (3),
                     exclude  (4)
                  }
          ACCESS  read-write
          STATUS  mandatory
          DESCRIPTION
                  "This parameter determines which routes learned by
                  an Interior Gateway Protocol (IGP) are reported by RIP-IP.  

                  If this is set to all (1), all routes learned from an IGP
                  are reported, provided those routes are allowed to be 
                  reported by the Network Policy (see a3RipIpNetPolCtl)
                  The metric that will be reported by RIP for all routes 
                  learned via an IGP (other than RIP) is specified by 
                  a3RipIpIntPolAllMet.

                  If this is set to none (2), none of the routes
                  learned from the IGP are reported.

                  If this is set to include (3) routes to destinations
                  listed in a3RipIpIntPolTable are reported.

                  If this is set to exclude (4), all routes
                  are reported except those listed in a3RipIpIntPolTable.
                  If no routes are listed, no routes will be reported.
                  The metric reported for routes learned via an IGP (other than RIP)
                  in this case is calculated using the formula specified in 
                  a3RipIpImpMetTable (for ospf or iisis).

                  (note, in all these cases, Network Policy must be
                  passed before this policy is applied).

                  If this objects gets changed from include to exclude,
                  or from exclude to include, all existing entries will
                  be flushed from the table."
          REFERENCE
                  "NETBuilder II Ref. Guide, RIPIP Service Parameter:
                  InteriorPolicy."
          DEFVAL { none }
          ::= { a3RipIpCtlEntry 9 }

      a3RipIpNetPolCtl  OBJECT-TYPE
          SYNTAX  INTEGER {
                     all      (1),
                     none     (2),
                     include  (3),
                     exclude  (4)
                  }
          ACCESS  read-write
          STATUS  mandatory
          DESCRIPTION
                  "This parameter determines which routes are reported by 
                  RIP-IP.  The policies defined by this object and 
                  a3RipIpNetPolTable overrides the policies defined in
                  a3RipIpIntPolCtl/Table, a3RipIpExtPolCtl/Table, and
                  a3RipIpStaPolCtl/Table in deciding whether a route
                  is to be reported. 

                  If this is set to all (1), all routes are reported, provided
                  they are allowed by either the interior policy or exterior
                  policy.  The metric that will be reported by RIP for all routes 
                  is specified by a3RipIpNetPolAllMet.

                  If this is set to none (2), none of the routes
                  are reported.

                  If this is set to include (3), routes to destinations
                  listed in a3RipIpNetPolTable are reported.

                  If this is set to exclude (4), all routes
                  are reported except those listed in a3RipIpNetPolTable.
                  If no routes are listed, no routes will be reported.
                  The metric reported for routes learned via RIP
                  in this case is taken directly from the routing table or
                  from the results of applying one of the other policies.

                  (note, in all these cases, the Interior Policy or Exterior
                  Policy must be passed after this policy is applied.  Only
                  those routes that pass both sets of policies will be
                  advertised).

                  If this objects gets changed from include to exclude,
                  or from exclude to include, all existing entries will
                  be flushed from the table."
          REFERENCE
                  "NETBuilder II Ref. Guide, RIPIP Service Parameter:
                  NetworkPolicy."
          DEFVAL { all }
          ::= { a3RipIpCtlEntry 10 }

      a3RipIpRcvPolCtl  OBJECT-TYPE
          SYNTAX  INTEGER {
                     all      (1),
                     none     (2),
                     include  (3),
                     exclude  (4)
                  }
          ACCESS  read-write
          STATUS  mandatory
          DESCRIPTION
                  "This parameter is used to filter routing updates
                  from trusted neighbors.  It allows control over
                  which RIP routes are received and stored in the 
                  routing table.  

                  If this is set to all (1), all routes reported by
                  trusted neighbors are received and stored in the
                  routing table.  The metric that will be stored in the routing
                  table in this case is specified by a3RipIpRcvPolAllMet.

                  If this is set to none (2), none of the routes
                  are received or stored in the routing table.

                  If this is set to include (3), routes to destinations
                  listed in a3RipIpRcvPolTable are received and
                  stored.

                  If this is set to exclude (4), all routes
                  are received and stored except those listed in 
                  a3RipIpRcvPolTable.

                  If this objects gets changed from include to exclude,
                  or from exclude to include, all existing entries will
                  be flushed from the table."
          REFERENCE
                  "NETBuilder II Ref. Guide, RIPIP Service Parameter:
                  ReceivePolicy."
          DEFVAL { all }
          ::= { a3RipIpCtlEntry 11 }

      a3RipIpStaPolCtl  OBJECT-TYPE
          SYNTAX  INTEGER {
                     all      (1),
                     none     (2),
                     include  (3),
                     exclude  (4)
                  }
          ACCESS  read-write
          STATUS  mandatory
          DESCRIPTION
                  "This parameter is used to filter the reporting
                  of static routes.  It allows control over
                  which static RIP routes are reported.

                  If this is set to all (1), all static routes 
                  are reported, provided those routes are allowed
                  to be reported by a3RipIpNetPolCtl/Table.  
                  The metric that will be stored in the routing
                  table in this case is specified by a3RipIpStaPolAllMet.

                  If this is set to none (2), none of the static 
                  routes are reported.

                  If this is set to include (3), static routes to 
                  destinations listed in a3RipIpStaPolTable are reported.

                  If this is set to exclude (4), all routes are reported 
                  except those listed in a3RipIpStaPolTable.

                  (note, in all these cases, Network Policy must be
                  passed before this policy is applied).

                  If this objects gets changed from include to exclude,
                  or from exclude to include, all existing entries will
                  be flushed from the table."
          REFERENCE
                  "NETBuilder II Ref. Guide, RIPIP Service Parameter:
                  StaticPolicy."
          DEFVAL { none }
          ::= { a3RipIpCtlEntry 12 }

--
--
--

      a3RipIpUnnAdvCtl  OBJECT-TYPE
          SYNTAX  INTEGER {
              subnetAdvUnn (1),
              netAdvUnn    (2)
          }
          ACCESS  read-write
          STATUS  mandatory
          DESCRIPTION
                  "This parameter specifies which routes are reported
                  by RIP updates sent over an unnumbered link.  
                  If this object is set to subnetAdvUnn (1), RIP explicitly
                  reports each subnetted route the system knows about.
                  If this object is set to netAdvUnn (2), RIP reports
                  only the IP network rather than each subnet." 
          DEFVAL { subnetAdvUnn }
          ::= { a3RipIpCtlEntry 13 }

      a3RipIpBcastCtl  OBJECT-TYPE
          SYNTAX  INTEGER {
              subnetBcast (1),
              all1sBcast  (2)
          }
          ACCESS  read-write
          STATUS  mandatory
          DESCRIPTION
                  "This object specifies the destination IP address
                  to which RIP updates are sent over this port.  If
                  this object is set to subnetBcast(1), the RIP
                  advertisement is sent using a directed broadcast
                  IP address as its destination (e.g., 129.213.255.255).

                  If this object has the value all1sBcast, the RIP
                  advertisement is sent using a limited broadcast
                  IP address as its destination (i.e., 255.255.255.255)."
          DEFVAL { subnetBcast }
          ::= { a3RipIpCtlEntry 14 }

      a3RipIpExtPolAllMet  OBJECT-TYPE
          SYNTAX  INTEGER (0..15)
          ACCESS  read-write
          STATUS  mandatory
          DESCRIPTION
                  "When a3RipIpExtPolCtl is set to all, this object specifies 
                  the metric used in RIP updates of routes learned via EGP or BGP.
                  If this object is set to zero, the metric is calculated from
                  the metric learned from EGP or BGP according to the formula defined
                  in the a3RipIpImpMetTable (ie, the entry corresponding to egp or bgp)." 
          DEFVAL { 0 }
          ::= { a3RipIpCtlEntry 15 }

      a3RipIpIntPolAllMet  OBJECT-TYPE
          SYNTAX  INTEGER (0..15)
          ACCESS  read-write
          STATUS  mandatory
          DESCRIPTION
                  "When a3RipIpIntPolCtl is set to all, this object specifies 
                  the metric used in RIP updates of routes learned via OSPF or IISIS.
                  If this object is set to zero, the metric is calculated from
                  the metric learned from OSPF or IISIS according to the formula defined
                  in the a3RipIpImpMetTable (ie, the entry corresponding to ospf or iisis)." 
          DEFVAL { 0 }
          ::= { a3RipIpCtlEntry 16 }

      a3RipIpNetPolAllMet  OBJECT-TYPE
          SYNTAX  INTEGER (0..15)
          ACCESS  read-write
          STATUS  mandatory
          DESCRIPTION
                  "When a3RipIpNetPolCtl is set to all, this object specifies 
                  the metric used in RIP updates of routes learned via RIP.
                  If this object is set to zero, the metric is taken directly from
                  the routing table."
          DEFVAL { 0 }
          ::= { a3RipIpCtlEntry 17 }

      a3RipIpRcvPolAllMet  OBJECT-TYPE
          SYNTAX  INTEGER (0..15)
          ACCESS  read-write
          STATUS  mandatory
          DESCRIPTION
                  "When a3RipIpRcvPolCtl is set to all, this object specifies 
                  the metric stored in the routing table when routing updates are
                  received via RIP (from trusted neighbors)." 
          DEFVAL { 0 }
          ::= { a3RipIpCtlEntry 18 }

      a3RipIpStaPolAllMet  OBJECT-TYPE
          SYNTAX  INTEGER (0..15)
          ACCESS  read-write
          STATUS  mandatory
          DESCRIPTION
                  "When a3RipIpStaPolCtl is set to all, this object specifies 
                  the metric used in RIP updates of static routes (ie, those
                  routes entered by a user).  If this object is set to zero, the 
                  metric is calculated from the metric specified by the static entry
                  according to the formula defined in the a3RipIpImpMetTable (ie, the 
                  entry corresponding to static)." 
          DEFVAL { 0 }
          ::= { a3RipIpCtlEntry 19 }

      a3RipIpDynNbrCtl  OBJECT-TYPE
          SYNTAX  INTEGER {
              dynamicNbr   (1),
              noDynamicNbr (2)
          } 
          ACCESS  read-write
          STATUS  mandatory
          DESCRIPTION
                  "When a3RipIpDynNbrCtl is set to dynamicNbr over FR or X.25,
		   and -RIP CONTrol is set to TALK, the neighbor list is learnt 
		   dynamically as InArp learn the IP addresses of the dlcis or 
		   as addresses are added to the ARP table. The user need not 
		   configure the -RIP Neighbor parameter manually. The 
		   dynamicNbr|NoDynamicNbr has no significance for non-FR and 
		   non-X.25 media. 

		   When a3RipIpDynNbrCtl is set to NodynamicNbr, any neighbor
		   in the neighbor list is deleted and the -RIP neighbor list 
		   from the config file is restored onto the neighbor list.	

		   When the -PORT owner parameter is changed from a non-FR and
		   non-X.25 owner to FR or X.25, the -RIP Neighbor list was
		   empty, and the -RIP CONTrol had the value TALK for this port,
		   the code automatically sets this object to DynamicNbr,
		   and fills up the neighbor list with the appropriate IP
		   addresses in the ARP table.
		   Note: only those neighbors of the same IP address network
		   number for this port is being copied from the ARP table
		   to this port's neighbor list.	

		   If the -PORT owner parameter is changed from a FR/X.25 to a 
		   non-FR and non-X25 media, and this object had the value 
		   DynamicNbr, the code automatically changes this object value
		   to NoDynamicNbr and restores the statically configured
		   neighbors from the config file into the -RIP neighbor list.

		   If a3RipIpDynNbrCtl has been set to dynamicNbr and the -PORT
		   owner is FR/X.25, no -RIP neighbor can be statically added."
          DEFVAL { noDynamicNbr }
          ::= { a3RipIpCtlEntry 20 }

      a3RipIpAggregateCtl  OBJECT-TYPE
          SYNTAX  INTEGER {
              aggregate   (1),
              noAggregate (2)
          }
          ACCESS  read-write
          STATUS  mandatory
          DESCRIPTION
                  "This parameter determines if RIP-IP aggregates
                   subnetworks with variable-length subnet masks
                   into one network."
          REFERENCE
                  "NETBuilder II Ref. Guide, RIPIP Service Parameter:
                  CONTol."
          DEFVAL { noAggregate }
          ::= { a3RipIpCtlEntry 21 }

      a3RipIpDeAggregateCtl  OBJECT-TYPE
          SYNTAX  INTEGER {
              deAggregate   (1),
              noDeAggregate (2)
          }
          ACCESS  read-write
          STATUS  mandatory
          DESCRIPTION
                  "This parameter determines if RIP-IP de-aggregate
                   a network into many subnetted network."
          REFERENCE
                  "NETBuilder II Ref. Guide, RIPIP Service Parameter:
                  CONTol."
          DEFVAL { noDeAggregate }
          ::= { a3RipIpCtlEntry 22 }

      a3RipIpNBMAmodeCtl  OBJECT-TYPE
          SYNTAX  INTEGER {
              fullMesh (1),
              nonMesh  (2)
          }
          ACCESS  read-write
          STATUS  mandatory
          DESCRIPTION
                  "This parameter determines if the underlying NBMA
                   network is full-mesh or non-mesh.  Partial-mesh
                   is treated as non-mesh.  When this object is set
                   to fullMesh(1), RIP-IP advertises routes based on
                   regular split-horizon. If nonMesh(2), RIP-Ip
                   advertises routes based on next-hop split-horizon.
                   This object is only meaningful when the underlying
                   interface is NBMA, (i.e. Frame Relay or X.25)"
          REFERENCE
                  "NETBuilder II Ref. Guide, RIPIP Service Parameter:
                  CONTol."
          DEFVAL { nonMesh }
          ::= { a3RipIpCtlEntry 23 }

--
-- The Exterior Policy Table
--

      a3RipIpExtPolTable  OBJECT-TYPE
          SYNTAX  SEQUENCE OF A3RipIpExtPolEntry
          ACCESS  not-accessible
          STATUS  mandatory
          DESCRIPTION
                  "The table contains a list of addresses learned via EGP
                  that are to be included or excluded from RIP reports."
          REFERENCE
                  "NETBuilder II Ref. Guide, RIPIP Service Parameter:
                  ExteriorPolicy."
          ::= { a3ComRipIp 3 }
     
      a3RipIpExtPolEntry  OBJECT-TYPE
          SYNTAX  A3RipIpExtPolEntry
          ACCESS  not-accessible
          STATUS  mandatory
          DESCRIPTION
                  "Each entry contains a single IP destination address.
                  This destination is either included or excluded from
                  RIP reports about routes learned via EGP.  Each entry 
                  also contains a metric to be used in the reports."
          REFERENCE
                  "NETBuilder II Ref. Guide, RIPIP Service Parameter:
                  ExteriorPolicy."
          INDEX { a3RipIpExtPolPort, a3RipIpExtPolAddr }
          ::= { a3RipIpExtPolTable 1 }

      A3RipIpExtPolEntry ::= 
          SEQUENCE {
             a3RipIpExtPolPort        INTEGER,
             a3RipIpExtPolAddr        IpAddress,
             a3RipIpExtPolMetric      INTEGER,
             a3RipIpExtPolStatus      RowStatus
          }

      a3RipIpExtPolPort  OBJECT-TYPE
          SYNTAX  INTEGER
          ACCESS  read-only
          STATUS  mandatory 
          DESCRIPTION
                  "This defines the port to which this entry applies."
          ::= { a3RipIpExtPolEntry 1 }

      a3RipIpExtPolAddr  OBJECT-TYPE
          SYNTAX  IpAddress
          ACCESS  read-only
          STATUS  mandatory
          DESCRIPTION
                  "This specifies a route destination learned via EGP
                  that is to be included or excluded (based on a3RipIpExtPolCtl)
                  from RIP reports."
          ::= { a3RipIpExtPolEntry 2 }

      a3RipIpExtPolMetric  OBJECT-TYPE
          SYNTAX  INTEGER (0..15)
          ACCESS  read-write
          STATUS  mandatory
          DESCRIPTION
                  "The metric that is to be used in RIP reports of this
                  route.  If a metric value in the range of 1 to 15 is
                  specified, the route, together with the specified metric,
                  is reported.  If the metric 0 is specified, the routing
                  table metric is calculated according to the formula
                  defined in a3RipIpImpMetTable (for either EGP or BGP).
                  (all fractions are rounded down to the next integer)"
          REFERENCE
                  "NETBuilder II Ref. Guide, RIPIP Service Parameter:
                  ExteriorPolicy."
          ::= { a3RipIpExtPolEntry 3 }

      a3RipIpExtPolStatus  OBJECT-TYPE
              SYNTAX  RowStatus
              ACCESS  read-write
              STATUS  mandatory
              DESCRIPTION
                   "This object is used to add and delete entries
                   in this table.  See the notes describing
                   RowStatus at the beginning of this MIB."
          ::= { a3RipIpExtPolEntry 4 }

--
-- The Interior Policy Table
--

      a3RipIpIntPolTable  OBJECT-TYPE
          SYNTAX  SEQUENCE OF A3RipIpIntPolEntry 
          ACCESS  not-accessible
          STATUS  mandatory
          DESCRIPTION
                  "The table contains a list of addresses learned via an IGP
                  other than RIP that are to be included or excluded from 
                  RIP reports."
          REFERENCE
                  "NETBuilder II Ref. Guide, RIPIP Service Parameter:
                  InteriorPolicy."
          ::= { a3ComRipIp 4 }
     
      a3RipIpIntPolEntry  OBJECT-TYPE
          SYNTAX  A3RipIpIntPolEntry
          ACCESS  not-accessible
          STATUS  mandatory
          DESCRIPTION
                  "Each entry contains a single IP destination address.
                  This destination is either included or excluded from
                  RIP reports.  Each entry also contains a metric to be 
                  used in the reports."
          REFERENCE
                  "NETBuilder II Ref. Guide, RIPIP Service Parameter:
                  InteriorPolicy."
          INDEX { a3RipIpIntPolPort, a3RipIpIntPolAddr }
          ::= { a3RipIpIntPolTable 1 }

      A3RipIpIntPolEntry ::= 
          SEQUENCE {
             a3RipIpIntPolPort        INTEGER,
             a3RipIpIntPolAddr        IpAddress,
             a3RipIpIntPolMetric      INTEGER,
             a3RipIpIntPolStatus      RowStatus
          }

      a3RipIpIntPolPort  OBJECT-TYPE
          SYNTAX  INTEGER
          ACCESS  read-only
          STATUS  mandatory 
          DESCRIPTION
                  "This defines the port to which this entry applies."
          ::= { a3RipIpIntPolEntry 1 }

      a3RipIpIntPolAddr  OBJECT-TYPE
          SYNTAX  IpAddress
          ACCESS  read-only
          STATUS  mandatory
          DESCRIPTION
                  "This specifies a route destination learned via an IGP 
                  that is to be included or excluded (based on a3RipIpIntPolCtl)
                  from RIP reports."
          ::= { a3RipIpIntPolEntry 2 }

      a3RipIpIntPolMetric  OBJECT-TYPE
          SYNTAX  INTEGER (0..15)
          ACCESS  read-write
          STATUS  mandatory
          DESCRIPTION
                  "The metric that is to be used in RIP reports of this
                  route.  It a metric value in the range of 1 to 15 is
                  specified, the route, together with the specified metric,
                  is reported.  If the metric 0 is specified, the routing
                  table metric is calculated according to the formula
                  defined in a3RipIpImpMetTable (for either OSPF or IISIS).
                  (all fractions are rounded down to the next integer)"
          REFERENCE
                  "NETBuilder II Ref. Guide, RIPIP Service Parameter:
                  InteriorPolicy."
          ::= { a3RipIpIntPolEntry 3 }

      a3RipIpIntPolStatus  OBJECT-TYPE
              SYNTAX  RowStatus
              ACCESS  read-write
              STATUS  mandatory
              DESCRIPTION
                   "This object is used to add and delete entries
                   in this table.  See the notes describing
                   RowStatus at the beginning of this MIB."
              ::= { a3RipIpIntPolEntry 4 }

--
-- The Network Policy Table
--

      a3RipIpNetPolTable  OBJECT-TYPE
          SYNTAX  SEQUENCE OF A3RipIpNetPolEntry
          ACCESS  not-accessible
          STATUS  mandatory
          DESCRIPTION
                  "The table contains a list of addresses that are to 
                  be included or excluded from RIP reports.  Note,
                  Network Policy overrides Static Policy, Interior
                  Policy, and Exterior Policy in deciding whether a
                  route is to be reported."
          REFERENCE
                  "NETBuilder II Ref. Guide, RIPIP Service Parameter:
                  NetworkPolicy."
          ::= { a3ComRipIp 5 }
     
      a3RipIpNetPolEntry  OBJECT-TYPE
          SYNTAX  A3RipIpNetPolEntry
          ACCESS  not-accessible
          STATUS  mandatory
          DESCRIPTION
                  "Each entry contains a single IP destination address.
                  This destination is either included or excluded from
                  RIP reports.  Each entry also contains a metric to be 
                  used in the reports."
          REFERENCE
                  "NETBuilder II Ref. Guide, RIPIP Service Parameter:
                  NetworkPolicy."
          INDEX { a3RipIpNetPolPort, a3RipIpNetPolAddr }
          ::= { a3RipIpNetPolTable 1 }

      A3RipIpNetPolEntry ::= 
          SEQUENCE {
             a3RipIpNetPolPort        INTEGER,
             a3RipIpNetPolAddr        IpAddress,
             a3RipIpNetPolMetric      INTEGER,
             a3RipIpNetPolStatus      RowStatus
          }

      a3RipIpNetPolPort  OBJECT-TYPE
          SYNTAX  INTEGER
          ACCESS  read-only
          STATUS  mandatory 
          DESCRIPTION
                  "This defines the port to which this entry applies."
          ::= { a3RipIpNetPolEntry 1 }

      a3RipIpNetPolAddr  OBJECT-TYPE
          SYNTAX  IpAddress
          ACCESS  read-only
          STATUS  mandatory
          DESCRIPTION
                  "This specifies a route destination that is to be 
                  included or excluded (based on a3RipIpNetPolCtl) from 
                  RIP reports."
          ::= { a3RipIpNetPolEntry 2 }

      a3RipIpNetPolMetric  OBJECT-TYPE
          SYNTAX  INTEGER (0..15)
          ACCESS  read-write
          STATUS  mandatory
          DESCRIPTION
                  "The metric that is to be used in RIP reports of this
                  route.  If a metric value in the range of 1 to 15 is
                  specified, the route, together with the specified metric,
                  is reported.  If the metric 0 is specified, the routing
                  table metric is used."
          REFERENCE
                  "NETBuilder II Ref. Guide, RIPIP Service Parameter:
                  NetworkPolicy."
          ::= { a3RipIpNetPolEntry 3 }

      a3RipIpNetPolStatus  OBJECT-TYPE
              SYNTAX  RowStatus
              ACCESS  read-write
              STATUS  mandatory
              DESCRIPTION
                   "This object is used to add and delete entries
                   in this table.  See the notes describing
                   RowStatus at the beginning of this MIB."
              ::= { a3RipIpNetPolEntry 4 }

--
-- The Receive Policy Table
--

      a3RipIpRcvPolTable  OBJECT-TYPE
          SYNTAX  SEQUENCE OF A3RipIpRcvPolEntry
          ACCESS  not-accessible
          STATUS  mandatory
          DESCRIPTION
                  "The table contains a list of addresses learned via trusted 
                  neighbors that are to be received and stored in the routing
                  table."
          REFERENCE
                  "NETBuilder II Ref. Guide, RIPIP Service Parameter:
                  ReceivePolicy."
          ::= { a3ComRipIp 6 }
     
      a3RipIpRcvPolEntry  OBJECT-TYPE
          SYNTAX  A3RipIpRcvPolEntry
          ACCESS  not-accessible
          STATUS  mandatory
          DESCRIPTION
                  "Each entry contains a single IP destination address.
                  This destination is either stored or not stored when
                  RIP reports from trusted neighbors are received.  Each 
                  entry also contains a metric to be used in the routing
                  table entry."
          REFERENCE
                  "NETBuilder II Ref. Guide, RIPIP Service Parameter:
                  ReceivePolicy."
          INDEX { a3RipIpRcvPolPort, a3RipIpRcvPolAddr }
          ::= { a3RipIpRcvPolTable 1 }

      A3RipIpRcvPolEntry ::= 
          SEQUENCE {
             a3RipIpRcvPolPort        INTEGER,
             a3RipIpRcvPolAddr        IpAddress,
             a3RipIpRcvPolMetric      INTEGER,
             a3RipIpRcvPolStatus      RowStatus
          }

      a3RipIpRcvPolPort  OBJECT-TYPE
          SYNTAX  INTEGER
          ACCESS  read-only
          STATUS  mandatory 
          DESCRIPTION
                  "This defines the port to which this entry applies."
          ::= { a3RipIpRcvPolEntry 1 }

      a3RipIpRcvPolAddr  OBJECT-TYPE
          SYNTAX  IpAddress
          ACCESS  read-only
          STATUS  mandatory
          DESCRIPTION
                  "This specifies a route destination that is to be stored 
                  or not stored (based on a3RipIpRcvPolCtl) when RIP reports
                  from trusted neighbors are received."
          ::= { a3RipIpRcvPolEntry 2 }

      a3RipIpRcvPolMetric  OBJECT-TYPE
          SYNTAX  INTEGER (0..15)
          ACCESS  read-write
          STATUS  mandatory
          DESCRIPTION
                  "The metric that is to be used in the routing table entry for 
                  this route.  It a metric value in the range of 1 to 15 is
                  specified, the route, together with the specified metric,
                  is stored.  If the metric 0 is specified, the routing
                  report metric is used."
          REFERENCE
                  "NETBuilder II Ref. Guide, RIPIP Service Parameter:
                  ReceivePolicy."
          ::= { a3RipIpRcvPolEntry 3 }

      a3RipIpRcvPolStatus  OBJECT-TYPE
              SYNTAX  RowStatus
              ACCESS  read-write
              STATUS  mandatory
              DESCRIPTION
                   "This object is used to add and delete entries
                   in this table.  See the notes describing
                   RowStatus at the beginning of this MIB."
              ::= { a3RipIpRcvPolEntry 4 }

--
-- The Static Policy Table
--

      a3RipIpStaPolTable  OBJECT-TYPE
          SYNTAX  SEQUENCE OF A3RipIpStaPolEntry
          ACCESS  not-accessible
          STATUS  mandatory
          DESCRIPTION
                  "The table contains a list of static addresses 
                  that are to be included or excluded from RIP reports."
          REFERENCE
                  "NETBuilder II Ref. Guide, RIPIP Service Parameter:
                  StaticPolicy."
          ::= { a3ComRipIp 7 }
     
      a3RipIpStaPolEntry  OBJECT-TYPE
          SYNTAX  A3RipIpStaPolEntry
          ACCESS  not-accessible
          STATUS  mandatory
          DESCRIPTION
                  "Each entry contains a single IP destination address
                  representing a static route.  This destination is either 
                  included or excluded from RIP reports.  Each entry also 
                  contains a metric to be used in the reports."
          REFERENCE
                  "NETBuilder II Ref. Guide, RIPIP Service Parameter:
                  StaticPolicy."
          INDEX { a3RipIpStaPolPort, a3RipIpStaPolAddr }
          ::= { a3RipIpStaPolTable 1 }

      A3RipIpStaPolEntry ::= 
          SEQUENCE {
             a3RipIpStaPolPort        INTEGER,
             a3RipIpStaPolAddr        IpAddress,
             a3RipIpStaPolMetric      INTEGER,
             a3RipIpStaPolStatus      RowStatus
          }

      a3RipIpStaPolPort  OBJECT-TYPE
          SYNTAX  INTEGER
          ACCESS  read-only
          STATUS  mandatory 
          DESCRIPTION
                  "This defines the port to which this entry applies."
          ::= { a3RipIpStaPolEntry 1 }

      a3RipIpStaPolAddr  OBJECT-TYPE
          SYNTAX  IpAddress
          ACCESS  read-only
          STATUS  mandatory
          DESCRIPTION
                  "This specifies a route destination learned statically
                  that is to be included or excluded (based on a3RipIpStaPolCtl)
                  from RIP reports."
          ::= { a3RipIpStaPolEntry 2 }

      a3RipIpStaPolMetric  OBJECT-TYPE
          SYNTAX  INTEGER (0..15)
          ACCESS  read-write
          STATUS  mandatory
          DESCRIPTION
                  "The metric that is to be used in RIP reports of this
                  route.  It a metric value in the range of 1 to 15 is
                  specified, the route, together with the specified metric,
                  is reported.  If the metric 0 is specified, the routing
                  table metric is calculated according to the formula
                  defined in a3RipIpImpMetTable (for static entries).
                  (all fractions are rounded down to the next integer)"
          REFERENCE
                  "NETBuilder II Ref. Guide, RIPIP Service Parameter:
                  StaticPolicy."
          ::= { a3RipIpStaPolEntry 3 }

      a3RipIpStaPolStatus  OBJECT-TYPE
              SYNTAX  RowStatus
              ACCESS  read-write
              STATUS  mandatory
              DESCRIPTION
                   "This object is used to add and delete entries
                   in this table.  See the notes describing
                   RowStatus at the beginning of this MIB."
              ::= { a3RipIpStaPolEntry 4 }

--
-- Neighbor Table
--

      a3RipIpNeighborTable  OBJECT-TYPE
          SYNTAX  SEQUENCE OF A3RipIpNeighborEntry
          ACCESS  not-accessible
          STATUS  mandatory
          DESCRIPTION
                  "This table contains a list of neighbor addresses that
                  RIP-IP uses to determine to which neighbors it should
                  send update packets.  RIP-IP neighbors are router
                  that share a common network and participate in the
                  RIP-IP protocol.  Each RIP-IP packet can be either broadcast
                  or addressed individually to each neighbor.  If no
                  neighbors are configured on the port, RIP broadcasts
                  update packets on the port."
          REFERENCE
                  "NETBuilder II Ref. Guide, RIPIP Service parameters,
                  Neighbor."
          ::= { a3ComRipIp 8 }

      a3RipIpNeighborEntry  OBJECT-TYPE
          SYNTAX  A3RipIpNeighborEntry
          ACCESS  not-accessible
          STATUS  mandatory
          DESCRIPTION
                  "Each entry contains information about a single
                  RIP-IP neighbor.  The information include the
                  neighbor's IP address as well as the port from
                  which it can be reached."
          INDEX { a3RipIpNeighborPort, a3RipIpNeighborAddr }
          ::= { a3RipIpNeighborTable 1 }

      A3RipIpNeighborEntry ::= 
          SEQUENCE {
              a3RipIpNeighborPort       INTEGER,
              a3RipIpNeighborAddr       IpAddress,
              a3RipIpNeighborStatus     RowStatus
          }

      a3RipIpNeighborPort  OBJECT-TYPE
          SYNTAX  INTEGER
          ACCESS  read-only
          STATUS  mandatory
          DESCRIPTION
                  "This indicates the port from which this neighbor
                  can be reached.  The neighbor must be attached to
                  the same network as this port."
          REFERENCE
                  "NETBuilder II Ref. Guide, RIPIP Service parameter:
                  Neighbor."
          ::= { a3RipIpNeighborEntry 1 } 

      a3RipIpNeighborAddr  OBJECT-TYPE
          SYNTAX  IpAddress
          ACCESS  read-only
          STATUS  mandatory
          DESCRIPTION
                  "This specifies the IP address of the RIP-IP neighbor."
          REFERENCE
                  "NETBuilder II Ref. Guide, RIPIP Service parameter:
                  Neighbor."
          ::= { a3RipIpNeighborEntry 2 } 
       
      a3RipIpNeighborStatus  OBJECT-TYPE
              SYNTAX  RowStatus
              ACCESS  read-write
              STATUS  mandatory
              DESCRIPTION
                   "This object is used to add and delete entries
                   in this table.  See the notes describing
                   RowStatus at the beginning of this MIB."
              ::= { a3RipIpNeighborEntry 3 }

--
-- Trusted Neighbor Table
--

      a3RipIpTrustedNbrTable  OBJECT-TYPE
          SYNTAX  SEQUENCE OF A3RipIpTrustedNbrEntry
          ACCESS  not-accessible
          STATUS  mandatory
          DESCRIPTION
                  "This table contains a list of RIP-IP neighbors 
                  from which RIP-IP accepts packets.  If this table
                  contains no entries for a particular port, RIP-IP
                  will accept all packets from that port."
          REFERENCE
                  "NETBuilder II Ref. Guide, RIPIP Service parameter:
                  TrustedNeighbor."
          ::= { a3ComRipIp 9 }

      a3RipIpTrustedNbrEntry  OBJECT-TYPE
          SYNTAX  A3RipIpTrustedNbrEntry
          ACCESS  not-accessible
          STATUS  mandatory
          DESCRIPTION
                  "Each entry identifies a trusted neighbor from which
                  RIP-IP will accept routing packets."
          INDEX { a3RipIpTrustedNbrPort, a3RipIpTrustedNbrAddr }
          ::= { a3RipIpTrustedNbrTable 1 }

      A3RipIpTrustedNbrEntry ::=
          SEQUENCE {
              a3RipIpTrustedNbrPort      INTEGER,
              a3RipIpTrustedNbrAddr      IpAddress,
              a3RipIpTrustedNbrStatus    RowStatus
          }

      a3RipIpTrustedNbrPort  OBJECT-TYPE
          SYNTAX  INTEGER
          ACCESS  read-only
          STATUS  mandatory
          DESCRIPTION
                  "This specifies the port for which this table entry
                  applies."
          ::= { a3RipIpTrustedNbrEntry 1 }

      a3RipIpTrustedNbrAddr  OBJECT-TYPE
          SYNTAX  IpAddress
          ACCESS  read-only
          STATUS  mandatory
          DESCRIPTION
                  "This identifies the IP address of a trusted neighbor
                  from which RIP-IP will accept (or not, depending on the value
                  of a3RipIpTrustedNbrCtl) routing packets."
          ::= { a3RipIpTrustedNbrEntry 2 }

      a3RipIpTrustedNbrStatus  OBJECT-TYPE
              SYNTAX  RowStatus
              ACCESS  read-write
              STATUS  mandatory
              DESCRIPTION
                   "This object is used to add and delete entries
                   in this table.  See the notes describing
                   RowStatus at the beginning of this MIB."
              ::= { a3RipIpTrustedNbrEntry 3 }

--
-- Import Metric Table.
--
--  This table specifies how metrics are to be reported when
-- routes learned via other protocols are reported by RIP.
-- Note, this only applies when these imported metrics are not 
-- explicitly specified (ie, when any of the a3RipIp*PolMetrics
-- are set to 0).  When these imported metrics are to be calculated
-- by the system, this table specifies the operations to be performed
-- on the imported metric before it is reported by RIP.
--
-- The operation is determined according to the following formula ...
--
--   RIP metric = (metric from native protocol / operand ) 
--   (if operation is divide)
--
--        - or -
--
--   RIP metric = (metric from native protocol * operand )
--   (if operation is multiply)
--
-- If the output of the operation results in a RIP metric of zero,
-- it is replaced with a metric of one.
--
--   
--

      a3RipIpImpMetTable  OBJECT-TYPE
          SYNTAX  SEQUENCE OF A3RipIpImpMetEntry
          ACCESS  not-accessible
          STATUS  mandatory
          DESCRIPTION
                  "This table specifies the operations to be performed
                  on metrics imported from other routing update protocols
                  before they are reported by RIP."
          REFERENCE
                  "NETBuilder II Ref. Guide, RIPIP Service parameter:
                  ImportMetric."
          ::= { a3ComRipIp 10 }

      a3RipIpImpMetEntry  OBJECT-TYPE
          SYNTAX  A3RipIpImpMetEntry
          ACCESS  not-accessible
          STATUS  mandatory
          DESCRIPTION
                  "Each entry specifies the operations to be performed
                  on the metric imported from a specific routing update
                  protocol before it is reported by RIP."
          INDEX { a3RipIpImpMetProtocol }
          ::= { a3RipIpImpMetTable 1 }

      A3RipIpImpMetEntry ::=
          SEQUENCE {
              a3RipIpImpMetProtocol      INTEGER,
              a3RipIpImpMetOperation     INTEGER,
              a3RipIpImpMetOperand       INTEGER
          }

      a3RipIpImpMetProtocol OBJECT-TYPE
          SYNTAX  INTEGER {
              ospf      (1),
              iisis     (2),
              egp       (3),
              bgp       (4),
              static    (5)
          }
          ACCESS  read-only
          STATUS  mandatory
          DESCRIPTION
              "This object identifies the routing update protocol
              from which metrics (and routes) are imported."
          ::= { a3RipIpImpMetEntry 1 }

      a3RipIpImpMetOperation OBJECT-TYPE
          SYNTAX  INTEGER {
              multiply (1),
              divide   (2)
          }
          ACCESS  read-write
          STATUS  mandatory
          DESCRIPTION
              "This specifies the operation to be performed on the
               native protocol metric before it is reported by RIP."
          DEFVAL { divide }
          ::= { a3RipIpImpMetEntry 2 }

      a3RipIpImpMetOperand OBJECT-TYPE
          SYNTAX  INTEGER (0..1073741823)
          ACCESS  read-write
          STATUS  mandatory
          DESCRIPTION
              "This specifies the operand of the operation specified
              by the corresponding instance of a3RipIpImpMetOperation.
              See the comments describing this table for more details.

              If this object has the value 0, the default formulas
              are used.  These are ...

                  for OSPF:  metric in routing table
                             -----------------------
                                      4096

                  for IISIS: metric in routing table
                             -----------------------
                                       64

                  for EGP:   metric in routing table
                             -----------------------
                                       16

                  for BGP:   metric in routing table
                             -----------------------
                                      1024

                  for static:  metric in routing table (unchanged)"
          ::= { a3RipIpImpMetEntry 3 }

END
