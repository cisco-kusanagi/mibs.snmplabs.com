ChrComPmDs3DS3-Interval-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComPmDs3				FROM  Chromatis-MIB
	chrComIfifIndex					FROM  ChrComIfifTable-MIB
	TruthValue				FROM  ChrTyp-MIB
	Gauge32				FROM  SNMPv2-SMI;

-- chrComPmDs3DS3-Interval Table

chrComPmDs3DS3-IntervalTable		OBJECT-TYPE
	SYNTAX		SEQUENCE OF ChrComPmDs3DS3-IntervalEntry
	MAX-ACCESS	not-accessible
	STATUS		current
	DESCRIPTION
	""
	::= { chrComPmDs3 12}

chrComPmDs3DS3-IntervalEntry		OBJECT-TYPE
	SYNTAX		ChrComPmDs3DS3-IntervalEntry
	MAX-ACCESS	not-accessible
	STATUS		current
	DESCRIPTION
	""
	INDEX  {  chrComIfifIndex, chrComPmDs3IntervalNumber }

--DEFAULT  get-function-async  MNIL_GetRoutine
--DEFAULT  set-function-async  MNIL_SetRoutine
--DEFAULT  next-function-async MNIL_NextRoutine
--DEFAULT  test-function-async MNIL_TestRoutine
--DEFAULT  cookie "DS3-Interval"
	::= { chrComPmDs3DS3-IntervalTable  1 }

ChrComPmDs3DS3-IntervalEntry  ::=
	SEQUENCE  {
	chrComPmDs3IntervalNumber		Unsigned32	(1..32),
	chrComPmDs3SuspectedInterval	TruthValue,
	chrComPmDs3ElapsedTime		Unsigned32	(0..4294967295),
	chrComPmDs3SuppressedIntrvls	Gauge32			(0..4294967295),
	chrComPmDs3LCV			Gauge32			(0..4294967295),
	chrComPmDs3LES			Gauge32			(0..4294967295),
	chrComPmDs3LSES			Gauge32			(0..4294967295),
	chrComPmDs3LOSS			Gauge32			(0..4294967295),
	chrComPmDs3PCV			Gauge32			(0..4294967295),
	chrComPmDs3CCV			Gauge32			(0..4294967295),
	chrComPmDs3PES			Gauge32			(0..4294967295),
	chrComPmDs3CES			Gauge32			(0..4294967295),
	chrComPmDs3PSES			Gauge32			(0..4294967295),
	chrComPmDs3CSES			Gauge32			(0..4294967295),
	chrComPmDs3SAS			Gauge32			(0..4294967295),
	chrComPmDs3AISS			Gauge32			(0..4294967295),
	chrComPmDs3UASP			Gauge32			(0..4294967295),
	chrComPmDs3UASCP			Gauge32			(0..4294967295),
	chrComPmDs3PSC			Gauge32			(0..4294967295),
	chrComPmDs3ESPLCP			Gauge32			(0..4294967295)
}

chrComPmDs3IntervalNumber 	OBJECT-TYPE
	SYNTAX		Unsigned32	(1..32)
	MAX-ACCESS 	read-only
	STATUS 		current
	DESCRIPTION
	""
	::= { chrComPmDs3DS3-IntervalEntry  1 }

chrComPmDs3SuspectedInterval 	OBJECT-TYPE
	SYNTAX		TruthValue
	MAX-ACCESS 	read-only
	STATUS 		current
	DESCRIPTION
	""
	::= { chrComPmDs3DS3-IntervalEntry  2 }

chrComPmDs3ElapsedTime 	OBJECT-TYPE
	SYNTAX		Unsigned32	(0..4294967295)
	MAX-ACCESS 	read-only
	STATUS 		current
	DESCRIPTION
	""
	::= { chrComPmDs3DS3-IntervalEntry  3 }

chrComPmDs3SuppressedIntrvls 	OBJECT-TYPE
	SYNTAX		Gauge32			(0..4294967295)
	MAX-ACCESS 	read-only
	STATUS 		current
	DESCRIPTION
	""
	::= { chrComPmDs3DS3-IntervalEntry  4 }

chrComPmDs3LCV 	OBJECT-TYPE
	SYNTAX		Gauge32			(0..4294967295)
	MAX-ACCESS 	read-only
	STATUS 		current
	DESCRIPTION
	""
	::= { chrComPmDs3DS3-IntervalEntry  5 }

chrComPmDs3LES 	OBJECT-TYPE
	SYNTAX		Gauge32			(0..4294967295)
	MAX-ACCESS 	read-only
	STATUS 		current
	DESCRIPTION
	""
	::= { chrComPmDs3DS3-IntervalEntry  6 }

chrComPmDs3LSES 	OBJECT-TYPE
	SYNTAX		Gauge32			(0..4294967295)
	MAX-ACCESS 	read-only
	STATUS 		current
	DESCRIPTION
	""
	::= { chrComPmDs3DS3-IntervalEntry  7 }

chrComPmDs3LOSS 	OBJECT-TYPE
	SYNTAX		Gauge32			(0..4294967295)
	MAX-ACCESS 	read-only
	STATUS 		current
	DESCRIPTION
	""
	::= { chrComPmDs3DS3-IntervalEntry  8 }

chrComPmDs3PCV 	OBJECT-TYPE
	SYNTAX		Gauge32			(0..4294967295)
	MAX-ACCESS 	read-only
	STATUS 		current
	DESCRIPTION
	""
	::= { chrComPmDs3DS3-IntervalEntry  9 }

chrComPmDs3CCV 	OBJECT-TYPE
	SYNTAX		Gauge32			(0..4294967295)
	MAX-ACCESS 	read-only
	STATUS 		current
	DESCRIPTION
	""
	::= { chrComPmDs3DS3-IntervalEntry  10 }

chrComPmDs3PES 	OBJECT-TYPE
	SYNTAX		Gauge32			(0..4294967295)
	MAX-ACCESS 	read-only
	STATUS 		current
	DESCRIPTION
	""
	::= { chrComPmDs3DS3-IntervalEntry  11 }

chrComPmDs3CES 	OBJECT-TYPE
	SYNTAX		Gauge32			(0..4294967295)
	MAX-ACCESS 	read-only
	STATUS 		current
	DESCRIPTION
	""
	::= { chrComPmDs3DS3-IntervalEntry  12 }

chrComPmDs3PSES 	OBJECT-TYPE
	SYNTAX		Gauge32			(0..4294967295)
	MAX-ACCESS 	read-only
	STATUS 		current
	DESCRIPTION
	""
	::= { chrComPmDs3DS3-IntervalEntry  13 }

chrComPmDs3CSES 	OBJECT-TYPE
	SYNTAX		Gauge32			(0..4294967295)
	MAX-ACCESS 	read-only
	STATUS 		current
	DESCRIPTION
	""
	::= { chrComPmDs3DS3-IntervalEntry  14 }

chrComPmDs3SAS 	OBJECT-TYPE
	SYNTAX		Gauge32			(0..4294967295)
	MAX-ACCESS 	read-only
	STATUS 		current
	DESCRIPTION
	""
	::= { chrComPmDs3DS3-IntervalEntry  15 }

chrComPmDs3AISS 	OBJECT-TYPE
	SYNTAX		Gauge32			(0..4294967295)
	MAX-ACCESS 	read-only
	STATUS 		current
	DESCRIPTION
	""
	::= { chrComPmDs3DS3-IntervalEntry  16 }

chrComPmDs3UASP 	OBJECT-TYPE
	SYNTAX		Gauge32			(0..4294967295)
	MAX-ACCESS 	read-only
	STATUS 		current
	DESCRIPTION
	""
	::= { chrComPmDs3DS3-IntervalEntry  17 }

chrComPmDs3UASCP 	OBJECT-TYPE
	SYNTAX		Gauge32			(0..4294967295)
	MAX-ACCESS 	read-only
	STATUS 		current
	DESCRIPTION
	""
	::= { chrComPmDs3DS3-IntervalEntry  18 }

chrComPmDs3PSC 	OBJECT-TYPE
	SYNTAX		Gauge32			(0..4294967295)
	MAX-ACCESS 	read-only
	STATUS 		current
	DESCRIPTION
	""
	::= { chrComPmDs3DS3-IntervalEntry  19 }

chrComPmDs3ESPLCP 	OBJECT-TYPE
	SYNTAX		Gauge32			(0..4294967295)
	MAX-ACCESS 	read-only
	STATUS 		current
	DESCRIPTION
	""
	::= { chrComPmDs3DS3-IntervalEntry  20 }


END
