-- Copyright 1998 General DataComm Inc., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.

-- Revision History
-- Version   Date	Name		Description
-- 1.00A     28-Apr-98  M. Cyr          Initial Revision


HDSLGT1030-MIB DEFINITIONS ::= BEGIN

IMPORTS
	OBJECT-TYPE			FROM RFC-1212
	DisplayString			FROM RFC1213-MIB
	hdslGT1030                      FROM GDCHDSL-MIB;

hdslGT1030System         OBJECT IDENTIFIER ::= { hdslGT1030 1 }
hdslGT1030Version        OBJECT IDENTIFIER ::= { hdslGT1030System 1 }

-- ***************************************************************************
-- The interfaces are defined as follows:
--	Unit	0
--	DTE	1
--	Loop1	2
-- ***************************************************************************

gdcGT1030SystemMIBversion OBJECT-TYPE
     	SYNTAX DisplayString (SIZE (5))
     	ACCESS read-only
     	STATUS mandatory
     	DESCRIPTION
     		"Identifies the version of the MIB. The format of the version
     		is x.yzT, where 'x' identifies the major revision number, 'y'
     		identifies the minor revision number, 'z' identifies the
     		typographical revision, and T identifies the test revision.
     		Acceptable values for the individual revision components are
     		as follows:
 
     		x: 1 - 9
     		y: 0 - 9
     		z: 0 - 9
     		T: A - Z
 
     		Upon formal release, no designation for the test revision will
     		be present."
     	::= { hdslGT1030Version 1 }

--********************************************************************
-- GDC Hdsl Alarm Object Identifier Definitions
--********************************************************************
hdslGT1030Alarms          OBJECT IDENTIFIER ::= { hdslGT1030 2 }

hdslGT1030NoResponseAlm		OBJECT IDENTIFIER ::= { hdslGT1030Alarms 1 }
hdslGT1030DiagRxErrAlm		OBJECT IDENTIFIER ::= { hdslGT1030Alarms 2 }
hdslGT1030PowerUpAlm		OBJECT IDENTIFIER ::= { hdslGT1030Alarms 3 }
hdslGT1030UnitFailure	        OBJECT IDENTIFIER ::= { hdslGT1030Alarms 4 }
hdslGT1030ChecksumCorrupt       OBJECT IDENTIFIER ::= { hdslGT1030Alarms 5 }
hdslGT1030LossofSignal		OBJECT IDENTIFIER ::= { hdslGT1030Alarms 6 }
hdslGT1030UnavailableSec	OBJECT IDENTIFIER ::= { hdslGT1030Alarms 7 }
hdslGT1030ErrorSec		OBJECT IDENTIFIER ::= { hdslGT1030Alarms 8 }
hdslGT1030LossofSyncWord	OBJECT IDENTIFIER ::= { hdslGT1030Alarms 9 }
hdslGT1030MajorBER 		OBJECT IDENTIFIER ::= { hdslGT1030Alarms 10 }
hdslGT1030MinorBER 		OBJECT IDENTIFIER ::= { hdslGT1030Alarms 11 }


-- ALARM			Maskable	Valid Interfaces
--===============================================================
--hdslNoResponseAlm		No		Unit
--hdslDiagRxErrAlm              No              Unit
--hdslPowerUpAlm		No		Unit
--hdslUnitFailure               No              Unit
--hdslChecksumCorrupt           No              Unit
--hdslLossofSignal		Yes		L1 
--hdslUnavailableSec		Yes		L1
--hdslErrorSec			Yes		L1
--hdslLossofSyncWord		Yes		L1
--hdslGT1030MajorBER		Yes		L1
--hdslGT1030MinorBER		Yes		L1

END
