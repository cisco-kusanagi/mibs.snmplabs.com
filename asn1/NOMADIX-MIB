--
--
--       NOMADIX Enterprise MIB
--
--
--    Copyright (c) 1999 - 2005 Nomadix, Inc.
--    All rights reserved.
--



NOMADIX-MIB DEFINITIONS ::= BEGIN

  IMPORTS
     enterprises,
     Counter32,
     Integer32,
     IpAddress,
     OBJECT-TYPE,
--      OBJECT-IDENTITY,
     NOTIFICATION-TYPE,
     MODULE-IDENTITY
         FROM SNMPv2-SMI

     MacAddress, RowStatus
         FROM SNMPv2-TC;

  --
  -- Nomadix enterprise module definition
  --

     nomadix MODULE-IDENTITY
          LAST-UPDATED "200501270000Z"
          ORGANIZATION "Nomadix, Inc"
          CONTACT-INFO "Nomadix, Inc
                        1100 Business Center Circle
                        Suite 100
                        Newbury Park, CA 91320
                        +1 818 597 1500
                        info@nomadix.com"
          DESCRIPTION
          "MIB definition for Nomadix AG-2000w wireless gateway."
          ::= {  enterprises 3309 }


  DisplayString ::= OCTET STRING


--
-- Groups in the Nomadix Enterprise mib
--

     products       OBJECT IDENTIFIER ::= { nomadix 1 }
     ag             OBJECT IDENTIFIER ::= { products 3 }

--
-- AG Modules
--

     aaa                  OBJECT IDENTIFIER ::= { ag 2 }
     accessControl        OBJECT IDENTIFIER ::= { ag 4 }
     bandwidthManagement  OBJECT IDENTIFIER ::= { ag 5 }
     billRecMirror        OBJECT IDENTIFIER ::= { ag 6 }
--    cms                  OBJECT IDENTIFIER ::= { ag 7 }
     dat                  OBJECT IDENTIFIER ::= { ag 8 }
     dhcp                 OBJECT IDENTIFIER ::= { ag 10 }
     dns                  OBJECT IDENTIFIER ::= { ag 12 }
     greTunneling         OBJECT IDENTIFIER ::= { ag 13 }
     hpr                  OBJECT IDENTIFIER ::= { ag 14 }
     icc                  OBJECT IDENTIFIER ::= { ag 16 }
     inat                 OBJECT IDENTIFIER ::= { ag 17 }
     licenseKeys          OBJECT IDENTIFIER ::= { ag 18 }
     location             OBJECT IDENTIFIER ::= { ag 19 }
--    mrs                  OBJECT IDENTIFIER ::= { ag 22 }
     passthrough          OBJECT IDENTIFIER ::= { ag 24 }
--    pms                  OBJECT IDENTIFIER ::= { ag 26 }
     portLoc              OBJECT IDENTIFIER ::= { ag 28 }
     smtp                 OBJECT IDENTIFIER ::= { ag 30 }
     snmpagent            OBJECT IDENTIFIER ::= { ag 32 }
     subsettings          OBJECT IDENTIFIER ::= { ag 33 }
     subnets              OBJECT IDENTIFIER ::= { ag 34 }
     system               OBJECT IDENTIFIER ::= { ag 35 }
     time                 OBJECT IDENTIFIER ::= { ag 36 }
     urlFiltering         OBJECT IDENTIFIER ::= { ag 37 }
     radiusProxy          OBJECT IDENTIFIER ::= { ag 38 }
     realmBasedRouter     OBJECT IDENTIFIER ::= { ag 39 }
     sessionlimit         OBJECT IDENTIFIER ::= { ag 40 }
     macFiltering         OBJECT IDENTIFIER ::= { ag 41 }
     tunneling            OBJECT IDENTIFIER ::= { ag 42 }
     wireless             OBJECT IDENTIFIER ::= { ag 43 }
     pppoeClient          OBJECT IDENTIFIER ::= { ag 44 }
     dyndns               OBJECT IDENTIFIER ::= { ag 50 }
     localWeb             OBJECT IDENTIFIER ::= { ag 52 }
     ipsec                OBJECT IDENTIFIER ::= { ag 54 }
     ndxTraps             OBJECT IDENTIFIER ::= { ag 0  }

  ----------------------------------------------------------------------
  --  Begin AAA MIB
  ----------------------------------------------------------------------
  -- AAA ON
   aaaOn OBJECT-TYPE
     SYNTAX         INTEGER { disabled(0), enabled(1) }
     MAX-ACCESS     read-write
     STATUS         current
     DESCRIPTION
          "Set to 1 to enable AAA, 0 to disable."
     ::= { aaa 1 }

  -- AAA XML ON
     aaaXmlOn OBJECT-TYPE
     SYNTAX         INTEGER { disabled(0), enabled(1) }
     MAX-ACCESS     read-write
     STATUS         current
     DESCRIPTION
        "Set to 1 to enable AAA XML Interface, 0 to disable.
        Note: If trying to set this value returns an error, please check to see if you have a valid license for this feature."
     ::= { aaa 2 }

  -- AAA XML SENDER 1 IP
     aaaXmlSender1Ip OBJECT-TYPE
     SYNTAX      IpAddress
     MAX-ACCESS      read-write
     STATUS      current
     DESCRIPTION
        "IP address of the first server that will send/process XML commands for
         subscriber management."
     ::= { aaa 3 }

  -- AAA XML SENDER 2 IP
     aaaXmlSender2Ip OBJECT-TYPE
     SYNTAX      IpAddress
     MAX-ACCESS      read-write
     STATUS      current
     DESCRIPTION
        "IP address of the second server that will send/process XML commands for
         subscriber management."
     ::= { aaa 22 }

  -- AAA Message New User Terms of Agreement On.
     aaaMessageNewUserTermsOn   OBJECT-TYPE
     SYNTAX         INTEGER { disabled(0), enabled(1) }
     MAX-ACCESS     read-write
     STATUS         current
     DESCRIPTION
        "Set to 1 to enable New User Terms of Agreement, 0 to disable."
     ::= { aaa 23 }


  -- AAA Message New User Terms of Agreement.
     aaaMessageNewUserTerms OBJECT-TYPE
     SYNTAX         DisplayString(SIZE(400))
     MAX-ACCESS     read-write
     STATUS         current
     DESCRIPTION
        "New User Terms of Agreement."
     ::= { aaa 24 }

  -- AAA PRINT BILLING COMMAND ON
           aaaPrintBillingCommandOn   OBJECT-TYPE
        SYNTAX         INTEGER { disabled(0), enabled(1) }
     MAX-ACCESS         read-write
     STATUS         current
     DESCRIPTION
        "Set to 1 to enable Print Billing Command, 0 to disable."
     ::= { aaa 4 }

  -- AAA PASSTHROUGH PORT ON
           aaaPassthroughPortOn    OBJECT-TYPE
        SYNTAX      INTEGER { disabled(0), enabled(1) }
     MAX-ACCESS     read-write
     STATUS         current
     DESCRIPTION
        "Set to 1 to enable AAA Passthrough Port, 0 to disable."
     ::= { aaa 5 }

  -- AAA PASSTHROUGH PORT NUMBER
     aaaPassthroughPortNumber   OBJECT-TYPE
     SYNTAX         Integer32
     MAX-ACCESS     read-write
     STATUS         current
     DESCRIPTION
        "The port number which is set as passthrough.  Must be
        different from 80, 2111 and 1111."
     ::= { aaa 6 }

  -- AAA 802.1X ON
           aaaDot1xOn  OBJECT-TYPE
        SYNTAX      INTEGER { disabled(0), enabled(1) }
     MAX-ACCESS     read-write
     STATUS         current
     DESCRIPTION
        "Set to 1 to enable AAA 802.1x Authentication, 0 to disable.
        Note: 802.1x requires that AAA, RADIUS Authentication and WEP be enabled."
     ::= { aaa 7 }

  -- AAA OS ENCODE ON
     aaaOSencodingOn      OBJECT-TYPE
     SYNTAX         INTEGER { disabled(0), enabled(1) }
     MAX-ACCESS     read-write
     STATUS         current
     DESCRIPTION
        "Set to 1 to enable OS parameter encoding when using Portal Page and EWS, 0 to disable."
     ::= { aaa 8 }

  -- AAA AUTH MODE
     aaaAuthMode OBJECT-TYPE
     SYNTAX         INTEGER { internalAuthorization(0), externalAuthorization(1) }
     MAX-ACCESS     read-write
     STATUS         current
     DESCRIPTION
        "Set to 0 to use Internal Authorization mode, 1 to use External Authorization mode.
        Note: If trying to set this value returns an error, please check to see if you have a valid license for this feature."
     ::= { aaa 9 }

  --------------------
  -- AAA INTERNAL AUTH
  --------------------
     aaaInternalAuth   OBJECT IDENTIFIER ::= { aaa 10 }
     -- AAA SSL SUPPORT ON
        aaaSslOn OBJECT-TYPE
        SYNTAX         INTEGER { disabled(0), enabled(1) }
        MAX-ACCESS     read-write
        STATUS         current
        DESCRIPTION
           "Set to 1 to enable SSL support, 0 to disable.
           Please reboot if you change this value."
        ::= { aaaInternalAuth 1 }
     -- AAA SSL SUPPORT CERTIFICATE DNS NAME
        aaaSslHostName OBJECT-TYPE
        SYNTAX      DisplayString(SIZE(0..64))
        MAX-ACCESS  read-write
        STATUS      current
        DESCRIPTION
           "Specify the certificate DNS name used by SSL"
        ::= { aaaInternalAuth 2 }
     -- AAA PORTAL PAGE ON
        aaaPortalPageOn OBJECT-TYPE
        SYNTAX      INTEGER { disabled(0), enabled(1) }
        MAX-ACCESS  read-write
        STATUS      current
        DESCRIPTION
           "Set to 1 to enable portal page redirection, 0 to disable."
        ::= { aaaInternalAuth 3 }
     -- AAA PORTAL PAGE URL
        aaaPortalPageUrl OBJECT-TYPE
        SYNTAX      DisplayString(SIZE(0..237))
        MAX-ACCESS  read-write
        STATUS      current
        DESCRIPTION
           "Specify the URL of the portal page web server"
        ::= { aaaInternalAuth 4 }
     -- AAA USERNAME ON
        aaaUsernameOn OBJECT-TYPE
        SYNTAX         INTEGER { disabled(0), enabled(1) }
        MAX-ACCESS     read-write
        STATUS         current
        DESCRIPTION
           "Set to 1 to enable username/password, 0 to disable."
        ::= { aaaInternalAuth 5 }
     -- AAA NEW SUBSCRIBER ON
        aaaNewSubscriberOn OBJECT-TYPE
        SYNTAX         INTEGER { disabled(0), enabled(1) }
        MAX-ACCESS     read-write
        STATUS         current
        DESCRIPTION
           "Set to 1 to allow new subscribers, 0 to disable."
        ::= { aaaInternalAuth 6 }
     -- AAA RELOGIN AFTER TIMEOUT ON
        aaaReloginOn OBJECT-TYPE
        SYNTAX         INTEGER { disabled(0), enabled(1) }
        MAX-ACCESS     read-write
        STATUS         current
        DESCRIPTION
           "Set to 1 to make subscribers relogin after a timeout,
           0 to disable."
        ::= { aaaInternalAuth 7 }
     -- AAA CREDIT CARD ON
        aaaCreditCardOn OBJECT-TYPE
        SYNTAX         INTEGER { disabled(0), enabled(1) }
        MAX-ACCESS     read-write
        STATUS         current
        DESCRIPTION
           "Set to 1 to enable credit card, 0 to disable.
           Note: If trying to set this value returns an error, please check to see if you have a valid license for this feature."
        ::= { aaaInternalAuth 8 }
     -- AAA CREDIT CARD URL
        aaaCreditCardUrl OBJECT-TYPE
        SYNTAX      DisplayString(SIZE(0..237))
        MAX-ACCESS  read-write
        STATUS      current
        DESCRIPTION
           "Specify the URL of the Credit Card Service Server"
        ::= { aaaInternalAuth 9 }
     -- AAA CREDIT CARD IP
        aaaCreditCardIp OBJECT-TYPE
        SYNTAX      IpAddress
        MAX-ACCESS  read-write
        STATUS      current
        DESCRIPTION
           "The IP address of the Credit Card Service Server"
        ::= { aaaInternalAuth 10 }
     -- AAA MERCHANT ID
        aaaMerchantId OBJECT-TYPE
        SYNTAX      DisplayString(SIZE(0..32))
        MAX-ACCESS  read-write
        STATUS      current
        DESCRIPTION
           "Specify Merchant ID used for Credit Card Service"
        ::= { aaaInternalAuth 11 }
     -- AAA SMART CLIENT SUPPORT ON
        aaaSmartClientOn OBJECT-TYPE
        SYNTAX      INTEGER { disabled(0), enabled(1) }
        MAX-ACCESS  read-write
        STATUS      current
        DESCRIPTION
           "Set to 1 to enable Smart client support, 0 to disable.
           Note: If trying to set this value returns an error, please check to see if you have a valid license for this feature."
        ::= { aaaInternalAuth 12 }
     -- AAA PORTAL PARAMETER PASSING
        aaaPortalParameterPassing OBJECT-TYPE
        SYNTAX         INTEGER { disabled(0), enabled(1) }
        MAX-ACCESS     read-write
        STATUS         current
        DESCRIPTION
           "Set to 1 to enable portal parameter passing, 0 to disable."
        ::= { aaaInternalAuth 13 }
     -- AAA PORTAL XML POST URL
        aaaPortalPostUrl OBJECT-TYPE
        SYNTAX      DisplayString(SIZE(0..237))
        MAX-ACCESS  read-write
        STATUS      current
        DESCRIPTION
           "Specify the URL of the portal XML POST URL"
        ::= { aaaInternalAuth 14 }
     -- AAA PORTAL XML POST Port
        aaaPortalXMLPort OBJECT-TYPE
        SYNTAX         Integer32
        MAX-ACCESS     read-write
        STATUS         current
        DESCRIPTION
           "Portal XML POST port number."
        ::= { aaaInternalAuth 15 }

     aaaSupportGISClients OBJECT-TYPE
       SYNTAX        INTEGER { disabled(0), enabled(1) }
       MAX-ACCESS    read-write
       STATUS        current
       DESCRIPTION
           "Set to 1 to enable support of GIS clients, 0 to disable."
       ::= { aaaInternalAuth 16 }

     aaaIWSLoginPageBlocking    OBJECT-TYPE
       SYNTAX        INTEGER { enabled(1), disabled(2) }
       MAX-ACCESS    read-write
       STATUS        current
       DESCRIPTION
           "Set to 1 to enable blocking of Internal Web Server Login Page , 2 to disable."
       ::= { aaaInternalAuth 20 }

     aaaCreditCardServerTypeSelection OBJECT-TYPE
       SYNTAX     INTEGER {
                      chainfusion(1),
                      authorize-net(2)
                      }
       MAX-ACCESS  read-write
       STATUS      current
       DESCRIPTION
         "Setting this value to (1) will select Chainfusion.
          Setting this value to (2) will select Authorize.net."
       ::= { aaaInternalAuth 21 }

     aaaChainfusionCCTransTime OBJECT-TYPE
       SYNTAX         Integer32
       MAX-ACCESS     read-write
       STATUS         current
       DESCRIPTION
          "The maximum amount of time allowed for a Chainfusion credit card
          transaction to complete (in minutes)."
       ::= { aaaInternalAuth 22 }

  -- AAA EXTERNAL AUTH
  --------------------
     aaaExternalAuth   OBJECT IDENTIFIER ::= { aaa 11 }
     -- AAA SECRET KEY
        aaaSecretKey OBJECT-TYPE
        SYNTAX      DisplayString(SIZE(0..32))
        MAX-ACCESS  read-write
        STATUS      current
        DESCRIPTION
           "Specify the secret key shared by the NSE and the external server"
        ::= { aaaExternalAuth 1 }
     -- AAA EXTERNAL AUTH IP address
        aaaExternalIPAddress OBJECT-TYPE
        SYNTAX      IpAddress
        MAX-ACCESS  read-write
        STATUS      current
        DESCRIPTION
           "Specify external authorization server IP Address."
        ::= { aaaExternalAuth 2 }
     -- AAA AUTHORIZATION URL
        aaaAuthorizationUrl OBJECT-TYPE
        SYNTAX      DisplayString(SIZE(0..237))
        MAX-ACCESS  read-write
        STATUS      current
        DESCRIPTION
           "Specify external authorization server URL."
        ::= { aaaExternalAuth 3 }

  --------------------
  -- AAA LOGGING
  --------------------

   -- AAA LOGGING ON
     aaaLoggingOn OBJECT-TYPE
     SYNTAX      INTEGER { disabled(0), enabled (1) }
     MAX-ACCESS  read-write
     STATUS      current
     DESCRIPTION
        "Setting this value to (1) will enable logging (via standard
        SYSLOG) of AAA messages.  Setting this value to (0) will
        disable AAA logging."
        ::= { aaa 12 }

   --
   -- AAA LOG NUMBER
   --
     aaaLogNumber   OBJECT-TYPE
     SYNTAX      Integer32(0..7)
     MAX-ACCESS  read-write
     STATUS      current
     DESCRIPTION
        "The log number (0-7 of standard SYSLOG) for AAA logging."
        ::= { aaa 13 }

   --
  -- AAA LOG FILTER
  --
      aaaLogFilter OBJECT-TYPE
      SYNTAX         INTEGER {emergency(0), alert(1), critical(2), error(3),
              warning(4), notice(5), info(6), debug(7) }
      MAX-ACCESS     read-write
      STATUS         current
      DESCRIPTION
    "Select the filter level for AAA Logs
     Available settings: Emergency(0), Alert(1), Critical(2), Error(3),
               Warning(4), Notice(5), Info(6), Debug(7)"
      ::= { aaa 20}


   --
   -- AAA LOG SERVER IP
   --
     aaaLogServerIp OBJECT-TYPE
     SYNTAX      IpAddress
     MAX-ACCESS      read-write
     STATUS      current
     DESCRIPTION
        "IP address of the SYSLOG server to receive AAA messages."
     ::= { aaa 14 }


   -- AAA LOG SAVE TO FILE ON
     aaaSaveToFile OBJECT-TYPE
     SYNTAX      INTEGER { disabled(0), enabled (1) }
     MAX-ACCESS  read-write
     STATUS      current
     DESCRIPTION
        "Setting this value to (1) will enable saving of AAA logs
        to file.  Setting this value to (0) will disable storing of
        AAA logs in a file."
        ::= { aaa 21 }


  --------------------
  -- AAA BILLING OPTION
  --------------------
     aaaBillingOption  OBJECT IDENTIFIER ::= { aaa 15 }
     -- AAA BILLOPT INTRO MSG
        aaaBilloptIntroMsg OBJECT-TYPE
        SYNTAX      DisplayString(SIZE(0..218))
        MAX-ACCESS      read-write
        STATUS      current
        DESCRIPTION
           "Specify the billing provisioning page intro message"
        ::= { aaaBillingOption 1 }
     -- AAA BILLOPT OFFER MSG
        aaaBilloptOfferMsg OBJECT-TYPE
        SYNTAX      DisplayString(SIZE(0..218))
        MAX-ACCESS      read-write
        STATUS      current
        DESCRIPTION
           "Specify the billing provisioning page offer message"
        ::= { aaaBillingOption 2 }
     -- AAA BILLOPT POLICY MSG
        aaaBilloptPolicyMsg OBJECT-TYPE
        SYNTAX      DisplayString(SIZE(0..218))
        MAX-ACCESS      read-write
        STATUS      current
        DESCRIPTION
           "Specify the billing provisioning page policy message"
        ::= { aaaBillingOption 3 }
     -- AAA BILLOPT MIN TIME UNIT MINUTES
        aaaBilloptMinTimeUnitMinute OBJECT-TYPE
        SYNTAX         Integer32
        MAX-ACCESS     read-write
        STATUS         current
        DESCRIPTION
           "Set the minimum unit (minutes) of time the subscriber can purchase"
        ::= { aaaBillingOption 5 }
     -- AAA BILLOPT MIN TIME UNIT HOURS
        aaaBilloptMinTimeUnitHour OBJECT-TYPE
        SYNTAX         Integer32
        MAX-ACCESS     read-write
        STATUS         current
        DESCRIPTION
           "Set the minimum unit (hours) of time the subscriber can purchase"
        ::= { aaaBillingOption 6 }
     -- AAA BILLOPT MIN TIME UNIT DAYS
        aaaBilloptMinTimeUnitDay OBJECT-TYPE
        SYNTAX         Integer32
        MAX-ACCESS     read-write
        STATUS         current
        DESCRIPTION
           "Set the minimum unit (days) of time the subscriber can purchase"
        ::= { aaaBillingOption 7 }
     -- AAA BILLOPT MIN TIME UNIT WEEKS
        aaaBilloptMinTimeUnitWeek OBJECT-TYPE
        SYNTAX         Integer32
        MAX-ACCESS     read-write
        STATUS         current
        DESCRIPTION
           "Set the minimum unit (weeks) of time the subscriber can purchase"
        ::= { aaaBillingOption 8 }
     -- AAA BILLOPT MIN TIME UNIT MONTHS
        aaaBilloptMinTimeUnitMonth OBJECT-TYPE
        SYNTAX         Integer32
        MAX-ACCESS     read-write
        STATUS         current
        DESCRIPTION
           "Set the minimum unit (months) of time the subscriber can purchase"
        ::= { aaaBillingOption 9 }
     -- AAA BILLOPT MAX TIME UNIT MINUTES
        aaaBilloptMaxTimeUnitMinute OBJECT-TYPE
        SYNTAX         Integer32
        MAX-ACCESS     read-write
        STATUS         current
        DESCRIPTION
           "Set the maximum unit (minutes) of time the subscriber can purchase"
        ::= { aaaBillingOption 10 }
     -- AAA BILLOPT MAX TIME UNIT HOURS
        aaaBilloptMaxTimeUnitHour OBJECT-TYPE
        SYNTAX         Integer32
        MAX-ACCESS     read-write
        STATUS         current
        DESCRIPTION
           "Set the maximum unit (hours) of time the subscriber can purchase"
        ::= { aaaBillingOption 11 }
     -- AAA BILLOPT MAX TIME UNIT DAYS
        aaaBilloptMaxTimeUnitDay OBJECT-TYPE
        SYNTAX         Integer32
        MAX-ACCESS     read-write
        STATUS         current
        DESCRIPTION
           "Set the maximum unit (days) of time the subscriber can purchase"
        ::= { aaaBillingOption 12 }
     -- AAA BILLOPT MAX TIME UNIT WEEKS
        aaaBilloptMaxTimeUnitWeek OBJECT-TYPE
        SYNTAX         Integer32
        MAX-ACCESS     read-write
        STATUS         current
        DESCRIPTION
           "Set the maximum unit (weeks) of time the subscriber can purchase"
        ::= { aaaBillingOption 13 }
     -- AAA BILLOPT MAX TIME UNIT MONTHS
        aaaBilloptMaxTimeUnitMonth OBJECT-TYPE
        SYNTAX         Integer32
        MAX-ACCESS     read-write
        STATUS         current
        DESCRIPTION
           "Set the maximum unit (months) of time the subscriber can purchase"
        ::= { aaaBillingOption 14 }
     -- AAA BILLOPT FREE ACCESS TIME
        aaaBilloptFreeAccessTime OBJECT-TYPE
        SYNTAX         Integer32
        MAX-ACCESS     read-write
        STATUS         current
        DESCRIPTION
           "Set default free access time for zero $ billing."
        ::= { aaaBillingOption 15 }
     -- AAA BILLOPT MAX SUB LIFETIME
        aaaBilloptMaxSubLifetime OBJECT-TYPE
        SYNTAX         Integer32
        MAX-ACCESS     read-write
        STATUS         current
        DESCRIPTION
           "Set maximum subscriber lifetime for zero $ billing."
        ::= { aaaBillingOption 16 }
     -- AAA TAX RATE
        aaaTaxRate OBJECT-TYPE
        SYNTAX         DisplayString(SIZE(1..5))
        MAX-ACCESS     read-write
        STATUS         current
        DESCRIPTION
           "Tax rate, which is to be assessed on all amounts billed by the access gateway. The rate may range from 0 (which means no tax) to 99.99 percent"
        ::= { aaaBillingOption 18 }
     -- AAA BILLOPT PLANS
        aaaBillingPlans OBJECT IDENTIFIER ::= { aaaBillingOption 19 }
           aaaBillingPlan0 OBJECT IDENTIFIER ::= { aaaBillingPlans 1 }
           aaaBillingPlan1 OBJECT IDENTIFIER ::= { aaaBillingPlans 2 }
           aaaBillingPlan2 OBJECT IDENTIFIER ::= { aaaBillingPlans 3 }
           aaaBillingPlan3 OBJECT IDENTIFIER ::= { aaaBillingPlans 4 }
           aaaBillingPlan4 OBJECT IDENTIFIER ::= { aaaBillingPlans 5 }
           aaaBillingPlan5 OBJECT IDENTIFIER ::= { aaaBillingPlans 6 }
        -- BILLING PLAN 0
           -- BILLING PLAN 0 ON
              aaaBillingPlanOn0 OBJECT-TYPE
              SYNTAX         INTEGER { disabled(0), enabled(1) }
              MAX-ACCESS     read-write
              STATUS         current
              DESCRIPTION
                 "Set to 1 to enable billing Plan 0, 0 to disable"
              ::= { aaaBillingPlan0 1 }
           -- BILLING PLAN 0 ASSIGNED
              aaaBillingPlanAssigned0 OBJECT-TYPE
              SYNTAX         INTEGER { disabled(0), enabled(1) }
              MAX-ACCESS     read-write
              STATUS         current
              DESCRIPTION
                 "Set to 1 to assign parameters to billing Plan 0, 0 to disable"
              ::= { aaaBillingPlan0 2 }
           -- BILLING PLAN 0 XOVERY
              aaaBillingPlanXoverY0 OBJECT-TYPE
              SYNTAX         INTEGER { disabled(0), enabled(1) }
              MAX-ACCESS     read-write
              STATUS         current
              DESCRIPTION
                 "Set to 1 to assign Plan 0 as XoverY plan, 0 to disable.
                 Please note: to use XoverY billing plan you MUST set
                 the variables aaaBillingPlanCost0, aaaBillingPlanDuration0,
                 and aaaBillingPlanValidity0, to non-zero values prior to
                 enabling the plan (setting aaaBillingPlanXoverY0 = 1).
                 Failure to do so will result in an error on the
                 aaaBillingPlanXoverY0 SNMP Set operation."
              ::= { aaaBillingPlan0 3 }
           -- BILLING PLAN 0 LABEL
              aaaBillingPlanLabel0 OBJECT-TYPE
              SYNTAX      DisplayString(SIZE(0..50))
              MAX-ACCESS      read-write
              STATUS      current
              DESCRIPTION
                 "Label for billing Plan 0"
              ::= { aaaBillingPlan0 4 }
           -- BILLING PLAN 0 DESCRIPTION
              aaaBillingPlanDesc0 OBJECT-TYPE
              SYNTAX      DisplayString(SIZE(0..140))
              MAX-ACCESS      read-write
              STATUS      current
              DESCRIPTION
                 "Service Description for billing Plan 0"
              ::= { aaaBillingPlan0 5 }
           -- BILLING PLAN 0 PRICE PER MIN
              aaaBillingPlanPricingMin0 OBJECT-TYPE
              SYNTAX      DisplayString(SIZE(0..32))
              MAX-ACCESS      read-write
              STATUS      current
              DESCRIPTION
                 "Rate Per Minute for billing Plan 0 for Normal Plans"
              ::= { aaaBillingPlan0 6 }
           -- BILLING PLAN 0 PRICE PER HOUR
              aaaBillingPlanPricingHour0 OBJECT-TYPE
              SYNTAX      DisplayString(SIZE(0..32))
              MAX-ACCESS      read-write
              STATUS      current
              DESCRIPTION
                 "Rate Per hour for billing Plan 0 for Normal Plans"
              ::= { aaaBillingPlan0 7 }
           -- BILLING PLAN 0 PRICE PER DAY
              aaaBillingPlanPricingDay0 OBJECT-TYPE
              SYNTAX      DisplayString(SIZE(0..32))
              MAX-ACCESS      read-write
              STATUS      current
              DESCRIPTION
                 "Rate Per day for billing Plan 0 for Normal Plans"
              ::= { aaaBillingPlan0 8 }
           -- BILLING PLAN 0 PRICE PER WEEK
              aaaBillingPlanPricingWeek0 OBJECT-TYPE
              SYNTAX      DisplayString(SIZE(0..32))
              MAX-ACCESS      read-write
              STATUS      current
              DESCRIPTION
                 "Rate Per week for billing Plan 0 for Normal Plans"
              ::= { aaaBillingPlan0 9 }
           -- BILLING PLAN 0 PRICE PER MONTH
              aaaBillingPlanPricingMonth0 OBJECT-TYPE
              SYNTAX      DisplayString(SIZE(0..32))
              MAX-ACCESS      read-write
              STATUS      current
              DESCRIPTION
                 "Rate Per Month for billing Plan 0 for Normal Plans"
              ::= { aaaBillingPlan0 10 }
           -- BILLING PLAN 0 BANDWIDTH UP
              aaaBillingPlanBandwidthUp0 OBJECT-TYPE
              SYNTAX      Integer32(0..1500)
              MAX-ACCESS  read-write
              STATUS      current
              DESCRIPTION
                 "Bandwidth Up for billing Plan 0"
              ::= { aaaBillingPlan0 11 }
           -- BILLING PLAN 0 BANDWIDTH DOWN
              aaaBillingPlanBandwidthDown0 OBJECT-TYPE
              SYNTAX      Integer32(0..1500)
              MAX-ACCESS  read-write
              STATUS      current
              DESCRIPTION
                 "Bandwidth Down for billing Plan 0"
              ::= { aaaBillingPlan0 12 }
           -- BILLING PLAN 0 DHCP POOL
              aaaBillingPlanDHCPPool0 OBJECT-TYPE
              SYNTAX      INTEGER { private(0), public(1) }
              MAX-ACCESS  read-write
              STATUS      current
              DESCRIPTION
                 "DHCP Pool for billing Plan 0: set to 0 for private pool,
                 set to 1 for public pool"
              ::= { aaaBillingPlan0 13 }
           -- BILLING PLAN 0 RATE SHOW
              aaaBillingPlanRateShow0 OBJECT-TYPE
              SYNTAX         INTEGER { minute(0),
                                         hour(1),
                                         day(2),
                                         week(3),
                                         month(4) }
              MAX-ACCESS     read-write
              STATUS         current
              DESCRIPTION
                 "Rate Show for billing Plan 0: Set to 0 if the time unit used is set
                    to minutes, 1 if hours, 2 if days, 3 if weeks, and 4 if months."
              ::= { aaaBillingPlan0 14 }
           -- BILLING PLAN 0 COST
              aaaBillingPlanCost0 OBJECT-TYPE
              SYNTAX      DisplayString(SIZE(0..32))
              MAX-ACCESS  read-write
              STATUS      current
              DESCRIPTION
                 "Cost of the XoverY billing Plan 0"
              ::= { aaaBillingPlan0 15 }
           -- BILLING PLAN 0 DURATION
              aaaBillingPlanDuration0 OBJECT-TYPE
              SYNTAX      Integer32
              MAX-ACCESS  read-write
              STATUS      current
              DESCRIPTION
                 "Duration (X) of the XoverY billing Plan 0"
              ::= { aaaBillingPlan0 16 }
           -- BILLING PLAN 0 VALIDITY
              aaaBillingPlanValidity0 OBJECT-TYPE
              SYNTAX      Integer32
              MAX-ACCESS  read-write
              STATUS      current
              DESCRIPTION
                 "Validity (Y) of the XoverY billing Plan 0"
              ::= { aaaBillingPlan0 17 }
           -- BILLING PLAN 0 VALIDITY RATE SHOW
              aaaBillingPlanValidityRateShow0 OBJECT-TYPE
              SYNTAX      INTEGER {day(2),
                                   week(3),
                                   month(4) }
              MAX-ACCESS  read-write
              STATUS      current
              DESCRIPTION
                 "Validity Rate Show for XoverY billing Plan 0: Set to 2 if the time unit used is set
                    to days, 3 if weeks, and 4 if months."
              ::= { aaaBillingPlan0 18 }
        -- BILLING PLAN 1
           -- BILLING PLAN 1 ON
              aaaBillingPlanOn1 OBJECT-TYPE
              SYNTAX      INTEGER { disabled(0), enabled(1) }
              MAX-ACCESS  read-write
              STATUS      current
              DESCRIPTION
                 "Set to 1 to enable billing Plan 1, 0 to disable"
              ::= { aaaBillingPlan1 1 }
           -- BILLING PLAN 1 ASSIGNED
              aaaBillingPlanAssigned1 OBJECT-TYPE
              SYNTAX      INTEGER { disabled(0), enabled(1) }
              MAX-ACCESS  read-write
              STATUS      current
              DESCRIPTION
                 "Set to 1 to assign parameters to billing Plan 1, 0 to disable"
              ::= { aaaBillingPlan1 2 }
           -- BILLING PLAN 1 XOVERY
              aaaBillingPlanXoverY1 OBJECT-TYPE
              SYNTAX      INTEGER { disabled(0), enabled(1) }
              MAX-ACCESS  read-write
              STATUS      current
              DESCRIPTION
                 "Set to 1 to assign Plan 1 as XoverY plan, 0 to disable.
                 Please note: to use XoverY billing plan you MUST set
                 the variables aaaBillingPlanCost1, aaaBillingPlanDuration1,
                 and aaaBillingPlanValidity1, to non-zero values prior to
                 enabling the plan (setting aaaBillingPlanXoverY1 = 1).
                 Failure to do so will result in an error on the
                 aaaBillingPlanXoverY1 SNMP Set operation."
              ::= { aaaBillingPlan1 3 }
           -- BILLING PLAN 1 LABEL
              aaaBillingPlanLabel1 OBJECT-TYPE
              SYNTAX      DisplayString(SIZE(0..50))
              MAX-ACCESS  read-write
              STATUS      current
              DESCRIPTION
                 "Label for billing Plan 1"
              ::= { aaaBillingPlan1 4 }
           -- BILLING PLAN 1 DESCRIPTION
              aaaBillingPlanDesc1 OBJECT-TYPE
              SYNTAX      DisplayString(SIZE(0..140))
              MAX-ACCESS  read-write
              STATUS      current
              DESCRIPTION
                 "Service Description for billing Plan 1"
              ::= { aaaBillingPlan1 5 }
           -- BILLING PLAN 1 PRICE PER MIN
              aaaBillingPlanPricingMin1 OBJECT-TYPE
              SYNTAX      DisplayString(SIZE(0..32))
              MAX-ACCESS  read-write
              STATUS      current
              DESCRIPTION
                 "Rate Per Minute for billing Plan 1 for Normal Plans"
              ::= { aaaBillingPlan1 6 }
           -- BILLING PLAN 1 PRICE PER HOUR
              aaaBillingPlanPricingHour1 OBJECT-TYPE
              SYNTAX      DisplayString(SIZE(0..32))
              MAX-ACCESS  read-write
              STATUS      current
              DESCRIPTION
                 "Rate Per hour for billing Plan 1 for Normal Plans"
              ::= { aaaBillingPlan1 7 }
           -- BILLING PLAN 1 PRICE PER DAY
              aaaBillingPlanPricingDay1 OBJECT-TYPE
              SYNTAX      DisplayString(SIZE(0..32))
              MAX-ACCESS  read-write
              STATUS      current
              DESCRIPTION
                 "Rate Per day for billing Plan 1 for Normal Plans"
              ::= { aaaBillingPlan1 8 }
           -- BILLING PLAN 1 PRICE PER WEEK
              aaaBillingPlanPricingWeek1 OBJECT-TYPE
              SYNTAX      DisplayString(SIZE(0..32))
              MAX-ACCESS  read-write
              STATUS      current
              DESCRIPTION
                 "Rate Per week for billing Plan 1 for Normal Plans"
              ::= { aaaBillingPlan1 9 }
           -- BILLING PLAN 1 PRICE PER MONTH
              aaaBillingPlanPricingMonth1 OBJECT-TYPE
              SYNTAX      DisplayString(SIZE(0..32))
              MAX-ACCESS  read-write
              STATUS      current
              DESCRIPTION
                 "Rate Per Month for billing Plan 1 for Normal Plans"
              ::= { aaaBillingPlan1 10 }
           -- BILLING PLAN 1 BANDWIDTH UP
              aaaBillingPlanBandwidthUp1 OBJECT-TYPE
              SYNTAX      Integer32(0..1500)
              MAX-ACCESS  read-write
              STATUS      current
              DESCRIPTION
                 "Bandwidth Up for billing Plan 1"
              ::= { aaaBillingPlan1 11 }
           -- BILLING PLAN 1 BANDWIDTH DOWN
              aaaBillingPlanBandwidthDown1 OBJECT-TYPE
              SYNTAX      Integer32(0..1500)
              MAX-ACCESS  read-write
              STATUS      current
              DESCRIPTION
                 "Bandwidth Down for billing Plan 1"
              ::= { aaaBillingPlan1 12 }
           -- BILLING PLAN 1 DHCP POOL
              aaaBillingPlanDHCPPool1 OBJECT-TYPE
              SYNTAX      INTEGER { private(0), public(1) }
              MAX-ACCESS  read-write
              STATUS      current
              DESCRIPTION
                 "DHCP Pool for billing Plan 1: set to 0 for private pool,
                 set to 1 for public pool"
              ::= { aaaBillingPlan1 13 }
           -- BILLING PLAN 1 RATE SHOW
              aaaBillingPlanRateShow1 OBJECT-TYPE
              SYNTAX      INTEGER { minute(0),
                                    hour(1),
                                    day(2),
                                    week(3),
                                    month(4) }
              MAX-ACCESS  read-write
              STATUS      current
              DESCRIPTION
                 "Rate Show for billing Plan 1: Set to 0 if the time unit used is set
                    to minutes, 1 if hours, 2 if days, 3 if weeks, and 4 if months."
              ::= { aaaBillingPlan1 14 }
           -- BILLING PLAN 1 COST
              aaaBillingPlanCost1 OBJECT-TYPE
              SYNTAX      DisplayString(SIZE(0..32))
              MAX-ACCESS  read-write
              STATUS      current
              DESCRIPTION
                 "Cost of the XoverY Plan 1"
              ::= { aaaBillingPlan1 15 }
           -- BILLING PLAN 1 DURATION
              aaaBillingPlanDuration1 OBJECT-TYPE
              SYNTAX      Integer32
              MAX-ACCESS  read-write
              STATUS      current
              DESCRIPTION
                 "Duration (X) of the XoverY Plan 1"
              ::= { aaaBillingPlan1 16 }
           -- BILLING PLAN 1 VALIDITY
              aaaBillingPlanValidity1 OBJECT-TYPE
              SYNTAX      Integer32
              MAX-ACCESS  read-write
              STATUS      current
              DESCRIPTION
                 "Validity (Y) of the XoverY Plan 1"
              ::= { aaaBillingPlan1 17 }
           -- BILLING PLAN 1 VALIDITY RATE SHOW
              aaaBillingPlanValidityRateShow1 OBJECT-TYPE
              SYNTAX      INTEGER {day(2),
                                   week(3),
                                   month(4) }
              MAX-ACCESS  read-write
              STATUS      current
              DESCRIPTION
                 "Validity Rate Show for XoverY Plan 1: Set to 2 if the time unit used is set
                    to days, 3 if weeks, and 4 if months."
              ::= { aaaBillingPlan1 18 }
        -- BILLING PLAN 2
           -- BILLING PLAN 2 ON
              aaaBillingPlanOn2 OBJECT-TYPE
              SYNTAX      INTEGER { disabled(0), enabled(1) }
              MAX-ACCESS  read-write
              STATUS      current
              DESCRIPTION
                 "Set to 1 to enable billing Plan 2, 0 to disable"
              ::= { aaaBillingPlan2 1 }
           -- BILLING PLAN 2 ASSIGNED
              aaaBillingPlanAssigned2 OBJECT-TYPE
              SYNTAX      INTEGER { disabled(0), enabled(1) }
              MAX-ACCESS  read-write
              STATUS      current
              DESCRIPTION
                 "Set to 1 to assign parameters to billing Plan 2, 0 to disable"
              ::= { aaaBillingPlan2 2 }
           -- BILLING PLAN 2 XOVERY
              aaaBillingPlanXoverY2 OBJECT-TYPE
              SYNTAX      INTEGER { disabled(0), enabled(1) }
              MAX-ACCESS  read-write
              STATUS      current
              DESCRIPTION
                 "Set to 1 to assign Plan 2 as XoverY plan, 0 to disable.
                 Please note: to use XoverY billing plan you MUST set
                 the variables aaaBillingPlanCost2, aaaBillingPlanDuration2,
                 and aaaBillingPlanValidity2, to non-zero values prior to
                 enabling the plan (setting aaaBillingPlanXoverY2 = 1).
                 Failure to do so will result in an error on the
                 aaaBillingPlanXoverY2 SNMP Set operation."
              ::= { aaaBillingPlan2 3 }
           -- BILLING PLAN 2 LABEL
              aaaBillingPlanLabel2 OBJECT-TYPE
              SYNTAX      DisplayString(SIZE(0..50))
              MAX-ACCESS  read-write
              STATUS      current
              DESCRIPTION
                 "Label for billing Plan 2"
              ::= { aaaBillingPlan2 4 }
           -- BILLING PLAN 2 DESCRIPTION
              aaaBillingPlanDesc2 OBJECT-TYPE
              SYNTAX      DisplayString(SIZE(0..140))
              MAX-ACCESS  read-write
              STATUS      current
              DESCRIPTION
                 "Service Description for billing Plan 2"
              ::= { aaaBillingPlan2 5 }
           -- BILLING PLAN 2 PRICE PER MIN
              aaaBillingPlanPricingMin2 OBJECT-TYPE
              SYNTAX      DisplayString(SIZE(0..32))
              MAX-ACCESS  read-write
              STATUS      current
              DESCRIPTION
                 "Rate Per Minute for billing Plan 2 for Normal Plans"
              ::= { aaaBillingPlan2 6 }
           -- BILLING PLAN 2 PRICE PER HOUR
              aaaBillingPlanPricingHour2 OBJECT-TYPE
              SYNTAX      DisplayString(SIZE(0..32))
              MAX-ACCESS  read-write
              STATUS      current
              DESCRIPTION
                 "Rate Per hour for billing Plan 2 for Normal Plans"
              ::= { aaaBillingPlan2 7 }
           -- BILLING PLAN 2 PRICE PER DAY
              aaaBillingPlanPricingDay2 OBJECT-TYPE
              SYNTAX      DisplayString(SIZE(0..32))
              MAX-ACCESS  read-write
              STATUS      current
              DESCRIPTION
                 "Rate Per day for billing Plan 2 for Normal Plans"
              ::= { aaaBillingPlan2 8 }
           -- BILLING PLAN 2 PRICE PER WEEK
              aaaBillingPlanPricingWeek2 OBJECT-TYPE
              SYNTAX      DisplayString(SIZE(0..32))
              MAX-ACCESS  read-write
              STATUS      current
              DESCRIPTION
                 "Rate Per week for billing Plan 2 for Normal Plans"
              ::= { aaaBillingPlan2 9 }
           -- BILLING PLAN 2 PRICE PER MONTH
              aaaBillingPlanPricingMonth2 OBJECT-TYPE
              SYNTAX      DisplayString(SIZE(0..32))
              MAX-ACCESS  read-write
              STATUS      current
              DESCRIPTION
                 "Rate Per Month for billing Plan 2 for Normal Plans"
              ::= { aaaBillingPlan2 10 }
           -- BILLING PLAN 2 BANDWIDTH UP
              aaaBillingPlanBandwidthUp2 OBJECT-TYPE
              SYNTAX      Integer32(0..1500)
              MAX-ACCESS  read-write
              STATUS      current
              DESCRIPTION
                 "Bandwidth Up for billing Plan 2"
              ::= { aaaBillingPlan2 11 }
           -- BILLING PLAN 2 BANDWIDTH DOWN
              aaaBillingPlanBandwidthDown2 OBJECT-TYPE
              SYNTAX      Integer32(0..1500)
              MAX-ACCESS  read-write
              STATUS      current
              DESCRIPTION
                 "Bandwidth Down for billing Plan 2"
              ::= { aaaBillingPlan2 12 }
           -- BILLING PLAN 2 DHCP POOL
              aaaBillingPlanDHCPPool2 OBJECT-TYPE
              SYNTAX      INTEGER { private(0), public(1) }
              MAX-ACCESS  read-write
              STATUS      current
              DESCRIPTION
                 "DHCP Pool for billing Plan 2: set to 0 for private pool,
                 set to 1 for public pool"
              ::= { aaaBillingPlan2 13 }
           -- BILLING PLAN 2 RATE SHOW
              aaaBillingPlanRateShow2 OBJECT-TYPE
              SYNTAX      INTEGER { minute(0),
                                    hour(1),
                                    day(2),
                                    week(3),
                                    month(4) }
              MAX-ACCESS  read-write
              STATUS      current
              DESCRIPTION
                 "Rate Show for billing Plan 2: Set to 0 if the time unit used is set
                    to minutes, 1 if hours, 2 if days, 3 if weeks, and 4 if months."
              ::= { aaaBillingPlan2 14 }
           -- BILLING PLAN 2 COST
              aaaBillingPlanCost2 OBJECT-TYPE
              SYNTAX      DisplayString(SIZE(0..32))
              MAX-ACCESS  read-write
              STATUS      current
              DESCRIPTION
                 "Cost of the XoverY billing Plan 2"
              ::= { aaaBillingPlan2 15 }
           -- BILLING PLAN 2 DURATION
              aaaBillingPlanDuration2 OBJECT-TYPE
              SYNTAX      Integer32
              MAX-ACCESS  read-write
              STATUS      current
              DESCRIPTION
                 "Duration (X) of the XoverY billing Plan 2"
              ::= { aaaBillingPlan2 16 }
           -- BILLING PLAN 2 VALIDITY
              aaaBillingPlanValidity2 OBJECT-TYPE
              SYNTAX      Integer32
              MAX-ACCESS  read-write
              STATUS      current
              DESCRIPTION
                 "Validity (Y) of the XoverY billing Plan 2"
              ::= { aaaBillingPlan2 17 }
           -- BILLING PLAN 2 VALIDITY RATE SHOW
              aaaBillingPlanValidityRateShow2 OBJECT-TYPE
              SYNTAX      INTEGER {day(2),
                                   week(3),
                                   month(4) }
              MAX-ACCESS  read-write
              STATUS      current
              DESCRIPTION
                 "Validity Rate Show for XoverY billing Plan 2: Set to 2 if the time unit used is set
                    to days, 3 if weeks, and 4 if months."
              ::= { aaaBillingPlan2 18 }
        -- BILLING PLAN 3
           -- BILLING PLAN 3 ON
              aaaBillingPlanOn3 OBJECT-TYPE
              SYNTAX      INTEGER { disabled(0), enabled(1) }
              MAX-ACCESS  read-write
              STATUS      current
              DESCRIPTION
                 "Set to 1 to enable billing Plan 3, 0 to disable"
              ::= { aaaBillingPlan3 1 }
           -- BILLING PLAN 3 ASSIGNED
              aaaBillingPlanAssigned3 OBJECT-TYPE
              SYNTAX      INTEGER { disabled(0), enabled(1) }
              MAX-ACCESS  read-write
              STATUS      current
              DESCRIPTION
                 "Set to 1 to assign parameters to billing Plan 3, 0 to disable"
              ::= { aaaBillingPlan3 2 }
           -- BILLING PLAN 3 XOVERY
              aaaBillingPlanXoverY3 OBJECT-TYPE
              SYNTAX      INTEGER { disabled(0), enabled(1) }
              MAX-ACCESS  read-write
              STATUS      current
              DESCRIPTION
                 "Set to 1 to assign Plan 3 as XoverY plan, 0 to disable.
                 Please note: to use XoverY billing plan you MUST set
                 the variables aaaBillingPlanCost3, aaaBillingPlanDuration3,
                 and aaaBillingPlanValidity3, to non-zero values prior to
                 enabling the plan (setting aaaBillingPlanXoverY3 = 1).
                 Failure to do so will result in an error on the
                 aaaBillingPlanXoverY3 SNMP Set operation."
              ::= { aaaBillingPlan3 3 }
           -- BILLING PLAN 3 LABEL
              aaaBillingPlanLabel3 OBJECT-TYPE
              SYNTAX      DisplayString(SIZE(0..50))
              MAX-ACCESS  read-write
              STATUS      current
              DESCRIPTION
                 "Label for billing Plan 3"
              ::= { aaaBillingPlan3 4 }
           -- BILLING PLAN 3 DESCRIPTION
              aaaBillingPlanDesc3 OBJECT-TYPE
              SYNTAX      DisplayString(SIZE(0..140))
              MAX-ACCESS  read-write
              STATUS      current
              DESCRIPTION
                 "Service Description for billing Plan 3"
              ::= { aaaBillingPlan3 5 }
           -- BILLING PLAN 3 PRICE PER MIN
              aaaBillingPlanPricingMin3 OBJECT-TYPE
              SYNTAX      DisplayString(SIZE(0..32))
              MAX-ACCESS  read-write
              STATUS      current
              DESCRIPTION
                 "Rate Per Minute for billing Plan 3 for Normal Plans"
              ::= { aaaBillingPlan3 6 }
           -- BILLING PLAN 3 PRICE PER HOUR
              aaaBillingPlanPricingHour3 OBJECT-TYPE
              SYNTAX      DisplayString(SIZE(0..32))
              MAX-ACCESS  read-write
              STATUS      current
              DESCRIPTION
                 "Rate Per hour for billing Plan 3 for Normal Plans"
              ::= { aaaBillingPlan3 7 }
           -- BILLING PLAN 3 PRICE PER DAY
              aaaBillingPlanPricingDay3 OBJECT-TYPE
              SYNTAX      DisplayString(SIZE(0..32))
              MAX-ACCESS  read-write
              STATUS      current
              DESCRIPTION
                 "Rate Per day for billing Plan 3 for Normal Plans"
              ::= { aaaBillingPlan3 8 }
           -- BILLING PLAN 3 PRICE PER WEEK
              aaaBillingPlanPricingWeek3 OBJECT-TYPE
              SYNTAX      DisplayString(SIZE(0..32))
              MAX-ACCESS  read-write
              STATUS      current
              DESCRIPTION
                 "Rate Per week for billing Plan 3 for Normal Plans"
              ::= { aaaBillingPlan3 9 }
           -- BILLING PLAN 3 PRICE PER MONTH
              aaaBillingPlanPricingMonth3 OBJECT-TYPE
              SYNTAX      DisplayString(SIZE(0..32))
              MAX-ACCESS  read-write
              STATUS      current
              DESCRIPTION
                 "Rate Per Month for billing Plan 3 for Normal Plans"
              ::= { aaaBillingPlan3 10 }
           -- BILLING PLAN 3 BANDWIDTH UP
              aaaBillingPlanBandwidthUp3 OBJECT-TYPE
              SYNTAX      Integer32(0..1500)
              MAX-ACCESS  read-write
              STATUS      current
              DESCRIPTION
                 "Bandwidth Up for billing Plan 3"
              ::= { aaaBillingPlan3 11 }
           -- BILLING PLAN 3 BANDWIDTH DOWN
              aaaBillingPlanBandwidthDown3 OBJECT-TYPE
              SYNTAX      Integer32(0..1500)
              MAX-ACCESS  read-write
              STATUS      current
              DESCRIPTION
                 "Bandwidth Down for billing Plan 3"
              ::= { aaaBillingPlan3 12 }
           -- BILLING PLAN 3 DHCP POOL
              aaaBillingPlanDHCPPool3 OBJECT-TYPE
              SYNTAX      INTEGER { private(0), public(1) }
              MAX-ACCESS  read-write
              STATUS      current
              DESCRIPTION
                 "DHCP Pool for billing Plan 3: set to 0 for private pool,
                 set to 1 for public pool"
              ::= { aaaBillingPlan3 13 }
           -- BILLING PLAN 3 RATE SHOW
              aaaBillingPlanRateShow3 OBJECT-TYPE
              SYNTAX      INTEGER { minute(0),
                                    hour(1),
                                    day(2),
                                    week(3),
                                    month(4) }
              MAX-ACCESS  read-write
              STATUS      current
              DESCRIPTION
                 "Rate Show for billing Plan 3: Set to 0 if the time unit used is set
                    to minutes, 1 if hours, 2 if days, 3 if weeks, and 4 if months."
              ::= { aaaBillingPlan3 14 }
           -- BILLING PLAN 3 COST
              aaaBillingPlanCost3 OBJECT-TYPE
              SYNTAX      DisplayString(SIZE(0..32))
              MAX-ACCESS  read-write
              STATUS      current
              DESCRIPTION
                 "Cost of the XoverY billing Plan 3"
              ::= { aaaBillingPlan3 15 }
           -- BILLING PLAN 3 DURATION
              aaaBillingPlanDuration3 OBJECT-TYPE
              SYNTAX      Integer32
              MAX-ACCESS  read-write
              STATUS      current
              DESCRIPTION
                 "Duration (X) of the XoverY billing Plan 3"
              ::= { aaaBillingPlan3 16 }
           -- BILLING PLAN 3 VALIDITY
              aaaBillingPlanValidity3 OBJECT-TYPE
              SYNTAX      Integer32
              MAX-ACCESS  read-write
              STATUS      current
              DESCRIPTION
                 "Validity (Y) of the XoverY billing Plan 3"
              ::= { aaaBillingPlan3 17 }
           -- BILLING PLAN 3 VALIDITY RATE SHOW
              aaaBillingPlanValidityRateShow3 OBJECT-TYPE
              SYNTAX      INTEGER {day(2),
                                   week(3),
                                   month(4) }
              MAX-ACCESS  read-write
              STATUS      current
              DESCRIPTION
                 "Validity Rate Show for XoverY billing Plan 3: Set to 2 if the time unit used is set
                    to days, 3 if weeks, and 4 if months."
              ::= { aaaBillingPlan3 18 }
        -- BILLING PLAN 4
           -- BILLING PLAN 4 ON
              aaaBillingPlanOn4 OBJECT-TYPE
              SYNTAX      INTEGER { disabled(0), enabled(1) }
              MAX-ACCESS  read-write
              STATUS      current
              DESCRIPTION
                 "Set to 1 to enable billing Plan 4, 0 to disable"
              ::= { aaaBillingPlan4 1 }
           -- BILLING PLAN 4 ASSIGNED
              aaaBillingPlanAssigned4 OBJECT-TYPE
              SYNTAX      INTEGER { disabled(0), enabled(1) }
              MAX-ACCESS  read-write
              STATUS      current
              DESCRIPTION
                 "Set to 1 to assign parameters to billing Plan 4, 0 to disable"
              ::= { aaaBillingPlan4 2 }
           -- BILLING PLAN 4 XOVERY
              aaaBillingPlanXoverY4 OBJECT-TYPE
              SYNTAX      INTEGER { disabled(0), enabled(1) }
              MAX-ACCESS  read-write
              STATUS      current
              DESCRIPTION
                 "Set to 1 to assign Plan 4 as XoverY plan, 0 to disable.
                 Please note: to use XoverY billing plan you MUST set
                 the variables aaaBillingPlanCost4, aaaBillingPlanDuration4,
                 and aaaBillingPlanValidity4, to non-zero values prior to
                 enabling the plan (setting aaaBillingPlanXoverY4 = 1).
                 Failure to do so will result in an error on the
                 aaaBillingPlanXoverY4 SNMP Set operation."
              ::= { aaaBillingPlan4 3 }
           -- BILLING PLAN 4 LABEL
              aaaBillingPlanLabel4 OBJECT-TYPE
              SYNTAX      DisplayString(SIZE(0..50))
              MAX-ACCESS  read-write
              STATUS      current
              DESCRIPTION
                 "Label for billing Plan 4"
              ::= { aaaBillingPlan4 4 }
           -- BILLING PLAN 4 DESCRIPTION
              aaaBillingPlanDesc4 OBJECT-TYPE
              SYNTAX      DisplayString(SIZE(0..140))
              MAX-ACCESS  read-write
              STATUS      current
              DESCRIPTION
                 "Service Description for billing Plan 4"
              ::= { aaaBillingPlan4 5 }
           -- BILLING PLAN 4 PRICE PER MIN
              aaaBillingPlanPricingMin4 OBJECT-TYPE
              SYNTAX      DisplayString(SIZE(0..32))
              MAX-ACCESS  read-write
              STATUS      current
              DESCRIPTION
                 "Rate Per Minute for billing Plan 4 for Normal Plans"
              ::= { aaaBillingPlan4 6 }
           -- BILLING PLAN 4 PRICE PER HOUR
              aaaBillingPlanPricingHour4 OBJECT-TYPE
              SYNTAX      DisplayString(SIZE(0..32))
              MAX-ACCESS  read-write
              STATUS      current
              DESCRIPTION
                 "Rate Per hour for billing Plan 4 for Normal Plans"
              ::= { aaaBillingPlan4 7 }
           -- BILLING PLAN 4 PRICE PER DAY
              aaaBillingPlanPricingDay4 OBJECT-TYPE
              SYNTAX      DisplayString(SIZE(0..32))
              MAX-ACCESS  read-write
              STATUS      current
              DESCRIPTION
                 "Rate Per day for billing Plan 4 for Normal Plans"
              ::= { aaaBillingPlan4 8 }
           -- BILLING PLAN 4 PRICE PER WEEK
              aaaBillingPlanPricingWeek4 OBJECT-TYPE
              SYNTAX      DisplayString(SIZE(0..32))
              MAX-ACCESS  read-write
              STATUS      current
              DESCRIPTION
                 "Rate Per week for billing Plan 4 for Normal Plans"
              ::= { aaaBillingPlan4 9 }
           -- BILLING PLAN 4 PRICE PER MONTH
              aaaBillingPlanPricingMonth4 OBJECT-TYPE
              SYNTAX      DisplayString(SIZE(0..32))
              MAX-ACCESS  read-write
              STATUS      current
              DESCRIPTION
                 "Rate Per Month for billing Plan 4 for Normal Plans"
              ::= { aaaBillingPlan4 10 }
           -- BILLING PLAN 4 BANDWIDTH UP
              aaaBillingPlanBandwidthUp4 OBJECT-TYPE
              SYNTAX      Integer32(0..1500)
              MAX-ACCESS  read-write
              STATUS      current
              DESCRIPTION
                 "Bandwidth Up for billing Plan 4"
              ::= { aaaBillingPlan4 11 }
           -- BILLING PLAN 4 BANDWIDTH DOWN
              aaaBillingPlanBandwidthDown4 OBJECT-TYPE
              SYNTAX      Integer32(0..1500)
              MAX-ACCESS  read-write
              STATUS      current
              DESCRIPTION
                 "Bandwidth Down for billing Plan 4"
              ::= { aaaBillingPlan4 12 }
           -- BILLING PLAN 4 DHCP POOL
              aaaBillingPlanDHCPPool4 OBJECT-TYPE
              SYNTAX      INTEGER { private(0), public(1) }
              MAX-ACCESS  read-write
              STATUS      current
              DESCRIPTION
                 "DHCP Pool for billing Plan 4: set to 0 for private pool,
                 set to 1 for public pool"
              ::= { aaaBillingPlan4 13 }
           -- BILLING PLAN 4 RATE SHOW
              aaaBillingPlanRateShow4 OBJECT-TYPE
              SYNTAX      INTEGER { minute(0),
                                    hour(1),
                                    day(2),
                                    week(3),
                                    month(4) }
              MAX-ACCESS  read-write
              STATUS      current
              DESCRIPTION
                 "Rate Show for billing Plan 4: Set to 0 if the time unit used is set
                    to minutes, 1 if hours, 2 if days, 3 if weeks, and 4 if months."
              ::= { aaaBillingPlan4 14 }
           -- BILLING PLAN 4 COST
              aaaBillingPlanCost4 OBJECT-TYPE
              SYNTAX      DisplayString(SIZE(0..32))
              MAX-ACCESS  read-write
              STATUS      current
              DESCRIPTION
                 "Cost of the XoverY billing Plan 4"
              ::= { aaaBillingPlan4 15 }
           -- BILLING PLAN 4 DURATION
              aaaBillingPlanDuration4 OBJECT-TYPE
              SYNTAX      Integer32
              MAX-ACCESS  read-write
              STATUS      current
              DESCRIPTION
                 "Duration (X) of the XoverY billing Plan 4"
              ::= { aaaBillingPlan4 16 }
           -- BILLING PLAN 4 VALIDITY
              aaaBillingPlanValidity4 OBJECT-TYPE
              SYNTAX      Integer32
              MAX-ACCESS  read-write
              STATUS      current
              DESCRIPTION
                 "Validity (Y) of the XoverY billing Plan 4"
              ::= { aaaBillingPlan4 17 }
           -- BILLING PLAN 4 VALIDITY RATE SHOW
              aaaBillingPlanValidityRateShow4 OBJECT-TYPE
              SYNTAX      INTEGER {day(2),
                                   week(3),
                                   month(4) }
              MAX-ACCESS  read-write
              STATUS      current
              DESCRIPTION
                 "Validity Rate Show for XoverY billing Plan 4: Set to 2 if the time unit used is set
                    to days, 3 if weeks, and 4 if months."
              ::= { aaaBillingPlan4 18 }
        -- BILLING PLAN 5
           -- BILLING PLAN 5 ON
              aaaBillingPlanOn5 OBJECT-TYPE
              SYNTAX      INTEGER { disabled(0), enabled(1) }
              MAX-ACCESS  read-write
              STATUS      current
              DESCRIPTION
                 "Set to 1 to enable billing Plan 5, 0 to disable"
              ::= { aaaBillingPlan5 1 }
           -- BILLING PLAN 5 ASSIGNED
              aaaBillingPlanAssigned5 OBJECT-TYPE
              SYNTAX     INTEGER { disabled(0), enabled(1) }
              MAX-ACCESS read-write
              STATUS     current
              DESCRIPTION
                 "Set to 1 to assign parameters to billing Plan 5, 0 to disable"
              ::= { aaaBillingPlan5 2 }
           -- BILLING PLAN 5 XOVERY
              aaaBillingPlanXoverY5 OBJECT-TYPE
              SYNTAX     INTEGER { disabled(0), enabled(1) }
              MAX-ACCESS read-write
              STATUS     current
              DESCRIPTION
                 "Set to 1 to assign Plan 5 as XoverY plan, 0 to disable.
                 Please note: to use XoverY billing plan you MUST set
                 the variables aaaBillingPlanCost5, aaaBillingPlanDuration5,
                 and aaaBillingPlanValidity5, to non-zero values prior to
                 enabling the plan (setting aaaBillingPlanXoverY5 = 1).
                 Failure to do so will result in an error on the
                 aaaBillingPlanXoverY5 SNMP Set operation."
              ::= { aaaBillingPlan5 3 }
           -- BILLING PLAN 5 LABEL
              aaaBillingPlanLabel5 OBJECT-TYPE
              SYNTAX     DisplayString(SIZE(0..50))
              MAX-ACCESS read-write
              STATUS     current
              DESCRIPTION
                 "Label for billing Plan 5"
              ::= { aaaBillingPlan5 4 }
           -- BILLING PLAN 5 DESCRIPTION
              aaaBillingPlanDesc5 OBJECT-TYPE
              SYNTAX     DisplayString(SIZE(0..140))
              MAX-ACCESS read-write
              STATUS     current
              DESCRIPTION
                 "Service Description for billing Plan 5"
              ::= { aaaBillingPlan5 5 }
           -- BILLING PLAN 5 PRICE PER MIN
              aaaBillingPlanPricingMin5 OBJECT-TYPE
              SYNTAX     DisplayString(SIZE(0..32))
              MAX-ACCESS read-write
              STATUS     current
              DESCRIPTION
                 "Rate Per Minute for billing Plan 5 for Normal Plans"
              ::= { aaaBillingPlan5 6 }
           -- BILLING PLAN 5 PRICE PER HOUR
              aaaBillingPlanPricingHour5 OBJECT-TYPE
              SYNTAX     DisplayString(SIZE(0..32))
              MAX-ACCESS read-write
              STATUS     current
              DESCRIPTION
                 "Rate Per hour for billing Plan 5 for Normal Plans"
              ::= { aaaBillingPlan5 7 }
           -- BILLING PLAN 5 PRICE PER DAY
              aaaBillingPlanPricingDay5 OBJECT-TYPE
              SYNTAX     DisplayString(SIZE(0..32))
              MAX-ACCESS read-write
              STATUS     current
              DESCRIPTION
                 "Rate Per day for billing Plan 5 for Normal Plans"
              ::= { aaaBillingPlan5 8 }
           -- BILLING PLAN 5 PRICE PER WEEK
              aaaBillingPlanPricingWeek5 OBJECT-TYPE
              SYNTAX     DisplayString(SIZE(0..32))
              MAX-ACCESS read-write
              STATUS     current
              DESCRIPTION
                 "Rate Per week for billing Plan 5 for Normal Plans"
              ::= { aaaBillingPlan5 9 }
           -- BILLING PLAN 5 PRICE PER MONTH
              aaaBillingPlanPricingMonth5 OBJECT-TYPE
              SYNTAX     DisplayString(SIZE(0..32))
              MAX-ACCESS read-write
              STATUS     current
              DESCRIPTION
                 "Rate Per Month for billing Plan 5 for Normal Plans"
              ::= { aaaBillingPlan5 10 }
           -- BILLING PLAN 5 BANDWIDTH UP
              aaaBillingPlanBandwidthUp5 OBJECT-TYPE
              SYNTAX      Integer32(0..1500)
              MAX-ACCESS  read-write
              STATUS      current
              DESCRIPTION
                 "Bandwidth Up for billing Plan 5"
              ::= { aaaBillingPlan5 11 }
           -- BILLING PLAN 5 BANDWIDTH DOWN
              aaaBillingPlanBandwidthDown5 OBJECT-TYPE
              SYNTAX      Integer32(0..1500)
              MAX-ACCESS  read-write
              STATUS      current
              DESCRIPTION
                 "Bandwidth Down for billing Plan 5"
              ::= { aaaBillingPlan5 12 }
           -- BILLING PLAN 5 DHCP POOL
              aaaBillingPlanDHCPPool5 OBJECT-TYPE
              SYNTAX      INTEGER { private(0), public(1) }
              MAX-ACCESS  read-write
              STATUS      current
              DESCRIPTION
                 "DHCP Pool for billing Plan 5: set to 0 for private pool,
                 set to 1 for public pool"
              ::= { aaaBillingPlan5 13 }
           -- BILLING PLAN 5 RATE SHOW
              aaaBillingPlanRateShow5 OBJECT-TYPE
              SYNTAX      INTEGER { minute(0),
                                    hour(1),
                                    day(2),
                                    week(3),
                                    month(4) }
              MAX-ACCESS  read-write
              STATUS      current
              DESCRIPTION
                 "Rate Show for billing Plan 5: Set to 0 if the time unit used is set
                    to minutes, 1 if hours, 2 if days, 3 if weeks, and 4 if months."
              ::= { aaaBillingPlan5 14 }
           -- BILLING PLAN 5 COST
              aaaBillingPlanCost5 OBJECT-TYPE
              SYNTAX      DisplayString(SIZE(0..32))
              MAX-ACCESS  read-write
              STATUS      current
              DESCRIPTION
                 "Cost of the XoverY billing Plan 5"
              ::= { aaaBillingPlan5 15 }
           -- BILLING PLAN 5 DURATION
              aaaBillingPlanDuration5 OBJECT-TYPE
              SYNTAX      Integer32
              MAX-ACCESS  read-write
              STATUS      current
              DESCRIPTION
                 "Duration (X) of the XoverY billing Plan 5"
              ::= { aaaBillingPlan5 16 }
           -- BILLING PLAN 5 VALIDITY
              aaaBillingPlanValidity5 OBJECT-TYPE
              SYNTAX      Integer32
              MAX-ACCESS  read-write
              STATUS      current
              DESCRIPTION
                 "Validity (Y) of the XoverY billing Plan 5"
              ::= { aaaBillingPlan5 17 }
           -- BILLING PLAN 5 VALIDITY RATE SHOW
              aaaBillingPlanValidityRateShow5 OBJECT-TYPE
              SYNTAX      INTEGER {day(2),
                                   week(3),
                                   month(4) }
              MAX-ACCESS  read-write
              STATUS      current
              DESCRIPTION
                 "Validity Rate Show for XoverY billing Plan 5: Set to 2 if the time unit used is set
                    to days, 3 if weeks, and 4 if months."
              ::= { aaaBillingPlan5 18 }
--
-- AAA SUB LOGIN UI
--
     aaaSubLoginUI     OBJECT IDENTIFIER ::= { aaa 16 }
     -- AAA WEB SERVICE MSG
        aaaWebServiceMsg OBJECT-TYPE
        SYNTAX      DisplayString(SIZE(0..218))
        MAX-ACCESS  read-write
        STATUS      current
        DESCRIPTION
           "Specify the service selection message"
        ::= { aaaSubLoginUI 1 }
     -- AAA WEB EXISTING USER MSG
        aaaWebExistingUserMsg OBJECT-TYPE
        SYNTAX      DisplayString(SIZE(0..218))
        MAX-ACCESS  read-write
        STATUS      current
        DESCRIPTION
           "Specify the message for an existing user"
        ::= { aaaSubLoginUI 2 }
     -- AAA WEB NEW USER MSG
        aaaWebNewUsernameMsg OBJECT-TYPE
        SYNTAX      DisplayString(SIZE(0..218))
        MAX-ACCESS  read-write
        STATUS      current
        DESCRIPTION
           "Specify the new username message"
        ::= { aaaSubLoginUI 3 }
     -- AAA WEB SERVICE MSG
        aaaWebContactMsg OBJECT-TYPE
        SYNTAX      DisplayString(SIZE(0..218))
        MAX-ACCESS  read-write
        STATUS      current
        DESCRIPTION
           "Specify the contact message"
        ::= { aaaSubLoginUI 4 }
     -- AAA MICROS USERNAME MSG
        aaaWebMicrosUsernameMsg OBJECT-TYPE
        SYNTAX      DisplayString(SIZE(0..218))
        MAX-ACCESS  read-write
        STATUS      current
        DESCRIPTION
           "Specify the PMS username message for MICROS PMS
            (Maximum length: 140 characters)"
        ::= { aaaSubLoginUI 5 }
     -- AAA WEB JAVASCRIPT ON
        aaaWebJavascriptOn OBJECT-TYPE
        SYNTAX      INTEGER { disabled(0), enabled(1) }
        MAX-ACCESS  read-write
        STATUS      current
        DESCRIPTION
           "Set to 1 to enable Javascript, 0 to disable."
        ::= { aaaSubLoginUI 6 }
     -- AAA WEB REMEMBERME ON
     aaaWebRememberMeOn OBJECT-TYPE
     SYNTAX         INTEGER { disabled(0), enabled(1) }
     MAX-ACCESS     read-write
     STATUS         current
     DESCRIPTION
        "Set to 1 to enable Remember Me browser cookie, 0 to disable."
     ::= { aaaSubLoginUI 7 }
     -- AAA REMEMBERME MSG
        aaaRememberMeMsg OBJECT-TYPE
        SYNTAX      DisplayString(SIZE(0..218))
        MAX-ACCESS  read-write
        STATUS      current
        DESCRIPTION
           "Specify the Remember Me message"
        ::= { aaaSubLoginUI 8 }
     -- AAA REMEMBERME DAYS
        aaaRememberMeDays OBJECT-TYPE
        SYNTAX      Integer32
        MAX-ACCESS  read-write
        STATUS      current
        DESCRIPTION
           "Set the number of days to retain the Remember Me browser cookie"
        ::= { aaaSubLoginUI 9 }
     -- AAA CURRENCY
        aaaCurrency OBJECT-TYPE
        SYNTAX      DisplayString(SIZE(0..15))
        MAX-ACCESS  read-write
        STATUS      current
        DESCRIPTION
           "Specify the currency symbol"
        ::= { aaaSubLoginUI 10 }
     -- AAA AMOUNT DECIMALS
        aaaAmountDecimals OBJECT-TYPE
        SYNTAX      Integer32
        MAX-ACCESS  read-write
        STATUS      current
        DESCRIPTION
           "Set the number of decimals in the currency"
        ::= { aaaSubLoginUI 11 }
     -- AAA WEB IMAGE
        aaaWebImage OBJECT-TYPE
        SYNTAX      DisplayString(SIZE(0..98))
        MAX-ACCESS  read-write
        STATUS      current
        DESCRIPTION
           "Specify the image file name.  Must be rebooted
           to take effect."
        ::= { aaaSubLoginUI 12 }
     -- AAA WEB PAGE BGCOLOR
        aaaWebPageBgcolor OBJECT-TYPE
        SYNTAX      DisplayString(SIZE(0..50))
        MAX-ACCESS  read-write
        STATUS      current
        DESCRIPTION
           "Specify the background color"
        ::= { aaaSubLoginUI 13 }
     -- AAA WEB TAB BGCOLOR
        aaaWebTabBgcolor OBJECT-TYPE
        SYNTAX      DisplayString(SIZE(0..98))
        MAX-ACCESS  read-write
        STATUS      current
        DESCRIPTION
           "Specify the background color for the table"
        ::= { aaaSubLoginUI 14 }
     -- AAA WEB TITLE FONT
        aaaWebTitleFont OBJECT-TYPE
        SYNTAX      DisplayString(SIZE(0..98))
        MAX-ACCESS  read-write
        STATUS      current
        DESCRIPTION
           "Specify the title font"
        ::= { aaaSubLoginUI 15 }
     -- AAA WEB ITEM FONT
        aaaWebItemFont OBJECT-TYPE
        SYNTAX      DisplayString(SIZE(0..98))
        MAX-ACCESS  read-write
        STATUS      current
        DESCRIPTION
           "Specify the line item font"
        ::= { aaaSubLoginUI 16 }
     -- AAA WEB SUB PAGE BLOCKED ACCESS ERROR
        aaaErrorAccessBlocked OBJECT-TYPE
        SYNTAX        DisplayString(SIZE(0..218))
        MAX-ACCESS  read-write
        STATUS        current
        DESCRIPTION
           "AG blocked subscriber access"
        ::= { aaaSubLoginUI 17 }
     -- AAA WEB SUB PAGE PASSWD REQ ACCESS ERROR
   aaaErrorAccessPassword OBJECT-TYPE
   SYNTAX       DisplayString(SIZE(0..218))
   MAX-ACCESS  read-write
   STATUS       current
   DESCRIPTION
       "Access to this document requires a password"
        ::= { aaaSubLoginUI 18 }
     -- AAA WEB SUB PAGE ERROR HAS OCCURED ERROR
         aaaErrorHasOccurred OBJECT-TYPE
         SYNTAX       DisplayString(SIZE(0..218))
         MAX-ACCESS  read-write
         STATUS       current
         DESCRIPTION
             "An error has occurred"
        ::= { aaaSubLoginUI 19 }
     -- AAA WEB SUB PAGE RECEIVED ISP ERROR
         aaaErrorISPChallenge OBJECT-TYPE
         SYNTAX       DisplayString(SIZE(0..218))
         MAX-ACCESS  read-write
         STATUS       current
         DESCRIPTION
             "You received a challenge from your Internet Service Provider"
        ::= { aaaSubLoginUI 20 }
     -- AAA WEB SUB PAGE NOT VALID VALUE ERROR
        aaaErrorMinMaxValues OBJECT-TYPE
        SYNTAX        DisplayString(SIZE(0..218))
        MAX-ACCESS  read-write
        STATUS        current
        DESCRIPTION
       "This field must contain a number between these two values"
        ::= { aaaSubLoginUI 21 }
     -- AAA WEB SUB PAGE NO BILLING OPTION ERROR
         aaaErrorNoBillingOpts OBJECT-TYPE
         SYNTAX       DisplayString(SIZE(0..218))
         MAX-ACCESS  read-write
         STATUS       current
         DESCRIPTION
             "No Billing options are available"
        ::= { aaaSubLoginUI 22 }
     -- AAA WEB SUB PAGE NO INTERNET SERVICE ERROR
   aaaErrorNotAvailable OBJECT-TYPE
   SYNTAX      DisplayString(SIZE(0..218))
   MAX-ACCESS read-write
   STATUS      current
   DESCRIPTION
       "Internet Service is not available right now. Try again later"
        ::= { aaaSubLoginUI 23 }
     -- AAA WEB SUB PAGE PASSWD NOT MATCHED ERROR
   aaaErrorPasswordMatch OBJECT-TYPE
   SYNTAX      DisplayString(SIZE(0..218))
   MAX-ACCESS read-write
   STATUS      current
   DESCRIPTION
       "The password fields you have entered do not match. Please try again"
        ::= { aaaSubLoginUI 24 }
     -- AAA WEB SUB PAGE INVALID PASSWD  ERROR
        aaaErrorPasswordWrong OBJECT-TYPE
        SYNTAX       DisplayString(SIZE(0..218))
        MAX-ACCESS read-write
        STATUS       current
        DESCRIPTION
       "The password field you have entered is not correct. Please try again"
        ::= { aaaSubLoginUI 25 }
     -- AAA WEB SUB PAGE BILLING ROOM ERROR
         aaaErrorRoomBilling OBJECT-TYPE
         SYNTAX      DisplayString(SIZE(0..218))
         MAX-ACCESS read-write
         STATUS      current
         DESCRIPTION
             "Error in Room Billing"
        ::= { aaaSubLoginUI 26 }
     -- AAA WEB SUB PAGE TOO MANY SUBSCRIBERS ERROR
   aaaErrorTooManyUsers OBJECT-TYPE
   SYNTAX      DisplayString(SIZE(0..218))
   MAX-ACCESS read-write
   STATUS      current
   DESCRIPTION
       "Too many subscribers are already logged in. Please try again later"
        ::= { aaaSubLoginUI 27 }
     -- AAA WEB SUB PAGE TRY AGAIN ERROR
   aaaErrorTryAgain OBJECT-TYPE
   SYNTAX      DisplayString(SIZE(0..218))
   MAX-ACCESS read-write
   STATUS      current
   DESCRIPTION
       "Try again"
        ::= { aaaSubLoginUI 28 }
     -- AAA WEB SUB PAGE NO USER ID ERROR
        aaaErrorUserIdMissing OBJECT-TYPE
        SYNTAX       DisplayString(SIZE(0..218))
        MAX-ACCESS read-write
        STATUS       current
        DESCRIPTION
           "The User ID you have entered cannot be found. Please try another"
        ::= { aaaSubLoginUI 29 }
     -- AAA WEB SUB PAGE INVALID USER ID ERROR
   aaaErrorUserIdTaken OBJECT-TYPE
   SYNTAX      DisplayString(SIZE(0..218))
   MAX-ACCESS read-write
   STATUS      current
   DESCRIPTION
       "The User ID you have entered is already taken. Please try another"
        ::= { aaaSubLoginUI 30 }
     -- AAA WEB SUB PAGE WE ARE SORRY ERROR
         aaaErrorWeAreSorry OBJECT-TYPE
         SYNTAX      DisplayString(SIZE(0..218))
         MAX-ACCESS read-write
         STATUS      current
         DESCRIPTION
             "We are sorry"
        ::= { aaaSubLoginUI 31 }
     -- AAA WEB SUB PAGE NOT A WHOLE NUMBER ERROR
         aaaErrorWholeNumber OBJECT-TYPE
         SYNTAX      DisplayString(SIZE(0..218))
         MAX-ACCESS read-write
         STATUS      current
         DESCRIPTION
             "This field must contain a whole number value, with no decimals"
        ::= { aaaSubLoginUI 32 }
     -- AAA WEB SUB PAGE CHECK USR ID AND PASSWD ERROR
   aaaErrorYourAccount OBJECT-TYPE
   SYNTAX      DisplayString(SIZE(0..218))
   MAX-ACCESS read-write
   STATUS      current
   DESCRIPTION
       "Your account was not found. Please check your Username and Password"
        ::= { aaaSubLoginUI 33 }
    -- AAA WEB SUB PAGE SELECT THE BILLING MODE MESSAGE
        aaaMessageBillingMode OBJECT-TYPE
        SYNTAX       DisplayString(SIZE(0..218))
        MAX-ACCESS read-write
        STATUS       current
        DESCRIPTION
           "Please select the Billing Mode"
        ::= { aaaSubLoginUI 34 }
     -- AAA WEB SUB PAGE BILL BY CREDIT CARD MESSAGE
      aaaMessagebyCreditCard OBJECT-TYPE
      SYNTAX      DisplayString(SIZE(0..218))
      MAX-ACCESS read-write
      STATUS      current
      DESCRIPTION
          "Bill by Credit Card"
        ::= { aaaSubLoginUI 35 }
     -- AAA WEB SUB PAGE BILL BY HOTEL ROOM MESSAGE
   aaaMessagebyHotelRoom OBJECT-TYPE
   SYNTAX      DisplayString(SIZE(0..218))
   MAX-ACCESS read-write
   STATUS      current
   DESCRIPTION
       "Bill by Hotel Room"
       ::= { aaaSubLoginUI 36 }
     -- AAA WEB SUB PAGE USER ID MESSAGE
   aaaMessageChooseUsername OBJECT-TYPE
   SYNTAX      DisplayString(SIZE(0..218))
   MAX-ACCESS read-write
   STATUS      current
   DESCRIPTION
       "Choose a User ID (optional)"
        ::= { aaaSubLoginUI 37 }
     -- AAA WEB SUB PAGE PASSWORD MESSAGE
        aaaMessageChoosePasswd1 OBJECT-TYPE
        SYNTAX       DisplayString(SIZE(0..218))
        MAX-ACCESS read-write
        STATUS       current
        DESCRIPTION
            "Choose a Password (optional)"
        ::= { aaaSubLoginUI 38 }
     -- AAA WEB SUB PAGE RETYPE PASSWORD MESSAGE
   aaaMessageChoosePasswd2 OBJECT-TYPE
   SYNTAX      DisplayString(SIZE(0..218))
   MAX-ACCESS read-write
   STATUS      current
   DESCRIPTION
       "Retype the Password (if entered above)"
        ::= { aaaSubLoginUI 39 }
     -- AAA WEB SUB PAGE FREE ACCESS TO INTERNET MESSAGE
      aaaMessageFreeInternet OBJECT-TYPE
      SYNTAX      DisplayString(SIZE(0..218))
      MAX-ACCESS read-write
      STATUS      current
      DESCRIPTION
          "Free access to the Internet"
        ::= { aaaSubLoginUI 40 }
     -- AAA WEB SUB PAGE A NEW USER MESSAGE
      aaaMessageNewUserLogin OBJECT-TYPE
      SYNTAX      DisplayString(SIZE(0..218))
      MAX-ACCESS read-write
      STATUS      current
      DESCRIPTION
          "Are you a new user? Click this button"
        ::= { aaaSubLoginUI 41 }
     -- AAA WEB SUB PAGE AN EXISTING USER MESSAGE
         aaaMessageOldUserLogin OBJECT-TYPE
         SYNTAX      DisplayString(SIZE(0..218))
         MAX-ACCESS read-write
         STATUS      current
         DESCRIPTION
          "Are you an existing user?"
         ::= { aaaSubLoginUI 42 }
     -- AAA WEB SUB PAGE IF NOT CORREDCT GO BACK PREVIOUS MESSAGE
   aaaMessagePurchaseOK1 OBJECT-TYPE
   SYNTAX      DisplayString(SIZE(0..218))
   MAX-ACCESS read-write
   STATUS      current
   DESCRIPTION
       "If this is not correct, please go back to the previous page"
        ::= { aaaSubLoginUI 43 }
     -- AAA WEB SUB PAGE AND MAKE CHANGES MESSAGE
      aaaMessagePurchaseOK2 OBJECT-TYPE
      SYNTAX      DisplayString(SIZE(0..218))
      MAX-ACCESS read-write
      STATUS      current
      DESCRIPTION
          "and make the necessary changes"
        ::= { aaaSubLoginUI 44 }
     -- AAA WEB SUB PAGE SELECT PURCHASE TIME MESSAGE
      aaaMessagePurchaseSelect OBJECT-TYPE
      SYNTAX      DisplayString(SIZE(0..218))
      MAX-ACCESS read-write
      STATUS      current
      DESCRIPTION
          "Please select purchase time"
        ::= { aaaSubLoginUI 45 }
     -- AAA WEB SUB PAGE REQUEST WAS DECLINED MESSAGE
   aaaMessageRequestFailed OBJECT-TYPE
   SYNTAX      DisplayString(SIZE(0..218))
   MAX-ACCESS read-write
   STATUS      current
   DESCRIPTION
            "Your request was declined"
        ::= { aaaSubLoginUI 49 }
     -- AAA WEB SUB PAGE REQUEST WAS SUCCESSFULL MESSAGE
      aaaMessageRequestGranted OBJECT-TYPE
      SYNTAX      DisplayString(SIZE(0..218))
      MAX-ACCESS read-write
      STATUS      current
      DESCRIPTION
          "Your request was successful"
        ::= { aaaSubLoginUI 50 }
     -- AAA WEB SUB PAGE THANKS FOR BUSINESS MESSAGE
   aaaMessageThankYou OBJECT-TYPE
   SYNTAX      DisplayString(SIZE(0..218))
   MAX-ACCESS read-write
   STATUS      current
   DESCRIPTION
       "Thank you for your business"
        ::= { aaaSubLoginUI 51}
     -- AAA WEB SUB PAGE VERIFYING YOUR ACCOUNT MESSAGE
         aaaMessageVerifying OBJECT-TYPE
         SYNTAX      DisplayString(SIZE(0..218))
         MAX-ACCESS read-write
         STATUS      current
         DESCRIPTION
            "We are verifying your account. Please wait"
        ::= { aaaSubLoginUI 52 }
     -- AAA WEB SUB PAGE BILLED DIRECTLY BY HOTEL MESSAGE
         aaaMessageYourHotel OBJECT-TYPE
         SYNTAX      DisplayString(SIZE(0..218))
         MAX-ACCESS read-write
         STATUS      current
         DESCRIPTION
            "You will be billed directly by your hotel"
        ::= { aaaSubLoginUI 53 }
     -- AAA WEB SUB PAGE PURCHASE INET ACCESS MESSAGE
   aaaMessageYourPurchase OBJECT-TYPE
   SYNTAX      DisplayString(SIZE(0..218))
   MAX-ACCESS read-write
   STATUS      current
   DESCRIPTION
       "You will be purchasing Internet access with these options"
        ::= { aaaSubLoginUI 54 }

   aaaPartnerImageOn OBJECT-TYPE
   SYNTAX     INTEGER { disabled(0), enabled(1) }
   MAX-ACCESS read-write
   STATUS     current
   DESCRIPTION
      "Setting this value to (1) will enable Partner Image splashscreen.
       Setting this value to (0) will disable this feature.
       Note: You must reboot for changes to take effect."
   ::= { aaaSubLoginUI 55 }

   aaaPartnerImageFileName OBJECT-TYPE
   SYNTAX     DisplayString(SIZE(1..32))
   MAX-ACCESS read-write
   STATUS     current
   DESCRIPTION
      "File Name of the Partner Image.  Note: You must reboot for changes to take effect."
   ::= { aaaSubLoginUI 56 }


  ------------------------
  -- AAA SUB POST SESSION
  ------------------------
     aaaSubPostSession     OBJECT IDENTIFIER ::= { aaa 17 }

       aaaSubGoodbyePage     OBJECT IDENTIFIER ::= { aaaSubPostSession 1 }

       -- AAA GOODBYE PAGE ON
               aaaSubGPEnable OBJECT-TYPE
               SYNTAX      INTEGER { disabled(0), enabled(1) }
               MAX-ACCESS  read-write
               STATUS      current
               DESCRIPTION
                       "Enables IWS Goodbye Page"
               ::= { aaaSubGoodbyePage 1 }

       -- AAA GOODBYE PAGE IP ADDRESS ON
               aaaSubGPIPAddressOn OBJECT-TYPE
               SYNTAX      INTEGER { disabled(0), enabled(1) }
               MAX-ACCESS  read-write
               STATUS      current
               DESCRIPTION
                       "Show IP Address on IWS Goodbye Page "
               ::= { aaaSubGoodbyePage 2 }

       -- AAA GOODBYE PAGE AUTHEN TYPE ON
               aaaSubGPAuthenTypeOn OBJECT-TYPE
               SYNTAX      INTEGER { disabled(0), enabled(1) }
               MAX-ACCESS  read-write
               STATUS      current
               DESCRIPTION
                       "Show Authen Type on IWS Goodbye Page "
               ::= { aaaSubGoodbyePage 3 }

       -- AAA GOODBYE PAGE START TIME ON
               aaaSubGPStartTimeOn OBJECT-TYPE
               SYNTAX      INTEGER { disabled(0), enabled(1) }
               MAX-ACCESS  read-write
               STATUS      current
               DESCRIPTION
                       "Show Start Time on IWS Goodbye Page "
               ::= { aaaSubGoodbyePage 4 }


       -- AAA GOODBYE PAGE STOP TIME ON
               aaaSubGPStopTimeOn OBJECT-TYPE
               SYNTAX      INTEGER { disabled(0), enabled(1) }
               MAX-ACCESS  read-write
               STATUS      current
               DESCRIPTION
                       "Show Stop Time on IWS Goodbye Page "
               ::= { aaaSubGoodbyePage 5 }


       -- AAA GOODBYE PAGE BYTE SENT ON
               aaaSubGPByteSentOn OBJECT-TYPE
               SYNTAX      INTEGER { disabled(0), enabled(1) }
               MAX-ACCESS  read-write
               STATUS      current
               DESCRIPTION
                       "Show Byte Sent on IWS Goodbye Page "
               ::= { aaaSubGoodbyePage 6 }


       -- AAA GOODBYE PAGE BYTE RECEIVE ON
               aaaSubGPByteReceivedOn OBJECT-TYPE
               SYNTAX      INTEGER { disabled(0), enabled(1) }
               MAX-ACCESS  read-write
               STATUS      current
               DESCRIPTION
                       "Show Byte Received on IWS Goodbye Page "
               ::= { aaaSubGoodbyePage 7 }


       -- AAA GOODBYE PAGE HYPERLINK ON
               aaaSubGPHyperlinkOn OBJECT-TYPE
               SYNTAX      INTEGER { disabled(0), enabled(1) }
               MAX-ACCESS  read-write
               STATUS      current
               DESCRIPTION
                       "Show Hyperlink on IWS Goodbye Page "
               ::= { aaaSubGoodbyePage 8 }


       -- AAA GOODBYE PAGE HYPERLINK
               aaaSubGPHyperlink OBJECT-TYPE
               SYNTAX      DisplayString(SIZE(0..237))
               MAX-ACCESS  read-write
               STATUS      current
               DESCRIPTION
                       "Show Jump To Hyperlink on IWS Goodbye Page "
               ::= { aaaSubGoodbyePage 9 }


       -- AAA GOODBYE PAGE SESSION SUMMARY LABEL
          aaaSubGPSessionSummaryLabel OBJECT-TYPE
          SYNTAX     DisplayString(SIZE(0..218))
          MAX-ACCESS  read-write
          STATUS     current
          DESCRIPTION
                  "Goodbye Page Session Summary Label"
          ::= { aaaSubGoodbyePage 10 }


       -- AAA GOODBYE PAGE SUB IP ADDRESS LABEL
          aaaSubGPSubIPAddressLabel OBJECT-TYPE
          SYNTAX     DisplayString(SIZE(0..218))
          MAX-ACCESS  read-write
          STATUS     current
          DESCRIPTION
                  "Goodbye Page Subscriber IP Address Label"
          ::= { aaaSubGoodbyePage 11 }

       -- AAA GOODBYE PAGE ATHENTIFICATION TYPE LABEL
          aaaSubGPAuthenTypeLabel OBJECT-TYPE
          SYNTAX     DisplayString(SIZE(0..218))
          MAX-ACCESS  read-write
          STATUS     current
          DESCRIPTION
                  "Goodbye Page Subscriber Authen Type Label"
          ::= { aaaSubGoodbyePage 12 }

       -- AAA GOODBYE PAGE START TIME LABEL
          aaaSubGPStartTimeLabel OBJECT-TYPE
          SYNTAX     DisplayString(SIZE(0..218))
          MAX-ACCESS  read-write
          STATUS     current
          DESCRIPTION
                  "Goodbye Page Start Time Label"
          ::= { aaaSubGoodbyePage 13 }

       -- AAA GOODBYE PAGE STOP TIME LABEL
          aaaSubGPStopTimeLabel OBJECT-TYPE
          SYNTAX     DisplayString(SIZE(0..218))
          MAX-ACCESS  read-write
          STATUS     current
          DESCRIPTION
                  "Goodbye Page Stop Time Label"
          ::= { aaaSubGoodbyePage 14 }

       -- AAA GOODBYE PAGE BYTE SENT LABEL
          aaaSubGPByteSentLabel OBJECT-TYPE
          SYNTAX     DisplayString(SIZE(0..218))
          MAX-ACCESS  read-write
          STATUS     current
          DESCRIPTION
                  "Goodbye Page Byte Sent Label"
          ::= { aaaSubGoodbyePage 15 }

        -- AAA GOODBYE PAGE BYTE SENT LABEL
           aaaSubGPByteReceivedLabel OBJECT-TYPE
           SYNTAX      DisplayString(SIZE(0..218))
           MAX-ACCESS  read-write
           STATUS      current
           DESCRIPTION
                   "Goodbye Page Byte Received Label"
           ::= { aaaSubGoodbyePage 16 }


       -- AAA GOODBYE PAGE HYPERTEXT URL LABEL
          aaaSubGPHypertextURLLabel OBJECT-TYPE
          SYNTAX    DisplayString(SIZE(0..218))
          MAX-ACCESS   read-write
          STATUS    current
          DESCRIPTION
                  "Goodbye Page Hypertext URL Label"
          ::= { aaaSubGoodbyePage 17 }


  -------------------
  -- AAA SUBSCRIBER
  -------------------
     aaaSubscriber     OBJECT IDENTIFIER ::= { aaa 18 }
        --
        -- SUBSCRIBER CURRENT TABLE
        --

     aaaSubCurrTable OBJECT-TYPE
       SYNTAX  SEQUENCE OF AaaSubCurrTableEntry
       MAX-ACCESS  not-accessible
       STATUS  current
       DESCRIPTION
         "List of current subscribers."
       ::= { aaaSubscriber 1 }

     aaaSubCurrTableEntry OBJECT-TYPE
       SYNTAX  AaaSubCurrTableEntry
       MAX-ACCESS  not-accessible
       STATUS  current
       DESCRIPTION
         "A subscriber entry."
       INDEX  { subIndex }
       ::= { aaaSubCurrTable 1 }

     AaaSubCurrTableEntry ::=
        SEQUENCE
        {
          subIndex        Integer32,
          subMac          DisplayString,
          subIp           IpAddress,
          subPort         Integer32,
          subName         DisplayString,
          subBwUp         Integer32,
          subBwDown       Integer32,
          subAaaState     DisplayString,
          subExpiration   DisplayString,
          subIdleTimeout  DisplayString,
          subBytesSent    Counter32,
          subBytesRec     Counter32,
          subBytesTotal   Counter32,
          subProxy        DisplayString,
          subSsid         DisplayString,
          subStatus       RowStatus
        }

     subIndex OBJECT-TYPE
       SYNTAX      Integer32
       MAX-ACCESS  read-only
       STATUS      current
       DESCRIPTION
          "Subscriber Index."
       ::= { aaaSubCurrTableEntry 1 }

     subMac OBJECT-TYPE
       SYNTAX      DisplayString
       MAX-ACCESS  read-only
       STATUS      current
       DESCRIPTION
          "Physical Address of the Subscriber."
       ::= { aaaSubCurrTableEntry 2 }

     subIp OBJECT-TYPE
       SYNTAX      IpAddress
       MAX-ACCESS  read-only
       STATUS      current
       DESCRIPTION
          "IP Address of the Subscriber."
       ::= { aaaSubCurrTableEntry 3 }

     subPort OBJECT-TYPE
       SYNTAX      Integer32
       MAX-ACCESS  read-only
       STATUS      current
       DESCRIPTION
          "Port of the Subscriber."
       ::= { aaaSubCurrTableEntry 4 }

     subName OBJECT-TYPE
       SYNTAX      DisplayString
       MAX-ACCESS  read-only
       STATUS      current
       DESCRIPTION
          "Name of the Subscriber."
       ::= { aaaSubCurrTableEntry 5 }

     subBwUp OBJECT-TYPE
       SYNTAX      Integer32
       MAX-ACCESS  read-only
       STATUS      current
       DESCRIPTION
          "Uploading Bandwidth granted to the Subscriber."
       ::= { aaaSubCurrTableEntry 6 }

     subBwDown OBJECT-TYPE
       SYNTAX      Integer32
       MAX-ACCESS  read-only
       STATUS      current
       DESCRIPTION
          "Downloading Bandwidth granted to the Subscriber."
       ::= { aaaSubCurrTableEntry 7 }

     subAaaState  OBJECT-TYPE
       SYNTAX      DisplayString
       MAX-ACCESS  read-only
       STATUS      current
       DESCRIPTION
          "The AAA state of the Subscriber."
       ::= { aaaSubCurrTableEntry 8 }

     subExpiration  OBJECT-TYPE
       SYNTAX      DisplayString
       MAX-ACCESS  read-only
       STATUS      current
       DESCRIPTION
          "Expiration Info of the Subscriber."
       ::= { aaaSubCurrTableEntry 9 }

     subIdleTimeout OBJECT-TYPE
       SYNTAX      DisplayString
       MAX-ACCESS  read-only
       STATUS      current
       DESCRIPTION
          "Time before the subscriber gets logged off due to inactivity."
       ::= { aaaSubCurrTableEntry 10 }

     subBytesSent OBJECT-TYPE
       SYNTAX      Counter32
       MAX-ACCESS  read-only
       STATUS      current
       DESCRIPTION
          "Bytes sent by the Subscriber, units are MBytes"
       ::= { aaaSubCurrTableEntry 11 }

     subBytesRec OBJECT-TYPE
       SYNTAX      Counter32
       MAX-ACCESS  read-only
       STATUS      current
       DESCRIPTION
          "Bytes received by the Subscriber, units are MBytes"
       ::= { aaaSubCurrTableEntry 12 }

     subBytesTotal OBJECT-TYPE
       SYNTAX      Counter32
       MAX-ACCESS  read-only
       STATUS      current
       DESCRIPTION
          "Total Bytes sent and received by the Subscriber, units are MBytes."
       ::= { aaaSubCurrTableEntry 13 }

     subProxy OBJECT-TYPE
       SYNTAX      DisplayString
       MAX-ACCESS  read-only
       STATUS      current
         DESCRIPTION
          "Indicates if the subscriber is proxied or not."
       ::= { aaaSubCurrTableEntry 14 }

     subSsid OBJECT-TYPE
       SYNTAX      DisplayString
       MAX-ACCESS  read-only
       STATUS      current
         DESCRIPTION
          "For wireless subscribers this entry shows their SSID."
       ::= { aaaSubCurrTableEntry 15 }

     subStatus OBJECT-TYPE
       SYNTAX      RowStatus
       MAX-ACCESS  read-write
       STATUS      current
       DESCRIPTION
          "Status of the Subscriber Current table entry. "
       ::= { aaaSubCurrTableEntry 16 }

--
-- AUTHORIZED SUBSCRIBER TABLE
--

     aaaAuthSubTable OBJECT-TYPE
       SYNTAX  SEQUENCE OF AaaAuthSubTableEntry
       MAX-ACCESS  not-accessible
       STATUS      current
       DESCRIPTION
         "List of authorized subscribers."
       ::= { aaaSubscriber 2 }

        aaaAuthSubTableEntry OBJECT-TYPE
        SYNTAX  AaaAuthSubTableEntry
        MAX-ACCESS  not-accessible
        STATUS      current
        DESCRIPTION
           "A subscriber entry."
        INDEX  { authSubIndex }
        ::= { aaaAuthSubTable 1 }

        AaaAuthSubTableEntry ::=
        SEQUENCE
        {
          authSubIndex          Integer32,
          authSubType         INTEGER,
          authSubDhcpAddrType   INTEGER,
          authSubDevicePort     Integer32,
          authSubMac            DisplayString,
          authSubIp             IpAddress,
          authSubName           DisplayString,
          authSubPassword     DisplayString,
          authSubCountDown      INTEGER,
          authSubExpTimeHrs     Integer32,
          authSubExpTimeMins    Integer32,
          authSubAmtPaid     DisplayString,
          authSubAmtLeft     DisplayString,
          authSubUser1       DisplayString,
          authSubUser2       DisplayString,
          authSubBwUp         Integer32,
          authSubBwDown       Integer32,
          authSubConfirmation   DisplayString,
          authSubStatus       RowStatus
        }

       authSubIndex OBJECT-TYPE
       SYNTAX     Integer32
       MAX-ACCESS read-only
       STATUS     current
       DESCRIPTION
          "Subscriber Index."
       ::= { aaaAuthSubTableEntry 1 }

       authSubType OBJECT-TYPE
       SYNTAX     INTEGER { subscriber(0), device(1) }
       MAX-ACCESS read-write
       STATUS     current
       DESCRIPTION
          "Set to 0 if adding a subscriber, to 1 if adding a device."
       ::= { aaaAuthSubTableEntry 2 }

       authSubDhcpAddrType OBJECT-TYPE
       SYNTAX     INTEGER { private(0), public(1) }
       MAX-ACCESS read-write
       STATUS     current
       DESCRIPTION
          "Set to 0 for private pool, set to 1 for public pool.
          Note: only used if subscriber is configured for DHCP."
       ::= { aaaAuthSubTableEntry 3 }

       authSubDevicePort OBJECT-TYPE
       SYNTAX     Integer32
       MAX-ACCESS read-write
       STATUS     current
       DESCRIPTION
          "802.1Q Device Port.
          Note: only if device and Port-Location is 802.1Q two-ways."
       ::= { aaaAuthSubTableEntry 4 }

       authSubMac OBJECT-TYPE
       SYNTAX     DisplayString(SIZE(0..17))
       MAX-ACCESS read-write
       STATUS     current
       DESCRIPTION
          "Physical Address of the subscriber entered in one of the formats:
      001122334455, 00-11-22-33-44-55 or 00:11:22:33:44:55.
      Default value is 00:00:00:00:00:00 if the authSubName is set and
      authSubMac was not entered yet."
       ::= { aaaAuthSubTableEntry 5 }

       authSubIp OBJECT-TYPE
       SYNTAX     IpAddress
       MAX-ACCESS read-write
       STATUS     current
       DESCRIPTION
          "IP Address of the subscriber."
       ::= { aaaAuthSubTableEntry 6 }

       authSubName OBJECT-TYPE
       SYNTAX     DisplayString(SIZE(0..96))
       MAX-ACCESS read-write
       STATUS     current
       DESCRIPTION
          "Name of the subscriber."
       ::= { aaaAuthSubTableEntry 7 }

       authSubPassword OBJECT-TYPE
       SYNTAX     DisplayString(SIZE(0..32))
       MAX-ACCESS read-write
       STATUS     current
       DESCRIPTION
          "Password of the subscriber."
       ::= { aaaAuthSubTableEntry 8 }

        authSubCountDown OBJECT-TYPE
        SYNTAX     INTEGER { disabled(0), enabled(1) }
       MAX-ACCESS read-write
       STATUS     current
       DESCRIPTION
          "Set to 1 to enable count-down after login for a subscriber, 0 to disable.
           Note: username and password should have been entered before, in order
           to enable this option.  Also, expiration time must be entered after enabling
           this option, in order for it to work properly."
       ::= { aaaAuthSubTableEntry 9 }

       authSubExpTimeHrs OBJECT-TYPE
  SYNTAX     Integer32
  MAX-ACCESS read-write
  STATUS     current
  DESCRIPTION
     "Expiration time (hours) of the subscriber."
       ::= { aaaAuthSubTableEntry 10 }

     authSubExpTimeMins OBJECT-TYPE
  SYNTAX     Integer32 (0..59)
  MAX-ACCESS read-write
  STATUS     current
  DESCRIPTION
      "Expiration time (mins) of the subscriber."
       ::= { aaaAuthSubTableEntry 11 }

     authSubAmtPaid OBJECT-TYPE
       SYNTAX     DisplayString(SIZE(0..17))
       MAX-ACCESS read-write
       STATUS     current
       DESCRIPTION
          "Amount paid by the subscriber shown in formats: dd.cc or dd.
      Default is 0.00. Entering dd will result in dd.00.
      d=dollar, c=cent."
       ::= { aaaAuthSubTableEntry 12 }

     authSubAmtLeft OBJECT-TYPE
       SYNTAX     DisplayString
       MAX-ACCESS read-only
       STATUS     current
       DESCRIPTION
          "Currency amount left when subscriber who has purchased access
     moves to a free plan. Formats same as in authSubAmtPaid."
       ::= { aaaAuthSubTableEntry 13 }

       authSubUser1 OBJECT-TYPE
       SYNTAX     DisplayString(SIZE(0..15))
       MAX-ACCESS read-write
       STATUS     current
       DESCRIPTION
          "Optional field.  Used for simple notations about the subscriber."
       ::= { aaaAuthSubTableEntry 14 }

       authSubUser2 OBJECT-TYPE
          SYNTAX     DisplayString(SIZE(0..15))
     MAX-ACCESS read-write
     STATUS     current
          DESCRIPTION
          "Optional field.  Used for simple notations about the subscriber."
       ::= { aaaAuthSubTableEntry 15 }

       authSubBwUp OBJECT-TYPE
          SYNTAX     Integer32
          MAX-ACCESS read-write
          STATUS     current
          DESCRIPTION
          "Uploading Bandwidth granted to the subscriber. Variable in the
      range from 0 to the max value found in bwmUpWanLinkSpeed. (in kbps)"
       ::= { aaaAuthSubTableEntry 16 }

       authSubBwDown OBJECT-TYPE
          SYNTAX     Integer32
          MAX-ACCESS read-write
          STATUS     current
          DESCRIPTION
          "Downloading Bandwidth granted to the subscriber. Variable in the
     range from 0 to the max value found in bwmDownWanLinkSpeed. (in kbps)"
       ::= { aaaAuthSubTableEntry 17 }

       authSubConfirmation OBJECT-TYPE
          SYNTAX     DisplayString
          MAX-ACCESS read-only
          STATUS     current
          DESCRIPTION
          "Confirmation number issued by credit card server."
       ::= { aaaAuthSubTableEntry 18 }

       authSubStatus OBJECT-TYPE
           SYNTAX     RowStatus
           MAX-ACCESS read-write
           STATUS     current
       DESCRIPTION
          "Status of the Authorized Subscriber  table entry."
       ::= { aaaAuthSubTableEntry 19 }

  ------------------------
  -- AAA LOGIN PAGE FAILOVER
  ------------------------
     aaaLoginPageFailover     OBJECT IDENTIFIER ::= { aaa 25 }

     aaaLoginPageFailoverOn OBJECT-TYPE
           SYNTAX      INTEGER { disabled(0), enabled(1) }
           MAX-ACCESS  read-write
           STATUS      current
           DESCRIPTION
                 "Enables Login Page Failover"
           ::= { aaaLoginPageFailover 1 }

      --
      -- AAA LOGIN PAGE FAILOVER STATUS TABLE
      --

        aaaLpfStatusTable OBJECT-TYPE
        SYNTAX  SEQUENCE OF AaaLpfStatusTableEntry
        MAX-ACCESS  not-accessible
        STATUS      current
        DESCRIPTION
           "List of External Login Page servers currently being tracked."
        ::= { aaaLoginPageFailover 2 }

        aaaLpfStatusTableEntry OBJECT-TYPE
        SYNTAX  AaaLpfStatusTableEntry
        MAX-ACCESS  not-accessible
        STATUS      current
        DESCRIPTION
           "An External Login Page server entry."
        INDEX  { lpfEntryIndex }
        ::= { aaaLpfStatusTable 1 }

        AaaLpfStatusTableEntry ::=
        SEQUENCE
        {
          lpfEntryIndex         Integer32,
          lpfEntryNickname DisplayString,
          lpfEntryOnlineStatus INTEGER
        }

       lpfEntryIndex OBJECT-TYPE
       SYNTAX     Integer32
       MAX-ACCESS read-only
       STATUS     current
       DESCRIPTION
          "External Login Page server index."
       ::= { aaaLpfStatusTableEntry 1 }

       lpfEntryNickname OBJECT-TYPE
       SYNTAX     DisplayString(SIZE(0..19))
       MAX-ACCESS read-only
       STATUS     current
       DESCRIPTION
          "Symbolic Name of the Login Page server."
       ::= { aaaLpfStatusTableEntry 2 }

       lpfEntryOnlineStatus OBJECT-TYPE
       SYNTAX      INTEGER { unknown(0), online(1), offline(2) }
       MAX-ACCESS  read-only
       STATUS      current
       DESCRIPTION
          "Status of an External Login Page server."
       ::= { aaaLpfStatusTableEntry 3 }

  --------------------
  -- RADIUS History  SYSLOGGING
  --------------------

   -- RADIUS History Logging ON
     radHistSysloggingOn OBJECT-TYPE
     SYNTAX      INTEGER { disabled(0), enabled (1) }
     MAX-ACCESS  read-write
     STATUS      current
     DESCRIPTION
        "Setting this value to (1) will enable logging (via standard
        SYSLOG) of RADIUS packets.  Setting this value to (0) will
        disable RADIUS history logging. (NOTE: Which types of RADIUS
        packets will be logged is specified using other parameters.)"
        ::= { aaaSubscriber 3 }

   -- RADIUS History LOG NUMBER
     radHistSyslogNumber   OBJECT-TYPE
     SYNTAX      Integer32(0..7)
     MAX-ACCESS  read-write
     STATUS      current
     DESCRIPTION
        "The log number (0-7 of standard SYSLOG) for AAA logging."
        ::= { aaaSubscriber 4 }


  -- RADIUS History LOG FILTER
     radHistSyslogFilter OBJECT-TYPE
     SYNTAX      INTEGER {emergency(0), alert(1), critical(2), error(3),
           warning(4), notice(5), info(6), debug(7) }
     MAX-ACCESS  read-write
     STATUS      current
     DESCRIPTION
    "Select the filter level for RADIUS History Logs
     Available settings: Emergency(0), Alert(1), Critical(2), Error(3),
               Warning(4), Notice(5), Info(6), Debug(7)"
     ::= { aaaSubscriber 8 }

   -- RADIUS History SERVER IP
     radHistSyslogServerIp OBJECT-TYPE
     SYNTAX      IpAddress
     MAX-ACCESS  read-write
     STATUS      current
     DESCRIPTION
        "IP address of the SYSLOG server to receive AAA messages."
     ::= { aaaSubscriber 5 }

   -- RADIUS History LOG SAVE TO FILE ON
     radHistSyslogSaveToFile OBJECT-TYPE
     SYNTAX      INTEGER { disabled(0), enabled (1) }
     MAX-ACCESS  read-write
     STATUS      current
     DESCRIPTION
        "Setting this value to (1) will enable saving of RADIUS History logs
        to file.  Setting this value to (0) will disable storing of
        AAA logs in a file."
        ::= { aaaSubscriber 9 }


   --   Enable/Disable RADIUS Proxy Accounting Session History Logfile
     radProxyAcctHistLog     OBJECT-TYPE
     SYNTAX      INTEGER { disabled(0), enabled(1) }
     MAX-ACCESS  read-write
     STATUS      current
     DESCRIPTION
         " Setting this value to (1) enables the logging of RADIUS Proxy Accounting
         packets to a logfile on the system flash. Setting it to zero disables such
         logging and purges the history logfile."
      ::= { aaaSubscriber 6}

   --   Enable/Disable RADIUS Proxy Accounting Session History Sslogging
     radProxyAcctHistSyslog     OBJECT-TYPE
     SYNTAX      INTEGER { disabled(0), enabled(1) }
     MAX-ACCESS  read-write
     STATUS      current
     DESCRIPTION
         " If RADIUS History Syslogging is enabled, then setting this value to (1)
         causes RADIUS Proxy accounting packets to be included in that syslogging.
         Setting it to zero causes these packets not to be included."
      ::= { aaaSubscriber 7}

  -------------------
  -- AAA RADIUS
  -------------------
     aaaRadius         OBJECT IDENTIFIER ::= { aaa 19 }

     -- AAA RADIUS Routing Mode
        aaaRadiusRoutingMode OBJECT-TYPE
        SYNTAX      INTEGER { disabled(0), realm-based(1), fixed(2) }
        MAX-ACCESS  read-write
        STATUS      current
        DESCRIPTION
              "Set to 0 to disable radius client operation.
               Set to 1 to enable realm-based routing of RADIUS requests.
               Set to 2 to route all RADIUS requests to the default RADIUS
               service profile.
               Note: If trying to set this value returns an error, please check
               to see if you have a valid license for this feature."
        ::= { aaaRadius 1 }

     -- AAA RADIUS DEFAULT SERVICE PROFILE
        aaaRadiusDefProf OBJECT-TYPE
        SYNTAX      DisplayString(SIZE(0..40))
        MAX-ACCESS  read-write
        STATUS      current
        DESCRIPTION
           "Set the default RADIUS service profile to be used for
           otherwise un-routeable RADIUS requests. Mandatory if
           the routing mode is set to fixed. There must be a profile
           defined with the specified name."
        ::= { aaaRadius 3 }

     -- AAA RADIUS CACHE ON
        aaaRadiusCacheOn OBJECT-TYPE
        SYNTAX      INTEGER { disabled(0), enabled(1) }
        MAX-ACCESS  read-write
        STATUS      current
        DESCRIPTION
           "Set to 1 to enable radius profile caching, 0 to disable."
        ::= { aaaRadius 5 }

     -- AAA RADIUS DEFAULT IDLE
        aaaRadiusDefaultIdle OBJECT-TYPE
        SYNTAX      Integer32
        MAX-ACCESS  read-write
        STATUS      current
        DESCRIPTION
           "Set default timeout for radius subscribers."
        ::= { aaaRadius 11 }

     -- AAA RADIUS NAS_ID_ON
        aaaRadiusNasIdOn OBJECT-TYPE
        SYNTAX      INTEGER { disabled(0), enabled(1) }
        MAX-ACCESS  read-write
        STATUS      current
        DESCRIPTION
           "Set to 1 to Send NAS ID, 0 to disable."
        ::= { aaaRadius 12 }

     -- AAA RADIUS NAS ID
        aaaRadiusNasId OBJECT-TYPE
        SYNTAX      DisplayString(SIZE(0..32))
        MAX-ACCESS  read-write
        STATUS      current
        DESCRIPTION
           "Set the NAS Identifier."
        ::= { aaaRadius 13 }

     -- AAA RADIUS NAS IP ON
        aaaRadiusNasIpOn OBJECT-TYPE
        SYNTAX      INTEGER { disabled(0), enabled(1) }
        MAX-ACCESS  read-write
        STATUS      current
        DESCRIPTION
           "Set to 1 to Send NAS IP, 0 to disable."
        ::= { aaaRadius 14 }

     -- AAA RADIUS NAS PORT TYPE ON
        aaaRadiusNasPortOn OBJECT-TYPE
        SYNTAX      INTEGER { disabled(0), enabled(1) }
        MAX-ACCESS  read-write
        STATUS      current
        DESCRIPTION
           "Set to 1 to Send NAS Port Type, 0 to disable."
        ::= { aaaRadius 15 }

     -- AAA RADIUS NAS PORT TYPE
        aaaRadiusNasPortType OBJECT-TYPE
        SYNTAX      Integer32
        MAX-ACCESS  read-write
        STATUS      current
        DESCRIPTION
           "Set the NAS Port Type."
        ::= { aaaRadius 16 }

     -- AAA RADIUS FIP ON
        aaaRadiusFipOn OBJECT-TYPE
        SYNTAX      INTEGER { disabled(0), enabled(1) }
        MAX-ACCESS  read-write
        STATUS      current
        DESCRIPTION
           "Set to 1 to Send Frame IP, 0 to disable."
        ::= { aaaRadius 17 }

      -- AAA RADIUS URL REDIRECTION ON
        aaaRadiusRedUrlOn OBJECT-TYPE
        SYNTAX      INTEGER { disabled(0), enabled(1) }
        MAX-ACCESS  read-write
        STATUS      current
        DESCRIPTION
           "Set to 1 to support URL redirection, 0 to disable."
        ::= { aaaRadius 18 }

      -- AAA RADIUS GOODBYE URL ON
        aaaRadiusGoodbyeUrlOn OBJECT-TYPE
        SYNTAX      INTEGER { disabled(0), enabled(1) }
        MAX-ACCESS  read-write
        STATUS      current
        DESCRIPTION
           "Set to 1 to support Goodbye URL redirection, 0 to disable."
        ::= { aaaRadius 19 }

      -- AAA RADIUS FORGOT PASSWORD URL ON
        aaaRadiusForgotPasswordUrlOn OBJECT-TYPE
        SYNTAX         INTEGER { disabled(0), enabled(1) }
        MAX-ACCESS         read-write
        STATUS         current
        DESCRIPTION
           "Set to 1 to support forgot password URL redirection, 0 to disable."
        ::= { aaaRadius 20 }

      -- AAA RADIUS FORGOT PASSWORD URL
        aaaRadiusForgotPasswordUrl OBJECT-TYPE
        SYNTAX         DisplayString(SIZE(1..238))
        MAX-ACCESS         read-write
        STATUS         current
        DESCRIPTION
           "URL of the RADIUS Forgot Password"
        ::= { aaaRadius 21 }


      -- AAA RADIUS SUBNET ATTRIBUTE ON
        aaaRadiusSubnetAttrOn OBJECT-TYPE
        SYNTAX         INTEGER { disabled(0), enabled(1) }
        MAX-ACCESS     read-write
        STATUS         current
        DESCRIPTION
           "Set to 1 to support subnet attribute, 0 to disable."
        ::= { aaaRadius 22 }

     -- AAA RADIUS WAN 802.1Q ATTRIBUTE ON
        aaaRadiusNetVlanOn OBJECT-TYPE
        SYNTAX      INTEGER { disabled(0), enabled(1) }
        MAX-ACCESS  read-write
        STATUS      current
        DESCRIPTION
           "Set to 1 to enable, 0 to disable RADIUS based WAN VLAN.
           Note: enabling RADIUS based WAN VLAN will automatically disable
           SSID based WAN VLAN."
        ::= { aaaRadius 23 }

     -- AAA RADIUS WAN 802.1Q DEFAULT TAG ON
        aaaRadiusNetVlanDefaultOn OBJECT-TYPE
        SYNTAX      INTEGER { disabled(0), enabled(1) }
        MAX-ACCESS  read-write
        STATUS      current
        DESCRIPTION
           "Set to 1 to enable default 802.1q tag for system traffic, 0 to disable."
        ::= { aaaRadius 24 }

     -- AAA RADIUS WAN 802.1Q DEFAULT TAG
        aaaRadiusNetVlanDefaultTag OBJECT-TYPE
        SYNTAX         Integer32(1..4094)
        MAX-ACCESS  read-write
        STATUS      current
        DESCRIPTION
           "Set the default 802.1q tag for system traffic."
        ::= { aaaRadius 25 }

     -- AAA RADIUS LOCAL AUTHENTICATION PORT
        aaaRadiusLocalAuthPort OBJECT-TYPE
        SYNTAX      Integer32
        MAX-ACCESS  read-write
        STATUS      current
        DESCRIPTION
           "Local UDP port for communicating with authentication servers. Must be either 0 or
           in the range 1024-5000."
        ::= { aaaRadius 26 }

     -- AAA RADIUS LOCAL AUTHENTICATION PORT
        aaaRadiusLocalAcctPort OBJECT-TYPE
        SYNTAX      Integer32
        MAX-ACCESS  read-write
        STATUS      current
        DESCRIPTION
           "Local UDP port for communicating with accounting servers. Must be either 0 or
           in the range 1024-5000."
        ::= { aaaRadius 27 }

     -- AAA RADIUS LOGIN REFRESH TIME
        aaaRadiusLoginRefresh OBJECT-TYPE
        SYNTAX      Integer32
        MAX-ACCESS  read-write
        STATUS      current
        DESCRIPTION
           "Login refresh time for RADIUS subscribers"
        ::= { aaaRadius 28 }

     -- AAA RADIUS TERMINATION ACTION ON
        aaaRadiusTerminationActionOn OBJECT-TYPE
        SYNTAX      INTEGER { disabled(0), enabled(1) }
        MAX-ACCESS  read-write
        STATUS      current
        DESCRIPTION
           "Set to 1 to support Termination-Action attribute, 0 to disable."
        ::= { aaaRadius 29 }

  ----------------------------------------------------------------------
  --  End AAA MIB
  ----------------------------------------------------------------------

--
-- ACCESS CONTROL
--

     blockTelnetAccessOn OBJECT-TYPE
       SYNTAX         INTEGER { disabled(0), enabled(1) }
       MAX-ACCESS     read-write
       STATUS         current
       DESCRIPTION
         "Set to 1 to enable blocking of all Telnet access, 0 to disable.
          Note: if set to 1, Telnet access will not be allowed, even from
          addresses in the access control IP Table."
       ::= { accessControl 1 }

     blockWebAccessOn OBJECT-TYPE
       SYNTAX         INTEGER { disabled(0), enabled(1) }
       MAX-ACCESS     read-write
       STATUS         current
       DESCRIPTION
         "Set to 1 to enable blocking of all Web access, 0 to disable.
          Note: if set to 1, Web access will not be allowed, even from
          addresses in the access control IP Table."
       ::= { accessControl 2 }

     blockFtpAccessOn OBJECT-TYPE
       SYNTAX         INTEGER { disabled(0), enabled(1) }
       MAX-ACCESS     read-write
       STATUS         current
       DESCRIPTION
         "Set to 1 to enable blocking of all FTP access, 0 to disable.
          Note: if set to 1, FTP access will not be allowed, even from
          addresses in the access control IP Table."
       ::= { accessControl 3 }

  --
  --  Enablement or Disablement of Source IP Access Control List
  --

     accessControlOn OBJECT-TYPE
       SYNTAX         INTEGER { disabled(0), enabled(1) }
       MAX-ACCESS     read-write
       STATUS         current
       DESCRIPTION
         "Set to 1 to enable Source IP Access Control, 0 to disable.
          Note: If trying to set this value returns an error, please check
          to see if you have a valid license for this feature."
       ::= { accessControl 4 }

  --
  --  Access Control List
  --
     accessControlIpTable OBJECT-TYPE
       SYNTAX  SEQUENCE OF AccessControlIpEntry
       MAX-ACCESS  not-accessible
       STATUS  current
       DESCRIPTION
         "Table of Access Control IPs"
       ::= { accessControl 5 }

     accessControlIpEntry OBJECT-TYPE
       SYNTAX  AccessControlIpEntry
       MAX-ACCESS  not-accessible
       STATUS  current
       DESCRIPTION
         " Access Control table entry "
       INDEX   { acIndex }
       ::= { accessControlIpTable 1 }

     AccessControlIpEntry ::=
           SEQUENCE {
                       acIndex         Integer32,
                       acStartAddress  IpAddress,
                       acEndAddress    IpAddress,
                       acStatus        RowStatus
                    }

     acIndex OBJECT-TYPE
       SYNTAX      Integer32
       MAX-ACCESS  read-only
       STATUS      current
       DESCRIPTION
         " access control table index "
       ::= { accessControlIpEntry 2 }

     acStartAddress OBJECT-TYPE
       SYNTAX      IpAddress
       MAX-ACCESS  read-write
       STATUS      current
       DESCRIPTION
         "Access Control range Starting IP address "
       ::= { accessControlIpEntry 4 }

     acEndAddress OBJECT-TYPE
       SYNTAX      IpAddress
       MAX-ACCESS  read-write
       STATUS      current
       DESCRIPTION
         "Access Control range end IP address "
       ::= { accessControlIpEntry 6 }

     acStatus OBJECT-TYPE
       SYNTAX     RowStatus
       MAX-ACCESS read-write
       STATUS     current
       DESCRIPTION
         "Status of the Access Control IP Table entry."
       ::= { accessControlIpEntry 7 }

     blockSFTPAccessOn OBJECT-TYPE
       SYNTAX         INTEGER { disabled(0), enabled(1) }
       MAX-ACCESS     read-write
       STATUS         current
       DESCRIPTION
         "Set to 1 to enable blocking of all SFTP access, 0 to disable.
         Note: if set to 1, SFTP access will not be allowed, even from
         addresses in the access control IP Table."
       ::= { accessControl 6 }

     blockSSHShellAccessOn OBJECT-TYPE
       SYNTAX         INTEGER { disabled(0), enabled(1) }
       MAX-ACCESS     read-write
       STATUS         current
       DESCRIPTION
         "Set to 1 to enable blocking of all SSH Shell access, 0 to disable.
          Note: if set to 1, SSH Shell access will not be allowed, even from
          addresses in the access control IP Table."
       ::= { accessControl 7 }

--
-- BANDWIDTH MANAGEMENT
--

     bandwidthManagementOn OBJECT-TYPE
        SYNTAX         INTEGER { disabled(0), enabled(1) }
        MAX-ACCESS     read-write
        STATUS         current
        DESCRIPTION
           "Set to 1 to enable Bandwidth Management, 0 to disable.
           Note: If trying to set this value returns an error, please check to see if you have a valid license for this feature.
           Note: You must reboot for changes to take effect."
        ::= { bandwidthManagement 1 }

     bwmUpWanLinkSpeed OBJECT-TYPE
        SYNTAX      Integer32
        MAX-ACCESS  read-write
        STATUS      current
        DESCRIPTION
           "Uplink Bandwidth through the Network's WAN Link to control using Bandwidth
           Management.  Note: You must reboot for changes to take effect."
        ::= { bandwidthManagement 3 }

     bwmDownWanLinkSpeed OBJECT-TYPE
        SYNTAX      Integer32
        MAX-ACCESS  read-write
        STATUS      current
        DESCRIPTION
           "Downlink Bandwidth through the Network's WAN link to control using Bandwidth
           Management.  Note: You must reboot for changes to take effect."
        ::= { bandwidthManagement 5 }



--
-- BillRecMirror
--
     brmMirrorOn         OBJECT-TYPE
       SYNTAX         INTEGER { enabled(1), disabled(0) }
       MAX-ACCESS     read-write
       STATUS         current
       DESCRIPTION
        "Setting this value to (1) will cause Bill Record Mirroring to be
         enabled by this unit. Setting this value to (0) will disable Bill Record Mirroring.
         Note: If trying to set this value returns an error, please check to see if you have a valid license for this feature."
       ::=   { billRecMirror 1 }

     brmPropertyId    OBJECT-TYPE
       SYNTAX         DisplayString(SIZE(1..32))
       MAX-ACCESS     read-write
       STATUS         current
       DESCRIPTION
         "Id of the Property the unit is installed in"
       ::=   { billRecMirror 2 }

     brmNseId         OBJECT-TYPE
       SYNTAX         DisplayString(SIZE(1..32))
       MAX-ACCESS     read-only
       STATUS         current
       DESCRIPTION
         "Id of this unit"
       ::=   { billRecMirror 3 }

     brmServerIpPrimary     OBJECT-TYPE
       SYNTAX         IpAddress
       MAX-ACCESS     read-write
       STATUS         current
       DESCRIPTION
         "IP Address of the Primary Mirroring Server"
       ::=   { billRecMirror 4 }

     brmServerUrlPrimary    OBJECT-TYPE
       SYNTAX         DisplayString(SIZE(1..238))
       MAX-ACCESS     read-write
       STATUS         current
       DESCRIPTION
         "URL of the Primary Mirroring Server"
       ::=   { billRecMirror 5 }

     brmServerSecretPrimary OBJECT-TYPE
       SYNTAX         DisplayString(SIZE(0..32))
       MAX-ACCESS     read-write
       STATUS         current
       DESCRIPTION
        "Secret Key of the Primary Mirroring Server"
       ::=   { billRecMirror 6 }

     brmServerPortPrimary   OBJECT-TYPE
       SYNTAX         Integer32
       MAX-ACCESS     read-write
       STATUS         current
       DESCRIPTION
        "Port Number of the Primary Mirroring Server"
       ::=   { billRecMirror 7 }

     brmServerIpSecondary   OBJECT-TYPE
       SYNTAX         IpAddress
       MAX-ACCESS     read-write
       STATUS         current
       DESCRIPTION
        "IP Address of the Secondary Mirroring Server"
       ::=   { billRecMirror 8 }

     brmServerUrlSecondary  OBJECT-TYPE
       SYNTAX         DisplayString(SIZE(1..238))
       MAX-ACCESS     read-write
       STATUS         current
       DESCRIPTION
        "URL of the Secondary Mirroring Server"
       ::=   { billRecMirror 9 }

     brmServerSecretSecondary  OBJECT-TYPE
       SYNTAX         DisplayString(SIZE(0..32))
       MAX-ACCESS     read-write
       STATUS         current
       DESCRIPTION
        "Secret Key of the Secondary Mirroring Server"
       ::=   { billRecMirror 10 }

     brmServerPortSecondary OBJECT-TYPE
       SYNTAX         Integer32
       MAX-ACCESS     read-write
       STATUS         current
       DESCRIPTION
        "Port Number of the Secondary Mirroring Server"
       ::=   { billRecMirror 11 }

     brmServerCCIpOne    OBJECT-TYPE
       SYNTAX         IpAddress
       MAX-ACCESS     read-write
       STATUS         current
       DESCRIPTION
        "IP Address of the First Carbon Copy Server"
       ::=   { billRecMirror 12 }

     brmServerCCUrlOne      OBJECT-TYPE
       SYNTAX         DisplayString(SIZE(1..238))
       MAX-ACCESS     read-write
       STATUS         current
       DESCRIPTION
        "URL of the First Carbon Copy Server"
       ::=   { billRecMirror 13 }

     brmServerCCSecretOne   OBJECT-TYPE
       SYNTAX         DisplayString(SIZE(0..32))
       MAX-ACCESS     read-write
       STATUS         current
       DESCRIPTION
        "Secret Key of the First Carbon Copy Server"
       ::=   { billRecMirror 14 }

     brmServerCCPortOne     OBJECT-TYPE
       SYNTAX         Integer32
       MAX-ACCESS     read-write
       STATUS         current
       DESCRIPTION
        "Port Number of the First Carbon Copy Server"
       ::=   { billRecMirror 15 }

     brmServerCCIpTwo    OBJECT-TYPE
       SYNTAX         IpAddress
       MAX-ACCESS     read-write
       STATUS         current
       DESCRIPTION
        "IP Address of the Second Carbon Copy Server"
       ::=   { billRecMirror 16 }

     brmServerCCUrlTwo      OBJECT-TYPE
       SYNTAX         DisplayString(SIZE(1..238))
       MAX-ACCESS     read-write
       STATUS         current
       DESCRIPTION
        "URL of the Second Carbon Copy Server"
       ::=   { billRecMirror 17 }

     brmServerCCSecretTwo   OBJECT-TYPE
       SYNTAX         DisplayString(SIZE(0..32))
       MAX-ACCESS     read-write
       STATUS         current
       DESCRIPTION
         "Secret Key of the Second Carbon Copy Server"
       ::=   { billRecMirror 18 }

     brmServerCCPortTwo     OBJECT-TYPE
       SYNTAX         Integer32
       MAX-ACCESS     read-write
       STATUS         current
       DESCRIPTION
        "Port Number of the Second Carbon Copy Server"
       ::=   { billRecMirror 19 }

     brmServerCCIpThree     OBJECT-TYPE
       SYNTAX         IpAddress
       MAX-ACCESS     read-write
       STATUS         current
       DESCRIPTION
        "IP Address of the Third Carbon Copy Server"
       ::=   { billRecMirror 20 }

     brmServerCCUrlThree    OBJECT-TYPE
       SYNTAX         DisplayString(SIZE(1..238))
       MAX-ACCESS     read-write
       STATUS         current
       DESCRIPTION
        "URL of the Third Carbon Copy Server"
       ::=   { billRecMirror 21 }

     brmServerCCSecretThree OBJECT-TYPE
       SYNTAX         DisplayString(SIZE(0..32))
       MAX-ACCESS     read-write
       STATUS         current
       DESCRIPTION
        "Secret Key of the Third Carbon Copy Server"
       ::=   { billRecMirror 22 }

     brmServerCCPortThree   OBJECT-TYPE
       SYNTAX         Integer32
       MAX-ACCESS     read-write
       STATUS         current
       DESCRIPTION
        "Port Number of the Third Carbon Copy Server"
       ::=   { billRecMirror 23 }

     brmRetransMethod    OBJECT-TYPE
       SYNTAX         INTEGER { alternate(1), notAlternate(2) }
       MAX-ACCESS     read-write
       STATUS         current
       DESCRIPTION
        "Retransmit Method.
         Set to (1) for Alternate (round robin)
         Set to (2) for Do Not Alternate (fail-over)"
       ::=   { billRecMirror 24 }

     brmRetransAttempts     OBJECT-TYPE
       SYNTAX         Integer32
       MAX-ACCESS     read-write
       STATUS         current
       DESCRIPTION
        "Number of Retransmit Attempts"
       ::=   { billRecMirror 25 }

     brmRetransDelay     OBJECT-TYPE
       SYNTAX         Integer32
       MAX-ACCESS     read-write
       STATUS         current
       DESCRIPTION
        "Retransmit Delay"
       ::=   { billRecMirror 26 }



-------------------
-- DAT
-------------------

     datSessionTable OBJECT-TYPE
       SYNTAX  SEQUENCE OF DatSessionTableEntry
       MAX-ACCESS  not-accessible
       STATUS  current
       DESCRIPTION
        "Current DAT sessions."
       ::= { dat 1 }

     datSessionTableEntry OBJECT-TYPE
       SYNTAX  DatSessionTableEntry
       MAX-ACCESS  not-accessible
       STATUS  current
       DESCRIPTION
        "DAT session Entry"
       INDEX   { datNetPort }
       ::= { datSessionTable 1 }

     DatSessionTableEntry ::=
       SEQUENCE {
                 datSubIp          IpAddress,
                 datSubPort        Integer32,
                 datSubMac         DisplayString,
                 datNetIp          IpAddress,
                 datNetPort        Integer32,
                 datDestIp         IpAddress,
                 datDestPort       Integer32,
                 datProto          DisplayString,
                 datSessState      DisplayString,
                 datTimeout        Integer32
              }

     datSubIp OBJECT-TYPE
       SYNTAX      IpAddress
       MAX-ACCESS  read-only
       STATUS      current
       DESCRIPTION
        "IP Address of the Subscriber"
       ::= { datSessionTableEntry 1 }

     datSubPort OBJECT-TYPE
       SYNTAX      Integer32
       MAX-ACCESS  read-only
       STATUS      current
       DESCRIPTION
        "Port of the TCP session"
       ::= { datSessionTableEntry 2 }

     datSubMac OBJECT-TYPE
       SYNTAX      DisplayString
       MAX-ACCESS  read-only
       STATUS      current
       DESCRIPTION
        "MAC Address of the Subscriber"
       ::= { datSessionTableEntry 3 }

     datNetIp OBJECT-TYPE
       SYNTAX      IpAddress
       MAX-ACCESS  read-only
       STATUS      current
       DESCRIPTION
        "IP address DAT mapped the TCP session to"
       ::= { datSessionTableEntry 4 }

     datNetPort OBJECT-TYPE
       SYNTAX      Integer32
       MAX-ACCESS  read-only
       STATUS      current
       DESCRIPTION
        "Port that DAT mapped the TCP session to"
       ::= { datSessionTableEntry 5 }

      datDestIp OBJECT-TYPE
        SYNTAX      IpAddress
        MAX-ACCESS  read-only
        STATUS      current
        DESCRIPTION
         "IP address of the destination"
        ::= { datSessionTableEntry 6 }

      datDestPort OBJECT-TYPE
        SYNTAX      Integer32
        MAX-ACCESS  read-only
        STATUS      current
        DESCRIPTION
         "Port of destination"
       ::= { datSessionTableEntry 7 }

     datProto OBJECT-TYPE
       SYNTAX      DisplayString
       MAX-ACCESS  read-only
       STATUS      current
       DESCRIPTION
        "Transport Protocol (ICMP, TCP, UDP, etc.)"
       ::= { datSessionTableEntry 8 }

     datSessState OBJECT-TYPE
       SYNTAX      DisplayString
       MAX-ACCESS  read-only
       STATUS      current
       DESCRIPTION
        "Session State"
       ::= { datSessionTableEntry 9 }

     datTimeout OBJECT-TYPE
       SYNTAX      Integer32
       MAX-ACCESS  read-only
       STATUS      current
       DESCRIPTION
        "DAT timeout"
       ::= { datSessionTableEntry 10 }

--
-- DHCP
--

     dhcpDisable OBJECT-TYPE
       SYNTAX INTEGER {
                       false(0),
                       true(1)
                       }
       MAX-ACCESS    read-write
       STATUS        current
       DESCRIPTION
         "Set to true to disable DHCP services.
     This variable returns false when one of the DHCP services
     is enabled through either dhcpIpUpsell, dhcpServerEnable or dhcpRelayEnable.
          Note: You must reboot for changes to take effect."
       ::= { dhcp 1 }

     dhcpIpUpsell OBJECT-TYPE
       SYNTAX    INTEGER {
                       disabled(0),
                       enabled(1)
                       }
       MAX-ACCESS     read-write
       STATUS         current
       DESCRIPTION
         "Set to 0 to disable public IP Upsell service, 1 to enable
         public IP Upsell.  Requires SUBNET to be enabled.  Make sure
         you have a valid license for this feature; otherwise, an error
         will be returned when trying to set. Please reboot for the
         changes to take effect."
     ::= { dhcp 2 }

--
-- DHCP Server
--
     dhcpServer   OBJECT IDENTIFIER ::= { dhcp 3 }

     dhcpServerEnable OBJECT-TYPE
       SYNTAX    INTEGER {
                       disabled(0),
                       enabled(1)
                       }
       MAX-ACCESS    read-write
       STATUS        current
       DESCRIPTION
         "Set to 0 to disable DHCP service, 1 to enable DHCP
          server.  Note: You must reboot for changes to take effect."
       ::= { dhcpServer 2 }

     dhcpServerSubnetBased OBJECT-TYPE
     SYNTAX        INTEGER { disabled(0), enabled(1) }
     MAX-ACCESS    read-write
     STATUS        current
     DESCRIPTION
        "Set to 0 to disable subnet-based DHCP service, 1 to enable subnet-based DHCP
        service.  Note: You must reboot for changes to take effect."
     ::= { dhcpServer 3 }

     dhcpServerTable OBJECT-TYPE
       SYNTAX      SEQUENCE OF DhcpPoolTableEntry
       MAX-ACCESS  not-accessible
       STATUS      current
       DESCRIPTION
         "Currently active DHCP pools."
       ::= { dhcpServer 4 }

     dhcpPoolTableEntry OBJECT-TYPE
       SYNTAX      DhcpPoolTableEntry
       MAX-ACCESS  not-accessible
       STATUS      current
       DESCRIPTION
         "Table of DHCP pools"
       INDEX   { poolIndex }
       ::= { dhcpServerTable 1 }

     DhcpPoolTableEntry ::=
            SEQUENCE {
                    poolIndex     Integer32,
                    serverIp      IpAddress,
                    netMask       IpAddress,
                    poolStartIp   IpAddress,
                    poolStopIp    IpAddress,
                    leaseMinutes  Integer32,
                    publicPool    INTEGER,
                    ipUpSell      INTEGER,
                    defaultPool   INTEGER,
                    poolStatus    RowStatus
           }

     poolIndex OBJECT-TYPE
       SYNTAX      Integer32
       MAX-ACCESS  read-only
       STATUS      current
       DESCRIPTION
         " Lease Table Index"
       ::= { dhcpPoolTableEntry 2 }

     serverIp OBJECT-TYPE
       SYNTAX      IpAddress
       MAX-ACCESS  read-write
       STATUS      current
       DESCRIPTION
        "IP Address to bind to the internal DHCP Server.
         Note: You must reboot for changes to take effect."
       ::= { dhcpPoolTableEntry 4 }

     netMask OBJECT-TYPE
       SYNTAX      IpAddress
       MAX-ACCESS  read-write
       STATUS      current
       DESCRIPTION
         "DHCP Server subnet mask.  Note: You must reboot for changes to take effect."
       ::= { dhcpPoolTableEntry 6 }

     poolStartIp OBJECT-TYPE
       SYNTAX      IpAddress
       MAX-ACCESS  read-write
       STATUS      current
       DESCRIPTION
         "Starting IP address of DHCP lease pool.
          Note: You must reboot for changes to take effect."
       ::= { dhcpPoolTableEntry 8 }

     poolStopIp OBJECT-TYPE
       SYNTAX      IpAddress
       MAX-ACCESS  read-write
       STATUS      current
       DESCRIPTION
         "Ending IP address of DHCP lease pool.
          Note: You must reboot for changes to take effect."
       ::= { dhcpPoolTableEntry 10 }

     leaseMinutes OBJECT-TYPE
       SYNTAX      Integer32
       MAX-ACCESS  read-write
       STATUS      current
       DESCRIPTION
         "DHCP lease duration in minutes.  Note: You must reboot for changes to take effect."
       ::= { dhcpPoolTableEntry 12 }

     publicPool OBJECT-TYPE
       SYNTAX      INTEGER { false(0), true(1) }
       MAX-ACCESS  read-write
       STATUS      current
       DESCRIPTION
         "public IP pool"
       ::= { dhcpPoolTableEntry 14 }

     ipUpSell OBJECT-TYPE
       SYNTAX      INTEGER { false(0), true(1) }
       MAX-ACCESS  read-write
       STATUS      current
       DESCRIPTION
         "IP pool used for IP Upsell"
       ::= { dhcpPoolTableEntry 16 }

     defaultPool OBJECT-TYPE
       SYNTAX      INTEGER { false(0), true(1) }
       MAX-ACCESS  read-write
       STATUS      current
       DESCRIPTION
         "IP pool is the default pool"
       ::= { dhcpPoolTableEntry 18 }

     poolStatus     OBJECT-TYPE
       SYNTAX         RowStatus
       MAX-ACCESS     read-write
       STATUS         current
       DESCRIPTION
         "Status of the DHCP pool table entry."
       ::= { dhcpPoolTableEntry 20 }

--
--  DHCP Lease Table
--
           dhcpLeaseTable OBJECT-TYPE
           SYNTAX  SEQUENCE OF DhcpLeaseTableEntry
           MAX-ACCESS  not-accessible
           STATUS  current
           DESCRIPTION
              "Currently active DHCP leases."
         ::= { dhcpServer 6 }

           dhcpLeaseTableEntry OBJECT-TYPE
           SYNTAX  DhcpLeaseTableEntry
           MAX-ACCESS  not-accessible
           STATUS  current
           DESCRIPTION
              "Table of DHCP Leases"
           INDEX   { leaseIndex }
              ::= { dhcpLeaseTable 1 }

           DhcpLeaseTableEntry ::=
           SEQUENCE {
                       leaseIndex     Integer32,
                       leaseAddress   IpAddress,
                       leaseCLID      MacAddress,
                       leaseStatus    INTEGER
                    }

           leaseIndex OBJECT-TYPE
           SYNTAX      Integer32
           MAX-ACCESS  read-only
           STATUS  current
           DESCRIPTION
              " Lease Table Index"
              ::= { dhcpLeaseTableEntry 2 }

           leaseAddress OBJECT-TYPE
           SYNTAX  IpAddress
           MAX-ACCESS  read-only
           STATUS  current
           DESCRIPTION
              "IP Address"
              ::= { dhcpLeaseTableEntry 4 }

           leaseCLID OBJECT-TYPE
           SYNTAX  MacAddress
           MAX-ACCESS  read-only
           STATUS  current
           DESCRIPTION
              "Client ID of subscriber to whom lease is assigned"
              ::= { dhcpLeaseTableEntry 6 }

           leaseStatus OBJECT-TYPE
           SYNTAX  INTEGER { available(0), reserved(1) }
           MAX-ACCESS  read-only
           STATUS  current
           DESCRIPTION
              "Status of the lease (available or reserved)"
              ::= { dhcpLeaseTableEntry 7 }

  --
  -- DHCP Relay
  --
     dhcpRelay OBJECT IDENTIFIER ::= { dhcp 10 }

     dhcpRelayEnable OBJECT-TYPE
       SYNTAX       INTEGER { disabled(0), enabled(1) }
       MAX-ACCESS       read-write
       STATUS       current
       DESCRIPTION
         "Set to 0 to disable DHCP Relay service, 1 to enable DHCP Relay service.
          Note: You must reboot for changes to take effect."
       ::= { dhcpRelay 2 }

     dhcpRelayAgentIP   OBJECT-TYPE
       SYNTAX  IpAddress
       MAX-ACCESS  read-write
       STATUS  current
       DESCRIPTION
         "IP Address of the Relay Agent.  Note: You must reboot for changes to take effect."
       ::= { dhcpRelay 4 }

     dhcpRelayServerIP   OBJECT-TYPE
       SYNTAX  IpAddress
       MAX-ACCESS  read-write
       STATUS  current
       DESCRIPTION
         "IP Address to which the Relay Agent will forward subscriber DHCP requests.
          Note: You must reboot for changes to take effect."
      ::= { dhcpRelay 5 }

--
--   DNS
--

     dnsHostName         OBJECT-TYPE
       SYNTAX         DisplayString(SIZE(1..64))
       MAX-ACCESS     read-write
       STATUS         current
       DESCRIPTION
        "DNS Hostname.  Note: You must reboot for changes to take effect."
       ::= { dns 1 }

     dnsDomain        OBJECT-TYPE
       SYNTAX         DisplayString(SIZE(1..64))
       MAX-ACCESS     read-write
       STATUS         current
       DESCRIPTION
        "DNS domain.  Note: In order to set this value,
         DHCP Client must be disabled.  Note: You must reboot for changes to take effect."
       ::= { dns 2 }

     dnsPrimaryServer    OBJECT-TYPE
       SYNTAX            IpAddress
       MAX-ACCESS        read-write
       STATUS            current
       DESCRIPTION
         "Primary DNS Server.  Note: In order to set this value,
          both DHCP Client and PPPoE Client must be disabled.  Note: You must
          reboot for changes to take effect."
       ::= { dns 3 }

     dnsSecondaryServer  OBJECT-TYPE
       SYNTAX            IpAddress
       MAX-ACCESS        read-write
       STATUS            current
       DESCRIPTION
         "Secondary DNS Server.  Note: In order to set this value,
          both DHCP Client and PPPoE Client must be disabled.  Note: You must
          reboot for changes to take effect."
       ::= { dns 4 }

     dnsTertiaryServer      OBJECT-TYPE
       SYNTAX         IpAddress
       MAX-ACCESS         read-write
       STATUS         current
       DESCRIPTION
         "Tertiary DNS Server.  Note: You must reboot for changes to take effect."
       ::= { dns 5 }

--
--   Dynamic DNS
--
     dynDnsEnable   OBJECT-TYPE
        SYNTAX       INTEGER { disabled(0), enabled(1) }
        MAX-ACCESS   read-write
        STATUS       current
        DESCRIPTION
        "Set to 0 to disable Dynamic DNS, 1 to enable Dynamic DNS"
        ::= { dyndns 0 }

     dynDnsProtocol OBJECT-TYPE
        SYNTAX       INTEGER { dynDnsOrgProto(0), dynDnsOrgProtoSecure(1) }
        MAX-ACCESS   read-write
        STATUS       current
        DESCRIPTION
        "Set to 0 to set protocol to dyndns.org, or set protocol to 1 to set it to dyndns.org (secure) protocol"
        ::= { dyndns 1 }

     dynDnsServer OBJECT-TYPE
        SYNTAX      DisplayString(SIZE(0..255))
        MAX-ACCESS  read-write
        STATUS      current
        DESCRIPTION
        "Server name given by dynamic DNS provider. Please specify only domain name, without http://, '/', etc"
        ::= { dyndns 2 }

     dynDnsPort      OBJECT-TYPE
        SYNTAX       INTEGER { dynDnsPort80(0), dynDnsPort8245(1), dynDnsPort443(2) }
        MAX-ACCESS   read-write
        STATUS       current
        DESCRIPTION
        "Set port on which to connect to dynamic dns provider. NOTE: port 443 may only be chosen if protocol is dynDnsOrgProtoSecure (dyndns.org (secure)). For non-secure version of dyndns.org protocol: set to 0 for port 80; set to 1 for port 8245. For secure version: set port to 443"
        ::= { dyndns 3 }

     dynDnsHostname OBJECT-TYPE
        SYNTAX      DisplayString(SIZE(0..255))
        MAX-ACCESS  read-write
        STATUS      current
        DESCRIPTION
        "Hostname which ip address of the NSE will be mapped to. Please specify only domain name, without http://, '/', etc"
        ::= { dyndns 4 }

     dynDnsUsername OBJECT-TYPE
        SYNTAX      DisplayString(SIZE(0..255))
        MAX-ACCESS  read-write
        STATUS      current
        DESCRIPTION
        "Username associated with dynamic dns account"
        ::= { dyndns 5 }

     dynDnsPassword OBJECT-TYPE
        SYNTAX      DisplayString(SIZE(0..255))
        MAX-ACCESS  read-write
        STATUS      current
        DESCRIPTION
        "Password associated with dynamic dns account."
        ::= { dyndns 6 }

     dynDnsForceUpdate OBJECT-TYPE
        SYNTAX      INTEGER { disabled(0), enabled(1) }
        MAX-ACCESS  read-write
        STATUS      current
        DESCRIPTION
        "When set to 1 will perform a forced dynamic DNS update. When set to false will have no effect. Will always return 0 on get. IMPORTANT: some Dynamic DNS Providers (e.g. dyndns.org) consider unnecessary updates (i.e. updates with unchanged IP addresses) abusive. Such updates may result in hostname / username being blocked."
        ::= { dyndns 7 }


  --
  -- GRE Tunneling
  --

     greTunnelingEnable OBJECT-TYPE
       SYNTAX       INTEGER { disabled(0), enabled(1) }
       MAX-ACCESS   read-write
       STATUS       current
       DESCRIPTION
      "Set to 0 to disable GRE Tunneling service, 1 to enable GRE Tunneling service.
      Note: you must reboot for changes to take effect."
       ::= { greTunneling 1 }

     greVpnConcentratorIp   OBJECT-TYPE
       SYNTAX      IpAddress
       MAX-ACCESS  read-write
       STATUS      current
       DESCRIPTION
      "IP Address of the VPN Concentrator Server.  Note: you must reboot for changes to take effect."
       ::= { greTunneling 2 }

     greInterfaceIp   OBJECT-TYPE
       SYNTAX      IpAddress
       MAX-ACCESS  read-write
       STATUS      current
       DESCRIPTION
      "IP Address of the GRE Interface on this device.  Note: you must reboot for changes to take effect."
       ::= { greTunneling 3 }

     greInterfaceNetmask   OBJECT-TYPE
       SYNTAX      IpAddress
       MAX-ACCESS  read-write
       STATUS      current
       DESCRIPTION
      "The Subnet Mask for the GRE Interface on this device.  Note: you must reboot for changes to take effect."
       ::= { greTunneling 4 }

     greInterfaceGateway   OBJECT-TYPE
       SYNTAX      IpAddress
       MAX-ACCESS  read-write
       STATUS      current
       DESCRIPTION
      "The Gateway for the GRE Interface on this device.  Note: you must reboot for changes to take effect."
       ::= { greTunneling 5 }

  --
  -- HPR - HOME PAGE REDIRECTION
  --

  --
  -- HPR ON
  --

              hprOn OBJECT-TYPE
              SYNTAX         INTEGER { disabled(0), enabled(1) }
              MAX-ACCESS         read-write
              STATUS         current
              DESCRIPTION
                 "Setting this value to (1) will cause home page redirection
                 to be performed by this unit.  Setting this value to (0) will
                 discontinue HPR.
                 Note: If trying to set this value returns an error, please check to see if you have a valid license for this feature."
              ::= { hpr 1 }

  --
  -- HPR URL
  --

              hprUrl   OBJECT-TYPE
              SYNTAX      DisplayString(SIZE(0..237))
              MAX-ACCESS      read-write
              STATUS      current
              DESCRIPTION
                 "The fully qualified WWW URL at which to redirect Home Page Requests."
              ::= { hpr 2 }

  --
  -- HPR PARAMETER PASSING
  --

              hprParameterPassing  OBJECT-TYPE
              SYNTAX         INTEGER { disabled(0), enabled(1) }
              MAX-ACCESS         read-write
              STATUS         current
              DESCRIPTION
                 "Setting this value to (1) will cause inclusion of parameters
                 with the passed URL during HPR.  Setting this value to (0) will
                 discontinue parameter passing."
              ::= { hpr 3 }

  --
  -- HPR REDIRECTION FREQUENCY
  --

              hprRedirectionFrequency OBJECT-TYPE
              SYNTAX      Integer32
              MAX-ACCESS  read-write
              STATUS      current
              DESCRIPTION
                 "The time interval, specified in minutes, after which the
                 next redirection will take place."
              ::= { hpr 4 }

  --
  -- ICC - Information and Control Console
  --

  --
  -- ICC ON
  --
              iccOn OBJECT-TYPE
              SYNTAX         INTEGER { disabled(0), enabled(1) }
              MAX-ACCESS     read-write
              STATUS         current
              DESCRIPTION
                 "Set to (1) to enable the ICC.  Set to (0) to disable.
                 Note: If trying to set this value returns an error, please check to see if you have a valid license for this feature."
              ::= { icc 1 }

  --
  -- ICC Title
  --

              iccTitle OBJECT-TYPE
              SYNTAX      DisplayString(SIZE(0..237))
              MAX-ACCESS      read-write
              STATUS      current
              DESCRIPTION
                 "The title to appear on the ICC console window"
              ::= { icc 2 }

  --
  -- ICC Logout Option
  --
              iccLogoutOption OBJECT-TYPE
              SYNTAX         INTEGER { redisplay(0), logout(2) }
              MAX-ACCESS     read-write
              STATUS         current
              DESCRIPTION
                 "What should the ICC do when a subscriber closes it?
                 0 to Redisplay, 2 to logout and return the user to a *Pending* state (valid only with RADIUS)"
              ::= { icc 3 }

  --
  -- TODO: ICC Logout URL
  --

  --          iccLogoutURL OBJECT-TYPE
  --             SYNTAX      DisplayString(SIZE(0..237))
  --             MAX-ACCESS      read-write
  --             STATUS      current
  --             DESCRIPTION
  --                "TODO: description"
  --             ::= { icc 4 }

  --
  -- ICC Language Option
  --
              iccLanguageOption OBJECT-TYPE
              SYNTAX         INTEGER { english(0), chinese(1), french(2),
                                       german(3), japanese(4), spanish(5), other(6) }
              MAX-ACCESS     read-write
              STATUS         current
              DESCRIPTION
                 "What language would you like to be displayed on the ICC?
                  Available settings: 0=English, 1=Chinese, 2=French, 3=German, 4=Japanese,
                                      5=Spanish, 6=Other.
                  If *other* is selected, please make a selection for iccCharSetOption."
              ::= { icc 5 }

  --
  -- ICC Timer Option
  --
              iccTimerOption OBJECT-TYPE
              SYNTAX         INTEGER { remaining(0), elapsed(1) }
              MAX-ACCESS     read-write
              STATUS         current
              DESCRIPTION
                 "Set to (1) for ICC Elapsed Time.  Set to (0) for Time Remaining.
                 Note: If trying to set this value returns an error, please check to see if you have a valid license for this feature."
              ::= { icc 6 }

  --
  -- ICC CharSet Option
  --
              iccCharSetOption OBJECT-TYPE
              SYNTAX         INTEGER { default(0), western-iso-8859-1(1), chinese-big5(2),
                                       chinese-euc-cn(3), chinese-euc-tw(4), chinese-gb2312(5),
                                       japanese-euc-jp(6), japanese-iso-2022-jp(7),
                                       japanese-shift-jis(8), korean-euc-kr(9),
                                       korean-iso-2022-kr(10), korean-ks-c-5601(11) }
              MAX-ACCESS     read-write
              STATUS         current
              DESCRIPTION
                 "This value indicates specific character set to be displayed.  In order to set
                  this value, iccLanguageOption should be first set to *other*.
                  Available settings:
                               0=default, 1=western-iso-8859-1, 2=chinese-big5,
                               3=chinese-euc-cn, 4=chinese-euc-tw, 5=chinese-gb2312,
                               6=japanese-euc-jp, 7=japanese-iso-2022-jp,
                               8=japanese-shift-jis, 9=korean-euc-kr,
                               10=korean-iso-2022-kr, 11=korean-ks-c-5601."
              ::= { icc 7 }


  --
  -- ICC Buttons
  --
              iccButtons  OBJECT IDENTIFIER ::= { icc 10 }

                 iccISPLogoButton   OBJECT IDENTIFIER ::= { iccButtons 5 }
                 iccButton2         OBJECT IDENTIFIER ::= { iccButtons 6 }
                 iccButton3         OBJECT IDENTIFIER ::= { iccButtons 7 }
                 iccButton4         OBJECT IDENTIFIER ::= { iccButtons 8 }
                 iccButton5         OBJECT IDENTIFIER ::= { iccButtons 9 }
                 iccButton6         OBJECT IDENTIFIER ::= { iccButtons 10 }
                 iccButton7         OBJECT IDENTIFIER ::= { iccButtons 11 }
                 iccButton8         OBJECT IDENTIFIER ::= { iccButtons 12 }
                 iccButton9         OBJECT IDENTIFIER ::= { iccButtons 13 }

  --
  -- ICC ISP Logo Button
  --

              iccISPLogoButtonName OBJECT-TYPE
              SYNTAX      DisplayString(SIZE(0..37))
              MAX-ACCESS      read-write
              STATUS      current
              DESCRIPTION
                 " ISP Logo Button Name"
              ::= { iccISPLogoButton 1 }

              iccISPLogoButtonURL OBJECT-TYPE
              SYNTAX      DisplayString(SIZE(0..237))
              MAX-ACCESS      read-write
              STATUS      current
              DESCRIPTION
                 " ISP Logo Button URL"
              ::= { iccISPLogoButton 2 }

              iccISPLogoButtonImgName OBJECT-TYPE
              SYNTAX      DisplayString(SIZE(0..31))
              MAX-ACCESS      read-write
              STATUS      current
              DESCRIPTION
                 " ISP Logo Button Image Name"
              ::= { iccISPLogoButton 3 }

  --
  -- ICC Button 2
  --

              iccButtonName2 OBJECT-TYPE
              SYNTAX      DisplayString(SIZE(0..37))
              MAX-ACCESS      read-write
              STATUS      current
              DESCRIPTION
                 " ICC Button 2 Name"
              ::= { iccButton2 1 }

              iccButtonURL2 OBJECT-TYPE
              SYNTAX      DisplayString(SIZE(0..237))
              MAX-ACCESS      read-write
              STATUS      current
              DESCRIPTION
                 " ICC Button 2 URL"
              ::= { iccButton2 2 }

              iccButtonImgName2 OBJECT-TYPE
              SYNTAX      DisplayString(SIZE(0..31))
              MAX-ACCESS      read-write
              STATUS      current
              DESCRIPTION
                 " ICC Button 2 Image Name"
              ::= { iccButton2 3 }

  --
  -- ICC Button 3
  --

              iccButtonName3 OBJECT-TYPE
              SYNTAX      DisplayString(SIZE(0..37))
              MAX-ACCESS      read-write
              STATUS      current
              DESCRIPTION
                 " ICC Button 3 Name"
              ::= { iccButton3 1 }

              iccButtonURL3 OBJECT-TYPE
              SYNTAX      DisplayString(SIZE(0..237))
              MAX-ACCESS      read-write
              STATUS      current
              DESCRIPTION
                 " ICC Button 3 URL"
              ::= { iccButton3 2 }

              iccButtonImgName3 OBJECT-TYPE
              SYNTAX      DisplayString(SIZE(0..31))
              MAX-ACCESS      read-write
              STATUS      current
              DESCRIPTION
                 " ICC Button 3 Image Name"
              ::= { iccButton3 3 }

  --
  -- ICC Button 4
  --

              iccButtonName4 OBJECT-TYPE
              SYNTAX      DisplayString(SIZE(0..37))
              MAX-ACCESS      read-write
              STATUS      current
              DESCRIPTION
                 " ICC Button 4 Name"
              ::= { iccButton4 1 }

              iccButtonURL4 OBJECT-TYPE
              SYNTAX      DisplayString(SIZE(0..237))
              MAX-ACCESS      read-write
              STATUS      current
              DESCRIPTION
                 " ICC Button 4 URL"
              ::= { iccButton4 2 }

              iccButtonImgName4 OBJECT-TYPE
              SYNTAX      DisplayString(SIZE(0..31))
              MAX-ACCESS      read-write
              STATUS      current
              DESCRIPTION
                 " ICC Button 4 Image Name"
              ::= { iccButton4 3 }

  --
  -- ICC Button 5
  --

              iccButtonName5 OBJECT-TYPE
              SYNTAX      DisplayString(SIZE(0..37))
              MAX-ACCESS      read-write
              STATUS      current
              DESCRIPTION
                 " ICC Button 5 Name"
              ::= { iccButton5 1 }

              iccButtonURL5 OBJECT-TYPE
              SYNTAX      DisplayString(SIZE(0..237))
              MAX-ACCESS      read-write
              STATUS      current
              DESCRIPTION
                 " ICC Button 5 URL"
              ::= { iccButton5 2 }

              iccButtonImgName5 OBJECT-TYPE
              SYNTAX      DisplayString(SIZE(0..31))
              MAX-ACCESS      read-write
              STATUS      current
              DESCRIPTION
                 " ICC Button 5 Image Name"
              ::= { iccButton5 3 }

  --
  -- ICC Button 6
  --

              iccButtonName6 OBJECT-TYPE
              SYNTAX      DisplayString(SIZE(0..37))
              MAX-ACCESS      read-write
              STATUS      current
              DESCRIPTION
                 " ICC Button 6 Name"
              ::= { iccButton6 1 }

              iccButtonURL6 OBJECT-TYPE
              SYNTAX      DisplayString(SIZE(0..237))
              MAX-ACCESS      read-write
              STATUS      current
              DESCRIPTION
                 " ICC Button 6 URL"
              ::= { iccButton6 2 }

              iccButtonImgName6 OBJECT-TYPE
              SYNTAX      DisplayString(SIZE(0..31))
              MAX-ACCESS      read-write
              STATUS      current
              DESCRIPTION
                 " ICC Button 6 Image Name"
              ::= { iccButton6 3 }

  --
  -- ICC Button 7
  --

              iccButtonName7 OBJECT-TYPE
              SYNTAX      DisplayString(SIZE(0..37))
              MAX-ACCESS      read-write
              STATUS      current
              DESCRIPTION
                 " ICC Button 7 Name"
              ::= { iccButton7 1 }

              iccButtonURL7 OBJECT-TYPE
              SYNTAX      DisplayString(SIZE(0..237))
              MAX-ACCESS      read-write
              STATUS      current
              DESCRIPTION
                 " ICC Button 7 URL"
              ::= { iccButton7 2 }

              iccButtonImgName7 OBJECT-TYPE
              SYNTAX      DisplayString(SIZE(0..31))
              MAX-ACCESS      read-write
              STATUS      current
              DESCRIPTION
                 " ICC Button 7 Image Name"
              ::= { iccButton7 3 }

  --
  -- ICC Button 8
  --

              iccButtonName8 OBJECT-TYPE
              SYNTAX      DisplayString(SIZE(0..37))
              MAX-ACCESS      read-write
              STATUS      current
              DESCRIPTION
                 " ICC Button 8 Name"
              ::= { iccButton8 1 }

              iccButtonURL8 OBJECT-TYPE
              SYNTAX      DisplayString(SIZE(0..237))
              MAX-ACCESS      read-write
              STATUS      current
              DESCRIPTION
                 " ICC Button 8 URL"
              ::= { iccButton8 2 }

              iccButtonImgName8 OBJECT-TYPE
              SYNTAX      DisplayString(SIZE(0..31))
              MAX-ACCESS      read-write
              STATUS      current
              DESCRIPTION
                 " ICC Button 8 Image Name"
              ::= { iccButton8 3 }

  --
  -- ICC Button 9
  --

              iccButtonName9 OBJECT-TYPE
              SYNTAX      DisplayString(SIZE(0..37))
              MAX-ACCESS      read-write
              STATUS      current
              DESCRIPTION
                 " ICC Button 9 Name"
              ::= { iccButton9 1 }

              iccButtonURL9 OBJECT-TYPE
              SYNTAX      DisplayString(SIZE(0..237))
              MAX-ACCESS      read-write
              STATUS      current
              DESCRIPTION
                 " ICC Button 9 URL"
              ::= { iccButton9 2 }

              iccButtonImgName9 OBJECT-TYPE
              SYNTAX      DisplayString(SIZE(0..31))
              MAX-ACCESS      read-write
              STATUS      current
              DESCRIPTION
                 " ICC Button 9 Image Name"
              ::= { iccButton9 3 }

  --
  -- ICC Banners
  --

              iccBanners  OBJECT IDENTIFIER ::= { icc 14 }

                 iccBanner1  OBJECT IDENTIFIER ::= { iccBanners 14 }
                 iccBanner2  OBJECT IDENTIFIER ::= { iccBanners 15 }
                 iccBanner3  OBJECT IDENTIFIER ::= { iccBanners 16 }
                 iccBanner4  OBJECT IDENTIFIER ::= { iccBanners 17 }
                 iccBanner5  OBJECT IDENTIFIER ::= { iccBanners 18 }

  --
  -- ICC Banner 1
  --

              iccBannerName1 OBJECT-TYPE
              SYNTAX      DisplayString(SIZE(0..15))
              MAX-ACCESS      read-write
              STATUS      current
              DESCRIPTION
                 " ICC Banner Name 1"
              ::= { iccBanner1 1 }

              iccBannerURL1 OBJECT-TYPE
              SYNTAX      DisplayString(SIZE(0..237))
              MAX-ACCESS      read-write
              STATUS      current
              DESCRIPTION
                 "ICC Banner 1 URL"
              ::= { iccBanner1 2 }

              iccBannerImgName1 OBJECT-TYPE
              SYNTAX      DisplayString(SIZE(0..31))
              MAX-ACCESS      read-write
              STATUS      current
              DESCRIPTION
                 "ICC Banner 1 Image Name"
              ::= { iccBanner1 3 }

              iccBannerDuration1 OBJECT-TYPE
              SYNTAX      Integer32
              MAX-ACCESS      read-write
              STATUS      current
              DESCRIPTION
                 "ICC Banner 1 Duration in seconds. Minimum allowed value is 30."
              ::= { iccBanner1 4 }

              iccBannerStartTime1 OBJECT-TYPE
              SYNTAX      DisplayString(SIZE(1..16))
              MAX-ACCESS      read-write
              STATUS      current
              DESCRIPTION
                 "Start Time (Optional) {Hour}:{Min}{AM/PM}"
              ::= { iccBanner1 5 }

              iccBannerStopTime1 OBJECT-TYPE
              SYNTAX      DisplayString(SIZE(1..16))
              MAX-ACCESS      read-write
              STATUS      current
              DESCRIPTION
                 "Stop Time (Optional) {Hour}:{Min}{AM/PM}"
              ::= { iccBanner1 6 }

  --
  -- ICC Banner 2
  --

              iccBannerName2 OBJECT-TYPE
              SYNTAX      DisplayString(SIZE(0..15))
              MAX-ACCESS      read-write
              STATUS      current
              DESCRIPTION
                 " ICC Banner Name 2"
              ::= { iccBanner2 1 }

              iccBannerURL2 OBJECT-TYPE
              SYNTAX      DisplayString(SIZE(0..237))
              MAX-ACCESS      read-write
              STATUS      current
              DESCRIPTION
                 "ICC Banner 2 URL"
              ::= { iccBanner2 2 }

              iccBannerImgName2 OBJECT-TYPE
              SYNTAX      DisplayString(SIZE(0..31))
              MAX-ACCESS      read-write
              STATUS      current
              DESCRIPTION
                 "ICC Banner 2 Image Name"
              ::= { iccBanner2 3 }

              iccBannerDuration2 OBJECT-TYPE
              SYNTAX      Integer32
              MAX-ACCESS      read-write
              STATUS      current
              DESCRIPTION
                 "ICC Banner 2 Duration in seconds. Minimum allowed value is 30."
              ::= { iccBanner2 4 }

              iccBannerStartTime2 OBJECT-TYPE
              SYNTAX      DisplayString(SIZE(1..16))
              MAX-ACCESS      read-write
              STATUS      current
              DESCRIPTION
                 "Start Time (Optional) {Hour}:{Min}{AM/PM}"
              ::= { iccBanner2 5 }

              iccBannerStopTime2 OBJECT-TYPE
              SYNTAX      DisplayString(SIZE(1..16))
              MAX-ACCESS      read-write
              STATUS      current
              DESCRIPTION
                 "Stop Time (Optional) {Hour}:{Min}{AM/PM}"
              ::= { iccBanner2 6 }

  --
  -- ICC Banner 3
  --

              iccBannerName3 OBJECT-TYPE
              SYNTAX      DisplayString(SIZE(0..15))
              MAX-ACCESS      read-write
              STATUS      current
              DESCRIPTION
                 " ICC Banner Name 3"
              ::= { iccBanner3 1 }

              iccBannerURL3 OBJECT-TYPE
              SYNTAX      DisplayString(SIZE(0..237))
              MAX-ACCESS      read-write
              STATUS      current
              DESCRIPTION
                 "ICC Banner 3 URL"
              ::= { iccBanner3 2 }

              iccBannerImgName3 OBJECT-TYPE
              SYNTAX      DisplayString(SIZE(0..31))
              MAX-ACCESS      read-write
              STATUS      current
              DESCRIPTION
                 "ICC Banner 3 Image Name"
              ::= { iccBanner3 3 }

              iccBannerDuration3 OBJECT-TYPE
              SYNTAX      Integer32
              MAX-ACCESS      read-write
              STATUS      current
              DESCRIPTION
                 "ICC Banner 3 Duration in seconds. Minimum allowed value is 30."
              ::= { iccBanner3 4 }

              iccBannerStartTime3 OBJECT-TYPE
              SYNTAX      DisplayString(SIZE(1..16))
              MAX-ACCESS      read-write
              STATUS      current
              DESCRIPTION
                 "Start Time (Optional) {Hour}:{Min}{AM/PM}"
              ::= { iccBanner3 5 }

              iccBannerStopTime3 OBJECT-TYPE
              SYNTAX      DisplayString(SIZE(1..16))
              MAX-ACCESS      read-write
              STATUS      current
              DESCRIPTION
                 "Stop Time (Optional) {Hour}:{Min}{AM/PM}"
              ::= { iccBanner3 6 }

  --
  -- ICC Banner 4
  --

              iccBannerName4 OBJECT-TYPE
              SYNTAX      DisplayString(SIZE(0..15))
              MAX-ACCESS      read-write
              STATUS      current
              DESCRIPTION
                 " ICC Banner Name 4"
              ::= { iccBanner4 1 }

              iccBannerURL4 OBJECT-TYPE
              SYNTAX      DisplayString(SIZE(0..237))
              MAX-ACCESS      read-write
              STATUS      current
              DESCRIPTION
                 "ICC Banner 4 URL"
              ::= { iccBanner4 2 }

              iccBannerImgName4 OBJECT-TYPE
              SYNTAX      DisplayString(SIZE(0..31))
              MAX-ACCESS      read-write
              STATUS      current
              DESCRIPTION
                 "ICC Banner 4 Image Name"
              ::= { iccBanner4 3 }

              iccBannerDuration4 OBJECT-TYPE
              SYNTAX      Integer32
              MAX-ACCESS      read-write
              STATUS      current
              DESCRIPTION
                 "ICC Banner 4 Duration in seconds. Minimum allowed value is 30."
              ::= { iccBanner4 4 }

              iccBannerStartTime4 OBJECT-TYPE
              SYNTAX      DisplayString(SIZE(1..16))
              MAX-ACCESS      read-write
              STATUS      current
              DESCRIPTION
                 "Start Time (Optional) {Hour}:{Min}{AM/PM}"
              ::= { iccBanner4 5 }

              iccBannerStopTime4 OBJECT-TYPE
              SYNTAX      DisplayString(SIZE(1..16))
              MAX-ACCESS      read-write
              STATUS      current
              DESCRIPTION
                 "Stop Time (Optional) {Hour}:{Min}{AM/PM}"
              ::= { iccBanner4 6 }

  --
  -- ICC Banner 5
  --

              iccBannerName5 OBJECT-TYPE
              SYNTAX      DisplayString(SIZE(0..15))
              MAX-ACCESS      read-write
              STATUS      current
              DESCRIPTION
                 " ICC Banner Name 5"
              ::= { iccBanner5 1 }

              iccBannerURL5 OBJECT-TYPE
              SYNTAX      DisplayString(SIZE(0..237))
              MAX-ACCESS      read-write
              STATUS      current
              DESCRIPTION
                 "ICC Banner 5 URL"
              ::= { iccBanner5 2 }

              iccBannerImgName5 OBJECT-TYPE
              SYNTAX      DisplayString(SIZE(0..31))
              MAX-ACCESS      read-write
              STATUS      current
              DESCRIPTION
                 "ICC Banner 5 Image Name"
              ::= { iccBanner5 3 }

              iccBannerDuration5 OBJECT-TYPE
              SYNTAX      Integer32
              MAX-ACCESS      read-write
              STATUS      current
              DESCRIPTION
                 "ICC Banner 5 Duration in seconds. Minimum allowed value is 30."
              ::= { iccBanner5 4 }

              iccBannerStartTime5 OBJECT-TYPE
              SYNTAX      DisplayString(SIZE(1..16))
              MAX-ACCESS      read-write
              STATUS      current
              DESCRIPTION
                 "Start Time (Optional) {Hour}:{Min}{AM/PM}"
              ::= { iccBanner5 5 }

              iccBannerStopTime5 OBJECT-TYPE
              SYNTAX      DisplayString(SIZE(1..16))
              MAX-ACCESS      read-write
              STATUS      current
              DESCRIPTION
                 "Stop Time (Optional) {Hour}:{Min}{AM/PM}"
              ::= { iccBanner5 6 }


  --
  -- iNAT
  --


        inatOn OBJECT-TYPE
        SYNTAX      INTEGER { disabled(0), enabled(1) }
              MAX-ACCESS      read-write
              STATUS      current
              DESCRIPTION
           "Set to 1 to enable iNAT, 0 to disable. Valid License is required "
              ::= { inat 1 }


        pptpOn OBJECT-TYPE
        SYNTAX      INTEGER { disabled(0), enabled(1) }
              MAX-ACCESS      read-write
              STATUS      current
              DESCRIPTION
           "Set to 1 to enable PPTP, 0 to disable.  Valid License is required"
              ::= { inat 2 }

        pptpidOn OBJECT-TYPE
        SYNTAX      INTEGER { disabled(0), enabled(1) }
              MAX-ACCESS      read-write
              STATUS      current
              DESCRIPTION
           "Set to 1 to enable PPTP ID support, 0 to disable.  Valid PPTP License is required
           Note: You must reboot for changes to take effect."
              ::= { inat 4 }

        ipsecOn OBJECT-TYPE
        SYNTAX      INTEGER { disabled(0), enabled(1) }
              MAX-ACCESS      read-write
              STATUS      current
              DESCRIPTION
           "Set to 1 to enable subscriber IPSec passthru, 0 to disable.  Valid License
            is required. (NOTE: This is not to be confused with the MIB variable
            ipsecVpnOn, which pertains to IPSec traffic between the NSE and remote hosts)."
              ::= { inat 3 }


--
--  iNAT Address Range List
--
       inatIpTable OBJECT-TYPE
       SYNTAX  SEQUENCE OF INATIpEntry
       MAX-ACCESS  not-accessible
       STATUS  current
       DESCRIPTION
          "Table of iNAT IPs"
       ::= { inat 5 }

       inatIpEntry OBJECT-TYPE
       SYNTAX  INATIpEntry
       MAX-ACCESS  not-accessible
       STATUS  current
       DESCRIPTION
          " iNAT table entry "
       INDEX   { inatIndex }
       ::= { inatIpTable 1 }

       INATIpEntry ::=
       SEQUENCE {
               inatIndex         Integer32,
               inatStartAddress  IpAddress,
               inatEndAddress    IpAddress,
       inatEntryStatus   RowStatus
                   }

       inatIndex OBJECT-TYPE
       SYNTAX      Integer32
       MAX-ACCESS  read-only
       STATUS  current
       DESCRIPTION
          " iNAT table index "
       ::= { inatIpEntry 2 }

       inatStartAddress OBJECT-TYPE
       SYNTAX  IpAddress
       MAX-ACCESS  read-write
       STATUS  current
       DESCRIPTION
          "iNAT range Starting IP address "
       ::= { inatIpEntry 4 }

       inatEndAddress OBJECT-TYPE
       SYNTAX  IpAddress
       MAX-ACCESS  read-write
       STATUS  current
       DESCRIPTION
          "iNAT range end IP address "
       ::= { inatIpEntry 6 }

       inatEntryStatus      OBJECT-TYPE
       SYNTAX         RowStatus
       MAX-ACCESS         read-write
       STATUS                      current
       DESCRIPTION
          "Status of the iNAT table entry."
       ::= { inatIpEntry 10 }

--
-- LICENSE KEYS
--

        lkKey OBJECT-TYPE
        SYNTAX      DisplayString(SIZE(1..32))
        MAX-ACCESS      read-only
        STATUS      current
        DESCRIPTION
           "License key."
        ::= { licenseKeys 1 }

        lkModelNo OBJECT-TYPE
        SYNTAX      DisplayString(SIZE(1..10))
        MAX-ACCESS      read-only
        STATUS      current
        DESCRIPTION
           "Model number."
        ::= { licenseKeys 2 }

        lkMaxNumSubs OBJECT-TYPE
        SYNTAX      Integer32
        MAX-ACCESS  read-only
        STATUS      current
        DESCRIPTION
           "Maximum number of subscribers."
        ::= { licenseKeys 3 }

        lkFeatureList OBJECT-TYPE
        SYNTAX      SEQUENCE OF LkFeatureListEntry
        MAX-ACCESS      not-accessible
        STATUS      current
        DESCRIPTION
           "List of features using the license key."
        ::= { licenseKeys 4 }

        lkFeatureListEntry      OBJECT-TYPE
        SYNTAX         LkFeatureListEntry
        MAX-ACCESS         not-accessible
        STATUS         current
        DESCRIPTION
            "Feature entry."
        INDEX   { lkFeatureIndex }
        ::= { lkFeatureList 1 }

        LkFeatureListEntry ::= SEQUENCE {
           lkFeatureIndex          Integer32,
           lkFeatureName           DisplayString,
           lkFeatureStatus         INTEGER
        }

        lkFeatureIndex OBJECT-TYPE
        SYNTAX      Integer32
        MAX-ACCESS  read-only
        STATUS      current
        DESCRIPTION
           " license key table index"
        ::= { lkFeatureListEntry 1 }

        lkFeatureName OBJECT-TYPE
        SYNTAX      DisplayString(SIZE(1..30))
        MAX-ACCESS      read-only
        STATUS      current
        DESCRIPTION
           "Feature name."
        ::= { lkFeatureListEntry 2 }

        lkFeatureStatus OBJECT-TYPE
        SYNTAX      INTEGER { notPurchased(0), purchased(1) }
        MAX-ACCESS      read-only
        STATUS      current
        DESCRIPTION
           "License status."
        ::= { lkFeatureListEntry 3 }

--
-- LOCATION
--

--
-- LOCATION COMPANY NAME
--

        locationCompanyName OBJECT-TYPE
        SYNTAX      DisplayString(SIZE(2..39))
        MAX-ACCESS      read-write
        STATUS      current
        DESCRIPTION
           "Name of the administrator's company."
        ::= { location 1 }

--
-- LOCATION SITE NAME
--

       locationSiteName OBJECT-TYPE
       SYNTAX      DisplayString(SIZE(1..39))
       MAX-ACCESS      read-write
       STATUS      current
       DESCRIPTION
          "Name of the deployment site."
       ::= { location 2 }

--
-- LOCATION ADDRESS 1
--

       locationAddress1 OBJECT-TYPE
       SYNTAX      DisplayString(SIZE(0..39))
       MAX-ACCESS      read-write
       STATUS      current
       DESCRIPTION
          "Physical location - address (line 1)."
       ::= { location 3 }

--
-- LOCATION ADDRESS 2
--

       locationAddress2 OBJECT-TYPE
       SYNTAX      DisplayString(SIZE(0..39))
       MAX-ACCESS      read-write
       STATUS      current
       DESCRIPTION
          "Physical location - address (line 2)."
       ::= { location 4 }

--
-- LOCATION CITY
--

       locationCity OBJECT-TYPE
       SYNTAX      DisplayString(SIZE(2..39))
       MAX-ACCESS      read-write
       STATUS      current
       DESCRIPTION
          "Physical location - city."
       ::= { location 5 }

--
-- LOCATION STATE
--

       locationState OBJECT-TYPE
       SYNTAX      DisplayString(SIZE(2..39))
       MAX-ACCESS      read-write
       STATUS      current
       DESCRIPTION
          "Physical location - state."
       ::= { location 6 }

--
-- LOCATION ZIP
--

       locationZip OBJECT-TYPE
       SYNTAX      DisplayString(SIZE(0..39))
       MAX-ACCESS      read-write
       STATUS      current
       DESCRIPTION
          "Physical location - zip."
       ::= { location 7 }

--
-- LOCATION COUNTRY
--

       locationCountry OBJECT-TYPE
       SYNTAX      DisplayString(SIZE(2..39))
       MAX-ACCESS      read-write
       STATUS      current
       DESCRIPTION
          "Physical location - country."
       ::= { location 8 }

--
-- LOCATION E-MAIL
--

       locationEmail OBJECT-TYPE
       SYNTAX      DisplayString(SIZE(5..39))
       MAX-ACCESS      read-write
       STATUS      current
       DESCRIPTION
          "Administrator's e-mail address."
       ::= { location 9 }

--
-- LOCATION VENUE TYPE
--

       locationVenueType OBJECT-TYPE
       SYNTAX      INTEGER {apartment(1),
                            bar-coffeeshop-restaurant(2),
                            convention-center(3),
                            corporate-guest-access(4),
                            education(5),
                            hospitality(6),
                            marina-camp-ground(7),
                            public-space(8),
                            public-transport(9),
                            other(10)
                           }
       MAX-ACCESS      read-write
       STATUS      current
       DESCRIPTION
          "This value indicates Venue Type chosen:
            (1) Apartment
            (2) Bar/Coffeeshop/Restaurant
            (3) Convention Center
            (4) Corporate Guest Access
            (5) Education
            (6) Hospitality
            (7) Marina/camp ground
            (8) Public Space
            (9) Public transport
           (10) Other"
       ::= { location 10 }

--
-- LOCATION NETWORK IP
--

       locationNetworkIp OBJECT-TYPE
       SYNTAX      IpAddress
       MAX-ACCESS      read-write
       STATUS      current
       DESCRIPTION
          "The IP Address for the Network side interface.  Note: in order
          to set this value, locationNetIntfCfgMode must be set to static.
          Note: you must reboot for changes to take effect."
       ::= { location 12 }

--
-- LOCATION NETMASK
--

       locationNetmask OBJECT-TYPE
       SYNTAX      IpAddress
       MAX-ACCESS      read-write
       STATUS      current
       DESCRIPTION
          "The Subnet Mask for the network side interface.  Note: in order
          to set this value, locationNetIntfCfgMode must be set to static.
          Note: you must reboot for changes to take effect."
       ::= { location 13 }

--
-- LOCATION GATEWAY
--

       locationGateway OBJECT-TYPE
       SYNTAX      IpAddress
       MAX-ACCESS      read-write
       STATUS      current
       DESCRIPTION
          "The IP Address of the default gateway.  Note: in order
          to set this value, locationNetIntfCfgMode must be set to static.
          Note: you must reboot for changes to take effect."
       ::= { location 14 }


--
-- LOCATION Network Interface Configuration Mode
--
       locationNetIntfCfgMode OBJECT-TYPE
       SYNTAX      INTEGER { static(0), dhcpClient(1), pppoeClient(2) }
       MAX-ACCESS      read-write
       STATUS      current
       DESCRIPTION
          "Setting this value to (0) will use statically configured IP
          address. Setting to (1) will enable DHCP Client for the system.
          Setting to (2) will enable PPPoE Client for the system.
          Note: you must reboot for changes to take effect."
       ::= { location 15 }


--
-- LOCATION ISO Country Code
--

       locationIsoCountryCode OBJECT-TYPE
       SYNTAX      DisplayString(SIZE(0..3))
       MAX-ACCESS      read-write
       STATUS      current
       DESCRIPTION
          "ISO Country Code"
       ::= { location 16 }

--
-- LOCATION Phone Country Code
--

       locationPhoneCountryCode OBJECT-TYPE
       SYNTAX      DisplayString(SIZE(0..10))
       MAX-ACCESS      read-write
       STATUS      current
       DESCRIPTION
          "Phone Country Code"
       ::= { location 17 }

--
-- LOCATION Calling Area Code
--

       locationCallingAreaCode OBJECT-TYPE
       SYNTAX      DisplayString(SIZE(0..10))
       MAX-ACCESS      read-write
       STATUS      current
       DESCRIPTION
          "Calling Area Code"
       ::= { location 18 }

--
-- LOCATION Network SSID/ZONE
--

       locationNetworkSsidZone OBJECT-TYPE
       SYNTAX      DisplayString(SIZE(0..32))
       MAX-ACCESS      read-write
       STATUS      current
       DESCRIPTION
          "Network SSID/ZONE"
       ::= { location 19 }


--
-- PASSTHROUGH
--

  ---
  --- PASSTHROUGH ON
  ---

  passthroughOn OBJECT-TYPE
  SYNTAX      INTEGER { disabled(0), enabled(1) }
  MAX-ACCESS      read-write
  STATUS      current
  DESCRIPTION
     "Setting this value to (1) will enable Passthrough Addresses feature.
     Setting this value to (0) will disable it.
     Note: If trying to set this value returns an error, please check to see if you have a valid license for this feature."
  ::= {passthrough 1}

   passthroughIPTable        OBJECT-TYPE
  SYNTAX            SEQUENCE OF PassThroughIPEntry
  MAX-ACCESS            not-accessible
  STATUS            current
  DESCRIPTION
      " Host passthrough table for IP addresses "
  ::= { passthrough 2 }

   passthroughIPEntry     OBJECT-TYPE
  SYNTAX         PassThroughIPEntry
  MAX-ACCESS         not-accessible
  STATUS         current
  DESCRIPTION
      " passthrough table entry "
  INDEX   { passthroughAddIndex }
  ::= { passthroughIPTable 1 }

   PassThroughIPEntry ::= SEQUENCE {
   passthroughAddIndex    Integer32,
   passthroughaddress     IpAddress,
   statusIP               RowStatus
   }

  passthroughAddIndex    OBJECT-TYPE
  SYNTAX         Integer32
  MAX-ACCESS     read-only
  STATUS         current
  DESCRIPTION
      " Passthrough Address Table Index"
  ::=   { passthroughIPEntry 1 }

  passthroughaddress     OBJECT-TYPE
  SYNTAX         IpAddress
  MAX-ACCESS         read-write
  STATUS         current
  DESCRIPTION
      " The packets destined for this IP address are
      passed through without authentication, authorization."
  ::= { passthroughIPEntry 2 }

  statusIP         OBJECT-TYPE
  SYNTAX         RowStatus
  MAX-ACCESS         read-write
  STATUS         current
  DESCRIPTION
         "Status of the Passthrough IP table entry."
  ::= { passthroughIPEntry 3 }

  passthroughDNSTable       OBJECT-TYPE
  SYNTAX            SEQUENCE OF PassThroughDNSEntry
  MAX-ACCESS            not-accessible
  STATUS            current
  DESCRIPTION
      " Host passthrough table for DNS names "
  ::= { passthrough 3 }

   passthroughDNSEntry    OBJECT-TYPE
  SYNTAX         PassThroughDNSEntry
  MAX-ACCESS         not-accessible
  STATUS         current
  DESCRIPTION
      " passthrough table entry "
  INDEX   { passthroughNameIndex }
  ::= { passthroughDNSTable 1 }

   PassThroughDNSEntry ::= SEQUENCE {
   passthroughNameIndex      Integer32,
   passthroughname           DisplayString,
   statusDNS                 RowStatus
   }

  passthroughNameIndex   OBJECT-TYPE
  SYNTAX         Integer32
  MAX-ACCESS     read-only
  STATUS         current
  DESCRIPTION
      " Passthrough Name Table Index"
  ::= { passthroughDNSEntry 1 }
   passthroughname     OBJECT-TYPE
  SYNTAX         DisplayString(SIZE(0..237))
  MAX-ACCESS         read-write
  STATUS         current
  DESCRIPTION
      " The packets destined for this DNS name are
      passed through without authentication, authorization."
  ::= { passthroughDNSEntry 2 }

   statusDNS        OBJECT-TYPE
  SYNTAX         RowStatus
  MAX-ACCESS         read-write
  STATUS         current
  DESCRIPTION
         "Status of the Passthrough DNS table entry."
  ::= { passthroughDNSEntry 3 }



  --
  -- PORTLOC - PORT LOCATION
  --

  --
  -- PORTLOC IN ROOM PORT MAPPING ON
  --

              portLocInRoomPortMappingOn OBJECT-TYPE
              SYNTAX      INTEGER { disabled(0), enabled(1) }
              MAX-ACCESS  read-write
              STATUS      current
              DESCRIPTION
                 "Setting this value to (1) will enable In Room Port Mapping
                 feature.  Setting this value to (0) will disable this feature.
                 Note: If trying to set this value returns an error, please check to see if you have a valid license for this feature."
              ::= { portLoc 1 }

  --
  -- PORTLOC IN ROOM PORT MAPPING USERNAME
  --

              portLocInRoomPortMappingUsername OBJECT-TYPE
              SYNTAX      DisplayString(SIZE(0..17))
              MAX-ACCESS      read-write
              STATUS      current
              DESCRIPTION
                 "Username needed when performing In Room Port Mapping.
                 (Maximum length: 17 characters)"
              ::= { portLoc 2 }

  --
  -- PORTLOC IN ROOM PORT MAPPING PASSWORD
  --

              portLocInRoomPortMappingPassword OBJECT-TYPE
              SYNTAX      DisplayString(SIZE(0..17))
              MAX-ACCESS      read-write
              STATUS      current
              DESCRIPTION
                 "Password needed when performing In Room Port Mapping."
              ::= { portLoc 3}

  --
  -- PORTLOC CONCENTRATOR TYPE
  --

              portLocConcentratorType OBJECT-TYPE
              SYNTAX      INTEGER { no(0), vlan1(1), vlan2(2),
                                   expresso(3), lucent(4), mdulite(5),
                                   rfc1493(6), riverdelta(7), elastic(8) }
              MAX-ACCESS  read-write
              STATUS      current
              DESCRIPTION
                 "Setting this value to (0) will indicate that no
                 concentrator will be used.  Entering (1) will mean the
                 device which understands 802.1Q VLAN IDs one-way will be
                 used, while (2) will indicate the device which understands
                 802.1Q VLAN IDs two-ways.  Entering (3) to (8) will indicate
                 that one of the following access concentrators will be
                 exploited: (3) Tut Systems Expresso, (4) Lucent DSL
                 Terminator, (5) Tut MDU Lite Systems, (6) any RFC1493
                 Compliant System, (7) RiverDelta 1000B, (8) Elastic Networks."
              ::= { portLoc 4 }

  --
  --  PORTLOC CONCENTRATOR TABLE
  --
              portLocConcentratorTable OBJECT-TYPE
              SYNTAX      SEQUENCE OF PortLocConcentratorTableEntry
              MAX-ACCESS      not-accessible
              STATUS      current
              DESCRIPTION
                 "List of IP addresses, SNMP community names, and uplink ports
                 for each concentrator."
                 ::= { portLoc 10 }

              portLocConcentratorTableEntry OBJECT-TYPE
              SYNTAX      PortLocConcentratorTableEntry
              MAX-ACCESS      not-accessible
              STATUS      current
              DESCRIPTION
                 "Concentrator table entry."
              INDEX       { portLocConcIndex }
                 ::= { portLocConcentratorTable 1 }

              PortLocConcentratorTableEntry ::= SEQUENCE {
                          portLocConcIndex     Integer32,
                          portLocAddress       IpAddress,
                          portLocCommunity     DisplayString,
                          portLocUplinkPort    Integer32
                       }

              portLocConcIndex OBJECT-TYPE
              SYNTAX      Integer32
              MAX-ACCESS  read-only
              STATUS      current
              DESCRIPTION
                 "Port-location Concentrator Table Index."
                 ::= { portLocConcentratorTableEntry 2 }

              portLocAddress OBJECT-TYPE
              SYNTAX      IpAddress
              MAX-ACCESS      read-only
              STATUS      current
              DESCRIPTION
                 "IP Address of the concentrator."
                 ::= { portLocConcentratorTableEntry 4 }

              portLocCommunity OBJECT-TYPE
              SYNTAX      DisplayString(SIZE(0..139))
              MAX-ACCESS      read-only
              STATUS      current
              DESCRIPTION
                 "SNMP community name of the concentrator."
                 ::= { portLocConcentratorTableEntry 6 }

              portLocUplinkPort OBJECT-TYPE
              SYNTAX      Integer32
              MAX-ACCESS  read-only
              STATUS      current
              DESCRIPTION
                 "Uplink port of the concentrator."
                 ::= { portLocConcentratorTableEntry 8 }
  --
  --  PORTLOC  TABLE
  --
              portLocTable OBJECT-TYPE
              SYNTAX      SEQUENCE OF PortLocTableEntry
              MAX-ACCESS      not-accessible
              STATUS      current
              DESCRIPTION
                 " Port-location Table maps ports to rooms"
                 ::= { portLoc 12 }

              portLocTableEntry OBJECT-TYPE
              SYNTAX      PortLocTableEntry
              MAX-ACCESS      not-accessible
              STATUS      current
              DESCRIPTION
                 " One entry of the
              port-location table"
              INDEX       { portLocIndex }
                 ::= { portLocTable 1 }

              PortLocTableEntry ::= SEQUENCE {
              portLocIndex         Integer32,
              portLocLocation      DisplayString,
              portLocPort          Integer32,
              portLocModemMAC      DisplayString,
              portLocDescription   DisplayString,
              portLocState         INTEGER
              }

              portLocIndex OBJECT-TYPE
              SYNTAX      Integer32
              MAX-ACCESS  read-only
              STATUS      current
              DESCRIPTION
                 " Port-location Table Index"
                 ::= { portLocTableEntry 1 }

              portLocLocation OBJECT-TYPE
              SYNTAX      DisplayString(SIZE(0..139))
              MAX-ACCESS      read-only
              STATUS      current
              DESCRIPTION
                 " Location description of the entry"
                 ::= { portLocTableEntry 2 }

              portLocPort OBJECT-TYPE
              SYNTAX      Integer32
              MAX-ACCESS  read-only
              STATUS      current
              DESCRIPTION
                 " Port of the concentrator this room is connected to"
                 ::= { portLocTableEntry 3 }

              portLocModemMAC OBJECT-TYPE
              SYNTAX      DisplayString
              MAX-ACCESS      read-only
              STATUS      current
              DESCRIPTION
                 " MAC Address of the Modem this room has (valid for
                 Riverdelta and similar concentrators only)"
                 ::= { portLocTableEntry 4 }

              portLocDescription OBJECT-TYPE
              SYNTAX      DisplayString(SIZE(0..139))
              MAX-ACCESS      read-only
              STATUS      current
              DESCRIPTION
                 " Description of the Location/Port"
                 ::= { portLocTableEntry 5 }

              portLocState OBJECT-TYPE
              SYNTAX      INTEGER { noCharge(0), charge(1), blocked(2) }
              MAX-ACCESS      read-only
              STATUS      current
              DESCRIPTION
                 " Billing/Access State of the port-location"
                 ::= { portLocTableEntry 6 }

  --
   --   RADIUS Proxy
   --

   --   RADIUS Proxy : RADIUS proxy enable/disable
  radProxyServices     OBJECT-TYPE
  SYNTAX         INTEGER { disabled(0), enabled(1) }
  MAX-ACCESS         read-write
  STATUS         current
  DESCRIPTION
      " Setting this value to (1) enables RADIUS proxy services.
      Setting it to zero disables RADIUS proxy services."
  ::= { radiusProxy 1 }

   --   RADIUS Proxy : Authentication server port number
  radProxyAuthSvrPort     OBJECT-TYPE
  SYNTAX         Integer32
  MAX-ACCESS     read-write
  STATUS         current
  DESCRIPTION
      " The UDP port number on which RADIUS authentication requests will be
      received. Setting this value to (0) disables RADIUS authentication proxy
      services."
  ::= { radiusProxy 2 }

   --   RADIUS Proxy : Accounting server port number
  radProxyAcctSvrPort     OBJECT-TYPE
  SYNTAX         Integer32
  MAX-ACCESS     read-write
  STATUS         current
  DESCRIPTION
      " The UDP port number on which RADIUS accounting requests will be
      received. Setting this value to (0) disables RADIUS accounting proxy
      services."
  ::= { radiusProxy 3 }


  -- RADIUS Proxy : Downstream server communication port number
  radProxyLocalServcomPort OBJECT-TYPE
  SYNTAX      Integer32
  MAX-ACCESS  read-write
  STATUS      current
  DESCRIPTION
     "Local UDP port for communicating with downstream servers. Must be either 0 or
     in the range 1024-5000."
  ::= { radiusProxy 5 }


   radProxyUpstreamNas    OBJECT IDENTIFIER ::= { radiusProxy 4 }

--
-- UPSTREAM NAS TABLE
--
     radProxyUpstreamNasTable OBJECT-TYPE
       SYNTAX      SEQUENCE OF RadProxyUpstreamNasTableEntry
       MAX-ACCESS  not-accessible
       STATUS  current
       DESCRIPTION
          "List of Upstream NASes."
       ::= { radProxyUpstreamNas 1 }

     radProxyUpstreamNasTableEntry OBJECT-TYPE
       SYNTAX      RadProxyUpstreamNasTableEntry
       MAX-ACCESS  not-accessible
       STATUS  current
       DESCRIPTION
          "An upstream NAS entry."
       INDEX  { nasIndex }
       ::= { radProxyUpstreamNasTable 1 }

     RadProxyUpstreamNasTableEntry ::=
       SEQUENCE
       {
        nasIndex        Integer32,
        nasEntryActive  INTEGER,
        nasIpAddress    IpAddress,
        nasAuthSec      DisplayString,
        nasAcctSec      DisplayString,
        nasDefProf      DisplayString,
        nasStatus       RowStatus
       }

     nasIndex OBJECT-TYPE
       SYNTAX     Integer32
       MAX-ACCESS  read-only
       STATUS     current
       DESCRIPTION
          "Upstream NAS Index"
       ::= { radProxyUpstreamNasTableEntry 1 }

     nasEntryActive OBJECT-TYPE
       SYNTAX      INTEGER { inactive(0), active(1) }
       MAX-ACCESS  read-write
       STATUS  current
       DESCRIPTION
          "Indicates whether or not this NAS is active. Requests from inactive NASes
           won't be processed"
       ::= { radProxyUpstreamNasTableEntry 2 }

     nasIpAddress OBJECT-TYPE
       SYNTAX      IpAddress
       MAX-ACCESS  read-write
       STATUS  current
       DESCRIPTION
          "IP Address of the upstream NAS."
       ::= { radProxyUpstreamNasTableEntry 3 }

     nasAuthSec   OBJECT-TYPE
       SYNTAX       DisplayString(SIZE(1..130))
       MAX-ACCESS       read-write
       STATUS       current
       DESCRIPTION
          "The secret key, shared with the upstream NAS, used for authentication
           packets."
       ::= { radProxyUpstreamNasTableEntry 4 }

     nasAcctSec   OBJECT-TYPE
       SYNTAX       DisplayString(SIZE(1..130))
       MAX-ACCESS       read-write
       STATUS       current
       DESCRIPTION
          "The secret key, shared with the upstream NAS, used for accounting
           packets."
       ::= { radProxyUpstreamNasTableEntry 5 }

     nasDefProf   OBJECT-TYPE
       SYNTAX       DisplayString(SIZE(1..40))
       MAX-ACCESS       read-write
       STATUS       current
       DESCRIPTION
          "(Optional) The name of the RADIUS service profile to handle requests from this
           upstream NAS if realm-basd routing fails. If not present, such packets will be
           discarded."
       ::= { radProxyUpstreamNasTableEntry 6 }

     nasStatus   OBJECT-TYPE
       SYNTAX       RowStatus
       MAX-ACCESS       read-write
       STATUS       current
       DESCRIPTION
          "Status of the upstream NAS table entry."
       ::= { radProxyUpstreamNasTableEntry 7}

--
--  Realm-based router
--

     rBserviceProfiles OBJECT IDENTIFIER ::= { realmBasedRouter 1 }

      --
      -- Table of service profiles
      --
     serviceProfileTable OBJECT-TYPE
       SYNTAX      SEQUENCE OF ServiceProfileTableEntry
       MAX-ACCESS  not-accessible
       STATUS  current
       DESCRIPTION
          "List of service profiles"
       ::= { rBserviceProfiles 1 }

     serviceProfileTableEntry OBJECT-TYPE
       SYNTAX      ServiceProfileTableEntry
       MAX-ACCESS  not-accessible
       STATUS  current
       DESCRIPTION
          "An entry in the list of service profiles."
       INDEX  { profIndex }
       ::= { serviceProfileTable 1 }

     ServiceProfileTableEntry ::=
       SEQUENCE
       {
        profIndex        Integer32,
        profName         DisplayString,
        radAuthOn        INTEGER,
        radAuthProto     INTEGER,
        radAuthSrv1Ip    IpAddress,
        radAuthSrv1Port  Integer32,
        radAuthSrv1Sec   DisplayString,
        radAuthSrv2Ip    IpAddress,
        radAuthSrv2Port  Integer32,
        radAuthSrv2Sec   DisplayString,
        radAcctOn        INTEGER,
        radAcctSrv1Ip    IpAddress,
        radAcctSrv1Port  Integer32,
        radAcctSrv1Sec   DisplayString,
        radAcctSrv2Ip    IpAddress,
        radAcctSrv2Port  Integer32,
        radAcctSrv2Sec   DisplayString,
        radRetrMethod    INTEGER,
        radRetrFreq      Integer32,
        radRetrAttempts  Integer32,
        profStatus       RowStatus
       }

     profIndex OBJECT-TYPE
       SYNTAX     Integer32
       MAX-ACCESS read-only
       STATUS current
       DESCRIPTION
          "Service Profile Index"
       ::= { serviceProfileTableEntry 1 }

     profName     OBJECT-TYPE
       SYNTAX       DisplayString(SIZE(1..40))
       MAX-ACCESS   read-write
       STATUS       current
       DESCRIPTION
          "The name of this service profile. Must be unique."
       ::= { serviceProfileTableEntry 2 }

     radAuthOn OBJECT-TYPE
       SYNTAX         INTEGER { disabled(0), enabled(1) }
       MAX-ACCESS     read-write
       STATUS         current
       DESCRIPTION
          "Set to 1 to enable radius authentication for this profile, 0 to disable."
       ::= { serviceProfileTableEntry 3 }

     radAuthProto OBJECT-TYPE
       SYNTAX         INTEGER   {
           rad-auth-proto-pap(0),
                 rad-auth-proto-chap(1),
           rad-auth-proto-mschap-v1(2),
                rad-auth-proto-mschap-v2(3)
           }
       MAX-ACCESS     read-write
       STATUS         current
       DESCRIPTION
          "Radius authentication protocol:
           rad-auth-proto-pap(0)         - PAP
           rad-auth-proto-chap(1)        - CHAP-MD5
           rad-auth-proto-mschap-v1(2)   - MS-CHAP v1
           rad-auth-proto-mschap-v2(3)   - MS-CHAP v2"
       ::= { serviceProfileTableEntry 4 }

     radAuthSrv1Ip OBJECT-TYPE
       SYNTAX      IpAddress
       MAX-ACCESS  read-write
       STATUS      current
       DESCRIPTION
          "IP address of the Primary Radius Authentication Server for this profile."
       ::= { serviceProfileTableEntry 5 }

     radAuthSrv1Port OBJECT-TYPE
       SYNTAX      Integer32
       MAX-ACCESS  read-write
       STATUS      current
       DESCRIPTION
          "Port of the Primary Radius Authentication Server for this profile."
       ::= { serviceProfileTableEntry 6 }

     radAuthSrv1Sec OBJECT-TYPE
       SYNTAX      DisplayString(SIZE(0..130))
       MAX-ACCESS  read-write
       STATUS      current
       DESCRIPTION
          "Secret Key of the Primary Radius Authentication Server for this profile."
       ::= { serviceProfileTableEntry 7 }

     radAuthSrv2Ip OBJECT-TYPE
       SYNTAX      IpAddress
       MAX-ACCESS  read-write
       STATUS      current
       DESCRIPTION
          "IP address of the Secondary Radius Authentication Server for this profile."
       ::= { serviceProfileTableEntry 8 }

     radAuthSrv2Port OBJECT-TYPE
       SYNTAX      Integer32
       MAX-ACCESS  read-write
       STATUS      current
       DESCRIPTION
          "Port of the Secondary Radius Authentication Server for this profile."
       ::= { serviceProfileTableEntry 9 }

     radAuthSrv2Sec OBJECT-TYPE
       SYNTAX      DisplayString(SIZE(0..130))
       MAX-ACCESS      read-write
       STATUS      current
       DESCRIPTION
          "Secret Key of the Secondary Radius Authentication Server for this profile."
       ::= { serviceProfileTableEntry 10}


     radAcctOn OBJECT-TYPE
       SYNTAX         INTEGER { disabled(0), enabled(1) }
       MAX-ACCESS     read-write
       STATUS         current
       DESCRIPTION
          "Set to 1 to enable radius accounting for this profile, 0 to disable."
       ::= { serviceProfileTableEntry 11 }

     radAcctSrv1Ip OBJECT-TYPE
       SYNTAX      IpAddress
       MAX-ACCESS  read-write
       STATUS      current
       DESCRIPTION
          "IP address of the Primary Radius Accounting Server for this profile."
       ::= { serviceProfileTableEntry 12 }

     radAcctSrv1Port OBJECT-TYPE
       SYNTAX      Integer32
       MAX-ACCESS  read-write
       STATUS      current
       DESCRIPTION
          "Port of the Primary Radius Accounting Server for this profile."
       ::= { serviceProfileTableEntry 13 }

     radAcctSrv1Sec OBJECT-TYPE
       SYNTAX      DisplayString(SIZE(0..130))
       MAX-ACCESS  read-write
       STATUS      current
       DESCRIPTION
          "Secret Key of the Primary Radius Accounting Server for this profile."
       ::= { serviceProfileTableEntry 14 }

     radAcctSrv2Ip OBJECT-TYPE
       SYNTAX      IpAddress
       MAX-ACCESS  read-write
       STATUS      current
       DESCRIPTION
          "IP address of the Secondary Radius Accounting Server for this profile."
       ::= { serviceProfileTableEntry 15 }

     radAcctSrv2Port OBJECT-TYPE
       SYNTAX      Integer32
       MAX-ACCESS  read-write
       STATUS      current
       DESCRIPTION
          "Port of the Secondary Radius Accounting Server for this profile."
       ::= { serviceProfileTableEntry 16 }

     radAcctSrv2Sec OBJECT-TYPE
       SYNTAX      DisplayString(SIZE(0..130))
       MAX-ACCESS      read-write
       STATUS      current
       DESCRIPTION
          "Secret Key of the Secondary Radius Accounting Server for this profile."
       ::= { serviceProfileTableEntry 17 }

     radRetrMethod OBJECT-TYPE
       SYNTAX         INTEGER { failover(0), round-robin(1) }
       MAX-ACCESS     read-write
       STATUS         current
       DESCRIPTION
          "Set to 0 if the retransmission method is failover, 1 if round-robin."
       ::= { serviceProfileTableEntry 18 }

     radRetrFreq OBJECT-TYPE
       SYNTAX         Integer32
       MAX-ACCESS     read-write
       STATUS         current
       DESCRIPTION
          "Set the frequency of retransmission (per second)."
       ::= { serviceProfileTableEntry 19 }

     radRetrAttempts OBJECT-TYPE
       SYNTAX         Integer32
       MAX-ACCESS     read-write
       STATUS         current
       DESCRIPTION
          "Set the number of retransmissions."
       ::= { serviceProfileTableEntry 20 }

     profStatus   OBJECT-TYPE
       SYNTAX       RowStatus
       MAX-ACCESS   read-write
       STATUS       current
       DESCRIPTION
          "Status of the service profile table entry."
       ::= { serviceProfileTableEntry 21}


   rBtunnelProfiles OBJECT IDENTIFIER ::= { realmBasedRouter 3 }

      --
      -- Table of tunnel profiles
      --
       tunnelProfileTable OBJECT-TYPE
       SYNTAX  SEQUENCE OF TunnelProfileTableEntry
       MAX-ACCESS  not-accessible
       STATUS  current
       DESCRIPTION
          "List of tunnel profiles"
       ::= { rBtunnelProfiles 1 }

       tunnelProfileTableEntry OBJECT-TYPE
       SYNTAX  TunnelProfileTableEntry
       MAX-ACCESS  not-accessible
       STATUS  current
       DESCRIPTION
          "An entry in the list of tunnel profiles."
       INDEX  { tunProfIndex }
       ::= { tunnelProfileTable 1 }

       TunnelProfileTableEntry ::=
       SEQUENCE
       {
        tunProfIndex     Integer32,
        tunProfName      DisplayString,
        tunPassword      DisplayString,
        tunPeerIp        IpAddress,
        tunProfStatus    RowStatus
       }

       tunProfIndex OBJECT-TYPE
       SYNTAX     Integer32
       MAX-ACCESS read-only
       STATUS current
       DESCRIPTION
          "Tunnel Profile Index"
       ::= { tunnelProfileTableEntry 2 }

       tunProfName  OBJECT-TYPE
       SYNTAX       DisplayString(SIZE(1..40))
       MAX-ACCESS       read-write
       STATUS       current
       DESCRIPTION
          "The name of this tunnel profile. Must be unique."
       ::= { tunnelProfileTableEntry 4 }

       tunPassword  OBJECT-TYPE
       SYNTAX       DisplayString(SIZE(1..64))
       MAX-ACCESS       read-write
       STATUS       current
       DESCRIPTION
          "The tunnel password."
       ::= { tunnelProfileTableEntry 6 }

       tunPeerIp   OBJECT-TYPE
       SYNTAX      IpAddress
       MAX-ACCESS      read-write
       STATUS      current
       DESCRIPTION
          "IP address of the tunnel peer for this tunnel."
       ::= { tunnelProfileTableEntry 8 }

       tunProfStatus   OBJECT-TYPE
       SYNTAX       RowStatus
       MAX-ACCESS       read-write
       STATUS       current
       DESCRIPTION
          "Status of the tunnel profile table entry."
       ::= { tunnelProfileTableEntry 20}


   rBroutes      OBJECT IDENTIFIER ::= { realmBasedRouter 2 }

      --
      -- Table of realm-based routes
      --
       realmBasedRoutingTable OBJECT-TYPE
       SYNTAX  SEQUENCE OF RealmBasedRoutingTableEntry
       MAX-ACCESS  not-accessible
       STATUS  current
       DESCRIPTION
          "List of realm-based routes"
       ::= { rBroutes 1 }

       realmBasedRoutingTableEntry OBJECT-TYPE
       SYNTAX  RealmBasedRoutingTableEntry
       MAX-ACCESS  not-accessible
       STATUS  current
       DESCRIPTION
          "An entry in the list of realm-based routes."
       INDEX  { realmIndex }
       ::= { realmBasedRoutingTable 1 }

       RealmBasedRoutingTableEntry ::=
       SEQUENCE
       {
        realmIndex       Integer32,
        realmEntryActive INTEGER,
        realmWildcard    INTEGER,
        realmName        DisplayString,
        realmMatchType   INTEGER,
        realmProfile     DisplayString,
        realmTunProfile  DisplayString,
        realmStrip       INTEGER,
        realmTunStrip    INTEGER,
   realmTunLocHostName DisplayString,
        realmStatus      RowStatus
       }

       realmIndex OBJECT-TYPE
       SYNTAX     Integer32
       MAX-ACCESS read-only
       STATUS current
       DESCRIPTION
          "realm-based route Index"
       ::= { realmBasedRoutingTableEntry 1 }

       realmEntryActive OBJECT-TYPE
       SYNTAX  INTEGER { inactive(0), active(1) }
       MAX-ACCESS  read-write
       STATUS  current
       DESCRIPTION
          "Indicates whether or not this route is active."
       ::= { realmBasedRoutingTableEntry 2 }

       realmWildcard OBJECT-TYPE
       SYNTAX  INTEGER { no(0), yes(1) }
       MAX-ACCESS  read-write
       STATUS  current
       DESCRIPTION
          "Indicates whether or not this route will match all realm-names or a single,
           specific realm-name."
       ::= { realmBasedRoutingTableEntry 3 }

       realmName   OBJECT-TYPE
       SYNTAX       DisplayString(SIZE(1..80))
       MAX-ACCESS       read-write
       STATUS       current
       DESCRIPTION
          "If this route is for a specific realm, this is the name of that realm."
       ::= { realmBasedRoutingTableEntry 4 }

       realmMatchType OBJECT-TYPE
       SYNTAX  INTEGER { prefixOnly(0), suffixOnly(1), prefixOrSuffix(2) }
       MAX-ACCESS  read-write
       STATUS  current
       DESCRIPTION
          "Indicates whether this policy pertains to prefix realms, suffix realms, or to both."
       ::= { realmBasedRoutingTableEntry 5 }

       realmProfile   OBJECT-TYPE
       SYNTAX       DisplayString(SIZE(1..40))
       MAX-ACCESS       read-write
       STATUS       current
       DESCRIPTION
          "The RADIUS service profile to which this policy will route."
       ::= { realmBasedRoutingTableEntry 6 }

       realmTunProfile   OBJECT-TYPE
       SYNTAX       DisplayString(SIZE(1..40))
       MAX-ACCESS       read-write
       STATUS       current
       DESCRIPTION
          "The tunnel profile to which this policy will route."
       ::= { realmBasedRoutingTableEntry 9 }

       realmStrip OBJECT-TYPE
       SYNTAX  INTEGER { dontStrip(0), strip(1) }
       MAX-ACCESS  read-write
       STATUS  current
       DESCRIPTION
          "Indicates whether or not realm-names should be stripped from user names
           before sending the username to a RADIUS server."
       ::= { realmBasedRoutingTableEntry 7 }

       realmTunStrip OBJECT-TYPE
       SYNTAX  INTEGER { dontStrip(0), strip(1) }
       MAX-ACCESS  read-write
       STATUS  current
       DESCRIPTION
          "Indicates whether or not realm-names should be stripped from user names
           before sending the username to a tunnel server (LNS)."
       ::= { realmBasedRoutingTableEntry 10 }

       realmTunLocHostName   OBJECT-TYPE
       SYNTAX       DisplayString(SIZE(1..40))
       MAX-ACCESS       read-write
       STATUS       current
       DESCRIPTION
          "Local host name fopr purposes of tunnels, whether profile-triggerred
          or RADIUS-triggerred "
       ::= { realmBasedRoutingTableEntry 11 }

  realmStatus   OBJECT-TYPE
       SYNTAX       RowStatus
       MAX-ACCESS       read-write
       STATUS       current
       DESCRIPTION
          "Status of the realm-based routing table entry."
       ::= { realmBasedRoutingTableEntry 8}



   --
  -- SESSION RATE LIMITING
  --


       --
       -- SESSION RATE LIMITING ENABLE
       --

              sessionLimitEnable OBJECT-TYPE
              SYNTAX      INTEGER { disabled(0), enabled(1) }
              MAX-ACCESS      read-write
              STATUS      current
              DESCRIPTION
                 "Enable/Disable sesstion rate limiting capability"
              ::= { sessionlimit 1 }


       --
       -- SESSION RATE LIMITING MEAN RATE
       --

              sessionLimitMeanRate OBJECT-TYPE
              SYNTAX      Integer32
              MAX-ACCESS  read-write
              STATUS      current
              DESCRIPTION
                  " This value indicates the
              session rate limiting mean rate.
              THE VALUE MUST BE LESS THAN the session
              rate limiting burst size."
               ::= { sessionlimit 2 }


       --
       -- SESSION RATE LIMITING BURST SIZE
       --

              sessionLimitBurstSize OBJECT-TYPE
              SYNTAX      Integer32
              MAX-ACCESS  read-write
              STATUS      current
              DESCRIPTION
                  " This value indicates the
              session rate burst size.
              THE VALUE MUST BE LARGER THAN the session
              rate limiting mean rate"
               ::= { sessionlimit 3 }

       --
       -- SESSION RATE LIMITING TIME INTERVAL
       --

              sessionLimitTimeInterval OBJECT-TYPE
              SYNTAX      Integer32
              MAX-ACCESS  read-write
              STATUS      current
              DESCRIPTION
                  " This value indicates the
              session rate time interval."
               ::= { sessionlimit 4 }

       --
       -- SESSION RATE LIMITING ADD OFFENDERS TO MAC FILTERING ENABLE
       --

              sessionLimitFilterOffendersEnable OBJECT-TYPE
              SYNTAX      INTEGER { disabled(0), enabled(1) }
              MAX-ACCESS  read-write
              STATUS      current
              DESCRIPTION
                 "Enable/Disable adding users who exceed prescribed rate to MAC Filtering"
              ::= { sessionlimit 5 }

   --
   --   SMTP
   --

   --
   --   SMTP : SMTP (Misconfigured) redirect enable/disable
   --
   smtpRedirect     OBJECT-TYPE
  SYNTAX         INTEGER { disabled(0), enabled(1) }
  MAX-ACCESS     read-write
  STATUS         current
  DESCRIPTION
      " Setting this value to (1) enables SMTP redirection for misconfigured subscribers.
      Setting this value to (0) disables SMTP redirection for misconfigured subscribers.
      (NOTE: Setting it to (0) also sets it to (0) for properly configureds)."
  ::= { smtp 1 }


   --
   --   SMTP : Server IP
   --
   smtpServerIP     OBJECT-TYPE
  SYNTAX         IpAddress
  MAX-ACCESS         read-write
  STATUS         current
  DESCRIPTION
      " The IP address of the SMTP server to redirect all SMTP messages to."
  ::= { smtp 2 }

   --
   --   SMTP : SMTP (Properly Configured) redirect enable/disable
   --
   smtpPcRedirect      OBJECT-TYPE
  SYNTAX         INTEGER { disabled(0), enabled(1) }
  MAX-ACCESS     read-write
  STATUS         current
  DESCRIPTION
      " Setting this value to (1) enables SMTP redirection for properly configured subscribers.
      Setting this value to (0) disables SMTP redirection for properly configured subscribers.
      (NOTE: Setting it to (1) also sets it to (1) for mis-configureds)."
  ::= { smtp 3 }

   --
   --   SMTP : SMTP server account username
   --
   smtpUsername  OBJECT-TYPE
  SYNTAX         DisplayString(SIZE(0..39))
  MAX-ACCESS         read-write
  STATUS         current
  DESCRIPTION
      " For SMTP servers which support login authentication, enter
        valid username for an account on that server.
        NOTE: Length of username should be shortest allowed by
        SMTP server. Clients with shorter username may not be able
        to send e-mail. "
  ::= { smtp 4 }

   --
   --   SMTP : SMTP server account password
   --
   smtpPassword  OBJECT-TYPE
  SYNTAX         DisplayString(SIZE(0..39))
  MAX-ACCESS         read-write
  STATUS         current
  DESCRIPTION
      " For SMTP servers which support login authentication, enter
        valid password for an account on that server.
        NOTE: Length of username should be shortest allowed by
        SMTP server. Clients with shorter password may not be able
        to send e-mail. "
  ::= { smtp 5 }

   --
   --   SMTP : Server DNS Name
   --
   smtpServerDNS     OBJECT-TYPE
  SYNTAX         DisplayString(SIZE(0..238))
  MAX-ACCESS         read-write
  STATUS         current
  DESCRIPTION
      " The DNS name of the SMTP server to redirect all SMTP messages to. If this field
      is set, then smtpServerIP will also be updated to reflect the resolved IP address
      of the DNS name."
  ::= { smtp 6 }


  --
  -- SNMP AGENT
  --

              snmpdOn OBJECT-TYPE
              SYNTAX         INTEGER { disabled(0), enabled(1) }
              MAX-ACCESS     read-write
              STATUS         current
              DESCRIPTION
                 "Set to 1 to enable SNMP, 0 to disable.  Note: If trying to set this value
                 returns an error, please check to see if you have a valid license for this
                 feature.  Note: You must reboot for changes to take effect."
              ::= { snmpagent 1 }

              systemContact OBJECT-TYPE
              SYNTAX         DisplayString(SIZE(1..238))
              MAX-ACCESS         read-write
              STATUS         current
              DESCRIPTION
                 "System contact person.  Note: You must reboot for changes to take effect."
              ::= { snmpagent 2 }

              systemLocation OBJECT-TYPE
              SYNTAX         DisplayString(SIZE(1..238))
              MAX-ACCESS         read-write
              STATUS         current
              DESCRIPTION
                 "Physical location of this device.  Note: You must reboot for changes to take effect."
              ::= { snmpagent 3 }

              getCommunity OBJECT-TYPE
              SYNTAX         DisplayString(SIZE(1..238))
              MAX-ACCESS         read-write
              STATUS         current
              DESCRIPTION
                 "Get community string.  Note: You must reboot for changes to take effect."
              ::= { snmpagent 4 }

              setCommunity OBJECT-TYPE
              SYNTAX         DisplayString(SIZE(1..238))
              MAX-ACCESS         read-write
              STATUS         current
              DESCRIPTION
                 "Set community string.  Note: You must reboot for changes to take effect."
              ::= { snmpagent 5 }

              trapCommunity OBJECT-TYPE
              SYNTAX         DisplayString(SIZE(1..238))
              MAX-ACCESS         read-write
              STATUS         current
              DESCRIPTION
                 "Trap community string.  Note: You must reboot for changes to take effect."
              ::= { snmpagent 6 }

              trapIP OBJECT-TYPE
              SYNTAX         IpAddress
              MAX-ACCESS         read-write
              STATUS         current
              DESCRIPTION
                 "IP address of host to which to send traps.  Note: You must reboot for changes to take effect."
              ::= { snmpagent 7 }


  --
  -- SUBNETS
  --

     subnetTable OBJECT-TYPE
       SYNTAX  SEQUENCE OF SubnetTableEntry
       MAX-ACCESS  not-accessible
       STATUS  current
       DESCRIPTION
         "Currently active public subnets."
       ::= { subnets 1 }

     subnetTableEntry OBJECT-TYPE
       SYNTAX  SubnetTableEntry
       MAX-ACCESS  not-accessible
       STATUS  current
       DESCRIPTION
         "Table of Public Subnets"
       INDEX   { subnetIndex }
       ::= { subnetTable 1 }

     SubnetTableEntry ::=
       SEQUENCE {
                subnetIndex  Integer32,
                subnet       IpAddress,
                mask         IpAddress,
                subnetStatus RowStatus
                    }

     subnetIndex OBJECT-TYPE
       SYNTAX  Integer32
       MAX-ACCESS  read-only
       STATUS  current
       DESCRIPTION
         " Subnet Table Index"
       ::= { subnetTableEntry 1 }

     subnet OBJECT-TYPE
       SYNTAX  IpAddress
       MAX-ACCESS  read-write
       STATUS  current
       DESCRIPTION
         " Subnet"
       ::= { subnetTableEntry 2 }

     mask OBJECT-TYPE
       SYNTAX  IpAddress
       MAX-ACCESS  read-write
       STATUS  current
       DESCRIPTION
         " Subnet mask"
       ::= { subnetTableEntry 3 }

     subnetStatus      OBJECT-TYPE
       SYNTAX         RowStatus
       MAX-ACCESS         read-write
       STATUS  current
       DESCRIPTION
         "Status of the public subnet table entry."
       ::= { subnetTableEntry 4 }

--
-- SUBSCRIBER SETTINGS
--

--
-- SUBSCRIBER idle timeout
--
     subIdleLogoutTimeout OBJECT-TYPE
       SYNTAX     Integer32(300..86400)
       MAX-ACCESS  read-write
  STATUS       current
  DESCRIPTION
     "Time (in seconds), after which subscriber is logged out. Does not apply
      to subscribers logged in via RADIUS. Valid values are from 300 to
      86400 seconds"
       ::= { subsettings 1 }

  --
  -- SUBSCRIBER-to-subscriber communications blocking
  --
     subToSubCommBlock  OBJECT-TYPE
  SYNTAX      INTEGER {disabled(0), enabled (1) }
  MAX-ACCESS  read-write
  STATUS       current
  DESCRIPTION
    "When enabled, this feature will prevent wireless subscribers from
     communicating with one another. When communications blocking is disabled,
     subscribers will be allowed to communicate"
  ::= { subsettings 2 }


--
-- SYSTEM
--
     systemLoggingOn OBJECT-TYPE
       SYNTAX      INTEGER { disabled(0), enabled (1) }
       MAX-ACCESS  read-write
       STATUS      current
       DESCRIPTION
         "Setting this value to (1) will enable logging (via standard
          SYSLOG) of system messages.  Setting this value to (0) will
          disable system logging."
       ::= { system 1 }

--
-- SYSTEM LOG NUMBER
--
     systemLogNumber OBJECT-TYPE
       SYNTAX      Integer32(0..7)
       MAX-ACCESS  read-write
       STATUS      current
       DESCRIPTION
         "The log number (0-7 of standard SYSLOG) for system logging."
       ::= { system 2 }

--
-- SYSTEM LOG FILTER
--
     systemLogFilter OBJECT-TYPE
       SYNTAX         INTEGER {emergency(0), alert(1), critical(2), error(3),
                          warning(4), notice(5), info(6), debug(7) }
       MAX-ACCESS     read-write
       STATUS         current
       DESCRIPTION
         "Select the filter level for SYSTEM Logs
     Available settings: Emergency(0), Alert(1), Critical(2), Error(3),
               Warning(4), Notice(5), Info(6), Debug(7)"
       ::= { system 3}

  --
  -- SYSTEM LOG SERVER IP
  --
     systemLogServerIp OBJECT-TYPE
       SYNTAX      IpAddress
       MAX-ACCESS  read-write
       STATUS      current
       DESCRIPTION
         "IP address of the SYSLOG server to receive system messages."
       ::= { system 4 }

     systemSaveToFile OBJECT-TYPE
       SYNTAX      INTEGER { disabled(0), enabled (1) }
       MAX-ACCESS  read-write
       STATUS      current
       DESCRIPTION
         "Setting this value to (1) will enable saving of SYSTEM logs
         to file.  Setting this value to (0) will disable storing of
       SYSTEM logs in a file."
       ::= { system 5 }

--
-- SYSTEM REPORT SYSLOGS
--
     systemReportLoggingOn OBJECT-TYPE
       SYNTAX      INTEGER { disabled(0), enabled (1) }
       MAX-ACCESS  read-write
       STATUS      current
       DESCRIPTION
         "Setting this value to (1) will enable logging (via standard
          SYSLOG) of SYSTEM REPORT messages. Setting this value to (0) will
          disable SYSTEM REPORT logging."
       ::= { system 6 }

     systemReportLogNumber OBJECT-TYPE
       SYNTAX      Integer32(0..7)
       MAX-ACCESS  read-write
       STATUS      current
       DESCRIPTION
         "The log number (0-7 of standard SYSLOG) for SYSTEM REPORT logging."
       ::= { system 7 }

     systemReportLogServerIp OBJECT-TYPE
       SYNTAX      IpAddress
       MAX-ACCESS  read-write
       STATUS      current
       DESCRIPTION
         "IP address of the SYSLOG server to receive SYSTEM REPORT log messages."
       ::= { system 8 }

     systemReportLogInterval OBJECT-TYPE
       SYNTAX      Integer32(1..99999)
       MAX-ACCESS  read-write
       STATUS      current
       DESCRIPTION
         "Interval (in minutes) with which SYSTEM REPORT log messages are sent"
       ::= { system 9 }

--
-- SYSTEM VERSION
--
     systemVersion OBJECT-TYPE
       SYNTAX      DisplayString(SIZE(1..32))
       MAX-ACCESS  read-only
       STATUS      current
       DESCRIPTION
         "Version of the unit, includes model and software version."
       ::= { system 10 }

--
-- SYSTEM NSE ID
--
     systemNseId OBJECT-TYPE
       SYNTAX      DisplayString(SIZE(1..32))
       MAX-ACCESS  read-only
       STATUS      current
       DESCRIPTION
         "ID of the unit."
       ::= { system 11 }

--
-- SYSTEM REBOOT
--
     systemReboot OBJECT-TYPE
       SYNTAX      INTEGER { reboot(1) }
       MAX-ACCESS  read-write
       STATUS      current
       DESCRIPTION
         "Setting this value to (1) will cause the operating system
          to reboot."
       ::= { system 12 }

--
-- SYSTEM BRIDGE MODE
--
     systemBridgeMode OBJECT-TYPE
       SYNTAX      INTEGER { disabled(0), enabled(1) }
       MAX-ACCESS  read-write
       STATUS      current
       DESCRIPTION
         "Setting this value to (1) will enable bridge mode.  Setting
          this value to (0) will disable bridge mode.  Note: If trying
          to set this value returns an error, please check to see if you have a valid license for this feature."
       ::= { system 13 }

--
-- SYSTEM CONFIG FILE
--

     systemConfigFile OBJECT-TYPE
       SYNTAX      INTEGER { factory(1), export(2), import(3) }
       MAX-ACCESS  read-write
       STATUS      current
       DESCRIPTION
         "Setting this value to (1) will restore the factory configuration
          settings.  Setting this value to (2) will export the current configuration
          to an archive file.  Setting this value to (3) will restore settings from
          the most recent archive file, if one exists."
       ::= { system 14 }

--
-- SYSTEM CONFIG FILE STATUS
--
     systemConfigFileStatus OBJECT-TYPE
       SYNTAX      INTEGER { noError(0), errorCurrentNotChanged(1),
                             errorCurrentMaybeCorrupted(2), errorCurrentNotArchived (3) }
       MAX-ACCESS  read-only
       STATUS      current
       DESCRIPTION
         "This value indicates the status of systemConfigFile set query.  (0) -
          no error occurred, (1) - error occurred, current settings were not changed,
          (2) - error occurred, current settings may have been corrupted,
          (3) - error occurred, current settings were not archived."
       ::= { system 15 }

     systemAdminConcurrencyOn OBJECT-TYPE
       SYNTAX      INTEGER { disabled(0), enabled(1) }
       MAX-ACCESS  read-write
       STATUS      current
       DESCRIPTION
         "Setting this value to (1) will enable Admin
          Interface Concurrency enforcement.  Setting this value
          to (0) will disable Concurrency enforcement. Note: If
          trying to set this value returns an error, please check
          to see if you have a valid license for this feature."
       ::= { system 16 }

  --
  -- SYSTEM UPTIME
  --

              systemUptime OBJECT-TYPE
              SYNTAX      DisplayString(SIZE(0..64))
              MAX-ACCESS  read-only
              STATUS      current
              DESCRIPTION
                 "Uptime of the unit"
              ::= { system 17 }

  --
  -- SYSTEM ACCESS/REBOOT HISTORY TABLE
  --

              systemHistoryTable OBJECT-TYPE
              SYNTAX      SEQUENCE OF SystemHistoryTableEntry
              MAX-ACCESS      not-accessible
              STATUS      current
              DESCRIPTION
                 "List of last 500 access/reboot history entries."
              ::= { system 18 }

              systemHistoryTableEntry OBJECT-TYPE
              SYNTAX      SystemHistoryTableEntry
              MAX-ACCESS      not-accessible
              STATUS      current
              DESCRIPTION
                 "Access/reboot history table entry."
              INDEX       { systemHistoryIndex }
              ::= { systemHistoryTable 1 }

              SystemHistoryTableEntry ::= SEQUENCE {
                          systemHistoryIndex      Integer32,
                          systemHistoryTimestamp  DisplayString,
                          systemHistoryLogin      DisplayString,
                          systemHistoryAddress    IpAddress,
                          systemHistoryMessage    DisplayString
                       }

              systemHistoryIndex OBJECT-TYPE
              SYNTAX      Integer32
              MAX-ACCESS  read-only
              STATUS      current
              DESCRIPTION
                 "Access/reboot history table index."
              ::= { systemHistoryTableEntry 1 }

              systemHistoryTimestamp OBJECT-TYPE
              SYNTAX      DisplayString(SIZE(24))
              MAX-ACCESS      read-only
              STATUS      current
              DESCRIPTION
                 "Time when access occurred."
              ::= { systemHistoryTableEntry 2 }

              systemHistoryLogin OBJECT-TYPE
              SYNTAX      DisplayString(SIZE(0..14))
              MAX-ACCESS      read-only
              STATUS      current
              DESCRIPTION
                 "Login name of the user who generated access."
              ::= { systemHistoryTableEntry 3 }

              systemHistoryAddress OBJECT-TYPE
              SYNTAX      IpAddress
              MAX-ACCESS      read-only
              STATUS      current
              DESCRIPTION
                 "IP Address of the machine from which access was made."
              ::= { systemHistoryTableEntry 4 }

              systemHistoryMessage OBJECT-TYPE
              SYNTAX      DisplayString(SIZE(0..429))
              MAX-ACCESS      read-only
              STATUS      current
              DESCRIPTION
                 "Type of access occurred."
              ::= { systemHistoryTableEntry 5 }


--
-- SYSTEM SYSLOG HISTORY TABLE
--

              systemSyslogTable OBJECT-TYPE
              SYNTAX      SEQUENCE OF SystemSyslogTableEntry
              MAX-ACCESS      not-accessible
              STATUS      current
              DESCRIPTION
                 "List of last 1000 syslog entries."
              ::= { system 19 }

              systemSyslogTableEntry OBJECT-TYPE
              SYNTAX      SystemSyslogTableEntry
              MAX-ACCESS      not-accessible
              STATUS      current
              DESCRIPTION
                 "Syslog history table entry."
              INDEX       { systemSyslogIndex }
              ::= { systemSyslogTable 1 }

              SystemSyslogTableEntry ::= SEQUENCE {
                          systemSyslogIndex      Integer32,
                          systemSyslogTimestamp  DisplayString,
                          systemSyslogVersion    DisplayString,
                          systemSyslogAddress    IpAddress,
                          systemSyslogMessage    DisplayString
                       }

              systemSyslogIndex OBJECT-TYPE
              SYNTAX      Integer32
              MAX-ACCESS  read-only
              STATUS      current
              DESCRIPTION
                 "Syslog history table index."
              ::= { systemSyslogTableEntry 1 }

              systemSyslogTimestamp OBJECT-TYPE
              SYNTAX      DisplayString(SIZE(24))
              MAX-ACCESS      read-only
              STATUS      current
              DESCRIPTION
                 "Time when syslog occurred."
              ::= { systemSyslogTableEntry 2 }

              systemSyslogVersion OBJECT-TYPE
              SYNTAX      DisplayString(SIZE(0..14))
              MAX-ACCESS      read-only
              STATUS      current
              DESCRIPTION
                 "Version of the sending machine."
              ::= { systemSyslogTableEntry 3 }

              systemSyslogAddress OBJECT-TYPE
              SYNTAX      IpAddress
              MAX-ACCESS      read-only
              STATUS      current
              DESCRIPTION
                 "IP Address of the machine which send the syslog."
              ::= { systemSyslogTableEntry 4 }

              systemSyslogMessage OBJECT-TYPE
              SYNTAX      DisplayString(SIZE(0..429))
              MAX-ACCESS      read-only
              STATUS      current
              DESCRIPTION
                 "Type of syslog."
              ::= { systemSyslogTableEntry 5 }




  --
  -- SYSTEM STATIC PORT-MAPPING TABLE
  --

              systemStaticPortMappingTable OBJECT-TYPE
              SYNTAX      SEQUENCE OF SystemStaticPortMappingTableEntry
              MAX-ACCESS      not-accessible
              STATUS      current
              DESCRIPTION
                 "List of Static Port-mapping Table entries."
              ::= { system 20 }

              systemStaticPortMappingTableEntry OBJECT-TYPE
              SYNTAX      SystemStaticPortMappingTableEntry
              MAX-ACCESS      not-accessible
              STATUS      current
              DESCRIPTION
                 "Static Port Mapping table entry."
              INDEX       { systemStaticPortMappingIndex }
              ::= { systemStaticPortMappingTable 1 }

              SystemStaticPortMappingTableEntry ::= SEQUENCE {
        systemStaticPortMappingIndex        Integer32,
        systemStaticPortMappingMAC    DisplayString,
        systemStaticPortMappingInternalIP   IpAddress,
        systemStaticPortMappingInternalPort Integer32,
        systemStaticPortMappingExternalIP   IpAddress,
        systemStaticPortMappingExternalPort Integer32,
        systemStaticPortMappingRemoteIP  IpAddress,
        systemStaticPortMappingRemotePort   Integer32,
        systemStaticPortMappingProto     INTEGER,
        systemStaticPortMappingStatus    RowStatus
        }

              systemStaticPortMappingIndex OBJECT-TYPE
              SYNTAX      Integer32
              MAX-ACCESS  read-only
              STATUS      current
              DESCRIPTION
                 "Access/reboot history table index."
              ::= { systemStaticPortMappingTableEntry 1 }

              systemStaticPortMappingMAC OBJECT-TYPE
                  SYNTAX DisplayString(SIZE(0..17))
                  MAX-ACCESS read-write
                  STATUS current
                  DESCRIPTION
                      "Physical Address of the subscriber/device entered in one of the formats:
                      001122334455, 00-11-22-33-44-55 or 00:11:22:33:44:55.
                      Default value is 00:00:00:00:00:00 ."
                  ::= { systemStaticPortMappingTableEntry 2 }

              systemStaticPortMappingInternalIP OBJECT-TYPE
                  SYNTAX IpAddress
                  MAX-ACCESS read-write
                  STATUS current
                  DESCRIPTION
                      "IP Address of the subscriber/device."
                  ::= { systemStaticPortMappingTableEntry 3 }

              systemStaticPortMappingInternalPort OBJECT-TYPE
                  SYNTAX      Integer32(1..65535)
                  MAX-ACCESS  read-write
                  STATUS      current
                  DESCRIPTION
                      "Internal Port (of the subscriber/device)"
                  ::= { systemStaticPortMappingTableEntry 4 }

              systemStaticPortMappingExternalIP OBJECT-TYPE
                  SYNTAX IpAddress
                  MAX-ACCESS read-write
                  STATUS current
                  DESCRIPTION
                      "IP Address of the NSE subscriber side (DAT IP)."
                  ::= { systemStaticPortMappingTableEntry 5 }

              systemStaticPortMappingExternalPort OBJECT-TYPE
              SYNTAX      Integer32(1024..65535)
                  MAX-ACCESS  read-write
                  STATUS      current
                  DESCRIPTION
                      "External Port (of the NSE)"
                  ::= { systemStaticPortMappingTableEntry 6 }

              systemStaticPortMappingRemoteIP OBJECT-TYPE
                  SYNTAX IpAddress
                  MAX-ACCESS read-write
                  STATUS current
                  DESCRIPTION
                      "(OPTIONAL) IP Address of the network side machine."
                  ::= { systemStaticPortMappingTableEntry 7 }

              systemStaticPortMappingRemotePort OBJECT-TYPE
                  SYNTAX      Integer32(0..65535)
                  MAX-ACCESS  read-write
                  STATUS      current
                  DESCRIPTION
                      "(OPTIONAL) Remote Port (of the network side machine)"
                  ::= { systemStaticPortMappingTableEntry 8 }

              systemStaticPortMappingProto OBJECT-TYPE
                  SYNTAX      INTEGER {udp(0), tcp(1) }
                  MAX-ACCESS  read-write
                  STATUS      current
                  DESCRIPTION
                      "Transport Protocol (TCP, UDP)"
                  ::= { systemStaticPortMappingTableEntry 9 }

              systemStaticPortMappingStatus OBJECT-TYPE
                  SYNTAX RowStatus
                  MAX-ACCESS read-write
                  STATUS current
                  DESCRIPTION
                      "Status of the Static Port-mapping table entry."
                  ::= { systemStaticPortMappingTableEntry 10 }



  --
  -- SYSTEM BLOCKING ICMP FOR PENDING SUBSCRIBERS
  --



              blockIcmpFromPending OBJECT-TYPE
              SYNTAX         INTEGER { disabled(0), enabled(1) }
              MAX-ACCESS     read-write
              STATUS         current
              DESCRIPTION
                 "Set to 1 to enable blocking ICMP packets from pending subscribers."
              ::= { system 21 }


  --
  -- TIME
  --

  --
  -- TIME CURRENT DATE AND TIME
  --

              timeCurrentDateAndTime OBJECT-TYPE
              SYNTAX      DisplayString(SIZE(24))
              MAX-ACCESS  read-only
              STATUS      current
              DESCRIPTION
                 "Current date and time."
              ::= { time 1 }

  --
  -- TIME OFFSET SIGN
  --

              timeOffsetSign OBJECT-TYPE
              SYNTAX      INTEGER { plus(0), minus (1) }
              MAX-ACCESS  read-write
              STATUS      current
              DESCRIPTION
                 "Offset sign for time offset (+/- hh:mm) from UTC.
                 Note: you must reboot for changes to take effect."
              ::= { time 2 }

  --
  -- TIME OFFSET HOURS
  --

              timeOffsetHours OBJECT-TYPE
              SYNTAX      Integer32(0..23)
              MAX-ACCESS  read-write
              STATUS      current
              DESCRIPTION
                 "Hours offset for time offset (+/- hh:mm) from UTC.
                 Note: you must reboot for changes to take effect."
              ::= { time 3 }

  --
  -- TIME OFFSET MINUTES
  --

              timeOffsetMinutes OBJECT-TYPE
              SYNTAX      Integer32(0..59)
              MAX-ACCESS  read-write
              STATUS      current
              DESCRIPTION
                 "Minutes offset for time offset (+/- hh:mm) from UTC.
                 Note: you must reboot for changes to take effect."
              ::= { time 4 }

  --
  -- TIME SERVER TIMEOUT
  --

              timeServerTimeout OBJECT-TYPE
              SYNTAX      Integer32(0..200)
              MAX-ACCESS  read-write
              STATUS      current
              DESCRIPTION
                 "Time server timeout in seconds.
                 Note: you must reboot for changes to take effect."
              ::= { time 5 }

  --
  -- TIME SERVER 1
  --

              timeServer1 OBJECT-TYPE
              SYNTAX      DisplayString(SIZE(0..238))
              MAX-ACCESS  read-write
              STATUS      current
              DESCRIPTION
                 "IP address or DNS name of the first time server.
                 Note: you must reboot for changes to take effect."
              ::= { time 6 }

  --
  -- TIME SERVER 2
  --

              timeServer2 OBJECT-TYPE
              SYNTAX      DisplayString(SIZE(0..238))
              MAX-ACCESS  read-write
              STATUS      current
              DESCRIPTION
                 "IP address or DNS name of the second time server.
                 Note: you must reboot for changes to take effect."
              ::= { time 7 }

  --
  -- TIME SERVER 3
  --

              timeServer3 OBJECT-TYPE
              SYNTAX      DisplayString(SIZE(0..238))
              MAX-ACCESS  read-write
              STATUS      current
              DESCRIPTION
                 "IP address or DNS name of the third time server.
                 Note: you must reboot for changes to take effect."
              ::= { time 8 }

  --
  -- TIME SERVER 4
  --

              timeServer4 OBJECT-TYPE
              SYNTAX      DisplayString(SIZE(0..238))
              MAX-ACCESS  read-write
              STATUS      current
              DESCRIPTION
                 "IP address or DNS name of the fourth time server.
                 Note: you must reboot for changes to take effect."
              ::= { time 9 }


--    systemCurrentDateAndTime OBJECT-TYPE
--      SYNTAX          DisplayString(SIZE(20..24))
--      MAX-ACCESS      read-write
--      STATUS          current
--      DESCRIPTION
--        "This object shows and allows setting of the current
--        system date and time.  The format of the string is as
--        follows :
--          DDD MMM dd hh:mm:ss yyyy
--        where
--          DDD  = day of week (3 characters)
--          MMM  = month (3 characters)
--          dd   = date (2 characters)
--          hh   = hour (2 characters, 24 hour clock)
--          mm   = minues (2 characters)
--          ss   = seconds (2 characters)
--          yyyy = year (4 characters)"
--      ::= { system 4 }

  --
  -- URL FILTERING
  --

  --
  -- URL FILTERING ON
  --

              urlFilteringOn OBJECT-TYPE
              SYNTAX      INTEGER { disabled(0), enabled(1) }
              MAX-ACCESS  read-write
              STATUS      current
              DESCRIPTION
                 "Setting this value to (1) will enable URL Filtering feature.
                 Setting this value to (0) will disable it."
              ::= { urlFiltering 1 }

  --
  -- URL FILTERING IP TABLE
  --

              urlFilteringIPTable OBJECT-TYPE
              SYNTAX      SEQUENCE OF UrlFilteringIPTableEntry
              MAX-ACCESS      not-accessible
              STATUS      current
              DESCRIPTION
                 "Table of IP addresses that will be filtered."
              ::= { urlFiltering 2 }

              urlFilteringIPTableEntry OBJECT-TYPE
              SYNTAX      UrlFilteringIPTableEntry
              MAX-ACCESS      not-accessible
              STATUS      current
              DESCRIPTION
                 "URL Filtering IP table entry."
              INDEX       { urlFilteringIPTableIndex }
              ::= { urlFilteringIPTable 1 }

              UrlFilteringIPTableEntry ::= SEQUENCE {
                          urlFilteringIPTableIndex      Integer32,
                          urlFilteringIPTableAddress    IpAddress,
                          urlFilteringIPTableStatus     RowStatus
                       }

              urlFilteringIPTableIndex OBJECT-TYPE
              SYNTAX      Integer32
              MAX-ACCESS  read-only
              STATUS      current
              DESCRIPTION
                 " URL Filtering IP Table Index"
              ::= { urlFilteringIPTableEntry 1 }

              urlFilteringIPTableAddress OBJECT-TYPE
              SYNTAX      IpAddress
              MAX-ACCESS      read-write
              STATUS      current
              DESCRIPTION
                 "IP address traffic to which will be blocked."
              ::= { urlFilteringIPTableEntry 2 }

              urlFilteringIPTableStatus OBJECT-TYPE
              SYNTAX      RowStatus
              MAX-ACCESS      read-write
              STATUS      current
              DESCRIPTION
                 "Status of the urlFilteringIPTable entry."
              ::= { urlFilteringIPTableEntry 3 }

  --
  -- URL FILTERING DNS TABLE
  --

              urlFilteringDNSTable OBJECT-TYPE
              SYNTAX      SEQUENCE OF UrlFilteringDNSTableEntry
              MAX-ACCESS      not-accessible
              STATUS      current
              DESCRIPTION
                 "Table of DNS names or Domain names that will be filtered."
              ::= { urlFiltering 3 }

              urlFilteringDNSTableEntry OBJECT-TYPE
              SYNTAX      UrlFilteringDNSTableEntry
              MAX-ACCESS      not-accessible
              STATUS      current
              DESCRIPTION
                 "URL Filtering DNS table entry."
              INDEX       { urlFilteringDNSTableIndex }
              ::= { urlFilteringDNSTable 1 }

              UrlFilteringDNSTableEntry ::= SEQUENCE {
                          urlFilteringDNSTableIndex     Integer32,
                          urlFilteringDNSTableName      DisplayString,
                          urlFilteringDNSTableStatus    RowStatus
                       }

              urlFilteringDNSTableIndex OBJECT-TYPE
              SYNTAX      Integer32
              MAX-ACCESS  read-only
              STATUS      current
              DESCRIPTION
                 " URL Filtering DNS
                          Table Index"
              ::= { urlFilteringDNSTableEntry 1 }

              urlFilteringDNSTableName OBJECT-TYPE
              SYNTAX      DisplayString(SIZE(0..237))
              MAX-ACCESS      read-write
              STATUS      current
              DESCRIPTION
                 "DNS name or Domain name traffic to which will be blocked."
              ::= { urlFilteringDNSTableEntry 2 }

              urlFilteringDNSTableStatus OBJECT-TYPE
              SYNTAX      RowStatus
              MAX-ACCESS      read-write
              STATUS      current
              DESCRIPTION
                 "Status of the URL Filtering DNS table entry."
              ::= { urlFilteringDNSTableEntry 3 }
  --
  -- MAC Filtering Enable
  --
              macFilteringOn OBJECT-TYPE
              SYNTAX      INTEGER { disabled(0), enabled(1) }
              MAX-ACCESS  read-write
              STATUS      current
              DESCRIPTION
                 "Setting this value to (1) will enable the MAC Filtering feature.
                 Setting this value to (0) will disable it."
              ::= { macFiltering 1 }

  --
  -- MAC FILTERING TABLE
  --

              macFilteringTable OBJECT-TYPE
              SYNTAX      SEQUENCE OF MacFilteringTableEntry
              MAX-ACCESS      not-accessible
              STATUS      current
              DESCRIPTION
                 "Table of MAC addresses that will be filtered."
              ::= { macFiltering 4 }

              macFilteringTableEntry OBJECT-TYPE
              SYNTAX      MacFilteringTableEntry
              MAX-ACCESS      not-accessible
              STATUS      current
              DESCRIPTION
                 "MAC Filtering IP table entry."
              INDEX       { macFilteringTableIndex }
              ::= { macFilteringTable 1 }

              MacFilteringTableEntry ::= SEQUENCE {
                          macFilteringTableIndex      Integer32,
                          macFilteringTableAddress    MacAddress,
                          macFilteringStatus          RowStatus
                       }

              macFilteringTableIndex OBJECT-TYPE
              SYNTAX      Integer32
              MAX-ACCESS  read-only
              STATUS      current
              DESCRIPTION
                 " MAC Filtering Table Index"
              ::= { macFilteringTableEntry 1 }

              macFilteringTableAddress OBJECT-TYPE
              SYNTAX      MacAddress
              MAX-ACCESS      read-write
              STATUS      current
              DESCRIPTION
                 "MAC address traffic to be filtered."
              ::= { macFilteringTableEntry 2 }

              macFilteringStatus OBJECT-TYPE
              SYNTAX      RowStatus
              MAX-ACCESS      read-write
              STATUS      current
              DESCRIPTION
                 "Status of the MAC Filter Table Entry."
              ::= { macFilteringTableEntry 3 }

  --
  -- Tunneling Enable
  --
              tunnelingOn OBJECT-TYPE
              SYNTAX      INTEGER { disabled(0), enabled(1) }
              MAX-ACCESS  read-write
              STATUS      current
              DESCRIPTION
                 "Setting this value to (1) will enable tunneling.
                 Setting this value to (0) will disable it."
              ::= { tunneling 1 }

  --
  -- WIRELESS
  --

  --
  -- WIRELESS SSID
  --

              wirelessSsid OBJECT-TYPE
              SYNTAX       DisplayString(SIZE(0..32))
              MAX-ACCESS   read-write
              STATUS       current
              DESCRIPTION
                 "Default SSID of the AG.
                 Note: you must reboot for changes to take effect."
              ::= { wireless 1 }

  --
  -- WIRELESS SSID BROADCAST ON
  --

              wirelessSsidBroadcastOn OBJECT-TYPE
              SYNTAX      INTEGER { disabled(0), enabled(1) }
              MAX-ACCESS  read-write
              STATUS      current
              DESCRIPTION
                 "Setting this value to (1) will enable Default SSID Broadcast.
                 Setting this value to (0) will disable it.
                 Note: you must reboot for changes to take effect."
              ::= { wireless 2 }

  --
  -- WIRELESS CHANNEL
  --

              wirelessChannel OBJECT-TYPE
              SYNTAX       Integer32(0..14|36|40|44|48|52|56|60|64)
              MAX-ACCESS   read-write
       STATUS    current
       DESCRIPTION
                 "Channel number for the wireless interface.  Setting it to zero
                 will enable auto channel configuration.
                 Note: not all of the channels might be available depending on
                 the regulatory domain and type of wireless interface (b/g or a).
                 Note: you must reboot for changes to take effect."
              ::= { wireless 3 }

  --
  -- WIRELESS RATE
  --

              wirelessRate OBJECT-TYPE
              SYNTAX       INTEGER { auto(0), rate-1Mbits(1), rate-2Mbits(2),
                                   rate-5andhalfMbits(3), rate-6Mbits(4),
                                   rate-9Mbits(5), rate-11Mbits(6), rate-12Mbits(7),
                                   rate-18Mbits(8), rate-24Mbits(9), rate-36Mbits(10),
                                   rate-48Mbits(11), rate-54Mbits(12) }
              MAX-ACCESS   read-write
              STATUS       current
              DESCRIPTION
                 "Data rate for the wireless interface.
                 Note: not all of the rates might be available depending on
                 type of wireless interface (b/g or a).
                 Note: you must reboot for changes to take effect."
              ::= { wireless 4 }

  --
  -- WIRELESS POWER
  --

              wirelessPower OBJECT-TYPE
              SYNTAX       INTEGER { full(0), half(1), quarter(2),
                                     eighth(3), min(4) }
              MAX-ACCESS   read-write
              STATUS       current
              DESCRIPTION
                 "Level of transmit power for the wireless interface.
                 Note: you must reboot for changes to take effect."
              ::= { wireless 5 }

  --
  -- WIRELESS FRAGMENT LENGTH
  --

              wirelessFragLength OBJECT-TYPE
              SYNTAX       Integer32(256..2346)
              MAX-ACCESS   read-write
              STATUS       current
              DESCRIPTION
                 "Fragment length. Note: you must reboot for changes to take effect."
              ::= { wireless 6 }

  --
  -- WIRELESS RTS LENGTH
  --

              wirelessRtsLength OBJECT-TYPE
              SYNTAX       Integer32(256..2346)
              MAX-ACCESS   read-write
              STATUS       current
              DESCRIPTION
                 "RTS length. Note: you must reboot for changes to take effect."
              ::= { wireless 7 }

  --
  -- WIRELESS BEACON INTERVAL
  --

              wirelessBeaconInterval OBJECT-TYPE
              SYNTAX       Integer32(20..1000)
              MAX-ACCESS   read-write
              STATUS       current
              DESCRIPTION
                 "Beacon interval. Note: you must reboot for changes to take effect."
              ::= { wireless 8 }

  --
  -- WIRELESS DTIM
  --

              wirelessDtim OBJECT-TYPE
              SYNTAX       Integer32(1..255)
              MAX-ACCESS   read-write
              STATUS       current
              DESCRIPTION
                 "Delivery Traffic Indication Message (DTIM).
                 Note: you must reboot for changes to take effect."
              ::= { wireless 9 }

  --
  -- WIRELESS SHORT PREAMBLE ON
  --

              wirelessShortPreambleOn OBJECT-TYPE
              SYNTAX      INTEGER { disabled(0), enabled(1) }
              MAX-ACCESS  read-write
              STATUS      current
              DESCRIPTION
                 "Setting this value to (1) will enable short preamble.
                 Setting this value to (0) will disable it.
                 Note: you must reboot for changes to take effect."
              ::= { wireless 10 }

  --
  -- WIRELESS WEP
  --

        wirelessMssid    OBJECT IDENTIFIER ::= { wireless 11 }


  --
  -- WIRELESS MULTIPLE SSID VLAN ON
  --
              wirelessMssidVlanOn OBJECT-TYPE
              SYNTAX      INTEGER { disabled(0), enabled(1) }
              MAX-ACCESS  read-write
              STATUS      current
              DESCRIPTION
                 "Set to 1 to enable, 0 to disable SSID based WAN VLAN.
                 Note: enabling SSID based WAN VLAN will automatically disable
                 RADIUS based WAN VLAN."
              ::= { wirelessMssid 1 }

  --
  -- WIRELESS MULTIPLE SSID 802.1Q DEFAULT TAG ON
  --

              wirelessMssidVlanDefaultOn OBJECT-TYPE
              SYNTAX      INTEGER { disabled(0), enabled(1) }
              MAX-ACCESS  read-write
              STATUS      current
              DESCRIPTION
                 "Set to 1 to enable default 802.1q tag for system traffic, 0 to disable."
              ::= { wirelessMssid 2 }

  --
  -- WIRELESS MULTIPLE SSID 802.1Q DEFAULT TAG
  --

              wirelessMssidVlanDefaultTag OBJECT-TYPE
              SYNTAX      Integer32(1..4094)
              MAX-ACCESS  read-write
              STATUS      current
              DESCRIPTION
                 "Set the default 802.1q tag for system traffic."
              ::= { wirelessMssid 3 }

  --
  -- WIRELESS MULTIPLE SSID TABLE
  --

              wirelessMssidTable OBJECT-TYPE
              SYNTAX      SEQUENCE OF WirelessMssidTableEntry
              MAX-ACCESS  not-accessible
              STATUS      current
              DESCRIPTION
                 "List of multiple SSID settings."
              ::= { wirelessMssid 4 }

              wirelessMssidTableEntry OBJECT-TYPE
              SYNTAX      WirelessMssidTableEntry
              MAX-ACCESS  not-accessible
              STATUS      current
              DESCRIPTION
                 "SSID entry."
              INDEX  { mssidIndex }
              ::= { wirelessMssidTable 1 }

              WirelessMssidTableEntry ::= SEQUENCE {
                            mssidIndex      Integer32,
                            mssidName    DisplayString,
                            mssidVlan    Integer32,
                            mssidStatus  RowStatus
              }

              mssidIndex OBJECT-TYPE
              SYNTAX     Integer32
              MAX-ACCESS read-only
              STATUS     current
              DESCRIPTION
                 "SSID index."
              ::= { wirelessMssidTableEntry 1 }

              mssidName OBJECT-TYPE
              SYNTAX     DisplayString(SIZE(0..32))
              MAX-ACCESS read-write
              STATUS     current
              DESCRIPTION
                 "SSID name.
                 Note: you must reboot for changes to take effect."
              ::= { wirelessMssidTableEntry 2 }

              mssidVlan OBJECT-TYPE
         SYNTAX     Integer32(1..4094)
         MAX-ACCESS read-write
         STATUS     current
         DESCRIPTION
                 "SSID VLAN.
                 Note: you must reboot for changes to take effect."
              ::= { wirelessMssidTableEntry 3 }

              mssidStatus OBJECT-TYPE
              SYNTAX     RowStatus
              MAX-ACCESS read-write
              STATUS     current
              DESCRIPTION
                 "Status of the Multiple SSID table entry."
              ::= { wirelessMssidTableEntry 4 }

  --
  -- WIRELESS WEP
  --

        wirelessWep    OBJECT IDENTIFIER ::= { wireless 12 }

  --
  -- WIRELESS WEP ON
  --

              wirelessWepOn OBJECT-TYPE
              SYNTAX      INTEGER { disabled(0), enabled(1) }
              MAX-ACCESS  read-write
              STATUS      current
              DESCRIPTION
                 "Setting this value to (1) will enable WEP.
                 Setting this value to (0) will disable it.
                 Note: you must reboot for changes to take effect."
              ::= { wirelessWep 1 }

  --
  -- WIRELESS WEP ALLOW UNENCRYPTED TRAFFIC
  --
--               wirelessWepAllowUnencrypted OBJECT-TYPE
--               SYNTAX      INTEGER { disabled(0), enabled(1) }
--               MAX-ACCESS  read-write
--               STATUS      current
--               DESCRIPTION
--                  "Setting this value to (1) will allow
--                  unencrypted traffic to be accepted, processed,
--                  and passed through. Setting it to (0) will disable
--                  such behavior.  Note: you must reboot for changes to take effect."
--               ::= { wirelessWep 2 }

  --
  -- WIRELESS WEP CLIENTS
  --

              wirelessWepClients OBJECT-TYPE
              SYNTAX      DisplayString(SIZE(6..21))
              MAX-ACCESS  read-only
              STATUS      current
              DESCRIPTION
                 "Type of clients supported by AG."
              ::= { wirelessWep 3 }

  --
  -- WIRELESS WEP AUTH TYPE
  --

              wirelessWepAuthType OBJECT-TYPE
              SYNTAX      INTEGER { open(0), shared(1) }
              MAX-ACCESS  read-write
              STATUS      current
              DESCRIPTION
                 "Setting this value to (0) will set 802.11 authentication type
                 to open.  Setting this value to (1) will set it to shared.
                 Note: you must reboot for changes to take effect."
              ::= { wirelessWep 4 }

  --
  -- WIRELESS WEP NON1X ALLOWED ON
  --

              wirelessWepNon1xAllowedOn OBJECT-TYPE
              SYNTAX      INTEGER { disabled(0), enabled(1) }
              MAX-ACCESS  read-write
              STATUS      current
              DESCRIPTION
                 "Setting this value to (1) will allow access for non-802.1x
                 clients.  Setting this value to (0) will disallow it.
                 Note: you must reboot for changes to take effect."
              ::= { wirelessWep 5 }

  --
  -- WIRELESS WEP KEY TYPE
  --

              wirelessWepKeyType OBJECT-TYPE
              SYNTAX      INTEGER { hex(0), ascii(1) }
              MAX-ACCESS  read-write
              STATUS      current
              DESCRIPTION
                 "Type of the WEP key: Hexadecimal digits or ASCII characters.
                 Note: you must reboot for changes to take effect."
              ::= { wirelessWep 6 }

  --
  -- WIRELESS WEP DEFAULT KEY
  --

              wirelessWepDefaultKey OBJECT-TYPE
              SYNTAX       INTEGER { key-1(1), key-2(2), key-3(3), key-4(4) }
              MAX-ACCESS   read-write
              STATUS       current
              DESCRIPTION
                 "Default WEP Key. Index of a WEP key which will be used to
                 encrypt all transmitted and received frames for the stations
                 which do not have a private key associated with them.
                 Note: you must reboot for changes to take effect."
              ::= { wirelessWep 7 }

  --
  -- WIRELESS WEP KEY 1
  --

              wirelessWepKey1 OBJECT-TYPE
              SYNTAX       DisplayString(SIZE(0..32))
              MAX-ACCESS   read-write
              STATUS       current
              DESCRIPTION
                 "WEP Key 1. Note: make sure that key length is correct
                 depending on the key type:
                    Ascii  64-bit key -  5 characters long
                    Ascii 128-bit key - 13 characters long
                    Ascii 152-bit key - 16 characters long
                    Hex    64-bit key - 10 hex digits long
                    Hex   128-bit key - 26 hex digits long
                    Hex   152-bit key - 32 hex digits long
                 Note: you must reboot for changes to take effect."
              ::= { wirelessWep 8 }

  --
  -- WIRELESS WEP KEY 2
  --

              wirelessWepKey2 OBJECT-TYPE
              SYNTAX       DisplayString(SIZE(0..32))
              MAX-ACCESS   read-write
              STATUS       current
              DESCRIPTION
                 "WEP Key 2. Note: make sure that key length is correct
                 depending on the key type:
                    Ascii  64-bit key -  5 characters long
                    Ascii 128-bit key - 13 characters long
                    Ascii 152-bit key - 16 characters long
                    Hex    64-bit key - 10 hex digits long
                    Hex   128-bit key - 26 hex digits long
                    Hex   152-bit key - 32 hex digits long
                 Note: you must reboot for changes to take effect."
              ::= { wirelessWep 9 }

  --
  -- WIRELESS WEP KEY 3
  --

              wirelessWepKey3 OBJECT-TYPE
              SYNTAX       DisplayString(SIZE(0..32))
              MAX-ACCESS   read-write
              STATUS       current
              DESCRIPTION
                 "WEP Key 3. Note: make sure that key length is correct
                 depending on the key type:
                    Ascii  64-bit key -  5 characters long
                    Ascii 128-bit key - 13 characters long
                    Ascii 152-bit key - 16 characters long
                    Hex    64-bit key - 10 hex digits long
                    Hex   128-bit key - 26 hex digits long
                    Hex   152-bit key - 32 hex digits long
                 Note: you must reboot for changes to take effect."
              ::= { wirelessWep 10 }

  --
  -- WIRELESS WEP KEY 4
  --

              wirelessWepKey4 OBJECT-TYPE
              SYNTAX       DisplayString(SIZE(0..32))
              MAX-ACCESS   read-write
              STATUS       current
              DESCRIPTION
                 "WEP Key 4. Note: make sure that key length is correct
                 depending on the key type:
                    Ascii  64-bit key -  5 characters long
                    Ascii 128-bit key - 13 characters long
                    Ascii 152-bit key - 16 characters long
                    Hex    64-bit key - 10 hex digits long
                    Hex   128-bit key - 26 hex digits long
                    Hex   152-bit key - 32 hex digits long
                 Note: you must reboot for changes to take effect."
              ::= { wirelessWep 11 }


  --
  -- NOTIFICATIONS
  --
     failedLogin NOTIFICATION-TYPE
       STATUS      current
       DESCRIPTION
         "Failed Login attempt"
       ::= { ndxTraps 8 }

     subCapacityReached NOTIFICATION-TYPE
       STATUS      current
       DESCRIPTION
         "Subscriber Capacity Reached"
       ::= { ndxTraps 9 }

     nseReboot NOTIFICATION-TYPE
       STATUS      current
       DESCRIPTION
         "The unit has rebooted"
       ::= { ndxTraps 10 }

     nseRadCapacityReached NOTIFICATION-TYPE
       STATUS      current
       DESCRIPTION
        "This trap is generated when the limit of Radius caching file is reached."
       ::= { ndxTraps 15 }


  --
  -- PPPoE CLIENT
  --

  --
  -- PPPoE Servicename
  --

              pppoeSvcName OBJECT-TYPE
              SYNTAX       DisplayString(SIZE(0..32))
              MAX-ACCESS   read-write
              STATUS       current
              DESCRIPTION
                 "Servicename that will be requested of the PPPoE client. Blank
                  means any service is acceptable."
              ::= { pppoeClient 1 }

  --
  -- PPP Echo Request Interval
  --

              pppEchoReqIntvl OBJECT-TYPE
              SYNTAX       Integer32
              MAX-ACCESS   read-write
              STATUS       current
              DESCRIPTION
                 "Frequency in seconds that LCP echo requests will be sent to the server."
              ::= { pppoeClient 2 }

  --
  -- PPP Echo Request Maximum non-responses
  --

              pppEchoMaxNonresp OBJECT-TYPE
              SYNTAX       Integer32
              MAX-ACCESS   read-write
              STATUS       current
              DESCRIPTION
                 "Maximum number of echo requests that can go unresponded to before
                  the PPP link is considered to be down."
              ::= { pppoeClient 3 }

  --
  -- PPP AUTHENTICATION USERNAME
  --

              pppAuthUsername OBJECT-TYPE
              SYNTAX       DisplayString(SIZE(0..128))
              MAX-ACCESS   read-write
              STATUS       current
              DESCRIPTION
                 "Username to be used during authentication phase of establishing PPP link.
                  Used for PAP or CHAP."
              ::= { pppoeClient 4 }

  --
  -- PPP AUTHENTICATION PASSWORD
  --

              pppAuthPassword OBJECT-TYPE
              SYNTAX       DisplayString(SIZE(0..128))
              MAX-ACCESS   read-write
              STATUS       current
              DESCRIPTION
                 "Password/Secret to be used during authentication phase of establishing PPP
                  link. Used for PAP or CHAP."
              ::= { pppoeClient 5 }

  --
  -- PPP IP ADDRESS CONFIGURATION MODE
  --

              pppIpCfgMode OBJECT-TYPE
              SYNTAX      INTEGER { dynamic(0), static(1) }
              MAX-ACCESS   read-write
              STATUS       current
              DESCRIPTION
                 "Decides whether to request an IP address from the server (dynamic)
                  or inform the server of the desired IP address (static)"
              ::= { pppoeClient 6 }

  --
  -- PPP STATIC IP ADDRESS
  --

              pppStaticIpAddr OBJECT-TYPE
               SYNTAX      IpAddress
              MAX-ACCESS   read-write
              STATUS       current
              DESCRIPTION
                 "If pppIpCfgMode is set to static, this is the IP address that will
                  be used."
              ::= { pppoeClient 7 }

  --
  -- PPP Maximum TCP MSS
  --

     pppMaxTcpMss OBJECT-TYPE
       SYNTAX       Integer32
       MAX-ACCESS   read-write
       STATUS       current
       DESCRIPTION
         "Specifies the maximum TCP MSS option value to use for subscriber TCP connections
          across the PPP network interface. The actual value used may be less than
          the configured value if necessary based on the MTU of the PPP interface.
          Values above 1952 are not allowed."
       ::= { pppoeClient 8 }

--
-- LOCAL WEB PAGES TABLE
--
     localWebPages    OBJECT IDENTIFIER ::= { localWeb 4 }
     localWebImages   OBJECT IDENTIFIER ::= { localWeb 8 }

     localWebPagesTable OBJECT-TYPE
       SYNTAX      SEQUENCE OF LocalWebPagesTableEntry
       MAX-ACCESS      not-accessible
       STATUS      current
       DESCRIPTION
         "Table of local Web page names."
       ::= { localWebPages 1 }

     localWebPagesTableEntry OBJECT-TYPE
       SYNTAX      LocalWebPagesTableEntry
       MAX-ACCESS  not-accessible
       STATUS      current
       DESCRIPTION
         "Local Web Pages table entry."
       INDEX       { localWebPagesTableIndex }
       ::= { localWebPagesTable 1 }

     LocalWebPagesTableEntry ::= SEQUENCE {
              localWebPagesTableIndex     Integer32,
              localWebPagesTableName      DisplayString,
              localWebPagesTableStatus    RowStatus
              }

     localWebPagesTableIndex OBJECT-TYPE
       SYNTAX      Integer32
       MAX-ACCESS  read-only
       STATUS      current
       DESCRIPTION
        " Local Web Pages Table Index."
       ::= { localWebPagesTableEntry 1 }

     localWebPagesTableName OBJECT-TYPE
       SYNTAX      DisplayString(SIZE(0..237))
       MAX-ACCESS      read-write
       STATUS      current
       DESCRIPTION
         "Local Web Pages entries."
       ::= { localWebPagesTableEntry 2 }

     localWebPagesTableStatus OBJECT-TYPE
       SYNTAX      RowStatus
       MAX-ACCESS      read-write
       STATUS      current
       DESCRIPTION
         "Status of the Local Web pages table entry."
       ::= { localWebPagesTableEntry 3 }

--
-- LOCAL WEB IMAGES TABLE
--
     localWebImagesTable OBJECT-TYPE
       SYNTAX      SEQUENCE OF LocalWebImagesTableEntry
       MAX-ACCESS      not-accessible
       STATUS      current
       DESCRIPTION
         "Table of local Web image names."
       ::= { localWebImages 1 }

     localWebImagesTableEntry OBJECT-TYPE
       SYNTAX      LocalWebImagesTableEntry
       MAX-ACCESS      not-accessible
       STATUS      current
       DESCRIPTION
         "Local Web Images table entry."
       INDEX       { localWebImagesTableIndex }
       ::= { localWebImagesTable 1 }

     LocalWebImagesTableEntry ::= SEQUENCE {
           localWebImagesTableIndex     Integer32,
           localWebImagesTableName      DisplayString,
           localWebImagesTableStatus    RowStatus
           }

     localWebImagesTableIndex OBJECT-TYPE
       SYNTAX      Integer32
       MAX-ACCESS  read-only
       STATUS      current
       DESCRIPTION
         " Local Web Images Index"
       ::= { localWebImagesTableEntry 1 }

     localWebImagesTableName OBJECT-TYPE
       SYNTAX      DisplayString(SIZE(0..237))
       MAX-ACCESS      read-write
       STATUS      current
       DESCRIPTION
         "Local Web Image entries."
       ::= { localWebImagesTableEntry 2 }

     localWebImagesTableStatus OBJECT-TYPE
       SYNTAX      RowStatus
       MAX-ACCESS      read-write
       STATUS      current
       DESCRIPTION
         "Status of local Web images table entry."
       ::= { localWebImagesTableEntry 3 }
--
--   IPSec
--

   ipsecVpnOn     OBJECT-TYPE
     SYNTAX         INTEGER { disabled(0), enabled(1) }
     MAX-ACCESS     read-write
     STATUS         current
     DESCRIPTION
       " Setting this value to (1) enables IPSec over the network interface.
         Setting it to zero disables it. Valid license is required. When this variable
         is changed, system must be rebooted for the change to take effect. (NOTE: This
         is not to be confused with the MIB variable ipsecOn, which pertains to the
         passthru of IPSec traffic to/from a subscriber host.)"
     ::= { ipsec 1 }

   ipsecPeers    OBJECT IDENTIFIER ::= { ipsec 4 }
   ipsecPolicies    OBJECT IDENTIFIER ::= { ipsec 5 }
   ipsecSaStatus    OBJECT IDENTIFIER ::= { ipsec 6 }

--
-- IPSec PEER TABLE
--
     ipsecPeerTable OBJECT-TYPE
       SYNTAX      SEQUENCE OF IpsecPeerTableEntry
       MAX-ACCESS  not-accessible
       STATUS  current
       DESCRIPTION
          "List of IPSec peers."
       ::= { ipsecPeers 1 }

     ipsecPeerTableEntry OBJECT-TYPE
       SYNTAX      IpsecPeerTableEntry
       MAX-ACCESS  not-accessible
       STATUS  current
       DESCRIPTION
          "Parameters for a specific IPSec peer."
       INDEX  { ipsecPeerIndex }
       ::= { ipsecPeerTable 1 }


     IpsecPeerTableEntry ::=
       SEQUENCE
       {
        ipsecPeerIndex Integer32,
        ipsecPeerIpAddr   IpAddress,
        ipsecPeerAuthMethod    INTEGER,
        ipsecPeerSharedKey     DisplayString,
        ipsecPeerPrivkeyFile   DisplayString,
        ipsecPeerCertFile      DisplayString,
        ipsecPeerEncDesOk INTEGER,
        ipsecPeerEnc3DesOk INTEGER,
        ipsecPeerHashMd5Ok INTEGER,
        ipsecPeerHashShaOk INTEGER,
        ipsecPeerKeyStrength INTEGER,
        ipsecPeerLifetime Integer32,
        ipsecPeerStatus        RowStatus
       }

     ipsecPeerIndex OBJECT-TYPE
       SYNTAX     Integer32
       MAX-ACCESS  read-only
       STATUS     current
       DESCRIPTION
          "IPSec Peer Index"
       ::= { ipsecPeerTableEntry 1 }

     ipsecPeerIpAddr OBJECT-TYPE
       SYNTAX      IpAddress
       MAX-ACCESS  read-write
       STATUS  current
       DESCRIPTION
          "IP Address of the IPSec peer."
       ::= { ipsecPeerTableEntry 2 }

     ipsecPeerAuthMethod   OBJECT-TYPE
       SYNTAX       INTEGER { preSharedKey(0), x509Certificate(1) }
       MAX-ACCESS       read-write
       STATUS       current
       DESCRIPTION
          "Method to be used to authenticate and be authenticated by IPSec peer"
       ::= { ipsecPeerTableEntry 3 }

     ipsecPeerSharedKey   OBJECT-TYPE
       SYNTAX       DisplayString(SIZE(1..128))
       MAX-ACCESS       read-write
       STATUS       current
       DESCRIPTION
          "The key to be used if ipsecPeerAuthMethod is preSharedKey."
       ::= { ipsecPeerTableEntry 4 }

     ipsecPeerPrivkeyFile   OBJECT-TYPE
       SYNTAX       DisplayString(SIZE(1..20))
       MAX-ACCESS       read-write
       STATUS       current
       DESCRIPTION
          "The filename (within the /flash/ipseccrt directory) of the file containing
           the private key to be used for X509 authentication. Only needed if
           ipsecPeerAuthMethod is x509Certificate"
      ::= { ipsecPeerTableEntry 5 }

     ipsecPeerCertFile   OBJECT-TYPE
       SYNTAX       DisplayString(SIZE(1..20))
       MAX-ACCESS       read-write
       STATUS       current
       DESCRIPTION
          "The filename (within the /flash/ipseccrt directory) of the file containing
           the X.509 certificate to be used for X509 authentication. Only needed if
           ipsecPeerAuthMethod is x509Certificate"
      ::= { ipsecPeerTableEntry 6 }

     ipsecPeerEncDesOk   OBJECT-TYPE
       SYNTAX       INTEGER { notAllowed(0), allowed(1) }
       MAX-ACCESS       read-write
       STATUS       current
       DESCRIPTION
          "Indicates whether DES encryption is allowed to be used on the IKE channel
          between the NSE and this peer."
       ::= { ipsecPeerTableEntry 7 }

     ipsecPeerEnc3DesOk   OBJECT-TYPE
       SYNTAX       INTEGER { notAllowed(0), allowed(1) }
       MAX-ACCESS       read-write
       STATUS       current
       DESCRIPTION
          "Indicates whether 3DES encryption is allowed to be used on the IKE channel
          between the NSE and this peer."
       ::= { ipsecPeerTableEntry 8 }

     ipsecPeerHashMd5Ok   OBJECT-TYPE
       SYNTAX       INTEGER { notAllowed(0), allowed(1) }
       MAX-ACCESS       read-write
       STATUS       current
       DESCRIPTION
          "Indicates whether MD5 hashing is allowed to be used on the IKE channel
          between the NSE and this peer."
       ::= { ipsecPeerTableEntry 9 }

     ipsecPeerHashShaOk   OBJECT-TYPE
       SYNTAX       INTEGER { notAllowed(0), allowed(1) }
       MAX-ACCESS       read-write
       STATUS       current
       DESCRIPTION
          "Indicates whether SHA hashing is allowed to be used on the IKE channel
          between the NSE and this peer."
       ::= { ipsecPeerTableEntry 10 }

     ipsecPeerKeyStrength   OBJECT-TYPE
       SYNTAX       INTEGER { key768-bit(0), key1024-bit(1) }
       MAX-ACCESS       read-write
       STATUS       current
       DESCRIPTION
          "The key strength to be used on the IKE channel between the NSE and this peer"
       ::= { ipsecPeerTableEntry 11 }

     ipsecPeerLifetime OBJECT-TYPE
       SYNTAX     Integer32
       MAX-ACCESS  read-write
       STATUS     current
       DESCRIPTION
          "The lifetime (in seconds) of the IKE channel between the NSE and this peer,
          before it needs to be torn down and re-established."
       ::= { ipsecPeerTableEntry 12 }

     ipsecPeerStatus   OBJECT-TYPE
       SYNTAX       RowStatus
       MAX-ACCESS       read-write
       STATUS       current
       DESCRIPTION
          "Status of the IPSec peer table entry."
       ::= { ipsecPeerTableEntry 20}

--
-- IPSec POLICY TABLE
--
     ipsecPolicyTable OBJECT-TYPE
       SYNTAX      SEQUENCE OF IpsecPolicyTableEntry
       MAX-ACCESS  not-accessible
       STATUS  current
       DESCRIPTION
          "List of IPSec security policies."
       ::= { ipsecPolicies 1 }

     ipsecPolicyTableEntry OBJECT-TYPE
       SYNTAX      IpsecPolicyTableEntry
       MAX-ACCESS  not-accessible
       STATUS  current
       DESCRIPTION
          "Parameters for a specific IPSec security policy."
       INDEX  { ipsecPolicyIndex }
       ::= { ipsecPolicyTable 1 }


     IpsecPolicyTableEntry ::=
       SEQUENCE
       {
        ipsecPolicyIndex Integer32,
        ipsecPolicyPeerIp IpAddress,
        ipsecPolicyProtocol INTEGER,
        ipsecPolicyRemIp IpAddress,
        ipsecPolicyRemSubnet IpAddress,
        ipsecPolicyRemPort INTEGER,
        ipsecPolicyUseNetIp INTEGER,
        ipsecPolicyLocIp IpAddress,
        ipsecPolicyLocSubnet IpAddress,
        ipsecPolicyLocPort INTEGER,
        ipsecPolicyType INTEGER,
        ipsecPolicyDirType INTEGER,
        ipsecPolicyEncDesOk INTEGER,
        ipsecPolicyEnc3desOk INTEGER,
        ipsecPolicyEncNullOk INTEGER,
        ipsecPolicyAuthMd5Ok INTEGER,
        ipsecPolicyAuthShaOk INTEGER,
        ipsecPolicyAuthNullOk INTEGER,
        ipsecPolicyPfsStrength INTEGER,
        ipsecPolicyMaxLifetime Integer32,
        ipsecPolicyMaxLifesize Integer32,
        ipsecPolicyAutoRenew INTEGER,
        ipsecPolicyStatus      RowStatus
       }

     ipsecPolicyIndex OBJECT-TYPE
       SYNTAX     Integer32
       MAX-ACCESS  read-only
       STATUS     current
       DESCRIPTION
          "IPSec Policy Index"
       ::= { ipsecPolicyTableEntry 1 }

     ipsecPolicyPeerIp OBJECT-TYPE
       SYNTAX      IpAddress
       MAX-ACCESS  read-write
       STATUS  current
       DESCRIPTION
          "IP Address of the IPSec peer for this policy. There must be an entry in
          the peer table for this peer"
       ::= { ipsecPolicyTableEntry 2 }

     ipsecPolicyProtocol   OBJECT-TYPE
       SYNTAX       INTEGER
       MAX-ACCESS       read-write
       STATUS       current
       DESCRIPTION
          "The IP protocol number (e.g. 6 for TCP) of the protocol this policy pertains
          to. a zero means it pertains to ANY protocol."
       ::= { ipsecPolicyTableEntry 3 }

     ipsecPolicyRemIp OBJECT-TYPE
       SYNTAX      IpAddress
       MAX-ACCESS  read-write
       STATUS  current
       DESCRIPTION
          "IP Address of the remote host/subnet to which this policy pertains."
       ::= { ipsecPolicyTableEntry 4 }

     ipsecPolicyRemSubnet OBJECT-TYPE
       SYNTAX      IpAddress
       MAX-ACCESS  read-write
       STATUS  current
       DESCRIPTION
          "Subnet mask of the remote subnet to which this policy pertains."
       ::= { ipsecPolicyTableEntry 5 }

     ipsecPolicyRemPort   OBJECT-TYPE
       SYNTAX       INTEGER
       MAX-ACCESS       read-write
       STATUS       current
       DESCRIPTION
          "The remote TCP/UDP port number to which this policy pertains. A zero means
          it pertains to ANY port number. This field is only used if the protocol
          number is 6 (TCP) or 17 (UDP)."
       ::= { ipsecPolicyTableEntry 6 }

     ipsecPolicyUseNetIp   OBJECT-TYPE
       SYNTAX       INTEGER { no(0), yes(1) }
       MAX-ACCESS       read-write
       STATUS       current
       DESCRIPTION
          "Indicates whether or not this policy pertains to traffic originated by
          and/or destined to the NSE's network interface IP address. Otherwise it
          would pertain to a device on the subscriber network."
       ::= { ipsecPolicyTableEntry 7 }

     ipsecPolicyLocIp OBJECT-TYPE
       SYNTAX      IpAddress
       MAX-ACCESS  read-write
       STATUS  current
       DESCRIPTION
          "If ipsecPolicyUseNetIp is no, this is the IP Address of the subscriber-side
          host/subnet to which this policy pertains."
       ::= { ipsecPolicyTableEntry 8 }

     ipsecPolicyLocSubnet OBJECT-TYPE
       SYNTAX      IpAddress
       MAX-ACCESS  read-write
       STATUS  current
       DESCRIPTION
          "If ipsecPolicyUseNetIp is no, this is the Subnet mask of the subscriber-side
          subnet to which this policy pertains."
       ::= { ipsecPolicyTableEntry 9 }

     ipsecPolicyLocPort   OBJECT-TYPE
       SYNTAX       INTEGER
       MAX-ACCESS       read-write
       STATUS       current
       DESCRIPTION
          "The local TCP/UDP port number to which this policy pertains. A zero means
          it pertains to ANY port number. This field is only used if the protocol
          number is 6 (TCP) or 17 (UDP)."
       ::= { ipsecPolicyTableEntry 10 }

     ipsecPolicyType   OBJECT-TYPE
       SYNTAX       INTEGER { discard(0), bypass(1), esp(2), ah(3) }
       MAX-ACCESS       read-write
       STATUS       current
       DESCRIPTION
          "The type of IPSec security policy this is, i.e., what type of action to take
          on packets that fit the traffic selectors."
       ::= { ipsecPolicyTableEntry 11 }

     ipsecPolicyDirType   OBJECT-TYPE
       SYNTAX       INTEGER { inOnly(0), outOnly(1), inAndOut(2) }
       MAX-ACCESS       read-write
       STATUS       current
       DESCRIPTION
          "The traffic direction to which this policy pertains. Used only for discard or
          bypass policies (ESP and AH tunnels always pertain to both directions)"
       ::= { ipsecPolicyTableEntry 12 }

     ipsecPolicyEncDesOk   OBJECT-TYPE
       SYNTAX       INTEGER { notAllowed(0), allowed(1) }
       MAX-ACCESS       read-write
       STATUS       current
       DESCRIPTION
          "Indicates whether DES encryption is allowed to be used on the security
          association based on this policy. Pertains only to ESP tunnels."
       ::= { ipsecPolicyTableEntry 13 }

     ipsecPolicyEnc3desOk   OBJECT-TYPE
       SYNTAX       INTEGER { notAllowed(0), allowed(1) }
       MAX-ACCESS       read-write
       STATUS       current
       DESCRIPTION
          "Indicates whether 3DES encryption is allowed to be used on the security
          association based on this policy. Pertains only to ESP tunnels."
       ::= { ipsecPolicyTableEntry 14 }

     ipsecPolicyEncNullOk   OBJECT-TYPE
       SYNTAX       INTEGER { notAllowed(0), allowed(1) }
       MAX-ACCESS       read-write
       STATUS       current
       DESCRIPTION
          "Indicates whether NULL encryption (i.e., not encrypted) is allowed to be used on
          the security association based on this policy. Pertains only to ESP tunnels."
       ::= { ipsecPolicyTableEntry 15 }

     ipsecPolicyAuthMd5Ok   OBJECT-TYPE
       SYNTAX       INTEGER { notAllowed(0), allowed(1) }
       MAX-ACCESS       read-write
       STATUS       current
       DESCRIPTION
          "Indicates whether MD5 authentication is allowed to be used on the security
          association based on this policy. Pertains to both ESP and AH tunnels."
       ::= { ipsecPolicyTableEntry 16 }

     ipsecPolicyAuthShaOk   OBJECT-TYPE
       SYNTAX       INTEGER { notAllowed(0), allowed(1) }
       MAX-ACCESS       read-write
       STATUS       current
       DESCRIPTION
          "Indicates whether SHA authentication is allowed to be used on the security
          association based on this policy. Pertains to both ESP and AH tunnels."
       ::= { ipsecPolicyTableEntry 17 }

     ipsecPolicyAuthNullOk   OBJECT-TYPE
       SYNTAX       INTEGER { notAllowed(0), allowed(1) }
       MAX-ACCESS       read-write
       STATUS       current
       DESCRIPTION
          "Indicates whether no authentication is allowed to be used on the security
          association based on this policy. Pertains only to ESP tunnels."
       ::= { ipsecPolicyTableEntry 18 }

     ipsecPolicyPfsStrength   OBJECT-TYPE
       SYNTAX       INTEGER { pfsNone(0), pfs768(1), pfs1024(2) }
       MAX-ACCESS       read-write
       STATUS       current
       DESCRIPTION
          "Indicates whether perfect forward secrecy is to be used on the security
          association based on this policy, and if so what lever of keying strength to
          use. Pertains to either ESP or AH tunnels."
       ::= { ipsecPolicyTableEntry 19 }

     ipsecPolicyMaxLifetime   OBJECT-TYPE
       SYNTAX       Integer32
       MAX-ACCESS   read-write
       STATUS       current
       DESCRIPTION
          "The maximum lifetime (in seconds) a security association based on this policy
          may stay up before it must either be torn down or renewed. A zero means there
          is no maximum."
       ::= { ipsecPolicyTableEntry 20 }

     ipsecPolicyMaxLifesize   OBJECT-TYPE
       SYNTAX       Integer32
       MAX-ACCESS   read-write
       STATUS       current
       DESCRIPTION
          "The maximum amount of data (in bytes) that may pass thru a tunnel based
          on this policy before it must either be torn down or renewed. A zero means
          there is no maximum."
       ::= { ipsecPolicyTableEntry 21 }

     ipsecPolicyAutoRenew   OBJECT-TYPE
       SYNTAX       INTEGER { no(0), yes(1) }
       MAX-ACCESS   read-write
       STATUS       current
       DESCRIPTION
          "Indicates whether the security association based on this policy should be
          automatically renewed or not. Used only if either ipsecPolicyMaxLifesize or
          ipsecPolicyMaxLifetime is non-zero."
       ::= { ipsecPolicyTableEntry 22 }

     ipsecPolicyStatus   OBJECT-TYPE
       SYNTAX       RowStatus
       MAX-ACCESS       read-write
       STATUS       current
       DESCRIPTION
          "Status of the IPSec policy table entry."
       ::= { ipsecPolicyTableEntry 40}


--
-- IPSec Security Association STATUS TABLE
--
     ipsecSaStatusTable OBJECT-TYPE
       SYNTAX      SEQUENCE OF IpsecSaStatusTableEntry
       MAX-ACCESS  not-accessible
       STATUS  current
       DESCRIPTION
          "List of the status of security associations  corresponding to
          configured IPSec security policies."
       ::= { ipsecSaStatus 1 }

     ipsecSaStatusTableEntry OBJECT-TYPE
       SYNTAX      IpsecSaStatusTableEntry
       MAX-ACCESS  not-accessible
       STATUS  current
       DESCRIPTION
          "Information about the status of an IPSec security association."
       INDEX  { ipsecSaStatusIndex }
       ::= { ipsecSaStatusTable 1 }


     IpsecSaStatusTableEntry ::=
       SEQUENCE
       {
        ipsecSaStatusIndex Integer32,
        ipsecSaStatusState      INTEGER,
        ipsecSaStatusStatus     RowStatus
       }

     ipsecSaStatusIndex OBJECT-TYPE
       SYNTAX     Integer32
       MAX-ACCESS  read-only
       STATUS     current
       DESCRIPTION
          "IPSec Security Association Status Index"
       ::= { ipsecSaStatusTableEntry 1 }

     ipsecSaStatusState   OBJECT-TYPE
       SYNTAX       INTEGER { ipsecUp(0), ipsecDisabled(1), notConfiguredInStack(2),
        noIkeChannelToPeer(3),notNegotiatedWithPeer(4) }
       MAX-ACCESS       read-only
       STATUS       current
       DESCRIPTION
          "Indicates the state ofwhether the security association corresponding to the configured
          security policy is presently up or down."
       ::= { ipsecSaStatusTableEntry 2 }

     ipsecSaStatusStatus   OBJECT-TYPE
       SYNTAX       RowStatus
       MAX-ACCESS       read-write
       STATUS       current
       DESCRIPTION
          "Status of the IPSec security association table entry."
       ::= { ipsecSaStatusTableEntry 20}



END
