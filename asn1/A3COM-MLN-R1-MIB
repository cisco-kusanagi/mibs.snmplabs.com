A3COM-MLN-R1-MIB DEFINITIONS ::= BEGIN

	IMPORTS
	  enterprises
		FROM RFC1155-SMI
	  PhysAddress, DisplayString
		FROM RFC1213-MIB
	  OBJECT-TYPE
		FROM RFC-1212;

	--
	-- This MIB is for Logical Networks (MLN) support.
	--

	a3Com		OBJECT IDENTIFIER ::= { enterprises 43 }
	brouterMIB	OBJECT IDENTIFIER ::= { a3Com 2 }
	a3ComMLN	OBJECT IDENTIFIER ::= { brouterMIB 23 }

	a3mlnStatistics OBJECT IDENTIFIER ::= { a3ComMLN 10 }

	RowStatus ::= INTEGER {
		active(1),
		notInService(2),
		notReady(3),
		createAndGo(4),
		createAndWait(5),
		destroy(6)
	}

	-- This data type, which has the same semantics as the rowStatus
	-- textual convention used in SNMPv2, is used to add and
	-- delete entries from a table.
	-- The tables in this MIB allow a subset of the functionality
	-- provided by the rowStatus textual convention.  In particular
	-- row creation is allowed using only the createAndGo method.

	-- That is, when adding entries to this table, this object
	-- must be set to createAndGo(4).  The instance identifier
	-- for this object will define the values of the columns
	-- that make up the index.

	-- In the same PDU, the appropriate remaining columns
	-- of that row must be set as well.  The agent
	-- will immediately set the value of this object to
	-- active(1) if the row is correct.  If not, the agent
	-- will refuse the SET request and return an
	-- error code.

	-- To modify an existing entry, it must be removed
	-- and another entry with the desired changes added.
	-- To remove an entry, set the value of this object
	-- to destroy(6).
	--

	--
	-- Globals - Agent's implementation
	--

        a3mlnMaxPorts OBJECT-TYPE
            SYNTAX  INTEGER
            ACCESS  read-only
            STATUS  mandatory
            DESCRIPTION
                "The maximum number of virtual and physical ports supported
		 by the agent. This value should be used to verify correct
		 port values."
            ::= { a3ComMLN 1 }

        a3mlnMaxPhyPorts OBJECT-TYPE
            SYNTAX  INTEGER
            ACCESS  read-only
            STATUS  mandatory
            DESCRIPTION
                "The maximum number of physical ports supported by the
                 agent. This value should be used to verify correct port
		 values."
            ::= { a3ComMLN 2 }

	--
	-- Globals - Status of the previous SET operation
	--

	a3mlnCCSsaveErr OBJECT-TYPE
	    SYNTAX  INTEGER
	    ACCESS  read-only
	    STATUS  mandatory
	    DESCRIPTION
		"The count of detected CCS Parameter saves that failed during
		 the previous set operation. A value other than zero indicates
		 that the running and stored configurations are not the same."
	    ::= { a3ComMLN 3 }

        a3mlnCCSdelErr OBJECT-TYPE
            SYNTAX  INTEGER
            ACCESS  read-only
            STATUS  mandatory
            DESCRIPTION
                "The count of detected CCS Parameter deletes that failed during
		 the previous set operation. A value other than zero indicates
                 that the running and stored configurations are not the same."
            ::= { a3ComMLN 4 }

	a3mlnSetStatus OBJECT-TYPE
	    SYNTAX  INTEGER {
		setNoErr(1),
		setErr(2),
		setWarning(3)
	    }
	    ACCESS  read-only
	    STATUS  mandatory
	    DESCRIPTION
		"The application's result of the last SET operation. This
		 object is used to determine if the a3mlnLastSetMsg object
		 is valid, and is NOT for general SNMP errors. In order to
		 see warnings, this object must be polled after any set. The
		 error state is communicated by the agent failing the set
		 operation."
	    ::= { a3ComMLN 5 }

	a3mlnSetMsg OBJECT-TYPE
	    SYNTAX  DisplayString (SIZE(0..128))
	    ACCESS  read-only
	    STATUS  mandatory
	    DESCRIPTION
		"The equalivent UI message for the previous SET operation.
		 Valid only if a3mlnLastSetStatus is set to a value other
		 than `setNoErr'."
	    ::= { a3ComMLN 6  }

	--
	-- a3mlnPortTable
	--
	-- A table of all ports in the MLN environment, including both physical
	-- and virtual ports, indexed by port number. An application would load
	-- this table first and use it to validate port types, media types, etc.
	-- before displaying choices to a user or sending group or member table
	-- row adds to the agent. Adding or removing entries from this table is
	-- not supported.

	a3mlnPortTable OBJECT-TYPE
	    SYNTAX  SEQUENCE OF A3mlnPortEntry
	    ACCESS  not-accessible
	    STATUS  mandatory
	    DESCRIPTION
		"A table of all physical and virtual ports which may
		 be configured with the Logical Networks service."
	    ::= { a3ComMLN 7 }

	a3mlnPortEntry OBJECT-TYPE
	    SYNTAX  A3mlnPortEntry
	    ACCESS  not-accessible
	    STATUS  mandatory
	    DESCRIPTION
		"Each entry in this table represents a physical or
		 virtual port."
	    INDEX { a3mlnPindex }
	    ::= { a3mlnPortTable 1 }

	A3mlnPortEntry ::=
	    SEQUENCE {
		a3mlnPindex		INTEGER,
		a3mlnPtype		INTEGER,
		a3mlnPowner		INTEGER,
		a3mlnPlink		INTEGER,
		a3mlnPstState		INTEGER,
		a3mlnPtbState		INTEGER,
		a3mlnPgrpPrimaryPort	INTEGER,
		a3mlnPgrpSrcAdrPort	INTEGER,
		a3mlnPgrpSrcAdrMedia	INTEGER,
		a3mlnPgrpSrcAdrValue	PhysAddress,
		a3mlnPgrpDescription	DisplayString (SIZE(0..50))
	    }

	a3mlnPindex OBJECT-TYPE
	    SYNTAX  INTEGER
	    ACCESS  read-only
	    STATUS  mandatory
	    DESCRIPTION
		"This object specifies a port entry in the table and is
		 specified as a value within the total port range
		 (a3mlnMaxPorts)."
	    ::= { a3mlnPortEntry 1 }

        a3mlnPtype OBJECT-TYPE
            SYNTAX  INTEGER {
		ppmPort(1),	-- Not configured as MLN port
                groupPort(2),	-- Configured as a Group Port
		memberPort(3),	-- Configured as a Member port
		primaryPort(4)	-- Configured as the primary Member port
            }
            ACCESS  read-only
            STATUS  mandatory
            DESCRIPTION
                "The port's type. A value of `ppmPort' indicates that the
		 port has not been configured in any Logical Network."
            ::= { a3mlnPortEntry 2 }

	a3mlnPowner OBJECT-TYPE
            SYNTAX  INTEGER {
                ethernet(1),
                tokenRing(2),
                fddi(3),
                otherMedia(4)
            }
            ACCESS  read-only
            STATUS  mandatory
            DESCRIPTION
                "The port's owner (media type). If this is a Group Port, all
		 Member ports must have the same owner. A value of `otherMedia'
		 would imply a non-supported owner (media type)."
	    ::= { a3mlnPortEntry 3 }

	a3mlnPlink OBJECT-TYPE
            SYNTAX  INTEGER
            ACCESS  read-only
            STATUS  mandatory
            DESCRIPTION
                "For a Group Port, this is either the value of the first
		 member port or, if there are no member ports, the value
		 negative two. For a Member port, this is the value of
		 Group Port."
	    ::= { a3mlnPortEntry 4 }

        a3mlnPstState OBJECT-TYPE
            SYNTAX  INTEGER {
                forwarding(1),
                blocking(2),
		ignore(3)
            }
            ACCESS  read-only
            STATUS  mandatory
            DESCRIPTION
                "The Spanning Tree state of this port. For a Group Port,
		 this is the aggregate of all Member port states. If all
		 Member ports are blocking, the Group Port is blocking.
		 If a single Member port is forwarding, the Group Port is
		 forwarding. For a Member port, this is that port's state.
		 If the port has not been configured as an MLN port, the
		 value `ignore' will be returned."
            ::= { a3mlnPortEntry 5 }

	a3mlnPtbState OBJECT-TYPE
            SYNTAX  INTEGER {
                learn(1),
                noLearn(2),
		ignore(3)	-- State not valid or not member port
            }
            ACCESS  read-only
            STATUS  mandatory
            DESCRIPTION
                "Only valid for Member ports. This is the Transparent Bridge
		 CONTrol value setting of the learn parameter. If the port
		 has not been configured as a Logical Network port, the value
		 `ignore' will be returned."
            ::= { a3mlnPortEntry 6 }

	a3mlnPgrpPrimaryPort OBJECT-TYPE
            SYNTAX  INTEGER
            ACCESS  read-only
            STATUS  mandatory
            DESCRIPTION
                "Only valid for Group Ports. This is the value of the physical
		 port assigned as the group's primary port. This value is
		 assigned by the agent and may change over time."
            ::= { a3mlnPortEntry 7 }

	a3mlnPgrpSrcAdrPort OBJECT-TYPE
	    SYNTAX  INTEGER
            ACCESS  read-only
            STATUS  mandatory
            DESCRIPTION
                "Only valid for Group Ports. This is the physical port used
		 to assign the group's source MAC address used for all packets
		 transmitted by the group. This value is assigned by the agent.
		 A value of negative two indicates that no source port has been
		 assigned or that this is not a Group Port."
	    ::= { a3mlnPortEntry 8 }

	a3mlnPgrpSrcAdrMedia OBJECT-TYPE
	    SYNTAX  INTEGER {
                mediaMAC(1),
                mediaOther(2)
            }
            ACCESS  read-only
            STATUS  mandatory
            DESCRIPTION
                "Only valid for Group Ports. This is the media type of the
		 physical port being used for the group's source address.
		 This value is assigned by the agent."
	    ::= { a3mlnPortEntry 9 }

	a3mlnPgrpSrcAdrValue OBJECT-TYPE
            SYNTAX  PhysAddress
            ACCESS  read-only
            STATUS  mandatory
            DESCRIPTION
                "Only valid for Group Ports. This is the physical MAC
		 address of the group's source port. In the future, a profile
		 VARIATION should be used to further specify media formats
		 such as MacAddress, SMDSAddress, etc. This value is assigned
		 by the agent."
	    ::= { a3mlnPortEntry 10 }

	a3mlnPgrpDescription OBJECT-TYPE
            SYNTAX  DisplayString (SIZE(0..50))
            ACCESS  read-only
            STATUS  mandatory
            DESCRIPTION
                "Only valid for Group Ports. This is the description (name)
		 string for this Logical Network."
	    ::= { a3mlnPortEntry 11 }

	--
	-- a3mlnGroupTable
	--
	-- A table of all configured Group Ports. The table is
	-- indexed via a Group Port (virtual port) value.


	a3mlnGroupTable OBJECT-TYPE
	    SYNTAX  SEQUENCE OF A3mlnGroupEntry
	    ACCESS  not-accessible
	    STATUS  mandatory
	    DESCRIPTION
		"A table of all configured Logical Network Group
		 Ports."
	    ::= { a3ComMLN 8 }

	a3mlnGroupEntry OBJECT-TYPE
	    SYNTAX  A3mlnGroupEntry
	    ACCESS  not-accessible
	    STATUS  mandatory
	    DESCRIPTION
		"Each entry in this table represents a Logical Network's
		 Group Port."
	    INDEX { a3mlnGrpPort }
	    ::= { a3mlnGroupTable 1 }

	A3mlnGroupEntry ::=
	    SEQUENCE {
		a3mlnGrpPort		INTEGER,
		a3mlnGrpPortType	INTEGER,
		a3mlnGrpPortState	INTEGER,
		a3mlnGrpPrimaryPort	INTEGER,
		a3mlnGrpOwner		INTEGER,
		a3mlnGrpMemberCount	INTEGER,
		a3mlnGrpFirstMember	INTEGER,
		a3mlnGrpDescription	DisplayString (SIZE(0..50)),
		a3mlnGrpEntryStatus	RowStatus
	    }

	a3mlnGrpPort OBJECT-TYPE
	    SYNTAX  INTEGER
	    ACCESS  read-only
	    STATUS  mandatory
	    DESCRIPTION
		"This object specifies an entry in the table, and is a
		 Group Port. Group Ports are virtual ports used as points
		 of attachment to Logical Networks by upper layer clients.
		 Valid values number within the virtual port range (greater
		 than a3mlnMaxPhyPorts and less than a3mlnMaxPorts)."
	    ::= { a3mlnGroupEntry 1 }

	a3mlnGrpPortType OBJECT-TYPE
	    SYNTAX  INTEGER {
                groupPort (2)
	    }
	    ACCESS  read-only
	    STATUS  mandatory
	    DESCRIPTION
		"This port's type. The only valid value for a Group Port is
		 `groupPort'."
	    ::= { a3mlnGroupEntry 2 }

	a3mlnGrpPortState OBJECT-TYPE
	    SYNTAX  INTEGER {
		disabled(1),
		enabled(2)
	    }
	    ACCESS  read-only
	    STATUS  mandatory
	    DESCRIPTION
		"The PPM state of this Group Port."
	    ::= { a3mlnGroupEntry 3 }

	a3mlnGrpPrimaryPort OBJECT-TYPE
	    SYNTAX  INTEGER
	    ACCESS  read-only
	    STATUS  mandatory
	    DESCRIPTION
		"This is the value of the physical port assigned as
		 the group's primary port. This value is assigned by
		 the agent."
	    ::= { a3mlnGroupEntry 4 }

	a3mlnGrpOwner OBJECT-TYPE
	    SYNTAX  INTEGER {
		ethernet (1),
		tokenRing (2),
		fddi (3)
	    }
	    ACCESS  read-write
	    STATUS  mandatory
	    DESCRIPTION
		"The owner of this group (which is actually the media type
		 for the group). All Member ports must have the same owner."
	    ::= { a3mlnGroupEntry 5 }

	a3mlnGrpMemberCount OBJECT-TYPE
	    SYNTAX  INTEGER
	    ACCESS  read-only
	    STATUS  mandatory
	    DESCRIPTION
		"The number of Member ports in this group."
	    ::= { a3mlnGroupEntry 6 }

	a3mlnGrpFirstMember OBJECT-TYPE
	    SYNTAX  INTEGER
	    ACCESS  read-only
	    STATUS  mandatory
	    DESCRIPTION
		"This is the value (index) of the first Member port of
		 this group. A value of negative two indicates that no
		 Member ports have been configured."
	    ::= { a3mlnGroupEntry 7 }

	a3mlnGrpDescription OBJECT-TYPE
	    SYNTAX  DisplayString (SIZE(0..50))
	    ACCESS  read-write
	    STATUS  mandatory
	    DESCRIPTION
		"The description (name) string for this logical network."
	    ::= { a3mlnGroupEntry 8 }

	a3mlnGrpEntryStatus OBJECT-TYPE
	    SYNTAX  RowStatus
	    ACCESS  read-write
	    STATUS  mandatory
	    DESCRIPTION
		"This object is used to add and delete entries in this
		 table. See RowStatus description at the beginning of
		 this MIB. Note - A group's description may be changed
		 without first deleting the row."
	    ::= { a3mlnGroupEntry 9 }

	--
	-- a3mlnMemberTable
	--
	-- A table of configured Logical Networks. Index by Group Port and
	-- Member port.

	a3mlnMemberTable OBJECT-TYPE
	    SYNTAX  SEQUENCE OF A3mlnMemberEntry
	    ACCESS  not-accessible
	    STATUS  mandatory
	    DESCRIPTION
		"A table of configured Logical Networks."
	    ::= { a3ComMLN 9 }

	a3mlnMemberEntry OBJECT-TYPE
	    SYNTAX  A3mlnMemberEntry
	    ACCESS  not-accessible
	    STATUS  mandatory
	    DESCRIPTION
		"Each entry in this table represents a Logical Network."
	    INDEX { a3mlnMemGrpPort, a3mlnMemPort }
	    ::= { a3mlnMemberTable 1 }

	A3mlnMemberEntry ::=
	    SEQUENCE {
		a3mlnMemGrpPort		INTEGER,
		a3mlnMemPort		INTEGER,
		a3mlnMemOwner		INTEGER,
		a3mlnMemEntryStatus	RowStatus
	    }

	a3mlnMemGrpPort OBJECT-TYPE
	    SYNTAX  INTEGER
	    ACCESS  read-only
	    STATUS  mandatory
	    DESCRIPTION
		"This object specifies a Logical Network within the table
		 and is a Group Port within the virtual port range (greater
		 than a3mlnMaxPhyPorts and less than a3mlnMaxPorts)."
	    ::= { a3mlnMemberEntry 1 }

	a3mlnMemPort OBJECT-TYPE
	    SYNTAX  INTEGER
	    ACCESS  read-only
	    STATUS  mandatory
	    DESCRIPTION
		"This object specifies a Member port within a Logical Network
		 and is a physical port within the physical port range
		 (less than a3mlnMaxPhyPorts)."
	    ::= { a3mlnMemberEntry 2 }

	a3mlnMemOwner OBJECT-TYPE
	    SYNTAX  INTEGER {
		ethernet(1),
		tokenRing(2),
		fddi(3),
		otherMedia(4)
	    }
	    ACCESS  read-write
	    STATUS  mandatory
	    DESCRIPTION
		"The owner of this group (which is actually the media type
		 for the group). All Member ports must have the same owner."
	    ::= { a3mlnMemberEntry 3 }

	a3mlnMemEntryStatus OBJECT-TYPE
	    SYNTAX  RowStatus
	    ACCESS  read-write
	    STATUS  mandatory
	    DESCRIPTION
		"This object is used to add and delete entries in this
                 table. See RowStatus description at the beginning of
                 this MIB."
	    ::= { a3mlnMemberEntry 4 }

	--
	-- Statistics Group
	--

        a3mlnStatSelGrpPort OBJECT-TYPE
            SYNTAX  INTEGER
            ACCESS  read-only
            STATUS  mandatory
            DESCRIPTION
                "The number of times a Group Port has been selected."
            ::= { a3mlnStatistics 1 }

        a3mlnStatSelMacAdr OBJECT-TYPE
            SYNTAX  INTEGER
            ACCESS  read-only
            STATUS  mandatory
            DESCRIPTION
                "The number of times a MAC address has been selected."
            ::= { a3mlnStatistics 2 }

	--
	-- a3mlnPortStatTable
	--
	-- A table of a Logical Network Member port statistics. The table is
	-- indexed by a Member port value.

	a3mlnPortStatTable OBJECT-TYPE
	    SYNTAX  SEQUENCE OF A3mlnPortStatEntry
	    ACCESS  not-accessible
	    STATUS  mandatory
	    DESCRIPTION
		"A table of Logical Network Member port statistics."
	    ::= { a3mlnStatistics 3 }

	a3mlnPortStatEntry OBJECT-TYPE
	    SYNTAX  A3mlnPortStatEntry
	    ACCESS  not-accessible
	    STATUS  mandatory
	    DESCRIPTION
		"Each entry in this table represents statistics for a
		 Member port of a Logical Network."
	    INDEX { a3mlnPStatIndex }
	    ::= { a3mlnPortStatTable 1 }

	A3mlnPortStatEntry ::=
	    SEQUENCE {
		a3mlnPStatIndex		INTEGER,
		a3mlnPStatRcvd		INTEGER,
		a3mlnPStatXmit		INTEGER,
		a3mlnPStatStaMoveFrom	INTEGER,
		a3mlnPStatStaMoveTo	INTEGER,
		a3mlnPStatSTAchange	INTEGER
	    }

	a3mlnPStatIndex OBJECT-TYPE
	    SYNTAX  INTEGER
	    ACCESS  read-only
	    STATUS  mandatory
	    DESCRIPTION
		"This object specifies an entry in the port statistics table
		 and is a Member port within the physical port range (less
		 than a3mlnMaxPhyPorts)."
	    ::= { a3mlnPortStatEntry 1 }

	a3mlnPStatRcvd OBJECT-TYPE
	    SYNTAX  INTEGER
	    ACCESS  read-only
	    STATUS  mandatory
	    DESCRIPTION
		"Count of data frames received on this port."
	    ::= { a3mlnPortStatEntry 2 }
	
	a3mlnPStatXmit OBJECT-TYPE
	    SYNTAX  INTEGER
	    ACCESS  read-only
	    STATUS  mandatory
	    DESCRIPTION
		"Count of data frames transmitted from this port."
	    ::= { a3mlnPortStatEntry 3 }

	a3mlnPStatStaMoveFrom OBJECT-TYPE
	    SYNTAX  INTEGER
	    ACCESS  read-only
	    STATUS  mandatory
	    DESCRIPTION
		"Count of detected stations moving away from this port."
	    ::= { a3mlnPortStatEntry 4 }

	a3mlnPStatStaMoveTo OBJECT-TYPE
	    SYNTAX  INTEGER
	    ACCESS  read-only
	    STATUS  mandatory
	    DESCRIPTION
		"Count of detected stations moving to this port."
	    ::= { a3mlnPortStatEntry 5 }

	a3mlnPStatSTAchange OBJECT-TYPE
	    SYNTAX  INTEGER
	    ACCESS  read-only
	    STATUS  mandatory
	    DESCRIPTION
		"Count of Spanning Tree state changes for this port."
	    ::= { a3mlnPortStatEntry 6 }
END
