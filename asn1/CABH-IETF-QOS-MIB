-- extracted from draft-ietf-ipcdn-cable-gateway-qos-mib-00.txt
-- at Wed Jun 25 06:13:37 2003

   CABH-IETF-QOS-MIB DEFINITIONS ::= BEGIN  
    
   IMPORTS  
      MODULE-IDENTITY,  
      OBJECT-TYPE, 
      Unsigned32, 
      mib-2  
                               FROM SNMPv2-SMI  
    
      TimeStamp, 
      TruthValue, 
      RowStatus                FROM SNMPv2-TC  
    
      OBJECT-GROUP,  
      MODULE-COMPLIANCE        FROM SNMPv2-CONF  
    
      InetPortNumber,  
      InetAddressType,  
      InetAddress              FROM INET-ADDRESS-MIB  
    
      ifIndex                  FROM IF-MIB; 

   cabhQosMib MODULE-IDENTITY  
       LAST-UPDATED    "200306210000Z" -- Jun 21, 2003 
       ORGANIZATION    "IETF IPCDN Working Group" 
       CONTACT-INFO  
               "Kevin Luehrs  
               Postal: Cable Television Laboratories, Inc.  
               400 Centennial Parkway  
               Louisville, Colorado 80027-1266  
               U.S.A.  
               Phone:  +1 303-661-9100  
               Fax:    +1 303-661-9199  
               E-mail: k.luehrs@cablelabs.com; mibs@cablelabs.com 
    
               IETF IPCDN Working Group 
               General Discussion: ipcdn@ietf.org 
               Subscribe: http://www.ietf.org/mailman/listinfo/ipcdn 
               Archive: ftp://ftp.ietf.org/ietf-mail-archive/ipcdn 
               Co-chairs: Richard Woundy, 
                          Richard_Woundy@cable.comcast.com 
                          Jean-Francois Mule, jf.mule@cablelabs.com" 
    
       DESCRIPTION  
               "This MIB module supplies parameters for the  
               configuration and monitoring of CableHome  
               prioritized QoS capability. 
    
               Copyright (C) The Internet Society (2003). This version 
               of this MIB module is part of RFC xxxx; see the RFC 
               itself for full legal notices." 
       REVISION         "200306210000Z" -- Jun 21, 2003 
       DESCRIPTION  
               "Initial version, published as RFC xxxx."  
                -- RFC editor to assign xxxx  
       ::= { mib-2 xx }    
     -- xx to be assigned by IANA 
    
   -- Textual conventions  
        
   cabhQosMibObjects         OBJECT IDENTIFIER ::= { cabhQosMib 1}  
   cabhPriorityQosMibObjects OBJECT IDENTIFIER ::= 
                                         { cabhQosMibObjects 1 } 
   cabhPriorityQosBase       OBJECT IDENTIFIER ::= 
                                         { cabhPriorityQosMibObjects 1 } 
   cabhPriorityQosBp         OBJECT IDENTIFIER ::= 
                                         { cabhPriorityQosMibObjects 2 } 
   cabhPriorityQosPs         OBJECT IDENTIFIER ::= 
                                         { cabhPriorityQosMibObjects 3 } 
        
      -- future parametric QOS  
      -- cabhParamQosMibObjects  OBJECT IDENTIFIER ::=  
      --                                        { cabhQosMibObjects 2 }  
        
      --================================================================  
      --  
      --  Application Priority Master Table  
      --  
      --  The cabhPriorityQosMasterTable contains the list of  
      --  application priorities provisioned by the cable operator.  
      --  Applications are identified by the IANA "well-known" port  
      --  numbers  assigned to them.  
      --  
      --================================================================  
   cabhPriorityQosMasterTable  OBJECT-TYPE  
       SYNTAX SEQUENCE OF CabhPriorityQosMasterEntry  
       MAX-ACCESS  not-accessible  
       STATUS      current  
       DESCRIPTION  
               "This table contains a list of mappings for Application 
               IDs to Default CableHome Priorities."  
        ::= { cabhPriorityQosBase 1  }  
         
   cabhPriorityQosMasterEntry OBJECT-TYPE  
       SYNTAX CabhPriorityQosMasterEntry  
       MAX-ACCESS  not-accessible  
       STATUS      current  
       DESCRIPTION  
               "An entry for mapping Application IDs to Default 
               CableHome Priorities."  
       INDEX { cabhPriorityQosMasterApplicationId }  
       ::= { cabhPriorityQosMasterTable 1 }  
        
         
   CabhPriorityQosMasterEntry ::= SEQUENCE {  
       cabhPriorityQosMasterApplicationId       Unsigned32,  
       cabhPriorityQosMasterDefaultCHPriority   Unsigned32,  
       cabhPriorityQosMasterRowStatus           RowStatus  
       }  
         
   cabhPriorityQosMasterApplicationId       OBJECT-TYPE  
       SYNTAX                  Unsigned32 (1..65535)  
       MAX-ACCESS              not-accessible  
       STATUS                  current  
       DESCRIPTION               
               "The IANA well-known port number identifying an  
               application."  
       ::= { cabhPriorityQosMasterEntry 1 }  
        
        
   cabhPriorityQosMasterDefaultCHPriority       OBJECT-TYPE  
       SYNTAX                  Unsigned32 (0..7)  
       MAX-ACCESS              read-create  
       STATUS                  current  
       DESCRIPTION               
               "The PriorityQos priority assigned to the application." 
       ::= { cabhPriorityQosMasterEntry 2 }  
        
   cabhPriorityQosMasterRowStatus  OBJECT-TYPE  
       SYNTAX                  RowStatus  
       MAX-ACCESS              read-create  
       STATUS                  current  
       DESCRIPTION               
               "The Row Status interlock for creation and deletion of 
               row entries. Specifying only this object (with the 
               appropriate index) on a PS is sufficient to create a row 
               with default values. There is no restrictions to change 
               the value of cabhPriorityQosMasterDefaultCHPriority in a 
               row while this object is set to active."  
       ::= { cabhPriorityQosMasterEntry 3 }   
        
        
        
      -- ===============================================================  
      --  
      --  SetToFactory Object 
      --  
      -- This object is used to clear some of the QoS MIB tables 
      --  
      -- =============================================================== 
    
   cabhPriorityQosSetToFactory OBJECT-TYPE 
       SYNTAX TruthValue 
       MAX-ACCESS read-write 
       STATUS current 
       DESCRIPTION 
               "When this object is set to true(1), the PS MUST  clear 
               all the entries in the cabhPriorityQosBpTable and  
               cabhPriorityQosBpDestTable. Reading this object always  
               returns false(2)." 
       ::= { cabhPriorityQosBase 2 } 
    
   cabhPriorityQosLastSetToFactory OBJECT-TYPE 
       SYNTAX TimeStamp 
       MAX-ACCESS read-only 
       STATUS current 
       DESCRIPTION 
               "The value of sysUpTime when cabhPriorityQosSetToFactory 
               was last set to true. Zero if never reset." 
       ::= { cabhPriorityQosBase 3 } 

      --===============================================================  
      --  
      --  BP Application Priority Table  
      --  
      --  The cabhPriorityQosBpTable contains the list of  
      --  BPs, the applications implemented on each, and the priority  
      --  assigned to each application.  
      --  
      --===============================================================  
        
   cabhPriorityQosBpTable OBJECT-TYPE  
       SYNTAX SEQUENCE OF CabhPriorityQosBpEntry  
       MAX-ACCESS not-accessible  
       STATUS current  
       DESCRIPTION  
               "This table contains the priorities for each of the 
               discovered CableHome Host (BP) applications and related  
               data."  
            ::= {cabhPriorityQosBp 1}  
         
   cabhPriorityQosBpEntry OBJECT-TYPE  
       SYNTAX      CabhPriorityQosBpEntry  
       MAX-ACCESS  not-accessible  
       STATUS      current  
       DESCRIPTION  
               "List of applications entries. 
    
               Implementors need to be aware that if the size 
               of cabhPriorityQosBpIpAddr exceeds 113 octets then OIDs 
               of column instances in this table will have more 
               than 128 sub-identifiers and cannot be accessed 
               using SNMPv1, SNMPv2c, or SNMPv3." 
       INDEX { cabhPriorityQosMasterApplicationId, 
               cabhPriorityQosBpIpAddrType, cabhPriorityQosBpIpAddr } 
       ::= { cabhPriorityQosBpTable 1 }  
         
   CabhPriorityQosBpEntry ::= SEQUENCE {  
       cabhPriorityQosBpIpAddrType         InetAddressType,  
       cabhPriorityQosBpIpAddr             InetAddress,  
       cabhPriorityQosBpApplicationId      Unsigned32,  
       cabhPriorityQosBpDefaultCHPriority  Unsigned32,  
       cabhPriorityQosBpIndex              Unsigned32  
       }  
         
   cabhPriorityQosBpIpAddrType   OBJECT-TYPE  
       SYNTAX      InetAddressType  
       MAX-ACCESS  read-only  
       STATUS      current  
       DESCRIPTION  
               "The type of the IP address assigned to a particular BP  
               element."  
       ::= { cabhPriorityQosBpEntry 1 }  
        
        
   cabhPriorityQosBpIpAddr    OBJECT-TYPE  
       SYNTAX      InetAddress  
       MAX-ACCESS  read-only  
       STATUS      current  
       DESCRIPTION  
               "The IP address assigned to a particular BP element."  
       ::= { cabhPriorityQosBpEntry 2 }  
        
   cabhPriorityQosBpApplicationId   OBJECT-TYPE  
       SYNTAX      Unsigned32 (1..65535)  
       MAX-ACCESS  read-only  
       STATUS      current  
       DESCRIPTION  
               "The IANA well-known port number assigned to a particular  
               application implemented on the CableHome Host device in  
               which this BP resides."  
         ::= { cabhPriorityQosBpEntry 3 }  
        
        
   cabhPriorityQosBpDefaultCHPriority  OBJECT-TYPE  
       SYNTAX      Unsigned32 (0..7)  
       MAX-ACCESS  read-only  
       STATUS      current  
       DESCRIPTION  
               "The PriorityQos priority assigned to a particular  
               application implemented on CableHome Host device in which  
               this BP resides. The PS populates this entry according to 
               the Application Priority Master Table."  
         ::= { cabhPriorityQosBpEntry 4 }  
        
   cabhPriorityQosBpIndex  OBJECT-TYPE  
       SYNTAX      Unsigned32 (1..65535)  
       MAX-ACCESS  read-only  
       STATUS      current  
       DESCRIPTION 
               "The unique identifier for a particular row in the BP  
               Application Priority Table. This identifier is used as  
               an index into the 'nested' Destination Priority Table."  
       ::= { cabhPriorityQosBpEntry 5 }  
        
        
      --===============================================================  
      --  
      --  Destination Priority Table  
      --  
      --  The cabhPriorityQosDestListTable contains the list of  
      --  provisioned destinations (IP address and port number) to  
      --  which a BP can send traffic with a special PriorityQos  
      --  priority. Any application listed in the BP Application  
      --  Priority Table can be provisioned with a Destination  
      --  Priority Table.  
      --  
      --===============================================================  
        
   cabhPriorityQosBpDestTable OBJECT-TYPE  
       SYNTAX SEQUENCE OF CabhPriorityQosBpDestEntry  
       MAX-ACCESS     not-accessible  
       STATUS      current  
       DESCRIPTION  
               "This table contains the priorities based on destination 
               IP address and port number. It is indexed with a unique 
               identifier for rows in the BP Application Priority 
               Table."  
       ::= {cabhPriorityQosBp 2}  
         
   cabhPriorityQosBpDestEntry OBJECT-TYPE 
       SYNTAX      CabhPriorityQosBpDestEntry 
       MAX-ACCESS  not-accessible 
       STATUS      current 
       DESCRIPTION 
               "List of Destination IP addresses and port numbers 
               for an application to which special PriorityQos 
               priority is provisioned. 
    
               Implementors need to be aware that if the size 
               of cabhPriorityQosBpIpAddr exceeds 112 octets then OIDs 
               of column instances in this table will have more 
               than 128 sub-identifiers and cannot be accessed 
               using SNMPv1, SNMPv2c, or SNMPv3." 
       INDEX { cabhPriorityQosMasterApplicationId, 
               cabhPriorityQosBpIpAddrType, 
               cabhPriorityQosBpIpAddr, 
               cabhPriorityQosBpDestIndex } 
      ::= { cabhPriorityQosBpDestTable 1 } 
        
   CabhPriorityQosBpDestEntry ::= SEQUENCE { 
       cabhPriorityQosBpDestIndex            Unsigned32, 
       cabhPriorityQosBpDestIpAddrType       InetAddressType, 
       cabhPriorityQosBpDestIpAddr           InetAddress, 
       cabhPriorityQosBpDestPort             InetPortNumber, 
       cabhPriorityQosBpDestIpPortPriority   Unsigned32 
       } 
    
   cabhPriorityQosBpDestIndex OBJECT-TYPE 
       SYNTAX      Unsigned32 (1..65535) 
       MAX-ACCESS  not-accessible 
       STATUS      current 
       DESCRIPTION 
               "The locally unique index into the Destination 
               Priority Table." 
       ::= { cabhPriorityQosBpDestEntry 1 } 
        
   cabhPriorityQosBpDestIpAddrType     OBJECT-TYPE  
       SYNTAX      InetAddressType  
       MAX-ACCESS  read-only  
       STATUS      current  
       DESCRIPTION  
               "The type of the Destination IP Address."  
       ::= { cabhPriorityQosBpDestEntry 2 }  
        
   cabhPriorityQosBpDestIpAddr   OBJECT-TYPE  
       SYNTAX      InetAddress  
       MAX-ACCESS  read-only  
       STATUS      current  
       DESCRIPTION  
               "The Destination IP address of the LAN IP Device of an  
               application to which special PriorityQos priority is  
               assigned."  
         ::= { cabhPriorityQosBpDestEntry 3 }  
        
   cabhPriorityQosBpDestPort     OBJECT-TYPE  
       SYNTAX      InetPortNumber  
       MAX-ACCESS  read-only  
       STATUS      current  
       DESCRIPTION  
               "The port number of an application to which special  
               PriorityQos priority is assigned."  
         ::= { cabhPriorityQosBpDestEntry 4 }  
        
   cabhPriorityQosBpDestIpPortPriority    OBJECT-TYPE  
       SYNTAX      Unsigned32 (1..8)  
       MAX-ACCESS  read-only  
       STATUS      current  
       DESCRIPTION  
               "The PriorityQos priority assigned to a particular  
               application in another LAN IP Device."  
       ::= { cabhPriorityQosBpDestEntry 5 }  
        
        
      --===============================================================  
      --  
      --  PS Interface Attributes Table  
      --  
      --  The cabhPriorityQosPsIfAttribTable contains the number of  
      --  media access priorities and number of queues associated with  
      --  each LAN interface in the Residential Gateway.  
      --  
      --===============================================================  
        
   cabhPriorityQosPsIfAttribTable   OBJECT-TYPE  
       SYNTAX SEQUENCE OF CabhPriorityQosPsIfAttribEntry  
       MAX-ACCESS   not-accessible  
       STATUS    current  
       DESCRIPTION  
               "This table contains the number of media access 
               priorities and number of queues associated with each 
               LAN interface in the Residential Gateway."  
            ::= { cabhPriorityQosPs 1  }  
         
   cabhPriorityQosPsIfAttribEntry      OBJECT-TYPE  
       SYNTAX    CabhPriorityQosPsIfAttribEntry  
       MAX-ACCESS   not-accessible  
       STATUS    current  
       DESCRIPTION  
               "Number of media access priorities and number of queues 
               for each LAN interface in the Residential Gateway. This 
               table applies only to interfaces through which data 
               flows."  
       INDEX { ifIndex }  
       ::= { cabhPriorityQosPsIfAttribTable 1 }  
         
   CabhPriorityQosPsIfAttribEntry ::= SEQUENCE {  
       cabhPriorityQosPsIfAttribIfNumPriorities   Unsigned32,  
       cabhPriorityQosPsIfAttribIfNumQueues       Unsigned32  
       }  
        
   cabhPriorityQosPsIfAttribIfNumPriorities OBJECT-TYPE  
       SYNTAX     Unsigned32 (1..8)  
           MAX-ACCESS read-only  
           STATUS     current  
           DESCRIPTION  
                   "The number of media access priorities supported by 
                   this LAN interface."  
       ::= { cabhPriorityQosPsIfAttribEntry 1 }  
        
   cabhPriorityQosPsIfAttribIfNumQueues OBJECT-TYPE  
       SYNTAX     Unsigned32 (1..8)  
       MAX-ACCESS read-only  
       STATUS     current  
       DESCRIPTION  
               "The number of queues associated with this LAN 
               interface."  
       ::= { cabhPriorityQosPsIfAttribEntry 2 }  
        
        
      -- Placeholder for notifications/traps.  
      --  
        
   cabhQosNotification         OBJECT IDENTIFIER  ::= { cabhQosMib 2 }  
   cabhPriorityQosNotification OBJECT IDENTIFIER  ::= 
                                             { cabhQosNotification 1 } 
        
        
        
      --  
      -- Conformance definitions  
      --  
   cabhQosConformance          OBJECT IDENTIFIER  ::= { cabhQosMib 3 }  
   cabhPriorityQosConformance  OBJECT IDENTIFIER  ::= 
                                              { cabhQosConformance 1 }  
   cabhPriorityQosGroups       OBJECT IDENTIFIER  ::= 
                                      { cabhPriorityQosConformance 1 } 
   cabhPriorityQosCompliances  OBJECT IDENTIFIER  ::= 
                                      { cabhPriorityQosConformance 2 }  
        
        
      -- ==================  
        
      -- compliance statements  
        
   cabhPriorityQosCompliance MODULE-COMPLIANCE  
       STATUS     current  
       DESCRIPTION  
               "The compliance statement for devices that implement  
               CableHome 1.1 PriorityQos capability."  
       MODULE   --cabhPriorityQosMib  
    
      -- unconditionally mandatory groups  
        
   MANDATORY-GROUPS {  
       cabhPriorityQosGroup  
       }  
        
   OBJECT cabhPriorityQosBpIpAddrType 
          SYNTAX InetAddressType { ipv4(1) } 
          DESCRIPTION 
              "An implementation is only required to support IPv4 
               addresses." 
    
   OBJECT cabhPriorityQosBpIpAddr 
          SYNTAX  InetAddress (SIZE(4)) 
          DESCRIPTION 
              "An implementation is only required to support IPv4 
               addresses." 
    
   OBJECT cabhPriorityQosBpDestIpAddrType 
          SYNTAX InetAddressType { ipv4(1) } 
          DESCRIPTION 
              "An implementation is only required to support IPv4 
               addresses." 
    
   OBJECT cabhPriorityQosBpDestIpAddr 
          SYNTAX  InetAddress (SIZE(4)) 
          DESCRIPTION 
              "An implementation is only required to support IPv4 
               addresses." 
    
      ::= { cabhPriorityQosCompliances 1}  
        
        
   cabhPriorityQosGroup OBJECT-GROUP  
       OBJECTS {  
           cabhPriorityQosMasterDefaultCHPriority,  
           cabhPriorityQosMasterRowStatus,  
           cabhPriorityQosSetToFactory, 
           cabhPriorityQosLastSetToFactory, 
           cabhPriorityQosBpIpAddrType,  
           cabhPriorityQosBpIpAddr,  
           cabhPriorityQosBpApplicationId,  
           cabhPriorityQosBpDefaultCHPriority,  
           cabhPriorityQosBpIndex,  
           cabhPriorityQosBpDestIpAddrType,  
           cabhPriorityQosBpDestIpAddr,  
           cabhPriorityQosBpDestPort,  
           cabhPriorityQosBpDestIpPortPriority,  
           cabhPriorityQosPsIfAttribIfNumPriorities,  
           cabhPriorityQosPsIfAttribIfNumQueues  
       }  
       STATUS    current  
       DESCRIPTION  
               "Group of objects for CableHome Application Priority 
               MIB."  
       ::= { cabhPriorityQosGroups 1 }   
      END 

--  
--    Copyright (C) The Internet Society (2003). All Rights Reserved. 
--     
--    This document and translations of it may be copied and furnished to 
--    others, and derivative works that comment on or otherwise explain it 
--    or assist in its implementation may be prepared, copied, published 
--    and distributed, in whole or in part, without restriction of any 
--    kind, provided that the above copyright notice and this paragraph are 
--    included on all such copies and derivative works.  However, this 
--    document itself may not be modified in any way, such as by removing 
--    the copyright notice or references to the Internet Society or other 
--    Internet organizations, except as needed for the purpose of 
--    developing Internet standards in which case the procedures for 
--    copyrights defined in the Internet Standards process must be 
--    followed, or as required to translate it into languages other than 
--    English. 
--     
--    The limited permissions granted above are perpetual and will not be 
--    revoked by the Internet Society or its successors or assigns. 
--     
--    This document and the information contained herein is provided on an 
--    "AS IS" basis and THE INTERNET SOCIETY AND THE INTERNET ENGINEERING 
--    TASK FORCE DISCLAIMS ALL WARRANTIES, EXPRESS OR IMPLIED, INCLUDING 
--    BUT NOT LIMITED TO ANY WARRANTY THAT THE USE OF THE INFORMATION 
--    HEREIN WILL NOT INFRINGE ANY RIGHTS OR ANY IMPLIED WARRANTIES OF 
--    MERCHANTABILITY OR FITNESS FOR A PARTICULAR PURPOSE.
