Wellfleet-BOT-MIB DEFINITIONS ::= BEGIN

-- Created by mdl2asn version 3.1
-- Creation date: Wed Sep  6 16:57:28 EDT 1995
-- Edited by ksheth on 10/12/95 - Added BotKeepaliveTimer attribute
--           ksheth    10/20/95 - changed CU address max value to 254
--           ksheth    04/09/96 - removed some IMPORTS statments 
--           sdey      06/28/96 - added range for configurable TCP ports

    IMPORTS

      IpAddress, Counter 
        FROM RFC1155-SMI
      OBJECT-TYPE
        FROM RFC-1212
      wfBotGroup
        FROM Wellfleet-COMMON-MIB;


    wfBot		OBJECT IDENTIFIER ::= { wfBotGroup 1 }

    wfBotDelete OBJECT-TYPE
        SYNTAX	INTEGER {
    		    created(1),
    		    deleted(2)
    		}
        ACCESS	read-write
        STATUS	mandatory
        DESCRIPTION
                "Create/Delete parameter. Default is created.
                User perform an SNMP SET operation on this object
                in order to create/delete BOT"
        DEFVAL	{ created }
        ::= { wfBot 1 }

    wfBotDisable OBJECT-TYPE
        SYNTAX	INTEGER {
    		    enabled(1),
    		    disabled(2)
    		}
        ACCESS	read-write
        STATUS	mandatory
        DESCRIPTION
                "Enable/Disable parameter. Default is enabled.
                User perform an SNMP SET operation on this object
                in order to enable/disable BOT"
        DEFVAL	{ enabled }
        ::= { wfBot 2 }

    wfBotState OBJECT-TYPE
        SYNTAX	INTEGER {
    		    up(1),
    		    down(2),
    		    init(3),
    		    notpresent(4)
    		}
        ACCESS	read-only
        STATUS	mandatory
        DESCRIPTION
                "The current state of BOT"
        DEFVAL	{ down }
        ::= { wfBot 3 }

    wfBotInterfaceTable OBJECT-TYPE
        SYNTAX	SEQUENCE OF WfBotInterfaceEntry
        ACCESS	not-accessible
        STATUS	mandatory
        DESCRIPTION
                "Interface table which lists all BISYNC line entries and other
                line related information"
        ::= { wfBotGroup 2 }

    wfBotInterfaceEntry OBJECT-TYPE
        SYNTAX	WfBotInterfaceEntry
        ACCESS	not-accessible
        STATUS	mandatory
        DESCRIPTION
                "An entry in wfBotInterfaceTable"
        INDEX	{ wfBotInterfaceSlotNumber,
    		  wfBotInterfaceCctNumber }
        ::= { wfBotInterfaceTable 1 }

    WfBotInterfaceEntry ::= SEQUENCE {
    	    wfBotInterfaceDelete
    		INTEGER,
    	    wfBotInterfaceDisable
    		INTEGER,
    	    wfBotInterfaceCctNumber
    		INTEGER,
    	    wfBotInterfaceSlotNumber
    		INTEGER,
    	    wfBotInterfaceState
    		INTEGER,
    	    wfBotInterfaceType
    		INTEGER,
    	    wfBotInterfaceAttachedTo
    		INTEGER,
    	    wfBotInterfacePktCnt
    		Counter,
	    wfBotKeepaliveInterval
		INTEGER,
	    wfBotKeepaliveRto
		INTEGER,
	    wfBotKeepaliveMaxRetry
		INTEGER
        }

    wfBotInterfaceDelete OBJECT-TYPE
        SYNTAX	INTEGER {
    		    created(1),
    		    deleted(2)
    		}
        ACCESS	read-write
        STATUS	mandatory
        DESCRIPTION
                "Create/Delete attribute. Default is Created
                Users perform SNMP SET operation on this object in
                order to create/delete a translation interface record"
        DEFVAL	{ created }
        ::= { wfBotInterfaceEntry 1 }

    wfBotInterfaceDisable OBJECT-TYPE
        SYNTAX	INTEGER {
    		    enabled(1),
    		    disabled(2)
    		}
        ACCESS	read-write
        STATUS	mandatory
        DESCRIPTION
                "Enables/Disables this mapping entry
                Setting of this attribute to DISABLED will disconnect
                all active sessions pertaining to this interface entry"
        DEFVAL	{ enabled }
        ::= { wfBotInterfaceEntry 2 }

    wfBotInterfaceCctNumber OBJECT-TYPE
        SYNTAX	INTEGER
        ACCESS	read-only
        STATUS	mandatory
        DESCRIPTION
                "The circuit from which the connection attempt is
                received that initiates a translation session."
        ::= { wfBotInterfaceEntry 3 }

    wfBotInterfaceSlotNumber OBJECT-TYPE
        SYNTAX	INTEGER
        ACCESS	read-only
        STATUS	mandatory
        DESCRIPTION
                "Slot number on which this interface is running"
        ::= { wfBotInterfaceEntry 4 }

    wfBotInterfaceState OBJECT-TYPE
        SYNTAX	INTEGER {
    		    up(1),
    		    down(2),
    		    init(3)
    		}
        ACCESS	read-only
        STATUS	mandatory
        DESCRIPTION
                "The current state of the Interface"
        DEFVAL	{ down }
        ::= { wfBotInterfaceEntry 5 }

    wfBotInterfaceType OBJECT-TYPE
        SYNTAX	INTEGER {
    		    singledrop(1),
    		    multidrop(2)
    		}
        ACCESS	read-write
        STATUS	mandatory
        DESCRIPTION
                "If this interface is point-to-point, i.e. no splitting
                occours we can straight away deliver BSC frame to designated
                TCP circuit, without looking into the CU address"
        DEFVAL	{ singledrop }
        ::= { wfBotInterfaceEntry 6 }

    wfBotInterfaceAttachedTo OBJECT-TYPE
        SYNTAX	INTEGER {
    		    primary(1),
    		    secondary(2)
    		}
        ACCESS	read-write
        STATUS	mandatory
        DESCRIPTION
                "Information that this interface is attached to the Primary or
                secondary BSC station"
        ::= { wfBotInterfaceEntry 7 }

    wfBotInterfacePktCnt OBJECT-TYPE
        SYNTAX	Counter
        ACCESS	read-only
        STATUS	mandatory
        DESCRIPTION
                "Interface packet count ..."
        ::= { wfBotInterfaceEntry 8 }

    wfBotKeepaliveInterval OBJECT-TYPE
        SYNTAX	INTEGER(0..86400)
        ACCESS	read-write
        STATUS	mandatory
        DESCRIPTION
                "Idle session timeout period, in seconds.  If an established
                TCP connection remains inactive for this interval, KEEPALIVE
                messages will be sent to the peer (if the Keepalive Timer is
                non-zero).  Setting the Idle Timer to zero disables the
                keepalive feature."
        DEFVAL	{ 120 }
        ::= { wfBotInterfaceEntry 9 }

    wfBotKeepaliveRto OBJECT-TYPE
        SYNTAX	INTEGER(0..600)
        ACCESS	read-write
        STATUS	mandatory
        DESCRIPTION
                "KEEPALIVE retransmit timeout period, in seconds.  This is
                the interval at which unacknowledged KEEPALIVE messages will
                be retransmitted.  If the Idle Timer is set to zero, this
                timer ignored.  If the Idle Timer is non-zero and this timer
                IS zero, no KEEPALIVEs are sent and the session is terminated
                upon expiration of the Idle Timer."
        DEFVAL	{ 4 }
        ::= { wfBotInterfaceEntry 10 }

    wfBotKeepaliveMaxRetry OBJECT-TYPE
        SYNTAX	INTEGER(0..99)
        ACCESS	read-write
        STATUS	mandatory
        DESCRIPTION
                "Number of unacknowledged KEEPALIVE messages retransmitted
		before the TCP session is terminated.  If this count is set
		to zero, only one KEEPALIVE message will be sent."
        DEFVAL	{ 5 }
        ::= { wfBotInterfaceEntry 11 }

    wfBotPeerTable OBJECT-TYPE
        SYNTAX	SEQUENCE OF WfBotPeerEntry
        ACCESS	not-accessible
        STATUS	mandatory
        DESCRIPTION
                "Peer table lists all TCP connections this router will have
                with its peers"
        ::= { wfBotGroup 3 }

    wfBotPeerEntry OBJECT-TYPE
        SYNTAX	WfBotPeerEntry
        ACCESS	not-accessible
        STATUS	mandatory
        DESCRIPTION
                "An entry in wfBotPeerTable"
        INDEX	{ wfBotPeerSlotNumber,
    		  wfBotPeerCctNumber,
    		  wfBotPeerRemoteIpAddr,
    		  wfBotPeerLocalTcpListenPort,
    		  wfBotPeerRemoteTcpListenPort,
    		  wfBotConnOriginator }
        ::= { wfBotPeerTable 1 }

    WfBotPeerEntry ::= SEQUENCE {
    	    wfBotPeerEntryDelete
    		INTEGER,
    	    wfBotPeerEntryDisable
    		INTEGER,
    	    wfBotPeerSlotNumber
    		INTEGER,
    	    wfBotPeerCctNumber
    		INTEGER,
    	    wfBotPeerRemoteIpAddr
    		IpAddress,
    	    wfBotConnOriginator
    		INTEGER,
    	    wfBotPeerLocalTcpListenPort
    		INTEGER,
    	    wfBotPeerRemoteTcpListenPort
    		INTEGER,
    	    wfBotPeerLocalTcpPort
    		INTEGER,
    	    wfBotPeerRemoteTcpPort
    		INTEGER
        }

    wfBotPeerEntryDelete OBJECT-TYPE
        SYNTAX	INTEGER {
    		    created(1),
    		    deleted(2)
    		}
        ACCESS	read-write
        STATUS	mandatory
        DESCRIPTION
                "Create/Delete attribute. Default is Created
                Users perform SNMP SET operation on this object in
                order to create/delete a peer record"
        DEFVAL	{ created }
        ::= { wfBotPeerEntry 1 }

    wfBotPeerEntryDisable OBJECT-TYPE
        SYNTAX	INTEGER {
    		    enabled(1),
    		    disabled(2)
    		}
        ACCESS	read-write
        STATUS	mandatory
        DESCRIPTION
                "Enables/Disables this mapping entry
                Setting of this attribute to DISABLED will disconnect
                all active sessions pertaining to this interface entry"
        DEFVAL	{ enabled }
        ::= { wfBotPeerEntry 2 }

    wfBotPeerSlotNumber OBJECT-TYPE
        SYNTAX	INTEGER
        ACCESS	read-only
        STATUS	mandatory
        DESCRIPTION
                "Slot number on which this peer entry is configured"
        ::= { wfBotPeerEntry 3 }

    wfBotPeerCctNumber OBJECT-TYPE
        SYNTAX	INTEGER
        ACCESS	read-only
        STATUS	mandatory
        DESCRIPTION
                "The circuit from which the connection attempt is
                received that initiates a translation session."
        ::= { wfBotPeerEntry 4 }

    wfBotPeerRemoteIpAddr OBJECT-TYPE
        SYNTAX	IpAddress
        ACCESS	read-only
        STATUS	mandatory
        DESCRIPTION
                "IP Address of the remote host with which this translation
                session is established."
        ::= { wfBotPeerEntry 5 }

    wfBotConnOriginator OBJECT-TYPE
        SYNTAX	INTEGER {
    		    self(1),
    		    partner(2)
    		}
        ACCESS	read-only
        STATUS	mandatory
        DESCRIPTION
                "Upon start up, based on the configuration either
                partner is going to initiate TCP conn. or myself"
        ::= { wfBotPeerEntry 6 }

    wfBotPeerLocalTcpListenPort OBJECT-TYPE
        SYNTAX	INTEGER(1000..9999)
        ACCESS	read-only
        STATUS	mandatory
        DESCRIPTION
                "Based on the field wfBotConnOriginator, SiteManager
                will allow user to configure only one of following two fields:

                if Originator = SELF  then
                   through SiteManager ask user to enter PeerTcpListenPort#
                else
                   through SiteManager ask user to enter LocalTcpListenPort#

                So, in any case one of the two fields will have NULL_VALUE."
        ::= { wfBotPeerEntry 7 }

    wfBotPeerRemoteTcpListenPort OBJECT-TYPE
        SYNTAX	INTEGER(1000..9999)
        ACCESS	read-only
        STATUS	mandatory
        DESCRIPTION
                "Peer listen port for TCP connection"
        ::= { wfBotPeerEntry 8 }

    wfBotPeerLocalTcpPort OBJECT-TYPE
        SYNTAX	INTEGER(1000..9999)
        ACCESS	read-only
        STATUS	mandatory
        DESCRIPTION
                "When TCP connection is established, we will have other TCP
                port number available which is assigned by the system from
                the available pool. We will fill in this information here
                in this READ_ONLY variable. Again, based on Originator
                only one of the following two fields will have valid value.
                if Originator = SELF then
                    fill in LocalTcpPort field inside the BOT module
                else
                    fill in PeerTcpPort field inside the BOT module

                In short,
                =========
                For Originator = SELF
                    PeerTcpListenPort and LocalTcpPort  entries are valid
                For Originator = PARTNER
                    LocalTcpListenPort and PeerTcpPort  entries are valid"
        ::= { wfBotPeerEntry 9 }

    wfBotPeerRemoteTcpPort OBJECT-TYPE
        SYNTAX	INTEGER(1000..9999)
        ACCESS	read-only
        STATUS	mandatory
        DESCRIPTION
                "Peer TCP port of the connection"
        ::= { wfBotPeerEntry 10 }

    wfBotCUTable OBJECT-TYPE
        SYNTAX	SEQUENCE OF WfBotCUEntry
        ACCESS	not-accessible
        STATUS	mandatory
        DESCRIPTION
                "CU table lists all CUs reachable from this router on all
                TCP connections listed in PEER_TABLE"
        ::= { wfBotGroup 4 }

    wfBotCUEntry OBJECT-TYPE
        SYNTAX	WfBotCUEntry
        ACCESS	not-accessible
        STATUS	mandatory
        DESCRIPTION
                "An entry in wfBotCUTable"
        INDEX	{ wfBotCUSlotNumber,
    		  wfBotCUCctNumber,
    		  wfBotCURemoteIpAddr,
    		  wfBotCULocalTcpListenPort,
    		  wfBotCURemoteTcpListenPort,
    		  wfBotCUAddrReachable }
        ::= { wfBotCUTable 1 }

    WfBotCUEntry ::= SEQUENCE {
    	    wfBotCUEntryDelete
    		INTEGER,
    	    wfBotCUEntryDisable
    		INTEGER,
    	    wfBotCUSlotNumber
    		INTEGER,
    	    wfBotCUCctNumber
    		INTEGER,
    	    wfBotCURemoteIpAddr
    		IpAddress,
    	    wfBotCULocalTcpListenPort
    		INTEGER,
    	    wfBotCURemoteTcpListenPort
    		INTEGER,
    	    wfBotCUAddrReachable
    		INTEGER
        }

    wfBotCUEntryDelete OBJECT-TYPE
        SYNTAX	INTEGER {
    		    created(1),
    		    deleted(2)
    		}
        ACCESS	read-write
        STATUS	mandatory
        DESCRIPTION
                "Create/Delete attribute. Default is Created
                Users perform SNMP SET operation on this object in
                order to create/delete a peer record"
        DEFVAL	{ created }
        ::= { wfBotCUEntry 1 }

    wfBotCUEntryDisable OBJECT-TYPE
        SYNTAX	INTEGER {
    		    enabled(1),
    		    disabled(2)
    		}
        ACCESS	read-write
        STATUS	mandatory
        DESCRIPTION
                "Enables/Disables this cu entry
                Setting of this attribute to DISABLED will disconnect
                active TCP conn. pertaining to the peer entry"
        DEFVAL	{ enabled }
        ::= { wfBotCUEntry 2 }

    wfBotCUSlotNumber OBJECT-TYPE
        SYNTAX	INTEGER
        ACCESS	read-only
        STATUS	mandatory
        DESCRIPTION
                "slot number used as an index"
        ::= { wfBotCUEntry 3 }

    wfBotCUCctNumber OBJECT-TYPE
        SYNTAX	INTEGER
        ACCESS	read-only
        STATUS	mandatory
        DESCRIPTION
                "The circuit from which the connection attempt is
                CCT number for easy link between peer table and cu table"
        ::= { wfBotCUEntry 4 }

    wfBotCURemoteIpAddr OBJECT-TYPE
        SYNTAX	IpAddress
        ACCESS	read-only
        STATUS	mandatory
        DESCRIPTION
                "IP Address of the remote host with which this translation
                session is established."
        ::= { wfBotCUEntry 5 }

    wfBotCULocalTcpListenPort OBJECT-TYPE
        SYNTAX	INTEGER(1000..9999)
        ACCESS	read-only
        STATUS	mandatory
        DESCRIPTION
                "As mentioned earlier only one of following two field will
                have a valid value, while other will be NULL_VAL, based on
                who is the ConnOriginator"
        ::= { wfBotCUEntry 6 }

    wfBotCURemoteTcpListenPort OBJECT-TYPE
        SYNTAX	INTEGER(1000..9999)
        ACCESS	read-only
        STATUS	mandatory
        DESCRIPTION
                "field from the peer table entry"
        ::= { wfBotCUEntry 7 }

    wfBotCUAddrReachable OBJECT-TYPE
        SYNTAX	INTEGER {
    		    address(254)
    		}
        ACCESS	read-only
        STATUS	mandatory
        DESCRIPTION
                "In BISYNC controller addresses range from 0-31. In MDL
                currently there is no way to represent the integer range.
                As lower bound is zero, here we specify only max possible"
        ::= { wfBotCUEntry 8 }

END  -- Wellfleet-BOT-MIB
