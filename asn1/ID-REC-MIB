ID-REC-MIB    DEFINITIONS ::= BEGIN
    IMPORTS
        enterprises    FROM RFC1155-SMI;
        
    marconi                          OBJECT IDENTIFIER ::= { enterprises 326 }
    systems                          OBJECT IDENTIFIER ::= { marconi 2 }
    external                         OBJECT IDENTIFIER ::= { systems 20 }
    dlink                            OBJECT IDENTIFIER ::= { external 1 }
    golf                             OBJECT IDENTIFIER ::= { dlink 2 }
    golfcommon                       OBJECT IDENTIFIER ::= { golf 2 }
    marconi-products                 OBJECT IDENTIFIER ::= { golfcommon 1 }
    

    marconi-es1000Prod               OBJECT IDENTIFIER ::= { marconi-products 24 }

    es1000DevRegistration            OBJECT IDENTIFIER ::= { marconi-es1000Prod 2 }
        es1000Device                     OBJECT IDENTIFIER ::= { es1000DevRegistration 1 }
    
    es1000UnitRegistration           OBJECT IDENTIFIER ::= { marconi-es1000Prod 3 }
        es1000Unit                       OBJECT IDENTIFIER ::= { es1000UnitRegistration 1 }
                   
    es1000ModuleRegistration         OBJECT IDENTIFIER ::= { marconi-es1000Prod 4 }
        es1000Module-Mainboard-22Port    OBJECT IDENTIFIER ::= { es1000ModuleRegistration 1 }
        es1000Module-362TX-2Ports        OBJECT IDENTIFIER ::= { es1000ModuleRegistration 2 }
        es1000Module-361FX-1Port         OBJECT IDENTIFIER ::= { es1000ModuleRegistration 3 }
        es1000Module-362FM-2Ports        OBJECT IDENTIFIER ::= { es1000ModuleRegistration 4 }
        es1000Module-3251G-1Port         OBJECT IDENTIFIER ::= { es1000ModuleRegistration 5 }
        es1000Module-3251GL-1Port        OBJECT IDENTIFIER ::= { es1000ModuleRegistration 6 }
        es1000Module-321GT-1Port         OBJECT IDENTIFIER ::= { es1000ModuleRegistration 7 }

    es1000PortRegistration           OBJECT IDENTIFIER ::= { marconi-es1000Prod 5 }
        es1000Port-10/100TX              OBJECT IDENTIFIER ::= { es1000PortRegistration 1 }
        es1000Port-100-SC                OBJECT IDENTIFIER ::= { es1000PortRegistration 2 }
        es1000Port-100-MTRJ              OBJECT IDENTIFIER ::= { es1000PortRegistration 3 }
        es1000Port-1000-SX               OBJECT IDENTIFIER ::= { es1000PortRegistration 4 }
        es1000Port-1000-LX               OBJECT IDENTIFIER ::= { es1000PortRegistration 5 }
        es1000Port-1000-TX               OBJECT IDENTIFIER ::= { es1000PortRegistration 6 }

    es1000PowerSupplyRegistration    OBJECT IDENTIFIER ::= { marconi-es1000Prod 6 }
        es1000PowerSupply                OBJECT IDENTIFIER ::= { es1000PowerSupplyRegistration 1 }

    es1000FanRegistration            OBJECT IDENTIFIER ::= { marconi-es1000Prod 7 }
        es1000Fan                        OBJECT IDENTIFIER ::= { es1000FanRegistration 1 }

    es1000SlotRegistration           OBJECT IDENTIFIER ::= { marconi-es1000Prod 8 }
        es1000Slot1                      OBJECT IDENTIFIER ::= { es1000SlotRegistration 1 }
        es1000Slot2                      OBJECT IDENTIFIER ::= { es1000SlotRegistration 2 }

    es1000SensorRegistration         OBJECT IDENTIFIER ::= { marconi-es1000Prod 9 }

    es1000BackplaneRegistration      OBJECT IDENTIFIER ::= { marconi-es1000Prod 10 }

END
