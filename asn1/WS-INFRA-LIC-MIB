WS-INFRA-LIC-MIB DEFINITIONS ::= BEGIN
 
		IMPORTS
			OBJECT-GROUP, MODULE-COMPLIANCE			
				FROM SNMPv2-CONF			
			Integer32, Unsigned32, OBJECT-TYPE, MODULE-IDENTITY			
				FROM SNMPv2-SMI			
			DisplayString			
				FROM SNMPv2-TC			
			wsInfraLic			
				FROM WS-INFRA-SMI-MIB;

		-- 1.3.6.1.4.1.388.14.1.9.1
		wsInfraLicMib MODULE-IDENTITY 
			LAST-UPDATED "200506231126Z"		-- June 23, 2005 at 11:26 GMT
			ORGANIZATION 
				"Symbol Technologies"
			CONTACT-INFO 
				"Symbol Technologies, Inc.
				Customer Service
				Postal:
				One Symbol Plaza
				Holtsville, NY 11742-1300
				USA
				Tel: +1. 631.738.6213
				E-mail: support@symbol.com
				Web: http://www.symbol.com/support"
			DESCRIPTION 
				"License management MIB."
			REVISION "200702071127Z"		-- February 07, 2007 at 11:27 GMT
			DESCRIPTION 
				"01a07"
			REVISION "200605241519Z"		-- May 24, 2006 at 15:19 GMT
			DESCRIPTION 
				"01a06"
			REVISION "200605011436Z"		-- May 01, 2006 at 14:36 GMT
			DESCRIPTION 
				"01a05"
			REVISION "200604281416Z"		-- April 28, 2006 at 14:16 GMT
			DESCRIPTION 
				"01a04"
			REVISION "200506271708Z"		-- June 27, 2005 at 17:08 GMT
			DESCRIPTION 
				"01a03"
			REVISION "200506221510Z"		-- June 22, 2005 at 15:10 GMT
			DESCRIPTION 
				"01a02"
			REVISION "200506221127Z"		-- June 22, 2005 at 11:27 GMT
			DESCRIPTION 
				"01a01"
			::= { wsInfraLic 1 }

		-- 1.3.6.1.4.1.388.14.1.9.1.1
		wsInfraAPLicNum OBJECT-TYPE
			SYNTAX Unsigned32
			MAX-ACCESS read-only
			STATUS current
			DESCRIPTION
				"A parameter associated with the number of licenses for the APs."
			::= { wsInfraLicMib 1 }

		-- 1.3.6.1.4.1.388.14.1.9.1.2
		wsInfraLicMgmt OBJECT IDENTIFIER ::= { wsInfraLicMib 2 }

		-- 1.3.6.1.4.1.388.14.1.9.1.2.1
		wsInfraLicNum OBJECT-TYPE
			SYNTAX Unsigned32
			MAX-ACCESS read-only
			STATUS current
			DESCRIPTION
				"Number of license types currently registered with the License
				Manager.  Effectively, this count reports on the number of rows
				in the license table."
			::= { wsInfraLicMgmt 1 }

		-- 1.3.6.1.4.1.388.14.1.9.1.2.2
		wsInfraLicActionFeature OBJECT-TYPE
			SYNTAX OCTET STRING (SIZE (0..15))
			MAX-ACCESS read-write
			STATUS current
			DESCRIPTION
				"Description."
			::= { wsInfraLicMgmt 2 }

		-- 1.3.6.1.4.1.388.14.1.9.1.2.3
		wsInfraLicActionKey OBJECT-TYPE
			SYNTAX OCTET STRING (SIZE (0..40))
			MAX-ACCESS read-write
			STATUS current
			DESCRIPTION
				"This object provides an entry point by which the License Manager
				receives instruction to alter the list of recognised licenses.
				Alterations are, for this entry point, limited to:
				
				1. addition of new license types, (a row in the license table);
				
				2. update of the count field of a license table row."
			::= { wsInfraLicMgmt 3 }

		-- 1.3.6.1.4.1.388.14.1.9.1.2.4
		wsInfraLicAction OBJECT-TYPE
			SYNTAX Integer32 (1..2)
			MAX-ACCESS read-write
			STATUS current
			DESCRIPTION
				"This object provides an entry point by which the License Manager
				receives instruction to alter the list of recognised licenses.
				Alteration are, for this entry point, limited to:
				
				1. deletion of license types, (a row of the license table)."
			::= { wsInfraLicMgmt 4 }

		-- 1.3.6.1.4.1.388.14.1.9.1.2.5
		wsInfraLicTable OBJECT-TYPE
			SYNTAX SEQUENCE OF WsInfraLicEntry
			MAX-ACCESS not-accessible
			STATUS current
			DESCRIPTION
				"This object represents a table of licenses that are know to the
				License Manager.  Licenses become known to the License Manager
				by means of license key submittal.  The submittal of a key that
				is unknown to the License Manager causes the creation of a row
				in this object.  The submittal of a known license key causes an
				update of the entries of the corresponding table row.
				
				NB - There is a one-to-one relationship between licenses and
				     table rows."
			::= { wsInfraLicMgmt 5 }

		-- 1.3.6.1.4.1.388.14.1.9.1.2.5.1
		wsInfraLicEntry OBJECT-TYPE
			SYNTAX WsInfraLicEntry
			MAX-ACCESS not-accessible
			STATUS current
			DESCRIPTION
				"A row of the license table."
			INDEX { wsInfraLicIndex }
			::= { wsInfraLicTable 1 }

		WsInfraLicEntry ::=
			SEQUENCE { 
				wsInfraLicIndex
					OCTET STRING,
				wsInfraLicFeature
					OCTET STRING,
				wsInfraLicKey
					OCTET STRING,
				wsInfraLicCount
					Integer32,
				wsInfraLicUsage
					Integer32
			 }

		-- 1.3.6.1.4.1.388.14.1.9.1.2.5.1.1
		wsInfraLicIndex OBJECT-TYPE
			SYNTAX OCTET STRING (SIZE (0..15))
			MAX-ACCESS not-accessible
			STATUS current
			DESCRIPTION
				"This object contains a character-coded representation of
				the license type, and is used as the license table index."
			::= { wsInfraLicEntry 1 }

		-- 1.3.6.1.4.1.388.14.1.9.1.2.5.1.2
		wsInfraLicFeature OBJECT-TYPE
			SYNTAX OCTET STRING (SIZE (0..15))
			MAX-ACCESS read-only
			STATUS current
			DESCRIPTION
				"The object contains a character-coded representation of
				the license type, and is also known as the *feature*."
			::= { wsInfraLicEntry 2 }

		-- 1.3.6.1.4.1.388.14.1.9.1.2.5.1.3
		wsInfraLicKey OBJECT-TYPE
			SYNTAX OCTET STRING (SIZE (0..40))
			MAX-ACCESS read-only
			STATUS current
			DESCRIPTION
				"This objecdt represents the key recognised by the License
				Manager for the feature described by the corresponding
				row of the license table."
			::= { wsInfraLicEntry 3 }

		-- 1.3.6.1.4.1.388.14.1.9.1.2.5.1.4
		wsInfraLicCount OBJECT-TYPE
			SYNTAX Integer32
			MAX-ACCESS read-only
			STATUS current
			DESCRIPTION
				"This object represents the number of licenses known to the
				License Manager for the license type of the corresponding
				row of the license table.  This number is the upper limit
				on the number of access points that the switch is allowed
				to support at any one time.
				
				NB - This value is specific to AP licensing, only."
			DEFVAL { 0 }
			::= { wsInfraLicEntry 4 }

		-- 1.3.6.1.4.1.388.14.1.9.1.2.5.1.5
		wsInfraLicUsage OBJECT-TYPE
			SYNTAX Integer32
			MAX-ACCESS read-only
			STATUS current
			DESCRIPTION
				"This object represents the current usage of the license
				type of the correpsonding row of the license table.  This
				value ranges from zero to the value of the license count,
				inclusively.
				
				NB - This value could exceed the license count, within
				     some cluster configurations.
				
				     See cluster statistics."
			DEFVAL { 0 }
			::= { wsInfraLicEntry 5 }

		-- 1.3.6.1.4.1.388.14.1.9.1.2.6
		wsInfraLicSerialNumber OBJECT-TYPE
			SYNTAX DisplayString
			MAX-ACCESS read-only
			STATUS current
			DESCRIPTION
				"The serial number of the wireless switch. This is used in the
				generation of the license key."
			::= { wsInfraLicMgmt 6 }

		-- 1.3.6.1.4.1.388.14.1.9.1.100
		wsInfraLicMIBConformance OBJECT IDENTIFIER ::= { wsInfraLicMib 100 }

		-- 1.3.6.1.4.1.388.14.1.9.1.100.1
		wsInfraLicMIBCompliances OBJECT IDENTIFIER ::= { wsInfraLicMIBConformance 1 }

		-- 1.3.6.1.4.1.388.14.1.9.1.100.1.1
		wsInfraLicMIBCompliance MODULE-COMPLIANCE
			STATUS current
			DESCRIPTION 
				"Description."
			MODULE -- this module
				MANDATORY-GROUPS { wsInfraLicMIBGroup }
			::= { wsInfraLicMIBCompliances 1 }

		-- 1.3.6.1.4.1.388.14.1.9.1.100.2
		wsInfraLicMIBGroups OBJECT IDENTIFIER ::= { wsInfraLicMIBConformance 2 }

		-- 1.3.6.1.4.1.388.14.1.9.1.100.2.1
		wsInfraLicMIBGroup OBJECT-GROUP
			OBJECTS { wsInfraAPLicNum }
			STATUS current
			DESCRIPTION 
				"Description."
			::= { wsInfraLicMIBGroups 1 }

		-- 1.3.6.1.4.1.388.14.1.9.1.100.2.2
		wsInfraLicMgmtGroup OBJECT-GROUP
			OBJECTS { wsInfraLicNum, wsInfraLicFeature, wsInfraLicActionKey, wsInfraLicAction, wsInfraLicUsage, 
				wsInfraLicKey, wsInfraLicSerialNumber, wsInfraAPLicNum, wsInfraLicCount, wsInfraLicActionFeature
				 }
			STATUS current
			DESCRIPTION 
				"The License Management group of objects."
			::= { wsInfraLicMIBGroups 2 }
	END
