SUN-SNMP-NETRA-CT-RSC-MIB DEFINITIONS ::= BEGIN

IMPORTS
     MODULE-IDENTITY, 
     OBJECT-TYPE, 
     IpAddress, 
     NOTIFICATION-TYPE 	FROM SNMPv2-SMI
     DisplayString, 
     MacAddress 	FROM SNMPv2-TC
     enterprises	FROM RFC1155-SMI;

netraCtRscMIB MODULE-IDENTITY
     LAST-UPDATED 	"0004181200Z"
     ORGANIZATION 	""
     CONTACT-INFO	""
     DESCRIPTION
         "The MIB module for the Netra ct 400/800 Remote System 
	  Control Products"
     REVISION 		"0004181200Z"
     DESCRIPTION "First version of MIB module SUN-SNMP-NETRA-CT-RSC-MIB."

     ::= { enterprises sun(42) prod(2) netract(65) 2 }
-- SMC uses prod, not products
--     ::= { enterprises sun(42) products(2) netract(65) 2 }


netraCtRscObjs		OBJECT IDENTIFIER ::= { netraCtRscMIB 1 }
netraCtRscEvents	OBJECT IDENTIFIER ::= { netraCtRscMIB 2 }
netraCtRscExpmnt	OBJECT IDENTIFIER ::= { netraCtRscMIB 3 }

netraCtRscAdminObjs	OBJECT IDENTIFIER ::= { netraCtRscObjs 1 }
netraCtRscConfigObjs	OBJECT IDENTIFIER ::= { netraCtRscObjs 2 }
netraCtRscSerial2Objs	OBJECT IDENTIFIER ::= { netraCtRscObjs 3 }
netraCtRscModemObjs	OBJECT IDENTIFIER ::= { netraCtRscObjs 4 }
netraCtRscEnetObjs	OBJECT IDENTIFIER ::= { netraCtRscObjs 5 }
netraCtRscEnvObjs 	OBJECT IDENTIFIER ::= { netraCtRscObjs 6 }
netraCtRscLogObjs 	OBJECT IDENTIFIER ::= { netraCtRscObjs 7 }
netraCtRscRccConfig	OBJECT IDENTIFIER ::= { netraCtRscExpmnt 1 }
netraCtRscTrapPrefix    OBJECT IDENTIFIER ::= { netraCtRscEvents 0 }

-- Type Definitions

DateAndTime ::= OCTET STRING (SIZE (11))

-- NetraCtRSC Admin Objects

netraCtRscAdminRscReset OBJECT-TYPE
     SYNTAX      INTEGER { set(1), clear(2), notimpl(2147483647) }
     MAX-ACCESS  read-write
     STATUS      current
     DESCRIPTION
         "Setting this will  soft Reset only the RSC 
          (Remote System Controller) card. 
					 The clear(2) setting is read-only for this variable. This 
           variable will always read as clear(2)."
     ::= { netraCtRscAdminObjs 1 }

netraCtRscAdminHostReset OBJECT-TYPE
     SYNTAX      INTEGER { set(1), clear(2), notimpl(2147483647) }
     MAX-ACCESS  read-write
     STATUS      current
     DESCRIPTION
	 "Setting netraCtRscAdminHostReset will cause either send
	  a break to the host, or will toggle a hard reset line.
		A break will be sent if netraCtRscPanicDump conatins the
		value of on(1).Otherwise, a hard reset will occur.
		The clear(2) setting is read-only for this variable.
	  This variable will always reads as clear(2)."
     ::= { netraCtRscAdminObjs 2 }

netraCtRscAdminXir OBJECT-TYPE
     SYNTAX      INTEGER { set(1), clear(2), notimpl(2147483647) }
     MAX-ACCESS  read-write
     STATUS      current
     DESCRIPTION
         "Sends a hardware xir pulse to the host when
	  set to true.  This variable resets itself to clear(2)
	  after the negation of the pulse."
     ::= { netraCtRscAdminObjs 3 }

netraCtRscAdminNmi OBJECT-TYPE
     SYNTAX      INTEGER { set(1), clear(2), notimpl(2147483647) }
     MAX-ACCESS  read-write
     STATUS      current
     DESCRIPTION
         "Sends a hardware nmi pulse to the host when 
	  set to true.  This variable resets itself to clear(2)
	  after the negation of the pulse."
     ::= { netraCtRscAdminObjs 4 }

netraCtRscAdminBreak OBJECT-TYPE
     SYNTAX      INTEGER { set(1), clear(2), notimpl(2147483647) }
     MAX-ACCESS  read-write
     STATUS      current
     DESCRIPTION
         "Sends a break to the Host when this is set.
					The clear(2) setting is read-only for this variable.
					This variable will always read as clear(2)."
     ::= { netraCtRscAdminObjs 5 }


-- NetraCtRSC General Configuration Objects

netraCtRscGlobalPageFlag OBJECT-TYPE
     SYNTAX      INTEGER { on(1), off(2), notimpl(2147483647) }
     MAX-ACCESS  read-write
     STATUS      current
     DESCRIPTION
         "An on(1) to this variable will enable paging for RSC alerts.
					An off(2) will disable paging."
     ::= { netraCtRscConfigObjs 1 }

netraCtRscGlobalEmailFlag OBJECT-TYPE
     SYNTAX      INTEGER { on(1), off(2), notimpl(2147483647) }
     MAX-ACCESS  read-write
     STATUS      current
     DESCRIPTION
         "An on(1) to this variable will enable email for RSC alerts.
					An off(2) will disable email."
     ::= { netraCtRscConfigObjs 2 }

netraCtRscGlobalIPModeFlag OBJECT-TYPE
     SYNTAX      INTEGER { disabled(1), config(2), dhcp(3), 
			   notimpl(2147483647) }
     MAX-ACCESS  read-write
     STATUS      current
     DESCRIPTION
         "IP mode global flag"
     ::= { netraCtRscConfigObjs 3 }

netraCtRscGlobalPPPFlag OBJECT-TYPE
     SYNTAX      INTEGER { on(1), off(2), notimpl(2147483647) }
     MAX-ACCESS  read-write
     STATUS      current
     DESCRIPTION
         "serial configuration flag indicating whether PPP should be 
	  the default."
     ::= { netraCtRscConfigObjs 4 }

netraCtRscHostname OBJECT-TYPE
     SYNTAX      DisplayString (SIZE (1..40))
     MAX-ACCESS  read-write
     STATUS      current
     DESCRIPTION
         "name of Host connected to RSC"
     ::= { netraCtRscConfigObjs 5 }

netraCtRscCustomerInfo OBJECT-TYPE
     SYNTAX      DisplayString (SIZE (1..40))
     MAX-ACCESS  read-write
     STATUS      current
     DESCRIPTION
         "Customer information used in the message generated for a pager
					or email alert"
     ::= { netraCtRscConfigObjs 6 }
 
netraCtRscVersionBootMajor OBJECT-TYPE
     SYNTAX      INTEGER (0..255)
     MAX-ACCESS  read-only
     STATUS      current
     DESCRIPTION
         "RSC Firmware BootMonitor Revision Major Number"
     ::= { netraCtRscConfigObjs 7 }

netraCtRscVersionBootMinor OBJECT-TYPE
     SYNTAX      INTEGER (0..255)
     MAX-ACCESS  read-only
     STATUS      current
     DESCRIPTION
         "RSC Firmware BootMonitor Revision Minor Number"
     ::= { netraCtRscConfigObjs 8 }

netraCtRscVersionBootMicro OBJECT-TYPE
     SYNTAX      INTEGER (0..255)
     MAX-ACCESS  read-only
     STATUS      current
     DESCRIPTION
          "RSC Firmware BootMonitor Revision Micro Number"
     ::= { netraCtRscConfigObjs 9 }


netraCtRscVersionMainMajor OBJECT-TYPE
     SYNTAX      INTEGER (0..255)
     MAX-ACCESS  read-only
     STATUS      current
     DESCRIPTION
         "RSC Core RSC Revision Major Number"
     ::= { netraCtRscConfigObjs 10 }

netraCtRscVersionMainMinor OBJECT-TYPE
     SYNTAX      INTEGER (0..255)
     MAX-ACCESS  read-only
     STATUS      current
     DESCRIPTION
         "RSC Core RSC Revision Minor Number"
     ::= { netraCtRscConfigObjs 11 }

netraCtRscVersionMainMicro OBJECT-TYPE
      SYNTAX      INTEGER (0..255)
      MAX-ACCESS  read-only
      STATUS      current
      DESCRIPTION
          "RSC Core RSC Revision Micro Number"
      ::= { netraCtRscConfigObjs 12 }

netraCtRscVersionFirmwareMajor OBJECT-TYPE
      SYNTAX      INTEGER (0..255)
      MAX-ACCESS  read-only
      STATUS      current
      DESCRIPTION
          "RSC Core Firmware Revision Major Number"
      ::= { netraCtRscConfigObjs 13 }

netraCtRscVersionFirmwareMinor OBJECT-TYPE
      SYNTAX      INTEGER (0..255)
      MAX-ACCESS  read-only
      STATUS      current
      DESCRIPTION
          "RSC Core Firmware Revision Minor Number"
      ::= { netraCtRscConfigObjs 14 }

netraCtRscVersionFirmwareMicro OBJECT-TYPE
      SYNTAX      INTEGER (0..255)
      MAX-ACCESS  read-only
      STATUS      current
      DESCRIPTION
          "RSC Core Firmware Revision Micro Number"
      ::= { netraCtRscConfigObjs 15 }

netraCtRscTOD OBJECT-TYPE
     SYNTAX      DateAndTime
     MAX-ACCESS  read-write
     STATUS      current
     DESCRIPTION
         "RSC time of day"
     ::= { netraCtRscConfigObjs 16 }

netraCtRscEscape OBJECT-TYPE
     SYNTAX      DisplayString (SIZE (1))
     MAX-ACCESS  read-write
     STATUS      current
     DESCRIPTION
         "set the first character of the 2-character escape sequence"
     ::= { netraCtRscConfigObjs 17 }

netraCtRscHostWatchDogReboot OBJECT-TYPE
     SYNTAX      INTEGER { on(1), off(2), notimpl(2147483647) }
     MAX-ACCESS  read-write
     STATUS      current
     DESCRIPTION
         "RSC monitors a heartbeat from the Solaris host. 
	  If this heartbeat is late, then a message will be 
	  logged, and an alarm will be set.  If 
	  netraCtRscHostWatchDogReboot is on, then the solaris 
	  host will also be rebooted."
     ::= { netraCtRscConfigObjs 18 }

netraCtRscHostWatchDogTimeout OBJECT-TYPE
     SYNTAX      INTEGER (0..2147483647)
     MAX-ACCESS  read-write
     STATUS      current
     DESCRIPTION
         "RSC monitors a heartbeat from the Solaris host. 
	  This variable indicates the maximum tolerable 
	  number of seconds between heartbeats, before RSC will
	  set alarm0.  A setting of 0 indicates that the heartbeat 
	  should not be monitored."
     ::= { netraCtRscConfigObjs 19 }

netraCtRscPanicDump OBJECT-TYPE
     SYNTAX      INTEGER { on(1), off(2), notimpl(2147483647) }
     MAX-ACCESS  read-write
     STATUS      current
     DESCRIPTION
         "If set to true when netraCtRscAdminHostReset is set, then
	  a break will be sent to the host, causing a core dump to
	  be saved on the host.  Otherwise, the setting of
	  netraCtRscAdminHostReset will cause a hardware reset."
     ::= { netraCtRscConfigObjs 20 }


-- NetraCtRSC Serial2 Objects

netraCtRscSerial2Mode OBJECT-TYPE
     SYNTAX      INTEGER { rcc(1), modem(2), tty(3), disabled(4), 
			   notimpl(2147483647) }
     MAX-ACCESS  read-write
     STATUS      current
     DESCRIPTION
         "serial port 2 configuration mode."
     ::= { netraCtRscSerial2Objs 1 }

netraCtRscSerial2Parity OBJECT-TYPE
     SYNTAX      INTEGER { none(1), odd(2), even(3), notimpl(2147483647) }
     MAX-ACCESS  read-write
     STATUS      current
     DESCRIPTION
         "serial port 2 parity mode."
     ::= { netraCtRscSerial2Objs 2 }

netraCtRscSerial2Stop OBJECT-TYPE
     SYNTAX      INTEGER { one(1), two(2), notimpl(2147483647) }
     MAX-ACCESS  read-write
     STATUS      current
     DESCRIPTION
         "serial port 2 stop bits."
     ::= { netraCtRscSerial2Objs 3 }

netraCtRscSerial2Data OBJECT-TYPE
     SYNTAX      INTEGER { seven(1), eight(2), notimpl(2147483647) }
     MAX-ACCESS  read-write
     STATUS      current
     DESCRIPTION
         "serial port 2 data bits."
     ::= { netraCtRscSerial2Objs 4 }

netraCtRscSerial2Baud OBJECT-TYPE
     SYNTAX      INTEGER {
                         b300(1),
                         b1200(2),
                         b1800(3),
                         b2400(4),
                         b4800(5),
                         b9600(6),
                         b19200(7),
                         b38400(8),
                         b57600(9),
                         b115200(10),
			 notimpl(2147483647)
                 }
     MAX-ACCESS  read-write
     STATUS      current
     DESCRIPTION
         "serial port 2 baud rate."
     ::= { netraCtRscSerial2Objs 5 }

netraCtRscSerial2HwFlowcontrol OBJECT-TYPE
     SYNTAX      INTEGER { on(1), off(2), notimpl(2147483647) }
     MAX-ACCESS  read-write
     STATUS      current
     DESCRIPTION
         "serial port 2 Hardware Flowcontrol."
     ::= { netraCtRscSerial2Objs 6 }

netraCtRscSerial2Inactivity OBJECT-TYPE
     SYNTAX      INTEGER { on(1), off(2), notimpl(2147483647) }
     MAX-ACCESS  read-write
     STATUS      current
     DESCRIPTION
         "serial port 2 inactivity."
     ::= { netraCtRscSerial2Objs 7 }

-- NetraCtRSC Serial2 Modem Configuration Objects

netraCtRscSerial2PagerOneConfig OBJECT-TYPE
     SYNTAX      DisplayString (SIZE (1..40))
     MAX-ACCESS  read-write
     STATUS      current
     DESCRIPTION
         "primary pager number for RSC."
     ::= { netraCtRscSerial2Objs 8 }


netraCtRscSerial2PagerTwoConfig OBJECT-TYPE
     SYNTAX      DisplayString (SIZE (1..40))
     MAX-ACCESS  read-write
     STATUS      current
     DESCRIPTION
         "secondary pager number for RSC"
     ::= { netraCtRscSerial2Objs 9 }

netraCtRscSerial2PagerOneBaud OBJECT-TYPE
     SYNTAX      INTEGER {
                         b300(1),
                         b1200(2),
                         b2400(3),
                         b4800(4),
                         b9600(5),
			 notimpl(2147483647)
                 }
     MAX-ACCESS  read-write
     STATUS      current
     DESCRIPTION
         "primary pager baud rate."
     ::= { netraCtRscSerial2Objs 10 }

netraCtRscSerial2PagerTwoBaud OBJECT-TYPE
     SYNTAX      INTEGER {
                         b300(1),
                         b1200(2),
                         b2400(3),
                         b4800(4),
                         b9600(5),
			 notimpl(2147483647)
                 }
     MAX-ACCESS  read-write
     STATUS      current
     DESCRIPTION
         "secondary pager baud rate."
     ::= { netraCtRscSerial2Objs 11 }

netraCtRscSerial2PagerOneParity OBJECT-TYPE
     SYNTAX      INTEGER { none(1), odd(2), even(3), 
			   notimpl(2147483647) }
     MAX-ACCESS  read-write
     STATUS      current
     DESCRIPTION
         "primary pager parity mode."
     ::= { netraCtRscSerial2Objs 12 }

netraCtRscSerial2PagerTwoParity OBJECT-TYPE
     SYNTAX      INTEGER { none(1), odd(2), even(3), 
			   notimpl(2147483647) }
     MAX-ACCESS  read-write
     STATUS      current
     DESCRIPTION
         "secondary pager parity mode."
     ::= { netraCtRscSerial2Objs 13 }

netraCtRscSerial2PagerOneStop OBJECT-TYPE
     SYNTAX      INTEGER { one(1), two(2), notimpl(2147483647) }
     MAX-ACCESS  read-write
     STATUS      current
     DESCRIPTION
         "primary pager stop bits."
     ::= { netraCtRscSerial2Objs 14 }

netraCtRscSerial2PagerTwoStop OBJECT-TYPE
     SYNTAX      INTEGER { one(1), two(2), notimpl(2147483647) }
     MAX-ACCESS  read-write
     STATUS      current
     DESCRIPTION
         "secondary pager stop bits."
     ::= { netraCtRscSerial2Objs 15 }

netraCtRscSerial2PagerOneData OBJECT-TYPE
     SYNTAX      INTEGER { seven(1), eight(2), notimpl(2147483647) }
     MAX-ACCESS  read-write
     STATUS      current
     DESCRIPTION
         "primary pager data bits."
     ::= { netraCtRscSerial2Objs 16 }

netraCtRscSerial2PagerTwoData OBJECT-TYPE
     SYNTAX      INTEGER { seven(1), eight(2), notimpl(2147483647) }
     MAX-ACCESS  read-write
     STATUS      current
     DESCRIPTION
         "secondary pager data bits."
     ::= { netraCtRscSerial2Objs 17 }

netraCtRscSerial2PagerOneInit OBJECT-TYPE
     SYNTAX      DisplayString (SIZE (1..30))
     MAX-ACCESS  read-write
     STATUS      current
     DESCRIPTION
         "primary pager modem init string."
     ::= { netraCtRscSerial2Objs 18 }

netraCtRscSerial2PagerTwoInit OBJECT-TYPE
     SYNTAX      DisplayString (SIZE (1..30))
     MAX-ACCESS  read-write
     STATUS      current
     DESCRIPTION
         "secondary pager modem init string."
     ::= { netraCtRscSerial2Objs 19 }

netraCtRscSerial2PagerOnePassword OBJECT-TYPE
     SYNTAX      DisplayString (SIZE (1..8))
     MAX-ACCESS  read-write
     STATUS      current
     DESCRIPTION
         "primary pager TAP password."
     ::= { netraCtRscSerial2Objs 20 }

netraCtRscSerial2PagerTwoPassword OBJECT-TYPE
     SYNTAX      DisplayString (SIZE (1..8))
     MAX-ACCESS  read-write
     STATUS      current
     DESCRIPTION
         "secondary pager TAP password."
     ::= { netraCtRscSerial2Objs 21 }


-- NetraCtRSC PCMCIA Modem configuration group

netraCtRscModemParity OBJECT-TYPE
      SYNTAX      INTEGER { none(1), odd(2), even(3), 
			    notimpl(2147483647) }
      MAX-ACCESS  read-write
      STATUS      current
      DESCRIPTION
          "modem parity mode."
      ::= { netraCtRscModemObjs 1 }

netraCtRscModemStop OBJECT-TYPE
      SYNTAX      INTEGER { one(1), two(2), notimpl(2147483647) }
      MAX-ACCESS  read-write
      STATUS      current
      DESCRIPTION
          "modem stop bits."
      ::= { netraCtRscModemObjs 2 }

netraCtRscModemData OBJECT-TYPE
      SYNTAX      INTEGER { seven(1), eight(2), notimpl(2147483647) }
      MAX-ACCESS  read-write
      STATUS      current
      DESCRIPTION
          "modem data bits."
      ::= { netraCtRscModemObjs 3 }

netraCtRscCountryCode OBJECT-TYPE
      SYNTAX      INTEGER (0..2147483647)
      MAX-ACCESS  read-write
      STATUS      current
      DESCRIPTION
          "country specified using CCITT internaional dial-plan number."
      ::= { netraCtRscModemObjs 4 }

netraCtRscModemModel OBJECT-TYPE
      SYNTAX      DisplayString (SIZE (1..40))
      MAX-ACCESS  read-only
      STATUS      current
      DESCRIPTION
          "the modem type used on the netraCtRsc card."
      ::= { netraCtRscModemObjs 5 }


-- NetraCtRSC Ethernet Configuration Objects

netraCtRscMacAddress OBJECT-TYPE
     SYNTAX      MacAddress
     MAX-ACCESS  read-only
     STATUS      current
     DESCRIPTION
         "Ethernet address for RSC."
     ::= { netraCtRscEnetObjs 1 }

netraCtRscEnetTpeLinkTest OBJECT-TYPE
     SYNTAX      INTEGER { on(1), off(2), notimpl(2147483647) }
     MAX-ACCESS  read-write
     STATUS      current
     DESCRIPTION
         "Determines whether tpe-link-test should be set of clear.
	  This should be off when interfacing with older-style hubs
	  that don't support heartbeat."
     ::= { netraCtRscEnetObjs 2 }

netraCtRscIPAddress OBJECT-TYPE
     SYNTAX      IpAddress
     MAX-ACCESS  read-write
     STATUS      current
     DESCRIPTION
         "configured IP address for RSC."
     ::= { netraCtRscEnetObjs 3 }

netraCtRscIpMask OBJECT-TYPE
     SYNTAX      IpAddress
     MAX-ACCESS  read-write
     STATUS      current
     DESCRIPTION
         "configured IP netmask for RSC."
     ::= { netraCtRscEnetObjs 4 }

netraCtRscIpGateway OBJECT-TYPE
     SYNTAX      IpAddress
     MAX-ACCESS  read-write
     STATUS      current
     DESCRIPTION
         "configured IP gateway for RSC."
     ::= { netraCtRscEnetObjs 5 }

netraCtRscSNMPHostAddress OBJECT-TYPE
     SYNTAX      IpAddress
     MAX-ACCESS  read-write
     STATUS      current
     DESCRIPTION
         "configured SNMP server for RSC alerts."
     ::= { netraCtRscEnetObjs 6 }

netraCtRscMailHostAddress OBJECT-TYPE
     SYNTAX      IpAddress
     MAX-ACCESS  read-write
     STATUS      current
     DESCRIPTION
         "Address of Mail Server."
     ::= { netraCtRscEnetObjs 7 }

netraCtRscMailUser OBJECT-TYPE
     SYNTAX      DisplayString (SIZE (1..40))
     MAX-ACCESS  read-write
     STATUS      current
     DESCRIPTION
         "email address for RSC alerts."
     ::= { netraCtRscEnetObjs 8 }

netraCtRscPPPLocalIP OBJECT-TYPE
     SYNTAX      IpAddress
     MAX-ACCESS  read-write
     STATUS      current
     DESCRIPTION
         "PPP local IP address."
     ::= { netraCtRscEnetObjs 9 }

netraCtRscPPPRemoteIP OBJECT-TYPE
     SYNTAX      IpAddress
     MAX-ACCESS  read-write
     STATUS      current
     DESCRIPTION
         "PPP remote IP address."
     ::= { netraCtRscEnetObjs 10 }

-- Bug#4369515
netraCtRscMailHostAddressBackup OBJECT-TYPE
     SYNTAX      IpAddress
     MAX-ACCESS  read-write
     STATUS      current
     DESCRIPTION
         " Backup Address of Mail Server. when no IP address is 
           configured for  mail server, back up IP address becomes 
           first IP address of mailhost "
     ::= { netraCtRscEnetObjs 11 }


-- NetraCtRSC Environment Objects

netraCtRscSystemType OBJECT-TYPE
     SYNTAX      DisplayString ( SIZE (1..127) )
     MAX-ACCESS  read-only
     STATUS      current
     DESCRIPTION
         "System Type.  This will currently return
	  one of the following 2 strings:
	  NetraCt400 , or
	  NetraCt800."
     ::= { netraCtRscEnvObjs 1 }

netraCtRscPowerSupplyCount OBJECT-TYPE
     SYNTAX      INTEGER (0..63)
     MAX-ACCESS  read-only
     STATUS      current
     DESCRIPTION
         "The total number of Power Supply FRUs in the platform."
     ::= { netraCtRscEnvObjs 2 }

netraCtRscPowerSupplyTable OBJECT-TYPE
     SYNTAX      SEQUENCE OF NetraCtRscPowerSupplyEntry
     MAX-ACCESS  not-accessible
     STATUS      current
     DESCRIPTION
         "A table listing the characteristics of the Power-Supply FRU."
     ::= { netraCtRscEnvObjs 3 }

netraCtRscPowerSupplyEntry OBJECT-TYPE
     SYNTAX      NetraCtRscPowerSupplyEntry
     MAX-ACCESS  not-accessible
     STATUS      current
     DESCRIPTION
         "an entry (conceptual row) in the netraCtRscPowerSupplyTable"
     INDEX       { netraCtRscPowerSupplyIndex }
     ::= { netraCtRscPowerSupplyTable 1 }

NetraCtRscPowerSupplyEntry ::= SEQUENCE {
     netraCtRscPowerSupplyIndex		INTEGER,
     netraCtRscPowerSupplyPresent	INTEGER,
     netraCtRscPowerSupplyOperState	INTEGER,
     netraCtRscPowerSupplyAdminState	INTEGER
}

netraCtRscPowerSupplyIndex OBJECT-TYPE
     SYNTAX      INTEGER (1..64)
     MAX-ACCESS  read-only
     STATUS      current
     DESCRIPTION
         "Entry number for this Power-Supply FRU row."
     ::= { netraCtRscPowerSupplyEntry 1 }

netraCtRscPowerSupplyPresent OBJECT-TYPE
     SYNTAX      INTEGER { true(1), false(2), unknown(3), 
		 	   notimpl(2147483647) }
     MAX-ACCESS  read-only
     STATUS      current
     DESCRIPTION
         "Power-Supply FRU is present."
     ::= { netraCtRscPowerSupplyEntry 2 }

netraCtRscPowerSupplyOperState OBJECT-TYPE
     SYNTAX      INTEGER { okay(1), failed(2), unknown(3), 
			                     offline(4), notimpl(2147483647) }
     MAX-ACCESS  read-only
     STATUS      current
     DESCRIPTION
     "The current status of the Power-Supply FRU."
     ::= { netraCtRscPowerSupplyEntry 3 }

netraCtRscPowerSupplyAdminState OBJECT-TYPE
     SYNTAX      INTEGER { on(1), off(2), notimpl(2147483647) }
     MAX-ACCESS  read-write
     STATUS      current
     DESCRIPTION
	  "Setting this value to on(1) requests that the power
	   supply be turned on.  Setting this value to off(2) 
	   requests that the power supply be turned off."
     ::= { netraCtRscPowerSupplyEntry 4 }


-- NetraCtRSC Alarm Table

netraCtRscAlarmCount OBJECT-TYPE
     SYNTAX      INTEGER (0..63)
     MAX-ACCESS  read-only
     STATUS      current
     DESCRIPTION
         "Number of Alarm Ports in this Platform"
     ::= { netraCtRscEnvObjs 4 }

netraCtRscAlarmTable OBJECT-TYPE
     SYNTAX      SEQUENCE OF NetraCtRscAlarmEntry
     MAX-ACCESS  not-accessible
     STATUS      current
     DESCRIPTION
         "a table listing the available Alarm Ports."
     ::= { netraCtRscEnvObjs 5 }

netraCtRscAlarmEntry OBJECT-TYPE
     SYNTAX      NetraCtRscAlarmEntry
     MAX-ACCESS  not-accessible
     STATUS      current
     DESCRIPTION
         "an entry (conceptual row) in the netraCtRscAlarmTable."
     INDEX       { netraCtRscAlarmIndex }
     ::= { netraCtRscAlarmTable 1 }

NetraCtRscAlarmEntry ::= SEQUENCE {
     netraCtRscAlarmIndex	INTEGER,
     netraCtRscAlarmID		INTEGER,
     netraCtRscAlarmOperState	INTEGER,
     netraCtRscAlarmAdminState	INTEGER,
     netraCtRscAlarmPrefix	INTEGER
}

netraCtRscAlarmIndex OBJECT-TYPE
     SYNTAX      INTEGER (1..64)
     MAX-ACCESS  not-accessible
     STATUS      current
     DESCRIPTION
         "row index into Alarm Port table"
     ::= { netraCtRscAlarmEntry 1 }

netraCtRscAlarmID OBJECT-TYPE
     SYNTAX      INTEGER (0..63)
     MAX-ACCESS  read-only
     STATUS      current
     DESCRIPTION
         "Alarm identifier.  The current Netra ct 400/800 Alarm Cards
	  currently supports Alarm IDs of 0,1,2, and 3."
     ::= { netraCtRscAlarmEntry 2 }

netraCtRscAlarmOperState OBJECT-TYPE
     SYNTAX      INTEGER { on(1), off(2), notimpl(2147483647) }
     MAX-ACCESS  read-only
     STATUS      current
     DESCRIPTION
         "This returns the current value of the Alarm, which may
	  have been set by either software due to environmental 
	  conditions, such as Fan failure, or manually, by the
	  setting of netraCtRscAlarmAdminState."
     ::= { netraCtRscAlarmEntry 3 }

netraCtRscAlarmAdminState OBJECT-TYPE
     SYNTAX      INTEGER { on(1), off(2) }
     MAX-ACCESS  read-write
     STATUS      current
     DESCRIPTION
         "This reflects the requested state of an alarm port by 
	  the SNMP manager."
     ::= { netraCtRscAlarmEntry 4 }

netraCtRscAlarmPrefix   OBJECT-TYPE
     SYNTAX      INTEGER (0..255)
     MAX-ACCESS  read-only
     STATUS      current
     DESCRIPTION
	  "The Alarm Prefix that will associate an FRU type to an alarm.
	   Currently supported definitions are:
	   	cpuunit(1),
		software(2),
		powersupply(3),
		temperature(4),
		fan(5).
		6 through 9 are reserved for future expansion.
		10 through 255 are undefined, and can be configured for
		user-defined messages and alarming."
     ::= { netraCtRscAlarmEntry 5 }


-- NetraCtRSC Fan Table

netraCtRscFanCount OBJECT-TYPE
     SYNTAX      INTEGER (0..63)
     MAX-ACCESS  read-only
     STATUS      current
     DESCRIPTION
         "Maximum number of Fan Tray FRUs in Platform"
     ::= { netraCtRscEnvObjs 6 }

netraCtRscFanTable OBJECT-TYPE
     SYNTAX      SEQUENCE OF NetraCtRscFanEntry
     MAX-ACCESS  not-accessible
     STATUS      current
     DESCRIPTION
         "a table listing the characteristics of the Fan Tray FRU."
     ::= { netraCtRscEnvObjs 7 }

netraCtRscFanEntry OBJECT-TYPE
     SYNTAX      NetraCtRscFanEntry
     MAX-ACCESS  not-accessible
     STATUS      current
     DESCRIPTION
         "an entry (conceptual row) in the netraCtRscFanTable."
     INDEX       { netraCtRscFanIndex }
     ::= { netraCtRscFanTable 1 }

NetraCtRscFanEntry ::= SEQUENCE {
     netraCtRscFanIndex                 INTEGER,
     netraCtRscFanPresent               INTEGER,
     netraCtRscFanStatus                INTEGER
}

netraCtRscFanIndex OBJECT-TYPE
     SYNTAX      INTEGER (1..64)
     MAX-ACCESS  read-only
     STATUS      current
     DESCRIPTION
         "row index into Fan FRU table"
     ::= { netraCtRscFanEntry 1 }

netraCtRscFanPresent OBJECT-TYPE
     SYNTAX      INTEGER { true(1), false(2), unknown(3), 
			   notimpl(2147483647) }
     MAX-ACCESS  read-only
     STATUS      current
     DESCRIPTION
         "Fan FRU is present"
     ::= { netraCtRscFanEntry 2 }

netraCtRscFanStatus OBJECT-TYPE
     SYNTAX      INTEGER { okay(1), failed(2), unknown(3), 
			   notimpl(2147483647) }
     MAX-ACCESS  read-only
     STATUS      current
     DESCRIPTION
         "The current status of the Fan FRU.
	  unknown will be returned if the status is unknown."
     ::= { netraCtRscFanEntry 3 }


-- NetraCtRSC Temperature Sensor Table

netraCtRscTemperatureCount OBJECT-TYPE
     SYNTAX      INTEGER (0..63)
     MAX-ACCESS  read-only
     STATUS      current
     DESCRIPTION
         "Maximum number of temperature sensors on Platform"
     ::= { netraCtRscEnvObjs 8 }

netraCtRscTemperatureTable OBJECT-TYPE
     SYNTAX      SEQUENCE OF NetraCtRscTemperatureEntry
     MAX-ACCESS  not-accessible
     STATUS      current
     DESCRIPTION
         "a table listing the contents of the event log as an 
	  array of strings."
     ::= { netraCtRscEnvObjs 9 }

netraCtRscTemperatureEntry OBJECT-TYPE
     SYNTAX      NetraCtRscTemperatureEntry
     MAX-ACCESS  not-accessible
     STATUS      current
     DESCRIPTION
         "an entry (conceptual row) in the netraCtRscTemperatureTable."
     INDEX       { netraCtRscTemperatureIndex }
     ::= { netraCtRscTemperatureTable 1 }

NetraCtRscTemperatureEntry ::= SEQUENCE {
     netraCtRscTemperatureIndex         INTEGER,
     netraCtRscTemperatureValid         INTEGER,
     netraCtRscTemperatureValue         INTEGER,
     netraCtRscTemperatureLowWarn       INTEGER,
     netraCtRscTemperatureHighWarn      INTEGER,
     netraCtRscTemperatureDesc          DisplayString
}

netraCtRscTemperatureIndex OBJECT-TYPE
     SYNTAX      INTEGER (1..64)
     MAX-ACCESS  read-only
     STATUS      current
     DESCRIPTION
         "current row of the Temperature sensor"
     ::= { netraCtRscTemperatureEntry 1 }

netraCtRscTemperatureValid OBJECT-TYPE
     SYNTAX      INTEGER { true(1), false(2) }
     MAX-ACCESS  read-only
     STATUS      current
     DESCRIPTION
         "The current temperature at this sensor is known.
	  If the temperature cannot be obtained, then false
	  will be returned, and netraCtRscTemperatureValue should
	  not be considered to be valid."
     ::= { netraCtRscTemperatureEntry 2 }

netraCtRscTemperatureValue OBJECT-TYPE
     SYNTAX      INTEGER (1..2147483647)
     MAX-ACCESS  read-only
     STATUS      current
     DESCRIPTION
         "current temperature at this sensor"
     ::= { netraCtRscTemperatureEntry 3 }

netraCtRscTemperatureLowWarn OBJECT-TYPE
     SYNTAX      INTEGER (1..2147483647)
     MAX-ACCESS  read-only
     STATUS      current
     DESCRIPTION
         "low warning threshold for this temperature sensor"
     ::= { netraCtRscTemperatureEntry 4 }

netraCtRscTemperatureHighWarn OBJECT-TYPE
     SYNTAX      INTEGER (1..2147483647)
     MAX-ACCESS  read-only
     STATUS      current
     DESCRIPTION
         "high warning threshold for this temperature sensor"
     ::= { netraCtRscTemperatureEntry 5 }

netraCtRscTemperatureDesc OBJECT-TYPE
     SYNTAX      DisplayString ( SIZE(1..255) )
     MAX-ACCESS  read-only
     STATUS      current
     DESCRIPTION
         "textual description of the Temperature sensor"
     ::= { netraCtRscTemperatureEntry 6 }


-- NetraCtRSC Logs Objects

-- NetraCtRSC Event Log Table

netraCtRscEventLogCount OBJECT-TYPE
     SYNTAX      INTEGER (0..2147483647)
     MAX-ACCESS  read-only
     STATUS      current
     DESCRIPTION
         "current number of lines in the event log"
     ::= { netraCtRscLogObjs 1 }

netraCtRscEventLogTable OBJECT-TYPE
     SYNTAX      SEQUENCE OF NetraCtRscEventLogEntry
     MAX-ACCESS  not-accessible
     STATUS      current
     DESCRIPTION
         "a table listing the contents of the event log as an 
	  array of strings."
     ::= { netraCtRscLogObjs 2 }

netraCtRscEventLogEntry OBJECT-TYPE
     SYNTAX      NetraCtRscEventLogEntry
     MAX-ACCESS  not-accessible
     STATUS      current
     DESCRIPTION
         "an entry (conceptual row) in the netraCtRscEventLogTable."
     INDEX       { netraCtRscEventLogIndex }
     ::= { netraCtRscEventLogTable 1 }

NetraCtRscEventLogEntry ::= SEQUENCE {
     netraCtRscEventLogIndex            INTEGER,
     netraCtRscEventLogTimeStamp        DateAndTime,
     netraCtRscEventLogMessage          DisplayString
}

netraCtRscEventLogIndex OBJECT-TYPE
     SYNTAX      INTEGER (0..2147483647)
     MAX-ACCESS  read-only
     STATUS      current
     DESCRIPTION
         "The index of the entry.  The oldest entry will start at index 0.
	  The most recent entry will be found at the index equal to 
	  netraCtRscEventLogCount - 1."
     ::= { netraCtRscEventLogEntry 1 }

netraCtRscEventLogTimeStamp OBJECT-TYPE
     SYNTAX      DateAndTime
     MAX-ACCESS  read-only
     STATUS      current
     DESCRIPTION
         "event timestamp"
     ::= { netraCtRscEventLogEntry 2 }

netraCtRscEventLogMessage OBJECT-TYPE
     SYNTAX      DisplayString ( SIZE(1..255) )
     MAX-ACCESS  read-only
     STATUS      current
     DESCRIPTION
         "textual description of an event."
     ::= { netraCtRscEventLogEntry 3 }


-- NetraCtRsc Original Console Log Table

netraCtRscOrigConsoleLogCount OBJECT-TYPE
     SYNTAX      INTEGER (0..2147483647)
     MAX-ACCESS  read-only
     STATUS      current
     DESCRIPTION
         "current number of lines in the original console log."
     ::= { netraCtRscLogObjs 3 }

netraCtRscOrigConsoleLogTable OBJECT-TYPE
     SYNTAX      SEQUENCE OF NetraCtRscOrigConsoleLogEntry
     MAX-ACCESS  not-accessible
     STATUS      current
     DESCRIPTION
         "a table listing the contents of the original console 
	  log as an array of strings."
     ::= { netraCtRscLogObjs 4 }

netraCtRscOrigConsoleLogEntry OBJECT-TYPE
     SYNTAX      NetraCtRscOrigConsoleLogEntry
     MAX-ACCESS  not-accessible
     STATUS      current
     DESCRIPTION
         "an entry (conceptual row) in the netraCtRscOrigConsoleLogTable."
     INDEX       { netraCtRscOrigConsoleLogIndex }
     ::= { netraCtRscOrigConsoleLogTable 1 }

NetraCtRscOrigConsoleLogEntry ::= SEQUENCE {
     netraCtRscOrigConsoleLogIndex            INTEGER,
     netraCtRscOrigConsoleLogTimeStamp        DateAndTime,
     netraCtRscOrigConsoleLogMessage          DisplayString
}

netraCtRscOrigConsoleLogIndex OBJECT-TYPE
     SYNTAX      INTEGER (0..2147483647)
     MAX-ACCESS  read-only
     STATUS      current
     DESCRIPTION
         "The index of the entry.  The oldest entry will start at index 0.
	  The most recent entry will be found at the index equal to 
	  netraCtRscOrigConsoleLogCount - 1."
     ::= { netraCtRscOrigConsoleLogEntry 1 }

netraCtRscOrigConsoleLogTimeStamp OBJECT-TYPE
     SYNTAX      DateAndTime
     MAX-ACCESS  read-only
     STATUS      current
     DESCRIPTION
         "Original Console Log timestamp"
     ::= { netraCtRscOrigConsoleLogEntry 2 }

netraCtRscOrigConsoleLogMessage OBJECT-TYPE
     SYNTAX      DisplayString ( SIZE(1..255) )
     MAX-ACCESS  read-only
     STATUS      current
     DESCRIPTION
         "textual description of an event."
     ::= { netraCtRscOrigConsoleLogEntry 3 }


-- NetraCtRsc Console Log Table

netraCtRscConsoleLogCount OBJECT-TYPE
     SYNTAX      INTEGER (0..2147483647)
     MAX-ACCESS  read-only
     STATUS      current
     DESCRIPTION
         "current number of lines in the console log."
     ::= { netraCtRscLogObjs 5 }

netraCtRscConsoleLogTable OBJECT-TYPE
     SYNTAX      SEQUENCE OF NetraCtRscConsoleLogEntry
     MAX-ACCESS  not-accessible
     STATUS      current
     DESCRIPTION
         "a table listing the contents of the console log as an 
	  array of strings."
     ::= { netraCtRscLogObjs 6 }

netraCtRscConsoleLogEntry OBJECT-TYPE
     SYNTAX      NetraCtRscConsoleLogEntry
     MAX-ACCESS  not-accessible
     STATUS      current
     DESCRIPTION
         "an entry (conceptual row) in the netraCtRscConsoleLogTable."
     INDEX       { netraCtRscConsoleLogIndex }
     ::= { netraCtRscConsoleLogTable 1 }

NetraCtRscConsoleLogEntry ::= SEQUENCE {
     netraCtRscConsoleLogIndex            INTEGER,
     netraCtRscConsoleLogTimeStamp        DateAndTime,
     netraCtRscConsoleLogMessage          DisplayString
}

netraCtRscConsoleLogIndex OBJECT-TYPE
     SYNTAX      INTEGER (0..2147483647)
     MAX-ACCESS  read-only
     STATUS      current
     DESCRIPTION
         "The index of the entry.  The oldest entry will start at index 0.
	  The most recent entry will be found at the index equal to 
	  netraCtRscConsoleLogCount - 1."
     ::= { netraCtRscConsoleLogEntry 1 }

netraCtRscConsoleLogTimeStamp OBJECT-TYPE
     SYNTAX      DateAndTime
     MAX-ACCESS  read-only
     STATUS      current
     DESCRIPTION
         "Console Log timestamp"
     ::= { netraCtRscConsoleLogEntry 2 }

netraCtRscConsoleLogMessage OBJECT-TYPE
     SYNTAX      DisplayString ( SIZE(1..255) )
     MAX-ACCESS  read-only
     STATUS      current
     DESCRIPTION
         "textual description of an event."
     ::= { netraCtRscConsoleLogEntry 3 }

netraCtRscConsoleReset OBJECT-TYPE
     SYNTAX      INTEGER { set(1), clear(2) }
     MAX-ACCESS  read-write
     STATUS      current
     DESCRIPTION
         "When set, the console log is reset so that the current
	  log is copied over to the original console log, and the
	  the console log will be cleared.  All new console messages
	  will then go to the console log.clear(2) setting is read-only."
     ::= { netraCtRscLogObjs 7 }


-- NetraCtRscRccConfig Objects.  Note that this group lives 
-- under an experimental branch, and support of the objects
-- under this branch may be subject to change.

netraCtRscRCCPowerOnEnable OBJECT-TYPE
     SYNTAX      INTEGER { on(1), off(2), notimpl(2147483647) }
     MAX-ACCESS  read-write
     STATUS      current
     DESCRIPTION
         "If set to false, masks the RCC PowerOn command."
     ::= { netraCtRscRccConfig 1 }

netraCtRscRCCPowerOffEnable OBJECT-TYPE
     SYNTAX      INTEGER { on(1), off(2), notimpl(2147483647) }
     MAX-ACCESS  read-write
     STATUS      current
     DESCRIPTION
         "If set to false, masks the RCC PowerOff command."
     ::= { netraCtRscRccConfig 2 }

netraCtRscRCCResetEnable OBJECT-TYPE
     SYNTAX      INTEGER { on(1), off(2), notimpl(2147483647) }
     MAX-ACCESS  read-write
     STATUS      current
     DESCRIPTION
         "If set to false, masks the RCC Reset command."
     ::= { netraCtRscRccConfig 3 }

netraCtRscRCCLinkNum OBJECT-TYPE
     SYNTAX      DisplayString ( SIZE(2) )
     MAX-ACCESS  read-write
     STATUS      current
     DESCRIPTION
         "2-byte string that defines the RCC Linknum address."
     ::= { netraCtRscRccConfig 4 }


-- NetraCtRSC (v2) Events (traps)

netraCtRscEvent NOTIFICATION-TYPE
     OBJECTS  { netraCtRscAlarmID, netraCtRscAlarmOperState,
		netraCtRscAlarmPrefix }
     STATUS   current
     DESCRIPTION
         "Event used to notify the snmp manager of a new RSC event. 
	  An event is generated when one of the values:
	  netraCtRscAlarmOperState, in the Table:netraCtRscAlarmTable
	  changes state."
     ::= { netraCtRscTrapPrefix 1 }


END
