VIDEOFRAME-SIGMON-VM0007-MIB DEFINITIONS ::= BEGIN

	--  Relationship to Other MIBs
	--
	--
	--  The objects defined in this MIB are located under the
	--  private.enterprises subtree as shown below:
	--
	--               iso(1).org(3).dod(6).internet(1)
	--                            |
	--                         private(4)
	--                            |
	--                       enterprises(1)
	--                            |
	--                       videoframe(4596)
	--                            |
	--                      vfProducts(4)
	--							  |
	--						vfSigmonFrame(2)
	--							  |
	--					  vfSigmonFrameModules(1)
	--							  |
	--					  vm0007TransferSwitch(7)
	--                                 
	--
	--  References
	--
	--  [1]  RFC 1902.  McCloghrie, K., and M. Rose, "Structure 
	--       of Management Information for Version 2 of the Simple
	--       Network Management Protocol (SNMPv2)".  
	--       January, 1996.
	--
	--  [2]  RFC 1903.  McCloghrie, K., and M. Rose, "Textual
	--       Conventions for Version 2 of the Simple Network
	--       Management Protocol (SNMPv2)".  
	--       January, 1996.
	--
	--  [3]  RFC 1904.  McCloghrie, K., and M. Rose, "Conformance
	--       Statements for Version 2 of the Simple Network
	--       Management Protocol (SNMPv2)".  
	--       January, 1996.
	--
	--  [4]  RFC 1907.  McCloghrie, K., and M. Rose, "Management 
	--       Information Base for Version 2 of the Simple Network
	--       Management Protocol (SNMPv2)".  
	--       January, 1996.
	--
	--	[5]  Perkins, David and McGinnis, Evan; "Understanding SNMP
	--		 MIBs".  Prentice Hall, ISBN 0-13-437708-7, 1997.
	--
	--
	--  Object Synopsis
	--  
	--
	--  All objects within this MIB are prefixed with the OBJECT
	--  IDENTIFIER "p", where "p" is:
	--
	--  iso(1).org(3).dod(6).internet(1).private(4).enterprises(1).
	--          videoframe(4596).vfProducts(4).vfSigmonFrame(2).
	--			vfSigmonFrameModuleTypes(1)
	--	
	--  or, 1.3.6.1.4.1.4596.4.2.1
	--
	--
	--  Object Name                               Object Id         
	--  --------------------------------          --------------
	--
	--	vm0007TransferSwitch						p.1
	--		vm0007Table								p.1.1
	--		vm0007TableEntry						p.1.1.1
	--			vm0007SlotNumber					p.1.1.1.1.m		m = slot #
	--			vm0007Active						p.1.1.1.2.m
	--			vm0007Locate						p.1.1.1.3.m
	--			vm0007VideoSignalSwitchState		p.1.1.1.4.m
	--			vm0007TransferSwitchAlarmAck		p.1.1.1.5.m
	--			vm0007CPUOverride					p.1.1.1.6.m
	--			vm0007VideoSource1Name				p.1.1.1.7.m
	--			vm0007VideoSource1Description		p.1.1.1.8.m
	--			vm0007VideoSource2Name				p.1.1.1.9.m
	--			vm0007VideoSource2Description		p.1.1.1.10.m
	--			vm0007VideoDest1Name				p.1.1.1.11.m
	--			vm0007VideoDest1Description			p.1.1.1.12.m
	--			vm0007VideoDest2Name				p.1.1.1.13.m
	--			vm0007VideoDest2Description			p.1.1.1.14.m
	--		vm0007AudioChannelTable					p.1.2
	--		vm0007AudioChannelEntry					p.1.2.1
	--			vm0007ChannelSlotNumber				p.1.2.1.1.m.n	m = slot #, n = signal #
	--			vm0007AudioChannelNumber			p.1.2.1.2.m.n
	--			vm0007AudioChannelSwitchState		p.1.2.1.3.m.n
	--			vm0007AudioChanSource1Name			p.1.2.1.4.m.n
	--			vm0007AudioChanSource1Description	p.1.2.1.5.m.n
	--			vm0007AudioChanSource2Name			p.1.2.1.6.m.n
	--			vm0007AudioChanSource2Description	p.1.2.1.7.m.n
	--			vm0007AudioChanDest1Name			p.1.2.1.8.m.n
	--			vm0007AudioChanDest1Description		p.1.2.1.9.m.n
	--			vm0007AudioChanDest2Name			p.1.2.1.10.m.n
	--			vm0007AudioChanDest2Description		p.1.2.1.11.m.n
	--		vm0007TransferSwitchEvents				p.1.3
	--			vm0007TransferSwitchEventsV2		p.1.3.0
	--				transferSwitchActivatedAlarm	p.1.3.0.1
	--				transferSwitchNormalAlarm		p.1.3.0.2
	--    

	IMPORTS
		OBJECT-TYPE FROM RFC1155-SMI
		MODULE-IDENTITY, OBJECT-IDENTITY, NOTIFICATION-TYPE,
		IpAddress
			FROM SNMPv2-SMI
		DisplayString, RowStatus
			FROM SNMPv2-TC
		MODULE-COMPLIANCE, OBJECT-GROUP
			FROM SNMPv2-CONF
		vfMIBModules
			FROM VIDEOFRAME-REGISTRATIONS-MIB
		vfBoxId
			FROM VIDEOFRAME-GENERIC-MIB
		vfSigmonFrameModuleTypes, vfProductsVF200Reg, vfFrameSlotNumber
			FROM VIDEOFRAME-SIGMON-MIB;

	videoframeSigmonVm0007MIB MODULE-IDENTITY
		LAST-UPDATED "0108300000Z"
		ORGANIZATION "Videoframe Systems"
		CONTACT-INFO
			"Videoframe Systems
			P.O. Box 1991,
			Grass Valley, CA 95945, USA.

			+1 (530) 477-2000

			http://www.videoframesystems.com"
	DESCRIPTION
		"This MIB describes the device specific objects of the VM0007
		Transfer Switch module, and augments MIB-2, VF-GENERIC, and VF-SIGMON
		in the identification of this Videoframe Systems managed device.

		This module will be extended or modified as required.

		Videoframe Systems reserves the right to
		make changes in specification and other 
		information contained in this document without 
		prior notice. The reader should consult Videoframe Systems
		to determine whether any such changes have been made.

		In no event shall Videoframe Systems be 
		liable for any incidental, indirect, special, 
		or consequential damages whatsoever (including 
		but not limited to lost profits) arising out of 
		or related to this document or the information 
		contained in it.

		Videoframe Systems grants vendors, end users, 
		and other interested parties a non-exclusive 
		license to use this specification in connection 
		with the management of Videoframe Systems products.

		Copyright 2001 Videoframe, Inc."
	REVISION      "0108300000Z"
	DESCRIPTION
		"First release."
	::= { vfMIBModules 7 }

	--
	-- VM0007 product registration. vfProductsVF200Reg is from
	-- vf-sigmon
	--

vfProductsVM0007Reg OBJECT-IDENTITY
		STATUS	current
		DESCRIPTION
			"Videoframe VM0007 A/V Transfer Switch Module."
		::= { vfProductsVF200Reg 7 }

	--
	--  The VM0007 MIB top-level groups
	--

	-- root of this MIB module
vm0007TransferSwitch		OBJECT IDENTIFIER ::= { vfSigmonFrameModuleTypes 7 }

	--
	-- Other signal monitoring modules, whose management information is defined in
	-- other MIB modules.
	--
	--		vm0001AnalogAudio		OBJECT IDENTIFIER ::= { vfSigmonFrameModuleTypes 1 }
	--		vm0002AnalogVideo		OBJECT IDENTIFIER ::= { vfSigmonFrameModuleTypes 2 }
	--		vm0003AESEBUAudio		OBJECT IDENTIFIER ::= { vfSigmonFrameModuleTypes 3 }
	--		vm0004SDIVideo			OBJECT IDENTIFIER ::= { vfSigmonFrameModuleTypes 4 }
	--		vm0005SerialIO			OBJECT IDENTIFIER ::= { vfSigmonFrameModuleTypes 5 }
	--		vm0006GPIInterface		OBJECT IDENTIFIER ::= { vfSigmonFrameModuleTypes 6 }
	--		vm0008CPU				OBJECT IDENTIFIER ::= { vfSigmonFrameModuleTypes 8 }
	--		vm0009DTMFTransceiver	OBJECT IDENTIFIER ::= { vfSigmonFrameModuleTypes 9 }
	--		vm0010GPOInterface		OBJECT IDENTIFIER ::= { vfSigmonFrameModuleTypes 10 }
	--		vm0011GPIOInterface		OBJECT IDENTIFIER ::= { vfSigmonFrameModuleTypes 11 }
	--

vm0007Table	OBJECT-TYPE
	SYNTAX	SEQUENCE OF Vm0007Entry
	MAX-ACCESS	not-accessible
	STATUS	current
	DESCRIPTION
		"Each row contains information about one VM0007 A/V Transfer Switch
		 module in the managed VF200 frame."

	::=	{ vm0007TransferSwitch 1}


vm0007Entry	OBJECT-TYPE
	SYNTAX	Vm0007Entry
    MAX-ACCESS not-accessible
    STATUS     current
    DESCRIPTION
        "A VM0007 A/V Transfer Switch module entry."
	INDEX { vfFrameSlotNumber }
    ::= { vm0007Table 1 } 
		
Vm0007Entry   ::= 
    SEQUENCE	{
		vm0007SlotNumber					INTEGER,
		vm0007Active						INTEGER,
		vm0007Locate						INTEGER,
		vm0007VideoSignalSwitchState		INTEGER,
		vm0007TransferSwitchAlarmAck		INTEGER,
		vm0007CPUOverride					INTEGER,
		vm0007VideoSource1Name				DisplayString,
		vm0007VideoSource1Description		DisplayString,
		vm0007VideoSource2Name				DisplayString,
		vm0007VideoSource2Description		DisplayString,
		vm0007VideoDest1Name				DisplayString,
		vm0007VideoDest1Description			DisplayString,
		vm0007VideoDest2Name				DisplayString,
		vm0007VideoDest2Description			DisplayString
				}	

vm0007SlotNumber OBJECT-TYPE
		SYNTAX	INTEGER (1..12)				
		MAX-ACCESS	read-only
		STATUS		current
		DESCRIPTION
			"The slot that this entry represents."
	::= { vm0007Entry 1 }

vm0007Active OBJECT-TYPE
		SYNTAX	INTEGER
					{
						active(1),
						inactive(2)
					}				
		MAX-ACCESS	read-only
		STATUS		current
		DESCRIPTION
			"Indicates whether this entry is active (this module is in
			 this slot)."
	::= { vm0007Entry 2 }

vm0007Locate OBJECT-TYPE
		SYNTAX	INTEGER
					{
						flash(1),
						off(2)
					}				
		MAX-ACCESS	read-write
		STATUS		current
		DESCRIPTION
			"Controls the locate indicator on the module and indicates its
			 current state.  Set to flash (1) to cause the locate LED on the
			 front of the module to begin flashing.  Set to off to stop flashing."
	::= { vm0007Entry 3 }

vm0007VideoSignalSwitchState OBJECT-TYPE
		SYNTAX	INTEGER
					{
						crossover(1),
						straightThrough(2)
					}				
		MAX-ACCESS	read-write
		STATUS		current
		DESCRIPTION
			"Controls the the video signal switch on the module and indicates its
			 current state."
	::= { vm0007Entry 4 }

vm0007TransferSwitchAlarmAck	OBJECT-TYPE
		SYNTAX	INTEGER
				{
					idle(1),
					unacknowledged(2),
					acknowledge(3)
				}
		MAX-ACCESS	read-write
		STATUS		current
		DESCRIPTION
			"Set to acknowledge (3) to acknowledge a triggered transfer switch alarm.
			 This will acknowledge both the transferSwitchActivatedAlarm and the
			 transferSwitchNormalAlarm.  With Auto Re-Arm off, one of each alarm will
			 be allowed between acknowledges."
	::= { vm0007Entry 5 }

vm0007CPUOverride OBJECT-TYPE
		SYNTAX	INTEGER
					{
						on(1),
						off(2)
					}				
		MAX-ACCESS	read-write
		STATUS		current
		DESCRIPTION
			"Set to 'on' to ignore GPI inputs on the module back panel and put
			 the switch completely under SNMP or network API control."
	::= { vm0007Entry 6 }

vm0007VideoSource1Name OBJECT-TYPE
		SYNTAX		DisplayString (SIZE(0..20))
		MAX-ACCESS	read-write
		STATUS		current
		DESCRIPTION
			"The name of the signal connected to the 'S1' video input."
	::= { vm0007Entry 7 }

vm0007VideoSource1Description OBJECT-TYPE
		SYNTAX		DisplayString (SIZE(0..120))
		MAX-ACCESS	read-write
		STATUS		current
		DESCRIPTION
			"Descriptive identification of the signal connected to the 'S1' video input."
	::= { vm0007Entry 8 }

vm0007VideoSource2Name OBJECT-TYPE
		SYNTAX		DisplayString (SIZE(0..20))
		MAX-ACCESS	read-write
		STATUS		current
		DESCRIPTION
			"The name of the signal connected to the 'S2' video input."
	::= { vm0007Entry 9 }

vm0007VideoSource2Description OBJECT-TYPE
		SYNTAX		DisplayString (SIZE(0..120))
		MAX-ACCESS	read-write
		STATUS		current
		DESCRIPTION
			"Descriptive identification of the signal connected to the 'S2' video input."
	::= { vm0007Entry 10 }

vm0007VideoDest1Name OBJECT-TYPE
		SYNTAX		DisplayString (SIZE(0..20))
		MAX-ACCESS	read-write
		STATUS		current
		DESCRIPTION
			"The name of the destination for the 'D1' video output."
	::= { vm0007Entry 11 }

vm0007VideoDest1Description OBJECT-TYPE
		SYNTAX		DisplayString (SIZE(0..120))
		MAX-ACCESS	read-write
		STATUS		current
		DESCRIPTION
			"Descriptive identification of the destination for the 'D1' video output."
	::= { vm0007Entry 12 }

vm0007VideoDest2Name OBJECT-TYPE
		SYNTAX		DisplayString (SIZE(0..20))
		MAX-ACCESS	read-write
		STATUS		current
		DESCRIPTION
			"The name of the destination for the 'D2' video output."
	::= { vm0007Entry 13 }

vm0007VideoDest2Description OBJECT-TYPE
		SYNTAX		DisplayString (SIZE(0..120))
		MAX-ACCESS	read-write
		STATUS		current
		DESCRIPTION
			"Descriptive identification of the destination for the 'D2' video output."
	::= { vm0007Entry 14 }

vm0007AudioChannelTable	OBJECT-TYPE
	SYNTAX	SEQUENCE OF Vm0007AudioChannelEntry
	MAX-ACCESS	not-accessible
	STATUS	current
	DESCRIPTION
		"Each row contains information about one audio channel of one
		 VM0007 A/V Transfer Switch module in the managed VF200 frame."

	::=	{ vm0007TransferSwitch 2}


vm0007AudioChannelEntry	OBJECT-TYPE
	SYNTAX	Vm0007AudioChannelEntry
    MAX-ACCESS not-accessible
    STATUS     current
    DESCRIPTION
        "An A/V Transfer Switch module audio channel entry."
	INDEX { vfFrameSlotNumber, vm0007AudioChannelNumber }
    ::= { vm0007AudioChannelTable 1 } 
		
Vm0007AudioChannelEntry   ::= 
    SEQUENCE	{
		vm0007AudioChannelSlotNumber			INTEGER,
		vm0007AudioChannelNumber				INTEGER,
		vm0007AudioChannelSwitchState			INTEGER,
		vm0007AudioChanSource1Name				DisplayString,
		vm0007AudioChanSource1Description		DisplayString,
		vm0007AudioChanSource2Name				DisplayString,
		vm0007AudioChanSource2Description		DisplayString,
		vm0007AudioChanDest1Name				DisplayString,
		vm0007AudioChanDest1Description			DisplayString,
		vm0007AudioChanDest2Name				DisplayString,
		vm0007AudioChanDest2Description			DisplayString
		}

vm0007AudioChannelSlotNumber OBJECT-TYPE
		SYNTAX	INTEGER (1..12)				
		MAX-ACCESS	read-only
		STATUS		current
		DESCRIPTION
			"The frame slot number that this entry represents."
	::= { vm0007AudioChannelEntry 1 }

vm0007AudioChannelNumber OBJECT-TYPE
		SYNTAX		INTEGER(1..4)
		MAX-ACCESS	read-only
		STATUS		current
		DESCRIPTION
			"The channel within the module to which this signal is connected."
	::= { vm0007AudioChannelEntry 2 }

vm0007AudioChannelSwitchState OBJECT-TYPE
		SYNTAX	INTEGER
					{
						crossover(1),
						straightThrough(2)
					}				
		MAX-ACCESS	read-write
		STATUS		current
		DESCRIPTION
			"Controls the audio signal switch for this channel and indicates its
			 current state."
	::= { vm0007AudioChannelEntry 3 }

vm0007AudioChanSource1Name OBJECT-TYPE
		SYNTAX		DisplayString (SIZE(0..20))
		MAX-ACCESS	read-write
		STATUS		current
		DESCRIPTION
			"The name of the signal connected to S1-An for this channel."
	::= { vm0007AudioChannelEntry 4 }

vm0007AudioChanSource1Description OBJECT-TYPE
		SYNTAX		DisplayString (SIZE(0..120))
		MAX-ACCESS	read-write
		STATUS		current
		DESCRIPTION
			"Descriptive identification of the signal connected to S1-An for this channel."
	::= { vm0007AudioChannelEntry 5 }

vm0007AudioChanSource2Name OBJECT-TYPE
		SYNTAX		DisplayString (SIZE(0..20))
		MAX-ACCESS	read-write
		STATUS		current
		DESCRIPTION
			"The name of the signal connected to S2-An for this channel."
	::= { vm0007AudioChannelEntry 6 }

vm0007AudioChanSource2Description OBJECT-TYPE
		SYNTAX		DisplayString (SIZE(0..120))
		MAX-ACCESS	read-write
		STATUS		current
		DESCRIPTION
			"Descriptive identification of the signal connected to S2-An for this channel."
	::= { vm0007AudioChannelEntry 7 }

vm0007AudioChanDest1Name OBJECT-TYPE
		SYNTAX		DisplayString (SIZE(0..20))
		MAX-ACCESS	read-write
		STATUS		current
		DESCRIPTION
			"The name of the signal connected to D1-An for this channel."
	::= { vm0007AudioChannelEntry 8 }

vm0007AudioChanDest1Description OBJECT-TYPE
		SYNTAX		DisplayString (SIZE(0..120))
		MAX-ACCESS	read-write
		STATUS		current
		DESCRIPTION
			"Descriptive identification of the signal connected to D1-An for this channel."
	::= { vm0007AudioChannelEntry 9 }

vm0007AudioChanDest2Name OBJECT-TYPE
		SYNTAX		DisplayString (SIZE(0..20))
		MAX-ACCESS	read-write
		STATUS		current
		DESCRIPTION
			"The name of the signal connected to D1-An for this channel."
	::= { vm0007AudioChannelEntry 10 }

vm0007AudioChanDest2Description OBJECT-TYPE
		SYNTAX		DisplayString (SIZE(0..120))
		MAX-ACCESS	read-write
		STATUS		current
		DESCRIPTION
			"Descriptive identification of the signal connected to D1-An for this channel."
	::= { vm0007AudioChannelEntry 11 }

	--
	-- vm0007 Events
	--

vm0007TransferSwitchEvents		OBJECT IDENTIFIER ::= { vm0007TransferSwitch 3 }
vm0007TransferSwitchEventsV2	OBJECT IDENTIFIER ::= { vm0007TransferSwitchEvents 0 }

transferSwitchActivatedAlarm	NOTIFICATION-TYPE
		OBJECTS
			{
				vfBoxId,
				vm0007SlotNumber,
				vm0007VideoSource1Name,
				vm0007VideoSource2Name,
				vm0007VideoDest1Name,
				vm0007VideoDest2Name
			}
		STATUS	current
		DESCRIPTION
			"An A/V Transfer Switch was switched to crossover (backup) mode."
		::= { vm0007TransferSwitchEventsV2 1 }

transferSwitchNormalAlarm	NOTIFICATION-TYPE
		OBJECTS
			{
				vfBoxId,
				vm0007SlotNumber,
				vm0007VideoSource1Name,
				vm0007VideoSource2Name,
				vm0007VideoDest1Name,
				vm0007VideoDest2Name
			}
		STATUS	current
		DESCRIPTION
			"An A/V Transfer Switch was switched to straight through (normal) mode."
		::= { vm0007TransferSwitchEventsV2 2 }


END
