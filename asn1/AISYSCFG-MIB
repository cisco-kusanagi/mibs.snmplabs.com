AISYSCFG-MIB DEFINITIONS ::= BEGIN

IMPORTS
    MODULE-IDENTITY, OBJECT-TYPE, enterprises
					FROM SNMPv2-SMI;

    aii OBJECT IDENTIFIER ::= {enterprises 539}

aiSysCfg MODULE-IDENTITY
    LAST-UPDATED "0104301700Z"
    ORGANIZATION "Applied Innovation Inc."
    CONTACT-INFO
"		Engineering MIB Administrator
		Postal: Applied Innovation Inc.
			5800 Innovation Drive
			Dublin, Ohio 43017-3271

		Tel:    614-798-2000
		Fax:    614-798-1770
		Email:  snmp@aiinet.com"
    DESCRIPTION
	"MIB module for system parameters."
    ::= {aii 32}

-- Module definitions

aiSysCfgSoftware MODULE-IDENTITY
    LAST-UPDATED "0104301700Z"
    ORGANIZATION "Applied Innovation Inc."
    CONTACT-INFO
"		Engineering MIB Administrator

		Postal: Applied Innovation Inc.
			5800 Innovation Drive
			Dublin, Ohio 43017-3271

		Tel:	614-798-2000
		Fax:	614-798-1770
		Email:	snmp@aiinet.com"
    DESCRIPTION
	"MIB module to describe software images.  Any
	software/firmware image/load/package should be describable by
	entries in aiSCSoftwareTable.  The set of (name, type,
	version, date) should uniquely identify any image loaded on an
	AI box."
    ::= { aiSysCfg 1 }

aiSysCfgTime MODULE-IDENTITY
    LAST-UPDATED "0104301700Z"
    ORGANIZATION "Applied Innovation Inc."
    CONTACT-INFO
"		Engineering MIB Administrator
		Postal: Applied Innovation Inc.
			5800 Innovation Drive
			Dublin, Ohio 43017-3271

		Tel:	614-798-2000
		Fax:	614-798-1770
		Email:	snmp@aiinet.com"
    DESCRIPTION
	"MIB module for timekeeping."
    ::= { aiSysCfg 2 }

aiSysCfgPower MODULE-IDENTITY
    LAST-UPDATED "0104301700Z"
    ORGANIZATION "Applied Innovation Inc."
    CONTACT-INFO
"		Engineering MIB Administrator
		Postal: Applied Innovation Inc.
			5800 Innovation Drive
			Dublin, Ohio 43017-3271

		Tel:	614-798-2000
		Fax:	614-798-1770
		Email:	snmp@aiinet.com"
    DESCRIPTION
	"MIB module for Power Supplies."
    ::= { aiSysCfg 3 }

aiSysCfgFan MODULE-IDENTITY
    LAST-UPDATED "0104301700Z"
    ORGANIZATION "Applied Innovation Inc."
    CONTACT-INFO
"		Engineering MIB Administrator
		Postal: Applied Innovation Inc.
			5800 Innovation Drive
			Dublin, Ohio 43017-3271

		Tel:	614-798-2000
		Fax:	614-798-1770
		Email:	snmp@aiinet.com"
    DESCRIPTION
	"MIB module for fans."
    ::= { aiSysCfg 4 }

aiSysCfgTemp MODULE-IDENTITY
    LAST-UPDATED "0104301700Z"
    ORGANIZATION "Applied Innovation Inc."
    CONTACT-INFO
"		Engineering MIB Administrator
		Postal: Applied Innovation Inc.
			5800 Innovation Drive
			Dublin, Ohio 43017-3271

		Tel:	614-798-2000
		Fax:	614-798-1770
		Email:	snmp@aiinet.com"
    DESCRIPTION
	"MIB module for Temperature Probes."
    ::= { aiSysCfg 5 }

END
