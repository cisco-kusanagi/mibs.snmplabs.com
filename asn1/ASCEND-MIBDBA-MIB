--			Ascend mibdba MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBDBA-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibdBAProfile  OBJECT IDENTIFIER ::= { configuration 71}

	-- The mibdBAProfile table
	--
	-- This table contains parameters for the mibdBAProfile profile
	--

    mibdBAProfileTable	OBJECT-TYPE
	SYNTAX		SEQUENCE OF MibdBAProfileEntry
	ACCESS		not-accessible
	STATUS		mandatory
	DESCRIPTION	"A list of mibdBAProfile profile entries."
	::= { mibdBAProfile 1 }

    mibdBAProfileEntry	OBJECT-TYPE
	SYNTAX		MibdBAProfileEntry
	ACCESS		not-accessible
	STATUS		mandatory
	DESCRIPTION	"A mibdBAProfile entry containing objects that
			 maps to the parameters of mibdBAProfile profile."
	INDEX		{ dBAProfile-Shelf-o, dBAProfile-Slot-o, dBAProfile-Item-o, dBAProfile-LogicalItem-o }
	::= { mibdBAProfileTable 1 }

    MibdBAProfileEntry ::=
	SEQUENCE {
	    dBAProfile-Shelf-o
		INTEGER,
	    dBAProfile-Slot-o
		INTEGER,
	    dBAProfile-Item-o
		INTEGER,
	    dBAProfile-LogicalItem-o
		INTEGER,
	    dBAProfile-LogicalAddress-PhysicalAddress-Shelf
		INTEGER,
	    dBAProfile-LogicalAddress-PhysicalAddress-Slot
		INTEGER,
	    dBAProfile-LogicalAddress-PhysicalAddress-ItemNumber
		INTEGER,
	    dBAProfile-LogicalAddress-LogicalItem
		INTEGER,
	    dBAProfile-Name
		DisplayString,
	    dBAProfile-PhoneNumber
		DisplayString,
	    dBAProfile-BillingNumber
		DisplayString,
	    dBAProfile-oCallType
		INTEGER,
	    dBAProfile-oCallMgm
		INTEGER,
	    dBAProfile-oDataSvc
		INTEGER,
	    dBAProfile-Force56
		INTEGER,
	    dBAProfile-BaseChannelCount
		INTEGER,
	    dBAProfile-IncrementChannelCount
		INTEGER,
	    dBAProfile-DecrementChannelCount
		INTEGER,
	    dBAProfile-oFailAction
		INTEGER,
	    dBAProfile-BitInversionRequired
		INTEGER,
	    dBAProfile-Ft1Caller
		INTEGER,
	    dBAProfile-Ft1Timeout
		INTEGER,
	    dBAProfile-CallByCallID
		INTEGER,
	    dBAProfile-CalledNumberType
		INTEGER,
	    dBAProfile-UnknownPlanUnknown
		INTEGER,
	    dBAProfile-LocalPlanIsdn
		INTEGER,
	    dBAProfile-TransitNumber
		DisplayString,
	    dBAProfile-oAutoBERT
		INTEGER,
	    dBAProfile-TimedCall
		INTEGER,
	    dBAProfile-FlagIdle
		INTEGER,
	    dBAProfile-oDynAlg
		INTEGER,
	    dBAProfile-SecondsOfHistory
		INTEGER,
	    dBAProfile-AddSecondsOfPersistence
		INTEGER,
	    dBAProfile-RemoveSecondsOfPersistence
		INTEGER,
	    dBAProfile-NailedUpGroup
		INTEGER,
	    dBAProfile-CallPassword
		DisplayString,
	    dBAProfile-DbaPriNumberingPlanId
		INTEGER,
	    dBAProfile-Action-o
		INTEGER
	}

    dBAProfile-Shelf-o	OBJECT-TYPE
	SYNTAX	INTEGER
	ACCESS	read-only
	STATUS	mandatory
	DESCRIPTION	""
	::= { mibdBAProfileEntry 1 }

    dBAProfile-Slot-o	OBJECT-TYPE
	SYNTAX	INTEGER
	ACCESS	read-only
	STATUS	mandatory
	DESCRIPTION	""
	::= { mibdBAProfileEntry 2 }

    dBAProfile-Item-o	OBJECT-TYPE
	SYNTAX	INTEGER
	ACCESS	read-only
	STATUS	mandatory
	DESCRIPTION	""
	::= { mibdBAProfileEntry 3 }

    dBAProfile-LogicalItem-o	OBJECT-TYPE
	SYNTAX	INTEGER
	ACCESS	read-only
	STATUS	mandatory
	DESCRIPTION	""
	::= { mibdBAProfileEntry 4 }

    dBAProfile-LogicalAddress-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibdBAProfileEntry 5 }

    dBAProfile-LogicalAddress-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibdBAProfileEntry 6 }

    dBAProfile-LogicalAddress-PhysicalAddress-ItemNumber	OBJECT-TYPE
	SYNTAX	INTEGER
	ACCESS	read-write
	STATUS	mandatory
	DESCRIPTION	"A number that specifies an addressable entity within the context of shelf and slot."
	::= { mibdBAProfileEntry 7 }

    dBAProfile-LogicalAddress-LogicalItem	OBJECT-TYPE
	SYNTAX	INTEGER
	ACCESS	read-write
	STATUS	mandatory
	DESCRIPTION	"A number that specifies an addressable logical entity within the context of a physical address."
	::= { mibdBAProfileEntry 8 }

    dBAProfile-Name	OBJECT-TYPE
	SYNTAX	DisplayString
	ACCESS	read-write
	STATUS	mandatory
	DESCRIPTION	"DBA Profiles are recognized by their names given them by the user. The name is a standard null terminated ASCII string."
	::= { mibdBAProfileEntry 9 }

    dBAProfile-PhoneNumber	OBJECT-TYPE
	SYNTAX	DisplayString
	ACCESS	read-write
	STATUS	mandatory
	DESCRIPTION	"The number to dial for this call."
	::= { mibdBAProfileEntry 10 }

    dBAProfile-BillingNumber	OBJECT-TYPE
	SYNTAX	DisplayString
	ACCESS	read-write
	STATUS	mandatory
	DESCRIPTION	"The billing number to use which is either a 'calling party number' or a 'billing suffix' that is appended to the end of the phone number."
	::= { mibdBAProfileEntry 11 }

    dBAProfile-oCallType	OBJECT-TYPE
	SYNTAX	INTEGER {
		    callChNBy (1),
		    callChNByBonding (2),
		    callCh1Ch (3),
		    callCh2Ch (4),
		    callChFt1 (5),
		    callChFt1Aim (6),
		    callChFt1Bo (7),
		    callChFt1StaticBo (8),
		    numberOfCallChTypes (9)
		}
	ACCESS	read-write
	STATUS	mandatory
	DESCRIPTION	"session channel type."
	::= { mibdBAProfileEntry 12 }

    dBAProfile-oCallMgm	OBJECT-TYPE
	SYNTAX	INTEGER {
		    callMgmtStaticRate (1),
		    callMgmtManualRate (2),
		    callMgmtDynamicRate (3),
		    callMgmtDeltaRate (4),
		    callMgmtTimeOfDay (5),
		    callMgmtOneOfEight (6),
		    callMgmtOneOfFourty (7),
		    callMgmtBonding0 (8),
		    callMgmtBonding1 (9),
		    callMgmtBonding2 (10),
		    callMgmtBonding3 (11),
		    numberOfCallMgmtProtocols (12)
		}
	ACCESS	read-write
	STATUS	mandatory
	DESCRIPTION	"One of the management type listed above."
	::= { mibdBAProfileEntry 13 }

    dBAProfile-oDataSvc	OBJECT-TYPE
	SYNTAX	INTEGER {
		    voice (1),
		    n-56kRestricted (2),
		    n-64kClear (3),
		    n-64kRestricted (4),
		    n-56kClear (5),
		    n-384kRestricted (6),
		    n-384kClear (7),
		    n-1536kClear (8),
		    n-1536kRestricted (9),
		    n-128kClear (10),
		    n-192kClear (11),
		    n-256kClear (12),
		    n-320kClear (13),
		    dws384Clear (14),
		    n-448Clear (15),
		    n-512Clear (16),
		    n-576Clear (17),
		    n-640Clear (18),
		    n-704Clear (19),
		    n-768Clear (20),
		    n-832Clear (21),
		    n-896Clear (22),
		    n-960Clear (23),
		    n-1024Clear (24),
		    n-1088Clear (25),
		    n-1152Clear (26),
		    n-1216Clear (27),
		    n-1280Clear (28),
		    n-1344Clear (29),
		    n-1408Clear (30),
		    n-1472Clear (31),
		    n-1600Clear (32),
		    n-1664Clear (33),
		    n-1728Clear (34),
		    n-1792Clear (35),
		    n-1856Clear (36),
		    n-1920Clear (37),
		    x30RestrictedBearer (39),
		    v110ClearBearer (40),
		    n-64kX30Restricted (41),
		    n-56kV110Clear (42),
		    modem (43),
		    atmodem (44),
		    n-2456kV110 (46),
		    n-4856kV110 (47),
		    n-9656kV110 (48),
		    n-19256kV110 (49),
		    n-38456kV110 (50),
		    n-2456krV110 (51),
		    n-4856krV110 (52),
		    n-9656krV110 (53),
		    n-19256krV110 (54),
		    n-38456krV110 (55),
		    n-2464kV110 (56),
		    n-4864kV110 (57),
		    n-9664kV110 (58),
		    n-19264kV110 (59),
		    n-38464kV110 (60),
		    n-2464krV110 (61),
		    n-4864krV110 (62),
		    n-9664krV110 (63),
		    n-19264krV110 (64),
		    n-38464krV110 (65),
		    v32 (66),
		    phs64k (67),
		    voiceOverIp (68),
		    atmSvc (70),
		    frameRelaySvc (71),
		    vpnTunnel (72),
		    wormarq (73),
		    n-14456kV110 (74),
		    n-28856kV110 (75),
		    n-14456krV110 (76),
		    n-28856krV110 (77),
		    n-14464kV110 (78),
		    n-28864kV110 (79),
		    n-14464krV110 (80),
		    n-28864krV110 (81),
		    modem31khzAudio (82),
		    x25Svc (83),
		    n-144kClear (255),
		    iptoip (263)
		}
	ACCESS	read-write
	STATUS	mandatory
	DESCRIPTION	"The type of bearer channel capability to set up for each switched call in the session."
	::= { mibdBAProfileEntry 14 }

    dBAProfile-Force56	OBJECT-TYPE
	SYNTAX	INTEGER {
		    no (1),
		    yes (2)
		}
	ACCESS	read-write
	STATUS	mandatory
	DESCRIPTION	"TRUE if the data should be treated as 7-bit data even if the switchedCallType would normally imply 8 bit data."
	::= { mibdBAProfileEntry 15 }

    dBAProfile-BaseChannelCount	OBJECT-TYPE
	SYNTAX	INTEGER
	ACCESS	read-write
	STATUS	mandatory
	DESCRIPTION	"When the session is initially set up, and if it is a fixed session, the number of channels to be used for the call."
	::= { mibdBAProfileEntry 16 }

    dBAProfile-IncrementChannelCount	OBJECT-TYPE
	SYNTAX	INTEGER
	ACCESS	read-write
	STATUS	mandatory
	DESCRIPTION	"Number of channels to increment as a block."
	::= { mibdBAProfileEntry 17 }

    dBAProfile-DecrementChannelCount	OBJECT-TYPE
	SYNTAX	INTEGER
	ACCESS	read-write
	STATUS	mandatory
	DESCRIPTION	"Number of channels to decrement as a block."
	::= { mibdBAProfileEntry 18 }

    dBAProfile-oFailAction	OBJECT-TYPE
	SYNTAX	INTEGER {
		    disc (1),
		    reduce (2),
		    retry (3),
		    numberOfFailureActions (4)
		}
	ACCESS	read-write
	STATUS	mandatory
	DESCRIPTION	"If unable to establish a dba session based on the parameters specified, then the action to be taken is specified in the failureAction."
	::= { mibdBAProfileEntry 19 }

    dBAProfile-BitInversionRequired	OBJECT-TYPE
	SYNTAX	INTEGER {
		    no (1),
		    yes (2)
		}
	ACCESS	read-write
	STATUS	mandatory
	DESCRIPTION	"TRUE if the data being transferred from the host should be inverted before being sent to the network, and FALSE otherwise. I think this needs to be supported by the device, but I will check before committing. Also, this affects the network interface too, I think."
	::= { mibdBAProfileEntry 20 }

    dBAProfile-Ft1Caller	OBJECT-TYPE
	SYNTAX	INTEGER {
		    no (1),
		    yes (2)
		}
	ACCESS	read-write
	STATUS	mandatory
	DESCRIPTION	"BOOLEAN which is true for Fractional T1 calls when this side is the caller, and FALSE otherwise."
	::= { mibdBAProfileEntry 21 }

    dBAProfile-Ft1Timeout	OBJECT-TYPE
	SYNTAX	INTEGER
	ACCESS	read-write
	STATUS	mandatory
	DESCRIPTION	""
	::= { mibdBAProfileEntry 22 }

    dBAProfile-CallByCallID	OBJECT-TYPE
	SYNTAX	INTEGER
	ACCESS	read-write
	STATUS	mandatory
	DESCRIPTION	"The ID for the call-by-call signalling for PRI."
	::= { mibdBAProfileEntry 23 }

    dBAProfile-CalledNumberType	OBJECT-TYPE
	SYNTAX	INTEGER
	ACCESS	read-write
	STATUS	mandatory
	DESCRIPTION	"Indication of whether national number, international number, etc. is specified."
	::= { mibdBAProfileEntry 24 }

    dBAProfile-UnknownPlanUnknown	OBJECT-TYPE
	SYNTAX	INTEGER {
		    no (1),
		    yes (2)
		}
	ACCESS	read-write
	STATUS	mandatory
	DESCRIPTION	"If TRUE indicates that UNKNOWN number plan is used in conjunction with unknown number instead of default, ISDN."
	::= { mibdBAProfileEntry 25 }

    dBAProfile-LocalPlanIsdn	OBJECT-TYPE
	SYNTAX	INTEGER {
		    no (1),
		    yes (2)
		}
	ACCESS	read-write
	STATUS	mandatory
	DESCRIPTION	"If TRUE indicates that ISDN number plan is used in conjunction with local number instead of default, PRIVATE."
	::= { mibdBAProfileEntry 26 }

    dBAProfile-TransitNumber	OBJECT-TYPE
	SYNTAX	DisplayString
	ACCESS	read-write
	STATUS	mandatory
	DESCRIPTION	"The string for use in the 'transit network ie' for PRI calling when going through a LEC."
	::= { mibdBAProfileEntry 27 }

    dBAProfile-oAutoBERT	OBJECT-TYPE
	SYNTAX	INTEGER {
		    off (1),
		    n-15Sec (2),
		    n-30Sec (3),
		    n-60Sec (4),
		    n-90Sec (5),
		    n-120Sec (6),
		    numberOfBertTestOptions (7)
		}
	ACCESS	read-write
	STATUS	mandatory
	DESCRIPTION	"Should we BERT at session startup and for how long."
	::= { mibdBAProfileEntry 28 }

    dBAProfile-TimedCall	OBJECT-TYPE
	SYNTAX	INTEGER {
		    no (1),
		    yes (2)
		}
	ACCESS	read-write
	STATUS	mandatory
	DESCRIPTION	"TRUE if we should pay attention to the following time period parameters. Not used when the call type is dynamic N-by."
	::= { mibdBAProfileEntry 29 }

    dBAProfile-FlagIdle	OBJECT-TYPE
	SYNTAX	INTEGER {
		    no (1),
		    yes (2)
		}
	ACCESS	read-write
	STATUS	mandatory
	DESCRIPTION	"TRUE if looking for flag idle, FALSE when looking for mark idle."
	::= { mibdBAProfileEntry 30 }

    dBAProfile-oDynAlg	OBJECT-TYPE
	SYNTAX	INTEGER {
		    constant (1),
		    linear (2),
		    quadratic (3)
		}
	ACCESS	read-write
	STATUS	mandatory
	DESCRIPTION	"The algorithm to use for determining weighted line utilization."
	::= { mibdBAProfileEntry 31 }

    dBAProfile-SecondsOfHistory	OBJECT-TYPE
	SYNTAX	INTEGER
	ACCESS	read-write
	STATUS	mandatory
	DESCRIPTION	"Number of seconds to keep history data around for. This number is in the range of 1 through MAX_HISTORY_SECONDS."
	::= { mibdBAProfileEntry 32 }

    dBAProfile-AddSecondsOfPersistence	OBJECT-TYPE
	SYNTAX	INTEGER
	ACCESS	read-write
	STATUS	mandatory
	DESCRIPTION	"Once the upper threshold of utilization is passed, the number of seconds it should stay there is defined here."
	::= { mibdBAProfileEntry 33 }

    dBAProfile-RemoveSecondsOfPersistence	OBJECT-TYPE
	SYNTAX	INTEGER
	ACCESS	read-write
	STATUS	mandatory
	DESCRIPTION	"Once the lower threshold of utilization is passed, the number of seconds it should stay there is defined here."
	::= { mibdBAProfileEntry 34 }

    dBAProfile-NailedUpGroup	OBJECT-TYPE
	SYNTAX	INTEGER
	ACCESS	read-write
	STATUS	mandatory
	DESCRIPTION	"Nailed-up group letter. This is a group or number field as defined in lcdparam.h."
	::= { mibdBAProfileEntry 35 }

    dBAProfile-CallPassword	OBJECT-TYPE
	SYNTAX	DisplayString
	ACCESS	read-write
	STATUS	mandatory
	DESCRIPTION	"DBA call password authenticated against port's password on receiver side. Ignored if port's password is not defined."
	::= { mibdBAProfileEntry 36 }

    dBAProfile-DbaPriNumberingPlanId	OBJECT-TYPE
	SYNTAX	INTEGER
	ACCESS	read-write
	STATUS	mandatory
	DESCRIPTION	"PRI Called Party element's Numbering-Plan-ID value for outgoing T1-to-PRI calls."
	::= { mibdBAProfileEntry 37 }

    dBAProfile-Action-o	OBJECT-TYPE
	SYNTAX	INTEGER {
		    noAction (1),
		    createProfile (2),
		    deleteProfile (3)
		}
	ACCESS	read-write
	STATUS	mandatory
	DESCRIPTION	""
	::= { mibdBAProfileEntry 38 }


	-- The mibdBAProfile__timer_period_parameters table
	--
	-- This table contains parameters for the mibdBAProfile__timer_period_parameters profile
	--

    mibdBAProfile-TimerPeriodParametersTable	OBJECT-TYPE
	SYNTAX		SEQUENCE OF MibdBAProfile-TimerPeriodParametersEntry
	ACCESS		not-accessible
	STATUS		mandatory
	DESCRIPTION	"A list of mibdBAProfile__timer_period_parameters profile entries."
	::= { mibdBAProfile 2 }

    mibdBAProfile-TimerPeriodParametersEntry	OBJECT-TYPE
	SYNTAX		MibdBAProfile-TimerPeriodParametersEntry
	ACCESS		not-accessible
	STATUS		mandatory
	DESCRIPTION	"A mibdBAProfile__timer_period_parameters entry containing objects that
			 maps to the parameters of mibdBAProfile__timer_period_parameters profile."
	INDEX		{ dBAProfile-TimerPeriodParameters-Shelf-o, dBAProfile-TimerPeriodParameters-Slot-o, dBAProfile-TimerPeriodParameters-Item-o, dBAProfile-TimerPeriodParameters-LogicalItem-o, dBAProfile-TimerPeriodParameters-Index-o }
	::= { mibdBAProfile-TimerPeriodParametersTable 1 }

    MibdBAProfile-TimerPeriodParametersEntry ::=
	SEQUENCE {
	    dBAProfile-TimerPeriodParameters-Shelf-o
		INTEGER,
	    dBAProfile-TimerPeriodParameters-Slot-o
		INTEGER,
	    dBAProfile-TimerPeriodParameters-Item-o
		INTEGER,
	    dBAProfile-TimerPeriodParameters-LogicalItem-o
		INTEGER,
	    dBAProfile-TimerPeriodParameters-Index-o
		INTEGER,
	    dBAProfile-TimerPeriodParameters-oActiv
		INTEGER,
	    dBAProfile-TimerPeriodParameters-StartingTime
		INTEGER,
	    dBAProfile-TimerPeriodParameters-MinimumChannelCount
		INTEGER,
	    dBAProfile-TimerPeriodParameters-MaximumChannelCount
		INTEGER,
	    dBAProfile-TimerPeriodParameters-TargetUtilization
		INTEGER,
	    dBAProfile-TimerPeriodParameters-X25chanTargetUtilization
		INTEGER
	}

    dBAProfile-TimerPeriodParameters-Shelf-o	OBJECT-TYPE
	SYNTAX	INTEGER
	ACCESS	read-only
	STATUS	mandatory
	DESCRIPTION	""
	::= { mibdBAProfile-TimerPeriodParametersEntry 1 }

    dBAProfile-TimerPeriodParameters-Slot-o	OBJECT-TYPE
	SYNTAX	INTEGER
	ACCESS	read-only
	STATUS	mandatory
	DESCRIPTION	""
	::= { mibdBAProfile-TimerPeriodParametersEntry 2 }

    dBAProfile-TimerPeriodParameters-Item-o	OBJECT-TYPE
	SYNTAX	INTEGER
	ACCESS	read-only
	STATUS	mandatory
	DESCRIPTION	""
	::= { mibdBAProfile-TimerPeriodParametersEntry 3 }

    dBAProfile-TimerPeriodParameters-LogicalItem-o	OBJECT-TYPE
	SYNTAX	INTEGER
	ACCESS	read-only
	STATUS	mandatory
	DESCRIPTION	""
	::= { mibdBAProfile-TimerPeriodParametersEntry 4 }

    dBAProfile-TimerPeriodParameters-Index-o	OBJECT-TYPE
	SYNTAX	INTEGER
	ACCESS	read-only
	STATUS	mandatory
	DESCRIPTION	""
	::= { mibdBAProfile-TimerPeriodParametersEntry 5 }

    dBAProfile-TimerPeriodParameters-oActiv	OBJECT-TYPE
	SYNTAX	INTEGER {
		    disabled (1),
		    enabled (2),
		    shutdown (3)
		}
	ACCESS	read-write
	STATUS	mandatory
	DESCRIPTION	"Like the other sub-structures above, the number of time-periods actually used is variable. Therefore, this is an indication within each structure of usage."
	::= { mibdBAProfile-TimerPeriodParametersEntry 6 }

    dBAProfile-TimerPeriodParameters-StartingTime	OBJECT-TYPE
	SYNTAX	INTEGER
	ACCESS	read-write
	STATUS	mandatory
	DESCRIPTION	"Each time period has a starting time, and an ending time (which is implicit by the next starting time specified in another structure). The starting time is specified internally as the number of seconds after midnight, where midnight itself has a value of zero."
	::= { mibdBAProfile-TimerPeriodParametersEntry 7 }

    dBAProfile-TimerPeriodParameters-MinimumChannelCount	OBJECT-TYPE
	SYNTAX	INTEGER
	ACCESS	read-write
	STATUS	mandatory
	DESCRIPTION	"The smallest number of channels to use during this time period."
	::= { mibdBAProfile-TimerPeriodParametersEntry 8 }

    dBAProfile-TimerPeriodParameters-MaximumChannelCount	OBJECT-TYPE
	SYNTAX	INTEGER
	ACCESS	read-write
	STATUS	mandatory
	DESCRIPTION	"The maximum number of channels to use during this time period."
	::= { mibdBAProfile-TimerPeriodParametersEntry 9 }

    dBAProfile-TimerPeriodParameters-TargetUtilization	OBJECT-TYPE
	SYNTAX	INTEGER
	ACCESS	read-write
	STATUS	mandatory
	DESCRIPTION	"The percentage utilization to aim for. This is used as a parameter to the bandwidth heuristics."
	::= { mibdBAProfile-TimerPeriodParametersEntry 10 }

    dBAProfile-TimerPeriodParameters-X25chanTargetUtilization	OBJECT-TYPE
	SYNTAX	INTEGER
	ACCESS	read-write
	STATUS	mandatory
	DESCRIPTION	"The percentage utilization to aim for. This is used as a parameter to the bandwidth heuristics."
	::= { mibdBAProfile-TimerPeriodParametersEntry 11 }

END
