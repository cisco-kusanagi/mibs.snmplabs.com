--
-- This SMIv2 module has been generated by smidump 0.2-cvs. Do not edit.
--

SONUS-DSP-RESOURCES-MIB DEFINITIONS ::= BEGIN

IMPORTS
    Integer32, MODULE-IDENTITY, NOTIFICATION-TYPE, OBJECT-TYPE
        FROM SNMPv2-SMI
    RowStatus
        FROM SNMPv2-TC
    sonusEventClass, sonusEventDescription, sonusEventLevel, 
    sonusShelfIndex
        FROM SONUS-COMMON-MIB
    sonusResourcesMIBs
        FROM SONUS-SMI
    SonusAdminState, SonusName, SonusShelfIndex
        FROM SONUS-TC;

sonusDspResourcesMIB MODULE-IDENTITY
    LAST-UPDATED    "200107310000Z"
    ORGANIZATION    
            "Sonus Networks, Inc."
    CONTACT-INFO    
            "   Customer Support    
             Sonus Networks, Inc,
             5 Carlisle Road
             Westford, MA 01886
             USA
             
             Tel: 978-692-8999
             Fax: 978-392-9118
             E-mail: cs.snmp@sonusnet.com"
    DESCRIPTION     
            "The MIB Module for DSP Resources Management."
    ::= { sonusResourcesMIBs 1 }


sonusDspResourcesMIBObjects OBJECT IDENTIFIER
    ::= { sonusDspResourcesMIB 1 }

sonusChannelStatTable OBJECT IDENTIFIER
    ::= { sonusDspResourcesMIBObjects 1 }

sonusDspAdmnTable OBJECT-TYPE
    SYNTAX          SEQUENCE OF SonusDspAdmnEntry
    MAX-ACCESS      not-accessible
    STATUS          current
    DESCRIPTION     
            "Table of Sonus Enterprise DSP Admn information"
    ::= { sonusDspResourcesMIBObjects 2 }

sonusDspAdmnEntry OBJECT-TYPE
    SYNTAX          SonusDspAdmnEntry
    MAX-ACCESS      not-accessible
    STATUS          current
    DESCRIPTION     
            "Entry in Table consisting of the all the Sonus DSP ADMN information"
    INDEX           { sonusDspAdmnShelfIndex, sonusDspAdmnSlotIndex, 
                      sonusDspAdmnDspIndex }
    ::= { sonusDspAdmnTable 1 }

SonusDspAdmnEntry ::=
    SEQUENCE {
        sonusDspAdmnShelfIndex          Integer32,
        sonusDspAdmnSlotIndex           Integer32,
        sonusDspAdmnDspIndex            Integer32,
        sonusDspAdmnType                INTEGER,
        sonusDspAdmnNumChannels         Integer32,
        sonusDspAdmnMaxTail             INTEGER,
        sonusDspAdmnEcAudioType         INTEGER,
        sonusDspAdmnEcSignallingTone    INTEGER,
        sonusDspAdmnNlpDisable          Integer32,
        sonusDspAdmnNlpEnable           Integer32,
        sonusDspAdmnJitterEvalPeriod    Integer32,
        sonusDspAdmnJitterMinOccThsh    Integer32,
        sonusDspResidualEchoControl     INTEGER,
        sonusDspEchoReturnLoss          INTEGER,
        sonusDspModemDisable            INTEGER,
        sonusDspHighLevelComp           INTEGER
    }

sonusDspAdmnShelfIndex OBJECT-TYPE
    SYNTAX          Integer32
    MAX-ACCESS      read-only
    STATUS          current
    DESCRIPTION     
            "Shelf Index for this table"
    ::= { sonusDspAdmnEntry 1 }

sonusDspAdmnSlotIndex OBJECT-TYPE
    SYNTAX          Integer32
    MAX-ACCESS      read-only
    STATUS          current
    DESCRIPTION     
            "Slot index for this table"
    ::= { sonusDspAdmnEntry 2 }

sonusDspAdmnDspIndex OBJECT-TYPE
    SYNTAX          Integer32
    MAX-ACCESS      read-only
    STATUS          current
    DESCRIPTION     
            "DSP index into this table"
    ::= { sonusDspAdmnEntry 3 }

sonusDspAdmnType OBJECT-TYPE
    SYNTAX          INTEGER { vpad(1), hdlc(2), g729AB(3), tone(4) }
    MAX-ACCESS      read-write
    STATUS          current
    DESCRIPTION     
            "DSP Function Type, VPAD XPAD TONE etc."
    ::= { sonusDspAdmnEntry 4 }

sonusDspAdmnNumChannels OBJECT-TYPE
    SYNTAX          Integer32
    MAX-ACCESS      read-write
    STATUS          current
    DESCRIPTION     
            "Number of channels on this DSP"
    ::= { sonusDspAdmnEntry 5 }

sonusDspAdmnMaxTail OBJECT-TYPE
    SYNTAX          INTEGER { millisecs24(1), millisec32(2), 
                        millisec48(3), millisec64(4) }
    MAX-ACCESS      read-write
    STATUS          current
    DESCRIPTION     
            "Maximum Echo tail length"
    DEFVAL          { millisec64 }
    ::= { sonusDspAdmnEntry 6 }

sonusDspAdmnEcAudioType OBJECT-TYPE
    SYNTAX          INTEGER { uLaw(1), aLaw(2) }
    MAX-ACCESS      read-write
    STATUS          current
    DESCRIPTION     
            "Echo Cancellation: A-law or U-law"
    DEFVAL          { uLaw }
    ::= { sonusDspAdmnEntry 7 }

sonusDspAdmnEcSignallingTone OBJECT-TYPE
    SYNTAX          INTEGER { none(1), c5(2) }
    MAX-ACCESS      read-write
    STATUS          current
    DESCRIPTION     
            "Echo Cancellation: None, 2400, 2600 or 2101 Hz"
    DEFVAL          { none }
    ::= { sonusDspAdmnEntry 8 }

sonusDspAdmnNlpDisable OBJECT-TYPE
    SYNTAX          Integer32 (0..15)
    MAX-ACCESS      read-write
    STATUS          current
    DESCRIPTION     
            "Non-linear processing control, Disable"
    DEFVAL          { 6 }
    ::= { sonusDspAdmnEntry 9 }

sonusDspAdmnNlpEnable OBJECT-TYPE
    SYNTAX          Integer32 (0..15)
    MAX-ACCESS      read-write
    STATUS          current
    DESCRIPTION     
            "Non-linear processing control, Enable"
    DEFVAL          { 12 }
    ::= { sonusDspAdmnEntry 10 }

sonusDspAdmnJitterEvalPeriod OBJECT-TYPE
    SYNTAX          Integer32 (0..65535)
    MAX-ACCESS      read-write
    STATUS          current
    DESCRIPTION     
            "Time period to decide when to periodically evaluate playout
             occupancy in units of 1.25 msec = 1 subframe"
    DEFVAL          { 800 }
    ::= { sonusDspAdmnEntry 11 }

sonusDspAdmnJitterMinOccThsh OBJECT-TYPE
    SYNTAX          Integer32 (10..65535)
    MAX-ACCESS      read-write
    STATUS          current
    DESCRIPTION     
            "If occupancy falls below this threshold for some time
             period we advance the playout time. Units are 125usec samples"
    DEFVAL          { 160 }
    ::= { sonusDspAdmnEntry 12 }

sonusDspResidualEchoControl OBJECT-TYPE
    SYNTAX          INTEGER { cancelOnly(1), suppressResidual(2), 
                        comfortNoise(4) }
    MAX-ACCESS      read-write
    STATUS          current
    DESCRIPTION     
            "For Network Echo Cancellation, specifies the residual echo
             cancellation."
    DEFVAL          { comfortNoise }
    ::= { sonusDspAdmnEntry 13 }

sonusDspEchoReturnLoss OBJECT-TYPE
    SYNTAX          INTEGER { dB6(1), dB3(2), dB0(3) }
    MAX-ACCESS      read-write
    STATUS          current
    DESCRIPTION     
            "For Network Echo Cancellation, specifies the echo
             return loss in dB's. Default value is 6dB."
    DEFVAL          { dB6 }
    ::= { sonusDspAdmnEntry 14 }

sonusDspModemDisable OBJECT-TYPE
    SYNTAX          INTEGER { ignore2100Hz(1), g164(2), g165(4) }
    MAX-ACCESS      read-write
    STATUS          current
    DESCRIPTION     
            "For Network Echo Cancellation, specifies whether to disable
             echo cancellation when a modem tone is detected."
    DEFVAL          { g165 }
    ::= { sonusDspAdmnEntry 15 }

sonusDspHighLevelComp OBJECT-TYPE
    SYNTAX          INTEGER { none(1), dB6(2) }
    MAX-ACCESS      read-write
    STATUS          current
    DESCRIPTION     
            "For Network Echo Cancellation, the high level compensation
             value. Default value is to attenuate by 6dB."
    DEFVAL          { dB6 }
    ::= { sonusDspAdmnEntry 16 }

sonusDspStatTable OBJECT IDENTIFIER
    ::= { sonusDspResourcesMIBObjects 3 }

sonusDspSlotStatTable OBJECT-TYPE
    SYNTAX          SEQUENCE OF SonusDspSlotStatEntry
    MAX-ACCESS      not-accessible
    STATUS          current
    DESCRIPTION     
            "Table of Sonus Enterprise DSP Resource Status for a particular slot"
    ::= { sonusDspResourcesMIBObjects 4 }

sonusDspSlotStatEntry OBJECT-TYPE
    SYNTAX          SonusDspSlotStatEntry
    MAX-ACCESS      not-accessible
    STATUS          current
    DESCRIPTION     
            "Entry in Table consisting of Sonus DSP Resource Status information for a particular slot"
    INDEX           { sonusDspSlotStatShelfIndex, 
                      sonusDspSlotStatSlotIndex }
    ::= { sonusDspSlotStatTable 1 }

SonusDspSlotStatEntry ::=
    SEQUENCE {
        sonusDspSlotStatShelfIndex      Integer32,
        sonusDspSlotStatSlotIndex       Integer32,
        sonusDspSlotStatG711EcTotal     Integer32,
        sonusDspSlotStatG711Total       Integer32,
        sonusDspSlotStatHdlcTotal       Integer32,
        sonusDspSlotStatToneTotal       Integer32,
        sonusDspSlotStatG729AbTotal     Integer32,
        sonusDspSlotStatG711EcUtilization Integer32,
        sonusDspSlotStatG711EcAllocFailures   Integer32,
        sonusDspSlotStatG711Utilization Integer32,
        sonusDspSlotStatG711AllocFailures Integer32,
        sonusDspSlotStatHdlcUtilization Integer32,
        sonusDspSlotStatHdlcAllocFailures Integer32,
        sonusDspSlotStatToneUtilization Integer32,
        sonusDspSlotStatToneAllocFailures Integer32,
        sonusDspSlotStatG729AbUtilization Integer32,
        sonusDspSlotStatG729AbAllocFailures   Integer32
    }

sonusDspSlotStatShelfIndex OBJECT-TYPE
    SYNTAX          Integer32
    MAX-ACCESS      read-only
    STATUS          current
    DESCRIPTION     
            "Shelf index for this table"
    ::= { sonusDspSlotStatEntry 1 }

sonusDspSlotStatSlotIndex OBJECT-TYPE
    SYNTAX          Integer32
    MAX-ACCESS      read-only
    STATUS          current
    DESCRIPTION     
            "Slot index for this table"
    ::= { sonusDspSlotStatEntry 2 }

sonusDspSlotStatG711EcTotal OBJECT-TYPE
    SYNTAX          Integer32
    MAX-ACCESS      read-only
    STATUS          current
    DESCRIPTION     
            "Total number of G711 with Echo Cancellation resources available on this slot"
    ::= { sonusDspSlotStatEntry 3 }

sonusDspSlotStatG711Total OBJECT-TYPE
    SYNTAX          Integer32
    MAX-ACCESS      read-only
    STATUS          current
    DESCRIPTION     
            "Total number of G711 resources available on this slot"
    ::= { sonusDspSlotStatEntry 4 }

sonusDspSlotStatHdlcTotal OBJECT-TYPE
    SYNTAX          Integer32
    MAX-ACCESS      read-only
    STATUS          current
    DESCRIPTION     
            "Total number of HDLC resources available on this slot"
    ::= { sonusDspSlotStatEntry 5 }

sonusDspSlotStatToneTotal OBJECT-TYPE
    SYNTAX          Integer32
    MAX-ACCESS      read-only
    STATUS          current
    DESCRIPTION     
            "Total number of Tones resources available on this slot"
    ::= { sonusDspSlotStatEntry 6 }

sonusDspSlotStatG729AbTotal OBJECT-TYPE
    SYNTAX          Integer32
    MAX-ACCESS      read-only
    STATUS          current
    DESCRIPTION     
            "Total number of G729A+B resources available on this slot"
    ::= { sonusDspSlotStatEntry 7 }

sonusDspSlotStatG711EcUtilization OBJECT-TYPE
    SYNTAX          Integer32
    MAX-ACCESS      read-only
    STATUS          current
    DESCRIPTION     
            "Percentage utilization of G711 Echo canceller resources on this slot"
    ::= { sonusDspSlotStatEntry 8 }

sonusDspSlotStatG711EcAllocFailures OBJECT-TYPE
    SYNTAX          Integer32
    MAX-ACCESS      read-only
    STATUS          current
    DESCRIPTION     
            "Percentage of G711 Echo canceller resources allocation failures on this slot"
    ::= { sonusDspSlotStatEntry 9 }

sonusDspSlotStatG711Utilization OBJECT-TYPE
    SYNTAX          Integer32
    MAX-ACCESS      read-only
    STATUS          current
    DESCRIPTION     
            "Percentage utilization of G711 resources on this slot"
    ::= { sonusDspSlotStatEntry 10 }

sonusDspSlotStatG711AllocFailures OBJECT-TYPE
    SYNTAX          Integer32
    MAX-ACCESS      read-only
    STATUS          current
    DESCRIPTION     
            "Percentage of G711 resources allocation failures on this slot"
    ::= { sonusDspSlotStatEntry 11 }

sonusDspSlotStatHdlcUtilization OBJECT-TYPE
    SYNTAX          Integer32
    MAX-ACCESS      read-only
    STATUS          current
    DESCRIPTION     
            "Percentage utilization HDLC resources on this slot"
    ::= { sonusDspSlotStatEntry 12 }

sonusDspSlotStatHdlcAllocFailures OBJECT-TYPE
    SYNTAX          Integer32
    MAX-ACCESS      read-only
    STATUS          current
    DESCRIPTION     
            "Percentage of HDLC resources allocation failures on this slot"
    ::= { sonusDspSlotStatEntry 13 }

sonusDspSlotStatToneUtilization OBJECT-TYPE
    SYNTAX          Integer32
    MAX-ACCESS      read-only
    STATUS          current
    DESCRIPTION     
            "Percentage utilization of Tone resources on this slot"
    ::= { sonusDspSlotStatEntry 14 }

sonusDspSlotStatToneAllocFailures OBJECT-TYPE
    SYNTAX          Integer32
    MAX-ACCESS      read-only
    STATUS          current
    DESCRIPTION     
            "Percentage of Tone resources allocation failures on this slot"
    ::= { sonusDspSlotStatEntry 15 }

sonusDspSlotStatG729AbUtilization OBJECT-TYPE
    SYNTAX          Integer32
    MAX-ACCESS      read-only
    STATUS          current
    DESCRIPTION     
            "Percentage utilization of G729A+B resources on this slot"
    ::= { sonusDspSlotStatEntry 16 }

sonusDspSlotStatG729AbAllocFailures OBJECT-TYPE
    SYNTAX          Integer32
    MAX-ACCESS      read-only
    STATUS          current
    DESCRIPTION     
            "Percentage of G729A+B resources allocation failures on this slot"
    ::= { sonusDspSlotStatEntry 17 }

sonusPadAdmnTable OBJECT-TYPE
    SYNTAX          SEQUENCE OF SonusPadAdmnEntry
    MAX-ACCESS      not-accessible
    STATUS          current
    DESCRIPTION     
            "Table of Sonus Enterprise Packet Assembler Dis-Assembler Admn information"
    ::= { sonusDspResourcesMIBObjects 5 }

sonusPadAdmnEntry OBJECT-TYPE
    SYNTAX          SonusPadAdmnEntry
    MAX-ACCESS      not-accessible
    STATUS          current
    DESCRIPTION     
            "Entry in Table consisting of the Sonus Packet Assembler Dis-assembler Administartion information"
    INDEX           { sonusPadAdmnShelfIndex }
    ::= { sonusPadAdmnTable 1 }

SonusPadAdmnEntry ::=
    SEQUENCE {
        sonusPadAdmnShelfIndex          SonusShelfIndex,
        sonusPadAdmnJitterEvalPeriod    Integer32,
        sonusPadAdmnJitterMinOccThsh    Integer32,
        sonusPadAdmnRtpG711ALaw         Integer32,
        sonusPadAdmnRtpG711ULaw         Integer32,
        sonusPadAdmnRtpG729A            Integer32,
        sonusPadAdmnRtpG729AB           Integer32,
        sonusPadAdmnG729ABThreshold     Integer32,
        sonusPadAdmnG729ABThresholdState SonusAdminState,
        sonusPadAdmnToneThreshold       Integer32,
        sonusPadAdmnToneThresholdState  SonusAdminState,
        sonusPadAdmnRowStatus           RowStatus,
        sonusPadAdmnRtpDtmfRelay        Integer32,
        sonusPadAdmnRtpFaxRelay         Integer32,
        sonusPadAdmnSidMinTime          Integer32,
        sonusPadAdmnSidMaxTime          Integer32,
        sonusPadAdmnSidHangoverTime     Integer32,
        sonusPadAdmnSidMinNoiseFloor    Integer32,
        sonusPadAdmnSidMaxNoiseFloor    Integer32,
        sonusPadAdmnComfortEnergy       Integer32
    }

sonusPadAdmnShelfIndex OBJECT-TYPE
    SYNTAX          SonusShelfIndex
    MAX-ACCESS      read-only
    STATUS          current
    DESCRIPTION     
            "Shelf Index for Sonus PAD table."
    ::= { sonusPadAdmnEntry 1 }

sonusPadAdmnJitterEvalPeriod OBJECT-TYPE
    SYNTAX          Integer32 (10..300000)
    MAX-ACCESS      read-write
    STATUS          current
    DESCRIPTION     
            "Time period to decide when to periodically evaluate playout
             occupancy in units of millisecond."
    DEFVAL          { 1000 }
    ::= { sonusPadAdmnEntry 2 }

sonusPadAdmnJitterMinOccThsh OBJECT-TYPE
    SYNTAX          Integer32 (2..200)
    MAX-ACCESS      read-write
    STATUS          current
    DESCRIPTION     
            "If occupancy falls below this threshold for some time
             period we advance the playout time in units of millisecond."
    DEFVAL          { 20 }
    ::= { sonusPadAdmnEntry 3 }

sonusPadAdmnRtpG711ALaw OBJECT-TYPE
    SYNTAX          Integer32 (0..127)
    MAX-ACCESS      read-write
    STATUS          obsolete
    DESCRIPTION     
            "This Payload type is no longer configurable. It has been standardized in
             RFC 1890."
    DEFVAL          { 8 }
    ::= { sonusPadAdmnEntry 4 }

sonusPadAdmnRtpG711ULaw OBJECT-TYPE
    SYNTAX          Integer32 (0..127)
    MAX-ACCESS      read-write
    STATUS          obsolete
    DESCRIPTION     
            "This Payload type is no longer configurable. It has been standardized in
             RFC 1890."
    DEFVAL          { 0 }
    ::= { sonusPadAdmnEntry 5 }

sonusPadAdmnRtpG729A OBJECT-TYPE
    SYNTAX          Integer32 (0..127)
    MAX-ACCESS      read-write
    STATUS          obsolete
    DESCRIPTION     
            "This Payload type is no longer configurable. It has been standardized in
             RFC 1890."
    DEFVAL          { 18 }
    ::= { sonusPadAdmnEntry 6 }

sonusPadAdmnRtpG729AB OBJECT-TYPE
    SYNTAX          Integer32 (0..127)
    MAX-ACCESS      read-write
    STATUS          obsolete
    DESCRIPTION     
            "This Payload type is no longer configurable. It has been standardized in
             RFC 1890."
    DEFVAL          { 18 }
    ::= { sonusPadAdmnEntry 7 }

sonusPadAdmnG729ABThreshold OBJECT-TYPE
    SYNTAX          Integer32 (1..100)
    MAX-ACCESS      read-write
    STATUS          current
    DESCRIPTION     
            "Perecentage Threshold crossing value for G729AB resources. When this threshold is 
             reached an event will be generated if sonusPadAdmnG729ABThresholdState is enabled."
    DEFVAL          { 90 }
    ::= { sonusPadAdmnEntry 8 }

sonusPadAdmnG729ABThresholdState OBJECT-TYPE
    SYNTAX          SonusAdminState
    MAX-ACCESS      read-write
    STATUS          current
    DESCRIPTION     
            "State of G729AB Threshold Event, Enabled/Disabled. An event will be generated only 
             if state is enabled."
    DEFVAL          { enabled }
    ::= { sonusPadAdmnEntry 9 }

sonusPadAdmnToneThreshold OBJECT-TYPE
    SYNTAX          Integer32 (1..100)
    MAX-ACCESS      read-write
    STATUS          current
    DESCRIPTION     
            "Perecentage Threshold crossing value for tone resources. When this threshold is 
             reached an event will be generated if sonusPadAdmnToneThresholdState is enabled."
    DEFVAL          { 90 }
    ::= { sonusPadAdmnEntry 10 }

sonusPadAdmnToneThresholdState OBJECT-TYPE
    SYNTAX          SonusAdminState
    MAX-ACCESS      read-write
    STATUS          current
    DESCRIPTION     
            "State of Tone Threshold Event, Enabled/Disabled. An event will be generated only 
             if state is enabled."
    DEFVAL          { enabled }
    ::= { sonusPadAdmnEntry 11 }

sonusPadAdmnRowStatus OBJECT-TYPE
    SYNTAX          RowStatus
    MAX-ACCESS      read-only
    STATUS          current
    DESCRIPTION     
            "This object is used to create, delete, or modify a row in this table."
    ::= { sonusPadAdmnEntry 12 }

sonusPadAdmnRtpDtmfRelay OBJECT-TYPE
    SYNTAX          Integer32 (0..127)
    MAX-ACCESS      read-write
    STATUS          current
    DESCRIPTION     
            "RTP Payload type used for DTMF relay during compressed calls."
    DEFVAL          { 100 }
    ::= { sonusPadAdmnEntry 13 }

sonusPadAdmnRtpFaxRelay OBJECT-TYPE
    SYNTAX          Integer32 (0..127)
    MAX-ACCESS      read-write
    STATUS          current
    DESCRIPTION     
            "RTP Payload type used for fax relay during compressed calls."
    DEFVAL          { 101 }
    ::= { sonusPadAdmnEntry 14 }

sonusPadAdmnSidMinTime OBJECT-TYPE
    SYNTAX          Integer32 (50..300000)
    MAX-ACCESS      read-write
    STATUS          current
    DESCRIPTION     
            "Minimum time between silence packets. In units of millisecond."
    DEFVAL          { 200 }
    ::= { sonusPadAdmnEntry 15 }

sonusPadAdmnSidMaxTime OBJECT-TYPE
    SYNTAX          Integer32 (50..300000)
    MAX-ACCESS      read-write
    STATUS          current
    DESCRIPTION     
            "Maximum time between silence packets. Must be larger than minimum time
             between silence packets. In units of millisecond."
    DEFVAL          { 2000 }
    ::= { sonusPadAdmnEntry 16 }

sonusPadAdmnSidHangoverTime OBJECT-TYPE
    SYNTAX          Integer32 (80..2560)
    MAX-ACCESS      read-write
    STATUS          current
    DESCRIPTION     
            "Minimum time after a VAD detects speaker going inactive before sending a
             silence packets. In units of millisecond."
    DEFVAL          { 300 }
    ::= { sonusPadAdmnEntry 17 }

sonusPadAdmnSidMinNoiseFloor OBJECT-TYPE
    SYNTAX          Integer32 (24..62)
    MAX-ACCESS      read-write
    STATUS          current
    DESCRIPTION     
            "Minimum noise floor, if energy level is below this it will be 
             considered as silence. Configuration range is between -62dBm -24dBm."
    DEFVAL          { 60 }
    ::= { sonusPadAdmnEntry 18 }

sonusPadAdmnSidMaxNoiseFloor OBJECT-TYPE
    SYNTAX          Integer32 (24..62)
    MAX-ACCESS      read-write
    STATUS          current
    DESCRIPTION     
            "Maximum noise floor, if the energy level is above this it will 
             be considered as speech. Configuration range is between -62dBm -24dBm."
    DEFVAL          { 48 }
    ::= { sonusPadAdmnEntry 19 }

sonusPadAdmnComfortEnergy OBJECT-TYPE
    SYNTAX          Integer32 (35..90)
    MAX-ACCESS      read-write
    STATUS          current
    DESCRIPTION     
            "Initial estimate to be used for generating comfort noise. It is used when 
             no silence packets are received to generate comfort noise. 
             Configuration range is between -90dBm and -35dBm."
    DEFVAL          { 56 }
    ::= { sonusPadAdmnEntry 20 }

sonusEchoCancellorProfile OBJECT IDENTIFIER
    ::= { sonusDspResourcesMIBObjects 6 }

sonusEchoCancellorProfileNextIndex OBJECT-TYPE
    SYNTAX          Integer32
    MAX-ACCESS      read-only
    STATUS          current
    DESCRIPTION     
            "The next valid index to use when creating an entry in
             the sonusEchoCancellorProfile."
    ::= { sonusEchoCancellorProfile 1 }

sonusEchoCancellorProfileTable OBJECT-TYPE
    SYNTAX          SEQUENCE OF SonusEchoCancellorProfileEntry
    MAX-ACCESS      not-accessible
    STATUS          current
    DESCRIPTION     
            "Table of Sonus Enterprise Echo Canceller Profile information"
    ::= { sonusEchoCancellorProfile 2 }

sonusEchoCancellorProfileEntry OBJECT-TYPE
    SYNTAX          SonusEchoCancellorProfileEntry
    MAX-ACCESS      not-accessible
    STATUS          current
    DESCRIPTION     
            "Entry in Table consisting of the Sonus Echo Canceller Profile entries"
    INDEX           { sonusEchoCancellorProfileIndex }
    ::= { sonusEchoCancellorProfileTable 1 }

SonusEchoCancellorProfileEntry ::=
    SEQUENCE {
        sonusEchoCancellorProfileIndex  Integer32,
        sonusEchoCancellorProfileName   SonusName,
        sonusEchoCancellorProfileState  SonusAdminState,
        sonusEchoCancellorProfileMaxTail INTEGER,
        sonusEchoCancellorProfileAudioType  INTEGER,
        sonusEchoCancellorProfileSignallingTone       INTEGER,
        sonusEchoCancellorProfileNlpDisable   Integer32,
        sonusEchoCancellorProfileNlpEnable  Integer32,
        sonusEchoCancellorProfileReturnLoss   INTEGER,
        sonusEchoCancellorProfileResidualEcho     INTEGER,
        sonusEchoCancellorProfileHiLevelComp    INTEGER,
        sonusEchoCancellorProfileModemDisable     INTEGER,
        sonusEchoCancellorProfileRowStatus  RowStatus,
        sonusEchoCancellorProfileNarrowbandDetection            INTEGER
    }

sonusEchoCancellorProfileIndex OBJECT-TYPE
    SYNTAX          Integer32
    MAX-ACCESS      read-only
    STATUS          current
    DESCRIPTION     
            "Index into the Echo Canceller Profile table"
    ::= { sonusEchoCancellorProfileEntry 1 }

sonusEchoCancellorProfileName OBJECT-TYPE
    SYNTAX          SonusName
    MAX-ACCESS      read-write
    STATUS          current
    DESCRIPTION     
            "Name of this Echo Canceller Profile"
    ::= { sonusEchoCancellorProfileEntry 2 }

sonusEchoCancellorProfileState OBJECT-TYPE
    SYNTAX          SonusAdminState
    MAX-ACCESS      read-write
    STATUS          current
    DESCRIPTION     
            "Echo Canceller Profile state. Profile can only be applied when in enabled state."
    DEFVAL          { disabled }
    ::= { sonusEchoCancellorProfileEntry 3 }

sonusEchoCancellorProfileMaxTail OBJECT-TYPE
    SYNTAX          INTEGER { millisec24(1), millisec32(2), 
                        millisec48(3), millisec64(4) }
    MAX-ACCESS      read-write
    STATUS          current
    DESCRIPTION     
            "Maximum Echo canceller tail length"
    DEFVAL          { millisec64 }
    ::= { sonusEchoCancellorProfileEntry 4 }

sonusEchoCancellorProfileAudioType OBJECT-TYPE
    SYNTAX          INTEGER { uLaw(1), aLaw(2) }
    MAX-ACCESS      read-write
    STATUS          current
    DESCRIPTION     
            "Audio encoding type A-law or U-law"
    DEFVAL          { uLaw }
    ::= { sonusEchoCancellorProfileEntry 5 }

sonusEchoCancellorProfileSignallingTone OBJECT-TYPE
    SYNTAX          INTEGER { none(1), c5(2) }
    MAX-ACCESS      read-write
    STATUS          current
    DESCRIPTION     
            "Echo Cancellation: None, 2400, 2600 or 2101 Hz"
    DEFVAL          { none }
    ::= { sonusEchoCancellorProfileEntry 6 }

sonusEchoCancellorProfileNlpDisable OBJECT-TYPE
    SYNTAX          Integer32 (0..16)
    MAX-ACCESS      read-write
    STATUS          current
    DESCRIPTION     
            "Non-linear processing control, Disable"
    DEFVAL          { 6 }
    ::= { sonusEchoCancellorProfileEntry 7 }

sonusEchoCancellorProfileNlpEnable OBJECT-TYPE
    SYNTAX          Integer32 (0..80)
    MAX-ACCESS      read-write
    STATUS          current
    DESCRIPTION     
            "Non-linear processing control, Enable"
    DEFVAL          { 75 }
    ::= { sonusEchoCancellorProfileEntry 8 }

sonusEchoCancellorProfileReturnLoss OBJECT-TYPE
    SYNTAX          INTEGER { dB6(1), dB3(2), dB0(3) }
    MAX-ACCESS      read-write
    STATUS          current
    DESCRIPTION     
            "For Network Echo Cancellation, specifies the echo
             return loss in dB's. Default value is 6dB."
    DEFVAL          { dB6 }
    ::= { sonusEchoCancellorProfileEntry 9 }

sonusEchoCancellorProfileResidualEcho OBJECT-TYPE
    SYNTAX          INTEGER { cancelOnly(1), suppressResidual(2), 
                        comfortNoise(4) }
    MAX-ACCESS      read-write
    STATUS          current
    DESCRIPTION     
            "For Network Echo Cancellation, specifies the residual echo
             cancellation."
    DEFVAL          { comfortNoise }
    ::= { sonusEchoCancellorProfileEntry 10 }

sonusEchoCancellorProfileHiLevelComp OBJECT-TYPE
    SYNTAX          INTEGER { none(1), dB6(2) }
    MAX-ACCESS      read-write
    STATUS          current
    DESCRIPTION     
            "For Network Echo Cancellation, the high level compensation
             value. Default value is to attenuate by 6dB."
    DEFVAL          { dB6 }
    ::= { sonusEchoCancellorProfileEntry 11 }

sonusEchoCancellorProfileModemDisable OBJECT-TYPE
    SYNTAX          INTEGER { ignore2100Hz(1), g164(2), g165(4) }
    MAX-ACCESS      read-write
    STATUS          current
    DESCRIPTION     
            "For Network Echo Cancellation, specifies whether to disable
             echo cancellation when a modem tone is detected."
    DEFVAL          { g165 }
    ::= { sonusEchoCancellorProfileEntry 12 }

sonusEchoCancellorProfileRowStatus OBJECT-TYPE
    SYNTAX          RowStatus
    MAX-ACCESS      read-write
    STATUS          current
    DESCRIPTION     
            "This object is used to create, delete, or modify a row in this table."
    ::= { sonusEchoCancellorProfileEntry 13 }

sonusEchoCancellorProfileNarrowbandDetection OBJECT-TYPE
    SYNTAX          INTEGER { off(1), on(2) }
    MAX-ACCESS      read-write
    STATUS          current
    DESCRIPTION     
            "For Network Echo Cancellation, narrow band detection is OFF or ON. If set ON
             it narrows the G.164 detection bandwidth in G.165 mode to the G.165 band."
    DEFVAL          { off }
    ::= { sonusEchoCancellorProfileEntry 14 }

sonusPadMIBNotifications OBJECT IDENTIFIER
    ::= { sonusDspResourcesMIB 2 }

sonusPadMIBNotificationsPrefix OBJECT IDENTIFIER
    ::= { sonusPadMIBNotifications 0 }

sonusPadMIBNotificationsObjects OBJECT IDENTIFIER
    ::= { sonusPadMIBNotifications 1 }

sonusPadThresholdType OBJECT-TYPE
    SYNTAX          INTEGER { g729AB(1), tone(2) }
    MAX-ACCESS      read-only
    STATUS          current
    DESCRIPTION     
            "Type of resource usage that caused a threshold crossing trap"
    ::= { sonusPadMIBNotificationsObjects 1 }

sonusPadThresholdState OBJECT-TYPE
    SYNTAX          INTEGER { off(1), on(2) }
    MAX-ACCESS      read-only
    STATUS          current
    DESCRIPTION     
            "State of threshold, indicates whether threshold is on or off"
    ::= { sonusPadMIBNotificationsObjects 2 }

sonusPadThresholdNotification NOTIFICATION-TYPE
    OBJECTS         { sonusShelfIndex, sonusPadThresholdType, 
                      sonusPadThresholdState, sonusEventDescription, 
                      sonusEventClass, sonusEventLevel }
    STATUS          current
    DESCRIPTION     
            "Generated when a PAD resource usage has gone above the threshold value.
             The type indicates the type reseource."
    ::= { sonusPadMIBNotificationsPrefix 1 }

END -- end of module SONUS-DSP-RESOURCES-MIB.
