XEDIA-CLIENT-GROUP-MIB DEFINITIONS ::= BEGIN

IMPORTS 
    MODULE-IDENTITY, OBJECT-TYPE, Integer32
        FROM SNMPv2-SMI
    RowStatus, DisplayString
        FROM SNMPv2-TC
    MODULE-COMPLIANCE, OBJECT-GROUP
        FROM SNMPv2-CONF
    xediaMibs
        FROM XEDIA-REG
    ;    

xediaClientGroupMIB MODULE-IDENTITY
    LAST-UPDATED "9912142200Z" -- Dec 14, 1999   
    ORGANIZATION "Xedia Corp."
    CONTACT-INFO
        "support@xedia.com"
    DESCRIPTION
        "This module defines objects for the management of the
	Dial-in Client Groups in Xedia devices."
    ::= { xediaMibs 41 }


-- ****************************************************************
-- Top-level organization of the MIB
-- ****************************************************************

clientGroupObjects          OBJECT IDENTIFIER ::= { xediaClientGroupMIB 1 }
clientGroupConformance      OBJECT IDENTIFIER ::= { xediaClientGroupMIB 2 }

-- ****************************************************************
-- Object Definitions
-- ****************************************************************

clientGroupTable   OBJECT-TYPE
    SYNTAX          SEQUENCE OF ClientGroupEntry
    MAX-ACCESS      not-accessible
    STATUS          current
    DESCRIPTION
       "The Client Group table."
    ::= { clientGroupObjects 1 }

clientGroupEntry   OBJECT-TYPE
    SYNTAX          ClientGroupEntry
    MAX-ACCESS      not-accessible
    STATUS          current
    DESCRIPTION
       "A Client Group entry."
    INDEX { clientGroupIdentifier }
    ::= { clientGroupTable 1 }

ClientGroupEntry ::=
    SEQUENCE {
        clientGroupIdentifier
            DisplayString,
        clientGroupAddressAssign
            BIT STRING,
        clientGroupAddressPool
            DisplayString,
        clientGroupClientType
            INTEGER,
        clientGroupPppEchoInterval
            Integer32,
        clientGroupStatus
            RowStatus
    }

clientGroupIdentifier  OBJECT-TYPE
    SYNTAX          DisplayString (SIZE (1..64))
    MAX-ACCESS      not-accessible
    STATUS          current
    DESCRIPTION
       "The identifier is a string which can be associate with users
        via the authentication sub-system."
    ::= { clientGroupEntry 1 }

clientGroupAddressAssign OBJECT-TYPE
    SYNTAX      BIT STRING {
                    acceptClient(0),
                    internalPool(1)
                }
    MAX-ACCESS  read-create
    STATUS      current
    DESCRIPTION
         "The allowed address assignment scheme(s) where
          acceptClient has priority over internalPool."
    -- DEFVAL      { { acceptClient, internalPool } }
    ::= { clientGroupEntry 2 }

clientGroupAddressPool OBJECT-TYPE
    SYNTAX          DisplayString
    MAX-ACCESS      read-create
    STATUS          current
    DESCRIPTION
       "The name of the local address pool."
    ::= { clientGroupEntry 3 }

clientGroupClientType OBJECT-TYPE
      SYNTAX      INTEGER { endNode(1),
			    router(2) } 
      MAX-ACCESS  read-create
      STATUS      current
      DESCRIPTION
        "Description of the client equipment."
      DEFVAL      { endNode }
      ::= { clientGroupEntry 4 }

clientGroupPppEchoInterval OBJECT-TYPE
    SYNTAX      Integer32 (0..3600)
    MAX-ACCESS  read-create
    STATUS      current
    DESCRIPTION
        "The amount of time to wait between sending PPP echos.
         A value of 0 indicates never send."
    DEFVAL      { 30 }
    ::= { clientGroupEntry 5 }

clientGroupStatus  OBJECT-TYPE
           SYNTAX          RowStatus
           MAX-ACCESS      read-create
           STATUS          current
           DESCRIPTION
              "The status of this client group entry."
           ::= { clientGroupEntry 6 }

-- ****************************************************************
-- Conformance Statements
-- ****************************************************************

clientGroupCompliances OBJECT IDENTIFIER ::= { clientGroupConformance 1 }
clientGroupGroups      OBJECT IDENTIFIER ::= { clientGroupConformance 2 }

--
-- Compliance Statements
--

clientGroupCompliance MODULE-COMPLIANCE
    STATUS      current
    DESCRIPTION
        "The compliance statement for all agents that support this
        MIB. A compliant agent implements all objects defined in this
        MIB."
    MODULE  -- this module
    MANDATORY-GROUPS {
        clientGroupGroup
    }
    ::= { clientGroupCompliances 1 }

--
-- Object Groups
--

clientGroupGroup OBJECT-GROUP
    OBJECTS {
--        clientGroupIdentifier,
        clientGroupAddressAssign,
        clientGroupAddressPool,
        clientGroupClientType,
        clientGroupPppEchoInterval,
        clientGroupStatus
    }
    STATUS      current
    DESCRIPTION
        "A collection of objects providing configuration of client groups."
    ::= { clientGroupGroups 1 }

END
