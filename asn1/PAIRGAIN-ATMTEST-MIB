------------------------------------------------------------
-- $Workfile:   pgatmtest.my  $
--   pg ATM Test MIB
-- $Archive:   S:\DSLAM\swdev\snmp14.2.1.16\mibs\common\pgatmtest.myv  $
-- $Revision:   1.6  $
-- $Date:   May 25 2000 15:42:00  $
-- $Author:   scialdt  $
------------------------------------------------------------
-- PairGain DSLAM ATM TEST MIB Release 2.0
-- Revision 10/11/99

-- Copyright 1999 PairGain Technologies, Inc.  All Rights
-- Reserved.  Reproduction of this document is authorized on
-- condition that the foregoing copyright notice is included.
-- This PairGain SNMP Management Information Base Specification
-- (Specification) embodies PairGain's confidential and
-- proprietary intellectual property.  PairGain retains all
-- title and ownership in the Specification, including any
-- revisions.
--
-- It is PairGain's intent to encourage the widespread use of
-- this Specification in connection with the management of
-- PairGain products. PairGain grants vendors, end-users,
-- and other interested parties a non-exclusive license to
-- use this Specification in connection with the management
-- of PairGain products.
--
-- This Specification is supplied "AS IS," and PairGain makes
-- no warranty, either expressed or implied, as to the use,
-- operation, condition, or performance of the Specification.
--
-- Revision History
--------------------------------------------------------------
-- Date     Ver     Programmer  Description
--------------------------------------------------------------
-- 05/25/99 1.0     Chirag      Initial Release
-- 10/11/99 2.0     Chirag      Added the Object pgoamLoopbackAddress
--				pgoamLoopbackErroredCells
--				Removed the Object pgoamLoopbackIdNext
--				pgoamLoopbackId.
--				Changed the access of types of Index objects.
--				Modified the Count Timeout and
--				Delay defaults.

PAIRGAIN-ATMTEST-MIB DEFINITIONS ::= BEGIN

IMPORTS
--  enterprises                      FROM RFC1155-SMI
    MODULE-IDENTITY, OBJECT-TYPE, NOTIFICATION-TYPE,
    Counter32, Integer32             FROM SNMPv2-SMI
    TruthValue, RowStatus            FROM SNMPv2-TC
    OwnerString                      FROM IF-MIB
    pgainDSLAM                       FROM PAIRGAIN-COMMON-HD-MIB
    MODULE-COMPLIANCE, OBJECT-GROUP  FROM SNMPv2-CONF;

pgATMTestMIB   MODULE-IDENTITY
     LAST-UPDATED       "9605010000Z"
     ORGANIZATION       "PairGain Technologies."
     CONTACT-INFO
                "       PairGain Technologies
                        Customer Service"

    DESCRIPTION
            "A MIB module for testing ATM Virtual Channel
            connections."
    ::= { pgainDSLAM 9 }


pgATMTestMIBObjects OBJECT IDENTIFIER ::= { pgATMTestMIB 1 }


--
--  The OAM Loopback Group
--
pgoamLoopbackAddress OBJECT-TYPE
    SYNTAX     OCTET STRING (SIZE (16))
    MAX-ACCESS read-write
    STATUS     current
    DESCRIPTION
	  "Specifies the local ATM device’s ATM address.
	 Other ATM devices use the ATM address to
	   identify this local ATM device as the device that is being
	   requested to loopback the OAM Loopback cell."
    DEFVAL { 'ffffffffffffffff'H }
    ::= { pgATMTestMIBObjects 1 }

pgoamLoopbackTable OBJECT-TYPE
    SYNTAX     SEQUENCE OF PgoamLoopbackEntry
    MAX-ACCESS not-accessible
    STATUS     current
    DESCRIPTION
        "A table of OAM loopback request entries."
    ::= { pgATMTestMIBObjects 2 }

pgoamLoopbackEntry OBJECT-TYPE
    SYNTAX     PgoamLoopbackEntry
    MAX-ACCESS not-accessible
    STATUS     current
    DESCRIPTION
        "A OAM loopback request entry.

	Each entry in the table is uniquely identified by
	ifIndex, VPI and VCI.

	To start a test, use NMS to create
	the associated instance of the row status and row owner objects.
	Also use NMS to modify the default values for the other configuration
	objects if the defaults are not appropriate.

        Once you have used NMS to create the appropriate instance of all of the configuration
        objects, either by an explicit SNMP
        set request or by default, use NMS to set the row status
        to active to initiate the request.  Note that this entire
        procedure can be initiated using a single set request that
        specifies a row status of createAndGo as well as the
        valid values for the non-defaulted configuration objects.

 once the OAM test sequence has been activated, it can be aborted
	by setting RowStatus from active to notInService.

        Once the test sequence completes, the NMS should
        retrieve the values of the status objects of interest and
 then delete the entry.  To prevent old
        entries from clogging the table, whenever a new OAM loopback
	test is requested on a VPI VCI, the old VPI VCI entry
        is deleted and the entries
	marked expired are also deleted."
    INDEX {  pgoamLoopbackIfIndex,pgoamLoopbackVpi,pgoamLoopbackVci}
    ::= { pgoamLoopbackTable 1 }

PgoamLoopbackEntry ::=
    SEQUENCE {
        -- index
	pgoamLoopbackIfIndex           Integer32,
        pgoamLoopbackVpi                 INTEGER,
        pgoamLoopbackVci                 INTEGER,

        -- configuration items
        pgoamLoopbackType                INTEGER,
        pgoamLoopbackLocation            OCTET STRING,
	pgoamLoopbackCount               INTEGER,
        pgoamLoopbackTimeout             INTEGER,
        pgoamLoopbackDelay               INTEGER,
        pgoamLoopbackTrapOnCompletion    TruthValue,
        -- status items
	pgoamLoopbackStatus		 INTEGER,
        pgoamLoopbackSentCells           Counter32,
        pgoamLoopbackReceivedCells       Counter32,
	pgoamLoopbackErroredCells	 Counter32,
        pgoamLoopbackEntryOwner          OwnerString,
        pgoamLoopbackEntryStatus         RowStatus,
        --Additional Configuration items
        pgoamLoopbackFlowType            INTEGER
    }


pgoamLoopbackIfIndex OBJECT-TYPE
    SYNTAX     Integer32
    MAX-ACCESS read-only
    STATUS     current
    DESCRIPTION
        "The interface of the connection on which F5 OAM loopbacks are
        to be sent.  Once an instance of this object is created, its
        value can not be changed. The value specified for this object
        must equate to a value of ifIndex in the ifTable."
    ::= { pgoamLoopbackEntry 1 }

pgoamLoopbackVpi OBJECT-TYPE
    SYNTAX     INTEGER (0..4095)
    MAX-ACCESS read-only
    STATUS     current
    DESCRIPTION
        "The VPI of the connection on which F4/F5 OAM loopbacks are
        to be sent."
    ::= { pgoamLoopbackEntry 2 }

pgoamLoopbackVci OBJECT-TYPE
    SYNTAX     INTEGER (0..65535)
    MAX-ACCESS read-only
    STATUS     current
    DESCRIPTION
        "The VCI of the connection on which OAM
        loopback cells are to be sent."
    ::= { pgoamLoopbackEntry 3 }

pgoamLoopbackType OBJECT-TYPE
    SYNTAX     INTEGER { segment(1), end2end(2) }
    MAX-ACCESS read-create
    STATUS     current
    DESCRIPTION
        "Specifies the type of OAM loopback to be performed: segment loopbacks (1) or end to end loopbacks (2).
The default is segment loopbacks (1)."
    DEFVAL { segment }
    ::= { pgoamLoopbackEntry 5 }

pgoamLoopbackLocation OBJECT-TYPE
    SYNTAX     OCTET STRING (SIZE (16))
    MAX-ACCESS read-create
    STATUS     current
    DESCRIPTION
        "Specifies the target ATM device’s ATM address to be placed in the 'Loopback Location ID' field
        of the OAM loopback cell.  It is used only when pgoamLoopbackType
	is set to segment (1)."
    DEFVAL { 'ffffffffffffffff'H }
    ::= { pgoamLoopbackEntry 6 }

pgoamLoopbackCount OBJECT-TYPE
    SYNTAX     INTEGER (1..10)
    MAX-ACCESS read-create
    STATUS     current
    DESCRIPTION
        "Specifies the number of OAM loopback cells (1 to 10) to send to the target
        in this test sequence.
The default is 1 cell."

    DEFVAL { 1 }
    ::= { pgoamLoopbackEntry 7 }

pgoamLoopbackTimeout OBJECT-TYPE
    SYNTAX     INTEGER (5..15)
    UNITS      "seconds"
    MAX-ACCESS read-create
    STATUS     current
    DESCRIPTION
        "Specifies the amount of time (5 to 15 seconds) to wait for a response from one
        transmitted OAM loopback cell before declaring the OAM
        loopback cells as 'dropped.'
The default is 5 seconds."

    DEFVAL { 5 }
    ::= { pgoamLoopbackEntry 8 }

pgoamLoopbackDelay OBJECT-TYPE
    SYNTAX     INTEGER (5..15)
    UNITS      "seconds"
    MAX-ACCESS read-create
    STATUS     current
    DESCRIPTION
        "Specifies the minimum amount of time (5 to 15 seconds) to wait before sending
        the next OAM loopback cell in a test sequence after receiving a
        response or declaring a timeout for a previous OAM cell.  The
        actual delay may be greater due to internal task scheduling.
The default is 5 seconds."

    DEFVAL { 5 }
    ::= { pgoamLoopbackEntry 9 }

pgoamLoopbackTrapOnCompletion OBJECT-TYPE
    SYNTAX     TruthValue
    MAX-ACCESS read-create
    STATUS     current
    DESCRIPTION
        "Specifies whether an oamLoopbackCompletion trap should
        be issued on completion of the test sequence of OAM loopback cells.
        If such a trap is desired, it is the responsibility of NMS
        to ensure that the SNMP administrative model is
        configured to allow the trap to be delivered."
    DEFVAL { false }
    ::= { pgoamLoopbackEntry 10 }

pgoamLoopbackSentCells OBJECT-TYPE
    SYNTAX     Counter32
    MAX-ACCESS read-only
    STATUS     current
    DESCRIPTION
        "The number of OAM loopback cells that have been sent to the
        target in this test sequence."
    ::= { pgoamLoopbackEntry 11 }

pgoamLoopbackReceivedCells OBJECT-TYPE
    SYNTAX     Counter32
    MAX-ACCESS read-only
    STATUS     current
    DESCRIPTION
        "The number of OAM loopback cells that have been received
         from the target in this test sequence."
    ::= { pgoamLoopbackEntry 12 }

pgoamLoopbackErroredCells OBJECT-TYPE
    SYNTAX	Counter32
    MAX-ACCESS  read-only
    STATUS 	current
    DESCRIPTION
	"The number of OAM Loopback cells that have been received
	with CRC errors."
    ::= { pgoamLoopbackEntry 13 }

pgoamLoopbackStatus OBJECT-TYPE
    SYNTAX     INTEGER { null(1),inProgress(2), completed(3), aborted(4) ,failed(5),expired(6) }
    MAX-ACCESS read-only
    STATUS     current
    DESCRIPTION
        "Set to null (1) when there is no status to report.
	 Set to inProgress (2) as soon as the first OAM loopback cell is sent.
	 Set to completed (3) when all the OAM loopback cells in this test sequence
        have been responded to or timed out.
	 Set to aborted (4) when the OAM loopback test is aborted by setting
	 pgoamLoopBackEntryStatus to notInService.
	 Set to failed (5) when the OAM loopback cells in this test sequence were timed out, not sent, or not returned.

      Set to expired (6) 5 minutes after the operation is aborted , completed or failed.
	When the Status is Expired, the next set operation will
      automatically delete this entry."
    ::= { pgoamLoopbackEntry 14 }

pgoamLoopbackEntryOwner OBJECT-TYPE
    SYNTAX     OwnerString
    MAX-ACCESS read-create
    STATUS     current
    DESCRIPTION
        "The NMS entity that configured this entry."
    ::= { pgoamLoopbackEntry 15 }

pgoamLoopbackEntryStatus OBJECT-TYPE
    SYNTAX     RowStatus
    MAX-ACCESS read-create
    STATUS     current
    DESCRIPTION
        "The status of this table entry.  Once the entry status is
        set to active, the associate entry cannot be deleted until
        the test sequence completes (oamLoopbackStatus is set to completed).
	But it can be set to notInService to abort the ongoing loopback
	Test"
    ::= { pgoamLoopbackEntry 16 }

pgoamLoopbackFlowType OBJECT-TYPE
    SYNTAX     INTEGER {
        oamF4(1),
        oamF5(2)
        }
    MAX-ACCESS read-write
    STATUS     current
    DESCRIPTION
        "This object identifies if the cells are of F4/F5 type when value
        of this object is set to oamF4, the value of pgoamloopbackVci has to
        be set to 3 or 4, else the agent should return error"
    DEFVAL { oamF5 }
    ::= { pgoamLoopbackEntry 17 }



pgATMTestMIBTrapPrefix OBJECT IDENTIFIER ::= { pgATMTestMIB 2 }
pgoamLoopbackMIBTraps OBJECT IDENTIFIER ::= { pgATMTestMIBTrapPrefix 0 }

pgoamLoopbackCompletionTrap NOTIFICATION-TYPE
    OBJECTS      {
			pgoamLoopbackIfIndex,
        		pgoamLoopbackVpi,
        		pgoamLoopbackVci,
			pgoamLoopbackStatus,
        		pgoamLoopbackSentCells,
        		pgoamLoopbackReceivedCells,
			pgoamLoopbackErroredCells

                 }
    STATUS       current
    DESCRIPTION
        "A oamLoopbackCompleted trap is sent at the completion
        of a test sequence of OAM loopback cells if such a trap was
        requested when the test sequence was initiated."
    ::= { pgoamLoopbackMIBTraps 1 }




-- conformance information

pgATMTestMIBConformance
              OBJECT IDENTIFIER ::= { pgATMTestMIB 3 }
pgATMTestMIBCompliances
              OBJECT IDENTIFIER ::= { pgATMTestMIBConformance 1 }
pgATMTestMIBGroups
              OBJECT IDENTIFIER ::= { pgATMTestMIBConformance 2 }


-- compliance statements

pgATMTestMIBCompliance MODULE-COMPLIANCE
    STATUS  current
    DESCRIPTION
            "The compliance statement for PairGain ATM Test MIB."
    MODULE  -- this module
            MANDATORY-GROUPS { pgATMTestMIBGroup }
    ::= { pgATMTestMIBCompliances 1 }


-- units of conformance

pgATMTestMIBGroup OBJECT-GROUP
    OBJECTS { pgoamLoopbackIfIndex, pgoamLoopbackVpi,
              pgoamLoopbackVci, pgoamLoopbackCount,
              pgoamLoopbackType, pgoamLoopbackLocation,
	      pgoamLoopbackTimeout, pgoamLoopbackDelay,
              pgoamLoopbackTrapOnCompletion, pgoamLoopbackSentCells,
	      pgoamLoopbackReceivedCells,pgoamLoopbackErroredCells,
 	      pgoamLoopbackStatus,pgoamLoopbackEntryOwner,
	      pgoamLoopbackEntryStatus
    }
    STATUS    current
    DESCRIPTION
        "A collection of objects that invoke
        the sending of OAM loopback cells."
    ::= { pgATMTestMIBGroups 1 }

END
