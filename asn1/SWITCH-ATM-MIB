SWITCH-ATM-MIB DEFINITIONS ::= BEGIN
	IMPORTS
    MODULE-IDENTITY, OBJECT-TYPE, 
	    Counter32, IpAddress, Integer32,
	    Unsigned32, Gauge32                FROM SNMPv2-SMI
    TEXTUAL-CONVENTION, RowStatus,
    	MacAddress, DisplayString          FROM SNMPv2-TC
    atmModule                              FROM TELESYN-ATI-TC
    ;
    switchAtmMib MODULE-IDENTITY
        LAST-UPDATED "9706201900Z"
	ORGANIZATION ""
	CONTACT-INFO ""
	DESCRIPTION  
			"The MIB module for ATM support.  This module is designed with
			the assumption that only one virtual path identifier (VPI) may
			be assigned and is usually determined by the underlying
			software implementation.  The VPI is never used as an index in
			any table in this module."
        REVISION "9706201900Z"
        DESCRIPTION
			"Changed the status of atmxCipVci to obsolete.
			
			Added atmxCipRipMode to atmxCipEntry.
			
			Added a new table, atmxCipVciTable. Each ATM CIP may be
			supported by multiple VCIs.  The atmxCipVciEntry links each
			atmxCipEntry to one or more conceptual rows in the
			atmxCipVciTable.  Revised the descripiton of
			atmxCipRowStatus to include the dependancy of
			atmxCipVciRowStatus.  See also the description of
			atmCipVciRowStatus for details of the relationship.
			
			Added atmxCipArpSource and atmxCipArpRowStatus to the
			atmxCipArpTable and atmxLecArpSource and atmxLecArpRowStatus to
			the atmxLecArpTable to allow managment to create and delete
			entries in these tables.
			
			Added the tables atmxPtToPtTable, atmxTrunkTable,
			atmxTrunkVlanTable.
			
			Added the object atmxLecVlanNumber to the atmxLecTable. 
			Changed the status of atmxLecUnicastMacAddress to obsolete.
			
			Added the object atmxPortSignalingMode to the atmxPortTable.
			"
        REVISION "9610291900Z"
        DESCRIPTION
		    "Initial version."
        ::= { atmModule 1 }
    
    IfIndexOrZero ::= TEXTUAL-CONVENTION
 		DISPLAY-HINT       "d"
 		STATUS             current
 		DESCRIPTION
			 "An extension of InterfacesIndex to include the value 0. The
			 value 0 may be used to indicate instances where 0, unknown,
			 or all interfaces may apply."
    	SYNTAX  Integer32 (0..2147483647)
    	
    AtmAddress     ::= TEXTUAL-CONVENTION
 		DISPLAY-HINT       "1x"
 		STATUS             current
 		DESCRIPTION
 		     "ATM Address."
    	SYNTAX  OCTET STRING (SIZE (0 | 20))
    AtmPortIndex   ::= TEXTUAL-CONVENTION
 		DISPLAY-HINT       "d"
 		STATUS             current
 		DESCRIPTION
 		     "ATM Port Index."
 		SYNTAX  INTEGER (1..10)
    AtmVpi         ::= TEXTUAL-CONVENTION
 		DISPLAY-HINT       "d"
 		STATUS             current
 		DESCRIPTION
 		     "ATM VPI.  This is a constant with a value of 0."
 		SYNTAX  INTEGER (0..0)
    AtmVci         ::= TEXTUAL-CONVENTION
 		DISPLAY-HINT       "d"
 		STATUS             current
 		DESCRIPTION
 		     "ATM VCI."
 		SYNTAX  INTEGER (0..1023)
    AtmClientVci   ::= TEXTUAL-CONVENTION
 		DISPLAY-HINT       "d"
 		STATUS             current
 		DESCRIPTION
			 "This type restricts VCI values to those not reserved by
			 the ATM Forum."
 		SYNTAX  INTEGER (32..1023)
    AtmLecIndex    ::= TEXTUAL-CONVENTION
 		DISPLAY-HINT       "d"
 		STATUS             current
 		DESCRIPTION
 		     "ATM Lan Emulation Client Index."
 		SYNTAX  INTEGER (1..32)
    AtmCipIndex    ::= TEXTUAL-CONVENTION
 		DISPLAY-HINT       "d"
 		STATUS             current
 		DESCRIPTION
 		     "ATM Classic IP Index."
 		SYNTAX  INTEGER (1..16)
    AtmAdminStatus ::= TEXTUAL-CONVENTION
 		DISPLAY-HINT       "d"
 		STATUS             current
 		DESCRIPTION
 		    "Admininstrative status codes"
 		SYNTAX    INTEGER {
 		    disable(1),
 		    enable(2)
 		}
	AtmOperStatus ::= TEXTUAL-CONVENTION
 		DISPLAY-HINT       "d"
 		STATUS             current
 		DESCRIPTION
 		     "ATM Operation Status."
 		SYNTAX  INTEGER {
				other(1),
				inactive(2),
				active(3),
				loopBack(4)
			}
	AtmConnectionOperStatusCodes ::= TEXTUAL-CONVENTION
 		DISPLAY-HINT       "d"
 		STATUS             current
 		DESCRIPTION
 		     "Virtual Connection operational status."
 		SYNTAX  INTEGER {
				unknown(1),
				up(2),
				down(3)
			}
	AtmTransmissionTypes ::= TEXTUAL-CONVENTION
 		DISPLAY-HINT       "d"
 		STATUS             current
 		DESCRIPTION
 		     "ATM Transmission types."
 		SYNTAX  INTEGER {
			unknown(1),
			sonetSTS3c(2)
		    }
	AtmMediaTypes ::= TEXTUAL-CONVENTION
 		DISPLAY-HINT       "d"
 		STATUS             current
 		DESCRIPTION
 		     "ATM Media Types."
 		SYNTAX  INTEGER {
				unknown(1),
				coaxCable(2),
				singleModeFiber(3),
				multiModeFiber(4),
				utp(5)
			}
	AtmQosClass	::= TEXTUAL-CONVENTION
 		DISPLAY-HINT       "d"
 		STATUS             current
 		DESCRIPTION
 		     "Quality of Service."
 		SYNTAX  INTEGER {
				unspecified(1),
				class1(2),
				class2(3),
				class3(4),
				class4(5)
			 }
	AtmClearStats ::= TEXTUAL-CONVENTION
 		DISPLAY-HINT       "d"
 		STATUS             current
 		DESCRIPTION
 		     "Flag to clear the counters to 0. A SNMP Get operation
 		     will always return 'noOp'"
 		SYNTAX  INTEGER {
				noOp(1),
				clearStats(2)
			 }
	AtmxArpEntryType ::= TEXTUAL-CONVENTION
 		DISPLAY-HINT       "d"
 		STATUS             current
 		DESCRIPTION
			"Indicates how the ArpEntry was learned or created and whether
			it is subject to aging
 		    
 		   other(1) - The entry does not fall into any other category.
 		   learnedViaArp(2) - learned from ARP.
 		   learnedViaData(3) - learned from observing incoming traffic.
 		   staticVolatile(4) - created by management and will not age. 
 		       It may not survive a system restart.
 		   staticNonVolatile(5) - created by management and will not age.
 		       It will survive a system restart.
 		   "
 		SYNTAX INTEGER {
 				other(1),
 				learnedViaArp(2),
 				learnedViaData(3),
 				staticVolatile(4),
 				staticNonVolatile(5)
 			}
	AtmxVlanRange ::= TEXTUAL-CONVENTION
 		DISPLAY-HINT       "d"
 		STATUS             current
 		DESCRIPTION
		    "The range of valid vlan numbers."
		SYNTAX INTEGER (1..65535)
		
		
    
    atmxPortGroup           OBJECT IDENTIFIER ::= { switchAtmMib 1 }
    atmxLecGroup            OBJECT IDENTIFIER ::= { switchAtmMib 2 }
    atmxCipGroup            OBJECT IDENTIFIER ::= { switchAtmMib 3 }
    atmxLayerStatsGroup     OBJECT IDENTIFIER ::= { switchAtmMib 4 }
    atmxVccStatsGroup       OBJECT IDENTIFIER ::= { switchAtmMib 5 }
    atmxLecStatsGroup       OBJECT IDENTIFIER ::= { switchAtmMib 6 }
    atmxCipStatsGroup       OBJECT IDENTIFIER ::= { switchAtmMib 7 }
    atmxSscopStatsGroup     OBJECT IDENTIFIER ::= { switchAtmMib 8 }
    atmxIlmiStatsGroup      OBJECT IDENTIFIER ::= { switchAtmMib 9 }
    atmxVccGroup            OBJECT IDENTIFIER ::= { switchAtmMib 10 }
    atmxAddressGroup        OBJECT IDENTIFIER ::= { switchAtmMib 11 }
    atmxCipArpGroup         OBJECT IDENTIFIER ::= { switchAtmMib 12 }
    atmxLecArpGroup         OBJECT IDENTIFIER ::= { switchAtmMib 13 }
    atmxPtToPtGroup         OBJECT IDENTIFIER ::= { switchAtmMib 14 }
    atmxTrunkGroup          OBJECT IDENTIFIER ::= { switchAtmMib 15 }
    
    
    atmxPortTable   OBJECT-TYPE
    SYNTAX   SEQUENCE OF AtmxPortEntry
		MAX-ACCESS   not-accessible
		STATUS        current
		DESCRIPTION
        	"A table of port layer status and parameter information
	            for the UNI's physical interface."
		::= { atmxPortGroup 1 }
    atmxPortEntry   OBJECT-TYPE
    SYNTAX   AtmxPortEntry
    MAX-ACCESS   not-accessible
    STATUS        current
    DESCRIPTION
        	"An entry in the table, containing information about
            the physical layer of a UNI interface."
    INDEX   { atmxPortIndex }
    ::= { atmxPortTable 1 }
    AtmxPortEntry ::= SEQUENCE {
 		atmxPortIndex              AtmPortIndex,
 		atmxPortDescription        DisplayString,
 		atmxPortTransmissionType   AtmTransmissionTypes,
 		atmxPortMediaType          AtmMediaTypes,
 		atmxPortOperStatus         AtmOperStatus,
 		atmxPortMaxVCCs            INTEGER,
 		atmxPortMaxVciBits         INTEGER,
 		atmxPortAddress            AtmAddress,
 		atmxPortSignalingVersion   INTEGER,
 		atmxPortSignalingVci       INTEGER,
 		atmxPortILMIVci            INTEGER,
 		atmxPortEnableIlmi         INTEGER,
 		atmxPortEnableIlmiPoll     INTEGER,
 		atmxPortEnablePlScramble   INTEGER,
 		atmxPortClock              INTEGER,
 		atmxPortMacAddress         MacAddress,
 		atmxPortAdaptorRamSize     INTEGER,
 		atmxPortIlmiStatus         AtmConnectionOperStatusCodes,
 		atmxPortSignalingStatus    AtmConnectionOperStatusCodes,
 		atmxPortSignalingMode      INTEGER
    }
    atmxPortIndex OBJECT-TYPE
        SYNTAX   AtmPortIndex
        MAX-ACCESS   not-accessible
        STATUS        current
        DESCRIPTION
            "A unique value which identifies this atm submodule port."
        ::= { atmxPortEntry 1 }
    atmxPortDescription OBJECT-TYPE
        SYNTAX   DisplayString (SIZE (0..31))
        MAX-ACCESS   read-write
        STATUS        current
        DESCRIPTION
            "A description for this atm port."
        ::= { atmxPortEntry 2 }
    atmxPortTransmissionType OBJECT-TYPE
        SYNTAX   AtmTransmissionTypes
        MAX-ACCESS   read-only
        STATUS        current
        DESCRIPTION
            "The transmission type of this port. For example, for a port using
            the Sonet STS-3c physical layer at 155.52 Mbs, this object would
            have the value 'sonetSTS3c'."
        ::= { atmxPortEntry 3 }
    atmxPortMediaType OBJECT-TYPE
        SYNTAX   AtmMediaTypes
        MAX-ACCESS   read-only
        STATUS        current
        DESCRIPTION
            "The type of media being used on this port. For example for a port
            using coaxial cable, the object would have the value 'coaxCable'."
        ::= { atmxPortEntry 4 }
    atmxPortOperStatus OBJECT-TYPE
        SYNTAX   AtmOperStatus
        MAX-ACCESS   read-only
        STATUS        current
        DESCRIPTION
            "The operational state (i.e., actual) of this port.
            The ILMI should not alarm on a physical interface when the
            value of this object is 'outOfService'. This capability is useful
            if the equipment is to be disconnected or for troubleshooting
            purposes.
            A value of 'loopBack' indicates that loopback is in place."
        ::= { atmxPortEntry 5 }
    atmxPortMaxVCCs OBJECT-TYPE
        SYNTAX   INTEGER (0..1023)
        MAX-ACCESS   read-only
        STATUS        current
        DESCRIPTION
            "The maximum number of VCCs supported on this UNI."
        ::= { atmxPortEntry 6 }
    atmxPortMaxVciBits OBJECT-TYPE
        SYNTAX   INTEGER (0..10)
        MAX-ACCESS   read-only
        STATUS        current
        DESCRIPTION
            "The number of active VCI bits on this interface."
        ::= { atmxPortEntry 7 }
    atmxPortAddress OBJECT-TYPE
        SYNTAX   AtmAddress
        MAX-ACCESS   read-write
        STATUS       current
        DESCRIPTION
			"The ATM address assigned to this port. The value of this
			attribute is normally set via the ILMI. If the ILMI Address
			registration mib, ATM-FORUM-ADDR-REG, is supported and the
			the value of atmxPortIlmiStatus is 'up' than atmxPortAddress
			should have a MAX-ACCESS of read-only."
        ::= { atmxPortEntry 8 }
    atmxPortSignalingVersion OBJECT-TYPE
        SYNTAX   INTEGER { ver30(1), ver31(2) }
        MAX-ACCESS   read-write
        STATUS        current
        DESCRIPTION
            "Version of the ATM forum UNI Signaling."
        ::= { atmxPortEntry 9 }
    atmxPortSignalingVci OBJECT-TYPE
        SYNTAX   INTEGER (5..5)
        MAX-ACCESS   read-only
        STATUS        current
        DESCRIPTION
            "Signaling Vci. ATM Forum has defined VPI/VCI as VPI 0, VCI 5 
            for signaling."
        ::= { atmxPortEntry 10 }
    atmxPortILMIVci OBJECT-TYPE
        SYNTAX   INTEGER (16..16)
        MAX-ACCESS   read-only
        STATUS        current
        DESCRIPTION
            "ILMI Vci. ATM Forum has defined the VPI 0, VCI 16 for ILMI."
        ::= { atmxPortEntry 11 }
    atmxPortEnableIlmi OBJECT-TYPE
        SYNTAX   INTEGER { false(1), true(2) }
        MAX-ACCESS   read-write
        STATUS        current
        DESCRIPTION
            "ILMI Enable."
        ::= { atmxPortEntry 12 }
    atmxPortEnableIlmiPoll	OBJECT-TYPE
        SYNTAX   INTEGER { false(1), true(2) }
        MAX-ACCESS   read-write
        STATUS        current
        DESCRIPTION
            "ILMI Poll Enable."
        ::= { atmxPortEntry 13 }
    atmxPortEnablePlScramble OBJECT-TYPE
        SYNTAX   INTEGER { false(1), true(2) }
        MAX-ACCESS   read-write
        STATUS        current
        DESCRIPTION
            "Payload Scrambling Enable."
        ::= { atmxPortEntry 14 }
    atmxPortClock	OBJECT-TYPE
        SYNTAX   INTEGER { local(1), loopTimed(2) }
        MAX-ACCESS   read-write
        STATUS        current
        DESCRIPTION
            "ATM Port clock mode."
        ::= { atmxPortEntry 15 }
    atmxPortMacAddress	OBJECT-TYPE
        SYNTAX   MacAddress
        MAX-ACCESS   read-only
        STATUS        current
        DESCRIPTION
            "ATM Port MAC Address."
        ::= { atmxPortEntry 16 }
    atmxPortAdaptorRamSize	OBJECT-TYPE
        SYNTAX   INTEGER (0..2147483647)
        MAX-ACCESS   read-only
        STATUS        current
        DESCRIPTION
            "Segmentation and reassembly memory size in bytes."
        ::= { atmxPortEntry 17 }
    atmxPortIlmiStatus	OBJECT-TYPE
        SYNTAX   AtmConnectionOperStatusCodes
        MAX-ACCESS   read-only
        STATUS        current
        DESCRIPTION
            "ILMI status."
        ::= { atmxPortEntry 18 }
    atmxPortSignalingStatus	OBJECT-TYPE
        SYNTAX   AtmConnectionOperStatusCodes
        MAX-ACCESS   read-only
        STATUS        current
        DESCRIPTION
            "Signaling Status."
        ::= { atmxPortEntry 19 }
    atmxPortSignalingMode	OBJECT-TYPE
        SYNTAX		INTEGER {
						pvc(1),
						svc(2)
					}
        MAX-ACCESS	read-write
        STATUS		current
        DESCRIPTION
			"If this has the value 'pvc' then signaling, ILMI
			and ILMI polling will be automatically disabled."
		DEFVAL { pvc }
		::= { atmxPortEntry 20}
    
    
    atmxLecTable   OBJECT-TYPE
        SYNTAX   SEQUENCE OF AtmxLecEntry
		MAX-ACCESS   not-accessible
		STATUS        current
		DESCRIPTION
        	"A table of LEC status and parameter information."
		::= { atmxLecGroup 1 }
    atmxLecEntry   OBJECT-TYPE
        SYNTAX   AtmxLecEntry
        MAX-ACCESS   not-accessible
        STATUS        current
        DESCRIPTION
        	"An entry in the table, containing information about
		     the indicated LEC."
        INDEX   { atmxLecIndex }
        ::= { atmxLecTable 1 }
    AtmxLecEntry ::= SEQUENCE {
    	atmxLecIndex				   AtmLecIndex,
    	atmxLecDescription  		   DisplayString,
    	atmxElanName				   DisplayString,
    	atmxLecConfigMode			   INTEGER,
    	atmxLecServerAddress		   AtmAddress,
    	atmxLecUnicastMacAddress	   MacAddress, 
    	atmxLecMaxUnknownFrameCount    INTEGER,
    	atmxLecMaxArpRetryCount 	   INTEGER,
    	atmxLecMaxUnknownFrameTime     INTEGER,
    	atmxLecControlTimeout		   INTEGER,
    	atmxLecVccTimeout			   Unsigned32,
    	atmxLecAgeingTime			   INTEGER,
    	atmxLecArpRespTime  		   INTEGER,
    	atmxLecFlushTimeout 		   INTEGER,
     	atmxLecVPortNumber  		   INTEGER,
     	atmxLecProtocolState		   INTEGER,
    	atmxLecRowStatus			   RowStatus,
    	atmxLecIfIndex  			   IfIndexOrZero,
    	atmxLecId					   INTEGER,
    	atmxLecControlDirectVcc  	   AtmVci,
    	atmxLecControlDistributeVcc    AtmVci,
    	atmxLecMulticastSendVcc  	   AtmVci,
    	atmxLecMulticastForwardVcc	   AtmVci,
    	atmxLecVlanNumber              AtmxVlanRange
    }
    atmxLecIndex	OBJECT-TYPE
        SYNTAX   AtmLecIndex
        MAX-ACCESS   not-accessible
        STATUS        current
        DESCRIPTION
            "A unique value which identifies this LEC entry."
        ::= { atmxLecEntry 1 }
    atmxLecDescription	OBJECT-TYPE
         SYNTAX   DisplayString (SIZE (0..31))
         MAX-ACCESS   read-create
         STATUS        current
         DESCRIPTION
            "A description for this LEC."
         ::= { atmxLecEntry 2 }
    atmxElanName	OBJECT-TYPE
         SYNTAX   DisplayString (SIZE (0..31))
         MAX-ACCESS   read-create
         STATUS        current
         DESCRIPTION
            "A Name for the ELAN."
         ::= { atmxLecEntry 3 }
    atmxLecConfigMode	OBJECT-TYPE
         SYNTAX   INTEGER { auto(1), manual(2) }
         MAX-ACCESS   read-create
         STATUS        current
         DESCRIPTION
            "Configuration Mode for this LEC."
         ::= { atmxLecEntry 4 }
    atmxLecServerAddress	OBJECT-TYPE
         SYNTAX   AtmAddress
         MAX-ACCESS   read-create
         STATUS        current
         DESCRIPTION
            "ATM Address of the LE Configuration Server if
            the configuration mode is auto; else, the LE
            Server ATM Address."
         ::= { atmxLecEntry 5 }
    atmxLecUnicastMacAddress	OBJECT-TYPE
         SYNTAX   MacAddress
         MAX-ACCESS   read-only
         STATUS        obsolete
         DESCRIPTION
            "The Local Unicast MAC address for this LEC.
            
            This is now obsolete because the information can
            be obtained from the vport entry identified by
            atmxLecVPortNumber."
         ::= { atmxLecEntry 6 }
    atmxLecMaxUnknownFrameCount	OBJECT-TYPE
         SYNTAX   INTEGER (1..10)
         MAX-ACCESS   read-create
         STATUS        current
         DESCRIPTION
            "Maximum number of frames to the BUS for a given
            unicast LAN destination within the Maximum unknown 
            Frame time."
         ::= { atmxLecEntry 7 }
    atmxLecMaxArpRetryCount	OBJECT-TYPE
         SYNTAX   INTEGER (0..2)
         MAX-ACCESS   read-create
         STATUS        current
         DESCRIPTION
            "Maximum number of times LE_ARP_REQUEST will be 
            retried for a given frame's LAN destination."
         ::= { atmxLecEntry 8 }
    atmxLecArpRespTime	OBJECT-TYPE
         SYNTAX   INTEGER (1..30)
         MAX-ACCESS   read-create
         STATUS        current
         DESCRIPTION
             "Maximum time in seconds that the LEC expects an 
             LE_ARP_REQUEST/LE_ARP_RESPONSE cycle to take."
         ::= { atmxLecEntry 9 }
    atmxLecMaxUnknownFrameTime	OBJECT-TYPE
         SYNTAX   INTEGER (1..60)
         MAX-ACCESS   read-create
         STATUS        current
         DESCRIPTION
            "Time period in seconds for the maximum number of frames that
            can be sent to the BUS for a given LAN destination."
         ::= { atmxLecEntry 10 }
    atmxLecControlTimeout	OBJECT-TYPE
         SYNTAX   INTEGER (10..300)
         MAX-ACCESS   read-create
         STATUS        current
         DESCRIPTION
            "Time out period in seconds for timing out most request response 
            control frame interations."
         ::= { atmxLecEntry 11 }
    atmxLecVccTimeout	OBJECT-TYPE
         SYNTAX   Unsigned32
         MAX-ACCESS   read-create
         STATUS        current
         DESCRIPTION
			"Maximum in-active time period in seconds a data direct
			VCC  will be active before being released. A value of 0
			indicates that it will never be release."
         ::= { atmxLecEntry 12 }
    atmxLecAgeingTime	OBJECT-TYPE
         SYNTAX   INTEGER (10..300)
         MAX-ACCESS   read-create
         STATUS        current
         DESCRIPTION
            "Maximum time in seconds that an LE client will maintain an 
             entry in its LE-ARP cache in the absence of verification."
         ::= { atmxLecEntry 13 }
    atmxLecFlushTimeout	OBJECT-TYPE
         SYNTAX   INTEGER (1..4)
         MAX-ACCESS   read-create
         STATUS        current
         DESCRIPTION
             "Time limit in seconds to wait to receive an LE_FLUSH_RESPONSE 
             after the LE_FLUSH_REQUEST has been sent before 
             taking recovery action."
         ::= { atmxLecEntry 14 }
    atmxLecVPortNumber	OBJECT-TYPE
         SYNTAX   INTEGER (0..256)
         MAX-ACCESS   read-only
         STATUS        deprecated
         DESCRIPTION
             "The Virtual port number with which this LEC is associated. If
             the value of this object is 0, then no virtual port has been
             assigned and the LEC is not active."
         ::= { atmxLecEntry 15 }
    atmxLecProtocolState	OBJECT-TYPE
    	SYNTAX   INTEGER {
    				 inActive(0),		  
    				 ctrlDirConReq(1),    
    				 ctrlDistConRsp(2),   
    				 mcastSndConReq(3),   
    				 mcastSndFwdConRsp(4),   
    				 mcastSndFwdConCfm(5),   
    				 mcastSndConCfm(6),   
    				 mcastFwdConRsp(7),   
    				 busArpReq(8),  	  
    				 cfgReq(9), 		  
    				 joinReq(10),		  
    				 active(11),		  
    				 cfgDirConReq(12)	  
    			 }
    	MAX-ACCESS   read-only
    	STATUS  	  current
    	DESCRIPTION
    		"This object contains the LAN emulation protocol state."
    	::= { atmxLecEntry 16 }
    atmxLecRowStatus	OBJECT-TYPE
    	SYNTAX   RowStatus
    	MAX-ACCESS   read-create
    	STATUS  	  current
    	DESCRIPTION
    		"This object is used to create and delete entries.  Only the
    		values 'active', 'createAndGo', and 'delete are supported."
    	::= { atmxLecEntry 17 }
    atmxLecIfIndex OBJECT-TYPE
    	SYNTAX   IfIndexOrZero
    	MAX-ACCESS   read-only
    	STATUS  	  current
    	DESCRIPTION
			"This object contains the ifIndex of the corresponding entry
			in the ifTable. If no such entry exists or unknown then value
			of this object is 0."
    	::= { atmxLecEntry 18 }
    atmxLecId   OBJECT-TYPE
    	SYNTAX   INTEGER (0..32767)
    	MAX-ACCESS   read-only
    	STATUS  	  current
    	DESCRIPTION
			"A value assigned by the LAN Emulation Service (LES) for the
			LEC identified by atmLecIndex.  The value 0 indicates the LES
			has not assigned a value."
    	::= { atmxLecEntry 19 }
    atmxLecControlDirectVcc OBJECT-TYPE
    	SYNTAX   AtmVci
    	MAX-ACCESS   read-only
    	STATUS  	  current
    	DESCRIPTION
			"The VCC assigned for the Control Direct connection.  The
			value 0 indicates the VCC is not set."
    	::= { atmxLecEntry 20 }
    atmxLecControlDistributeVcc OBJECT-TYPE
    	SYNTAX   AtmVci
    	MAX-ACCESS   read-only
    	STATUS  	  current
    	DESCRIPTION
			"The VCC assigned for the Control Distribute connection.  The
			value 0 indicates the VCC is not set."
    	::= { atmxLecEntry 21 }
    atmxLecMulticastSendVcc OBJECT-TYPE
    	SYNTAX   AtmVci
    	MAX-ACCESS   read-only
    	STATUS  	  current
    	DESCRIPTION
			"The VCC assigned for Multicast send.  The value 0 indicates
			the VCC is not set."
    	::= { atmxLecEntry 22 }
    atmxLecMulticastForwardVcc OBJECT-TYPE
    	SYNTAX   AtmVci
    	MAX-ACCESS   read-only
    	STATUS  	  current
    	DESCRIPTION
    		"The VCC assigned for multicast forwarding. The value 0
    		indicates the VCC is not set."
    	::= { atmxLecEntry 23 }
    atmxLecVlanNumber OBJECT-TYPE
    	SYNTAX       AtmxVlanRange
    	MAX-ACCESS   read-create
    	STATUS  	  current
    	DESCRIPTION
			"The virtual LAN number to which this LEC is attached.  This 
			object is required for row creation and the value of this
			object must correspond to an existing vLanNumber object in
			the 'SWITCH-VLAN-MIB.vLanTable'.
			 
			After a successful row creation, this value may change as a
			result of moving the virtual port, atmxLecIfIndex, to a different
			Vlan."
		REFERENCE
			"SWITCH-VLAN-MIB"
    	::= { atmxLecEntry 24 }
    
    
    atmxCipTable   OBJECT-TYPE
    	SYNTAX   SEQUENCE OF AtmxCipEntry
		MAX-ACCESS   not-accessible
		STATUS        current
		DESCRIPTION
        	"A table of CIP status and parameter information."
		::= { atmxCipGroup 1 }
    atmxCipEntry   OBJECT-TYPE
        SYNTAX   AtmxCipEntry
        MAX-ACCESS   not-accessible
        STATUS        current
        DESCRIPTION
            "An entry in the table, containing information about
            the indicated CIP."
        INDEX   { atmxCipIndex }
        ::= { atmxCipTable 1 }
    AtmxCipEntry ::= SEQUENCE {
    	atmxCipIndex			   AtmCipIndex,
    	atmxCipDescription  	   DisplayString,
    	atmxCipIPAddress		   IpAddress,
		atmxCipIPSubnetMask 	   IpAddress,
    	atmxCipConnectionType	   INTEGER,
    	atmxCipVci				   AtmVci, 
    	atmxCipServerAtmAddress    AtmAddress,
    	atmxCipMtuSize  		   INTEGER,
    	atmxCipIfIndex  		   IfIndexOrZero,
    	atmxCipProtocolState	   INTEGER,
    	atmxCipAdmStatus		   AtmAdminStatus,
    	atmxCipOperStatus		   AtmOperStatus,
    	atmxCipRowStatus		   RowStatus,
    	atmxCipRipMode             INTEGER
    }
    atmxCipIndex	OBJECT-TYPE
        SYNTAX   AtmCipIndex
        MAX-ACCESS   not-accessible
        STATUS        current
        DESCRIPTION
           "A unique value which identifies this CIP entry."
        ::= { atmxCipEntry 1 }
    atmxCipDescription	OBJECT-TYPE
        SYNTAX   DisplayString (SIZE (0..31))
        MAX-ACCESS   read-create
        STATUS        current
        DESCRIPTION
           "A description for this CIP."
        ::= { atmxCipEntry 2 }
    atmxCipIPAddress	OBJECT-TYPE
        SYNTAX   IpAddress
        MAX-ACCESS   read-create
        STATUS        current
        DESCRIPTION
           "The IP address associated with this CIP entity."
        ::= { atmxCipEntry 3 }
    atmxCipIPSubnetMask	OBJECT-TYPE
        SYNTAX   IpAddress
        MAX-ACCESS   read-create
        STATUS        current
        DESCRIPTION
           "The IP subnet mask associated with this CIP entity."
        ::= { atmxCipEntry 4 }
    atmxCipConnectionType	OBJECT-TYPE
        SYNTAX   INTEGER {	pvc(1), svc(2) }
        MAX-ACCESS   read-create
        STATUS        current
        DESCRIPTION
			"The connection type of this CIP. If during row creation
			the value of this object is 'pvc', then at least one entry
			in the atmxCipVciTable is required before 
			atmxCipRowStatus can be set to 'active'.  If during row
			creation the value is 'svc' then atmxCipServerAtmAddress
			must be set before atmxCipRowStatus can be set to
			'active'."
        ::= { atmxCipEntry 5 }
    atmxCipVci	OBJECT-TYPE
        SYNTAX   AtmVci
        MAX-ACCESS   read-create
        STATUS        obsolete
        DESCRIPTION
           "The virtual channel identifier associated with this 
            CIP, if PVC."
        ::= { atmxCipEntry 6 }
    atmxCipServerAtmAddress	OBJECT-TYPE
        SYNTAX   AtmAddress
        MAX-ACCESS    read-create
        STATUS        current
        DESCRIPTION
            "ATM Address of the ARP server for the logical IP
            subnet, to which this CIP belongs. This object is
            required if atmxCipConnectionType is 'svc'."
        ::= { atmxCipEntry 7 }
    atmxCipMtuSize	OBJECT-TYPE
        SYNTAX   INTEGER (64..9180)
        MAX-ACCESS   read-create
        STATUS        current
        DESCRIPTION
            "The maximum size of the transmit or receive
            SDU size of all connections associated with
            this CIP entity."
        DEFVAL { 9160 }
        ::= { atmxCipEntry 8 }
	atmxCipIfIndex OBJECT-TYPE
	    SYNTAX  IfIndexOrZero
	    MAX-ACCESS  read-only
	    STATUS  current
	    DESCRIPTION
			"This value of this object identifies the corresponding
			entry in the ifTable.  If this object has the value of 0
			then there is  no corresponding entry in the ifTable."
	    ::= { atmxCipEntry 9 }
	atmxCipProtocolState OBJECT-TYPE
	    SYNTAX  INTEGER {
	    		inactive(0),
	    		arpConReq(1),
	    		active(2)
	    	}
		MAX-ACCESS  read-only
	    STATUS  current
	    DESCRIPTION
			"The state of the CIP Protocol."
	    ::= { atmxCipEntry 10 }
	atmxCipAdmStatus OBJECT-TYPE
	    SYNTAX  AtmAdminStatus
	    MAX-ACCESS  read-create
	    STATUS  current
	    DESCRIPTION
			"The administrative status of this CIP instance."
	    ::= { atmxCipEntry 11 }
	atmxCipOperStatus OBJECT-TYPE
	    SYNTAX  AtmOperStatus
	    MAX-ACCESS  read-only
	    STATUS  current
	    DESCRIPTION
			"The operational status of this CIP instance."
	    ::= { atmxCipEntry 12 }
	atmxCipRowStatus OBJECT-TYPE
	    SYNTAX  RowStatus
	    MAX-ACCESS  read-create
	    STATUS  current
	    DESCRIPTION
			"This object is used to create and delete atmxCipEntry. To
			create of a logical row, set this object to
			'createAndWait'. Before this object can be set to 'active',
			the objects atmxCipIPAddress, atmxCipIPSubnetMask,
			atmxCipConnectionType must be set to the appropriate values
			and at least one entry must be created in the
			atmxCipVciTable with the same atmxCipIndex value as used
			with this object instance.
			
			When this object is set to 'active', the logical rows in
			atmxCipVciTable with the same atmxCipIndex value will also
			be set to 'active'.
			
			If this object is set to 'delete', the logical rows in
			atmxCipVciTable with the same atmxCipIndex value will also
			be deleted."
	    ::= { atmxCipEntry 13 }
 	atmxCipRipMode OBJECT-TYPE
		SYNTAX  INTEGER {
					silent(1),
					active(2),
					deaf(3),
					inactive(4)
				}
		MAX-ACCESS  read-create
		STATUS  current
		DESCRIPTION
			"If the value of this object is 'silent', RIP daemon
			processes received routing packets and does NOT send
			routing packets over the interface identified by 
			atmxCipIfIndex.  With a value of 'active', RIP sends and
			receives routing packets. With a value of 'deaf' RIP sends
			routing packets and does not process recieved packets. 
			With a value of 'inactive' RIP deamon  does not send nor
			receive routing packets."
		DEFVAL { silent }
		::= { atmxCipEntry 14 }
    
    
    
    atmxCipVciTable   OBJECT-TYPE
    	SYNTAX   SEQUENCE OF AtmxCipVciEntry
		MAX-ACCESS   not-accessible
		STATUS        current
		DESCRIPTION
        	"A table which contains VCIs associated with each CIP."
		::= { atmxCipGroup 2 }
    atmxCipVciEntry   OBJECT-TYPE
        SYNTAX   AtmxCipVciEntry
        MAX-ACCESS   not-accessible
        STATUS        current
        DESCRIPTION
            "An entry in the table, identifying each VCI for a CIP."
        INDEX   { atmxCipIndex, atmxCipVciId }
        ::= { atmxCipVciTable 1 }
    AtmxCipVciEntry ::= SEQUENCE {
    	atmxCipVciId            AtmClientVci,
    	atmxCipVciRowStatus     RowStatus
    }
    
    atmxCipVciId    OBJECT-TYPE
        SYNTAX       AtmClientVci
        MAX-ACCESS   not-accessible
        STATUS       current
        DESCRIPTION
           "The virtual channel identifier associated with this 
            CIP."
        ::= { atmxCipVciEntry 1 }
	atmxCipVciRowStatus OBJECT-TYPE
	    SYNTAX  RowStatus
	    MAX-ACCESS  read-create
	    STATUS  current
	    DESCRIPTION
			"This object is used to create and delete entries in the
			atmxCipVciTable.  An object instance of this object
			corresponds to an object instance of atmxCipRowStatus if both
			objects have the same for atmxCipIndex index value.  There
			may be multiple instances of this object which correspond to
			the same instance of atmxCipRowStatus.
			
			To create a conceptual row in this table and the
			corresponding object instance atmxCipRowStatus does not exist
			or has the value 'notReady', the value for
			atmxCipVciRowStatus in an SNMP Set operation can be only
			'createAndWait'. Under these conditions, atmxCipVciRowStatus
			cannot be set to 'active' but transitions to 'active' as a
			side effect of an SNMP set operation changing 
			atmxCipRowStatus to 'active'.  At least one corresponding
			instance of atmxCipVciRowStatus must exist before
			atmxCipRowStatus can transition to 'active'.   
			
			To create a conceptual row in this table and the
			corresponding object instance atmxCipRowStatus exists with
			the value 'active' then the value for atmxCipVciRowStatus may
			be 'createAndWait' or 'createAndGo'.
			
			An SNMP Set operation may not set the value of this object to
			'active' unless the the corresponde atmxCipRowStatus has the
			value 'active'."
	    ::= { atmxCipVciEntry 2 }
    
     
     
     atmxLayerStatsTable   OBJECT-TYPE
         SYNTAX   SEQUENCE OF AtmxLayerStatsEntry
         MAX-ACCESS   not-accessible
         STATUS        current
         DESCRIPTION
         	"A table of ATM layer statistics information."
         ::= { atmxLayerStatsGroup 1 }
     atmxLayerStatsEntry   OBJECT-TYPE
         SYNTAX   AtmxLayerStatsEntry
         MAX-ACCESS   not-accessible
         STATUS        current
         DESCRIPTION
         	"An entry in the table, containing information about
            the ATM layer statistics."
         INDEX   { atmxPortIndex }
        ::= { atmxLayerStatsTable 1 }
     AtmxLayerStatsEntry ::= SEQUENCE {
 	 	 atmxLayerStatsTxCells  		Counter32,
 	 	 atmxLayerStatsRxCells  		Counter32,
 	 	 atmxLayerStatsTxCellDiscards	Counter32,
 	 	 atmxLayerStatsRxCellDiscards	Counter32,
 	 	 atmxLayerStatsClear			AtmClearStats,
 	 	 atmxLayerStatsClearTime		INTEGER
 	 }
     atmxLayerStatsTxCells OBJECT-TYPE
         SYNTAX   Counter32
         MAX-ACCESS   read-only
         STATUS        current
         DESCRIPTION
            "The total number of successfully transmitted cells."
         ::= { atmxLayerStatsEntry 2 }
     atmxLayerStatsRxCells OBJECT-TYPE
         SYNTAX   Counter32
         MAX-ACCESS   read-only
         STATUS        current
         DESCRIPTION
            "The total number of successfully received cells."
         ::= { atmxLayerStatsEntry 3 }
     atmxLayerStatsTxCellDiscards OBJECT-TYPE
         SYNTAX   Counter32
         MAX-ACCESS   read-only
         STATUS        current
         DESCRIPTION
            "The total number of transmit cells that are discarded."
         ::= { atmxLayerStatsEntry 4 }
     atmxLayerStatsRxCellDiscards OBJECT-TYPE
         SYNTAX   Counter32
         MAX-ACCESS   read-only
         STATUS        current
         DESCRIPTION
            "The total number of receive cells that are discarded."
         ::= { atmxLayerStatsEntry 5 }
     atmxLayerStatsClear OBJECT-TYPE
         SYNTAX   AtmClearStats
         MAX-ACCESS   read-write
         STATUS        current
         DESCRIPTION
			 "When this attribute is set to 'clearStats', the counters
			 for this logical row are reset to 0 and
			 atmxLayerStatsClearTime is  reset to 0."
         ::= { atmxLayerStatsEntry 6 }
     atmxLayerStatsClearTime OBJECT-TYPE
         SYNTAX   INTEGER (0..2147483647)
         MAX-ACCESS   read-only
         STATUS        current
         DESCRIPTION
            "Amount of time in seconds that has elapsed since the 
            counters have been cleared."
         ::= { atmxLayerStatsEntry 7 }
     
     
     aal5LayerStatsTable   OBJECT-TYPE
         SYNTAX   SEQUENCE OF Aal5LayerStatsEntry
         MAX-ACCESS   not-accessible
         STATUS        current
         DESCRIPTION
         	"A table of AAL5 layer statistics information."
         ::= { atmxLayerStatsGroup 2 }
     aal5LayerStatsEntry	OBJECT-TYPE
         SYNTAX   Aal5LayerStatsEntry
         MAX-ACCESS   not-accessible
         STATUS        current
         DESCRIPTION
         	"An entry in the table, containing information about
            the AAL5 layer statistics."
         INDEX   { atmxPortIndex }
         ::= { aal5LayerStatsTable 1 }
     Aal5LayerStatsEntry ::= SEQUENCE {
 		 aal5LayerTxOctets  		Counter32,
 		 aal5LayerTxCells			Counter32,
 		 aal5LayerTxSDUs			Counter32,
 		 aal5LayerTxSDUDiscards 	Counter32,
 		 aal5LayerTxErrors  		Counter32,
 		 aal5LayerRxOctets  		Counter32,
 		 aal5LayerRxCells			Counter32,
 		 aal5LayerRxSDUs			Counter32,
 		 aal5LayerRxSDUDiscards 	Counter32,
 		 aal5LayerRxErrors  		Counter32,
 		 aal5LayerRxSarTimeouts 	Counter32,
 		 aal5LayerRxCrcErrors		Counter32,
 		 aal5LayerRxSDUInvalidSz	Counter32,
 		 aal5LayerClearStats		AtmClearStats,
 		 aal5LayerStatsClearTime	INTEGER
 	 }
     aal5LayerTxOctets	OBJECT-TYPE
         SYNTAX   Counter32
         MAX-ACCESS   read-only
         STATUS        current
         DESCRIPTION
            "The total number of successfully transmitted octets
            for all AAL5 connections."
         ::= { aal5LayerStatsEntry 2 }
     aal5LayerTxCells	OBJECT-TYPE
         SYNTAX   Counter32
         MAX-ACCESS   read-only
         STATUS        current
         DESCRIPTION
            "The total number of successfully transmitted cells
            for all AAL5 connections."
         ::= { aal5LayerStatsEntry 3 }
     aal5LayerTxSDUs	OBJECT-TYPE
         SYNTAX   Counter32
         MAX-ACCESS   read-only
         STATUS        current
         DESCRIPTION
            "The total number of successfully transmitted service
            data units for all AAL5 connections."
         ::= { aal5LayerStatsEntry 4 }
     aal5LayerTxSDUDiscards	OBJECT-TYPE
         SYNTAX   Counter32
         MAX-ACCESS   read-only
         STATUS        current
         DESCRIPTION
            "The total number of transmit SDUs discarded."
         ::= { aal5LayerStatsEntry 5 }
     aal5LayerTxErrors	OBJECT-TYPE
         SYNTAX   Counter32
         MAX-ACCESS   read-only
         STATUS        current
         DESCRIPTION
            "The total number of transmit SDUs that could
            not be transmitted due to errors."
         ::= { aal5LayerStatsEntry 6 }
     aal5LayerRxOctets	OBJECT-TYPE
         SYNTAX   Counter32
         MAX-ACCESS   read-only
         STATUS        current
         DESCRIPTION
            "The total number of successfully received octets
            for all AAL5 connections."
         ::= { aal5LayerStatsEntry 7 }
     aal5LayerRxCells	OBJECT-TYPE
         SYNTAX   Counter32
         MAX-ACCESS   read-only
         STATUS        current
         DESCRIPTION
            "The total number of successfully received cells
            for all AAL5 connections."
         ::= { aal5LayerStatsEntry 8 }
     aal5LayerRxSDUs	OBJECT-TYPE
         SYNTAX   Counter32
         MAX-ACCESS   read-only
         STATUS        current
         DESCRIPTION
            "The total number of successfully received service
            data units for all AAL5 connections."
         ::= { aal5LayerStatsEntry 9 }
     aal5LayerRxSDUDiscards	OBJECT-TYPE
         SYNTAX   Counter32
         MAX-ACCESS   read-only
         STATUS        current
         DESCRIPTION
            "The total number of received SDUs discarded."
         ::= { aal5LayerStatsEntry 10 }
     aal5LayerRxErrors	OBJECT-TYPE
         SYNTAX   Counter32
         MAX-ACCESS   read-only
         STATUS        current
         DESCRIPTION
            "The total number of errored SDUs that received."
         ::= { aal5LayerStatsEntry 11 }
     aal5LayerRxSarTimeouts	OBJECT-TYPE
         SYNTAX   Counter32
         MAX-ACCESS   read-only
         STATUS        current
         DESCRIPTION
            "The total number of partially re-assembled SDUs
            that were discarded."
         ::= { aal5LayerStatsEntry 12 }
     aal5LayerRxCrcErrors	OBJECT-TYPE
         SYNTAX   Counter32
         MAX-ACCESS   read-only
         STATUS        current
         DESCRIPTION
            "The total number of SDUs that were received with
            CRC errors."
         ::= { aal5LayerStatsEntry 13 }
     aal5LayerRxSDUInvalidSz	OBJECT-TYPE
         SYNTAX   Counter32
         MAX-ACCESS   read-only
         STATUS        current
         DESCRIPTION
            "The total number of SDUs discarded because their
            size exceeded the max SDU size."
         ::= { aal5LayerStatsEntry 14 }
     aal5LayerClearStats OBJECT-TYPE
         SYNTAX   AtmClearStats 
         MAX-ACCESS   read-write
         STATUS        current
         DESCRIPTION
             "When this attribute is set to 'clearStats', the counters for this
             logical row are reset to 0 and aal5LayerStatsClearTime is 
             reset to 0."
         ::= { aal5LayerStatsEntry 15 }
     aal5LayerStatsClearTime OBJECT-TYPE
         SYNTAX   INTEGER (0..2147483647)
         MAX-ACCESS   read-only
         STATUS        current
         DESCRIPTION
            "Amount of time in seconds that has elapsed since the 
            counters have been reset."
         ::= { aal5LayerStatsEntry 16 }
    
     atmxVccStatsTable   OBJECT-TYPE
         SYNTAX   SEQUENCE OF AtmxVccStatsEntry
         MAX-ACCESS   not-accessible
         STATUS        current
         DESCRIPTION
         	"A table of ATM virtual channel connection statistics 
         	information."
         ::= { atmxVccStatsGroup 1 }
     atmxVccStatsEntry   OBJECT-TYPE
         SYNTAX   AtmxVccStatsEntry
         MAX-ACCESS   not-accessible
         STATUS        current
         DESCRIPTION
            "An entry in the table, containing information about
            the ATM virtual channel connection statistics."
	     INDEX   { atmxPortIndex, atmxVccVci }
         ::= { atmxVccStatsTable 1 }
     AtmxVccStatsEntry ::= SEQUENCE {
 		 atmxVccStatsTxSDUs 		Counter32,
 		 atmxVccStatsTxCells		Counter32,
 		 atmxVccStatsTxOctets		Counter32,
 		 atmxVccStatsRxSDUs 		Counter32,
 		 atmxVccStatsRxCells		Counter32,
 		 atmxVccStatsRxOctets		Counter32,
 		 atmxVccStatsTxSDUDiscards  Counter32,
 		 atmxVccStatsTxErrors		Counter32,
 		 atmxVccStatsRxSDUDiscards  Counter32,
 		 atmxVccStatsRxErrors		Counter32,
 		 atmxVccStatsRxSarTimeouts  Counter32,
 		 atmxVccStatsRxCrcErrors	Counter32,
 		 atmxVccStatsRxOversizedSdus   Counter32,
 		 atmxVccStatsConnCreateTime    INTEGER,
 		 atmxVccStatsConnInIdleTime    INTEGER,
 		 atmxVccStatsConnOutIdleTime   INTEGER,
 		 atmxVccStatsConnModifiedTime  INTEGER
     }
     atmxVccStatsTxSDUs OBJECT-TYPE
         SYNTAX   Counter32
         MAX-ACCESS   read-only
         STATUS        current
         DESCRIPTION
            "The total number of transmitted SDU's on this virtual channel."
         ::= { atmxVccStatsEntry 3 }
     atmxVccStatsTxCells OBJECT-TYPE
         SYNTAX   Counter32
         MAX-ACCESS   read-only
         STATUS        current
         DESCRIPTION
            "The total number of transmitted cells on this virtual channel."
         ::= { atmxVccStatsEntry 4 }
	     atmxVccStatsTxOctets OBJECT-TYPE
         SYNTAX   Counter32
         MAX-ACCESS   read-only
         STATUS        current
         DESCRIPTION
            "The total number of transmitted octets on this virtual channel."
         ::= { atmxVccStatsEntry 5 }
     atmxVccStatsRxSDUs OBJECT-TYPE
         SYNTAX   Counter32
         MAX-ACCESS   read-only
         STATUS        current
         DESCRIPTION
            "The total number of received SDU's on this virtual channel."
         ::= { atmxVccStatsEntry 6 }
     atmxVccStatsRxCells OBJECT-TYPE
         SYNTAX   Counter32
         MAX-ACCESS   read-only
         STATUS        current
         DESCRIPTION
            "The total number of received cells on this virtual channel."
         ::= { atmxVccStatsEntry 7 }
     atmxVccStatsRxOctets	OBJECT-TYPE
         SYNTAX   Counter32
         MAX-ACCESS   read-only
         STATUS        current
         DESCRIPTION
            "The total number of received octets on this virtual channel."
         ::= { atmxVccStatsEntry 8 }
     atmxVccStatsTxSDUDiscards OBJECT-TYPE
         SYNTAX   Counter32
         MAX-ACCESS   read-only
         STATUS        current
         DESCRIPTION
            "The total number of transmit SDUs discarded on this virtual channel."
         ::= { atmxVccStatsEntry 9 }
     atmxVccStatsTxErrors OBJECT-TYPE
         SYNTAX   Counter32
         MAX-ACCESS   read-only
         STATUS        current
         DESCRIPTION
            "The total number of transmit SDU errors on this virtual channel."
         ::= { atmxVccStatsEntry 10 }
     atmxVccStatsRxSDUDiscards OBJECT-TYPE
         SYNTAX   Counter32
         MAX-ACCESS   read-only
         STATUS        current
         DESCRIPTION
            "The total number of receive SDU's discarded on this virtual channel."
         ::= { atmxVccStatsEntry 11 }
     atmxVccStatsRxErrors OBJECT-TYPE
         SYNTAX   Counter32
         MAX-ACCESS   read-only
         STATUS        current
         DESCRIPTION
            "The total number of receive SDU's with errors on this virtual channel."
         ::= { atmxVccStatsEntry 12 }
     atmxVccStatsRxSarTimeouts OBJECT-TYPE
         SYNTAX   Counter32
         MAX-ACCESS   read-only
         STATUS        current
         DESCRIPTION
            "The  total number of partially re-assembled SDUs that were discarded."
         ::= { atmxVccStatsEntry 13 }
     atmxVccStatsRxCrcErrors OBJECT-TYPE
         SYNTAX   Counter32
         MAX-ACCESS   read-only
         STATUS        current
         DESCRIPTION
            "The total number of receive SDU's crc errors on this virtual channel."
         ::= { atmxVccStatsEntry 14 }
     atmxVccStatsRxOversizedSdus	OBJECT-TYPE
         SYNTAX   Counter32
         MAX-ACCESS   read-only
         STATUS        current
         DESCRIPTION
            "The total number of receive SDU's that are oversized."
         ::= { atmxVccStatsEntry 15 }
     atmxVccStatsConnCreateTime	OBJECT-TYPE
         SYNTAX   INTEGER (0..2147483647)
         MAX-ACCESS   read-only
         STATUS        current
         DESCRIPTION
            "Time elapsed in seconds since the connection has been created."
         ::= { atmxVccStatsEntry 16 }
     atmxVccStatsConnInIdleTime	OBJECT-TYPE
         SYNTAX   INTEGER (0..2147483647)
         MAX-ACCESS   read-only
         STATUS        current
         DESCRIPTION
            "Time that has elapsed in seconds since any traffic has
            been received on this connection."
         ::= { atmxVccStatsEntry 17 }
     atmxVccStatsConnOutIdleTime	OBJECT-TYPE
         SYNTAX   INTEGER (0..2147483647)
         MAX-ACCESS   read-only
         STATUS        current
         DESCRIPTION
            "Time that has elapsed in seconds since any traffic has
            been sent out on this connection."
         ::= { atmxVccStatsEntry 18 }
     atmxVccStatsConnModifiedTime	OBJECT-TYPE
         SYNTAX   INTEGER (0..2147483647)
         MAX-ACCESS   read-only
         STATUS        current
         DESCRIPTION
            "Time that has elapsed in seconds since any connection 
            parameters have been modified."
         ::= { atmxVccStatsEntry 19 }
    
     atmxLecStatsTable   OBJECT-TYPE
         SYNTAX   SEQUENCE OF AtmxLecStatsEntry
         MAX-ACCESS   not-accessible
         STATUS        current
         DESCRIPTION
         	"A table of ATM LEC statistics information."
         ::= { atmxLecStatsGroup 1 }
     atmxLecStatsEntry   OBJECT-TYPE
         SYNTAX   AtmxLecStatsEntry
         MAX-ACCESS   not-accessible
         STATUS        current
         DESCRIPTION
            "An entry in the table, containing information about
            the LEC statistics."
         INDEX   { atmxLecIndex }
         ::= { atmxLecStatsTable 1 }
     AtmxLecStatsEntry ::= SEQUENCE {
 		 atmxLecStatsTxArpReq			Counter32,
 		 atmxLecStatsTxArpRsp			Counter32,
 		 atmxLecStatsTxControlPkts  	Counter32,
 		 atmxLecStatsTxUnicastPkts  	Counter32,
 		 atmxLecStatsTxMulticastPkts	Counter32,
 		 atmxLecStatsTxBroadcastPkts	Counter32,
 		 atmxLecStatsTxDiscardPkts  	Counter32,
 		 atmxLecStatsRxArpReq			Counter32,
 		 atmxLecStatsRxArpRsp			Counter32,
 		 atmxLecStatsRxControlPkts  	Counter32,
 		 atmxLecStatsRxUnicastPkts  	Counter32,
 		 atmxLecStatsRxMulticastPkts	Counter32,
 		 atmxLecStatsRxBroadcastPkts	Counter32,
 		 atmxLecStatsRxDiscardPkts  	Counter32
     }
     atmxLecStatsTxArpReq	OBJECT-TYPE
         SYNTAX   Counter32
         MAX-ACCESS   read-only
         STATUS        current
         DESCRIPTION
            "Total number of ARP requests transmitted from this LEC."
         ::= { atmxLecStatsEntry 2 }
     atmxLecStatsTxArpRsp	OBJECT-TYPE
         SYNTAX	Counter32
         MAX-ACCESS   read-only
         STATUS        current
         DESCRIPTION
            "Total number of ARP responses transmitted from this LEC."
         ::= { atmxLecStatsEntry 3 }
     atmxLecStatsTxControlPkts	OBJECT-TYPE
         SYNTAX 	Counter32  
         MAX-ACCESS   read-only
         STATUS        current
         DESCRIPTION
            "Total number of control packets transmitted from this LEC."
         ::= { atmxLecStatsEntry 4 }
     atmxLecStatsTxUnicastPkts	OBJECT-TYPE
         SYNTAX	Counter32   
         MAX-ACCESS   read-only
         STATUS        current
         DESCRIPTION
            "Total number of unicast packets transmitted from this LEC."
         ::= { atmxLecStatsEntry 5 }
     atmxLecStatsTxMulticastPkts	OBJECT-TYPE
         SYNTAX	Counter32   
         MAX-ACCESS   read-only
         STATUS        current
         DESCRIPTION
            "Total number of multicast packets transmitted from this LEC."
         ::= { atmxLecStatsEntry 6 }
     atmxLecStatsTxBroadcastPkts	OBJECT-TYPE
         SYNTAX	Counter32   
         MAX-ACCESS   read-only
         STATUS        current
         DESCRIPTION
            "Total number of broadcast packets transmitted from this LEC."
         ::= { atmxLecStatsEntry 7 }
     atmxLecStatsTxDiscardPkts	OBJECT-TYPE
         SYNTAX	Counter32   
         MAX-ACCESS   read-only
         STATUS        current
         DESCRIPTION
            "Total number of transmission packets discarded from this LEC."
         ::= { atmxLecStatsEntry 8 }
     atmxLecStatsRxArpReq	OBJECT-TYPE
         SYNTAX	Counter32   
         MAX-ACCESS   read-only
         STATUS        current
         DESCRIPTION
            "Total number of ARP requests received for this LEC."
         ::= { atmxLecStatsEntry 9 }
     atmxLecStatsRxArpRsp	OBJECT-TYPE
         SYNTAX	Counter32   
         MAX-ACCESS   read-only
         STATUS        current
         DESCRIPTION
            "Total number of ARP responses received for this LEC."
         ::= { atmxLecStatsEntry 10 }
     atmxLecStatsRxControlPkts	OBJECT-TYPE
         SYNTAX	Counter32   
         MAX-ACCESS   read-only
         STATUS        current
         DESCRIPTION
            "Total number of control packets received for this LEC."
         ::= { atmxLecStatsEntry 11 }
     atmxLecStatsRxUnicastPkts	OBJECT-TYPE
         SYNTAX	Counter32   
         MAX-ACCESS   read-only
         STATUS        current
         DESCRIPTION
            "Total number of unicast packets received for this LEC."
         ::= { atmxLecStatsEntry 12 }
     atmxLecStatsRxMulticastPkts	OBJECT-TYPE
         SYNTAX	Counter32   
         MAX-ACCESS   read-only
         STATUS        current
         DESCRIPTION
            "Total number of multicast packets received for this LEC."
         ::= { atmxLecStatsEntry 13 }
     atmxLecStatsRxBroadcastPkts	OBJECT-TYPE
         SYNTAX	Counter32   
         MAX-ACCESS   read-only
         STATUS        current
         DESCRIPTION
            "Total number of broadcast packets received for this LEC."
         ::= { atmxLecStatsEntry 14 }
     atmxLecStatsRxDiscardPkts	OBJECT-TYPE
         SYNTAX	Counter32   
         MAX-ACCESS   read-only
         STATUS        current
         DESCRIPTION
            "Total number of discarded packets received for this LEC."
         ::= { atmxLecStatsEntry 15 }
    
     atmxCipStatsTable   OBJECT-TYPE
         SYNTAX   SEQUENCE OF AtmxCipStatsEntry
         MAX-ACCESS   not-accessible
         STATUS        current
         DESCRIPTION
         	"A table of ATM CIP statistics information."
         ::= { atmxCipStatsGroup 1 }
     atmxCipStatsEntry   OBJECT-TYPE
         SYNTAX   AtmxCipStatsEntry
         MAX-ACCESS   not-accessible
         STATUS        current
         DESCRIPTION
            "An entry in the table, containing information about
            the CIP statistics."
         INDEX   { atmxCipIndex }
         ::= { atmxCipStatsTable 1 }
     AtmxCipStatsEntry ::= SEQUENCE {
 		 atmxCipStatsPktsFromOtherLIS	Counter32,
 		 atmxCipStatsTxArpReq		Counter32,
 		 atmxCipStatsTxArpRsp		Counter32,
 		 atmxCipStatsTxInArpReq 	Counter32,
 		 atmxCipStatsTxInArpRsp 	Counter32,
 		 atmxCipStatsTxDiscards 	Counter32,
 		 atmxCipStatsRxArpReq		Counter32,
 		 atmxCipStatsRxArpRsp		Counter32,
 		 atmxCipStatsRxInArpReq 	Counter32,
 		 atmxCipStatsRxInArpRsp 	Counter32,
 		 atmxCipStatsRxDiscards 	Counter32
     }
     atmxCipStatsPktsFromOtherLIS	OBJECT-TYPE
         SYNTAX   Counter32
         MAX-ACCESS   read-only
         STATUS        current
         DESCRIPTION
            "Total number of packets received that does not belong 
            to this logical IP subnet."
         ::= { atmxCipStatsEntry 2 }
     atmxCipStatsTxArpReq	OBJECT-TYPE
         SYNTAX   Counter32
         MAX-ACCESS   read-only
         STATUS        current
         DESCRIPTION
            "Total number of ARP requests transmitted from this CIP."
         ::= { atmxCipStatsEntry 3 }
     atmxCipStatsTxArpRsp	OBJECT-TYPE
         SYNTAX   Counter32
         MAX-ACCESS   read-only
         STATUS        current
         DESCRIPTION
            "Total number of ARP responses transmitted from this CIP."
         ::= { atmxCipStatsEntry 4 }
     atmxCipStatsTxInArpReq	OBJECT-TYPE
         SYNTAX   Counter32
         MAX-ACCESS   read-only
         STATUS        current
         DESCRIPTION
            "Total number of InARP requests transmitted from this CIP."
         ::= { atmxCipStatsEntry 5 }
     atmxCipStatsTxInArpRsp	OBJECT-TYPE
         SYNTAX   Counter32
         MAX-ACCESS   read-only
         STATUS        current
         DESCRIPTION
            "Total number of InARP responses transmitted from this CIP."
         ::= { atmxCipStatsEntry 6 }
     atmxCipStatsTxDiscards	OBJECT-TYPE
         SYNTAX   Counter32
         MAX-ACCESS   read-only
         STATUS        current
         DESCRIPTION
            "Total number of packets discarded on transmit from this CIP."
         ::= { atmxCipStatsEntry 7 }
     atmxCipStatsRxArpReq	OBJECT-TYPE
         SYNTAX   Counter32
         MAX-ACCESS   read-only
         STATUS        current
         DESCRIPTION
            "Total number of ARP requests received for this CIP."
         ::= { atmxCipStatsEntry 8 }
     atmxCipStatsRxArpRsp	OBJECT-TYPE
         SYNTAX   Counter32
         MAX-ACCESS   read-only
         STATUS        current
         DESCRIPTION
            "Total number of ARP responses received for this CIP."
         ::= { atmxCipStatsEntry 9 }
     atmxCipStatsRxInArpReq	OBJECT-TYPE
         SYNTAX   Counter32
         MAX-ACCESS   read-only
         STATUS        current
         DESCRIPTION
            "Total number of InARP requests received for this CIP."
         ::= { atmxCipStatsEntry 10 }
     atmxCipStatsRxInArpRsp	OBJECT-TYPE
         SYNTAX   Counter32
         MAX-ACCESS   read-only
         STATUS        current
         DESCRIPTION
            "Total number of InARP responsese received for this CIP."
         ::= { atmxCipStatsEntry 11 }
     atmxCipStatsRxDiscards	OBJECT-TYPE
         SYNTAX   Counter32
         MAX-ACCESS   read-only
         STATUS        current
         DESCRIPTION
            "Total number of packets discarded on receive for this CIP."
         ::= { atmxCipStatsEntry 12 }
    
     atmxSscopStatsTable   OBJECT-TYPE
         SYNTAX   SEQUENCE OF AtmxSscopStatsEntry
         MAX-ACCESS   not-accessible
         STATUS        current
         DESCRIPTION
         	"A table of ATM Service Specific Connection Oriented Protocol
         	(SSCOP)  statistics information."
         ::= { atmxSscopStatsGroup 1 }
     atmxSscopStatsEntry   OBJECT-TYPE
         SYNTAX   AtmxSscopStatsEntry
         MAX-ACCESS   not-accessible
         STATUS        current
         DESCRIPTION
            "An entry in the table, containing information about
            the ATM SSCOP statistics."
         INDEX   { atmxPortIndex }
         ::= { atmxSscopStatsTable 1 }
     AtmxSscopStatsEntry ::= SEQUENCE {
 		 atmxSscopStatsTxTotalPdus  	Counter32,
 		 atmxSscopStatsTxDiscardSdus	Counter32,
 		 atmxSscopStatsTxDiscardPdus	Counter32,
 		 atmxSscopStatsTxErrorPdus  	Counter32,
 		 atmxSscopStatsTxBufferInUseCtr Counter32,
 		 atmxSscopStatsTxBufferInUseGauge	Gauge32,
 		 atmxSscopStatsRxTotalPdus  		Counter32,
 		 atmxSscopStatsRxDiscardPdus		Counter32,
 		 atmxSscopStatsRxErrorPdus  		Counter32,
 		 atmxSscopStatsRxBufferInUseCtr 	Counter32,
 		 atmxSscopStatsRxBufferInUseGauge	Gauge32
     }
     atmxSscopStatsTxTotalPdus OBJECT-TYPE
         SYNTAX   Counter32
         MAX-ACCESS   read-only
         STATUS        current
         DESCRIPTION
            "Total number of transmit PDU's sent without error by SSCOP."
         ::= { atmxSscopStatsEntry 1 }
     atmxSscopStatsTxDiscardSdus OBJECT-TYPE
         SYNTAX   Counter32
         MAX-ACCESS   read-only
         STATUS        current
         DESCRIPTION
            "Total number of transmit SDUs discarded by SSCOP."
         ::= { atmxSscopStatsEntry 2 }
     atmxSscopStatsTxDiscardPdus OBJECT-TYPE
         SYNTAX   Counter32
         MAX-ACCESS   read-only
         STATUS        current
         DESCRIPTION
            "Total number of transmit PDUs discarded by SSCOP."
         ::= { atmxSscopStatsEntry 3 }
     atmxSscopStatsTxErrorPdus OBJECT-TYPE
         SYNTAX   Counter32
         MAX-ACCESS   read-only
         STATUS        current
         DESCRIPTION
            "Total number of transmit PDUs with transmission errors."
         ::= { atmxSscopStatsEntry 4 }
     atmxSscopStatsTxBufferInUseCtr	OBJECT-TYPE
         SYNTAX   Counter32
         MAX-ACCESS   read-only
         STATUS        current
         DESCRIPTION
            "Transmit buffer in-use counter."
         ::= { atmxSscopStatsEntry 5 }
     atmxSscopStatsTxBufferInUseGauge OBJECT-TYPE
         SYNTAX   Gauge32
         MAX-ACCESS   read-only
         STATUS        current
         DESCRIPTION
            "Transmit buffer in-use gauge."
         ::= { atmxSscopStatsEntry 6 }
     atmxSscopStatsRxTotalPdus OBJECT-TYPE
         SYNTAX   Counter32
         MAX-ACCESS   read-only
         STATUS        current
         DESCRIPTION
            "Total number of PDU's received without error by SSCOP."
         ::= { atmxSscopStatsEntry 7 }
     atmxSscopStatsRxDiscardPdus OBJECT-TYPE
         SYNTAX   Counter32
         MAX-ACCESS   read-only
         STATUS        current
         DESCRIPTION
            "Total number of PDUs discarded on receipt by SSCOP."
         ::= { atmxSscopStatsEntry 8 }
     atmxSscopStatsRxErrorPdus OBJECT-TYPE
         SYNTAX   Counter32
         MAX-ACCESS   read-only
         STATUS        current
         DESCRIPTION
            "Total number of received PDUs with reception errors."
         ::= { atmxSscopStatsEntry 9 }
     atmxSscopStatsRxBufferInUseCtr OBJECT-TYPE
         SYNTAX   Counter32
         MAX-ACCESS   read-only
         STATUS        current
         DESCRIPTION
            "Receive buffer in-use counter."
         ::= { atmxSscopStatsEntry 10 }
     atmxSscopStatsRxBufferInUseGauge OBJECT-TYPE
         SYNTAX   Gauge32
         MAX-ACCESS   read-only
         STATUS        current
         DESCRIPTION
            "Receive buffer in-use gauge."
         ::= { atmxSscopStatsEntry 11 }
    
     atmxIlmiStatsTable   OBJECT-TYPE
         SYNTAX   SEQUENCE OF AtmxIlmiStatsEntry
         MAX-ACCESS   not-accessible
         STATUS        current
         DESCRIPTION
         	"A table of ATM ILMI statistics information."
         ::= { atmxIlmiStatsGroup 1 }
     atmxIlmiStatsEntry   OBJECT-TYPE
         SYNTAX   AtmxIlmiStatsEntry
         MAX-ACCESS   not-accessible
         STATUS        current
         DESCRIPTION
            "An entry in the table, containing information about
            the ATM ILMI statistics."
         INDEX   { atmxPortIndex }
         ::= { atmxIlmiStatsTable 1 }
     AtmxIlmiStatsEntry ::= SEQUENCE {
 		 atmxIlmiTxPDUs 		 Counter32,
 		 atmxIlmiRxPDUs 		 Counter32,
 		 atmxIlmiRxDiscardPDUs   Counter32
     }
     atmxIlmiTxPDUs	OBJECT-TYPE
         SYNTAX   Counter32
         MAX-ACCESS   read-only
         STATUS        current
         DESCRIPTION
            "Total number of transmitted PDUs over the
		ILMI connection."
         ::= { atmxIlmiStatsEntry 2 }
     atmxIlmiRxPDUs	OBJECT-TYPE
         SYNTAX   Counter32
         MAX-ACCESS   read-only
         STATUS        current
         DESCRIPTION
            "Total number of received PDUs over the ILMI 
		connection."
         ::= { atmxIlmiStatsEntry 3 }
     atmxIlmiRxDiscardPDUs	OBJECT-TYPE
         SYNTAX   Counter32
         MAX-ACCESS   read-only
         STATUS        current
         DESCRIPTION
            "Total number of received PDUs that are
		received over the ILMI connection and discarded."
         ::= { atmxIlmiStatsEntry 4 }
     
     
     atmxVccTable   OBJECT-TYPE
         SYNTAX   SEQUENCE OF AtmxVccEntry
         MAX-ACCESS   not-accessible
         STATUS        current
         DESCRIPTION
            "A table of ATM virtual channel connections status and
            parameter information."
            ::= { atmxVccGroup 1 }
     atmxVccEntry   OBJECT-TYPE
         SYNTAX   AtmxVccEntry
         MAX-ACCESS   not-accessible
         STATUS        current
         DESCRIPTION
            "An entry in the table, containing information about
            the ATM virtual channel connections."
         INDEX   { atmxPortIndex, atmxVccVci}
            ::= { atmxVccTable 1 }
	AtmxVccEntry ::= SEQUENCE {
		atmxVccVpi             AtmVpi,
		atmxVccVci             AtmVci,
		atmxVccCircuitType     INTEGER,
		atmxVccOperStatus      AtmConnectionOperStatusCodes,
		atmxVccUpTime          Unsigned32,
		atmxVccTxQosClass      AtmQosClass,
		atmxVccTxBestEffort    INTEGER,
		atmxVccTxPeakCellRate  INTEGER,
		atmxVccRxQosClass      AtmQosClass,
		atmxVccRxBestEffort    INTEGER,
		atmxVccRxPeakCellRate  INTEGER,
		atmxVccRowStatus       RowStatus,
		atmxVccServiceType     INTEGER
	}
    atmxVccVpi OBJECT-TYPE
        SYNTAX   AtmVpi
        MAX-ACCESS   read-only
        STATUS       current
        DESCRIPTION
            "The virtual path identifier associated with this
            virtual connection."
        ::= { atmxVccEntry 2 }
    atmxVccVci OBJECT-TYPE
        SYNTAX   AtmVci
        MAX-ACCESS   not-accessible
        STATUS        current
        DESCRIPTION
            "The virtual channel identifier associated with the
            virtual connection."
        ::= { atmxVccEntry 3 }
    atmxVccCircuitType OBJECT-TYPE
        SYNTAX      INTEGER {	pvc(1), svc(2) }
        MAX-ACCESS  read-create
        STATUS      current
        DESCRIPTION
            "The virtual connection circuit type."
        ::= { atmxVccEntry 4 }
    atmxVccOperStatus OBJECT-TYPE
        SYNTAX   AtmConnectionOperStatusCodes
        MAX-ACCESS   read-only
        STATUS        current
        DESCRIPTION
            "The actual operational status of the VCC."
        ::= { atmxVccEntry 5 }
    atmxVccUpTime OBJECT-TYPE
        SYNTAX   Unsigned32
        MAX-ACCESS   read-only
        STATUS        current
        DESCRIPTION
            "The virtual channel connection up time in seconds since 
            atmxVccOperStatus transitioned to the value 'up'."
        ::= { atmxVccEntry 6 }
    atmxVccTxQosClass	OBJECT-TYPE
        SYNTAX   AtmQosClass
        MAX-ACCESS   read-create
        STATUS        current
        DESCRIPTION
            "Transmit Quality of Service for this virtual channel
            connection."
        ::= { atmxVccEntry 7 }
    atmxVccTxBestEffort	OBJECT-TYPE
        SYNTAX   INTEGER { false(1), true(2) }
        MAX-ACCESS   read-create
        STATUS        current
        DESCRIPTION
            "Transmit Best Effort Indicator for this virtual channel
            connection."
        ::= { atmxVccEntry 8 }
    atmxVccTxPeakCellRate	OBJECT-TYPE
        SYNTAX   INTEGER (192..20000)
        MAX-ACCESS   read-create
        STATUS        current
        DESCRIPTION
            "Peak Cell Rate for CLP 0+1 in the transmit direction
            for this virtual channel connection."
        ::= { atmxVccEntry 9 }
    atmxVccRxQosClass	OBJECT-TYPE
        SYNTAX   AtmQosClass
        MAX-ACCESS   read-create
        STATUS        current
        DESCRIPTION
            "Receive Quality of Service for this virtual channel
            connection."
        ::= { atmxVccEntry 10 }
    atmxVccRxBestEffort	OBJECT-TYPE
        SYNTAX      INTEGER { false(1), true(2) }
        MAX-ACCESS  read-create
        STATUS      current
        DESCRIPTION
            "Receive Best Effort Indicator for this virtual channel
            connection."
        ::= { atmxVccEntry 11 }
    atmxVccRxPeakCellRate	OBJECT-TYPE
        SYNTAX   INTEGER (192..20000)
        MAX-ACCESS   read-create
        STATUS        current
        DESCRIPTION
            "Peak Cell Rate for CLP 0+1 in the receive direction
            for this virtual channel connection."
        ::= { atmxVccEntry 12 }
    atmxVccRowStatus	OBJECT-TYPE
        SYNTAX   RowStatus
        MAX-ACCESS   read-create
        STATUS        current
        DESCRIPTION
            "Only the values 'active', 'createAndGo', and 'delete'
            are supported."
        ::= { atmxVccEntry 13 }
    atmxVccServiceType OBJECT-TYPE
        SYNTAX      INTEGER {
				sscop(1), 
				ilmi(2),
				lec(3),
				cip(4),
				oam(5),
				pt-pt(6),
				trunk(7),
				csr(8)
				}
        MAX-ACCESS  read-create
        STATUS      current
        DESCRIPTION
            "The virtual connection Service type."
        ::= { atmxVccEntry 14 }
    
    
    
    
    atmxLecArpTable	OBJECT-TYPE
        SYNTAX   SEQUENCE OF AtmxLecArpEntry
        MAX-ACCESS   not-accessible
        STATUS        current
        DESCRIPTION
            "A table of ATM address to MAC address information."
        ::= { atmxLecArpGroup 1 }
    atmxLecArpEntry   OBJECT-TYPE
        SYNTAX   AtmxLecArpEntry
        MAX-ACCESS   not-accessible
        STATUS        current
        DESCRIPTION
            "An entry in the table, containing information about
            the ATM address."
        INDEX   { atmxLecIndex, atmxLecArpMacAddress}
        ::= { atmxLecArpTable 1 }
    AtmxLecArpEntry ::= SEQUENCE {
 		atmxLecArpMacAddress	MacAddress,
 		atmxLecArpAtmAddress	AtmAddress,
 		atmxLecArpVci			AtmVci,
 		atmxLecArpTimeToLive	INTEGER,
 		atmxLecArpSource        AtmxArpEntryType,
 		atmxLecArpRowStatus     RowStatus
    }
    atmxLecArpMacAddress	OBJECT-TYPE
        SYNTAX   MacAddress
        MAX-ACCESS   not-accessible
        STATUS        current
        DESCRIPTION
            "The MAC address for identifying this Arp entry."
        ::= { atmxLecArpEntry 2 }
    atmxLecArpAtmAddress OBJECT-TYPE
        SYNTAX   AtmAddress
        MAX-ACCESS   read-create
        STATUS        current
        DESCRIPTION
            "The ATM address for the corresponding MAC addess."
        ::= { atmxLecArpEntry 3 }
    atmxLecArpVci OBJECT-TYPE
        SYNTAX   AtmVci
        MAX-ACCESS   read-create
        STATUS        current
        DESCRIPTION
            "The virtual channel identifier associated with Arp entry."
        ::= { atmxLecArpEntry 4 }
    atmxLecArpTimeToLive OBJECT-TYPE
        SYNTAX   INTEGER (0..15)
        MAX-ACCESS   read-only
        STATUS        current
        DESCRIPTION
            "The address time to live in seconds. The value 0 indicates
            an infinite time to live."
        ::= { atmxLecArpEntry 5 }
    atmxLecArpSource OBJECT-TYPE
        SYNTAX   AtmxArpEntryType
        MAX-ACCESS   read-only
        STATUS        current
        DESCRIPTION
           "The source of this Arp entry."
        ::= { atmxLecArpEntry 6 }
    atmxLecArpRowStatus OBJECT-TYPE
        SYNTAX       RowStatus
        MAX-ACCESS   read-create
        STATUS       current
        DESCRIPTION
            "Only the values 'active', 'createAndGo', and 'delete'
            are supported."
        ::= { atmxLecArpEntry 7 }
    
    
    
    
    atmxCipArpTable OBJECT-TYPE
        SYNTAX   SEQUENCE OF AtmxCipArpEntry
        MAX-ACCESS   not-accessible
        STATUS        current
        DESCRIPTION
           "A table of ATM address to IP address information."
        ::= { atmxCipArpGroup 1 }
    atmxCipArpEntry   OBJECT-TYPE
        SYNTAX   AtmxCipArpEntry
        MAX-ACCESS   not-accessible
        STATUS        current
        DESCRIPTION
        	"An entry in the table, containing information about
            the ATM address."
        INDEX   { atmxCipIndex, atmxCipArpIPAddress}
        ::= { atmxCipArpTable 1 }
    AtmxCipArpEntry ::=  SEQUENCE {
 		 atmxCipArpIPAddress	 IpAddress,
 		 atmxCipArpAtmAddress	 AtmAddress,
 		 atmxCipArpVci  		 AtmClientVci,
 		 atmxCipArpTimeToLive	 INTEGER,
 		 atmxCipArpSource        AtmxArpEntryType,
 		 atmxCipArpRowStatus     RowStatus
    }
    atmxCipArpIPAddress OBJECT-TYPE
        SYNTAX   IpAddress
        MAX-ACCESS   not-accessible
        STATUS        current
        DESCRIPTION
           "The IP address for this Arp entry."
        ::= { atmxCipArpEntry 2 }
    atmxCipArpAtmAddress OBJECT-TYPE
        SYNTAX   AtmAddress
        MAX-ACCESS   read-create
        STATUS        current
        DESCRIPTION
           "The ATM address for the Arp address."
        ::= { atmxCipArpEntry 3 }
    atmxCipArpVci OBJECT-TYPE
        SYNTAX   AtmClientVci
        MAX-ACCESS   read-create
        STATUS        current
        DESCRIPTION
           "The virtual channel identifier associated with Arp entry."
        ::= { atmxCipArpEntry 4 }
    atmxCipArpTimeToLive OBJECT-TYPE
        SYNTAX   INTEGER (0..15)
        MAX-ACCESS   read-only
        STATUS        current
        DESCRIPTION
           "The Arp Entry time to live in seconds. The value 0 indicates
           an infinite time to live"
        ::= { atmxCipArpEntry 5 }
    atmxCipArpSource OBJECT-TYPE
        SYNTAX   AtmxArpEntryType
        MAX-ACCESS   read-create
        STATUS        current
        DESCRIPTION
           "The source of this Arp entry."
        ::= { atmxCipArpEntry 6 }
    atmxCipArpRowStatus OBJECT-TYPE
        SYNTAX       RowStatus
        MAX-ACCESS   read-create
        STATUS       current
        DESCRIPTION
            "Only the values 'active', 'createAndGo', and 'delete'
            are supported."
        ::= { atmxCipArpEntry 7 }
    
    
    
    
    atmxPtToPtTable OBJECT-TYPE
        SYNTAX   SEQUENCE OF AtmxPtToPtEntry
        MAX-ACCESS   not-accessible
        STATUS        current
        DESCRIPTION
           "A table of point to point over ATM."
        ::= { atmxPtToPtGroup 1 }
    atmxPtToPtEntry   OBJECT-TYPE
        SYNTAX   AtmxPtToPtEntry
        MAX-ACCESS   not-accessible
        STATUS        current
        DESCRIPTION
        	"An entry in the table containg information about the 
        	point to point connection."
        INDEX   { atmxPtToPtIndex}
        ::= { atmxPtToPtTable 1 }
    AtmxPtToPtEntry ::=  SEQUENCE {
        atmxPtToPtIndex         INTEGER,
        atmxPtToPtDescription   DisplayString,
 		atmxPtToPtEncap         INTEGER,
 		atmxPtToPtConnType      INTEGER,
 		atmxPtToPtVci           AtmClientVci,
 		atmxPtToPtDestAddr      AtmAddress,
 		atmxPtToPtRowStatus     RowStatus,
        atmxPtToPtIfIndex       IfIndexOrZero,
        atmxPtToPtVlanNumber	AtmxVlanRange,
        atmxPtToPtAdminStatus   AtmAdminStatus,
        atmxPtToPtOperStatus    AtmConnectionOperStatusCodes
    }
    atmxPtToPtIndex OBJECT-TYPE
        SYNTAX      INTEGER (1..32)
        MAX-ACCESS  not-accessible
        STATUS      current
        DESCRIPTION
            "The index which identifies each entry instance."
        ::= { atmxPtToPtEntry 1 }
    atmxPtToPtDescription OBJECT-TYPE
        SYNTAX      DisplayString (SIZE(0..31))
        MAX-ACCESS  read-create
        STATUS      current
        DESCRIPTION
            "A description of the point to point link."
        ::= { atmxPtToPtEntry 2 }
    atmxPtToPtEncap OBJECT-TYPE
        SYNTAX      INTEGER {
                        rfc1483(1),
                        private(2)
                    }
        MAX-ACCESS  read-create
        STATUS      current
        DESCRIPTION
            "The data encapsulation format. 'rfc1483' identifies the
            format defined in RFC 1483."
        ::= { atmxPtToPtEntry 3 }
    atmxPtToPtConnType OBJECT-TYPE
        SYNTAX      INTEGER {
                        pvc(1),
                        svc(2)
                    }
        MAX-ACCESS  read-create
        STATUS      current
        DESCRIPTION
            "The connection type of the point to point link."
        ::= { atmxPtToPtEntry 4 }
    atmxPtToPtVci OBJECT-TYPE
        SYNTAX      AtmClientVci
        MAX-ACCESS  read-create
        STATUS      current
        DESCRIPTION
            "The VCI used if atmxPtToPtConnType has the value 'pvc'."
        ::= { atmxPtToPtEntry 5 }
    atmxPtToPtDestAddr OBJECT-TYPE
        SYNTAX      AtmAddress
        MAX-ACCESS  read-create
        STATUS      current
        DESCRIPTION
            "The ATM address of the other end point of the connection."
        ::= { atmxPtToPtEntry 6 }
    atmxPtToPtRowStatus OBJECT-TYPE
        SYNTAX      RowStatus
        MAX-ACCESS  read-create
        STATUS      current
        DESCRIPTION
            "This object is used to create or delete an entry in the
            atmxPtToPtTable. Only the values 'active', 'createAndGo', and
            'delete' are supported.
            
			The objects atmxPtToPtVlanNumber, atmxPtToPtConnType, and 
			atmxPtToPtVci if atmxPtToPtConnType is 'pvc' or
			atmxPtToPtDestAddr if atmxPtToPtConnType is 'svc' are
			required for a successful 'createAndGo'.
            "
        ::= { atmxPtToPtEntry 7 }
    atmxPtToPtIfIndex OBJECT-TYPE
        SYNTAX      IfIndexOrZero
        MAX-ACCESS  read-only
        STATUS      current
        DESCRIPTION
            "This is the value of ifIndex or 0 if ifIndex is not known."
        ::= { atmxPtToPtEntry 8 }
    atmxPtToPtVlanNumber OBJECT-TYPE
        SYNTAX      AtmxVlanRange
        MAX-ACCESS  read-create
        STATUS      current
        DESCRIPTION
            "The VLAN which is supported by this point to point link."
        ::= { atmxPtToPtEntry 9 }
 	atmxPtToPtAdminStatus OBJECT-TYPE
	    SYNTAX  AtmAdminStatus
	    MAX-ACCESS  read-create
	    STATUS  current
	    DESCRIPTION
			"The administrative status of this point to point instance."
	    ::= { atmxPtToPtEntry 10 }
	atmxPtToPtOperStatus OBJECT-TYPE
	    SYNTAX  AtmConnectionOperStatusCodes
	    MAX-ACCESS  read-only
	    STATUS  current
	    DESCRIPTION
			"The operational status of this point to point instance."
	    ::= { atmxPtToPtEntry 11 }
    
    atmxPtToPtStatsTable OBJECT-TYPE
        SYNTAX   SEQUENCE OF AtmxPtToPtStatsEntry
        MAX-ACCESS   not-accessible
        STATUS        current
        DESCRIPTION
           "A table of point to point Statistics."
        ::= { atmxPtToPtGroup 2 }
    atmxPtToPtStatsEntry   OBJECT-TYPE
        SYNTAX   AtmxPtToPtStatsEntry
        MAX-ACCESS   not-accessible
        STATUS        current
        DESCRIPTION
        	"An entry in the table containg information about the 
        	point to point connection statistics."
        INDEX   { atmxPtToPtIndex}
        ::= { atmxPtToPtStatsTable 1 }
    AtmxPtToPtStatsEntry ::=  SEQUENCE {
        atmxPtToPtStatsTotalTxPkts    		INTEGER,
 	atmxPtToPtStatsTotalRxPkts    		INTEGER,
 	atmxPtToPtStatsTotalTxDiscards		INTEGER,
 	atmxPtToPtStatsTotalRxDiscards  	INTEGER
    }
    atmxPtToPtStatsTotalTxPkts OBJECT-TYPE
	 SYNTAX  INTEGER
	 MAX-ACCESS  read-only
	 STATUS  current
	 DESCRIPTION
		"Total Transmission Packets through this Connection."
	 ::= { atmxPtToPtStatsEntry 1 }
    atmxPtToPtStatsTotalRxPkts OBJECT-TYPE
	 SYNTAX  INTEGER
	 MAX-ACCESS  read-only
	 STATUS  current
	 DESCRIPTION
		"Total Packets Received through this Connection."
	 ::= { atmxPtToPtStatsEntry 2 }
    atmxPtToPtStatsTotalTxDiscards OBJECT-TYPE
	 SYNTAX  INTEGER
	 MAX-ACCESS  read-only
	 STATUS  current
	 DESCRIPTION
		"Total Transmission packets discarded by this connection."
	 ::= { atmxPtToPtStatsEntry 3 }
    atmxPtToPtStatsTotalRxDiscards OBJECT-TYPE
	 SYNTAX  INTEGER
	 MAX-ACCESS  read-only
	 STATUS  current
	 DESCRIPTION
		"Total Received packets discarded by this connection."
	 ::= { atmxPtToPtStatsEntry 4 }
   
    
    
    
    atmxTrunkTable OBJECT-TYPE
        SYNTAX   SEQUENCE OF AtmxTrunkEntry
        MAX-ACCESS   not-accessible
        STATUS        current
        DESCRIPTION
            "A table of trunk over ATM."
        ::= { atmxTrunkGroup 1 }
    atmxTrunkEntry   OBJECT-TYPE
        SYNTAX   AtmxTrunkEntry
        MAX-ACCESS   not-accessible
        STATUS        current
        DESCRIPTION
        	"An entry in the table containg information about the 
        	trunk connection."
        INDEX   { atmxTrunkIndex}
        ::= { atmxTrunkTable 1 }
    AtmxTrunkEntry ::=  SEQUENCE {
 		atmxTrunkIndex         INTEGER,
 		atmxTrunkDescription   DisplayString,
 		atmxTrunkConnType      INTEGER,
 		atmxTrunkVci           AtmClientVci,
 		atmxTrunkDestAddr      AtmAddress,
 		atmxTrunkRowStatus     RowStatus,
 		atmxTrunkAdminStatus   AtmAdminStatus,
 		atmxTrunkOperStatus    AtmConnectionOperStatusCodes
    }
    atmxTrunkIndex OBJECT-TYPE
        SYNTAX      INTEGER (1..32)
        MAX-ACCESS  not-accessible
        STATUS      current
        DESCRIPTION
            "The index which identifies each entry instance."
        ::= { atmxTrunkEntry 1 }
    atmxTrunkDescription OBJECT-TYPE
        SYNTAX      DisplayString (SIZE(0..31))
        MAX-ACCESS  read-create
        STATUS      current
        DESCRIPTION
            "A description of the trunk link."
        ::= { atmxTrunkEntry 2 }
    atmxTrunkConnType OBJECT-TYPE
        SYNTAX      INTEGER {
                        pvc(1),
                        svc(2)
                    }
        MAX-ACCESS  read-create
        STATUS      current
        DESCRIPTION
            "The connection type of the trunk link."
        ::= { atmxTrunkEntry 3 }
    atmxTrunkVci OBJECT-TYPE
        SYNTAX      AtmClientVci
        MAX-ACCESS  read-create
        STATUS      current
        DESCRIPTION
            "The VCI used if atmxTrunkConnType has the value 'pvc'."
        ::= { atmxTrunkEntry 4 }
    atmxTrunkDestAddr OBJECT-TYPE
        SYNTAX      AtmAddress
        MAX-ACCESS  read-create
        STATUS      current
        DESCRIPTION
            "The ATM address of the other end point of the connection if
            atmxTrunkConnType is 'svc'."
        ::= { atmxTrunkEntry 5 }
    atmxTrunkRowStatus OBJECT-TYPE
        SYNTAX      RowStatus
        MAX-ACCESS  read-create
        STATUS      current
        DESCRIPTION
			"This attribute is used to create or delete an entry in the
			atmxTrunkTable. Only the values 'active', 'createAndGo', and
			'delete' are supported.
			
			The following objects must exist for a successful create,
			atmxTrunkConnType and atmxTrunkVci if  atmxTrunkConnType has
			the value 'pvc' or atmxTrunkDestAddr if atmxTrunkConnType has
			the value 'svc'."
        ::= { atmxTrunkEntry 6 }
 	atmxTrunkAdminStatus OBJECT-TYPE
	    SYNTAX  AtmAdminStatus
	    MAX-ACCESS  read-create
	    STATUS  current
	    DESCRIPTION
			"The administrative status of this trunk instance."
	    ::= { atmxTrunkEntry 7 }
	atmxTrunkOperStatus OBJECT-TYPE
	    SYNTAX  AtmConnectionOperStatusCodes
	    MAX-ACCESS  read-only
	    STATUS  current
	    DESCRIPTION
			"The operational status of this trunk instance."
	    ::= { atmxTrunkEntry 8 }
	
	
	
    atmxTrunkVlanTable OBJECT-TYPE
        SYNTAX   SEQUENCE OF AtmxTrunkVlanEntry
        MAX-ACCESS   not-accessible
        STATUS        current
        DESCRIPTION
           "A table containing the list of 1 or more VLan which are
           trunked over ATM.  Creating an entry in this table creates
           entries in ifTable and SWITCH-VLAN_MIB.vPortTable. "
        ::= { atmxTrunkGroup 2 }
    atmxTrunkVlanEntry   OBJECT-TYPE
        SYNTAX   AtmxTrunkVlanEntry
        MAX-ACCESS   not-accessible
        STATUS        current
        DESCRIPTION
        	"An entry in the table identifies each VLAN and the 
        	trunk connection."
        INDEX   { atmxTrunkIndex, atmxTrunkVlanNumber}
        ::= { atmxTrunkVlanTable 1 }
    AtmxTrunkVlanEntry ::=  SEQUENCE {
    	atmxTrunkVlanNumber    AtmxVlanRange,
        atmxTrunkVlanIfIndex   IfIndexOrZero,
        atmxTrunkVlanRowStatus RowStatus
    }
    atmxTrunkVlanNumber OBJECT-TYPE
        SYNTAX      AtmxVlanRange
        MAX-ACCESS  not-accessible
        STATUS      current
        DESCRIPTION
			"This identifies the VLAN whose traffic is carried over the
			trunk.  The value of this object corresponds to vLanNumber
			defined in the SWITCH-VLAN-MIB module."
        ::= { atmxTrunkVlanEntry 1 }
    atmxTrunkVlanIfIndex OBJECT-TYPE
        SYNTAX      IfIndexOrZero
        MAX-ACCESS  read-only
        STATUS      current
        DESCRIPTION
			"This is the value of ifIndex of the Vlan interface."
        ::= { atmxTrunkVlanEntry 2 }
    atmxTrunkVlanRowStatus OBJECT-TYPE
        SYNTAX      RowStatus
        MAX-ACCESS  read-create
        STATUS      current
        DESCRIPTION
			"This attribute is used to create or delete an entry in the
			atmxTrunkTable. Only the values 'active', 'createAndGo', and
			'delete' are supported.  The corresponding atmTrunkRowStatus
			must have the value 'active' before this object may be
			created."
        ::= { atmxTrunkVlanEntry 3 }
    
    atmxTrunkStatsTable OBJECT-TYPE
        SYNTAX   SEQUENCE OF AtmxTrunkStatsEntry
        MAX-ACCESS   not-accessible
        STATUS        current
        DESCRIPTION
            "A table of trunk statistics."
        ::= { atmxTrunkGroup 3 }
    atmxTrunkStatsEntry   OBJECT-TYPE
        SYNTAX   AtmxTrunkStatsEntry
        MAX-ACCESS   not-accessible
        STATUS        current
        DESCRIPTION
        	"An entry in the table containg information about the 
        	trunk connection statistics."
        INDEX   { atmxTrunkIndex}
        ::= { atmxTrunkStatsTable 1 }
    AtmxTrunkStatsEntry ::=  SEQUENCE {
        atmxTrunkStatsTotalTxPkts    		INTEGER,
 	atmxTrunkStatsTotalRxPkts    		INTEGER,
 	atmxTrunkStatsTotalTxDiscards		INTEGER,
 	atmxTrunkStatsTotalRxDiscards  		INTEGER
    }
    atmxTrunkStatsTotalTxPkts OBJECT-TYPE
	 SYNTAX  INTEGER
	 MAX-ACCESS  read-only
	 STATUS  current
	 DESCRIPTION
		"Total Transmission Packets through this Connection."
	 ::= { atmxTrunkStatsEntry 1 }
    atmxTrunkStatsTotalRxPkts OBJECT-TYPE
	 SYNTAX  INTEGER
	 MAX-ACCESS  read-only
	 STATUS  current
	 DESCRIPTION
		"Total Packets Received through this Connection."
	 ::= { atmxTrunkStatsEntry 2 }
    atmxTrunkStatsTotalTxDiscards OBJECT-TYPE
	 SYNTAX  INTEGER
	 MAX-ACCESS  read-only
	 STATUS  current
	 DESCRIPTION
		"Total Transmission packets discarded by this connection."
	 ::= { atmxTrunkStatsEntry 3 }
    atmxTrunkStatsTotalRxDiscards OBJECT-TYPE
	 SYNTAX  INTEGER
	 MAX-ACCESS  read-only
	 STATUS  current
	 DESCRIPTION
		"Total Received packets discarded by this connection."
	 ::= { atmxTrunkStatsEntry 4 }
END
