XEDIA-DRIVER-MIB DEFINITIONS ::= BEGIN

IMPORTS
    MODULE-IDENTITY, OBJECT-TYPE, Counter32, Gauge32
        FROM SNMPv2-SMI
    MODULE-COMPLIANCE, OBJECT-GROUP
        FROM SNMPv2-CONF
    ifIndex 
        FROM IF-MIB
    xediaMibs
        FROM XEDIA-REG
    ;

xediaDriverMIB MODULE-IDENTITY
    LAST-UPDATED "9703252155Z" -- March 25, 1997
    ORGANIZATION "Xedia Corp."
    CONTACT-INFO
        "support@xedia.com"
    DESCRIPTION
        "This module defines proprietary objects that extend those in
        the driver type  MIBs."
    ::= { xediaMibs 6 }


-- ================================================================
-- Top-level organization of the MIB
-- ================================================================

xdriverObjects        OBJECT IDENTIFIER ::= { xediaDriverMIB 1 }
xdriverConformance    OBJECT IDENTIFIER ::= { xediaDriverMIB 2 } 

-- ================================================================
-- Object Definitions
-- ================================================================

--
-- Xedia Driver Statistics Table
--

xdriverStatsTable OBJECT-TYPE
    SYNTAX      SEQUENCE OF XdriverStatsEntry
    MAX-ACCESS  not-accessible
    STATUS      current
    DESCRIPTION
        "Xedia proprietary statistics for drivers."
    ::= { xdriverObjects 1 }

xdriverStatsEntry OBJECT-TYPE
    SYNTAX     XdriverStatsEntry 
    MAX-ACCESS  not-accessible
    STATUS      current
    DESCRIPTION
        "Xedia proprietary statistics for single driver interface."
    INDEX      { ifIndex }
    ::= { xdriverStatsTable 1 }

XdriverStatsEntry ::= SEQUENCE {
    xdriverStatsInternalQOverflows    Counter32,
    xdriverStatsOutGoodFrames         Counter32,
    xdriverStatsOutPercentGood        Gauge32,  
    xdriverStatsOutPercentBad         Gauge32, 
    xdriverStatsOutAvgFrameLen        Gauge32,
    xdriverStatsInCRCErrors           Gauge32,
    xdriverStatsInGoodFrames          Counter32, 
    xdriverStatsInNoResources         Counter32,
    xdriverStatsInPercentGood         Gauge32,  
    xdriverStatsInPercentBad          Gauge32, 
    xdriverStatsInAvgFrameLen         Gauge32 
}


xdriverStatsInternalQOverflows OBJECT-TYPE
    SYNTAX      Counter32
    MAX-ACCESS  read-only
    STATUS      current
    DESCRIPTION
        "A count of the number of times the driver software failed to
        drain the hardware's statistics queue fast enough (and
        therefore may not have incremented some statistics properly)."
    ::= { xdriverStatsEntry 1 }

xdriverStatsOutGoodFrames OBJECT-TYPE
    SYNTAX      Counter32
    MAX-ACCESS  read-only
    STATUS      current
    DESCRIPTION
        "The total number of frames that were transmitted without
        error. This is the sum of ifOutUcastPkts, ifOutMulticastPkts,
        and ifOutBroadcastPkts."
    ::= { xdriverStatsEntry 2 }

xdriverStatsOutPercentGood OBJECT-TYPE
    SYNTAX      Gauge32 (0..100)
    UNITS       "%"
    MAX-ACCESS  read-only
    STATUS      current
    DESCRIPTION
        "The percentage of the total frames that were transmitted
        without error. (This is the throughput of the interface.)"
    ::= { xdriverStatsEntry 3 }

xdriverStatsOutPercentBad OBJECT-TYPE
    SYNTAX      Gauge32 (0..100)
    UNITS       "%"
    MAX-ACCESS  read-only
    STATUS      current
    DESCRIPTION
        "The percentage of the total frames that the higher layers
        requested to be transmitted that could not be due to errors."
    ::= { xdriverStatsEntry 4 }

xdriverStatsOutAvgFrameLen OBJECT-TYPE
    SYNTAX      Gauge32
    MAX-ACCESS  read-only
    STATUS      current
    DESCRIPTION
        "The average length of the frames transmitted out this
        interface."
    ::= { xdriverStatsEntry 5 }

xdriverStatsInCRCErrors  OBJECT-TYPE
    SYNTAX      Gauge32
    MAX-ACCESS  read-only
    STATUS      current
    DESCRIPTION
        "The number of frames that had CRC errors on this interface."
    ::= { xdriverStatsEntry 6 }

xdriverStatsInGoodFrames OBJECT-TYPE
    SYNTAX      Counter32
    MAX-ACCESS  read-only
    STATUS      current
    DESCRIPTION
        "The number of frames that were received on this interface
        that did not have errors."
    ::= { xdriverStatsEntry 7 }

xdriverStatsInNoResources OBJECT-TYPE
    SYNTAX      Counter32
    MAX-ACCESS  read-only
    STATUS      current
    DESCRIPTION
        "The number of times the driver was suspended because of a
        lack of resources."
    ::= { xdriverStatsEntry 8 }
 
xdriverStatsInPercentGood OBJECT-TYPE
    SYNTAX      Gauge32 (0..100)
    UNITS       "%"
    MAX-ACCESS  read-only
    STATUS      current
    DESCRIPTION
        "The percentage of incoming frames that did not have any
        error."
    ::= { xdriverStatsEntry 9 }

xdriverStatsInPercentBad OBJECT-TYPE
    SYNTAX      Gauge32 (0..100)
    UNITS       "%"
    MAX-ACCESS  read-only
    STATUS      current
    DESCRIPTION
        "The percentage of incoming frames that had errors."
    ::= { xdriverStatsEntry 10 }

xdriverStatsInAvgFrameLen OBJECT-TYPE
    SYNTAX      Gauge32
    MAX-ACCESS  read-only
    STATUS      current
    DESCRIPTION
        "The average length of a frame received on the interface."
    ::= { xdriverStatsEntry 11 }

-- ================================================================
-- Conformance Information
-- ================================================================

xdriverCompliances    OBJECT IDENTIFIER ::= { xdriverConformance 1 }
xdriverGroups         OBJECT IDENTIFIER ::= { xdriverConformance 2 }

--
-- Compliance Statements
--

xdriverCompliance MODULE-COMPLIANCE
    STATUS      current
    DESCRIPTION
        "The compliance statement for all agents that support this
        MIB. A compliant agent implements all objects defined in this
        MIB."
    MODULE  -- this module
    MANDATORY-GROUPS {
        xdriverGroup
    }
    ::= { xdriverCompliances 1 }

--
-- Object Groups
--

xdriverGroup OBJECT-GROUP
    OBJECTS {
        xdriverStatsInternalQOverflows,
        xdriverStatsOutGoodFrames,
        xdriverStatsOutPercentGood,
        xdriverStatsOutPercentBad,
        xdriverStatsOutAvgFrameLen,
        xdriverStatsInCRCErrors,
        xdriverStatsInGoodFrames,
        xdriverStatsInNoResources,
        xdriverStatsInPercentGood,
        xdriverStatsInPercentBad,
        xdriverStatsInAvgFrameLen
    }
    STATUS      current
    DESCRIPTION
        "The set of all accessible objects in this MIB."
    ::= { xdriverGroups 1 }

END
