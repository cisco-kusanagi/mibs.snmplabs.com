GRPEXT-MIB 

   --FORCE-INCLUDE <mib.h>
   --FORCE-INCLUDE <snmpdefs.h>
   --FORCE-INCLUDE <snmpstat.h>
   --FORCE-INCLUDE "mibproto.h"
 
	DEFINITIONS ::= BEGIN

	IMPORTS
		MODULE-IDENTITY, OBJECT-TYPE, Counter32, Integer32, IpAddress
			FROM SNMPv2-SMI
		DisplayString, RowStatus
			FROM SNMPv2-TC
		grpExt
			FROM APENT-MIB;

--GRPEXT MIB

    apGrpExtMib MODULE-IDENTITY
	   LAST-UPDATED "9710092000Z" -- Thu October 9 20:00:00 EST 1997
	   ORGANIZATION "ArrowPoint Communications Inc."
	   CONTACT-INFO
	   "                      
	   Postal:               ArrowPoint Communications Inc.
				                 50 Nagog Park
				                 Acton, Massachusetts 01720
	   Tel:                   +1 978-206-3000  option 1
	   E-Mail:                support@arrowpoint.com"
       DESCRIPTION
	  "The MIB module used to describe the ArrowPoint Communications
	  content rule table"
      ::= { grpExt 1}


apGrpTable OBJECT-TYPE
	SYNTAX          SEQUENCE OF APGrpEntry
	MAX-ACCESS      not-accessible
	STATUS          current
	DESCRIPTION
		"A list of content rule entries."
	::= { grpExt 2 }

apGrpEntry OBJECT-TYPE
	SYNTAX          APGrpEntry
	MAX-ACCESS      not-accessible
	STATUS          current
	DESCRIPTION
		"A group of information to uniquely identify a content providing 
		service."
	INDEX   { apGrpName }
	--DEFAULT apjam-group apGroupRowInst, apGrpName
	--DEFAULT apjam-popup-def apGroupRowInst, Properties, local
	--DEFAULT apjam-popup-def apGroupRowInst, Delete, special, apGrpStatus
	--DEFAULT apjam-wizard	Source Group Wizard, 1, images/arrowlogo.gif, "Source Groups provide NATing for farm initiated flows."
	::= { apGrpTable 1 }

APGrpEntry ::= SEQUENCE {
		apGrpName                    DisplayString,
		apGrpIndex                   Integer32,
		apGrpIPAddress               IpAddress,
		apGrpIPProtocol              INTEGER,
		apGrpPort                    Integer32,
		apGrpEnable                  INTEGER,
		apGrpStatus                  RowStatus,
		apPortMapCrateBasePort       Integer32,
		apPortMapAvailPortsPerSfp    Integer32,
		apGrpHitCount		     Counter32,
		apGrpByteCount 		     Counter32,
		apGrpFrameCount		     Counter32,
		apGrpCurConnections	     Counter32,
		apGrpTotConnections	     Counter32,
		apGrpCurFTPControl	     Counter32,
		apGrpTotFTPControl	     Counter32
}

apGrpName OBJECT-TYPE
	SYNTAX          DisplayString (SIZE(1..31))
	MAX-ACCESS      read-create
	STATUS          current
	DESCRIPTION     
			"The name of the content providing service."
	--DEFAULT ap-display-name	Name
	--DEFAULT apjam-popup-ref apGroupRowInst, Properties
	--DEFAULT apjam-wizard-field	1, normal
	--DEFAULT ap-create-requires Yes
	--DEFAULT apjam-noedit-dlg	True
	::= {apGrpEntry 1}

apGrpIndex OBJECT-TYPE
	SYNTAX          Integer32
	MAX-ACCESS      read-only
	STATUS  		current
	DESCRIPTION     
		"The unique service index assigned to the name by the SCM."
	::= {apGrpEntry 2}

apGrpIPAddress OBJECT-TYPE
	SYNTAX          IpAddress
	MAX-ACCESS      read-create
	STATUS  		current
	DESCRIPTION     
		"The IP Address the of the content providing service."
	--DEFAULT ap-display-name	Ip Address
	--DEFAULT apjam-popup-ref apGroupRowInst, Properties
	--DEFAULT apjam-wizard-field	1, normal
	::= {apGrpEntry 3}

apGrpIPProtocol OBJECT-TYPE
	SYNTAX          INTEGER {
							tcp (6),
							udp (17)
							}
	MAX-ACCESS      read-create
	STATUS  		current
	DESCRIPTION     
		"The IP Protocol the of the content providing service."
	DEFVAL { tcp }
	::= {apGrpEntry 4}

apGrpPort OBJECT-TYPE
	SYNTAX          Integer32 (0..65535)
	MAX-ACCESS      read-create
	STATUS  		current
	DESCRIPTION     
		"The UDP or TCP port of the content providing service."
	::= {apGrpEntry 5}

apGrpEnable  OBJECT-TYPE
	SYNTAX  INTEGER {
					disable(0),
					enable(1)
 					}
	MAX-ACCESS      read-create
	STATUS 			current
	DESCRIPTION     
		"The state of the group, either enable or disabled"
	DEFVAL { disable }
	--DEFAULT ap-display-name	Status
	--DEFAULT apjam-popup-ref apGroupRowInst, Properties
	--DEFAULT apjam-wizard-field	1, normal
	::= {apGrpEntry  6}

apGrpStatus OBJECT-TYPE
	SYNTAX          RowStatus
	MAX-ACCESS      read-create
	STATUS          current
	DESCRIPTION      
		"Status entry for this row "
	::= {apGrpEntry 7}

apPortMapCrateBasePort OBJECT-TYPE
	SYNTAX          Integer32 (8192..65530)
	MAX-ACCESS      read-create
	STATUS  		current
	DESCRIPTION     
		"The base port for the entire unit when mapping ports."
	DEFVAL { 8192 }
	::= {apGrpEntry 8}

apPortMapAvailPortsPerSfp OBJECT-TYPE
	SYNTAX          Integer32 (1..10000)
	MAX-ACCESS      read-create
	STATUS  		current
	DESCRIPTION     
		"The number of ports to allow per SFP when mapping ports."
	DEFVAL { 1024 }
	::= {apGrpEntry 9}

apGrpHitCount OBJECT-TYPE
	SYNTAX          Counter32
	MAX-ACCESS      read-only
	STATUS  	current
	DESCRIPTION     
		"Number of times the group has been used."
	::= {apGrpEntry 10}

apGrpByteCount OBJECT-TYPE
	SYNTAX          Counter32
	MAX-ACCESS      read-only
	STATUS  	current
	DESCRIPTION     
		"Number of Bytes passed through the group."
	::= {apGrpEntry 11}

apGrpFrameCount OBJECT-TYPE
	SYNTAX          Counter32
	MAX-ACCESS      read-only
	STATUS  	current
	DESCRIPTION     
		"Number of frames passed through the group."
	::= {apGrpEntry 12}

apGrpCurConnections OBJECT-TYPE
	SYNTAX          Counter32
	MAX-ACCESS      read-only
	STATUS  	current
	DESCRIPTION     
		"Number of current connections through the group."
	::= {apGrpEntry 13}

apGrpTotConnections OBJECT-TYPE
	SYNTAX          Counter32
	MAX-ACCESS      read-only
	STATUS  	current
	DESCRIPTION     
		"Total number of connections through the group."
	::= {apGrpEntry 14}

apGrpCurFTPControl OBJECT-TYPE
	SYNTAX          Counter32
	MAX-ACCESS      read-only
	STATUS  	current
	DESCRIPTION     
		"Number of current FTP control connections through the group."
	::= {apGrpEntry 15}

apGrpTotFTPControl OBJECT-TYPE
	SYNTAX          Counter32
	MAX-ACCESS      read-only
	STATUS  	current
	DESCRIPTION     
		"Total number of FTP control connections through the group."
	::= {apGrpEntry 16}

END
