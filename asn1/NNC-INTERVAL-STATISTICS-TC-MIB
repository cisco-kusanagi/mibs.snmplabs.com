-------------------------------------------------------------------------------
-- file: IntervalStatisticsTC.mib 
--
-- description:
--  This file contains SNMP textual conventions common to the interval 
--  statistics collection mibs.
--
-- history:
--  31A0611 / 96.03.13 / A. Brzezinski / Creation from V1.0 of MIBTemplate.mib
--  31A0611 / 96.03.21 / A. Brzezinski / Modifications after review meeting
--
--%%history-start%%
--96.04.15 brzezins 31A0611: Changed name to conform with Newbridge 
--  standards. 
--%%history-end%%
--
-- Copyright 1996 Newbridge Networks Corporation.  All Rights Reserved
-------------------------------------------------------------------------------
NNC-INTERVAL-STATISTICS-TC-MIB DEFINITIONS ::= BEGIN

  IMPORTS
    MODULE-IDENTITY
            FROM SNMPv2-SMI
    TEXTUAL-CONVENTION 
            FROM SNMPv2-TC
    NncUnsigned32, nncExtensions
            FROM NNCGNI0001-SMI;

  nncExtIntvlStats MODULE-IDENTITY
    LAST-UPDATED   "9603211520Z"
    ORGANIZATION   "Newbridge Networks Corporation"
    CONTACT-INFO
                  "Newbridge Networks Corporation
                   Postal: 600 March Road
                         Kanata, Ontario
                         Canada K2K 2E6

                   Phone:  +1 613 591 3600
                   Fax:    +1 613 591 3680"
    
   DESCRIPTION
     "The MIB module containing type definitions common to
      interval statistics collection mibs."
  
  ::= { nncExtensions 31 }


--------------------------------------------------------------------------------
-- Type Definitions
--------------------------------------------------------------------------------

  NncExtIntvlStateType ::= TEXTUAL-CONVENTION
    STATUS    current
    DESCRIPTION
      "The type describing the state of the interval in the 
       interval statistics interface.
       Possible states are:
         normal      (1) - normal interval; no change in time and no resets
         nonexistent (2) - statistics do not exist for this interval
         userReset   (3) - the user has reset statistics collection 
                           during this interval
         start       (4) - this is the first interval
         timeChange  (5) - the system time has been changed during this
                           interval"
    SYNTAX INTEGER {
      normal      (1),
      nonexistent (2),
      userReset   (3),
      start       (4),
      timeChange  (5)
    }

  NncExtAbsIntvlNumberType ::= TEXTUAL-CONVENTION
    STATUS    current
    DESCRIPTION
      "The type describing the absolute interval number of the 
       stats interval in the interval statistics interface.

       For the short, 15 minutes intervals the possible values are:

         absolute interval           interval 
              index                start    end
         -----------------         ------------
                 1                 00:00  00:15
                 2                 00:15  00:30
                 3                 00:30  00:45
                ...                 ...    ...

                95                 23:30  23:45
                96                 23:45  00:00

      For the long, 1 hour intervals the possible values are:

         absolute interval           interval 
              index                start    end
         -----------------         ------------
                 1                 00:00  01:00
                 2                 01:00  02:00
                 3                 02:00  03:00
                ...                 ...    ...

                23                 22:00  23:00
                24                 23:00  24:00

      For other interval types or interval durations absolute
      interval index in not defined."
    SYNTAX    NncUnsigned32

  NncExtRelIntvlNumberType ::= TEXTUAL-CONVENTION
    STATUS    current
    DESCRIPTION
      "The type describing the relative interval number of the
       statistics interval in the interval statistics interface.
       The values are from 1 to N, where 1 represents the most
       recently completed interval, 2 represents the second
       most recently completed interval, etc., and N is the total
       number of previous intervals supported."
    SYNTAX    NncUnsigned32

  NncExtIntvlDurationType ::= TEXTUAL-CONVENTION
    STATUS    current
    DESCRIPTION
      "The type describing the duration of the statistics interval
       in the interval statistics interface. The value represents
       the number of seconds that have elapsed since the beginning
       of the interval." 
    SYNTAX    NncUnsigned32


-------------------------------------------------------------------------------
--  Review Minutes 
-------------------------------------------------------------------------------
-- MINUTES-BEGIN
-- REVIEW-DATE  "1996.03.19"
-- BODY  "
--
--
-- TO:  Jonathan Bosloy*, Nelson Gillette, Randy Jones*, Steve Buchko*, 
--  Andrew Paterson*, David Watkinson*, Frank Chen*
-- CC:  Numbers Admin, Melanie Paquette, Wing-Leung Chan, Sriram Darbha
-- FROM:  Art Brzezinski*
--
-- A meeting was held on 1996.03.19 to review NNCEXTINTVLSTATS.mib.
-- Attendees are marked with * in the TO and CC lists above.
--
-- Outcome
--
-- It was the consensus of the review team that this file is acceptable 
-- with the indicated modifications.
--
-- Actions:
--  A1 -   Art Brzezinski to update the file as indicated in D1 below.  
--  Response:                          Status: CLOSED
--         All changes has been made as indicated in D1 below.
--
--  A2 -   Randy Jones to supervise modifications of ATMStatistics.mib
--         to make use of the textual-conventions defined in the mib file.
--  Response:                          Status: CLOSED
--         ATMStatistics.mib has been changed to make use of the textual-
--         conventions defined in this mib file.
--
--  A3 -   Art Brzezinski to notify Chris Gibson of the existence of the mib 
--         file with textual conventions for interval statistics mib.
--  Response:                          Status: CLOSED
--         Chris Gibson has been notified of this mib file existance.
--
--  A4 -   Art Brzezinski to check rfc1903 for textual convention 
--         that could be used for the interval start time.
--  Response:                          Status: CLOSED
--         DateAndTime textual convention defined in rfc1903 will 
--         be used as the interval start time type in interval
--         statistics SNMP mibs. Previously defined here type
--         NncExtIntvlStartTimeType is no longer needed and has
--         been removed.
--
--  A5 -   Art Brzezinski to check rfc1595 for textual convention of
--         interval duration time.
--  Response:                          Status: CLOSED
--         rfc1595 does not define textual convention usable for the
--         purpose of the interval duration time. However the 
--         descirption of sonetMediumTimeElapsed object found in 
--         rfc1595 will be used to clarify meaning of defined here
--         NncExtIntvlDurationType type.
--
--  A6 -   Art Brzezinski to update stats interface as indicated in D2 below.
--  Response:                          Status: CLOSED
--         Stats interface has been modified as indicated in D2 below.
--         
--
-- Decisions:
--  D1 -   NNCEXTINTVLSTATS.mib shall be updated as follows:
--   a) rename file to IntvlStatsTC.mib 
--   b) rename module to NNCEXTINTVLSTATS-TC
--   c) add prefix 'NncExt' to all type names
--   d) modify description of absolute interval type such that
--      the first interval index is 1 not 0
--   e) enhance description of the interval duration type
--   f) add units info (seconds) to the interval duration type description
--   g) create textual convention for the relative interval index and
--      provide a detailed description - explain that 1 means previous
--      interval, etc.
--   h) correct error in the comment at the end of the file
--
--  D2 -   Stats interface interval state type shall be changed to avoid the
--   use of a zero value.
--
--  "
--
-- END-MINUTES
--

END -- DEFINITION OF NNCEXTINTVLSTATS-TC
