-->#
--># Copyright (C) Siemens AG 1999
-->#               All rights reserved
-->#
-->#protocol specification
-->%PROTOCOL SNMP
-->#
-->#configuration
-->%REMCONFIG NO
-->%REMOPERATION NO
-->#
 
Subagent-Supervision-MIB DEFINITIONS ::= BEGIN
 
--
-- Title:   MIB for supervision of the subagents of the BS2000 SNMP agent
-- Date:    October 1997
-- Author:  Stefan Reisch        OEC BS2 DC3
--
 
 
IMPORTS
	TRAP-TYPE FROM RFC-1215
        enterprises
            FROM RFC1155-SMI
        DisplayString
            FROM RFC1213-MIB
        OBJECT-TYPE
            FROM RFC-1212;
 
 
sni                        OBJECT IDENTIFIER ::= { enterprises 231 }
sniProductMibs             OBJECT IDENTIFIER ::= { sni 2 }
sniSupervisor              OBJECT IDENTIFIER ::= { sniProductMibs 34 }
 
--
-- Definition of Objects
--
 
superVisObjects            OBJECT IDENTIFIER ::= { sniSupervisor 1 }
superVisGlobalDatas        OBJECT IDENTIFIER ::= { superVisObjects 1 }
superVisSubagents          OBJECT IDENTIFIER ::= { superVisObjects 2 }
superVisTrpAck             OBJECT IDENTIFIER ::= { superVisObjects 3 }
 
superVisVersion OBJECT-TYPE
    SYNTAX  DisplayString
    ACCESS  read-only
    STATUS  mandatory
    DESCRIPTION "version of supervisor subagent"
    ::= { superVisGlobalDatas 1}
 
superVisActiveNumber OBJECT-TYPE
    SYNTAX  INTEGER
    ACCESS  read-only
    STATUS  mandatory
    DESCRIPTION
           "number of active subagents"
    ::= { superVisGlobalDatas 2 }
 
superVisMaxSubagentNumber OBJECT-TYPE
    SYNTAX  INTEGER
    ACCESS  read-only
    STATUS  mandatory
    DESCRIPTION
           "maximal Number of subagents"
    ::= { superVisGlobalDatas 3 }
 
superVisObjectNumber OBJECT-TYPE
    SYNTAX  INTEGER
    ACCESS  read-only
    STATUS  mandatory
    DESCRIPTION
           "Number of objects currently supported by the BS2000 SNMP agent"
    ::= { superVisGlobalDatas 4 }
 
superVisTrapAckId OBJECT-TYPE
    SYNTAX  INTEGER
    ACCESS  read-write
    STATUS  mandatory
    DESCRIPTION
           "Id of last trap to be acknowledged by manager.
            Setting this object with its current value
            means acknowlegement of the last trap"
    ::= { superVisGlobalDatas 5 }
 
superVisSubagentNumber OBJECT-TYPE
    SYNTAX  INTEGER
    ACCESS  read-only
    STATUS  mandatory
    DESCRIPTION
           "Number of entries in subagent table"
    ::= { superVisSubagents 1 }
 
superVisSubagentTable OBJECT-TYPE
    SYNTAX  SEQUENCE OF SuperVisSubagentEntry
    ACCESS  not-accessible
    STATUS  mandatory
    DESCRIPTION
           "The table of subagents"
    ::= { superVisSubagents 2 }
 
superVisSubagentEntry OBJECT-TYPE
    SYNTAX  SuperVisSubagentEntry
    ACCESS  not-accessible
    STATUS  mandatory
    DESCRIPTION
           "entry for each subagent"
    INDEX   { superVisSubagentName }
    ::= { superVisSubagentTable 1 }
 
SuperVisSubagentEntry ::=
    SEQUENCE {
        superVisSubagentName
        DisplayString,
        superVisSubagentSID
        INTEGER,
--      superVisSubagentVersion
--      DisplayString,
        superVisSubagentStatus
        INTEGER,
        superVisSubagentConnTime
--      DateAndTime,
        DisplayString,
        superVisSubagentDisconnTime
--      DateAndTime,
        DisplayString,
        superVisSubagentLastResponseTime
--      DateAndTime,
        DisplayString,
        superVisSubagentRequestsDone
        INTEGER,
        superVisSubagentTrapsSent
        INTEGER,
        superVisSubagentOID
        OBJECT IDENTIFIER,
        superVisSubagentProcessID
        INTEGER,
        superVisSubagentUserId
        DisplayString,
        superVisSubagentCpuTime
        INTEGER,
        superVisSubagentCommand
        DisplayString
    }
 
-- superVisSubagentVersion    OBJECT-TYPE
 
superVisSubagentName    OBJECT-TYPE
        SYNTAX  DisplayString
        ACCESS  read-only
        STATUS  mandatory
        DESCRIPTION "Name of the subagent (for BS2000-Subagents only)"
        ::= { superVisSubagentEntry 1 }
 
superVisSubagentSID      OBJECT-TYPE
        SYNTAX  INTEGER
        ACCESS  read-only
        STATUS  mandatory
        DESCRIPTION "SID of subagents: Index used by master agent
                     for the management of the subagent. "
        ::= { superVisSubagentEntry 2 }
 
-- superVisSubagentVersion    OBJECT-TYPE
--         SYNTAX   DisplayString
--         ACCESS  read-only
--         STATUS  mandatory
--         DESCRIPTION "Version of the subagent"
--         ::= { superVisSubagentEntry 3 }
--
 
superVisSubagentStatus     OBJECT-TYPE
        SYNTAX   INTEGER {
        active(1),
        disconnected(2),
        undefined(3)
        }
        ACCESS  read-only
        STATUS  mandatory
        DESCRIPTION
           "Status of subagent:
            active:       the subagent is connected and works normally
            disconnected: the subagent has sent a disconnect event
                          it is no longer available.
            undefined:    no answer from the subagent has been received
                          since an request has been sent after X minutes.
                          There was no disconnect event sent by this
                          subagent."
        ::= { superVisSubagentEntry 4 }
 
superVisSubagentConnTime     OBJECT-TYPE
--      SYNTAX  DateAndTime
        SYNTAX  DisplayString
        ACCESS  read-only
        STATUS  mandatory
        DESCRIPTION "Time when subagent connected"
        ::= { superVisSubagentEntry 5 }
 
superVisSubagentDisconnTime     OBJECT-TYPE
--      SYNTAX  DateAndTime
        SYNTAX  DisplayString
        ACCESS  read-only
        STATUS  mandatory
        DESCRIPTION "Time when subagent disconnected"
        ::= { superVisSubagentEntry 6 }
 
superVisSubagentLastResponseTime     OBJECT-TYPE
--      SYNTAX  DateAndTime
        SYNTAX  DisplayString
        ACCESS  read-only
        STATUS  mandatory
        DESCRIPTION "Time when subagent has answered at last"
        ::= { superVisSubagentEntry 7 }
 
superVisSubagentRequestsDone    OBJECT-TYPE
        SYNTAX  INTEGER
        ACCESS  read-only
        STATUS  mandatory
        DESCRIPTION "Number of requests done by the subagent"
    ::= { superVisSubagentEntry 8 }
 
superVisSubagentTrapsSent    OBJECT-TYPE
        SYNTAX  INTEGER
        ACCESS  read-only
        STATUS  mandatory
        DESCRIPTION "Number of traps caused by the subagent"
    ::= { superVisSubagentEntry 9 }
 
superVisSubagentOID        OBJECT-TYPE
        SYNTAX   OBJECT IDENTIFIER
        ACCESS  read-only
        STATUS  mandatory
        DESCRIPTION "first objectidentifier supported by the subagent"
        ::= { superVisSubagentEntry 10 }
 
superVisSubagentProcessID       OBJECT-TYPE
        SYNTAX  INTEGER
        ACCESS  read-only
        STATUS  mandatory
        DESCRIPTION "process identifier of the subagent"
    ::= { superVisSubagentEntry 11 }
 
superVisSubagentUserId       OBJECT-TYPE
        SYNTAX  DisplayString
        ACCESS  read-only
        STATUS  mandatory
        DESCRIPTION "Userid belonging to the process identifier"
    ::= { superVisSubagentEntry 12 }
 
superVisSubagentCpuTime         OBJECT-TYPE
        SYNTAX  INTEGER
        ACCESS  read-only
        STATUS  mandatory
        DESCRIPTION "CPU Time used by the subagent"
    ::= { superVisSubagentEntry 13 }
 
superVisSubagentCommand      OBJECT-TYPE
        SYNTAX  DisplayString
        ACCESS  read-only
        STATUS  mandatory
        DESCRIPTION "Command string found in the output of ps-command
                     belonging to the process identifier"
    ::= { superVisSubagentEntry 14 }
 

superVisTrpAckState OBJECT-TYPE
    SYNTAX   INTEGER {
       active(1),
       inactiv(2),
       undefined(3)
       }
    ACCESS  read-write
    STATUS  mandatory
    DESCRIPTION
	   "State of global Trap-Ack"
    ::= { superVisTrpAck 1 }

superVisTrpAckId OBJECT-TYPE
    SYNTAX  INTEGER
    ACCESS  read-write
    STATUS  mandatory
    DESCRIPTION
           "Id of last trap to be acknowledged by manager.
            Setting this object with its current value
            means acknowlegement of the last trap"
    ::= { superVisTrpAck 2 }

superVisTrpAckQueueCnt OBJECT-TYPE
    SYNTAX  INTEGER
    ACCESS  read-write
    STATUS  mandatory
    DESCRIPTION
	   "Number of currently queued traps
	    Setting this object means dequeue traps
	    except the given number"
    ::= { superVisTrpAck 3 }

--
-- Definition of Traps
--
 
superVisTraps              OBJECT IDENTIFIER ::= { sniSupervisor 2 }
 
superVisSubAgentConnected TRAP-TYPE
    ENTERPRISE  superVisTraps
    VARIABLES   { superVisSubagentName }
    DESCRIPTION
           "An superVisSubAgentStart trap signifies that subagent has
            connected."
    ::= 301
 
superVisSubAgentDisconnected TRAP-TYPE
    ENTERPRISE  superVisTraps
    VARIABLES   { superVisSubagentName }
    DESCRIPTION
           "An superVisSubAgentStart trap signifies that master agent has
            disconnected."
    ::= 302
 
superVisSubAgentNoAnswer TRAP-TYPE
   ENTERPRISE  superVisTraps
    VARIABLES   { superVisSubagentName }
   DESCRIPTION
          "An superVisSubAgentStart trap signifies that subagent has
           not answered to a request for X minutes."
    ::= 303
 
END
