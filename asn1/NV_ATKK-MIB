----	  $Header: nv_atkk.mib,v 1.1 96/06/11 21:50:24 staki Exp $
----      Header:   L:/VCS/RIVA_SRC/EPILOG/EMISSARY/MIBS/NV_ATKK.MIv   1.0
----                15 May 1996 13:02:40   OHY  

	  NV_ATKK-MIB DEFINITIONS ::= BEGIN

	  IMPORTS
		     Counter, TimeTicks, NetworkAddress
			     FROM RFC1155-SMI
		     mib-2
			     FROM RFC1213-MIB
		     OBJECT-TYPE
			     FROM RFC-1212
		     TRAP-TYPE
			     FROM RFC-1215;

	  -- All representations of MAC addresses in this MIB Module
	  -- use, as a textual convention (i.e. this convention does
	  -- not affect their encoding), the data type:

	  MacAddress ::= OCTET STRING (SIZE (6))    -- a 6 octet address
						    -- in the
						    -- "canonical"
						    -- order
	  -- defined by IEEE 802.1a, i.e., as if it were transmitted
	  -- least significant bit first, even though 802.5 (in
	  -- contrast to other n802.x protocols) requires MAC
	  -- addresses to be transmitted most significant bit first.
	  --
	  -- 16-bit addresses, if needed, are represented by setting
	  -- their upper 4 octets to all 0's, i.e., AAFF would be
	  -- represented as 00000000AAFF.


	  -- Similarly, all representations of Bridge-Id in this MIB
	  -- Module use, as a textual convention (i.e. this
	  -- convention does not affect their encoding), the data
	  -- type:

	  BridgeId ::= OCTET STRING (SIZE (8))   -- the
						 -- Bridge-Identifier
						 -- as used in the
						 -- Spanning Tree
	  -- Protocol to uniquely identify a bridge.  Its first two
	  -- octets (in network byte order) contain a priority
	  -- value and its last 6 octets contain the MAC address
	  -- used to refer to a bridge in a unique fashion
	  -- (typically, the numerically smallest MAC address
	  -- of all ports on the bridge).


	  -- Several objects in this MIB module represent values of
	  -- timers used by the Spanning Tree Protocol.  In this
	  -- MIB, these timers have values in units of hundreths of
	  -- a second (i.e. 1/100 secs).
	  -- These timers, when stored in a Spanning Tree Protocol's
	  -- BPDU, are in units of 1/256 seconds.  Note, however,
	  -- that 802.1D-1990 specifies a settable granularity of
	  -- no more than 1 second for these timers.  To avoid
	  -- ambiguity, a data type is defined here as a textual
	  -- convention and all representation of these timers
	  -- in this MIB module are defined using this data type.  An
	  -- algorithm is also defined for converting between the
	  -- different units, to ensure a timer's value is not
	  -- distorted by multiple conversions.
	  -- The data type is:

	  Timeout ::= INTEGER -- a STP timer in units of 1/100 seconds

	  -- To convert a Timeout value into a value in units of
	  -- 1/256 seconds, the following algorithm should be used:
	  --
	  --      b  = floor( (n * 256) / 100)
	  --
	  -- where:
	  --      floor   =  quotient [ignore remainder]
	  --      n is the value in 1/100 second units
	  --      b is the value in 1/256 second units
	  --
	  -- To convert the value from 1/256 second units back to
	  -- 1/100 seconds, the following algorithm should be used:
	  --
	  --      n = ceiling( (b * 100) / 256)
	  --
	  -- where:
	  --      ceiling =  quotient [if remainder is 0], or
	  --                 quotient + 1 [if remainder is non-zero]
	  --      n is the value in 1/100 second units
	  --      b is the value in 1/256 second units
	  --
	  -- Note: it is important that the arithmetic operations are
	  -- done in the order specified (i.e., multiply first, divide
	  -- second).

	  C3716TR OBJECT IDENTIFIER ::= { enterprises ati(207) mibobjs(8) 3 }

	  atiSystemConfig  OBJECT IDENTIFIER ::= { C3716TR 1 }
--	  atiPortTable  OBJECT IDENTIFIER ::= { C3716TR 2 }
	  atiSwitch  OBJECT IDENTIFIER ::= { C3716TR 3 }

	  atiSystemConfigInfo ::=
	      SEQUENCE {
	          atiSysSerialno         DisplayString,
	          atiSysTftpIPAddress    NetworkAddress,
	          atiSysTftpFilename     DisplayString,
	          atiSysPowerupCount     INTEGER,
	          atiSysBrcastCutoffRate INTEGER,
	          atiSysGatewayIPAddress NetworkAddress
              }

	-- atiSystemConfig stuff

	  atiSysSerialno OBJECT-TYPE
	      SYNTAX  DisplayString (SIZE (0..255))
	      ACCESS  read-only
	      STATUS  mandatory
	      DESCRIPTION
		      "Serial number."
	      ::= { atiSystemConfig 1 }

	  atiSysTftpIPAddress OBJECT-TYPE
	      SYNTAX  NetworkAddress
	      ACCESS  read-write
	      STATUS mandatory
	      DESCRIPTION
		     "TFTP Server IP address."  
	      ::= { atiSystemConfig 2 }

	  atiSysTftpFilename OBJECT-TYPE
	      SYNTAX  DisplayString (SIZE (0..255))
	      ACCESS  read-write
	      STATUS  mandatory
	      DESCRIPTION
		      "TFTP file name."
	      ::= { atiSystemConfig 3 }

	  atiSysPowerupCount OBJECT-TYPE
	      SYNTAX  INTEGER
	      ACCESS  read-only
	      STATUS  mandatory
	      DESCRIPTION
		      "Powerup Count."
	      ::= { atiSystemConfig 4 }

	  atiSysBrcastCutoffRate OBJECT-TYPE
	      SYNTAX  INTEGER
	      ACCESS  read-write
	      STATUS  mandatory
	      DESCRIPTION
		      "Broadcast Cutoff Rate. (0..100000)"
	      ::= { atiSystemConfig 5 }

	  atiSysGatewayIPAddress OBJECT-TYPE
	      SYNTAX NetworkAddress
	      ACCESS read-write
	      STATUS mandatory
	      DESCRIPTION
		     "Gateway IP address."      
	      ::= { atiSystemConfig 6 }


	  -- ati port table - indexed by port

	  atiPortTable OBJECT-TYPE
	      SYNTAX  SEQUENCE OF atiPortentry
	      ACCESS  not-accessible
	      STATUS  mandatory
	      DESCRIPTION
		      "The port setup table."
	      ::= { C3716TR 2 }

	  atiPortEntry OBJECT-TYPE
	      SYNTAX  atiPortentry
	      ACCESS  not-accessible
	      STATUS  mandatory
	      DESCRIPTION
		      "The port setup entry."
	      INDEX   { atiPort }
	      ::= { atiPortTable 1 }

	  atiPortentry ::=
	      SEQUENCE {
		  atiPort
		      INTEGER,
		  atiPortStatus
		      INTEGER,
		  atiPortDuplexStatus
		      INTEGER,		
		  atiPortForwardedFrames
		      Counter,		
		  atiPortRcvdLocalFrames
		      Counter
		  }

	  atiPort OBJECT-TYPE
	      SYNTAX  INTEGER
	      ACCESS  read-only
	      STATUS  mandatory
	      DESCRIPTION
		      "A number from 1 to number of ports on the switch."
	      ::= { atiPortEntry 1 }

	  atiPortStatus OBJECT-TYPE
	      SYNTAX  INTEGER{
                UP (1),
                DOWN (2)
		}
	      ACCESS  read-only
	      STATUS  mandatory
	      DESCRIPTION
		      "Port status."
	      ::= { atiPortEntry 2 }

	  atiPortDuplexStatus OBJECT-TYPE
	      SYNTAX  INTEGER{
                HALF (1),
                FULL (2)
		}
	      ACCESS  read-only
	      STATUS  mandatory
	      DESCRIPTION
		      "Port duplex status."
	      ::= { atiPortEntry 3 }

	  atiPortForwardedFrames OBJECT-TYPE
	      SYNTAX  Counter
	      ACCESS  read-only
	      STATUS  mandatory
	      DESCRIPTION
		      "Number of frames received on this port and forwarded to another port on the system module for processing."
	      ::= { atiPortEntry 4 }

	  atiPortRcvdLocalFrames OBJECT-TYPE
	      SYNTAX  Counter
	      ACCESS  read-only
	      STATUS  mandatory
	      DESCRIPTION
		      "Number of frames received where the destination is on this port."
	      ::= { atiPortEntry 5 }

	-- atiSwitch stuff

	  atiSwitchIPAddress OBJECT-TYPE
	      SYNTAX NetworkAddress
	      ACCESS read-write
	      STATUS mandatory
	      DESCRIPTION
		     "Since bridges can now be accessed without an IP address,
		     there needs to be a way to find out there addresses."
	      ::= { atiSwitch 1 }

	  atiSwitchSubnetMask OBJECT-TYPE
	      SYNTAX NetworkAddress
	      ACCESS read-write
	      STATUS mandatory
	      DESCRIPTION
		     "The switch's submask."
	      ::= { atiSwitch 2 }

	  atiActiveAgingTime OBJECT-TYPE
	      SYNTAX  INTEGER
	      ACCESS  read-write
	      STATUS  mandatory
	      DESCRIPTION
		      "Active Aging Time."
	      ::= { atiSwitch 3 }

	  atiPurgeAgingTime OBJECT-TYPE
	      SYNTAX  INTEGER
	      ACCESS  read-write
	      STATUS  mandatory
	      DESCRIPTION
		      "Purge Aging Time."
	      ::= { atiSwitch 4 }

	  atiSwitchSTPStatus OBJECT-TYPE
	      SYNTAX  INTEGER{
                ON (1),
                OFF (2)
		}
	      ACCESS  read-write
	      STATUS  mandatory
	      DESCRIPTION
		      "The switch's Spanning Tree status, enter ON or OFF."
	      ::= { atiSwitch 5 }

	  atiSwitchManagerInfo ::=
	      SEQUENCE {
	         atiSwitcTrapRcvr1      NetworkAddress,
	         atiSwitcTrapRcvr2      NetworkAddress,
	         atiSwitcTrapRcvr3      NetworkAddress,
	         atiSwitcTrapRcvr4      NetworkAddress
             }

	  atiSwitchManager OBJECT-TYPE
	      SYNTAX NetworkAddress
	      ACCESS read-write
	      STATUS mandatory
	      DESCRIPTION
		     "The 1th SNMP Trap Destination."
	      ::= { atiSwitch 6 }

	  atiSwitcTrapRcvr1 OBJECT-TYPE
	      SYNTAX NetworkAddress
	      ACCESS read-write
	      STATUS mandatory
	      DESCRIPTION
		     "The 1th SNMP Trap Destination."
	      ::= { atiSwitchManager 1 }

	  atiSwitcTrapRcvr2 OBJECT-TYPE
	      SYNTAX NetworkAddress
	      ACCESS read-write
	      STATUS mandatory
	      DESCRIPTION
		     "The 2th SNMP Trap Destination."
	      ::= { atiSwitchManager 2 }

	  atiSwitcTrapRcvr3 OBJECT-TYPE
	      SYNTAX NetworkAddress
	      ACCESS read-write
	      STATUS mandatory
	      DESCRIPTION
		     "The 3th SNMP Trap Destination."
	      ::= { atiSwitchManager 3 }

	  atiSwitcTrapRcvr4 OBJECT-TYPE
	      SYNTAX NetworkAddress
	      ACCESS read-write
	      STATUS mandatory
	      DESCRIPTION
		     "The 4th SNMP Trap Destination."
	      ::= { atiSwitchManager 4 }

	  END
