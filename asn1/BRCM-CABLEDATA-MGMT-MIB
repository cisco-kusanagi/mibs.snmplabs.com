--**************************************************************************
--                                                                          
--    Copyright 2003 Broadcom Corporation                                   
--    All Rights Reserved                                                   
--    No portions of this material may be reproduced in any form without the
--    written permission of:                                                
--             Broadcom Corporation                                         
--             16251 Laguna Canyon Road                                     
--             Irvine, California  92618                                    
--    All information contained in this document is Broadcom Corporation    
--    company private, proprietary, and trade secret.                       
--                                                                          
--                                                                          
--                                                                          
--**************************************************************************
--    Filename: brcm-cabledata-mgmt.mib
--    Author:   Kevin O'Neal
--    Creation Date: 3-march-2002
--
--**************************************************************************
--    Description:
--
--		private MIB for cableData products
--		
--**************************************************************************
--    Revision History:
--
--**************************************************************************

BRCM-CABLEDATA-MGMT-MIB DEFINITIONS ::= BEGIN

IMPORTS
    MODULE-IDENTITY,
    OBJECT-TYPE
        FROM SNMPv2-SMI
    cableDataMgmt
        FROM BRCM-CABLEDATA-SMI;
                
cableDataMgmtMIB MODULE-IDENTITY
    LAST-UPDATED "200206040000Z"
    ORGANIZATION "Broadcom Corporation"
    CONTACT-INFO
        "	BANANA-CABLEDATA
                (cableData branch of the
                Broadcom Assigned Numbers and Naming Authority)
                Broadcom Corporation

        Postal: 4385 River Green Parkway
                Duluth, GA  30096
                USA

           Tel: +1 770 232-0018

        E-mail: banana-cabledata@broadcom.com"
    DESCRIPTION
        "Broadcom cabledata management MIB"
    REVISION      "200206040000Z"
    DESCRIPTION
            "Initial version of this MIB module."
    ::= { cableDataMgmt 2 }
        
cableDataMgmtMIBObjects OBJECT IDENTIFIER ::= { cableDataMgmtMIB 1}

--
-- The cableDataMgmtMIBObjects branch will follow the same model as the
-- cableDataFactory branch.  In general we'll try to keep these synced
-- up just for consistency.  Branches are indicated below as comments,
-- see specific MIBs as indicated.  Some of these branches may not have 
-- been created yet.
--

cableDataMgmtBase OBJECT IDENTIFIER ::= { cableDataMgmtMIBObjects 1 }

-- BRCM-CM-MGMT-MIB
-- cablemodemMgmt OBJECT IDENTIFIER ::= { cableDataMgmtMIBObjects 2 }

-- BRCM-CABLEHOME-MGMT-MIB
-- cableHomeMgmt OBJECT IDENTIFIER ::= { cableDataMgmtMIBObjects 3 }

-- BRCM-V2-MGMT-MIB
-- v2Mgmt OBJECT IDENTIFIER ::= { cableDataMgmtMIBObjects 4 }

-- BRCM-80211-MGMT-MIB
-- ieee802dot11Mgmt OBJECT IDENTIFIER ::= { cableDataMgmtMIBObjects 5 }

-- BRCM-EMTA-MGMT-MIB
-- emtaMgmt OBJECT IDENTIFIER ::= { cableDataMgmtMIBObjects 6 }

-- BRCM-RG-MGMT-MIB
-- residentialGatewayMgmt OBJECT IDENTIFIER ::= { cableDataMgmtMIBObjects 7 }

-- This node is provided for vendor extensions to this MIB.
-- Each vendor may request any objects under a node which is located at
-- cableDataFactoryVendor.vendorEnterpriseNumber.
cableDataMgmtVendor OBJECT IDENTIFIER ::= { cableDataMgmt 99 }

-- Broadcom vendor node.  This may seem peculiar but in fact is actually
-- used for objects associated with the Broadcom generic vendor extension.
broadcomCableDataMgmt OBJECT IDENTIFIER ::= { cableDataMgmtVendor 4413 }
        
END
