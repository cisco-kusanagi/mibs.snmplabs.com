Cisco90Series-MIB DEFINITIONS ::= BEGIN

   IMPORTS
      enterprises, Counter, TimeTicks
         FROM RFC1155-SMI
      OBJECT-TYPE
         FROM RFC-1212
      TRAP-TYPE
         FROM RFC-1215;

      -- From RFC1213-MIB (MIB-II)
      DisplayString ::=
         OCTET STRING

    ciscoTelesend     OBJECT IDENTIFIER ::= { enterprises 1570 }
    frMux        OBJECT IDENTIFIER ::= { ciscoTelesend 1 }

 -- Frame Relay Multiplexer MIB groups
 -- system group
   frxSys        OBJECT IDENTIFIER ::= { frMux 1 }

 -- defaults group
   frxDefault    OBJECT IDENTIFIER ::= { frMux 2 }

 -- bank group
   frxBank       OBJECT IDENTIFIER ::= { frMux 3 }

 -- channel unit group
   frxChUnit     OBJECT IDENTIFIER ::= { frMux 4 }

 -- channel unit management group
   frxMgt        OBJECT IDENTIFIER ::= { frMux 5 }

 -- port group
   frxPort       OBJECT IDENTIFIER ::= { frMux 6 }

 -- frxSys group
   frxSysDescr OBJECT-TYPE
      SYNTAX  DisplayString (SIZE (0..255))
      ACCESS  read-only
      STATUS  mandatory
      DESCRIPTION
         "Description of the Cisco 90 Series System."
     ::= { frxSys 1 }

   frxClockHour OBJECT-TYPE
      SYNTAX  INTEGER   (0..23)
      ACCESS  read-write
      STATUS  mandatory
      DESCRIPTION
         "Synchronized 24 hour clock for the Cisco 90 Series system -
         Hour.  This clock is used by the channel units
         and BRITE cards to set the performance monitoring
         end-of-hour and end-of-day intervals."
      ::= { frxSys 2 }

   frxClockMin OBJECT-TYPE
      SYNTAX  INTEGER   (0..59)
      ACCESS  read-write
      STATUS  mandatory
      DESCRIPTION
         "Synchronized 24 hour clock for the Cisco 90 Series system -
         Minutes. This clock is used by the channel units
         and BRITE cards to set the performance monitoring
         end-of-hour and end-of-day intervals."
      ::= { frxSys 3 }

   frxClockSec OBJECT-TYPE
      SYNTAX  INTEGER   (0..59)
      ACCESS  read-write
      STATUS  mandatory
      DESCRIPTION
         "Synchronized 24 hour clock for the Cisco 90 Series system -
         Seconds. This clock is used by the channel units
         and BRITE cards to set the performance monitoring
         end-of-hour and end-of-day intervals."
     ::= { frxSys 4 }

   frxUpTime OBJECT-TYPE
      SYNTAX  TimeTicks
      ACCESS  read-only
      STATUS  mandatory
      DESCRIPTION
         "Time since the agent was last initialized in
         0.01 second increments."
     ::= { frxSys 5 }

   frxAdminContact OBJECT-TYPE
      SYNTAX  DisplayString (SIZE (0..255))
      ACCESS  read-write
      STATUS  mandatory
      DESCRIPTION
         "Cisco 90 Series administrative contact name."
      ::= { frxSys 6 }

   frxSysName OBJECT-TYPE
      SYNTAX  DisplayString (SIZE (0..255))
      ACCESS  read-write
      STATUS  mandatory
      DESCRIPTION
         "Administratively assigned name for this Cisco 90 Series agent."
     ::= { frxSys 7 }

   frxSysLoc OBJECT-TYPE
      SYNTAX  DisplayString (SIZE (0..255))
      ACCESS  read-write
      STATUS  mandatory
      DESCRIPTION
         "Physical location of the Cisco 90 Series agent."
      ::= { frxSys 8 }

   frxSysVersion OBJECT-TYPE
      SYNTAX  INTEGER (0..65535)
      ACCESS  read-only
      STATUS  mandatory
      DESCRIPTION
         "Cisco 90 Series Agent version number. The version number is
         an INTEGER representation of the actual version number string.
         The way to translate to a version number string is 200 = 2.0.0,
         201 = 2.0.1, etc."
     ::= { frxSys 9 }

   frxUPerfTrapEnable OBJECT-TYPE
      SYNTAX  INTEGER {
         enableUPerfTrap(1),
         disableUPerfTrap(2)
         }
      ACCESS  read-write
      STATUS  mandatory
      DESCRIPTION
         "1=Enable sending the frxUPerfTrap trap to the
         SNMP manager when  a performance monitoring
         threshold is crossed at an Cisco 90 Series channel unit or
         a downstream BRITE card.
         2=Disable Trap."
      ::= { frxSys 10 }

   frxAgtLinkErrors OBJECT-TYPE
      SYNTAX  Counter
      ACCESS  read-only
      STATUS  mandatory
      DESCRIPTION
         "Number of Annex-D signaling link reliability errors
         between the Cisco 90 Series Agent and the Frame Relay Switch.
         A signaling reliability error is declared whenever
         the Cisco 90 Series Agent did not receive a reply from the
         frame relay switch in response to an Annex-D link
         integrity poll or full status inquiry poll"
      ::= { frxSys 11 }

   frxAgtProtErrors OBJECT-TYPE
      SYNTAX  Counter
      ACCESS  read-only
      STATUS  mandatory
      DESCRIPTION
         "Number of Annex-D signaling protocol errors
         between the Cisco 90 Series Agent and the Frame
         Relay Switch. A signaling protocol error is
         declared whenever the Cisco 90 Series Agent
         receives a reply with incorrect format or
         sequence numbers from the frame relay switch in
         response to an Annex-D link integrity poll or
         full status inquiry poll"
      ::= { frxSys 12 }

   frxAgtChInactive OBJECT-TYPE
      SYNTAX  Counter
      ACCESS  read-only
      STATUS  mandatory
      DESCRIPTION
         "Number of times the Cisco 90 Series Agent Annex-D signaling
         channel was declared inactive."
      ::= { frxSys 13 }

   frxAgtChStatus OBJECT-TYPE
      SYNTAX  INTEGER {
         active(1),
         inactive(2)
         }
      ACCESS  read-only
      STATUS  mandatory
      DESCRIPTION
         "Current status of the Annex-D signaling channel
         between the Cisco 90 Series Agent and the Frame Relay Switch."
      ::= { frxSys 14 }

 -- frxDefault group
   frxDefaultEnable OBJECT-TYPE
      SYNTAX  INTEGER {
         enableAutoLoad(1),
         disableAutoLoad(2)
         }
      ACCESS  read-write
      STATUS  mandatory
      DESCRIPTION
         "1=Enable automatic loading of defaults (defined
         in this group) to the channel unit when the
         Download Configuration pushbutton on the channel
         unit faceplate is pushed. 2=Disable loading."
      ::= { frxDefault 1 }

   frxDefaultTrap OBJECT-TYPE
      SYNTAX  INTEGER {
         enableConfigureTrap(1),
         disableConfigureTrap(2)
         }
      ACCESS  read-write
      STATUS  mandatory
      DESCRIPTION
         "1=Enable sending the frxDownloadTrap trap to
         the SNMP manager when  the Download Configuration
         pushbutton on the channel unit faceplate is pushed.
         2=Disable Trap"
      ::= { frxDefault 2 }

   frxDConfigSrc OBJECT-TYPE
      SYNTAX  INTEGER {
         annexD(1),
         snmp(2)
         }
      ACCESS  read-write
      STATUS  mandatory
      DESCRIPTION
         "System default for frxConfigSrc - used when the
         Download Configuration pushbutton on the channel unit
         faceplate is pushed and when frxDefaultEnable is set to 1.
         1=Data rate and protocol set by Annex-D assignment rules.
         2=Data rate and protocol set by the SNMP variables
           frxPortSpeed and frxPortProtocol"
      ::= { frxDefault 3 }

   frxDMgtT391   OBJECT-TYPE
      SYNTAX  INTEGER (5..30)
      ACCESS  read-write
      STATUS  mandatory
      DESCRIPTION
         "System Default for frxMgtT391 - used when the
         Download Configuration pushbutton on the channel unit
         faceplate is pushed and when frxDefaultEnable is set to 1.
         This controls how often (in seconds) the channel units
         send an Annex-D poll to the frame relay switch.
         This is the Annex-D T391 parameter (Typical value 10)"
      ::= { frxDefault 4 }

   frxDMgtT392 OBJECT-TYPE
      SYNTAX  INTEGER (5..30)
      ACCESS  read-write
      STATUS  mandatory
      DESCRIPTION
         "System Default for frxMgtT392 - used when the
         Download Configuration pushbutton on the channel unit
         faceplate is pushed and when frxDefaultEnable is set to 1.
         This controls how long (in seconds) the channel unit
         will wait for a subscriber to send it an Annex-D poll
         before declaring a link error from the subscriber.
         This is the Annex-D T392 parameter (Typical value 15)"
      ::= { frxDefault 5 }


   frxDMgtN391   OBJECT-TYPE
      SYNTAX  INTEGER (1..255)
      ACCESS  read-write
      STATUS  mandatory
      DESCRIPTION
         "System Default for frxMgtN391 - used when the
         Download Configuration pushbutton on the channel unit
         faceplate is pushed and when frxDefaultEnable is set to 1.
         This controls how often the channel units send a full
         status inquiry poll to the frame relay switch instead of
         a link integrity verification poll.
         This is the Annex-D N391 parameter (Typical value 6)"
      ::= { frxDefault 6 }

   frxDMgtN392   OBJECT-TYPE
      SYNTAX  INTEGER (1..10)
      ACCESS  read-write
      STATUS  mandatory
      DESCRIPTION
         "System Default for frxMgtN392 - used when the
         Download Configuration pushbutton on the channel unit
         faceplate is pushed and when frxDefaultEnable is set to 1.
         When more than frxMgtN392 errors are detected in any
         frxMgtN393 monitored Annex-D events, the network is
         declared inactive.
         This is the Annex-D N392 parameter (Typical value 3)"
      ::= { frxDefault 7 }


   frxDMgtN393   OBJECT-TYPE
      SYNTAX  INTEGER (1..10)
      ACCESS  read-write
      STATUS  mandatory
      DESCRIPTION
         "System Default for frxMgtN393 - used when the
         Download Configuration pushbutton on the channel unit
         faceplate is pushed and when frxDefaultEnable is set to 1.
         When more than frxMgtN392 errors are detected in any
         frxMgtN393 monitored Annex-D events, the network is
         declared inactive.
         This is the Annex-D N393 parameter (Typical value 4)"
      ::= { frxDefault 8 }

   frxDPortSpeed OBJECT-TYPE
      SYNTAX  INTEGER  {
         use56kbps(1),
         use64kbps(2),
         use128kbps(3),
         use144kbps(4)
         }
      ACCESS  read-write
      STATUS  mandatory
      DESCRIPTION
         "System Default for frxPortSpeed - used when the
         Download Configuration pushbutton on the channel unit
         faceplate is pushed and when frxDefaultEnable is set to 1.
         This is the speed that the channel unit port runs at.
         1=56kbps   2=64kbps   3=128kbps   4=144kbps"
      ::= { frxDefault 9 }


   frxDPortProtocol OBJECT-TYPE
      SYNTAX  INTEGER {
         frameRelay(1),
         ppp(2)
         }
      ACCESS  read-write
      STATUS  mandatory
      DESCRIPTION
         "System Default for frxPortProtocol - used when the
         Download Configuration pushbutton on the channel unit
         faceplate is pushed and when frxDefaultEnable is set to 1.
         1=Port uses Frame Relay protocol
         2=Port uses PPP protocol - do RFC-1973 encapsulation"
      ::= { frxDefault 10 }

   frxDCktCIR OBJECT-TYPE
      SYNTAX  INTEGER (0..1544000)
      ACCESS  read-write
      STATUS  mandatory
      DESCRIPTION
         "System Default for frxCktCIR - used when the
         Download Configuration pushbutton on the channel unit
         faceplate is pushed and when frxDefaultEnable is set to 1.
         This is the committed information rate (CIR) in bits per
         second.  (Typical value 1536000/#ports)"
      ::= { frxDefault 11 }

   frxDCktBc OBJECT-TYPE
      SYNTAX  INTEGER (0..16777215)
      ACCESS  read-write
      STATUS  mandatory
      DESCRIPTION
         "System Default for frxCktBc - used when the
         Download Configuration pushbutton on the channel unit
         faceplate is pushed and when frxDefaultEnable is set to 1.
         This is the committed BurstSize (Bc) in bits. The time
         interval over which the burst is measured is Bc/CIR.
         (Typically set to same number as frxDCktCIR)."
      ::= { frxDefault 12 }

   frxDCktBe OBJECT-TYPE
      SYNTAX  INTEGER (0..16777212)
      ACCESS  read-write
      STATUS  mandatory
      DESCRIPTION
         "System Default for frxCktBe - used when the
         Download Configuration pushbutton on the channel unit
         faceplate is pushed and when frxDefaultEnable is set to 1.
         This is the excess BurstSize (Be) in bits. The time
         interval over which the excess burst is measured is Be/CIR.
         (Typical value 1536000)."
      ::= { frxDefault 13 }

 -- frxBank group
 -- frxBank Table
   frxBankTable OBJECT-TYPE
      SYNTAX  SEQUENCE OF FrxBankEntry
      ACCESS  not-accessible
      STATUS  mandatory
      DESCRIPTION
         "This Cisco 90 Series Bank Di-group Table contains channel
         bank level information for each of the channel bank di-groups
         in the system. A di-group is a T1 interface to the frame
         relay network. The table is indexed using the Cisco 90 Series
         channel bank digroup number"
      ::= { frxBank 1 }

   frxBankEntry OBJECT-TYPE
      SYNTAX  FrxBankEntry
      ACCESS  not-accessible
      STATUS  mandatory
      DESCRIPTION
         "A specific entry in the Cisco 90 Series Bank Di-group
         Table. There is one entry for each channel bank di-group
         (T1) in the system. There are no entries for unused banks"
      INDEX   {
         frxBankIndex
         }
      ::= { frxBankTable 1 }

   FrxBankEntry ::= SEQUENCE {
      frxBankIndex  INTEGER,
      frxBankType   INTEGER
      }

   frxBankIndex OBJECT-TYPE
      SYNTAX  INTEGER (16..1007)
      ACCESS  read-only
      STATUS  mandatory
      DESCRIPTION
         "Channel Bank Di-group Number. This index is used to address
         the various channel banks in the system. This number is the
         same as the DLCI number used to communicate with the bank at
         the Cisco 90 SNMP Agent. (note that this is NOT the same
         as the DLCI number at the channel bank.  The channel bank
         always uses DLCI 30 or 31 to communicate with the Agent.)"
      ::= { frxBankEntry 1 }

   frxBankType OBJECT-TYPE
      SYNTAX  INTEGER {
         d4(1)
         }
      ACCESS  read-write
      STATUS  mandatory
      DESCRIPTION
         "This is the type of channel bank and is for future use.
         D4 banks return a value of 1."
      ::= { frxBankEntry 2 }


 -- frxChUnit group
 -- frxChUnit Table

   frxChUTable OBJECT-TYPE
      SYNTAX  SEQUENCE OF FrxChUEntry
      ACCESS  not-accessible
      STATUS  mandatory
      DESCRIPTION
         "This Cisco 90 Series Channel Unit Table contains channel unit
         level control and statistics for each of the Cisco 90 Series
         channel units in the system. The table is indexed
         first using the Cisco 90 Series channel bank digroup number,
         then the channel unit number (1 to 24)."
      ::= { frxChUnit 1 }

   frxChUEntry OBJECT-TYPE
      SYNTAX  FrxChUEntry
      ACCESS  not-accessible
      STATUS  mandatory
      DESCRIPTION
         "A specific entry in the Cisco 90 Series Channel Unit Table.
         There is one entry for each Cisco 90 Series channel unit in
         the system. There are no entries for unused banks or empty
         channel unit slots"
      INDEX   {
         frxBankIndex,
         frxChUIndex
         }
      ::= { frxChUTable 1 }

   FrxChUEntry ::= SEQUENCE {
      frxChUIndex          INTEGER,
      frxChUType           INTEGER,
      frxChUVersion        INTEGER,
      frxSigProtocol       INTEGER,
      frxConfigSrc         INTEGER,
      frxDLCIAdLen         INTEGER,
      frxNetInOctets       Counter,
      frxNetOutOctets      Counter,
      frxNetBadFrames      Counter,
      frxNetHDLCEs         Counter,
      frxNetCRCEs          Counter,
      frxNetLinkEs         Counter,
      frxNetFrShEs         Counter,
      frxNetFrLgEs         Counter,
      frxNetPPPEs          Counter,
      frxNetBufEs          Counter
      }

   frxChUIndex OBJECT-TYPE
      SYNTAX  INTEGER (1..24)
      ACCESS  read-only
      STATUS  mandatory
      DESCRIPTION
         "Channel Unit Number.  This index is used to address a
         specific channel unit in a bank. For D4 channel banks
         this number is the same as the physical slot number 1-24"
      ::= { frxChUEntry 1 }

   frxChUType OBJECT-TYPE
      SYNTAX  INTEGER {
         cisco90i(100)
         }
      ACCESS  read-only
      STATUS  mandatory
      DESCRIPTION
         "Type of Cisco 90 Series channel unit installed."
      ::= { frxChUEntry 2 }

   frxChUVersion OBJECT-TYPE
      SYNTAX  INTEGER (0..65535)
      ACCESS  read-only
      STATUS  mandatory
      DESCRIPTION
         "Cisco 90 Series channel unit version number."
      ::= { frxChUEntry 3 }

   frxSigProtocol OBJECT-TYPE
      SYNTAX  INTEGER {
         annexD(1)
         }
      ACCESS  read-only
      STATUS  mandatory
      DESCRIPTION
         "This is the type of Local In-channel Signaling used
         when the subscriber is running frame relay protocol.
         It is provided for future use. Set to 1 for T1.617
         Annex-D"
      ::= { frxChUEntry 4 }

   frxConfigSrc OBJECT-TYPE
      SYNTAX  INTEGER {
         annexD(1),
         snmp(2)
         }
      ACCESS  read-write
      STATUS  mandatory
      DESCRIPTION
         "Source for configuring speed and protocol for each port.
          1=Data rate and protocol set by DLCI assignment rules
            as reported by Annex-D.  This option allows control
            of these basic parameters from the frame relay switch
            management station instead of the Cisco 90 Series
            management station.
          2=Data rate and protocol set by SNMP variables
            frxPortSpeed and frxPortProtocol"
     ::= { frxChUEntry 5 }

   frxDLCIAdLen OBJECT-TYPE
      SYNTAX  INTEGER {
         twoOctetDlci(1)
         }
      ACCESS  read-only
      STATUS  mandatory
      DESCRIPTION
         "The number of bytes used for the DLCI address.
         For future use.  1=two octets."
      ::= { frxChUEntry 6 }

   frxNetInOctets OBJECT-TYPE
      SYNTAX  Counter
      ACCESS  read-only
      STATUS  mandatory
      DESCRIPTION
         "Total number of octets received by this channel
         unit from Frame Relay Switch (on the T1 interface)
         Only frames whose DLCI is addressed to a port on
         this channel unit are counted.  Bad frames, Annex-D
         and SNMP frames are not counted. CRC bytes are not
         counted"
      ::= { frxChUEntry 7 }

   frxNetOutOctets OBJECT-TYPE
      SYNTAX  Counter
      ACCESS  read-only
      STATUS  mandatory
      DESCRIPTION
         "Total number of octets transmitted to the Frame
         Relay Switch (on the T1 interface) by this channel
         unit. Annex-D and SNMP frames are not counted. CRC
         bytes are not counted"
      ::= { frxChUEntry 8 }

   frxNetBadFrames OBJECT-TYPE
      SYNTAX  Counter
      ACCESS  read-only
      STATUS  mandatory
      DESCRIPTION
         "Total number of frames received on the network (T1)
         interface that are discarded by this channel unit.
         Possible reasons for discard are:
            Frame contained HDLC abort (7 or more ones in a row)
            Frame had a CRC error
            Frame had a non-integral number of bytes
            Frame was too short (less than 5 bytes)
            Frame was too long (more than 8192 bytes)
            Frame had bad RFC-1973 (PPP) header - this error only
               occurs if destination port is set for PPP protocol.
            Frame was discarded due to lack of buffer space.
         Only frames whose DLCI is addressed to a port on
         this channel unit are counted."
      ::= { frxChUEntry 9 }

   frxNetHDLCEs OBJECT-TYPE
      SYNTAX  Counter
      ACCESS  read-only
      STATUS  mandatory
      DESCRIPTION
         "Network Errored Seconds caused by HDLC aborts (7 or more
         ones in a row). Total number of seconds in which a frame
         with an HDLC abort is received by this channel unit on
         the network (T1) interface. Only frames whose DLCI is
         addressed to a port on this channel unit are counted."
      ::= { frxChUEntry 10 }

   frxNetCRCEs OBJECT-TYPE
      SYNTAX  Counter
      ACCESS  read-only
      STATUS  mandatory
      DESCRIPTION
         "Network Errored Seconds caused by CRC errors.
         Total number of seconds in which a frame with a CRC
         error is received by this channel unit on the network
         (T1) interface. Only frames whose DLCI is addressed
         to a port on this channel unit are counted."
      ::= { frxChUEntry 11 }

   frxNetLinkEs OBJECT-TYPE
      SYNTAX  Counter
      ACCESS  read-only
      STATUS  mandatory
      DESCRIPTION
         "Network Errored Seconds caused by Non-integral Bytes.
         Total number of seconds in which a frame with a non-integral
         number of bytes is received by this channel unit on the
         network (T1) interface. Only frames whose DLCI is addressed
         to a port on this channel unit are counted."
      ::= { frxChUEntry 12 }

   frxNetFrShEs OBJECT-TYPE
      SYNTAX  Counter
      ACCESS  read-only
      STATUS  mandatory
      DESCRIPTION
         "Network Errored Seconds caused by Short Frames received.
         Total number of seconds in which a frame that is too
         short (less than 5 bytes) is received by this channel
         unit on the network (T1) interface. Only frames whose
         DLCI is addressed to a port on this channel unit are
         counted."
      ::= { frxChUEntry 13 }

   frxNetFrLgEs OBJECT-TYPE
      SYNTAX  Counter
      ACCESS  read-only
      STATUS  mandatory
      DESCRIPTION
         "Network Errored Seconds caused by Long Frames received.
         Total number of seconds in which a frame that is too
         long (more than 8192 bytes) is received by this channel
         unit on the network (T1) interface. Only frames whose
         DLCI is addressed to a port on this channel unit are
         counted."
      ::= { frxChUEntry 14 }

   frxNetPPPEs OBJECT-TYPE
      SYNTAX  Counter
      ACCESS  read-only
      STATUS  mandatory
      DESCRIPTION
         "Errored seconds caused by bad RFC-1973 (PPP) header.
         Total number of seconds in which a frame with an
         invalid RFC-1973 (PPP) header is received by this
         channel unit on the network (T1) interface. Only frames
         whose DLCI is addressed to a port that is set to PPP
         protocol and is on this channel unit are counted."
      ::= { frxChUEntry 15 }

   frxNetBufEs OBJECT-TYPE
      SYNTAX  Counter
      ACCESS  read-only
      STATUS  mandatory
      DESCRIPTION
         "Errored Seconds caused by Buffer Overflow.
         Total number of seconds in which a frame received
         by this channel unit on the network (T1) interface
         was discarded due to insufficient buffer space. Only
         frames whose DLCI is addressed to a port on this
         channel unit are counted."
      ::= { frxChUEntry 16 }

 -- frxMgt group
 -- frxMgt Table
   frxMgtTable OBJECT-TYPE
      SYNTAX  SEQUENCE OF FrxMgtEntry
      ACCESS  not-accessible
      STATUS  mandatory
      DESCRIPTION
         "This table monitors and controls the T1-617 Annex-D
         parameters used by the channel units. There is one
         table row for every channel unit in every bank. The
         table is indexed first using the Cisco 90 Series channel
         bank digroup number, then the channel unit number (1 to 24).
         For best performance, all of the channel units in a
         given bank should be set to identical values.  These
         values are typically set using global parameters in the
         frxDefaultTable instead of directly via this table. "
      ::= { frxMgt 1 }

    frxMgtEntry OBJECT-TYPE
       SYNTAX  FrxMgtEntry
       ACCESS  not-accessible
       STATUS  mandatory
       DESCRIPTION
         "A specific entry in the Cisco 90 Series Management Table.
         There is one entry for each Cisco 90 Series channel unit
         in the system. There are no entries for unused banks or
         empty channel unit slots"
       INDEX   {
          frxBankIndex,
          frxChUIndex
          }
       ::= { frxMgtTable 1 }

   FrxMgtEntry ::= SEQUENCE {
      frxPortsInSvc         INTEGER,
      frxMgtT391            INTEGER,
      frxMgtT392            INTEGER,
      frxMgtN391            INTEGER,
      frxMgtN392            INTEGER,
      frxMgtN393            INTEGER,
      frxNetLinkErrors      Counter,
      frxNetProtErrors      Counter,
      frxNetChInactive      Counter,
      frxNetChStatus        INTEGER
      }

   frxPortsInSvc OBJECT-TYPE
      SYNTAX  INTEGER (0..4)
      ACCESS  read-only
      STATUS  mandatory
      DESCRIPTION
         "Ports in service. The number of ports on a Cisco 90 Series
         channel unit that have one or more active PVCs, as determined
         by Annex-D."
      ::= { frxMgtEntry 1 }

   frxMgtT391 OBJECT-TYPE
      SYNTAX  INTEGER (5..30)
      ACCESS  read-write
      STATUS  mandatory
      DESCRIPTION
         "This controls how often (in seconds) the channel unit
         sends an Annex-D poll to the frame relay switch.
         This is the Annex-D T391 parameter (Typical value 10)"
      ::= { frxMgtEntry 2 }

   frxMgtT392 OBJECT-TYPE
      SYNTAX  INTEGER (5..30)
      ACCESS  read-write
      STATUS  mandatory
      DESCRIPTION
         "This controls how long (in seconds) the channel unit
         will wait for a subscriber to send it an Annex-D poll
         before declaring a link error from the subscriber.
         This is the Annex-D T392 parameter (Typical value 15)"
      ::= { frxMgtEntry 3 }

   frxMgtN391 OBJECT-TYPE
      SYNTAX  INTEGER (1..255)
      ACCESS  read-write
      STATUS  mandatory
      DESCRIPTION
         "This controls how often (in polls) the channel unit
         sends a full status inquiry poll to the frame relay
         switch instead of a link integrity verification poll.
         This is the Annex-D N391 parameter (Typical value 6)"
      ::= { frxMgtEntry 4 }

   frxMgtN392 OBJECT-TYPE
      SYNTAX  INTEGER (1..10)
      ACCESS  read-write
      STATUS  mandatory
      DESCRIPTION
         "When more than frxMgtN392 errors are detected in any
         frxMgtN393 monitored Annex-D events, the network is
         declared inactive. This is the Annex-D N392 parameter
         (Typical value 3)"
      ::= { frxMgtEntry 5 }

   frxMgtN393 OBJECT-TYPE
      SYNTAX  INTEGER (1..10)
      ACCESS  read-write
      STATUS  mandatory
      DESCRIPTION
         "When more than frxMgtN392 errors are detected in any
         frxMgtN393 monitored Annex-D events, the network is
         declared inactive. This is the Annex-D N393 parameter
         (Typical value 4)"
      ::= { frxMgtEntry 6 }

   frxNetLinkErrors OBJECT-TYPE
      SYNTAX  Counter
      ACCESS  read-only
      STATUS  mandatory
      DESCRIPTION
         "Number of signaling link reliability errors from
         network.  A signaling reliability error is declared
         whenever the channel units did not receive a reply
         from the frame relay switch to an Annex-D link
         integrity poll or full status inquiry poll"
      ::= { frxMgtEntry 7 }

   frxNetProtErrors OBJECT-TYPE
      SYNTAX  Counter
      ACCESS  read-only
      STATUS  mandatory
      DESCRIPTION
         "Number of signaling protocol errors from network.
         A signaling protocol error is declared whenever
         the channel units receive a reply with incorrect
         format or sequence numbers from the frame relay
         switch in response to an Annex-D link integrity
         poll or full status inquiry poll"
      ::= { frxMgtEntry 8 }

   frxNetChInactive OBJECT-TYPE
      SYNTAX  Counter
      ACCESS  read-only
      STATUS  mandatory
      DESCRIPTION
         "Number of times network Annex-D signaling channel
         was declared inactive."
      ::= { frxMgtEntry 9 }

   frxNetChStatus OBJECT-TYPE
      SYNTAX  INTEGER {
         active(1),
         inactive(2)
         }
      ACCESS  read-only
      STATUS  mandatory
      DESCRIPTION
         "Current status of the Annex-D signaling channel on
         the network side of the channel bank."
      ::= { frxMgtEntry 10 }

 -- frxMgtPortTable
   frxMgtPortTable OBJECT-TYPE
      SYNTAX  SEQUENCE OF FrxMgtPortEntry
      ACCESS  not-accessible
      STATUS  mandatory
      DESCRIPTION
         "This table monitors the T1-617 Annex-D link
         between the channel units and the subscribers.
         There is one table row for every port on every
         channel unit in every bank. The table is indexed
         first using the channel bank digroup number, then
         the channel unit number (1 to 24), and then the
         port number (0 to 3)."
      ::= { frxMgt 2 }

   frxMgtPortEntry OBJECT-TYPE
      SYNTAX  FrxMgtPortEntry
      ACCESS  not-accessible
      STATUS  mandatory
      DESCRIPTION
         "A specific entry in the Cisco 90 Series Management Port
         Table. There is one entry for each port on each
         Cisco 90 Series channel unit in the system.  There are no
         entries  for unused banks or empty channel unit
         slots."
      INDEX   {
         frxBankIndex,
         frxChUIndex,
         frxPortIndex
         }
      ::= { frxMgtPortTable 1 }

   FrxMgtPortEntry ::= SEQUENCE {
      frxPortIndex           INTEGER,
      frxPortLinkErrors      Counter,
      frxPortProtErrors      Counter,
      frxPortChInactive      Counter
      }

   frxPortIndex OBJECT-TYPE
      SYNTAX  INTEGER (0..3)
      ACCESS  read-only
      STATUS  mandatory
      DESCRIPTION
         "Which subscriber port on the channel unit is
         addressed.  Ports are numbered from 0 to 3.
         Some channel unit types have less than 4 ports."
      ::= { frxMgtPortEntry 1 }

   frxPortLinkErrors OBJECT-TYPE
      SYNTAX  Counter
      ACCESS  read-only
      STATUS  mandatory
      DESCRIPTION
         "Number of signaling link reliability errors from
         subscriber port.  A signaling reliability error is
         declared whenever the channel units did not receive
         an Annex-D link integrity poll or full status inquiry
         poll from the subscriber port within the required time."
      ::= { frxMgtPortEntry 2 }

   frxPortProtErrors OBJECT-TYPE
      SYNTAX  Counter
      ACCESS  read-only
      STATUS  mandatory
      DESCRIPTION
         "Number of signaling protocol errors from subscriber
         port. A signaling protocol error is declared whenever
         the channel units receive an Annex-D link integrity
         poll or full status inquiry poll with incorrect
         format or sequence numbers from the subscriber port."
      ::= { frxMgtPortEntry 3 }

   frxPortChInactive OBJECT-TYPE
      SYNTAX  Counter
      ACCESS  read-only
      STATUS  mandatory
      DESCRIPTION
         "Number of times the subscriber port Annex-D signaling
         channel was declared inactive"
      ::= { frxMgtPortEntry 4 }

 -- frxPort group
 -- frxPort Table
   frxPortTable OBJECT-TYPE
      SYNTAX  SEQUENCE OF FrxPortEntry
      ACCESS  not-accessible
      STATUS  mandatory
      DESCRIPTION
         "This Cisco 90 Series Port Table contains per-port control and
         statistics for each of the subscriber ports in the
         system. The table is indexed first using the Cisco 90 Series
         channel bank digroup number, then by the channel
         unit number (1 to 24), and finally by the port
         number (0-3)."
      ::= { frxPort 1 }

   frxPortEntry OBJECT-TYPE
     SYNTAX  FrxPortEntry
     ACCESS  not-accessible
     STATUS  mandatory
     DESCRIPTION
         "A specific entry in the Cisco 90 Series Port Table. There is
         one entry for each port on each Cisco 90 Series channel unit
         in the system.  There are no entries for unused banks or
         empty channel unit slots."
     INDEX   {
        frxBankIndex,
        frxChUIndex,
        frxPortIndex
        }
     ::= { frxPortTable 1 }

   FrxPortEntry ::= SEQUENCE {
      frxPortSpeed         INTEGER,
      frxPortProtocol      INTEGER,
      frxDSLStatus         INTEGER,
      frxPVCAssigned       INTEGER,
      frxLastChange        TimeTicks,
      frxBrite             INTEGER,
      frxDSLInOctets       Counter,
      frxDSLOutOctets      Counter,
      frxT1InOctets        Counter,
      frxT1OutOctets       Counter,
      frxDSLBadFrames      Counter,
      frxDSLHDLCEs         Counter,
      frxDSLCRCEs          Counter,
      frxDSLLinkEs         Counter,
      frxDSLFrShEs         Counter,
      frxDSLFrLgEs         Counter,
      frxDSLDLCIEs         Counter,
      frxTxBuf             INTEGER,
      frxRxBuf             INTEGER,
      frxPortNetEs         Counter
      }

   frxPortSpeed OBJECT-TYPE
      SYNTAX  INTEGER {
         use56kbps(1),
         use64kbps(2),
         use128kbps(3),
         use144kbps(4)
         }
      ACCESS  read-write
      STATUS  mandatory
      DESCRIPTION
         "This is the speed that the channel unit port runs at.
           1=56kbps   2=64kbps   3=128kbps   4=144kbps
         This parameter can only be changed if frxConfigSrc is
         set to SNMP."
      ::= { frxPortEntry 1 }

   frxPortProtocol OBJECT-TYPE
      SYNTAX  INTEGER {
         frameRelay(1),
         ppp(2)
         }
      ACCESS  read-write
      STATUS  mandatory
      DESCRIPTION
         "This parameter controls what protocol the channel
         unit should expect the subscriber to send on the port.
           1=Port uses Frame Relay protocol - no encapsulation
           2=Port uses PPP protocol - do RFC-1973 encapsulation
         This parameter can only be changed if frxConfigSrc is
         set to SNMP."
      ::= { frxPortEntry 2 }

   frxDSLStatus OBJECT-TYPE
      SYNTAX  INTEGER {
         loopDown(1),
         dslSyncOnly(2),
         loopUpInactive(3),
         loopUp(4)
         }
      ACCESS  read-only
      STATUS  mandatory
      DESCRIPTION
         "This is the status of the DSL loop to the subscriber.
         1=Loop is down.
         2=Frx card has achieved physical layer activation with
           the first BRITE card or the NT1 if there are no BRITE cards.
         3=Link is up but Annex-D is still inactive.  The ACT bit has
           been exchanged with the NT1 indicating a clear channel path
           to the customer has been established. Ports running protocols
           (i.e. PPP) that do not support Annex-D will never be in this
           state.
         4=Link is fully up.  Annex-D (if appropriate) is active."
      ::= { frxPortEntry 3 }

   frxPVCAssigned OBJECT-TYPE
     SYNTAX  INTEGER (0..8)
     ACCESS  read-only
     STATUS  mandatory
     DESCRIPTION
        "Number of PVCs assigned to Subscriber Port as determined
        by Annex-D"
     ::= { frxPortEntry 4 }

   frxLastChange OBJECT-TYPE
     SYNTAX  TimeTicks
     ACCESS  read-only
     STATUS  mandatory
     DESCRIPTION
        "Time since DSL went in sync or lost sync in 0.01
        second increments."
     ::= { frxPortEntry 5 }

   frxBrite OBJECT-TYPE
      SYNTAX  INTEGER (0..6)
      ACCESS  read-only
      STATUS  mandatory
      DESCRIPTION
         "Number of BRITE cards downstream.  BRITE cards are used
         to extend the loop over subscriber loop carrier systems
         and are detected via a background polling operation."
      ::= { frxPortEntry 6 }

   frxDSLInOctets OBJECT-TYPE
      SYNTAX  Counter
      ACCESS  read-only
      STATUS  mandatory
      DESCRIPTION
         "Number of octets received from the subscriber DSL
         Does not include Annex-D octets"
      ::= { frxPortEntry 7 }

   frxDSLOutOctets OBJECT-TYPE
      SYNTAX  Counter
      ACCESS  read-only
      STATUS  mandatory
      DESCRIPTION
         "Number of octets transmitted to the subscriber DSL.
         Does not include Annex-D octets"
      ::= { frxPortEntry 8 }

   frxT1InOctets OBJECT-TYPE
      SYNTAX  Counter
      ACCESS  read-only
      STATUS  mandatory
      DESCRIPTION
        "Number of octets received from the network
        directed at this subscriber port"
      ::= { frxPortEntry 9 }

   frxT1OutOctets OBJECT-TYPE
      SYNTAX  Counter
      ACCESS  read-only
      STATUS  mandatory
      DESCRIPTION
         "Number of octets transmitted to the network
         from this subscriber port"
      ::= { frxPortEntry 10 }

   frxDSLBadFrames OBJECT-TYPE
      SYNTAX  Counter
      ACCESS  read-only
      STATUS  mandatory
      DESCRIPTION
         "Total number of frames received from this subscriber port
         that were discarded. Possible reasons for discard are:
            Frame contained HDLC abort (7 or more ones in a row)
            Frame had a CRC error
            Frame had a non-integral number of bytes
            Frame was too short (less than 5 bytes)
            Frame was too long (more than 8192 bytes)
            Frame had illegal DLCI (not 16-23)
            Frame was discarded due to lack of buffer space or
               due to congestion control"
      ::= { frxPortEntry 11 }

   frxDSLHDLCEs OBJECT-TYPE
      SYNTAX  Counter
      ACCESS  read-only
      STATUS  mandatory
      DESCRIPTION
         "Subscriber port Errored Seconds caused by HDLC aborts
         (7 or more ones in a row). Total number of seconds in
         which a frame with an HDLC abort is received from this
         port."
      ::= { frxPortEntry 12 }

   frxDSLCRCEs OBJECT-TYPE
      SYNTAX  Counter
      ACCESS  read-only
      STATUS  mandatory
      DESCRIPTION
         "Subscriber port Errored Seconds caused by CRC errors.
         Total number of seconds in which a frame with a CRC
         error is received from this port."
      ::= { frxPortEntry 13 }

   frxDSLLinkEs OBJECT-TYPE
      SYNTAX  Counter
      ACCESS  read-only
      STATUS  mandatory
      DESCRIPTION
         "Subscriber port Errored Seconds caused by Non-integral
         Bytes. Total number of seconds in which a frame with a
         non-integral  number of bytes is received from this
         port."
      ::= { frxPortEntry 14 }

   frxDSLFrShEs OBJECT-TYPE
      SYNTAX  Counter
      ACCESS  read-only
      STATUS  mandatory
      DESCRIPTION
         "Subscriber port Errored Seconds caused by Short Frames.
         received Total number of seconds in which a frame that
         is too short (less than 5 bytes) is received from this
         port."
      ::= { frxPortEntry 15 }

   frxDSLFrLgEs OBJECT-TYPE
      SYNTAX  Counter
      ACCESS  read-only
      STATUS  mandatory
      DESCRIPTION
         "Subscriber port Errored Seconds caused by Long Frames
         received. Total number of seconds in which a frame that
         is too long (more than 8192 bytes) is received from this
         port."
      ::= { frxPortEntry 16 }

   frxDSLDLCIEs OBJECT-TYPE
      SYNTAX  Counter
      ACCESS  read-only
      STATUS  mandatory
      DESCRIPTION
         "Subscriber port Errored Seconds caused by illegal DLCI.
         Total number of seconds in which a frame that has a DLCI
         other than 16 to 23 (or 0) is received from this port."
      ::= { frxPortEntry 17 }

   frxTxBuf OBJECT-TYPE
      SYNTAX  INTEGER (0..65535)
      ACCESS  read-only
      STATUS  mandatory
      DESCRIPTION
         "Number of octets in the transmit buffer for this
         subscriber port.  This data is waiting to be sent
         to the network (T1)."
      ::= { frxPortEntry 18 }

   frxRxBuf OBJECT-TYPE
      SYNTAX  INTEGER (0..65535)
      ACCESS  read-only
      STATUS  mandatory
      DESCRIPTION
         "Number of octets in the receive buffer for this
         subscriber port.  This data is from the network (T1)
         and is waiting to be sent to the subscriber port."
      ::= { frxPortEntry 19 }

   frxPortNetEs OBJECT-TYPE
      SYNTAX  Counter
      ACCESS  read-only
      STATUS  mandatory
      DESCRIPTION
         "Total number of seconds in which a frame received
         from the network (T1) and targeted at this subscriber
         port was discarded."
      ::= { frxPortEntry 20 }


 -- frxCircuit Table
   frxCircuitTable OBJECT-TYPE
      SYNTAX  SEQUENCE OF FrxCircuitEntry
      ACCESS  not-accessible
      STATUS  mandatory
      DESCRIPTION
         "This Cisco 90 Series Circuit Table contains
         per-virtual-circuit control and statistics for each of the
         permanent virtual circuits in the system. The table is
         indexed first using the Cisco 90 Series channel bank
         digroup number, then by the channel unit number (1 to 24),
         then by the port number (0-3) and finally by the circuit
         DLCI number (16 to 23)."
      ::= { frxPort 2 }

   frxCircuitEntry OBJECT-TYPE
      SYNTAX  FrxCircuitEntry
      ACCESS  not-accessible
      STATUS  mandatory
      DESCRIPTION
         "A specific entry in the Cisco 90 Series Circuit Table.
         There is one entry for each permanent virtual circuit
         in the system.  There are no entries for unused
         banks or empty channel unit slots."
     INDEX   {
        frxBankIndex,
        frxChUIndex,
        frxPortIndex,
        frxPvcIndex
        }
     ::= { frxCircuitTable 1 }

   FrxCircuitEntry ::= SEQUENCE {
      frxPvcIndex         INTEGER,
      frxCktCIR           INTEGER,
      frxCktBc            INTEGER,
      frxCktBe            INTEGER,
      frxFarEndOpStat     INTEGER,
      frxCktInOctets      Counter,
      frxCktOutOctets     Counter,
      frxCktInFrames      Counter,
      frxCktOutFrames     Counter,
      frxCktDiscards      Counter
     }

   frxPvcIndex OBJECT-TYPE
      SYNTAX  INTEGER (16..23)
      ACCESS  read-only
      STATUS  mandatory
      DESCRIPTION
         "This index is the subscriber loop DLCI number of the
         permanent virtual circuit. It ranges from 16 to 23.
         The corresponding network side DLCI must be assigned
         in the frame relay switch and communicated to the Cisco 90
         Series channel units via the Annex-D protocol before this
         element can be addressed."
      ::= { frxCircuitEntry 1 }

   frxCktCIR OBJECT-TYPE
      SYNTAX  INTEGER (0..1544000)
      ACCESS  read-write
      STATUS  mandatory
      DESCRIPTION
         "This is the committed information rate (CIR) in bits
         per second for the addressed permanent virtual circuit.
         (Typical value 1536000/#ports)."
     ::= { frxCircuitEntry 2 }

   frxCktBc OBJECT-TYPE
      SYNTAX  INTEGER (0..16777215)
      ACCESS  read-write
      STATUS  mandatory
      DESCRIPTION
         "This is the Committed Burst Size (Bc) in bits for the
         addressed permanent virtual circuit. The time interval
         over which the burst is measured is Bc/CIR. (Typically
         set to same number as frxCktCIR)."
      ::= { frxCircuitEntry 3 }

   frxCktBe OBJECT-TYPE
      SYNTAX  INTEGER (0..16777215)
      ACCESS  read-write
      STATUS  mandatory
      DESCRIPTION
         "This is the Excess Burst Size (Be) in bits for the
         addressed permanent virtual circuit. The time interval
         over which the excess burst is measured is Be/CIR.
         (Typical value 1536000)."
      ::= { frxCircuitEntry 4 }

   frxFarEndOpStat OBJECT-TYPE
      SYNTAX  INTEGER {
         active(1),
         inactive(2)
         }
      ACCESS  read-only
      STATUS  mandatory
      DESCRIPTION
         "This is the status of the far end of the frame relay
         permanent virtual circuit (through the frame relay
         network) as determined by Annex-D.
           1=active
           2=inactive"
      ::= { frxCircuitEntry 5 }

   frxCktInOctets OBJECT-TYPE
      SYNTAX  Counter
      ACCESS  read-only
      STATUS  mandatory
      DESCRIPTION
         "The number of input octets from the subscriber port
         on the addressed permanent virtual circuit.  These
         octets are destined for the network (T1)."
      ::= { frxCircuitEntry 6 }

   frxCktOutOctets OBJECT-TYPE
      SYNTAX  Counter
      ACCESS  read-only
      STATUS  mandatory
      DESCRIPTION
         "The number of output octets to the subscriber port
         on the addressed permanent virtual circuit.  These
         octets were received from the network (T1)."
      ::= { frxCircuitEntry 7 }

   frxCktInFrames OBJECT-TYPE
      SYNTAX  Counter
      ACCESS  read-only
      STATUS  mandatory
      DESCRIPTION
         "The number of input frames from the subscriber port
         on the addressed permanent virtual circuit.  These
         frames are destined for the network (T1)."
      ::= { frxCircuitEntry 8 }

   frxCktOutFrames OBJECT-TYPE
      SYNTAX  Counter
      ACCESS  read-only
      STATUS  mandatory
      DESCRIPTION
         "The number of output frames to the subscriber port
         on the addressed permanent virtual circuit.  These
         frames were received from the network (T1)."
      ::= { frxCircuitEntry 9 }

   frxCktDiscards OBJECT-TYPE
      SYNTAX  Counter
      ACCESS  read-only
      STATUS  mandatory
      DESCRIPTION
         "The number of input frames from the subscriber port
         on the addressed permanent virtual circuit that were
         discarded due to congestion (lack of buffer space or
         congestion control."
      ::= { frxCircuitEntry 10 }


 -- frxUEoc Table
   frxUEocTable OBJECT-TYPE
      SYNTAX  SEQUENCE OF FrxUEocEntry
      ACCESS  not-accessible
      STATUS  mandatory
      DESCRIPTION
         "This Cisco 90 Series Embedded Operations Channel Table
         is used to diagnose and sectionalize problems with the
         subscriber loop.  It contains one entry for each of the
         Cisco 90 Series channel units in the system. The table
         is indexed first using the Cisco 90 Series channel bank
         digroup number, then the channel unit number (1 to 24)."
      ::= { frxPort 3 }

   frxUEocEntry OBJECT-TYPE
      SYNTAX  FrxUEocEntry
      ACCESS  not-accessible
      STATUS  mandatory
      DESCRIPTION
         "A specific entry in the Cisco 90 Series Embedded Operations
         Channel Table. There is one entry for each Cisco 90 Series
         channel unit in the system. There are no entries for unused
         banks or empty channel unit slots"
      INDEX   {
         frxBankIndex,
         frxChUIndex
         }
      ::= { frxUEocTable 1 }

   FrxUEocEntry ::= SEQUENCE {
      frxTestPort          INTEGER,
      frxTestType          INTEGER,
      frxLoopLoc           INTEGER,
      frxLoopCh            INTEGER,
      frxStartTest         INTEGER,
      frxBertRst           INTEGER,
      frxBertBE            Counter,
      frxBertTestTime      TimeTicks,
      frxTestInProg        INTEGER
      }

   frxTestPort OBJECT-TYPE
      SYNTAX  INTEGER (0..3)
      ACCESS  read-write
      STATUS  mandatory
      DESCRIPTION
         "This parameter indicates which subscriber port on the
         channel unit to test. It has no effect until frxStartTest
         is set to start the test. Only one port on a given channel
         unit may be tested at a time."
      ::= { frxUEocEntry 1 }

   frxTestType OBJECT-TYPE
      SYNTAX  INTEGER {
         loopbackAndBert(1),
         bertOnly(2),
         sendCorruptCRC(3),
         loopbackOnly(4),
         localLoopAllPorts(5)
         }
      ACCESS  read-write
      STATUS  mandatory
      DESCRIPTION
         "This parameter indicates the type of test to perform. It
         has no effect until frxStartTest is set to start the test.
         1=Set up a loopback and run a PN-2047 Bit Error Rate Test.
         2=Run a (straightaway) PN-2047 Bit Error Rate Test.  This
           test assumes a loopback has been manually set up somewhere
           downstream or another test set running PN-2047 BERT is
           connected downstream.
         3=Send corrupted CRC on the DSL.  This has no effect on the
           frame relay CRC, only the out-of-band DSL CRC (used for
           performance monitoring) is corrupted.
         4=Set up a loopback at the specified location to loop the
           frame relay or PPP data in both directions.
         5=Setup a local loopback on all 4 ports.  frxTestPort and
           frxLoopLoc are ignored for this test."
      ::= { frxUEocEntry 2 }

   frxLoopLoc OBJECT-TYPE
      SYNTAX  INTEGER {
         localFrx(7),
         briteCard1(1),
         briteCard2(2),
         briteCard3(3),
         briteCard4(4),
         briteCard5(5),
         briteCard6(6),
         nt1(8)
         }
      ACCESS  read-write
      STATUS  mandatory
      DESCRIPTION
         "This parameter indicates the location of the loopback or
         the card that will send corrupt CRC. It has no effect
         until frxStartTest is set to start the test.  It has no
         effect for a BertOnly test.
         7=Local Cisco 90 Series card  8=NT1 at customer premise
         1 to 6 is used to address intervening BRITE cards."
      ::= { frxUEocEntry 3 }

   frxLoopCh OBJECT-TYPE
      SYNTAX  INTEGER {
         b1only(1),
         b2only(2),
         all(3)
         }
      ACCESS  read-write
      STATUS  mandatory
      DESCRIPTION
         "This parameter indicates which channels to use for the
         loopbackOnly and localLoopAllPorts test. It has no effect
         until frxStartTest is set to start the test. Note that the
         loopbackAndBert test always loops all channels back.
         1=B1 channel   2=B2 channel   3=All channels (includes all
           B channels plus all D channels"
      ::= { frxUEocEntry 4 }

   frxStartTest OBJECT-TYPE
      SYNTAX  INTEGER {
         stopTest(1),
         startTest(2)
         }
      ACCESS  read-write
      STATUS  mandatory
      DESCRIPTION
         "This parameter is used to start and stop the test.
         frxTestPort, frxTestType, frxLoopLoc, and frxLoopCh should
         be set up prior to starting the test.
         1=stop test.   2=start test."
      ::= { frxUEocEntry 5 }

   frxBertRst OBJECT-TYPE
      SYNTAX  INTEGER {
         normal(1),
         resetBert(2)
         }
      ACCESS  read-write
      STATUS  mandatory
      DESCRIPTION
         "This parameter may be used during a LoopbackAndBert test
         or a BertOnly test to reset the frxBertBE counter. It
         must be returned to the normal posiion to allow errors to
         be counted.
         1=normal.   2=Reset BERT counter."
      ::= { frxUEocEntry 6 }

   frxBertBE OBJECT-TYPE
      SYNTAX  Counter
      ACCESS  read-only
      STATUS  mandatory
      DESCRIPTION
         "BERT test block errors"
      ::= { frxUEocEntry 7 }

   frxBertTestTime OBJECT-TYPE
      SYNTAX  TimeTicks
      ACCESS  read-only
      STATUS  mandatory
      DESCRIPTION
         "BERT test time in 0.01 second increments"
      ::= { frxUEocEntry 8 }

   frxTestInProg OBJECT-TYPE
      SYNTAX  INTEGER {
         testInProgress(1),
         normalOperation(2)
         }
      ACCESS  read-only
      STATUS  mandatory
      DESCRIPTION
         "Test in progress (1); Normal operation (2)"
      ::= { frxUEocEntry 9 }

 -- frxUThr Table
   frxUThrTable OBJECT-TYPE
      SYNTAX  SEQUENCE OF FrxUThrEntry
      ACCESS  not-accessible
      STATUS  mandatory
      DESCRIPTION
         "This table contains the U-interface Performance Monitoring
         Thresholds and Alarms for each of the subscriber loops in
         the system and for any BRITE cards extending those loops
         (e.g. using Subscriber Loop Carrier systems)  The table is
         indexed first using the Cisco 90 Series channel bank digroup
         number, then the channel unit number (1 to 24), then the port
         number (0, 1, etc) and finally the location number (the BRITE
         card number (1 to 6) or 7 for local parameters in the Cisco
         90 Series card). These registers are defined by Bellcore
         TR-TSY-000829."
      ::= { frxPort 4 }

   frxUThrEntry OBJECT-TYPE
      SYNTAX  FrxUThrEntry
      ACCESS  not-accessible
      STATUS  mandatory
      DESCRIPTION
         "A specific entry in the U-interface Performance Monitoring
         Threshold table.  There is one entry for each port on each
         Cisco 90 Series channel unit in the system and one entry for
         each BRITE card extending those ports.  There are no entries
         for unused banks or empty channel unit slots"
     INDEX   {
        frxBankIndex,
        frxChUIndex,
        frxPortIndex,
        frxPAddrIndex
       }
     ::= { frxUThrTable 1 }

   FrxUThrEntry ::= SEQUENCE {
      frxPAddrIndex        INTEGER,
      frxChEsTh            INTEGER,
      frxCdEsTh            INTEGER,
      frxChSesTh           INTEGER,
      frxCdSesTh           INTEGER,
      frxAlertMask         INTEGER,
      frxThCond            INTEGER
     }

   frxPAddrIndex OBJECT-TYPE
      SYNTAX  INTEGER {
         localFrx(7),
         briteCard1(1),
         briteCard2(2),
         briteCard3(3),
         briteCard4(4),
         briteCard5(5),
         briteCard6(6)
         }
      ACCESS  read-only
      STATUS  mandatory
      DESCRIPTION
         "This is the physical location where the performance
         monitoring takes place.  It may be set to localFrx(7)
         to access and control PM values local to the Cisco 90
         Series channel unit. If there are BRITE cards in the
         subscriber loop between the Cisco 90 Series channel
         unit and the customer, PM values contained in those
         cards may be accessed using briteCard1(1) to
         briteCard6(6) where briteCard1 is the card closest
         to the Cisco 90 Series channel unit."
      ::= { frxUThrEntry 1 }

   frxChEsTh OBJECT-TYPE
      SYNTAX  INTEGER (1..3600)
      ACCESS  read-write
      STATUS  mandatory
      DESCRIPTION
         "Current Hour Errored Seconds threshold. This
         threshold is used for both the transmit and receive
         directions. When errors are detected that exceed this
         threshold and the corresponding bit in the frxAlertMask
         register is 0, the corresponding bit in the frxThCond
         register is set and a trap is generated (depending on
         the state of frxUPerfTrapEnable). Factory defaut is 40.
         Indexed by Bank.ChannelUnit.Port.Address"
      ::= { frxUThrEntry 2 }

   frxCdEsTh OBJECT-TYPE
      SYNTAX  INTEGER (1..65535)
      ACCESS  read-write
      STATUS  mandatory
      DESCRIPTION
         "Current Day Errored Seconds threshold. This
         threshold is used for both the transmit and receive
         directions. When errors are detected that exceed this
         threshold and the corresponding bit in the frxAlertMask
         register is 0, the corresponding bit in the frxThCond
         register is set and a trap is generated (depending on
         the state of frxUPerfTrapEnable). Factory defaut is 100.
         Indexed by Bank.ChannelUnit.Port.Address"
      ::= { frxUThrEntry 3 }

   frxChSesTh OBJECT-TYPE
      SYNTAX  INTEGER (1..3600)
      ACCESS  read-write
      STATUS  mandatory
      DESCRIPTION
         "Current Hour Severely Errored Seconds threshold. This
         threshold is used for both the transmit and receive
         directions. When errors are detected that exceed this
         threshold and the corresponding bit in the frxAlertMask
         register is 0, the corresponding bit in the frxThCond
         register is set and a trap is generated (depending on
         the state of frxUPerfTrapEnable). Factory defaut is 10.
         Indexed by Bank.ChannelUnit.Port.Address"
      ::= { frxUThrEntry 4 }

   frxCdSesTh OBJECT-TYPE
      SYNTAX  INTEGER (1..65535)
      ACCESS  read-write
      STATUS  mandatory
      DESCRIPTION
         "Current Day Severely Errored Seconds threshold. This
         threshold is used for both the transmit and receive
         directions. When errors are detected that exceed this
         threshold and the corresponding bit in the frxAlertMask
         register is 0, the corresponding bit in the frxThCond
         register is set and a trap is generated (depending on
         the state of frxUPerfTrapEnable). Factory defaut is 25.
         Indexed by Bank.ChannelUnit.Port.Address"
      ::= { frxUThrEntry 5 }

   frxAlertMask OBJECT-TYPE
      SYNTAX  INTEGER (0..255)
      ACCESS  read-write
      STATUS  mandatory
      DESCRIPTION
         "8-bit Alert Mask register. One bit for each threshold in
         both directions.  When set to 1, the corresponding threshold
         crossing is ignored. When set to 0, the corresponding threshold
         crossing is indicated in frxThCond and may cause a trap to be
         sent depending on the state of frxUPerfTrapEnable.
              1  Current Day Severely Errored Seconds Receive
              2  Current Day Severely Errored Seconds Transmit
              4  Current Day Errored Seconds Receive
              8  Current Day Errored Seconds Receive
             16  Current Hour Severely Errored Seconds Receive
             32  Current Hour Severely Errored Seconds Transmit
             64  Current Hour Errored Seconds Receive
            128  Current Hour Errored Seconds Transmit
         Transmit is data from the customer towards the network.
         Receive is data from the network towards the Customer.
         This register is defined by Bellcore TR-TSY-000829.
         Indexed by Bank.ChannelUnit.Port.Address"
      ::= { frxUThrEntry 6 }

   frxThCond OBJECT-TYPE
      SYNTAX  INTEGER (0..255)
      ACCESS  read-write
      STATUS  mandatory
      DESCRIPTION
         "8-bit Threshold Condition register. One bit for each
         threshold in both directions.  Set to 1 if the threshold
         is exceeded and the corresponding bit in the frxAlertMask
         register is set to 0. Only set to 0 by the SNMP manager.
              1  Current Day Severely Errored Seconds Receive
              2  Current Day Severely Errored Seconds Transmit
              4  Current Day Errored Seconds Receive
              8  Current Day Errored Seconds Receive
             16  Current Hour Severely Errored Seconds Receive
             32  Current Hour Severely Errored Seconds Transmit
             64  Current Hour Errored Seconds Receive
            128  Current Hour Errored Seconds Transmit
         Receive is data from the customer towards the network.
         Transmit is data from the network towards the Customer.
         SNMP manager should reset bits to 0 after they it has been
         read by issuing a set using the inverted byte read. Sets
         will only reset bits where the set data is a 0.  Setting
         a bit to a 1 has no effect.  This register is defined
         by Bellcore TR-TSY-000829.  In the spirit of SNMP, the bits
         are inverted when read relative to that specification so
         the sense of the bits is the same for sets and gets.
         Indexed by Bank.ChannelUnit.Port.Address"
      ::= { frxUThrEntry 7 }

 -- frxUPerf Table
   frxUPerfTable OBJECT-TYPE
      SYNTAX  SEQUENCE OF FrxUPerfEntry
      ACCESS  not-accessible
      STATUS  mandatory
      DESCRIPTION
         "This table contains the U-interface Performance Monitoring
         Statistics for each of the subscriber loops in the system
         and for any BRITE cards extending those loops (e.g. using
         Subscriber Loop Carrier systems)  The table is indexed
         first using the Cisco 90 Series channel bank digroup number,
         then the channel unit number (1 to 24), then the port number
         (0, 1, etc) and finally the location number (the BRITE card
         number (1 to 6) or 7 for local parameters in the Cisco 90
         Series card). These registers are defined by Bellcore
         TR-TSY-000829."
      ::= { frxPort 5 }

   frxUPerfEntry OBJECT-TYPE
      SYNTAX  FrxUPerfEntry
      ACCESS  not-accessible
      STATUS  mandatory
      DESCRIPTION
         "A specific entry in the U-interface Performance Monitoring
         Statistics table.  There is one entry for each port on each
         Cisco 90 Series channel unit in the system and one entry for
         each BRITE card extending those ports.  There are no entries for
         unused banks or empty channel unit slots"
      INDEX   {
         frxBankIndex,
         frxChUIndex,
         frxPortIndex,
         frxPAddrIndex
      }
      ::= { frxUPerfTable 1 }

   FrxUPerfEntry ::= SEQUENCE {
      frxResetPM           INTEGER,
      frxPMtype            INTEGER,
      frxChEsTx            INTEGER,
      frxChEsRx            INTEGER,
      frxPhEsTx            INTEGER,
      frxPhEsRx            INTEGER,
      frxH2EsTx            INTEGER,
      frxH2EsRx            INTEGER,
      frxH3EsTx            INTEGER,
      frxH3EsRx            INTEGER,
      frxH4EsTx            INTEGER,
      frxH4EsRx            INTEGER,
      frxH5EsTx            INTEGER,
      frxH5EsRx            INTEGER,
      frxH6EsTx            INTEGER,
      frxH6EsRx            INTEGER,
      frxH7EsTx            INTEGER,
      frxH7EsRx            INTEGER,
      frxH8EsTx            INTEGER,
      frxH8EsRx            INTEGER,
      frxCdEsTx            INTEGER,
      frxCdEsRx            INTEGER,
      frxPdEsTx            INTEGER,
      frxPdEsRx            INTEGER,
      frxChSesTx           INTEGER,
      frxChSesRx           INTEGER,
      frxPhSesTx           INTEGER,
      frxPhSesRx           INTEGER,
      frxCdSesTx           INTEGER,
      frxCdSesRx           INTEGER,
      frxPdSesTx           INTEGER,
      frxPdSesRx           INTEGER,
      frxChBeTx            INTEGER,
      frxChBeRx            INTEGER,
      frxPhBeTx            INTEGER,
      frxPhBeRx            INTEGER
     }

   frxResetPM OBJECT-TYPE
      SYNTAX  INTEGER {
         normal(1),
         resetPM(2)
         }
      ACCESS  read-write
      STATUS  mandatory
      DESCRIPTION
         "Reset all of the performance monitoring statistics on the
         specified Cisco 90 Series channel unit or BRITE card.
         1=Normal. 2=Reset.  There is no need to set this register
         back to Normal after doing a reset."
      ::= { frxUPerfEntry 1 }

   frxPMtype OBJECT-TYPE
      SYNTAX  INTEGER {
         segmentedPM(1),
         pathPM(2)
         }
      ACCESS  read-only
      STATUS  mandatory
      DESCRIPTION
         "Determines if the Cisco 90 Series channel unit or the downstream
         BRITE cards is doing segmented or path performance monitoring as
         specified in Bellcore document TR-NWT-000397.  Only segmented
         performance monitoring should be used.  In segmented PM, CRC
         errors are counted on each segment of the loop, instead of
         over the entire path.  If no BRITE cards exist in the system,
         there is no difference between segmented and path PM
         1=Segmented.   2=Path."
      ::= { frxUPerfEntry 2 }

   frxChEsTx OBJECT-TYPE
      SYNTAX  INTEGER (0..3600)
      ACCESS  read-only
      STATUS  mandatory
      DESCRIPTION
         "Current Hour Errored Seconds - Transmit direction.
         Transmit is data from the network towards the customer.
         Errored Seconds are seconds in which one or more block
         errors occur.  These errors are measured at the physical
         link level (e.g. DSL CRC or BPV errors) and not at the
         frame relay level. This register is defined by Bellcore
         TR-TSY-000829. Indexed by Bank.ChannelUnit.Port.Address
         (note: DDS loops cannot detect transmit errors)"
      ::= { frxUPerfEntry 3 }

   frxChEsRx OBJECT-TYPE
      SYNTAX  INTEGER (0..3600)
      ACCESS  read-only
      STATUS  mandatory
      DESCRIPTION
         "Current Hour Errored Seconds - Receive direction.
         Receive is data from the customer towards the network.
         Errored Seconds are seconds in which one or more block
         errors occur.  These errors are measured at the physical
         link level (e.g. DSL CRC or BPV errors) and not at the
         frame relay level. This register is defined by Bellcore
         TR-TSY-000829. Indexed by Bank.ChannelUnit.Port.Address"
      ::= { frxUPerfEntry 4 }

   frxPhEsTx OBJECT-TYPE
      SYNTAX  INTEGER (0..3600)
      ACCESS  read-only
      STATUS  mandatory
      DESCRIPTION
         "Previous Hour Errored Seconds - Transmit direction.
         Transmit is data from the network towards the customer.
         Errored Seconds are seconds in which one or more block
         errors occur.  These errors are measured at the physical
         link level (e.g. DSL CRC or BPV errors) and not at the
         frame relay level. This register is defined by Bellcore
         TR-TSY-000829. Indexed by Bank.ChannelUnit.Port.Address
         (note: DDS loops cannot detect transmit errors)"
      ::= { frxUPerfEntry 5 }

   frxPhEsRx OBJECT-TYPE
      SYNTAX  INTEGER (0..3600)
      ACCESS  read-only
      STATUS  mandatory
      DESCRIPTION
         "Previous Hour Errored Seconds - Receive direction.
         Receive is data from the customer towards the network.
         Errored Seconds are seconds in which one or more block
         errors occur.  These errors are measured at the physical
         link level (e.g. DSL CRC or BPV errors) and not at the
         frame relay level. This register is defined by Bellcore
         TR-TSY-000829. Indexed by Bank.ChannelUnit.Port.Address"
      ::= { frxUPerfEntry 6 }

   frxH2EsTx OBJECT-TYPE
      SYNTAX  INTEGER (0..3600)
      ACCESS  read-only
      STATUS  mandatory
      DESCRIPTION
         "Errored Seconds 2 hours ago - Transmit direction.
         Transmit is data from the network towards the customer.
         Errored Seconds are seconds in which one or more block
         errors occur.  These errors are measured at the physical
         link level (e.g. DSL CRC or BPV errors) and not at the
         frame relay level. This register is defined by Bellcore
         TR-TSY-000829. Indexed by Bank.ChannelUnit.Port.Address
         (note: DDS loops cannot detect transmit errors)"
     ::= { frxUPerfEntry 7 }

   frxH2EsRx OBJECT-TYPE
      SYNTAX  INTEGER (0..3600)
      ACCESS  read-only
      STATUS  mandatory
      DESCRIPTION
         "Errored Seconds 2 hours ago - Receive direction.
         Receive is data from the customer towards the network.
         Errored Seconds are seconds in which one or more block
         errors occur.  These errors are measured at the physical
         link level (e.g. DSL CRC or BPV errors) and not at the
         frame relay level. This register is defined by Bellcore
         TR-TSY-000829. Indexed by Bank.ChannelUnit.Port.Address"
      ::= { frxUPerfEntry 8 }

   frxH3EsTx OBJECT-TYPE
      SYNTAX  INTEGER (0..3600)
      ACCESS  read-only
      STATUS  mandatory
      DESCRIPTION
         "Errored Seconds 3 hours ago - Transmit direction.
         Transmit is data from the network towards the customer.
         Errored Seconds are seconds in which one or more block
         errors occur.  These errors are measured at the physical
         link level (e.g. DSL CRC or BPV errors) and not at the
         frame relay level. This register is defined by Bellcore
         TR-TSY-000829. Indexed by Bank.ChannelUnit.Port.Address
         (note: DDS loops cannot detect transmit errors)"
      ::= { frxUPerfEntry 9 }

   frxH3EsRx OBJECT-TYPE
      SYNTAX  INTEGER (0..3600)
      ACCESS  read-only
      STATUS  mandatory
      DESCRIPTION
         "Errored Seconds 3 hours ago - Receive direction.
         Receive is data from the customer towards the network.
         Errored Seconds are seconds in which one or more block
         errors occur.  These errors are measured at the physical
         link level (e.g. DSL CRC or BPV errors) and not at the
         frame relay level. This register is defined by Bellcore
         TR-TSY-000829. Indexed by Bank.ChannelUnit.Port.Address"
      ::= { frxUPerfEntry 10 }

   frxH4EsTx OBJECT-TYPE
      SYNTAX  INTEGER (0..3600)
      ACCESS  read-only
      STATUS  mandatory
      DESCRIPTION
         "Errored Seconds 4 hours ago - Transmit direction.
         Transmit is data from the network towards the customer.
         Errored Seconds are seconds in which one or more block
         errors occur.  These errors are measured at the physical
         link level (e.g. DSL CRC or BPV errors) and not at the
         frame relay level. This register is defined by Bellcore
         TR-TSY-000829. Indexed by Bank.ChannelUnit.Port.Address
         (note: DDS loops cannot detect transmit errors)"
      ::= { frxUPerfEntry 11 }

   frxH4EsRx OBJECT-TYPE
      SYNTAX  INTEGER (0..3600)
      ACCESS  read-only
      STATUS  mandatory
      DESCRIPTION
         "Errored Seconds 4 hours ago - Receive direction.
         Receive is data from the customer towards the network.
         Errored Seconds are seconds in which one or more block
         errors occur.  These errors are measured at the physical
         link level (e.g. DSL CRC or BPV errors) and not at the
         frame relay level. This register is defined by Bellcore
         TR-TSY-000829. Indexed by Bank.ChannelUnit.Port.Address"
      ::= { frxUPerfEntry 12 }

   frxH5EsTx OBJECT-TYPE
      SYNTAX  INTEGER (0..3600)
      ACCESS  read-only
      STATUS  mandatory
      DESCRIPTION
         "Errored Seconds 5 hours ago - Transmit direction.
         Transmit is data from the network towards the customer.
         Errored Seconds are seconds in which one or more block
         errors occur.  These errors are measured at the physical
         link level (e.g. DSL CRC or BPV errors) and not at the
         frame relay level. This register is defined by Bellcore
         TR-TSY-000829. Indexed by Bank.ChannelUnit.Port.Address
         (note: DDS loops cannot detect transmit errors)"
      ::= { frxUPerfEntry 13 }

   frxH5EsRx OBJECT-TYPE
      SYNTAX  INTEGER (0..3600)
      ACCESS  read-only
      STATUS  mandatory
      DESCRIPTION
         "Errored Seconds 5 hours ago - Receive direction.
         Receive is data from the customer towards the network.
         Errored Seconds are seconds in which one or more block
         errors occur.  These errors are measured at the physical
         link level (e.g. DSL CRC or BPV errors) and not at the
         frame relay level. This register is defined by Bellcore
         TR-TSY-000829. Indexed by Bank.ChannelUnit.Port.Address"
      ::= { frxUPerfEntry 14 }

   frxH6EsTx OBJECT-TYPE
      SYNTAX  INTEGER (0..3600)
      ACCESS  read-only
      STATUS  mandatory
      DESCRIPTION
         "Errored Seconds 6 hours ago - Transmit direction.
         Transmit is data from the network towards the customer.
         Errored Seconds are seconds in which one or more block
         errors occur.  These errors are measured at the physical
         link level (e.g. DSL CRC or BPV errors) and not at the
         frame relay level. This register is defined by Bellcore
         TR-TSY-000829. Indexed by Bank.ChannelUnit.Port.Address
         (note: DDS loops cannot detect transmit errors)"
      ::= { frxUPerfEntry 15 }

   frxH6EsRx OBJECT-TYPE
      SYNTAX  INTEGER (0..3600)
      ACCESS  read-only
      STATUS  mandatory
      DESCRIPTION
         "Errored Seconds 6 hours ago - Receive direction.
         Receive is data from the customer towards the network.
         Errored Seconds are seconds in which one or more block
         errors occur.  These errors are measured at the physical
         link level (e.g. DSL CRC or BPV errors) and not at the
         frame relay level. This register is defined by Bellcore
         TR-TSY-000829. Indexed by Bank.ChannelUnit.Port.Address"
      ::= { frxUPerfEntry 16 }

   frxH7EsTx OBJECT-TYPE
      SYNTAX  INTEGER (0..3600)
      ACCESS  read-only
      STATUS  mandatory
      DESCRIPTION
         "Errored Seconds 7 hours ago - Transmit direction.
         Transmit is data from the network towards the customer.
         Errored Seconds are seconds in which one or more block
         errors occur.  These errors are measured at the physical
         link level (e.g. DSL CRC or BPV errors) and not at the
         frame relay level. This register is defined by Bellcore
         TR-TSY-000829. Indexed by Bank.ChannelUnit.Port.Address
         (note: DDS loops cannot detect transmit errors)"
      ::= { frxUPerfEntry 17 }

   frxH7EsRx OBJECT-TYPE
      SYNTAX  INTEGER (0..3600)
      ACCESS  read-only
      STATUS  mandatory
      DESCRIPTION
         "Errored Seconds 7 hours ago - Receive direction.
         Receive is data from the customer towards the network.
         Errored Seconds are seconds in which one or more block
         errors occur.  These errors are measured at the physical
         link level (e.g. DSL CRC or BPV errors) and not at the
         frame relay level. This register is defined by Bellcore
         TR-TSY-000829. Indexed by Bank.ChannelUnit.Port.Address"
      ::= { frxUPerfEntry 18 }

   frxH8EsTx OBJECT-TYPE
      SYNTAX  INTEGER (0..3600)
      ACCESS  read-only
      STATUS  mandatory
      DESCRIPTION
         "Errored Seconds 8 hours ago - Transmit direction.
         Transmit is data from the network towards the customer.
         Errored Seconds are seconds in which one or more block
         errors occur.  These errors are measured at the physical
         link level (e.g. DSL CRC or BPV errors) and not at the
         frame relay level. This register is defined by Bellcore
         TR-TSY-000829. Indexed by Bank.ChannelUnit.Port.Address
         (note: DDS loops cannot detect transmit errors)"
      ::= { frxUPerfEntry 19 }

   frxH8EsRx OBJECT-TYPE
      SYNTAX  INTEGER (0..3600)
      ACCESS  read-only
      STATUS  mandatory
      DESCRIPTION
         "Errored Seconds 8 hours ago - Receive direction.
         Receive is data from the customer towards the network.
         Errored Seconds are seconds in which one or more block
         errors occur.  These errors are measured at the physical
         link level (e.g. DSL CRC or BPV errors) and not at the
         frame relay level. This register is defined by Bellcore
         TR-TSY-000829. Indexed by Bank.ChannelUnit.Port.Address"
      ::= { frxUPerfEntry 20 }

   frxCdEsTx OBJECT-TYPE
      SYNTAX  INTEGER (0..65535)
      ACCESS  read-only
      STATUS  mandatory
      DESCRIPTION
         "Current Day Errored Seconds - Transmit direction.
         Transmit is data from the network towards the customer.
         Errored Seconds are seconds in which one or more block
         errors occur.  These errors are measured at the physical
         link level (e.g. DSL CRC or BPV errors) and not at the
         frame relay level. This register is defined by Bellcore
         TR-TSY-000829. Indexed by Bank.ChannelUnit.Port.Address
         (note: DDS loops cannot detect transmit errors)"
      ::= { frxUPerfEntry 21 }

   frxCdEsRx OBJECT-TYPE
      SYNTAX  INTEGER (0..65535)
      ACCESS  read-only
      STATUS  mandatory
      DESCRIPTION
         "Current Day Errored Seconds - Receive direction.
         Receive is data from the customer towards the network.
         Errored Seconds are seconds in which one or more block
         errors occur.  These errors are measured at the physical
         link level (e.g. DSL CRC or BPV errors) and not at the
         frame relay level. This register is defined by Bellcore
         TR-TSY-000829. Indexed by Bank.ChannelUnit.Port.Address"
      ::= { frxUPerfEntry 22 }

  frxPdEsTx OBJECT-TYPE
     SYNTAX  INTEGER (0..65535)
     ACCESS  read-only
     STATUS  mandatory
     DESCRIPTION
        "Previous Day Errored Seconds - Transmit direction.
         Transmit is data from the network towards the customer.
         Errored Seconds are seconds in which one or more block
         errors occur.  These errors are measured at the physical
         link level (e.g. DSL CRC or BPV errors) and not at the
         frame relay level. This register is defined by Bellcore
         TR-TSY-000829. Indexed by Bank.ChannelUnit.Port.Address
         (note: DDS loops cannot detect transmit errors)"
    ::= { frxUPerfEntry 23 }

   frxPdEsRx OBJECT-TYPE
      SYNTAX  INTEGER (0..65535)
      ACCESS  read-only
      STATUS  mandatory
      DESCRIPTION
         "Previous Day Errored Seconds - Receive direction.
         Receive is data from the customer towards the network.
         Errored Seconds are seconds in which one or more block
         errors occur.  These errors are measured at the physical
         link level (e.g. DSL CRC or BPV errors) and not at the
         frame relay level. This register is defined by Bellcore
         TR-TSY-000829. Indexed by Bank.ChannelUnit.Port.Address"
      ::= { frxUPerfEntry 24 }

   frxChSesTx OBJECT-TYPE
      SYNTAX  INTEGER (0..3600)
      ACCESS  read-only
      STATUS  mandatory
      DESCRIPTION
         "Current Hour Severely Errored Seconds - Transmit direction.
         Transmit is data from the network towards the customer.
         Severely Errored Seconds are seconds in which three or more
         block errors occur.  These errors are measured at the physical
         link level (e.g. DSL CRC or BPV errors) and not at the
         frame relay level. This register is defined by Bellcore
         TR-TSY-000829. Indexed by Bank.ChannelUnit.Port.Address
         (note: DDS loops cannot detect transmit errors)"
      ::= { frxUPerfEntry 25 }

   frxChSesRx OBJECT-TYPE
      SYNTAX  INTEGER (0..3600)
      ACCESS  read-only
      STATUS  mandatory
      DESCRIPTION
         "Current Hour Severely Errored Seconds - Receive direction.
         Receive is data from the customer towards the network.
         Severely Errored Seconds are seconds in which three or more
         block errors occur.  These errors are measured at the physical
         link level (e.g. DSL CRC or BPV errors) and not at the
         frame relay level. This register is defined by Bellcore
         TR-TSY-000829. Indexed by Bank.ChannelUnit.Port.Address"
      ::= { frxUPerfEntry 26 }

   frxPhSesTx OBJECT-TYPE
      SYNTAX  INTEGER (0..3600)
      ACCESS  read-only
      STATUS  mandatory
      DESCRIPTION
         "Previous Hour Severely Errored Seconds - Transmit direction.
         Transmit is data from the network towards the customer.
         Severely Errored Seconds are seconds in which three or more
         block errors occur.  These errors are measured at the physical
         link level (e.g. DSL CRC or BPV errors) and not at the
         frame relay level. This register is defined by Bellcore
         TR-TSY-000829. Indexed by Bank.ChannelUnit.Port.Address
         (note: DDS loops cannot detect transmit errors)"
      ::= { frxUPerfEntry 27 }

   frxPhSesRx OBJECT-TYPE
      SYNTAX  INTEGER (0..3600)
      ACCESS  read-only
      STATUS  mandatory
      DESCRIPTION
         "Previous Hour Severely Errored Seconds - Receive direction.
         Receive is data from the customer towards the network.
         Severely Errored Seconds are seconds in which three or more
         block errors occur.  These errors are measured at the physical
         link level (e.g. DSL CRC or BPV errors) and not at the
         frame relay level. This register is defined by Bellcore
         TR-TSY-000829. Indexed by Bank.ChannelUnit.Port.Address"
      ::= { frxUPerfEntry 28 }

   frxCdSesTx OBJECT-TYPE
      SYNTAX  INTEGER (0..65535)
      ACCESS  read-only
      STATUS  mandatory
      DESCRIPTION
         "Current Day Severely Errored Seconds - Transmit direction.
         Transmit is data from the network towards the customer.
         Severely Errored Seconds are seconds in which three or more
         block errors occur.  These errors are measured at the physical
         link level (e.g. DSL CRC or BPV errors) and not at the
         frame relay level. This register is defined by Bellcore
         TR-TSY-000829. Indexed by Bank.ChannelUnit.Port.Address"
      ::= { frxUPerfEntry 29 }

   frxCdSesRx OBJECT-TYPE
      SYNTAX  INTEGER (0..65535)
      ACCESS  read-only
      STATUS  mandatory
      DESCRIPTION
         "Current Day Severely Errored Seconds - Receive direction.
         Receive is data from the customer towards the network.
         Severely Errored Seconds are seconds in which three or more
         block errors occur.  These errors are measured at the physical
         link level (e.g. DSL CRC or BPV errors) and not at the
         frame relay level. This register is defined by Bellcore
         TR-TSY-000829. Indexed by Bank.ChannelUnit.Port.Address"
      ::= { frxUPerfEntry 30 }

   frxPdSesTx OBJECT-TYPE
      SYNTAX  INTEGER (0..65535)
      ACCESS  read-only
      STATUS  mandatory
      DESCRIPTION
         "Previous Day Severely Errored Seconds - Transmit direction.
         Transmit is data from the network towards the customer.
         Severely Errored Seconds are seconds in which three or more
         block errors occur.  These errors are measured at the physical
         link level (e.g. DSL CRC or BPV errors) and not at the
         frame relay level. This register is defined by Bellcore
         TR-TSY-000829. Indexed by Bank.ChannelUnit.Port.Address"
      ::= { frxUPerfEntry 31 }

   frxPdSesRx OBJECT-TYPE
      SYNTAX  INTEGER (0..65535)
      ACCESS  read-only
      STATUS  mandatory
      DESCRIPTION
         "Previous Day Severely Errored Seconds - Receive direction.
         Receive is data from the customer towards the network.
         Severely Errored Seconds are seconds in which three or more
         block errors occur.  These errors are measured at the physical
         link level (e.g. DSL CRC or BPV errors) and not at the
         frame relay level. This register is defined by Bellcore
         TR-TSY-000829. Indexed by Bank.ChannelUnit.Port.Address"
      ::= { frxUPerfEntry 32 }

   frxChBeTx OBJECT-TYPE
      SYNTAX  INTEGER (0..65535)
      ACCESS  read-only
      STATUS  mandatory
      DESCRIPTION
         "Current Hour Block Errors - Transmit direction.
         Transmit is data from the network towards the customer.
         Block errors are 12 millisecond time periods in which a
         physical link level (e.g. DSL CRC or BPV) error occurs.
         These errors are not the same as frame relay level errors.
         This register is defined by Bellcore TR-TSY-000829.
         Indexed by Bank.ChannelUnit.Port.Address"
      ::= { frxUPerfEntry 33 }

   frxChBeRx OBJECT-TYPE
      SYNTAX  INTEGER (0..65535)
      ACCESS  read-only
      STATUS  mandatory
      DESCRIPTION
         "Current Hour Block Errors - Receive direction.
         Receive is data from the customer towards the network.
         Block errors are 12 millisecond time periods in which a
         physical link level (e.g. DSL CRC or BPV) error occurs.
         These errors are not the same as frame relay level errors.
         This register is defined by Bellcore TR-TSY-000829.
         Indexed by Bank.ChannelUnit.Port.Address"
      ::= { frxUPerfEntry 34 }

   frxPhBeTx OBJECT-TYPE
      SYNTAX  INTEGER (0..65535)
      ACCESS  read-only
      STATUS  mandatory
      DESCRIPTION
         "Previous Hour Block Errors - Transmit direction.
         Transmit is data from the network towards the customer.
         Block errors are 12 millisecond time periods in which a
         physical link level (e.g. DSL CRC or BPV) error occurs.
         These errors are not the same as frame relay level errors.
         This register is defined by Bellcore TR-TSY-000829.
         Indexed by Bank.ChannelUnit.Port.Address"
      ::= { frxUPerfEntry 35 }

   frxPhBeRx OBJECT-TYPE
      SYNTAX  INTEGER (0..65535)
      ACCESS  read-only
      STATUS  mandatory
      DESCRIPTION
         "Previous Hour Block Errors - Receive direction.
         Receive is data from the customer towards the network.
         Block errors are 12 millisecond time periods in which a
         physical link level (e.g. DSL CRC or BPV) error occurs.
         These errors are not the same as frame relay level errors.
         This register is defined by Bellcore TR-TSY-000829.
         Indexed by Bank.ChannelUnit.Port.Address"
      ::= { frxUPerfEntry 36 }

 -- frx Traps
   frxDownloadTrap TRAP-TYPE
      ENTERPRISE frMux
      VARIABLES  { frxBankIndex, frxChUIndex }
      DESCRIPTION
         "This trap is sent if the Download Config pushbutton
         on the channel unit faceplate is pushed and frxDefaultTrap
         is set to 1."
      ::= 1

   frxUPerfTrap TRAP-TYPE
      ENTERPRISE frMux
      VARIABLES  { frxBankIndex, frxChUIndex }
      DESCRIPTION
         "This trap is sent if a performance monitoring threshold
         on a channel unit or a BRITE card is exceeded and the
         corresponding bit in the frxAlertMask is enabled and
         frxUPerfTrapEnable is enabled.  The manager should read
         and clear all of the threshold condition registers
         for the specified channel unit to enable the trap to
         be sent again."
      ::= 2

   frxInsertChUTrap TRAP-TYPE
      ENTERPRISE frMux
      VARIABLES  { frxBankIndex, frxChUIndex }
      DESCRIPTION
         "This trap is sent when the channel unit is inserted."
      ::= 3 

   frxRemoveChUTrap TRAP-TYPE
      ENTERPRISE frMux
      VARIABLES  { frxBankIndex, frxChUIndex }
      DESCRIPTION
         "This trap is sent when the channel unit is removed."
      ::= 4 

   frxDConfigFailed TRAP-TYPE
      ENTERPRISE frMux
      VARIABLES  { frxBankIndex, frxChUIndex }
      DESCRIPTION
         "This trap is sent if downloading configuration data
         to a channel unit fails."
      ::= 5

END
