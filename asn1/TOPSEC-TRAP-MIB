-- Copyright (c) 1996-2007, Topsec, Inc.
-- All rights reserved.

TOPSEC-TRAP-MIB DEFINITIONS ::= BEGIN

IMPORTS 
	  MODULE-IDENTITY, NOTIFICATION-TYPE, OBJECT-TYPE
        FROM SNMPv2-SMI
    DisplayString
        FROM SNMPv2-TC
    TRAP-TYPE
        FROM RFC-1215
 		topsec
				FROM TOS-MIB       
        ;
    
    
topsecVar MODULE-IDENTITY
	    LAST-UPDATED "07-8-20" 
	    ORGANIZATION "TOPSEC"
	    CONTACT-INFO
	            " Topsec Beijing
	              China
	              E-mail: support@topsec.com.cn "
	    DESCRIPTION
	            "The TRAP MIB module for SNMP TRAP of Topsec Operating System Security Product, independent of the specific encapsulation scheme in use."
	    REVISION     "07-08-20" 
	    DESCRIPTION
	            "Initial version."
	    ::= {topsec 4 }	    

topsecTrapInfoDesc OBJECT-TYPE
    SYNTAX        DisplayString (SIZE(0..255))
    MAX-ACCESS    accessible-for-notify
    STATUS        current
    DESCRIPTION
        "The textual description of the alarm"
    ::= { topsecVar 2 }
    
topsecTrapMsgDesc OBJECT-TYPE
    SYNTAX        DisplayString (SIZE(0..255))
    MAX-ACCESS    accessible-for-notify
    STATUS        current
    DESCRIPTION
        "The textual description of the msg from alarm"
    ::= { topsecTrapInfoDesc 1 }
    
topsecTrapPriDesc OBJECT-TYPE
    SYNTAX        DisplayString (SIZE(0..255))
    MAX-ACCESS    accessible-for-notify
    STATUS        current
    DESCRIPTION
        "The textual description of the priority of the alarm"
    ::= { topsecTrapInfoDesc 2 }
    
topsecTrapBodyDesc OBJECT-TYPE
    SYNTAX        DisplayString (SIZE(0..255))
    MAX-ACCESS    accessible-for-notify
    STATUS        current
    DESCRIPTION
        "The textual description of the message body of the alarm"
    ::= { topsecTrapInfoDesc 3 }
    
topsecTrapRecorDesc OBJECT-TYPE
    SYNTAX        DisplayString (SIZE(0..255))
    MAX-ACCESS    accessible-for-notify
    STATUS        current
    DESCRIPTION
        "The textual description of the Recorder of func module which send the alarm"
    ::= { topsecTrapInfoDesc 4 }
    
topsecTrapOpDesc OBJECT-TYPE
    SYNTAX        DisplayString (SIZE(0..255))
    MAX-ACCESS    accessible-for-notify
    STATUS        current
    DESCRIPTION
        "The textual description of the operation which cause the alarm"
    ::= { topsecTrapInfoDesc 5 }
    
topsecTrapSubtypeDesc OBJECT-TYPE
    SYNTAX        DisplayString (SIZE(0..255))
    MAX-ACCESS    accessible-for-notify
    STATUS        current
    DESCRIPTION
        "The textual description of the subtype which the alarm is "
    ::= { topsecTrapInfoDesc 6 }
    
        
   --enterprise specific type define (beta)
-- tosEnterpriseTrap OBJECT IDENTIFIER ::= { enterprises  6 }

topsecProduct OBJECT IDENTIFIER ::= { topsec 1}

topsecTos OBJECT IDENTIFIER ::= { topsecProduct 4}

TOSMGMT_SPECIFIC  TRAP-TYPE
		ENTERPRISE  topsecTos
    VARIABLES   {topsecMsgDesc}
    DESCRIPTION
                          "mgmt trap"
              ::= 11
              
TOSSYSTEM_SPECIFIC  TRAP-TYPE
		ENTERPRISE  topsecTos
    VARIABLES   {topsecMsgDesc}
    DESCRIPTION
                          "system trap"
              ::= 12
              
TOSSECURE_SPECIFIC  TRAP-TYPE
		ENTERPRISE  topsecTos
    VARIABLES   {topsecMsgDesc}
    DESCRIPTION
                          "secure trap"
              ::= 13
              
TOSPOLICY_SPECIFIC  TRAP-TYPE
		ENTERPRISE  topsecTos
    VARIABLES   {topsecMsgDesc}
    DESCRIPTION
                          "policy trap"
              ::= 14
TOSCOMMU_SPECIFIC   TRAP-TYPE
		ENTERPRISE  topsecTos
    VARIABLES   {topsecTrapSubtypeDesc,topsecMsgDesc,topsecTrapRecorDesc,topsecTrapOpDesc}
    DESCRIPTION
                          "commucation trap include vpn commu"
              ::= 15
              
TOSHARDWARE_SPECIFIC  TRAP-TYPE
		ENTERPRISE  topsecTos
    VARIABLES   {topsecMsgDesc,topsecTrapRecorDesc,topsecTrapOpDesc}
    DESCRIPTION
                          "hardware trap"
              ::= 16
           
TOSRECOVER_SPECIFIC  TRAP-TYPE
		ENTERPRISE  topsecTos
    VARIABLES   {topsecMsgDesc}
    DESCRIPTION
                          "recover trap"
              ::= 17
              
TOSOTHER_SPECIFIC  TRAP-TYPE
		ENTERPRISE  topsecTos
    VARIABLES   {topsecMsgDesc}
    DESCRIPTION
                          "other trap"
              ::= 18
         
TOSTEST_SPECIFIC  TRAP-TYPE
		ENTERPRISE  topsecTos
    VARIABLES   {topsecMsgDesc}
    DESCRIPTION
                          "a test trap"
              ::= 20
              

    END
