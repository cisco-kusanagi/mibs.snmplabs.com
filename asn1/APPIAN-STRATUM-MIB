--
--  Title:  Appian Stratum Clock MIB
--
--  Dated:  08/22/2000
--  Author: D. Theriault
--
--  Description:
--
--  This MIB file contains the definitions and support for the Appian
--  Optical Services Access Platform(s).
-- 
--  The Stratum Clock MIB allows configuration and status for the bits
--  Clock module which is optional for an OSAP-4800 chassis.
--
--
APPIAN-STRATUM-MIB DEFINITIONS ::= BEGIN

    IMPORTS
        acOsap, AcOpStatus, AcNodeId             FROM APPIAN-SMI-MIB

        acChassisCurrentTime, acChassisRingId    FROM APPIAN-CHASSIS-MIB

        MODULE-IDENTITY,OBJECT-TYPE, 
        NOTIFICATION-TYPE                        FROM SNMPv2-SMI

        TruthValue                               FROM SNMPv2-TC;


acStratum
    MODULE-IDENTITY
        LAST-UPDATED        "0008220000Z"
        ORGANIZATION        "Appian Communications, Inc."
        CONTACT-INFO        "Brian Johnson"

        DESCRIPTION 
        "Appian Communications Stratum MIB contain the definitions for 
        the configuration and control of Stratum Clock module hardware 
        information and status." 

        REVISION            "0008220000Z" 
        
        DESCRIPTION         "Draft MIB for Engineering use only."

    ::= { acOsap 9 }


--
-- Stratum Clock MIB starts
--

acStratumTable   OBJECT-TYPE
    SYNTAX  SEQUENCE OF AcStratumEntry
    MAX-ACCESS  not-accessible
    STATUS  current
    DESCRIPTION
    "This table contains two rows for access and control of the Stratum-3
    clock modules."

    ::= { acStratum 1 }

acStratumEntry   OBJECT-TYPE
    SYNTAX  AcStratumEntry
    MAX-ACCESS  not-accessible
    STATUS  current
    DESCRIPTION
    "A row within the Stratum table containing access control and status
    information relating to the operation of the Stratum-3 clock module."
    
    INDEX   { acStratumNodeId }

    ::= { acStratumTable 1 }

    AcStratumEntry ::=
        SEQUENCE {
            acStratumNodeId                      AcNodeId,
            acStratumClockSource                 INTEGER,
            acStratumOpStatusModuleA             AcOpStatus,
            acStratumOpStatusModuleB             AcOpStatus,
            acStratumAlarmStatusModuleA          INTEGER,
            acStratumAlarmStatusModuleB          INTEGER,
            acStratumCurrentClockSourceModuleA   INTEGER,
            acStratumCurrentClockSourceModuleB   INTEGER,
            acStratumLockoutReference            INTEGER,
            acStratumManualSwitch                INTEGER,
            acStratumForcedSwitch                INTEGER,
            acStratumRevertiveRefSwitchEnabled   TruthValue,
            acStratumClearAlarms                 TruthValue,
            acStratumLineTimingPortSlot1         INTEGER,
            acStratumLineTimingPortSlot2         INTEGER,
            acStratumBITSFramingType             INTEGER,
	    acStratumCurrentClockSourceSystem    INTEGER
        }


acStratumNodeId    OBJECT-TYPE
    SYNTAX      AcNodeId
    MAX-ACCESS  accessible-for-notify
    STATUS      current
    DESCRIPTION
    "The unique node identification number representing a chassis within a
    ring of OSAP's."

    ::= { acStratumEntry 1 }

acStratumClockSource  OBJECT-TYPE
    SYNTAX  INTEGER {
                internal(1),
                bits(2),
                line(3)
                }
    MAX-ACCESS  read-write
    STATUS  current
    DESCRIPTION
    "This attribute determines the clock source."
    DEFVAL { internal }

    ::= { acStratumEntry 2 }

acStratumOpStatusModuleA  OBJECT-TYPE
    SYNTAX  AcOpStatus
    MAX-ACCESS  read-only
    STATUS      current
    DESCRIPTION
    "This field indicates the current operational status for the clock card
     in slot 16, module A . Only the following values are applicable to the 
     module: operational, offline, initializing, selfTesting, upgrading, 
     standby, shuttingDown, failed, and hw not present."

    ::= { acStratumEntry 3 }

acStratumOpStatusModuleB  OBJECT-TYPE
    SYNTAX  AcOpStatus
    MAX-ACCESS  read-only
    STATUS      current
    DESCRIPTION
    "This field indicates the current operational status for the clock card
     in slot 16, module B . Only the following values are applicable to the 
     module: operational, offline, initializing, selfTesting, upgrading, 
     standby, shuttingDown, failed, and hw not present."

    ::= { acStratumEntry 4 }


acStratumAlarmStatusModuleA  OBJECT-TYPE
    SYNTAX  INTEGER (1..6)
    MAX-ACCESS  read-only
    STATUS  current
    DESCRIPTION
    "This attribute contains the current status of the clock alarms.
    The acStratumAlarmStatus is a bit map represented as a sum.  Normal 
    may only be set if and only if no other alarms are set.

    The various bit positions are:

      1   normal        No alarm present
      2   los           Loss of Signal 
      4   lof           Loss of Frame   "

    ::= { acStratumEntry 5 }

acStratumAlarmStatusModuleB  OBJECT-TYPE
    SYNTAX  INTEGER (1..6)
    MAX-ACCESS  read-only
    STATUS  current
    DESCRIPTION
    "This attribute contains the current status of the clock alarms.
    The acStratumAlarmStatus is a bit map represented as a sum.  Normal 
    must be set if and oly if no other flash is set.

    The various bit positions are:

      1   normal        No alarm present
      2   los           Loss of Signal 
      4   lof           Loss of Frame   "

    ::= { acStratumEntry 6 }

acStratumCurrentClockSourceModuleA  OBJECT-TYPE
    SYNTAX  INTEGER {
                unknown(0),
                none(1),
                bits-a(2),
                bits-b(3),
                line-slot1-port1(4),
                line-slot1-port2(5),
                line-slot2-port1(6),
                line-slot2-port2(7),
                holdover(8),
                internal(9)
                }
    MAX-ACCESS  read-only
    STATUS  current
    DESCRIPTION
    "This attribute displays the current source that the clock card is 
     selecting."

    ::= { acStratumEntry 7 }

acStratumCurrentClockSourceModuleB  OBJECT-TYPE
    SYNTAX  INTEGER {
                unknown(0),
                none(1),
                bits-a(2),
                bits-b(3),
                line-slot1-port1(4),
                line-slot1-port2(5),
                line-slot2-port1(6),
                line-slot2-port2(7),
                holdover(8),
                internal(9)
                }
    MAX-ACCESS  read-only
    STATUS  current
    DESCRIPTION
    "This attribute displays the current source that the clock card is 
     selecting."

    ::= { acStratumEntry 8 }

acStratumLockoutReference  OBJECT-TYPE
    SYNTAX  INTEGER (0..63)
    MAX-ACCESS  read-write
    STATUS  current
    DESCRIPTION
    "This attribute is a bit mask of clock references that should be
     locked out from selection for the clock source.  None can only
     be selected when no other lockout references are selected.

    The various bit positions are:

      0   none          No clock references are locked out from selection.
      1   bits-a        BITS source from clock module A is locked out.
      2   bits-b        BITS source from clock module B is locked out.
      4   line-slot1    LINE timing source from SONET slot 1 is locked out.
      8   line-slot2    LINE timing source from SONET slot 2 is locked out.
      16  holdover-a    Holdover from clock module A is locked out.
      32  holdover-b    Holdover from clock module B is locked out.  "
    DEFVAL { 0 }

    ::= { acStratumEntry 9 }

acStratumManualSwitch  OBJECT-TYPE
    SYNTAX  INTEGER {
                none(0),
                bits-a(1),
                bits-b(2),
                line-slot1(3),
                line-slot2(4)
                }
    MAX-ACCESS  read-write
    STATUS  current
    DESCRIPTION
    "This attribute will manually switch the clock references. If the 
     clock reference does not exist, is locked out, or the reference has
     failed, the switch will not take place." 
    DEFVAL { 0 }

    ::= { acStratumEntry 10 }

acStratumForcedSwitch  OBJECT-TYPE
    SYNTAX  INTEGER {
                none(0),
                bits-a(1),
                bits-b(2),
                line-slot1(3),
                line-slot2(4)
                }
    MAX-ACCESS  read-write
    STATUS  current
    DESCRIPTION
    "This attribute will force switch the clock references. If the 
     clock reference does not exist or is locked out, the switch will 
     not take place."
    DEFVAL { 0 }

    ::= { acStratumEntry 11 }

acStratumRevertiveRefSwitchEnabled OBJECT-TYPE
    SYNTAX  TruthValue
    MAX-ACCESS  read-write
    STATUS  current
    DESCRIPTION
    "Setting of this attribute to true(1) will the reference to revert
     back to the original reference when that reference become ready again."
    DEFVAL { false }

    ::= { acStratumEntry 12 }

acStratumClearAlarms  OBJECT-TYPE
    SYNTAX  TruthValue
    MAX-ACCESS  read-write
    STATUS  current
    DESCRIPTION
    "Setting of this attribute to true(1) will cause the alarm contacts 
     to clear.  Reading this attribute will always return false."
    DEFVAL { false }

    ::= { acStratumEntry 13 }

acStratumLineTimingPortSlot1  OBJECT-TYPE
    SYNTAX  INTEGER (1..2)
    MAX-ACCESS  read-write
    STATUS  current
    DESCRIPTION
    "When configured for line timing, this value describes which port
     on the SONET card will be used to drive the line.  This value is
     not applicable when not configured for line timing."
    DEFVAL { 1 }

    ::= { acStratumEntry 14 }

acStratumLineTimingPortSlot2  OBJECT-TYPE
    SYNTAX  INTEGER (1..2)
    MAX-ACCESS  read-write
    STATUS  current
    DESCRIPTION
    "When configured for line timing, this value describes which port
     on the SONET card will be used to drive the line.  This value is
     not applicable when not configured for line timing."
    DEFVAL { 1 }

    ::= { acStratumEntry 15 }

acStratumBITSFramingType  OBJECT-TYPE
    SYNTAX  INTEGER {
                esf(1),
                d4(2)
            }
    MAX-ACCESS  read-write
    STATUS  current
    DESCRIPTION
    "When configured for BITS timing, this value describes the type
     of framing that will be used on the BITS interface.  This value is
     not applicable when not configured for BITS timing."
    DEFVAL { esf }

    ::= { acStratumEntry 16 }

acStratumCurrentClockSourceSystem  OBJECT-TYPE
    SYNTAX  INTEGER {
                unknown(0),
                bits-a(1),
                bits-b(2),
                line-slot1-port1(3),
                line-slot1-port2(4),
                line-slot2-port1(5),
                line-slot2-port2(6),
                holdover-clock-a(7),
                holdover-clock-b(8),
                internal-clock-a(9),
                internal-clock-b(10),
                internal-sonet-slot1(11),
                internal-sonet-slot2(12)
                }
    MAX-ACCESS  read-only
    STATUS  current
    DESCRIPTION
    "This attribute displays the current clock source that the system is 
     selecting."

    ::= { acStratumEntry 17 }
-- 

-- 
-- Stratum MIB Trap Definitions
--
--
acStratumTraps   OBJECT IDENTIFIER ::= { acStratum 0 }

acStratumFailedModuleATrap  NOTIFICATION-TYPE
    OBJECTS { 
        acChassisCurrentTime, acChassisRingId,
        acStratumNodeId
    } 
    STATUS  current
    DESCRIPTION
    "The stratum clock module failed."
    
    ::= { acStratumTraps 1 }
    
acStratumFailedModuleBTrap  NOTIFICATION-TYPE
    OBJECTS { 
        acChassisCurrentTime, acChassisRingId,
        acStratumNodeId
    } 
    STATUS  current
    DESCRIPTION
    "The stratum clock module failed."
    
    ::= { acStratumTraps 2 }

acStratumClockFailureModuleATrap  NOTIFICATION-TYPE
    OBJECTS { 
        acChassisCurrentTime, acChassisRingId,
        acStratumNodeId, 
        acStratumAlarmStatusModuleA 
    } 
    STATUS  current
    DESCRIPTION
    "Stratum clock agent has detected a clock timing failure."
    
    ::= { acStratumTraps 3 }

acStratumClockFailureModuleBTrap  NOTIFICATION-TYPE
    OBJECTS { 
        acChassisCurrentTime, acChassisRingId,
        acStratumNodeId, 
        acStratumAlarmStatusModuleB 
    } 
    STATUS  current
    DESCRIPTION
    "Stratum clock agent has detected a clock timing failure."
    
    ::= { acStratumTraps 4 }

acStratumRemovalModuleATrap  NOTIFICATION-TYPE
    OBJECTS { 
        acChassisCurrentTime, acChassisRingId,
        acStratumNodeId
    } 
    STATUS  current
    DESCRIPTION
    "The stratum clock module has been removed from the system."
    
    ::= { acStratumTraps 5 }

acStratumRemovalModuleBTrap  NOTIFICATION-TYPE
    OBJECTS { 
        acChassisCurrentTime, acChassisRingId,
        acStratumNodeId
    } 
    STATUS  current
    DESCRIPTION
    "The stratum clock module has been removed from the system."
    
    ::= { acStratumTraps 6 }

acStratumInsertedModuleATrap  NOTIFICATION-TYPE
    OBJECTS { 
        acChassisCurrentTime, acChassisRingId,
        acStratumNodeId
    } 
    STATUS  current
    DESCRIPTION
    "A stratum clock module has been inserted into the system."
    
    ::= { acStratumTraps 7 }

acStratumInsertedModuleBTrap  NOTIFICATION-TYPE
    OBJECTS { 
        acChassisCurrentTime, acChassisRingId,
        acStratumNodeId
    } 
    STATUS  current
    DESCRIPTION
    "A stratum clock module has been inserted into the system."
    
    ::= { acStratumTraps 8 }

acStratumClockModuleAOk  NOTIFICATION-TYPE
    OBJECTS { 
        acChassisCurrentTime, acChassisRingId,
        acStratumNodeId, 
        acStratumAlarmStatusModuleA
    } 
    STATUS  current
    DESCRIPTION
    "Stratum clock agent has recovered clock timing."
    
    ::= { acStratumTraps 9 }
    
acStratumClockModuleBOk  NOTIFICATION-TYPE
    OBJECTS { 
        acChassisCurrentTime, acChassisRingId,
        acStratumNodeId, 
        acStratumAlarmStatusModuleB
    } 
    STATUS  current
    DESCRIPTION
    "Stratum clock agent has recovered clock timing."
    
    ::= { acStratumTraps 10 }

acStratumSystemClockSourceChange NOTIFICATION-TYPE
    OBJECTS { 
        acChassisCurrentTime, acChassisRingId,
        acStratumNodeId, 
        acStratumCurrentClockSourceSystem
    } 
    STATUS  current
    DESCRIPTION
    "Stratum clock source has changed to acStratumCurrentClockSourceSystem."
    
    ::= { acStratumTraps 11 }

END
