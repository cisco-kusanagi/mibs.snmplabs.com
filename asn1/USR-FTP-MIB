USR-FTP-MIB DEFINITIONS ::= BEGIN

	IMPORTS
          OBJECT-TYPE
                  FROM RFC-1212
          DisplayString FROM RFC1213-MIB
			 usrFtp, UsrConfigStatus
                  FROM USR-DEFINITIONS-MIB;


   -- textual conventions
   -- 
   -- textual conventions are like pre-processor macro in 'C'
   --        (i.e. #define statements)
   -- Use them to define your own 'datatypes'

   -- memory size, expressed in units of 1024bytes


	-- A sample Table definiton.

	usrFtpConfigFileName OBJECT-TYPE
		SYNTAX      DisplayString
		ACCESS      read-write
		STATUS      mandatory
		DESCRIPTION		
		  "The name of a ConfigFile to read/write permanent database records.
		   If the value of this object is an empty string, then the
		   FTP client  process uses the default name `@file://FtpProcess.cfg'. "
	::= { usrFtp 1 }

	usrFtpCFMStatusFlag  OBJECT-TYPE
	 	SYNTAX	  UsrConfigStatus
		ACCESS      read-write
		STATUS      mandatory
		DESCRIPTION
		  "Setting the value of this object to `save' causes the values
		   of the FTP Group to be written out to the current config
		   file, which is stored in the usrFtpConfigFileName object.
		   While the new ConfigFile is being written, the FTP process
		   will set the value of this flag to `saving''. Any
		   attempts to set the value while it is not `normal'
		   (i.e. the file is currently being written to the
		   ConfigFile) while result in a badValue error being
		   returned. Setting the value to `normal' will result in no
		   action."
	::= { usrFtp 2 }


     -- FTP Client Request Table

     usrFtpClientRequestTable OBJECT-TYPE
          SYNTAX  SEQUENCE OF UsrFtpClientRequestEntry
          ACCESS  not-accessible
          STATUS  mandatory
          DESCRIPTION
            "The FTP Client Request Table"
     ::= { usrFtp 3 }

     usrFtpClientRequestEntry OBJECT-TYPE
          SYNTAX  UsrFtpClientRequestEntry
          ACCESS  not-accessible
          STATUS  mandatory
          DESCRIPTION
            ""
         INDEX   { usrFtpClientRequestFileName }
     ::= { usrFtpClientRequestTable 1 }

     UsrFtpClientRequestEntry ::=
          SEQUENCE {
               usrFtpClientRequestFileName
                    OCTET STRING,
               usrFtpClientRequestServer
                    OCTET STRING,
               usrFtpClientRequestAction
                    INTEGER,
               usrFtpClientRequestStatus
                    INTEGER,
               usrFtpClientRequestErrorString
                    DisplayString,
               usrFtpClientRequestPath
                    OCTET STRING,
               usrFtpClientRequestLoginName
                    OCTET STRING,
               usrFtpClientRequestPassword
                    OCTET STRING
         }

     usrFtpClientRequestFileName OBJECT-TYPE
         	SYNTAX  OCTET STRING
         	ACCESS  not-accessible
         	STATUS  mandatory
         	DESCRIPTION
            "The name of the file which will either be requested from or
             sent to the FTP server."
     ::= { usrFtpClientRequestEntry 1 }

     usrFtpClientRequestServer OBJECT-TYPE
          SYNTAX  OCTET STRING
          ACCESS  read-write
          STATUS  mandatory
          DESCRIPTION
            "The name or IP address of the FTP server."
          --CONFIGURABLE
         ::= { usrFtpClientRequestEntry 2 }

     usrFtpClientRequestAction OBJECT-TYPE
          SYNTAX  INTEGER {
                    get(1),
                    put(2)
                    }
          ACCESS  read-write
          STATUS  mandatory
          DESCRIPTION
            "The type of request that will be sent to the FTP server."
          --CONFIGURABLE
         ::= { usrFtpClientRequestEntry 3 }

     usrFtpClientRequestStatus OBJECT-TYPE
          SYNTAX  INTEGER {
                    normal(1),
                    enable(2),
                    getting(3),
                    putting(4),
                    delete(5),
                    error(6)
                    }
          ACCESS  read-write
          STATUS  mandatory
          DESCRIPTION
            "The status of this row. Setting this object to enable(2)
             will cause a request (defined by usrFtpClientRequestAction)
             to be sent to the FTP server. Depending on the type of
             request, this object will then be set to either getting(3)
             or putting(4). When the request is completed, this object
             will be set to normal(1) which indicates success. If an
             error occurred, this object will be set to error(5) and
             the usrFtpClientRequestErrorString will indicate the
             type of error."
         ::= { usrFtpClientRequestEntry 7 }

     usrFtpClientRequestErrorString OBJECT-TYPE
          SYNTAX  DisplayString
          ACCESS  read-only
          STATUS  mandatory
          DESCRIPTION
            "This object will indicate what type of error occurred when
             the object usrFtpClientRequestStatus is set to error(5)."
         ::= { usrFtpClientRequestEntry 8 }

     usrFtpClientRequestPath OBJECT-TYPE
          SYNTAX  OCTET STRING
          ACCESS  read-write
          STATUS  mandatory
          DESCRIPTION
            "The path name of the source file being requested from or
             sent to the FTP server."
          --CONFIGURABLE
         ::= { usrFtpClientRequestEntry 9 }

     usrFtpClientRequestLoginName OBJECT-TYPE
          SYNTAX  OCTET STRING
          ACCESS  read-write
          STATUS  mandatory
          DESCRIPTION
            "The User's Login Name on the FTP Server."
          --CONFIGURABLE
         ::= { usrFtpClientRequestEntry 10 }

     usrFtpClientRequestPassword OBJECT-TYPE
          SYNTAX  OCTET STRING
          ACCESS  read-write
          STATUS  mandatory
          DESCRIPTION
            "The User's password on the FTP Server."
          --CONFIGURABLE
         ::= { usrFtpClientRequestEntry 11 }
END         -- End usr TFTP MIB definitions
