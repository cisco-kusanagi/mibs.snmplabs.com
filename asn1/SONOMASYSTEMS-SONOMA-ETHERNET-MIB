-- |**********************************************************************|
 -- | Copyright 1998 - Sonoma Systems, Inc. Marina del Rey, CA 90292       |
 -- |    Unpublished software - All rights reserved.                       |
 -- |                                                                      |
 -- | The information in this software is subject to change without notice |
 -- | and should not be construed as a commitment by Sonoma Systems, Inc.  |
 -- |                                                                      |
 -- | Sonoma Systems, Inc. assumes no responsibility for the use or        |
 -- | reliability of its software on equipment which is not supplied by    |
 -- | Sonoma Systems, Inc.                                                 |
 -- |                                                                      |
 -- | This software is furnished under a license and may be copied only    |
 -- | under the terms of that license and with the inclusion of this       |
 -- | notice. This software, or any other copies thereof, may not be       |
 -- | provided or otherwise made available to any other person except to   |
 -- | one who agrees to these license terms. Title to and ownership of the |
 -- | software shall at all times remain with Sonoma Systems, Inc.         |
 -- |**********************************************************************|
 --
 -- Sonoma Systems Inc.,
 -- 4640 Admiralty Way, Suite #600,
 -- Marina Del Rey,
 -- California 90292-6695.
 --
 -- Web : www.sonoma-systems.com
 -- Phone:  310.827.8000
 --
 -- NAME        : smcmib.def
 --
 -- DESCRIPTION : 
 --
 -- This is the MIB for the SMC adapter ethernet group.
 -- The objects in this group are only applicable to the 
 -- SMC 9332 and 8432 family of adapters supported on the
 -- Sonoma Access.
 --
 -- ARCHIVE : $Archive:   M:\pvcs\pvcsproj\sonoma3\src\mib\smcmib.dev  $
 -- REVISION: $Revision:   1.5  $
 -- AUTHOR  : $Author:   PCaswell  $
 -- DATE    : $Date:   Jan 05 1999 16:35:24  $

      SONOMASYSTEMS-SONOMA-ETHERNET-MIB     DEFINITIONS ::= BEGIN
 
      IMPORTS
         Counter
         FROM RFC1155-SMI
         OBJECT-TYPE
         FROM RFC-1212
         sonomaLAN 
         FROM SONOMASYSTEMS-SONOMA-MIB;

   -- Hierarchy for these groups
    -- enterprises     OBJECT IDENTIFIER ::= { private 4 }
    -- sonomaSystems   OBJECT IDENTIFIER ::= {  enterprises 2926 }
    -- sonomaSeries    OBJECT IDENTIFIER ::= { sonomaSystems 25 }
    -- sonomaLAN       OBJECT IDENTIFIER ::= { sonomaSeries 5 }
    sonomaEthernet  OBJECT IDENTIFIER ::= { sonomaLAN 1 }
    ethernetAdapterGroup OBJECT IDENTIFIER ::= { sonomaEthernet 1 }
    enetSMCGroup    OBJECT IDENTIFIER ::= { ethernetAdapterGroup 1 }

    --
    -- The Ethernet Group
    --
      enetSMCConfigTable OBJECT-TYPE
          SYNTAX  SEQUENCE OF EnetSMCConfigEntry
          ACCESS  not-accessible
          STATUS  mandatory
          DESCRIPTION
             "A table of Ethernet physical port configuration
              parameters."
          ::= { enetSMCGroup 1 }

      enetSMCConfigEntry  OBJECT-TYPE
          SYNTAX  EnetSMCConfigEntry
          ACCESS  not-accessible
          STATUS  mandatory
          DESCRIPTION
             "An entry in the enetSMC port table."
          INDEX  { enetSMCConfigIndex }
          ::= { enetSMCConfigTable 1 }

      EnetSMCConfigEntry ::= SEQUENCE {
          enetSMCConfigIndex      INTEGER,
          enetSMCConfigLineSpeed  INTEGER,
          enetSMCConfigInterface  INTEGER,
          enetSMCConfigMode       INTEGER
          }

      enetSMCConfigIndex  OBJECT-TYPE
          SYNTAX  INTEGER
          ACCESS  read-only
          STATUS  mandatory
          DESCRIPTION
             "The value of the index uniquely specifies the physical 
              port number to which this entry is applicable."
          ::= { enetSMCConfigEntry 1 }

      enetSMCConfigLineSpeed  OBJECT-TYPE
          SYNTAX  INTEGER {
                            speed10Mbps (1),
                            speed100Mbps (2),
							speedAuto (3)
                          }
          ACCESS  read-write
          STATUS  mandatory
          DESCRIPTION
             "The line speed configured for this adapter.  Auto and 100 
			  Mbit are only valid for the 9332 card."
          DEFVAL { speed10Mbps }
          ::= { enetSMCConfigEntry 2 }

      enetSMCConfigInterface  OBJECT-TYPE
          SYNTAX  INTEGER {
                           aui (1),
                           twistedPair (2),
                           utp (3),
                           bnc (4),
                           auto (5)
                          }
          ACCESS  read-write
          STATUS  mandatory
          DESCRIPTION
             "This type of interface which is configured on this 
              adapter. Setting the value to aui (1) is an invalid 
              operation for interfaces which only support twistedPair
              or utp. Where: aui - Attachment Unit Interface,
                             utp - Unshielded Twisted Pair."
          DEFVAL  { auto }
          ::= { enetSMCConfigEntry 3 }

      enetSMCConfigMode  OBJECT-TYPE
          SYNTAX  INTEGER {
                           halfDuplex (1),
                           fullDuplex (2)
                          }
          ACCESS  read-write
          STATUS  mandatory
          DESCRIPTION
             "Indicates which duplex mode is configured on this interface."
          DEFVAL  { halfDuplex }
           ::= { enetSMCConfigEntry 4 }

      enetSMCStatsTable  OBJECT-TYPE
          SYNTAX  SEQUENCE OF EnetSMCStatsEntry
          ACCESS  not-accessible
          STATUS  mandatory
          DESCRIPTION
             "A table of Ethernet physical port statistics parameters."
          ::= { enetSMCGroup 2 }

      enetSMCStatsEntry  OBJECT-TYPE
          SYNTAX  EnetSMCStatsEntry
          ACCESS  not-accessible
          STATUS  mandatory
          DESCRIPTION
             "An entry in the enetSMC port table."
          INDEX  { enetSMCStatsIndex }
          ::= { enetSMCStatsTable 1 }

      EnetSMCStatsEntry ::= SEQUENCE {
          enetSMCStatsIndex              INTEGER,
          enetSMCSQEErrors               Counter,
          enetSMCRxMissedFrames          Counter,
          enetSMCRetries                 Counter,
          enetSMCCollisions              Counter,
          enetSMCRunts                   Counter,
          enetSMCFRAMorCRCErrors         Counter,
          enetSMCTxDeferrals             Counter,
          enetSMCLateCollisions          Counter,
          enetSMCLossofCarrierErrors     Counter,
          enetSMCRetryErrors             Counter,
          enetSMCNoOfLinkResets          Counter,
          enetSMCLastLinkResetReason     INTEGER,
          enetSMCTimeSinceLastLinkReset  INTEGER,
          enetSMCRxPackets               Counter
       }

      enetSMCStatsIndex  OBJECT-TYPE
          SYNTAX  INTEGER
          ACCESS  read-only
          STATUS  mandatory
          DESCRIPTION
             "The value of the index uniquely specifies the physical 
              port number to which this entry is applicable."
          ::= { enetSMCStatsEntry 1 }

      enetSMCSQEErrors  OBJECT-TYPE
          SYNTAX  Counter
          ACCESS  read-only
          STATUS  mandatory
          DESCRIPTION
             "The number of SQE/Heartbeat errors detected."
          ::= { enetSMCStatsEntry 2 }

      enetSMCRxMissedFrames  OBJECT-TYPE
          SYNTAX  Counter
          ACCESS  read-only
          STATUS  mandatory
          DESCRIPTION
             "The number of receive frames missed because no buffers
              were available to accept the incoming data."
          ::= { enetSMCStatsEntry 3 }

      enetSMCRetries  OBJECT-TYPE
          SYNTAX  Counter
          ACCESS  read-only
          STATUS  mandatory
          DESCRIPTION
             "Total number of transmission retries by this station on 
              the attached LAN."
          ::= { enetSMCStatsEntry 4 }

      enetSMCCollisions  OBJECT-TYPE
          SYNTAX  Counter
          ACCESS  read-only
          STATUS  mandatory
          DESCRIPTION
             "Total collisions detected on the attached LAN."
          ::= { enetSMCStatsEntry 5 }

      enetSMCRunts  OBJECT-TYPE
          SYNTAX  Counter
          ACCESS  read-only
          STATUS  mandatory
          DESCRIPTION
             "Total number of runts detected on the attached LAN."
          ::= { enetSMCStatsEntry 6 }

      enetSMCFRAMorCRCErrors  OBJECT-TYPE
          SYNTAX  Counter
          ACCESS  read-only
          STATUS  mandatory
          DESCRIPTION
             "Total number of Framing or CRC errors detected on LAN."
          ::= { enetSMCStatsEntry 7 }

      enetSMCTxDeferrals  OBJECT-TYPE
          SYNTAX  Counter
          ACCESS  read-only
          STATUS  mandatory
          DESCRIPTION
             "The total number of TX deferrals encountered on the LAN 
              segment."
          ::= { enetSMCStatsEntry 8 }

      enetSMCLateCollisions  OBJECT-TYPE
          SYNTAX  Counter
          ACCESS  read-only
          STATUS  mandatory
          DESCRIPTION
             "Total number of late collisions encountered during 
              transmission by this port."
          ::= { enetSMCStatsEntry 9 }

      enetSMCLossofCarrierErrors  OBJECT-TYPE
          SYNTAX  Counter
          ACCESS  read-only
          STATUS  mandatory
          DESCRIPTION
             "Total number of loss of carrier errors encountered by this 
              port."
          ::= { enetSMCStatsEntry 10 }

      enetSMCRetryErrors  OBJECT-TYPE
          SYNTAX  Counter
          ACCESS  read-only
          STATUS  mandatory
          DESCRIPTION
             "Total number of TX retry limit errors encountered during
              transmission by this port."
          ::= { enetSMCStatsEntry 11 }

      enetSMCNoOfLinkResets  OBJECT-TYPE
          SYNTAX  Counter
          ACCESS  read-only
          STATUS  mandatory
          DESCRIPTION
             "This is the number of link resets which have occurred
              since the last reinitialization of the unit."
          ::= { enetSMCStatsEntry 18 }

      enetSMCLastLinkResetReason  OBJECT-TYPE
          SYNTAX  INTEGER {
                  noReason (1),
                  management (2),
                  deviceReset (3),
                  cableDrop (4)
                  }
          ACCESS  read-only
          STATUS  mandatory
          DESCRIPTION
             "This object gives the reason code for the last reset which
              occurred on this LAN physical link. A value of noReason(1)
              is returned if the link has not reset. A value of 
              management(2) is returned when a link reset has been 
              caused by a management protocol (either SNMP or by LMS). 
              A value of deviceReset(3) is returned if the link reset 
              was caused by a hardware failure.
              A value of cableDrop(4) is returned when the link reset 
              was caused by a missing or faulty cable."
          ::= { enetSMCStatsEntry 19 }

    enetSMCTimeSinceLastLinkReset  OBJECT-TYPE
        SYNTAX  INTEGER
        ACCESS  read-only
        STATUS  mandatory
        DESCRIPTION
            "This is the time, in seconds, since the last link reset."
        ::= { enetSMCStatsEntry 20 }

      enetSMCRxPackets  OBJECT-TYPE
          SYNTAX  Counter
          ACCESS  read-only
          STATUS  mandatory
          DESCRIPTION
             "This is the number of packets received on this link
              by the device driver."
          ::= { enetSMCStatsEntry 21 }


	enetSMCStatusTable  OBJECT-TYPE
          SYNTAX  SEQUENCE OF EnetSMCStatusEntry
          ACCESS  not-accessible
          STATUS  mandatory
          DESCRIPTION
             "A table of Ethernet physical port status parameters."
          ::= { enetSMCGroup 3 }

      enetSMCStatusEntry  OBJECT-TYPE
          SYNTAX  EnetSMCStatusEntry
          ACCESS  not-accessible
          STATUS  mandatory
          DESCRIPTION
             "An entry in the enetSMC port status table."
          INDEX  { enetSMCStatsIndex }
          ::= { enetSMCStatusTable 1 }

      EnetSMCStatusEntry ::= SEQUENCE {
          enetSMCLineSpeed	INTEGER,
          enetSMCLineMode	INTEGER,
          enetSMCLineInterface INTEGER
       }

      enetSMCLineSpeed OBJECT-TYPE
          SYNTAX  INTEGER {
                            speed10Mbps (1),
                            speed100Mbps (2),
                            speedAuto( 3)
                          }
          ACCESS  read-only
          STATUS  mandatory
          DESCRIPTION
             "Indicates the current line speed."
          ::= { enetSMCStatusEntry 1 }

      enetSMCLineMode  OBJECT-TYPE
          SYNTAX  INTEGER {
                           halfDuplex (1),
                           fullDuplex (2)
                          }
          ACCESS  read-only
          STATUS  mandatory
          DESCRIPTION
             "Indicates the current duplex mode on this interface."
           ::= { enetSMCStatusEntry 2 }

      enetSMCLineInterface  OBJECT-TYPE
          SYNTAX  INTEGER {
                           aui (1),
                           twistedPair (2),
                           utp (3),
                           bnc (4),
                           auto (5)
                          }
          ACCESS  read-only
          STATUS  mandatory
          DESCRIPTION
             "Indicate the interface as detected."
          ::= { enetSMCStatusEntry 3 }

END
