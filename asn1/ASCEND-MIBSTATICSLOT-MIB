--			Ascend mibstaticslot MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBSTATICSLOT-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibmibProfSlotStatic  OBJECT IDENTIFIER ::= { configuration 31}

	-- The mibmibProfSlotStatic table
	--
	-- This table contains parameters for the mibmibProfSlotStatic profile
	--

    mibmibProfSlotStaticTable	OBJECT-TYPE
	SYNTAX		SEQUENCE OF MibmibProfSlotStaticEntry
	ACCESS		not-accessible
	STATUS		mandatory
	DESCRIPTION	"A list of mibmibProfSlotStatic profile entries."
	::= { mibmibProfSlotStatic 1 }

    mibmibProfSlotStaticEntry	OBJECT-TYPE
	SYNTAX		MibmibProfSlotStaticEntry
	ACCESS		not-accessible
	STATUS		mandatory
	DESCRIPTION	"A mibmibProfSlotStatic entry containing objects that
			 maps to the parameters of mibmibProfSlotStatic profile."
	INDEX		{ mibProfSlotStatic-Shelf-o, mibProfSlotStatic-Slot-o, mibProfSlotStatic-Item-o }
	::= { mibmibProfSlotStaticTable 1 }

    MibmibProfSlotStaticEntry ::=
	SEQUENCE {
	    mibProfSlotStatic-Shelf-o
		INTEGER,
	    mibProfSlotStatic-Slot-o
		INTEGER,
	    mibProfSlotStatic-Item-o
		INTEGER,
	    mibProfSlotStatic-Name
		DisplayString,
	    mibProfSlotStatic-PhysicalAddress-Shelf
		INTEGER,
	    mibProfSlotStatic-PhysicalAddress-Slot
		INTEGER,
	    mibProfSlotStatic-PhysicalAddress-ItemNumber
		INTEGER,
	    mibProfSlotStatic-AtmParameters-IncomingPriority
		INTEGER,
	    mibProfSlotStatic-InterfaceType
		INTEGER,
	    mibProfSlotStatic-Action-o
		INTEGER
	}

    mibProfSlotStatic-Shelf-o	OBJECT-TYPE
	SYNTAX	INTEGER
	ACCESS	read-only
	STATUS	mandatory
	DESCRIPTION	""
	::= { mibmibProfSlotStaticEntry 1 }

    mibProfSlotStatic-Slot-o	OBJECT-TYPE
	SYNTAX	INTEGER
	ACCESS	read-only
	STATUS	mandatory
	DESCRIPTION	""
	::= { mibmibProfSlotStaticEntry 2 }

    mibProfSlotStatic-Item-o	OBJECT-TYPE
	SYNTAX	INTEGER
	ACCESS	read-only
	STATUS	mandatory
	DESCRIPTION	""
	::= { mibmibProfSlotStaticEntry 3 }

    mibProfSlotStatic-Name	OBJECT-TYPE
	SYNTAX	DisplayString
	ACCESS	read-write
	STATUS	mandatory
	DESCRIPTION	"For future use. The current design does not use this name attribute but instead references a LIM or CM slot by its profile index; we may in the future support referencing a LIM or CM slot by its name as well as by its physical address. This name attribute consists of a null-terminated ASCII string; is read-only; and defaults to the ASCII form of this LIM or CM slot physical address."
	::= { mibmibProfSlotStaticEntry 4 }

    mibProfSlotStatic-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibmibProfSlotStaticEntry 5 }

    mibProfSlotStatic-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibmibProfSlotStaticEntry 6 }

    mibProfSlotStatic-PhysicalAddress-ItemNumber	OBJECT-TYPE
	SYNTAX	INTEGER
	ACCESS	read-write
	STATUS	mandatory
	DESCRIPTION	"A number that specifies an addressable entity within the context of shelf and slot."
	::= { mibmibProfSlotStaticEntry 7 }

    mibProfSlotStatic-AtmParameters-IncomingPriority	OBJECT-TYPE
	SYNTAX	INTEGER {
		    lowPriority (1),
		    highPriority (2)
		}
	ACCESS	read-write
	STATUS	mandatory
	DESCRIPTION	"Specifies the relative priority of ATM cells incoming from this LIM or CM slot. A slot's incoming-priority is used to select the appropriate outgoing queue that is associated with the outgoing port from the internal ATM cell processing engine. All ports on this slot and all ATM service categories share the same incoming-priority. An outgoing port (from the internal ATM cell processing engine) can have multiple queues associated with a given QoS. The incoming-priority is used to select which queue to use among all the queues associated with the given QoS."
	::= { mibmibProfSlotStaticEntry 8 }

    mibProfSlotStatic-InterfaceType	OBJECT-TYPE
	SYNTAX	INTEGER {
		    default (1),
		    gShdsl (2),
		    hdsl2 (3)
		}
	ACCESS	read-write
	STATUS	mandatory
	DESCRIPTION	"Modifying this field does not effect non-hdsl/shdsl cards. All slots are set to 'default' at initialization. g.shdsl is used as 'default' for slots with hdsl2/g.shdsl cards. non-hdsl/shdsl slots default into their card types. The HDSL2 and SHDSL slot cards support HDSL2 or G.SHDSL modem technologies."
	::= { mibmibProfSlotStaticEntry 10 }

    mibProfSlotStatic-Action-o	OBJECT-TYPE
	SYNTAX	INTEGER {
		    noAction (1),
		    createProfile (2),
		    deleteProfile (3)
		}
	ACCESS	read-write
	STATUS	mandatory
	DESCRIPTION	""
	::= { mibmibProfSlotStaticEntry 9 }

END
