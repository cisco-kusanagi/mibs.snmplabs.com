EQUIPE-TRAP-MIB DEFINITIONS ::= BEGIN

    --
    -- EBOX System Traps
    --

    IMPORTS
        enterprises    
            FROM RFC1155-SMI
        EqIfType, EqAtmPvcType, 
        EqApsLineState, EqSeverityLevel,
        eqModuleShelfId, eqModuleSlotId, 
        eqModuleEid, eqModuleRedOperRole,
        eqHardDiskEid, eqHardDiskUsedHiMark, 
        eqHardDiskUsedLowMark, eqFanUnitEid,
        eqFaultTime, eqFaultScope,
        eqFaultModule, eqFaultSwlm,
        eqStratumCentStatus, eqStratumCentRedStatus
            FROM EQUIPE-SYSTEM-MIB
        DisplayString, DateAndTime
            FROM SNMPv2-TC
        ifIndex 
            FROM IF-MIB
        MODULE-IDENTITY, OBJECT-TYPE, NOTIFICATION-TYPE, IpAddress
            FROM SNMPv2-SMI;

    equipe     OBJECT IDENTIFIER ::= { enterprises 5022 }

    eqTraps MODULE-IDENTITY
        LAST-UPDATED "0112040000Z"            -- Dec 4, 2001
        ORGANIZATION ""
        CONTACT-INFO
            "Jas Parmar
            Equipe Communications
            100 Nagog Park
            Acton MA 01720"
        DESCRIPTION
            "This is the Equipe traps MIB module."
    ::= { equipe 4 }

    --
    -- Trap Groups
    --

    eqTrapObjects         OBJECT IDENTIFIER ::= { eqTraps 1 }
    eqSystemTraps         OBJECT IDENTIFIER ::= { eqTraps 2 }
    eqModuleTraps         OBJECT IDENTIFIER ::= { eqTraps 3 }
    eqIfTraps             OBJECT IDENTIFIER ::= { eqTraps 4 }
    eqAppsTraps           OBJECT IDENTIFIER ::= { eqTraps 5 }

    --
    -- App-specific Trap Groups
    --

    eqSrmTraps            OBJECT IDENTIFIER ::= { eqAppsTraps 1 }
    eqSonetTraps          OBJECT IDENTIFIER ::= { eqAppsTraps 2 }
    eqAtmTraps            OBJECT IDENTIFIER ::= { eqAppsTraps 3 }
    eqIpTraps             OBJECT IDENTIFIER ::= { eqAppsTraps 4 }
    eqMplsTraps           OBJECT IDENTIFIER ::= { eqAppsTraps 5 }

    --
    -- Trap Specifc Objects.
    --

    eqSystemId OBJECT-TYPE
        SYNTAX      DisplayString
        MAX-ACCESS  not-accessible
        STATUS      current
        DESCRIPTION
            "The unique name assigned to the system." 
        ::= { eqTrapObjects 1 }

    eqEid OBJECT-TYPE
        SYNTAX      INTEGER (1..2147483647)
        MAX-ACCESS  not-accessible
        STATUS      current
        DESCRIPTION
            "The unique integer value assigned to a system resource."
        ::= { eqTrapObjects 2 }

    eqIfName OBJECT-TYPE
        SYNTAX      DisplayString
        MAX-ACCESS  not-accessible
        STATUS      current
        DESCRIPTION
            "The textual name assigned to an interface."
        ::= { eqTrapObjects 3 }

    eqIpAddress OBJECT-TYPE
        SYNTAX      IpAddress
        MAX-ACCESS  not-accessible
        STATUS      current
        DESCRIPTION
            "An ip address representing a host."
        ::= { eqTrapObjects 4 }

    eqFileName OBJECT-TYPE
        SYNTAX      DisplayString
        MAX-ACCESS  not-accessible
        STATUS      current
        DESCRIPTION
            "An ascii string representing name of a file."
        ::= { eqTrapObjects 5 }

    eqTrapDescr OBJECT-TYPE
        SYNTAX      DisplayString
        MAX-ACCESS  not-accessible
        STATUS      current
        DESCRIPTION
            "An ascii string containing textual description for a trap."
        ::= { eqTrapObjects 6 }

    eqModuleFuseType OBJECT-TYPE
        SYNTAX      INTEGER {
                  fuseTypeA(1),
                  fuseTypeB(2)
        }
        MAX-ACCESS  not-accessible
        STATUS      current
        DESCRIPTION
            "The module fuse type."
        ::= { eqTrapObjects 7 }

    eqApsLineState OBJECT-TYPE
        SYNTAX      EqApsLineState
        MAX-ACCESS  not-accessible
        STATUS      current
        DESCRIPTION
            "The APS line state value."
        ::= { eqTrapObjects 8 }

    eqIfType OBJECT-TYPE
        SYNTAX      EqIfType
        MAX-ACCESS  not-accessible
        STATUS      current
        DESCRIPTION
            "The equipe interface type."
        ::= { eqTrapObjects 9 }

    eqAtmPvcType OBJECT-TYPE
        SYNTAX      EqAtmPvcType
        MAX-ACCESS  not-accessible
        STATUS      current
        DESCRIPTION
            "The equipe atm pvc type."
        ::= { eqTrapObjects 10 }

    eqEventTime OBJECT-TYPE
        SYNTAX      DateAndTime
        MAX-ACCESS  not-accessible
        STATUS      current
        DESCRIPTION
            "The time of an event occurrence."
        ::= { eqTrapObjects 11 }

    eqThresholdValue OBJECT-TYPE
        SYNTAX      INTEGER (1..2147483647)
        MAX-ACCESS  not-accessible
        STATUS      current
        DESCRIPTION
            "The configured value of a threshold."
        ::= { eqTrapObjects 12 }

    eqCurrentValue OBJECT-TYPE
        SYNTAX      INTEGER (1..2147483647)
        MAX-ACCESS  not-accessible
        STATUS      current
        DESCRIPTION
            "The current value of a resource parameter."       
        ::= { eqTrapObjects 13 }

    eqResourceId OBJECT-TYPE  
        SYNTAX      DisplayString
        MAX-ACCESS  not-accessible
        STATUS      current
        DESCRIPTION
            "The string identifying a resource."   
        ::= { eqTrapObjects 14 }

    eqSeverityLevel OBJECT-TYPE
        SYNTAX      EqSeverityLevel
        MAX-ACCESS  not-accessible
        STATUS      current
        DESCRIPTION
            "The severity level of an event occurrence."
        ::= { eqTrapObjects 15 }

    --
    -- System Traps.
    --

    eqHardDiskUsedHiMarkReached NOTIFICATION-TYPE
        OBJECTS { eqTrapDescr, eqModuleShelfId, eqModuleSlotId, 
                  eqHardDiskEid, eqHardDiskUsedHiMark }
        STATUS  current
        DESCRIPTION
           "This trap is generated when the percentage of used disk space 
            on the hard disk has reached the value indicated by
            eqHardDiskUsedHiMark. 

            eqTrapDescr provides a textual description for this trap.
            eqModuleShelfId is the shelf id in which the hard disk resides.
            eqModuleSlotId is the (shelf-relative) slot id in which the 
            hard disk resides.

            To reduce flapping, this trap is only generated if the
            value for this object had previously crossed the 
            eqHardDiskUsedLowMark."
        -- EQ_TRAP_DESCR  
        --    "The amount of disk space used on hard disk '%s' has reached 
        --     %d percent."
        ::= { eqSystemTraps 1 }

    eqHardDiskUsedLowMarkReached NOTIFICATION-TYPE
        OBJECTS { eqTrapDescr, eqModuleShelfId, eqModuleSlotId, 
                  eqHardDiskEid, eqHardDiskUsedLowMark }
        STATUS  current
        DESCRIPTION
           "This trap is generated when the percentage of used disk space
            on the hard disk has reached the value indicated by
            eqHardDiskUsedLowMark. 

            eqTrapDescr provides a textual description for this trap.
            eqModuleShelfId is the shelf id in which the hard disk resides.
            eqModuleSlotId is the (shelf-relative) slot id in which the 
            hard disk resides.

            To reduce flapping, this trap is only generated if the 
            value for this object had previously crossed the 
            eqHardDiskUsedHiMark."
        -- EQ_TRAP_DESCR  
        --  "The amount of disk space used on hard disk '%s' has reached 
        --   %d percent."
        ::= { eqSystemTraps 2 }

    eqFanUnitFailed NOTIFICATION-TYPE
        OBJECTS { eqTrapDescr, eqModuleShelfId, 
                  eqModuleSlotId, eqFanUnitEid }
        STATUS  current
        DESCRIPTION
           "This trap indicates that a fan unit failed.

            eqTrapDescr provides a textual description for this trap.
            eqModuleShelfId is the shelf id in which the fan unit resides.
            eqModuleSlotId is the (shelf-relative) slot id in which the 
            fan unit resides."
        -- EQ_TRAP_DESCR  
        --  "The fan unit in slot labeled '%s' has failed."
        ::= { eqSystemTraps 3 }

    eqFanUnitFaulty NOTIFICATION-TYPE
        OBJECTS { eqTrapDescr, eqModuleShelfId, 
                  eqModuleSlotId, eqFanUnitEid }
        STATUS  current
        DESCRIPTION
           "This trap indicates that the RPM of a fan unit has gone
            below x rpm.

            eqTrapDescr provides a textual description for this trap.
            eqModuleShelfId is the shelf id in which the fan unit resides.
            eqModuleSlotId is the (shelf-relative) slot id in which the 
            fan unit resides."
        -- EQ_TRAP_DESCR  
        --  "The fan unit in slot labeled '%s' is faulty."
        ::= { eqSystemTraps 4 }

    eqAcctDataWriteToDiskFailed NOTIFICATION-TYPE
        OBJECTS { eqTrapDescr }
        STATUS  current
        DESCRIPTION
           "This trap indicates that the accounting server failed
            to write the data to the local hard disk.
            eqTrapDescr provides a textual description for this trap."
        -- EQ_TRAP_DESCR  
        --  "The fan unit in slot labeled '%s' is faulty."
        ::= { eqSystemTraps 5 }

    eqAcctDataFileDeletedBeforeTransfer NOTIFICATION-TYPE
        OBJECTS { eqTrapDescr, eqFileName, eqSystemId }
        STATUS  current
        DESCRIPTION
           "This trap indicates that an accounting file was deleted
            before it had a chance to be transferred out of the
            box to an accounting server.

            eqTrapDescr provides a textual description for this trap.
            eqFileName is the name of the file that was deleted before
            it could be transferred out of the box.
            eqSystemId is the id assigned to the system generating the 
            trap."
        -- EQ_TRAP_DESCR  
        --  "The accounting data file '%s' was deleted before server
        --   could transfer it to host '%s'."
        ::= { eqSystemTraps 6 }

    eqAcctDataXferError NOTIFICATION-TYPE
        OBJECTS { eqTrapDescr, eqIpAddress, eqFileName, eqSystemId }
        STATUS  current
        DESCRIPTION
           "This trap indicates that the accounting server encountered
            an error while transferring an accounting file to the
            accounting server. The system will retry the transfer to an 
            alternative host if one is configured. 

            eqTrapDescr provides a textual description for this trap.
            eqIpAddress is the ip address of the host to which the
            file was being transferred.
            eqFileName is the name of the file that encountered the
            error.
            eqSystemId is the id assigned to the system generating the 
            trap."
        -- EQ_TRAP_DESCR  
        --  "The accounting server failed to transfer data file '%s' to
        --   host '%s'."
        ::= { eqSystemTraps 7 }

    eqLogServerWriteToDiskFailed NOTIFICATION-TYPE
        OBJECTS { eqTrapDescr }
        STATUS  current
        DESCRIPTION
           "This trap indicates that the log server failed
            to write system log data out to the local hard disk.
            eqTrapDescr provides a textual description for this trap."
        -- EQ_TRAP_DESCR  
        --  "The log server failed to write data to the hard disk."
        ::= { eqSystemTraps 8 }

    eqLogDataFileDeletedBeforeTransfer NOTIFICATION-TYPE
        OBJECTS { eqTrapDescr, eqFileName, eqSystemId }
        STATUS  current
        DESCRIPTION
           "This trap indicates that an log file was deleted
            before it had a chance to be transferred out of the
            box to a logging server.

            eqTrapDescr provides a textual description for this trap.
            eqFileName is the name of the file that was deleted before
            it could be transferred out of the box.
            eqSystemId is the id assigned to the system generating the 
            trap."
        -- EQ_TRAP_DESCR  
        --  "The log file '%s' was deleted before server could transfer it 
        --   to host '%s'."
        ::= { eqSystemTraps 9 }

    eqLogDataXferError NOTIFICATION-TYPE
        OBJECTS { eqTrapDescr, eqIpAddress, eqFileName, eqSystemId }
        STATUS  current
        DESCRIPTION
           "This trap indicates that the log server failed to transfer 
            the system log file out of the box to an external host.
            The system will retry the transfer to an alternative
            host if one is configured.

            eqTrapDescr provides a textual description for this trap.
            eqIpAddress is the ip address of the host to which the
            file was being transferred.
            eqFileName is the name of the file that encountered the
            error.
            eqSystemId is the id assigned to the system generating the 
            trap."
        -- EQ_TRAP_DESCR  
        --  "The log server failed to transfer data file '%s' to host '%s'."
        ::= { eqSystemTraps 10 }

    eqMidPlaneParityError NOTIFICATION-TYPE
        OBJECTS { eqTrapDescr }
        STATUS  current
        DESCRIPTION
           "This trap indicates that a parity error occurred on the
            midplane.
            eqTrapDescr provides a textual description for this trap."
        -- EQ_TRAP_DESCR  
        --  "A parity error occurred on the midplane."
        ::= { eqSystemTraps 11 }

    eqSonetTimingCfgChanged NOTIFICATION-TYPE
        OBJECTS { eqTrapDescr, eqEid }
        STATUS  current
        DESCRIPTION
           "This trap indicates that the sonet timing config was
            changed via the NMS.
            eqEid indicates the eid of the sonet timing node that was
            modified."
        -- EQ_TRAP_DESCR  
        --  "The sonet timing config was changed by the NMS for sonet
        --   timing node '%d'."
        ::= { eqSystemTraps 12 }

    eqRisingThresholdAlert NOTIFICATION-TYPE
        OBJECTS { eqTrapDescr, eqModuleShelfId, eqModuleSlotId, 
                  eqEid, eqIfName, eqEventTime, eqThresholdValue, 
                  eqCurrentValue, eqResourceId, eqSeverityLevel }
        STATUS  current
        DESCRIPTION
           "This trap indicates that the a rising threshold crossing
            has occurred for the specified entity. 

            eqTrapDescr provides a textual description for this trap.
            eqModuleShelfId is the shelf id on which the entity exists.
            eqModuleSlotId is the (shelf-relative) slot id on which
            the entity exists.
            eqEid is the id of the entity.
            eqIfName is the name of the entity.
            eqEventTime is the time of the threshold crossing.
            eqThresholdValue is the configured value of the threshold.
            eqCurrentValue is the current value of the resource parameter.
            eqResourceId is the string identifying the resource parameter.
            eqSeverityLevel is the configured severity for this threshold
            crossing."
        -- EQ_TRAP_DESCR
        --  "Attribute %s for %s %s at location %s (%d.%d.%d) crossed rising 
        --   threshold (current value %lu, rising threshold %lu)."
        ::= { eqSystemTraps 13 }

    eqFallingThresholdAlert NOTIFICATION-TYPE
        OBJECTS { eqTrapDescr, eqModuleShelfId, eqModuleSlotId, 
                  eqEid, eqIfName, eqEventTime, eqThresholdValue, 
                  eqCurrentValue, eqResourceId, eqSeverityLevel }
        STATUS  current
        DESCRIPTION
           "This trap indicates that the a falling threshold crossing
            has occurred for the specified entity.

            eqTrapDescr provides a textual description for this trap.
            eqModuleShelfId is the shelf id on which the entity exists.
            eqModuleSlotId is the (shelf-relative) slot id on which
            the entity exists.
            eqEid is the id of the entity.
            eqIfName is the name of the entity.
            eqEventTime is the time of the threshold crossing.
            eqThresholdValue is the configured value of the threshold.
            eqCurrentValue is the current value of the resource parameter.
            eqResourceId is the string identifying the resource parameter.
            eqSeverityLevel is the configured severity for this threshold
            crossing."
        -- EQ_TRAP_DESCR
        --  "Attribute %s for %s %s at location %s (%d.%d.%d) crossed falling 
        --   threshold (current value %lu, falling threshold %lu)."
        ::= { eqSystemTraps 14 }

    --
    -- Module Traps.
    --

    eqModuleInserted NOTIFICATION-TYPE
        OBJECTS { eqTrapDescr, eqModuleShelfId, eqModuleSlotId, eqModuleEid }
        STATUS  current
        DESCRIPTION
           "This trap indicates that a module has been inserted in a slot. 

            eqTrapDescr provides a textual description for this trap.
            eqModuleShelfId is the shelf id in which the module resides.
            eqModuleSlotId is the (shelf-relative) slot id in which the 
            module resides. 
            eqModuleEid is the eid of the module."
        -- EQ_TRAP_DESCR  
        --  "Module '%s' inserted in slot labeled '%s' (%d.%d)."
        ::= { eqModuleTraps 1 }

    eqModuleRemoved NOTIFICATION-TYPE
        OBJECTS { eqTrapDescr, eqModuleShelfId, eqModuleSlotId, eqModuleEid }
        STATUS  current
        DESCRIPTION
           "This trap indicates that a module has been removed from a slot.

            eqTrapDescr provides a textual description for this trap.
            eqModuleShelfId is the shelf id in which the module resides.
            eqModuleSlotId is the (shelf-relative) slot id in which the 
            module resides. 
            eqModuleEid is the eid of the module."
        -- EQ_TRAP_DESCR  
        --  "Module '%s' removed from slot labeled '%s' (%d.%d)."
        ::= { eqModuleTraps 2 }

    eqModuleWentOffline NOTIFICATION-TYPE
        OBJECTS { eqTrapDescr, eqModuleShelfId, eqModuleSlotId, eqModuleEid }
        STATUS  current
        DESCRIPTION
           "This trap indicates that a module has been taken offline.

            eqTrapDescr provides a textual description for this trap.
            eqModuleShelfId is the shelf id in which the module resides.
            eqModuleSlotId is the (shelf-relative) slot id in which the 
            module resides. 
            eqModuleEid is the eid of the module."
        -- EQ_TRAP_DESCR  
        --  "Module '%s' went offline in slot labeled '%s' (%d.%d)."
        ::= { eqModuleTraps 3 }

    eqModuleReset NOTIFICATION-TYPE
        OBJECTS { eqTrapDescr, eqModuleShelfId, eqModuleSlotId, eqModuleEid }
        STATUS  current
        DESCRIPTION
           "This trap indicates that a module has been reset.

            eqTrapDescr provides a textual description for this trap.
            eqModuleShelfId is the shelf id in which the module resides.
            eqModuleSlotId is the (shelf-relative) slot id in which the 
            module resides. 
            eqModuleEid is the eid of the module."
        -- EQ_TRAP_DESCR  
        --  "Module '%s' reset in slot labeled '%s' (%d.%d)."
        ::= { eqModuleTraps 4 }

    eqModuleFuseBlownMother NOTIFICATION-TYPE
        OBJECTS { eqTrapDescr, eqModuleShelfId, eqModuleSlotId, eqModuleEid, 
                  eqModuleFuseType }
        STATUS  current
        DESCRIPTION
           "This trap indicates that an A/B fuse has blown on a 
            mother board.

            eqTrapDescr provides a textual description for this trap.
            eqModuleShelfId is the shelf id in which the module resides.
            eqModuleSlotId is the (shelf-relative) slot id in which the 
            module resides. 
            eqModuleEid is the eid of the module.
            eqModuleFuseType indicates the blown fuse (A or B)."
        -- EQ_TRAP_DESCR  
        --  "The fuse has blown on mother board of module in slot
        --   labeled '%s' (%d.%d)."
        ::= { eqModuleTraps 5 }

    eqModuleFuseBlownDaughter NOTIFICATION-TYPE
        OBJECTS { eqTrapDescr, eqModuleShelfId, eqModuleSlotId, eqModuleEid,
                  eqModuleFuseType }
        STATUS  current
        DESCRIPTION
           "This trap indicates that an A/B fuse has blown on a 
            daughter board.

            eqTrapDescr provides a textual description for this trap.
            eqModuleShelfId is the shelf id in which the module resides.
            eqModuleSlotId is the (shelf-relative) slot id in which the 
            module resides. 
            eqModuleEid is the eid of the module.
            eqModuleFuseType indicates the blown fuse (A or B)."
        -- EQ_TRAP_DESCR  
        --  "The fuse has blown on daughter board of module in slot
        --   labeled '%s' (%d.%d)."
        ::= { eqModuleTraps 6 }

    eqModulePowerSupplyFailed NOTIFICATION-TYPE
        OBJECTS { eqTrapDescr, eqModuleShelfId, eqModuleSlotId, eqModuleEid }
        STATUS  current
        DESCRIPTION
           "This trap indicates that a power supply unit has failed.

            eqTrapDescr provides a textual description for this trap.
            eqModuleShelfId is the shelf id in which the module resides.
            eqModuleSlotId is the (shelf-relative) slot id in which the 
            module resides. 
            eqModuleEid is the eid of the module."
        -- EQ_TRAP_DESCR  
        --  "The power supply in slot labeled '%s' has failed."
        ::= { eqModuleTraps 7 }

    eqModuleRedRoleChanged NOTIFICATION-TYPE
        OBJECTS { eqTrapDescr, eqModuleEid, eqModuleRedOperRole }
        STATUS  current
        DESCRIPTION
           "This trap indicates that a module's redundancy role has changed.

            eqTrapDescr provides a textual description for this trap.
            eqModuleEid is the eid of the module.
            eqModuleRedOperRole is the module's new redundancy role."
        -- EQ_TRAP_DESCR  
        --  "Module in slot labeled '%s' has changed role from '%s' 
        --   to '%s'."
        ::= { eqModuleTraps 8 }

    eqModuleTypeMismatch NOTIFICATION-TYPE
        OBJECTS { eqTrapDescr, eqModuleShelfId, eqModuleSlotId, eqModuleEid }
        STATUS  current
        DESCRIPTION
           "This trap indicates that a module has been inserted in a slot,
            and the module does not match the module that was there 
            previously, 

            eqTrapDescr provides a textual description for this trap.
            eqModuleShelfId is the shelf id in which the module resides.
            eqModuleSlotId is the (shelf-relative) slot id in which the 
            module resides. 
            eqModuleEid is the eid of the module."
        -- EQ_TRAP_DESCR  
        --  "Wrong Module Type. Expected Module '%s' in slot '%s' (%d.%d)."
        ::= { eqModuleTraps 9 }

    eqModuleStratumCentStatusChanged NOTIFICATION-TYPE
        OBJECTS { eqTrapDescr, eqModuleShelfId, eqModuleSlotId, eqModuleEid,
                  eqStratumCentStatus }
        STATUS  current
        DESCRIPTION
           "This trap indicates that the central stratum timing
            subsystem has changed status.

            eqTrapDescr provides a textual description for this trap.
            eqModuleShelfId is the shelf id in which the module resides.
            eqModuleSlotId is the (shelf-relative) slot id in which the 
            module resides. 
            eqModuleEid is the eid of the module.
            eqStratumCentStatus is the new status of the stratum timing
            subsystem."
        -- EQ_TRAP_DESCR  
        --  "Central stratum timing subsystem on module in slot labeled
        --   '%s' has changed status (%d.%d)."
        ::= { eqModuleTraps 10 }

    eqModuleStratumCentRedStatusChanged NOTIFICATION-TYPE
        OBJECTS { eqTrapDescr, eqModuleShelfId, eqModuleSlotId, eqModuleEid,
                  eqStratumCentRedStatus }
        STATUS  current
        DESCRIPTION
           "This trap indicates that the central stratum timing
            subsystem has changed redundancy status.

            eqTrapDescr provides a textual description for this trap.
            eqModuleShelfId is the shelf id in which the module resides.
            eqModuleSlotId is the (shelf-relative) slot id in which the 
            module resides. 
            eqModuleEid is the eid of the module.
            eqStratumCentRedStatus is the new redundancy status of the 
            stratum timing subsystem."
        -- EQ_TRAP_DESCR  
        --  "Central stratum timing subsystem on module in slot labeled
        --   '%s' has changed redundancy status (%d.%d)."
        ::= { eqModuleTraps 11 }

    --
    -- Interface Traps.
    --

    eqIfAdded NOTIFICATION-TYPE
        OBJECTS { eqTrapDescr, eqModuleShelfId, eqModuleSlotId, 
                  ifIndex, eqIfName, eqIfType }
        STATUS  current
        DESCRIPTION
           "This trap indicates that an interface has been added.

            eqTrapDescr provides a textual description for this trap.
            eqModuleShelfId is the shelf id in which the interface
            has been added.
            eqModuleSlotId is the (shelf-relative) slot id in which 
            the interface has been added.
            ifIndex is the id of the newly added interface.
            eqIfName is the name of the newly added interface.
            eqIfType is the interface type of the newly added interface."
        -- EQ_TRAP_DESCR  
        --  "Interface '%s' of type '%s' added on module in slot labeled 
        --   '%s' (%d.%d.%d)."
        ::= { eqIfTraps 1 }

    eqIfRemoved NOTIFICATION-TYPE
        OBJECTS { eqTrapDescr, eqModuleShelfId, eqModuleSlotId, 
                  ifIndex, eqIfName, eqIfType }
        STATUS  current
        DESCRIPTION
           "This trap indicates that an interface has been deleted.

            eqTrapDescr provides a textual description for this trap.
            eqModuleShelfId is the shelf id in which the interface
            has been deleted.
            eqModuleSlotId is the (shelf-relative) slot id in which 
            the interface has been deleted.
            ifIndex is the id of the deleted interface.
            eqIfName is the name of the deleted interface.
            eqIfType is the interface type of the deleted interface."
        -- EQ_TRAP_DESCR  
        --  "Interface '%s' of type '%s' deleted on module in slot labeled 
        --   '%s' (%d.%d.%d)."
        ::= { eqIfTraps 2 }

    eqIfModified NOTIFICATION-TYPE
        OBJECTS { eqTrapDescr, eqModuleShelfId, eqModuleSlotId, 
                  ifIndex, eqIfName, eqIfType }
        STATUS  current
        DESCRIPTION
           "This trap indicates that an interface has been modified.

            eqTrapDescr provides a textual description for this trap.
            eqModuleShelfId is the shelf id in which the interface
            has been modified.
            eqModuleSlotId is the (shelf-relative) slot id in which 
            the interface has been modified.
            ifIndex is the id of the modified interface.
            eqIfName is the name of the modified interface.
            eqIfType is the interface type of the modified interface."
        -- EQ_TRAP_DESCR  
        --  "Interface '%s' of type '%s' modified on module in slot labeled 
        --   '%s' (%d.%d.%d)."
        ::= { eqIfTraps 3 }

    eqAtmPvcAdded NOTIFICATION-TYPE
        OBJECTS { eqTrapDescr, eqModuleShelfId, eqModuleSlotId, 
                  eqEid, eqIfName, eqAtmPvcType }
        STATUS  current
        DESCRIPTION
           "This trap indicates that an atm pvc has been added.

            eqTrapDescr provides a textual description for this trap.
            eqModuleShelfId is the shelf id in which the atm pvc
            has been added.
            eqModuleSlotId is the (shelf-relative) slot id in which 
            the atm pvc has been added.
            ifIndex is the id of the newly added atm pvc.
            eqIfName is the name of the newly added atm pvc.
            eqAtmPvcType is the pvc type of the newly added atm pvc."
        -- EQ_TRAP_DESCR  
        --  "ATM PVC '%s' of type '%s' added on module in slot labeled 
        --   '%s' (%d.%d.%d)."
        ::= { eqIfTraps 4 }

    eqAtmPvcRemoved NOTIFICATION-TYPE
        OBJECTS { eqTrapDescr, eqModuleShelfId, eqModuleSlotId, 
                  eqEid, eqIfName, eqAtmPvcType }
        STATUS  current
        DESCRIPTION
           "This trap indicates that an atm pvc has been deleted.

            eqTrapDescr provides a textual description for this trap.
            eqModuleShelfId is the shelf id in which the atm pvc
            has been deleted.
            eqModuleSlotId is the (shelf-relative) slot id in which 
            the atm pvc has been deleted.
            ifIndex is the id of the deleted atm pvc.
            eqIfName is the name of the deleted atm pvc.
            eqAtmPvcIfType is the pvc type of the deleted atm pvc."
        -- EQ_TRAP_DESCR  
        --  "ATM PVC '%s' of type '%s' deleted on module in slot labeled 
        --   '%s' (%d.%d.%d)."
        ::= { eqIfTraps 5 }

    eqAtmPvcModified NOTIFICATION-TYPE
        OBJECTS { eqTrapDescr, eqModuleShelfId, eqModuleSlotId, 
                  eqEid, eqIfName, eqAtmPvcType }
        STATUS  current
        DESCRIPTION
           "This trap indicates that an atm pvc has been modified.

            eqTrapDescr provides a textual description for this trap.
            eqModuleShelfId is the shelf id in which the atm pvc
            has been modified.
            eqModuleSlotId is the (shelf-relative) slot id in which 
            the atm pvc has been modified.
            ifIndex is the id of the modified atm pvc.
            eqIfName is the name of the modified atm pvc.
            eqAtmPvcIfType is the pvc type of the modified atm pvc."
        -- EQ_TRAP_DESCR  
        --  "ATM PVC '%s' of type '%s' modified on module in slot labeled 
        --   '%s' (%d.%d.%d)."
        ::= { eqIfTraps 6 }

    --
    -- Sonet Traps.
    --

    eqSonetApsSwitchEvent NOTIFICATION-TYPE
        OBJECTS { eqTrapDescr, eqModuleShelfId, eqModuleSlotId, ifIndex, 
                  eqIfName, eqApsLineState }
        STATUS  current
        DESCRIPTION
           "This trap indicates that an aps protection switch event has
            taken place and the protecting line is now in the indicated
            state.

            eqTrapDescr provides a textual description for this trap.
            eqModuleShelfId is the shelf id in which the sonet port
            is located.
            eqModuleSlotId is the (shelf-relative) slot id in which 
            the sonet port is located.
            ifIndex is the eid of the sonet port.
            eqIfName is the name of the physical sonet port.
            eqApsLineState is the new state of the protecting line."
        -- EQ_TRAP_DESCR  
        --  "An APS switch event ocurred on sonet port labeled '%s'
        --   (%d.%d)".
        ::= { eqSonetTraps 1 }


    eqSonetApsWorkingLineRestored NOTIFICATION-TYPE
        OBJECTS { eqTrapDescr, eqModuleShelfId, eqModuleSlotId, ifIndex, 
                  eqIfName }
        STATUS  current
        DESCRIPTION
           "This trap indicates that a working line has resumed carrying
            user traffic. This could be due to an auto switch condition
            that has cleared or due to a problem detected on the
            working line.

            eqTrapDescr provides a textual description for this trap.
            eqModuleShelfId is the shelf id in which the sonet port
            is located.
            eqModuleSlotId is the (shelf-relative) slot id in which 
            the sonet port is located.
            ifIndex is the eid of the sonet port.
            eqIfName is the name of the physical sonet port."
        -- EQ_TRAP_DESCR  
        --  "An APS working line has been restored on sonet port
        --   labeled '%s' (%d.%d)".
        ::= { eqSonetTraps 2 }

    eqSonetApsModeMismatch NOTIFICATION-TYPE
        OBJECTS { eqTrapDescr, eqModuleShelfId, eqModuleSlotId, ifIndex, 
                  eqIfName }
        STATUS  current
        DESCRIPTION
           "This trap indicates that a mode mismatch has been detected
            based on the port's aps configuration and the received
            K2 byte. This can happen when one LTE is configured for
            1+1 APS and the other for 1:N APS. The LTE configured for
            1:N will fallback to 1+1 mode.

            eqTrapDescr provides a textual description for this trap.
            eqModuleShelfId is the shelf id in which the sonet port
            is located.
            eqModuleSlotId is the (shelf-relative) slot id in which 
            the sonet port is located.
            ifIndex is the eid of the sonet port.
            eqIfName is the name of the physical sonet port."
        -- EQ_TRAP_DESCR  
        --  "An APS mode mismatch has been detected on sonet port 
        --   labeled '%s' (%d.%d)".
        ::= { eqSonetTraps 3 }

    eqSonetApsProtectLineFailure NOTIFICATION-TYPE
        OBJECTS { eqTrapDescr, eqModuleShelfId, eqModuleSlotId, ifIndex, 
                  eqIfName }
        STATUS  current
        DESCRIPTION
           "This trap indicates that a protecting line is now in a failed
            state. APS switchover to the protection line will not be 
            possible. If the protecting line was carrying user traffic, 
            it is switched back to the working line.

            eqTrapDescr provides a textual description for this trap.
            eqModuleShelfId is the shelf id in which the sonet port
            is located.
            eqModuleSlotId is the (shelf-relative) slot id in which 
            the sonet port is located.
            ifIndex is the eid of the sonet port.
            eqIfName is the name of the physical sonet port."
        -- EQ_TRAP_DESCR  
        --  "An APS protection line failure has been detected on
        --   sonet port labeled '%s' (%d.%d)".
        ::= { eqSonetTraps 4 }

    eqSonetApsProtectLineRestored NOTIFICATION-TYPE
        OBJECTS { eqTrapDescr, eqModuleShelfId, eqModuleSlotId, ifIndex, 
                  eqIfName }
        STATUS  current
        DESCRIPTION
           "This trap indicates that protection line is now in an
            operational state and an aps switchover to protection is
            now possible.

            eqTrapDescr provides a textual description for this trap.
            eqModuleShelfId is the shelf id in which the sonet port
            is located.
            eqModuleSlotId is the (shelf-relative) slot id in which 
            the sonet port is located.
            ifIndex is the eid of the sonet port.
            eqIfName is the name of the physical sonet port."
        -- EQ_TRAP_DESCR  
        --  "An APS protection line has been restored on sonet port 
        --   labeled '%s' (%d.%d)".
        ::= { eqSonetTraps 5 }

    eqSonetApsProtectByteFailure NOTIFICATION-TYPE
        OBJECTS { eqTrapDescr, eqModuleShelfId, eqModuleSlotId, ifIndex, 
                  eqIfName }
        STATUS  current
        DESCRIPTION
           "This trap indicates that the protection line has declared
            a protection byte failure. This happens when a protection
            byte defect or inconsistent K1 byte is received and the 
            condition persists for 2.5 seconds. When this happens, 
            aps switchover to protection is prohibited. If the
            protection line was carrying any user traffic, it is 
            switched over to the working line.

            eqTrapDescr provides a textual description for this trap.
            eqModuleShelfId is the shelf id in which the sonet port
            is located.
            eqModuleSlotId is the (shelf-relative) slot id in which 
            the sonet port is located.
            ifIndex is the eid of the sonet port.
            eqIfName is the name of the physical sonet port."
        -- EQ_TRAP_DESCR  
        --  "An APS protection byte failure has been detected on 
        --   sonet port labeled '%s' (%d.%d)".
        ::= { eqSonetTraps 6 }

    eqSonetApsFarEndProtectLineFailure NOTIFICATION-TYPE
        OBJECTS { eqTrapDescr, eqModuleShelfId, eqModuleSlotId, ifIndex, 
                  eqIfName }
        STATUS  current
        DESCRIPTION
           "This trap indicates that a far end protection line failure 
            has been declared. This happens when the received K1 byte
            indicates SF on the protection line and the condition persists
            for 2.5 seconds.

            eqTrapDescr provides a textual description for this trap.
            eqModuleShelfId is the shelf id in which the sonet port
            is located.
            eqModuleSlotId is the (shelf-relative) slot id in which 
            the sonet port is located.
            ifIndex is the eid of the sonet port.
            eqIfName is the name of the physical sonet port."
        -- EQ_TRAP_DESCR  
        --  "An APS far end protection line failure has been detcted on 
        --   sonet port labeled '%s' (%d.%d)".
        ::= { eqSonetTraps 7 }

    eqSonetApsFarEndProtectLineCleared NOTIFICATION-TYPE
        OBJECTS { eqTrapDescr, eqModuleShelfId, eqModuleSlotId, ifIndex, 
                  eqIfName }
        STATUS  current
        DESCRIPTION
           "This trap indicates that a far end protection line failure 
            has been cleared. This happens 10 seconds after a K1 byte is 
            received without SF indication on the protection line.

            eqTrapDescr provides a textual description for this trap.
            eqModuleShelfId is the shelf id in which the sonet port
            is located.
            eqModuleSlotId is the (shelf-relative) slot id in which 
            the sonet port is located.
            ifIndex is the eid of the sonet port.
            eqIfName is the name of the physical sonet port."
        -- EQ_TRAP_DESCR  
        --  "An APS far end protection line has been cleared on 
        --   sonet port labeled '%s' (%d.%d)".
        ::= { eqSonetTraps 8 }

    --
    -- EBOX Application traps
    --

    --
    --    SRM traps
    --

    eqSrmFault NOTIFICATION-TYPE
        OBJECTS { eqTrapDescr, eqFaultTime, eqFaultScope, eqFaultModule, 
                  eqFaultSwlm }
        STATUS  current
        DESCRIPTION
           "This trap indicates that an srm fault has occurred.

            eqTrapDescr provides a textual description for this trap.
            eqSrmFaultDomain identifies the fault domain.
            eqSrmFaultHandle is the fault handle.
            eqSrmFaultTime contains the time at which the fault occurred."
        -- EQ_TRAP_DESCR  
        --  "SRM fault occurred on module '%s' in slot labeled '%s' in
        --   software load module '%s'."
        ::= { eqSrmTraps 1 }


END
