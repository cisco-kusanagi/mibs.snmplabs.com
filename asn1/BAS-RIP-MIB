BAS-RIP-MIB DEFINITIONS ::= BEGIN
    IMPORTS
        
        MODULE-IDENTITY, OBJECT-TYPE, Counter32, 
        IpAddress                         FROM SNMPv2-SMI
        TruthValue                        FROM SNMPv2-TC
        TimeTicks                         FROM RFC1155-SMI
        RowStatus                         FROM SNMPv2-TC
	basRip          		  FROM BAS-MIB;
        
        -- ------------------------------------------------------------ --
        --
        --  The following OBJECT IDENTIFIER definition should be moved to
        --  some other location, to conform with the statement in RFC 1442
        --  that the MODULE-IDENTITY section must appear immediately after
        --  any IMPORTs or EXPORTs statements.
        --
        --  However, some MIB utilities don't like MODULE-IDENTITY OIDs of
        --  the form { enterprises atmForum(353) ... 1 }.  Separate OBJECT
        --  IDENTIFIER definitions appear to be more widely accepted - so,
        --  in the interests of compatibility, it remains.
        --
        -- ------------------------------------------------------------ --


            basRIP MODULE-IDENTITY
                LAST-UPDATED "9704170315Z"
                ORGANIZATION "BAS Systems"
                CONTACT-INFO
                      "Dheerendra Talur
	                 Postal: BAS Systems
                       1595 Spring Hill Road
                       5th Floor
                       Vienna, VA 22182

                       Phone:  703-245-4561
                       E-Mail: dtalur@bas.com"

                DESCRIPTION
                    "This module defines a portion of the proprietary
                     management information base (MIB) for managing routing
                     information protocol (RIP)."
                ::= { basRip 1 }

            -- The object identifier subtree for BAS Proprietary RIP MIB
            -- This Proprietary MIB module consists of following objects
            --
            -- (1) Rip statistics group
            --
            -- (2) Rip Interface table
            --
            -- (3) Rip Neighbor table
            --
            --
            -- ------------------------------------------------------------- --

            --
            --  Group of RIP Statistics since last clear
            --

            ripIfStatsCurGroup OBJECT IDENTIFIER
                ::= { basRIP 1 }
            
            ripIfResetTime OBJECT-TYPE
                SYNTAX TimeTicks
                MAX-ACCESS read-only
                STATUS current
                DESCRIPTION
                    "Time of last stats clear"
                ::= {ripIfStatsCurGroup 1}
 
            ripIfStatsIntfCnt OBJECT-TYPE
                SYNTAX Counter32
                MAX-ACCESS read-only
                STATUS current
                DESCRIPTION
                    "Number of enabled interfaces running RIP"
                ::= {ripIfStatsCurGroup 2}
            
            ripIfStatsNbrCnt OBJECT-TYPE
                SYNTAX Counter32
                MAX-ACCESS read-only
                STATUS current
                DESCRIPTION
                    "Total number of neighbors of all RIP interfaces"
                ::= {ripIfStatsCurGroup 3}
            
            ripIfStatsPktsRcvd OBJECT-TYPE
                SYNTAX Counter32
                MAX-ACCESS read-only
                STATUS current
                DESCRIPTION
                    "Total number of RIP packets received on all interfaces"
                ::= {ripIfStatsCurGroup 4}
            
            ripIfStatsPktsSent OBJECT-TYPE
                SYNTAX Counter32
                MAX-ACCESS read-only
                STATUS current
                DESCRIPTION
                    "Total number of RIP packets sent out on all interfaces"
                ::= {ripIfStatsCurGroup 5}
            
            ripIfStatsReqsRcvd OBJECT-TYPE
                SYNTAX Counter32
                MAX-ACCESS read-only
                STATUS current
                DESCRIPTION
            	"Total number of RIP requests received on all interfaces"
                ::= {ripIfStatsCurGroup 6}
            
            ripIfStatsReqsSent OBJECT-TYPE
                SYNTAX Counter32
                MAX-ACCESS read-only
                STATUS current
                DESCRIPTION
            	"Total number of RIP requests sent out on all interfaces"
                ::= {ripIfStatsCurGroup 7}
            
            ripIfStatsRspsRcvd OBJECT-TYPE
                SYNTAX Counter32
                MAX-ACCESS read-only
                STATUS current
                DESCRIPTION
            	"Total number of RIP responses received on all interfaces"
                ::= {ripIfStatsCurGroup 8}
            
            ripIfStatsRspsSent OBJECT-TYPE
                SYNTAX Counter32
                MAX-ACCESS read-only
                STATUS current
                DESCRIPTION
            	"Total number of RIP responses sent out on all interfaces"
                ::= {ripIfStatsCurGroup 9}
            
            ripIfStatsRteTimouts OBJECT-TYPE
                SYNTAX Counter32
                MAX-ACCESS read-only
                STATUS current
                DESCRIPTION
                    "Total number of RIP routes timed out"
                ::= {ripIfStatsCurGroup 10}
            
            ripIfStatsShrtPktsRcvd OBJECT-TYPE
                SYNTAX Counter32
                MAX-ACCESS read-only
                STATUS current
                DESCRIPTION
                    "Total number of RIP packets with size less than RIP header size
            	received on all interfaces"
                ::= {ripIfStatsCurGroup 11}
            
            ripIfStatsBadVerRcvd OBJECT-TYPE
                SYNTAX Counter32
                MAX-ACCESS read-only
                STATUS current
                DESCRIPTION
                    "Total number of RIP packets with version other than
		RIP version 1 or RIP version 2, received on all interfaces"
                ::= {ripIfStatsCurGroup 12}
            
            ripIfStatsBadZeroRcvd OBJECT-TYPE
                SYNTAX Counter32
                MAX-ACCESS read-only
                STATUS current
                DESCRIPTION
                    "Total number of RIP packets with must be zero fields not set to 
            	zero, received on all interfaces" 
                ::= {ripIfStatsCurGroup 13}
            
            ripIfStatsBadSrcPortRcvd OBJECT-TYPE
                SYNTAX Counter32
                MAX-ACCESS read-only
                STATUS current
                DESCRIPTION
                    "Total number of RIP packets which did not originate from port
		520, received on all interfaces"
                ::= {ripIfStatsCurGroup 14}
            
            ripIfStatsBadSrcIpRcvd OBJECT-TYPE
                SYNTAX Counter32
                MAX-ACCESS read-only
                STATUS current
                DESCRIPTION
                    "Total number of RIP packets with invalid ip address,
            	received on all interfaces"
                ::= {ripIfStatsCurGroup 15}
            
            ripIfStatsPktsFrmSelfRcvd OBJECT-TYPE
                SYNTAX Counter32
                MAX-ACCESS read-only
                STATUS current
                DESCRIPTION
                    "Total number of RIP packets with receiver being the sender on all
            	interfaces"
                ::= {ripIfStatsCurGroup 16}
            
            ripIfStatsReset OBJECT-TYPE
                SYNTAX TruthValue
                MAX-ACCESS read-write
                STATUS current
                DESCRIPTION
                    "Writing a 1 in ripIfStatsReset has the effect of
                clearing current RIP statistics"
                ::= {ripIfStatsCurGroup 17}
            

            --
            -- Group of RIP statistics since system reset (all stats)
            --

            ripIfStatsAllGroup OBJECT IDENTIFIER
                ::= { basRIP 2 }

            ripIfAllResetTime OBJECT-TYPE
                SYNTAX TimeTicks
                MAX-ACCESS read-only
                STATUS current
                DESCRIPTION
                    "Time since system reboot"
                ::= {ripIfStatsAllGroup 1}
 
            ripIfAllStatsIntfCnt OBJECT-TYPE
                SYNTAX Counter32
                MAX-ACCESS read-only
                STATUS current
                DESCRIPTION
                    "Number of interfaces (enabled and disabled) running RIP"
                ::= {ripIfStatsAllGroup 2}
            
            ripIfAllStatsNbrCnt OBJECT-TYPE
                SYNTAX Counter32
                MAX-ACCESS read-only
                STATUS current
                DESCRIPTION
                    "Total number of neighbors of all RIP interfaces"
                ::= {ripIfStatsAllGroup 3}
            
            ripIfAllStatsPktsRcvd OBJECT-TYPE
                SYNTAX Counter32
                MAX-ACCESS read-only
                STATUS current
                DESCRIPTION
                    "Total number of RIP packets received on all interfaces"
                ::= {ripIfStatsAllGroup 4}
            
            ripIfAllStatsPktsSent OBJECT-TYPE
                SYNTAX Counter32
                MAX-ACCESS read-only
                STATUS current
                DESCRIPTION
                    "Total number of RIP packets sent out on all interfaces"
                ::= {ripIfStatsAllGroup 5}
            
            ripIfAllStatsReqsRcvd OBJECT-TYPE
                SYNTAX Counter32
                MAX-ACCESS read-only
                STATUS current
                DESCRIPTION
            	"Total number of RIP requests received on all interfaces"
                ::= {ripIfStatsAllGroup 6}
            
            ripIfAllStatsReqsSent OBJECT-TYPE
                SYNTAX Counter32
                MAX-ACCESS read-only
                STATUS current
                DESCRIPTION
            	"Total number of RIP requests sent out on all interfaces"
                ::= {ripIfStatsAllGroup 7}
            
            ripIfAllStatsRspsRcvd OBJECT-TYPE
                SYNTAX Counter32
                MAX-ACCESS read-only
                STATUS current
                DESCRIPTION
            	"Total number of RIP responses received on all interfaces"
                ::= {ripIfStatsAllGroup 8}
            
            ripIfAllStatsRspsSent OBJECT-TYPE
                SYNTAX Counter32
                MAX-ACCESS read-only
                STATUS current
                DESCRIPTION
            	"Total number of RIP responses sent out on all interfaces"
                ::= {ripIfStatsAllGroup 9}
            
            ripIfAllStatsRteTimouts OBJECT-TYPE
                SYNTAX Counter32
                MAX-ACCESS read-only
                STATUS current
                DESCRIPTION
                    "Total number of RIP routes timed out"
                ::= {ripIfStatsAllGroup 10}
            
            ripIfAllStatsShrtPktsRcvd OBJECT-TYPE
                SYNTAX Counter32
                MAX-ACCESS read-only
                STATUS current
                DESCRIPTION
                    "Total number of RIP packets with size less than RIP header size
            	received on all interfaces"
                ::= {ripIfStatsAllGroup 11}
            
            ripIfAllStatsBadVerRcvd OBJECT-TYPE
                SYNTAX Counter32
                MAX-ACCESS read-only
                STATUS current
                DESCRIPTION
                    "Total number of RIP packets with version other than
		RIP version 1 or RIP version 2, received on all interfaces"
                ::= {ripIfStatsAllGroup 12}
            
            ripIfAllStatsBadZeroRcvd OBJECT-TYPE
                SYNTAX Counter32
                MAX-ACCESS read-only
                STATUS current
                DESCRIPTION
                    "Total number of RIP packets with must be zero fields not set to 
            	zero, received on all interfaces" 
                ::= {ripIfStatsAllGroup 13}
            
            ripIfAllStatsBadSrcPortRcvd OBJECT-TYPE
                SYNTAX Counter32
                MAX-ACCESS read-only
                STATUS current
                DESCRIPTION
                    "Total number of RIP packets which did not originate from port
		520, received on all interfaces"
                ::= {ripIfStatsAllGroup 14}
            
            ripIfAllStatsBadSrcIpRcvd OBJECT-TYPE
                SYNTAX Counter32
                MAX-ACCESS read-only
                STATUS current
                DESCRIPTION
                    "Total number of RIP packets with invalid ip address,
            	received on all interfaces"
                ::= {ripIfStatsAllGroup 15}
            
            ripIfAllStatsPktsFrmSelfRcvd OBJECT-TYPE
                SYNTAX Counter32
                MAX-ACCESS read-only
                STATUS current
                DESCRIPTION
                    "Total number of RIP packets with receiver being the sender on all
            	interfaces"
                ::= {ripIfStatsAllGroup 16}
            
            --
            -- RIP Interface table 
            --

            basRipIfTable OBJECT-TYPE
                SYNTAX   SEQUENCE OF BasRipIfEntry
                MAX-ACCESS   not-accessible
                STATUS   current
                DESCRIPTION
                   "This is used for proprietry interface info."
                REFERENCE
                   "Scalable Routing IDD. Section on RIP."
                ::= { basRIP 4 }
            
            basRipIfEntry OBJECT-TYPE
                SYNTAX  BasRipIfEntry
                MAX-ACCESS not-accessible
                STATUS   current
                DESCRIPTION
                   "Interface configuration entry."
                INDEX {
                        ripIfIpAddress,
                        ripIfAddressLessIf
                      }
                ::= { basRipIfTable 1 }
            
            BasRipIfEntry ::=
               SEQUENCE {
                     --
                     -- Index ipaddress, ifindex
                     --
                     ripIfIpAddress
                        IpAddress,
                     ripIfAddressLessIf
                        INTEGER,

                     --
                     -- Interface parameters
                     --
                     ripIfType
                        INTEGER,
                     ripIfVersion
                        INTEGER,
                     ripIfRecvVer
                        INTEGER,
                     ripIfMetric
                        INTEGER,
                     ripIfAcceptDefault
                        TruthValue,
                     ripIfSilent
                        TruthValue,
                     ripIfRecvRoutes
                        TruthValue,
                     ripIfSubnetsOnly
                        TruthValue,
                     ripIfSendDefaultOnly
                        TruthValue,
                     ripIfSendDefaultAlso
                        TruthValue,
                     ripIfDfltRouteMetric
                        INTEGER,
                     ripIfSplitHorizon
                        TruthValue,
                     ripIfPoison
                        TruthValue,
                     ripIfFlash
                        TruthValue,

                     --
                     -- Authentication related fields
                     --
                     ripAuthOn
                        TruthValue,
                     ripIfAuthType
                        INTEGER,
                     ripIfAuthKeyId
                        INTEGER,
                     ripIfAuthKey
                         OCTET STRING (SIZE(0..16)),

                     --
                     -- Parameters related to RIP updates
                     --
                     ripIfUpdateInterval
                        INTEGER,
                     ripIfUpdateInterPktGap
                        INTEGER,
                     ripIfPktsPerUpdate
                        INTEGER,

                     --
                     -- Administrative fields
                     --
                     ripIfPortDown
                        TruthValue,
                     ripIfRowStat
                        RowStatus
                 }
            
            ripIfIpAddress OBJECT-TYPE
                SYNTAX IpAddress
                MAX-ACCESS read-write
                STATUS current
                DESCRIPTION
                    "Ip address of the interface running RIP"
                ::= {basRipIfEntry 1}
            
            ripIfAddressLessIf OBJECT-TYPE
                SYNTAX INTEGER
                MAX-ACCESS read-write
                STATUS current
                DESCRIPTION
                    "IfIndex of the interface running RIP"
                ::= {basRipIfEntry 2}
            
            ripIfType OBJECT-TYPE
                SYNTAX INTEGER {
				ripIfTypeBroadcast(1),
				ripIfTypeNBMA(2),
				ripIfTypePointToPoint(3)
			}
                MAX-ACCESS read-write
                STATUS current
                DESCRIPTION
                    "Type of the interface running RIP"
                ::= {basRipIfEntry 3}
            
            ripIfVersion OBJECT-TYPE
                SYNTAX INTEGER {
				ripSendNone(1),
				ripSendVer1(2),
				ripSendCompat(3),
				ripSendVer2(4),
				ripSendVer1Demand(5),
				ripSendVer2Demand(6)
			}
                MAX-ACCESS read-write
		STATUS current
		DESCRIPTION
			"What the router sends on this interface.
                ripVersion1 implies sending RIP updates compliant
                with  RFC  1058.  ripSendCompat  implies
                broadcasting RIP-2 updates using RFC 1058 route
                subsumption rules.  ripSendVer2 implies
                multicasting RIP-2 updates.  ripSendVer1Demand
                indicates the use of Demand RIP on a WAN interface
                under RIP Version 1 rules.  ripSendVer2Demand
                indicates the use of Demand RIP on a WAN interface
                under Version 2 rules." 
                ::= {basRipIfEntry 4}
            
            ripIfRecvVer OBJECT-TYPE
	        SYNTAX INTEGER {
                    ripRcvVer1 (1),
                    ripRcvVer2 (2),
                    ripRcvVer1and2 (3),
                    ripRcvNone (4)
                 }
                MAX-ACCESS read-write
                STATUS current
                DESCRIPTION
                     "This indicates which version of RIP updates
                are to be accepted.  Note that ripRcvVer2 and
                ripRcvVer1and2 implies reception of multicast
                packets."
                ::= {basRipIfEntry 5}

            ripIfMetric OBJECT-TYPE
                SYNTAX INTEGER
                MAX-ACCESS read-write
                STATUS current
                DESCRIPTION
                    "Value of metric corresponding to this
		interface. Metric value will be added to all routes
                leared from this interface"
                ::= {basRipIfEntry 6}
            
            ripIfAcceptDefault OBJECT-TYPE
                SYNTAX TruthValue
                MAX-ACCESS read-write
                STATUS current
                DESCRIPTION
                    "If ripIfAcceptDefault is TRUE then default routes
                will be accepted on this interface"
                ::= {basRipIfEntry 7}
            
            ripIfSilent OBJECT-TYPE
                SYNTAX TruthValue
                MAX-ACCESS read-write
                STATUS current
                DESCRIPTION
                    "If ripIfSilent is TRUE then no RIP updates would
                be sent of by this interface"
                ::= {basRipIfEntry 8}
            
            ripIfRecvRoutes OBJECT-TYPE
                SYNTAX TruthValue
                MAX-ACCESS read-write
                STATUS current
                DESCRIPTION
                    "If ripIfRecvRoutes is TRUE then RIP updates 
                received on this interface are disregarded"
                ::= {basRipIfEntry 9}

            ripIfSubnetsOnly OBJECT-TYPE
                SYNTAX TruthValue
                MAX-ACCESS read-write
                STATUS current
                DESCRIPTION
                    "If ripIfSubnetsOnly is TRUE, then "
                ::= {basRipIfEntry 10}
            
            ripIfSendDefaultOnly OBJECT-TYPE
                SYNTAX TruthValue
                MAX-ACCESS read-write
                STATUS current
                DESCRIPTION
                    "If ripIfSendDefaultOnly is TRUE, RIP update from
                this interface would consist of only the default
                route" 
                ::= {basRipIfEntry 11}

            ripIfSendDefaultAlso OBJECT-TYPE
                SYNTAX TruthValue
                MAX-ACCESS read-write
                STATUS current
                DESCRIPTION
                    "If ripIfSendDefaultAlso is TRUE, RIP update from
                this interface would consist of default route along
                with other routes"
                ::= {basRipIfEntry 12}

            ripIfDfltRouteMetric OBJECT-TYPE
                SYNTAX INTEGER
                MAX-ACCESS read-write
                STATUS current
                DESCRIPTION
                    "This variable indicates the metric that is to
                be used for the default route entry in RIP updates
                originated on this interface."
                ::= {basRipIfEntry 13}
            
            ripIfSplitHorizon OBJECT-TYPE
                SYNTAX TruthValue
                MAX-ACCESS read-write
                STATUS current
                DESCRIPTION
                    "If ripIfSplitHorizon is TRUE, enables split
                horizon processing as defined in RFC 1058"
                ::= {basRipIfEntry 14}
            
            ripIfPoison OBJECT-TYPE
                SYNTAX TruthValue
                MAX-ACCESS read-write
                STATUS current
                DESCRIPTION
                    "In ripIfPoison is TRUE, enables Poison reverse
                updates on this interface. (Poison reverse is defined
                in RCF 1058)" 
                ::= {basRipIfEntry 15}
            
            ripIfFlash OBJECT-TYPE
                SYNTAX TruthValue
                MAX-ACCESS read-write
                STATUS current
                DESCRIPTION
                    "if ripIfFlash is TRUE flash updates will be sent
                out from this interface following a route change"
                ::= {basRipIfEntry 16}
            
            ripAuthOn OBJECT-TYPE
                SYNTAX TruthValue
                MAX-ACCESS read-write
                STATUS current
                DESCRIPTION
                    "If ripAuthOn TRUE enables authentication on this
                interface. All updates generated from this interface
                would be authenticated using specified authentication
                type set by ripIfAuthType" 
                ::= {basRipIfEntry 17}

            ripIfAuthType OBJECT-TYPE
                SYNTAX   INTEGER {
                        noAuthentication (1),
                        simplePassword (2),
                        md5 (3)
                    }
                MAX-ACCESS read-write
                STATUS current
                DESCRIPTION
                    "The type of Authentication used on this
                interface."
                ::= {basRipIfEntry 18}
            
            ripIfAuthKeyId OBJECT-TYPE
                SYNTAX   INTEGER
                MAX-ACCESS read-write
                STATUS current
                DESCRIPTION
                    "md5 authentication keyid used for this
                interface. RFC2082 describes md5 authentication and
                keyids" 
                ::= {basRipIfEntry 19}

            ripIfAuthKey OBJECT-TYPE
                SYNTAX OCTET STRING (SIZE(0..16))
                MAX-ACCESS read-write
                STATUS current
                DESCRIPTION
                  "The value to be used as the Authentication Key
                whenever the corresponding instance of
                ripIfAuthType has a value other than
                noAuthentication.  A modification of the corresponding
                instance of ripIfAuthType does not modify
                the rip2IfConfAuthKey value.  If a string shorter
                than 16 octets is supplied, it will be left-
                justified and padded to 16 octets, on the right,
                with nulls (0x00).
     
                Reading this object always results in an  OCTET
                STRING of length zero; authentication may not
                be bypassed by reading the MIB object."
                     ::= {basRipIfEntry 20}
            
            ripIfUpdateInterval OBJECT-TYPE
                SYNTAX INTEGER
                MAX-ACCESS read-only
                STATUS current
                DESCRIPTION
                    "Time between 2 RIP updates for this interface" 
                ::= {basRipIfEntry 21}
            
            ripIfUpdateInterPktGap OBJECT-TYPE
                SYNTAX INTEGER
                MAX-ACCESS read-only
                STATUS current
                DESCRIPTION
                    "Time between sending 2 packets of the same RIP
                update when update is more than 1 packet"
                ::= {basRipIfEntry 22}
            
            ripIfPktsPerUpdate OBJECT-TYPE
                SYNTAX INTEGER
                MAX-ACCESS read-only
                STATUS current
                DESCRIPTION
                    "Maximum number of packets allowed per update on
                this interface"
                ::= {basRipIfEntry 23}
            
            ripIfPortDown OBJECT-TYPE
                SYNTAX TruthValue
                MAX-ACCESS read-only
                STATUS current
                DESCRIPTION
                    "Indicates if port on which this interface exists
                is down."
                ::= {basRipIfEntry 24}
            
            ripIfRowStat OBJECT-TYPE
                SYNTAX RowStatus
                MAX-ACCESS read-write
                STATUS current
                DESCRIPTION
                    "Administrative control over, creation and
                enabling RIP interface "
                ::= {basRipIfEntry 25}
            
            --
            -- RIP Neighbor table
            --

            basRipNbrTable OBJECT-TYPE
                SYNTAX   SEQUENCE OF BasRipNbrEntry
                MAX-ACCESS   not-accessible
                STATUS   current
                DESCRIPTION
                   "Neighbor table"
                REFERENCE
                   "Scalable Routing IDD. Section on RIP."
                ::= { basRIP 3 }
            
            basRipNbrEntry OBJECT-TYPE
                SYNTAX  BasRipNbrEntry
                MAX-ACCESS not-accessible
                STATUS   current
                DESCRIPTION
                    "A particular neighbour entry."
                INDEX {
                        ripNbrIfIpAddr,
                        ripNbrIpAddr
                      }
                ::= { basRipNbrTable 1 }
            
            BasRipNbrEntry ::= 
               SEQUENCE {
                     ripNbrIfIpAddr
                        IpAddress,
                     ripNbrIpAddr
                        IpAddress,
                     ripNbrAddressLessIf
                        INTEGER,
                     ripNbrType
                        INTEGER,
                     ripNbrLastUpdate
                        Counter32,
                     ripNbrTriggerMode
                        INTEGER,
                     ripNbrRowStatus
                        RowStatus
                 }
            
            ripNbrIfIpAddr OBJECT-TYPE
                SYNTAX IpAddress
                MAX-ACCESS not-accessible
                STATUS current
                DESCRIPTION
                    "Ip address on the RIP interface of which this is
                a neighbor"
                ::= {basRipNbrEntry 1}
            
            ripNbrIpAddr OBJECT-TYPE
                SYNTAX IpAddress
                MAX-ACCESS not-accessible
                STATUS current
                DESCRIPTION
                    "Ip address of the neighbor"
                ::= {basRipNbrEntry 2}
            
            ripNbrAddressLessIf OBJECT-TYPE
                SYNTAX INTEGER                
                MAX-ACCESS read-only
                STATUS current
                DESCRIPTION
                    "If index of the RIP interface
                on this this is a neighbor"
                ::= {basRipNbrEntry 3}
            
            ripNbrType OBJECT-TYPE
                SYNTAX INTEGER {
                        ripNbrTypeConfigured(1),
                        ripNbrTypeDiscovered(2)
                   }
                MAX-ACCESS read-only
                STATUS current
                DESCRIPTION
                    "Neighbor type is ripNbrTypeConfigured if it
                is configured on the interface. A neighbor is of type
                discovered it is not configured and updates from this
                neighbor are received on this interface"
                ::= {basRipNbrEntry 4}
            
            ripNbrLastUpdate OBJECT-TYPE
                SYNTAX Counter32
                MAX-ACCESS read-only
                STATUS current
                DESCRIPTION
                    "Time simce last update was received from this
                neighbor" 
                ::= {basRipNbrEntry 5}

            ripNbrTriggerMode OBJECT-TYPE
                SYNTAX INTEGER
                MAX-ACCESS read-only
                STATUS current
                DESCRIPTION
                    "Indicates if the neighbor is triggered or not"
                ::= {basRipNbrEntry 6}
            
            ripNbrRowStatus OBJECT-TYPE
                SYNTAX RowStatus
                MAX-ACCESS read-write
                STATUS current
                DESCRIPTION
                    "Administrative control to creat and delete a
                neighbor" 
                ::= {basRipNbrEntry 7}
            
END
