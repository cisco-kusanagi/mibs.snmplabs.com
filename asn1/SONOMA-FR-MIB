-- |**********************************************************************|
 -- | Copyright 1999 - Sonoma Systems, Inc. Marina del Rey, CA 90292       |
 -- |    Unpublished software - All rights reserved.                       |
 -- |                                                                      |
 -- | The information in this software is subject to change without notice |
 -- | and should not be construed as a commitment by Sonoma Systems, Inc.  |
 -- |                                                                      |
 -- | Sonoma Systems, Inc. assumes no responsibility for the use or        |
 -- | reliability of its software on equipment which is not supplied by    |
 -- | Sonoma Systems, Inc.                                                 |
 -- |                                                                      |
 -- | This software is furnished under a license and may be copied only    |
 -- | under the terms of that license and with the inclusion of this       |
 -- | notice. This software, or any other copies thereof, may not be       |
 -- | provided or otherwise made available to any other person except to   |
 -- | one who agrees to these license terms. Title to and ownership of the |
 -- | software shall at all times remain with Sonoma Systems, Inc.         |
 -- |**********************************************************************|
 --
 -- Sonoma Systems Inc.,
 -- 4640 Admiralty Way, Suite #600,
 -- Marina Del Rey,
 -- California 90292-6695.
 --
 -- Web : www.sonoma-systems.com
 -- Phone:  310.827.8000
 --
 -- NAME        : sonfr.def
 --
 -- DESCRIPTION : This is the Sonoma private FR MIB.
 --
 -- ARCHIVE : $Archive:   M:\pvcs\pvcsproj\sonoma3\src\mib\sonfr.def  $
 -- REVISION: $Revision:   1.3  $
 -- AUTHOR  : $Author:   FREEVE  $
 -- DATE    : $Date:   Nov 13 1998 10:33:22  $

   SONOMA-FR-MIB DEFINITIONS ::= BEGIN

   IMPORTS
        OBJECT-TYPE
        FROM RFC-1212
        Counter
        FROM RFC1155-SMI
		sonomaSeries 
        FROM SONOMASYSTEMS-SONOMA-MIB;

        --
        -- Sonoma Systems defined groups
        --
        -- Define all the groups supported on the Sonoma Series
        -- of products.

        sonomaFR   OBJECT IDENTIFIER ::= { sonomaSeries 9 } 

   -- T1 Fractional Table

   sonomaFracTable OBJECT-TYPE
       SYNTAX SEQUENCE OF SonomaFracEntry
       ACCESS not-accessible
       STATUS mandatory
       DESCRIPTION
              ""
       ::= { sonomaFR 1 }

   sonomaFracEntry OBJECT-TYPE
       SYNTAX SonomaFracEntry
       ACCESS not-accessible
       STATUS mandatory
       DESCRIPTION
           ""
       INDEX { sonomaFracIndex }
       ::= { sonomaFracTable 1 }

   SonomaFracEntry ::= SEQUENCE {
           sonomaFracIndex
               INTEGER,
           sonomaFracCount
               INTEGER
       }

   sonomaFracIndex OBJECT-TYPE
       SYNTAX INTEGER
       ACCESS read-only
       STATUS mandatory
       DESCRIPTION
           "Same index as DSX1LineIndex."
       ::= { sonomaFracEntry 1 }

   sonomaFracCount OBJECT-TYPE
       SYNTAX INTEGER
       ACCESS read-write
       STATUS mandatory
       DESCRIPTION
           "Number of Fractional T1 channels (1 - 24)."
       ::= { sonomaFracEntry 2 }



   -- The FRF.5 Connection Type Table

   ccT5Table OBJECT-TYPE
       SYNTAX SEQUENCE OF CcT5Entry
       ACCESS not-accessible
       STATUS mandatory
       DESCRIPTION
           "FRF.5 Connection Type Table."
       ::= { sonomaFR 3 }

   ccT5Entry OBJECT-TYPE
       SYNTAX CcT5Entry
       ACCESS not-accessible
       STATUS mandatory
       DESCRIPTION
           "An entry in the cross-connection table of type FRF.5. The
	   indexing of this table is identical to pmCrossConnectionTable.
	   ccT5EndPointA will always refer to a FR logical port."
       INDEX { ccT5EndPointA, ccT5EndPointB }
       ::= { ccT5Table 1 }

   CcT5Entry ::= SEQUENCE {
           ccT5EndPointA
               INTEGER,
           ccT5EndPointB
               INTEGER,
           ccT5FRSSCSDLCI 
               INTEGER,
           ccT5DEtoCLPMapping
               INTEGER,
           ccT5CLPtoDEMapping
               INTEGER,
           ccT5SSCSManagement
               INTEGER,
           ccT5RowStatus
               INTEGER
       }

    ccT5EndPointA  OBJECT-TYPE
        SYNTAX  INTEGER (1..1024)
        ACCESS  read-only
        STATUS  mandatory
        DESCRIPTION
            "The logical port number."
       ::= { ccT5Entry 1 }


    ccT5EndPointB  OBJECT-TYPE
        SYNTAX  INTEGER (1..1024)
        ACCESS  read-only
        STATUS  mandatory
        DESCRIPTION
            "The logical port number."
       ::= { ccT5Entry 2 }

   ccT5FRSSCSDLCI OBJECT-TYPE
       SYNTAX INTEGER
       ACCESS read-write
       STATUS mandatory
       DESCRIPTION
           "DLCI which will be used over this interface. Can and often is
           different from the DLCI on the frame relay physical port."
       ::= { ccT5Entry 3 }

   ccT5DEtoCLPMapping OBJECT-TYPE
       SYNTAX INTEGER {
                       frandclp(1),
                       fronlyclp0(2),
                       fronlyclp1(3)
		       }
       ACCESS read-write
       STATUS mandatory
       DESCRIPTION
           "1 - Maps DE in Q.922 to DE in FR-SSCS frame and maps it to the CLP in ATM Header;
           2 - Maps DE in Q.922 to DE in FR-SSCS frame but always sets CLP in ATM header to 0.
           3 - Maps DE in Q.922 to DE in FR-SSCS frame but always sets CLP in ATM header to 1."
       DEFVAL { frandclp }
       ::= { ccT5Entry 4 }

   ccT5CLPtoDEMapping OBJECT-TYPE
       SYNTAX INTEGER {
                       fronly(1),
                       either(2)
		       }
       ACCESS read-write
       STATUS mandatory
       DESCRIPTION
           "1 - Maps DE in FR-SSCS to DE in Q.922 frame and maps it to the CLP in ATM Header;
           2 - Maps DE in FR-SSCS to DE in Q.922  frame but always sets CLP in ATM header to 0.
           3 - Maps DE in FR-SSCS to DE in Q.922 frame but always sets CLP in ATM header to 1."
       DEFVAL { either }
       ::= { ccT5Entry 5 }

   ccT5SSCSManagement OBJECT-TYPE
       SYNTAX INTEGER {
	          disabled(1),
			  enabled(2)
	          }
       ACCESS read-write
       STATUS mandatory
       DESCRIPTION
           "Enable FR SSCS Management."
       DEFVAL { disabled }
       ::= { ccT5Entry 6 }

   ccT5RowStatus OBJECT-TYPE
--     SYNTAX  RowStatus
       SYNTAX       INTEGER {
                  -- the following two values are states:
                  -- these values may be read or written
                  active(1),
                  notInService(2),

                  -- the following value is a state:
                  -- this value may be read, but not written
                  notReady(3),

                  -- the following three values are
                  -- actions: these values may be written,
                  --   but are never read
                  createAndGo(4),
                  createAndWait(5),
                  destroy(6)
                  }
       ACCESS read-write
       STATUS mandatory
       DESCRIPTION
             "This object is used to create new rows in this
             table, modify existing rows, and to delete
             existing rows."
       ::= { ccT5Entry 7 }

   -- The Sonoma FR DCE Port Table

   sonomaFRDcePortTable OBJECT-TYPE
       SYNTAX SEQUENCE OF SonomaFRDcePortEntry
       ACCESS not-accessible
       STATUS mandatory
       DESCRIPTION
           "Sonoma FR DCE Port Table."
       ::= { sonomaFR 4 }

   sonomaFRDcePortEntry OBJECT-TYPE
       SYNTAX SonomaFRDcePortEntry
       ACCESS not-accessible
       STATUS mandatory
       DESCRIPTION
           "An entry in the Sonoma FR Port Table which represents a DCE.
	   The main reason for this table is to support the Craft interface.
	   For this, the number of subids in the OID of the index needs to be
	   the same as for frLportEntry."
       INDEX { sonomaFRDcePort }
       ::= { sonomaFRDcePortTable 1 }

   SonomaFRDcePortEntry ::= SEQUENCE {
           sonomaFRDcePort
               INTEGER,
           sonomaFRDcePortType
               INTEGER,
           sonomaFRDcePortIncomingRateControl
               INTEGER,
           sonomaFRDcePortOutgoingRateControl 
               INTEGER
       }

    sonomaFRDcePort  OBJECT-TYPE
        SYNTAX  INTEGER (1..1024)
        ACCESS  read-only
        STATUS  mandatory
        DESCRIPTION
            "The FR port index."
       ::= { sonomaFRDcePortEntry 1 }

   sonomaFRDcePortType OBJECT-TYPE
       SYNTAX INTEGER {
	          dce(1),
			  dte(2)
	          }
       ACCESS read-write
       STATUS mandatory
       DESCRIPTION
           "."
       ::= { sonomaFRDcePortEntry 2 }

   sonomaFRDcePortIncomingRateControl OBJECT-TYPE
       SYNTAX INTEGER {
	          disabled(1),
			  enabled(2)
	          }
       ACCESS read-write
       STATUS mandatory
       DESCRIPTION
           "Enable the enforcement of incoming rate control."
       ::= { sonomaFRDcePortEntry 3 }

   sonomaFRDcePortOutgoingRateControl OBJECT-TYPE
       SYNTAX INTEGER {
	          disabled(1),
			  enabled(2)
	          }
       ACCESS read-write
       STATUS mandatory
       DESCRIPTION
           "Enable the enforcement of outgoing rate control."
       ::= { sonomaFRDcePortEntry 4 }


   -- The Sonoma FR DLCI Table

   sonomaFRDlciTable OBJECT-TYPE
       SYNTAX SEQUENCE OF SonomaFRDlciEntry
       ACCESS not-accessible
       STATUS mandatory
       DESCRIPTION
           "Sonoma FR Dlci Table."
       ::= { sonomaFR 5 }

   sonomaFRDlciEntry OBJECT-TYPE
       SYNTAX SonomaFRDlciEntry
       ACCESS not-accessible
       STATUS mandatory
       DESCRIPTION
           "An entry in the Sonoma FR Dlci Table. The only reason for this
	   table is to support the Craft interface. For this, the number of
	   subids in the OID of the index needs to be the same as for
	   frPVCEndptEntry."
       INDEX { sonomaFRDlciPort, sonomaFRDlci }
       ::= { sonomaFRDlciTable 1 }

   SonomaFRDlciEntry ::= SEQUENCE {
           sonomaFRDlciPort
               INTEGER,
           sonomaFRDlci
               INTEGER
       }

    sonomaFRDlciPort  OBJECT-TYPE
        SYNTAX  INTEGER (1..1024)
        ACCESS  read-only
        STATUS  mandatory
        DESCRIPTION
            "The FR port index."
       ::= { sonomaFRDlciEntry 1 }

    sonomaFRDlci  OBJECT-TYPE
        SYNTAX  INTEGER (1..1024)
        ACCESS  read-only
        STATUS  mandatory
        DESCRIPTION
            "The FR port index."
       ::= { sonomaFRDlciEntry 2 }


-- A copy of the frDlcmiTable from RFC 2115 to overcome limitation
-- in Craft about lengths of OIDs in tables.
sonomaFrDlcmiTable OBJECT-TYPE
 SYNTAX   SEQUENCE OF SonomaFrDlcmiEntry
 ACCESS   not-accessible
 STATUS   mandatory
 DESCRIPTION
	"The Parameters for the Data Link Connection Management
	Interface for the frame relay service on this
	interface."
 ::= { sonomaFR 6 }

sonomaFrDlcmiEntry OBJECT-TYPE
 SYNTAX   SonomaFrDlcmiEntry
 ACCESS   not-accessible
 STATUS   mandatory
 DESCRIPTION
	"The Parameters for a particular Data Link Connection
	Management Interface."
 INDEX { sonomaFrDlcmiIfIndex }
 ::= { sonomaFrDlcmiTable 1 }





SonomaFrDlcmiEntry ::= SEQUENCE {
	 sonomaFrDlcmiIfIndex                  INTEGER,
	 sonomaFrDlcmiState                    INTEGER,
	 sonomaFrDlcmiPollingInterval          INTEGER,
	 sonomaFrDlcmiFullEnquiryInterval      INTEGER,
	 sonomaFrDlcmiErrorThreshold           INTEGER,
	 sonomaFrDlcmiMonitoredEvents          INTEGER,
	 sonomaFrDlcmiStatus                   INTEGER
}


sonomaFrDlcmiIfIndex OBJECT-TYPE

 SYNTAX   INTEGER
 ACCESS   read-only
 STATUS   mandatory
 DESCRIPTION
	"The ifIndex value of the corresponding ifEntry."
 ::= { sonomaFrDlcmiEntry 1 }


sonomaFrDlcmiState OBJECT-TYPE
 SYNTAX INTEGER      {
	 noLmiConfigured (1),
	 lmiRev1         (2),
	 ansiT1617D      (3),  -- ANSI T1.617 Annex D
	 itut933A        (5)   -- CCITT Q933 Annex A
 }
 ACCESS   read-write
 STATUS   mandatory
 DESCRIPTION
	"This variable states which Data Link Connection
	Management scheme is active (and by implication, what
	DLCI it uses) on the Frame Relay interface."

 ::= { sonomaFrDlcmiEntry 2 }


sonomaFrDlcmiPollingInterval OBJECT-TYPE
 SYNTAX   INTEGER (5..30)
 ACCESS   read-write
 STATUS   mandatory
 DESCRIPTION
	"This is the number of seconds between successive
	status enquiry messages."
 DEFVAL { 10 }
 ::= { sonomaFrDlcmiEntry 5 }


sonomaFrDlcmiFullEnquiryInterval OBJECT-TYPE
 SYNTAX   INTEGER (1..255)
 ACCESS   read-write
 STATUS   mandatory
 DESCRIPTION
	"Number of status enquiry intervals that pass before
	issuance of a full status enquiry message."
 DEFVAL { 6 }
 ::= { sonomaFrDlcmiEntry 6 }


sonomaFrDlcmiErrorThreshold OBJECT-TYPE
 SYNTAX   INTEGER (1..10)
 ACCESS   read-write
 STATUS   mandatory
 DESCRIPTION
	"This is the maximum number of unanswered Status
	Enquiries the equipment shall accept before declaring
	the interface down."
 DEFVAL { 3 }
 ::= { sonomaFrDlcmiEntry 7 }


sonomaFrDlcmiMonitoredEvents OBJECT-TYPE
 SYNTAX   INTEGER (1..10)
 ACCESS   read-write
 STATUS   mandatory
 DESCRIPTION
	"This is the number of status polling intervals over
	which the error threshold is counted.  For example, if
	within 'MonitoredEvents' number of events the station
	receives 'ErrorThreshold' number of errors, the
	interface is marked as down."
 DEFVAL { 4 }
 ::= { sonomaFrDlcmiEntry 8 }


sonomaFrDlcmiStatus OBJECT-TYPE
 SYNTAX   INTEGER    {
			 running      (1),    -- init complete, system running
			 fault        (2),    -- error threshold exceeded
			 initializing (3)     -- system start up
			 }
 ACCESS   read-only
 STATUS   mandatory
 DESCRIPTION
	"This indicates the status of the Frame Relay interface
	as determined by the performance of the dlcmi.  If no
	dlcmi is running, the Frame Relay interface will stay
	in the running state indefinitely."
 ::= { sonomaFrDlcmiEntry 11 }


   -- The Sonoma FR DTE Port Table

   sonomaFRDtePortTable OBJECT-TYPE
       SYNTAX SEQUENCE OF SonomaFRDtePortEntry
       ACCESS not-accessible
       STATUS mandatory
       DESCRIPTION
           "Sonoma FR DTE Port Table."
       ::= { sonomaFR 7 }

   sonomaFRDtePortEntry OBJECT-TYPE
       SYNTAX SonomaFRDtePortEntry
       ACCESS not-accessible
       STATUS mandatory
       DESCRIPTION
           "An entry in the Sonoma FR Port Table which represents a DTE.
	   The main reason for this table is to support the Craft interface.
	   For this, the number of subids in the OID of the index needs to be
	   the same as for sonomaFrDlcmiEntry."
       INDEX { sonomaFRDtePort }
       ::= { sonomaFRDtePortTable 1 }

   SonomaFRDtePortEntry ::= SEQUENCE {
           sonomaFRDtePort
               INTEGER,
           sonomaFRDtePortType
               INTEGER
       }

    sonomaFRDtePort  OBJECT-TYPE
        SYNTAX  INTEGER (1..1024)
        ACCESS  read-only
        STATUS  mandatory
        DESCRIPTION
            "The FR port index."
       ::= { sonomaFRDtePortEntry 1 }

   sonomaFRDtePortType OBJECT-TYPE
       SYNTAX INTEGER {
	          dce(1),
			  dte(2)
	          }
       ACCESS read-write
       STATUS mandatory
       DESCRIPTION
           "."
       ::= { sonomaFRDtePortEntry 2 }


   -- The FRF.8 Connection Type Table

   ccT8Table OBJECT-TYPE
       SYNTAX SEQUENCE OF CcT8Entry
       ACCESS not-accessible
       STATUS mandatory
       DESCRIPTION
           "FRF.8 Connection Type Table."
       ::= { sonomaFR 8 }

   ccT8Entry OBJECT-TYPE
       SYNTAX CcT8Entry
       ACCESS not-accessible
       STATUS mandatory
       DESCRIPTION
           "An entry in the cross-connection table of type FRF.8. The
	   indexing of this table is identical to pmCrossConnectionTable.
	   ccT8EndPointA will always refer to a FR logical port."
       INDEX { ccT8EndPointA, ccT8EndPointB }
       ::= { ccT8Table 1 }

   CcT8Entry ::= SEQUENCE {
           ccT8EndPointA
               INTEGER,
           ccT8EndPointB
               INTEGER,
           ccT8DECLPMapping
               INTEGER,
           ccT8FECNEFCIMapping
               INTEGER,
		ccT8ULPEncapsulation               
				INTEGER,	
           ccT8RowStatus
               INTEGER
       }

    ccT8EndPointA  OBJECT-TYPE
        SYNTAX  INTEGER (1..1024)
        ACCESS  read-only
        STATUS  mandatory
        DESCRIPTION
            "The logical port or bundle number."
       ::= { ccT8Entry 1 }


    ccT8EndPointB  OBJECT-TYPE
        SYNTAX  INTEGER (1..1024)
        ACCESS  read-only
        STATUS  mandatory
        DESCRIPTION
            "The logical port or bundle number."
       ::= { ccT8Entry 2 }

   ccT8DECLPMapping OBJECT-TYPE
       SYNTAX INTEGER {
                       always0(1),
                       always1(2),
                       convert(3)
		       }
       ACCESS read-write
       STATUS mandatory
       DESCRIPTION
           ""
       DEFVAL { convert }
       ::= { ccT8Entry 3 }

   ccT8FECNEFCIMapping OBJECT-TYPE
       SYNTAX INTEGER {
                       always0(1),
                       always1(2),
                       convert(3)
	          }
       ACCESS read-write
       STATUS mandatory
       DESCRIPTION
           "FECN/EFCI Mapping."
       DEFVAL { convert }
       ::= { ccT8Entry 4 }

   ccT8ULPEncapsulation OBJECT-TYPE
       SYNTAX INTEGER {
	          disabled(1),
			  enabled(2)
	          }
       ACCESS read-write
       STATUS mandatory
       DESCRIPTION
           "ULP Encapsulation."
       DEFVAL { enabled }
       ::= { ccT8Entry 5 }

   ccT8RowStatus OBJECT-TYPE
--     SYNTAX  RowStatus
       SYNTAX       INTEGER {
                  -- the following two values are states:
                  -- these values may be read or written
                  active(1),
                  notInService(2),

                  -- the following value is a state:
                  -- this value may be read, but not written
                  notReady(3),

                  -- the following three values are
                  -- actions: these values may be written,
                  --   but are never read
                  createAndGo(4),
                  createAndWait(5),
                  destroy(6)
                  }
       ACCESS read-write
       STATUS mandatory
       DESCRIPTION
             "This object is used to create new rows in this
             table, modify existing rows, and to delete
             existing rows."
       ::= { ccT8Entry 6 }


   -- The Sonoma FR Port Statistics Table

   sonomaFRPortStatsTable OBJECT-TYPE
       SYNTAX SEQUENCE OF SonomaFRPortStatsEntry
       ACCESS not-accessible
       STATUS mandatory
       DESCRIPTION
           "Sonoma FR Port Statistics Table."
       ::= { sonomaFR 9 }

   sonomaFRPortStatsEntry OBJECT-TYPE
       SYNTAX SonomaFRPortStatsEntry
       ACCESS not-accessible
       STATUS mandatory
       DESCRIPTION
           "FR Port Statistics for both DCE and DTE ports."
       INDEX { sonomaFRPortStatsPort }
       ::= { sonomaFRPortStatsTable 1 }

   SonomaFRPortStatsEntry ::= SEQUENCE {
           sonomaFRPortStatsPort
               INTEGER,
           sonomaFRPortStatsRecvLIVReqs
               Counter,
           sonomaFRPortStatsSentLIVReqs
               Counter,
           sonomaFRPortStatsRecvLIVRsps
               Counter,
           sonomaFRPortStatsSentLIVRsps
               Counter,
           sonomaFRPortStatsRecvFullReqs
               Counter,
           sonomaFRPortStatsSentFullReqs
               Counter,
           sonomaFRPortStatsRecvFullRsps
               Counter,
           sonomaFRPortStatsSentFullRsps
               Counter,
           sonomaFRPortStatsRecvAsyncStatus
               Counter,
           sonomaFRPortStatsSentAsyncStatus
               Counter,
           sonomaFRPortStatsInvalidMessages
               Counter,
           sonomaFRPortStatsInvalidSeqNumbers
               Counter,
           sonomaFRPortStatsTimeouts
               Counter,
           sonomaFRPortStatsServAffectingConditions
               Counter
       }

    sonomaFRPortStatsPort  OBJECT-TYPE
        SYNTAX  INTEGER (1..1024)
        ACCESS  read-only
        STATUS  mandatory
        DESCRIPTION
            "The FR port index."
       ::= { sonomaFRPortStatsEntry 1 }

   sonomaFRPortStatsRecvLIVReqs OBJECT-TYPE
       SYNTAX Counter
       ACCESS read-only
       STATUS mandatory
       DESCRIPTION
           ""
       ::= { sonomaFRPortStatsEntry 2 }

   sonomaFRPortStatsSentLIVReqs OBJECT-TYPE
       SYNTAX Counter
       ACCESS read-only
       STATUS mandatory
       DESCRIPTION
           ""
       ::= { sonomaFRPortStatsEntry 3 }

   sonomaFRPortStatsRecvLIVRsps OBJECT-TYPE
       SYNTAX Counter
       ACCESS read-only
       STATUS mandatory
       DESCRIPTION
           ""
       ::= { sonomaFRPortStatsEntry 4 }

   sonomaFRPortStatsSentLIVRsps OBJECT-TYPE
       SYNTAX Counter
       ACCESS read-only
       STATUS mandatory
       DESCRIPTION
           ""
       ::= { sonomaFRPortStatsEntry 5 }

   sonomaFRPortStatsRecvFullReqs OBJECT-TYPE
       SYNTAX Counter
       ACCESS read-only
       STATUS mandatory
       DESCRIPTION
           ""
       ::= { sonomaFRPortStatsEntry 6 }

   sonomaFRPortStatsSentFullReqs OBJECT-TYPE
       SYNTAX Counter
       ACCESS read-only
       STATUS mandatory
       DESCRIPTION
           ""
       ::= { sonomaFRPortStatsEntry 7 }

   sonomaFRPortStatsRecvFullRsps OBJECT-TYPE
       SYNTAX Counter
       ACCESS read-only
       STATUS mandatory
       DESCRIPTION
           ""
       ::= { sonomaFRPortStatsEntry 8 }

   sonomaFRPortStatsSentFullRsps OBJECT-TYPE
       SYNTAX Counter
       ACCESS read-only
       STATUS mandatory
       DESCRIPTION
           ""
       ::= { sonomaFRPortStatsEntry 9 }

   sonomaFRPortStatsRecvAsyncStatus OBJECT-TYPE
       SYNTAX Counter
       ACCESS read-only
       STATUS mandatory
       DESCRIPTION
           ""
       ::= { sonomaFRPortStatsEntry 10 }

   sonomaFRPortStatsSentAsyncStatus OBJECT-TYPE
       SYNTAX Counter
       ACCESS read-only
       STATUS mandatory
       DESCRIPTION
           ""
       ::= { sonomaFRPortStatsEntry 11 }

   sonomaFRPortStatsInvalidMessages OBJECT-TYPE
       SYNTAX Counter
       ACCESS read-only
       STATUS mandatory
       DESCRIPTION
           ""
       ::= { sonomaFRPortStatsEntry 12 }

   sonomaFRPortStatsInvalidSeqNumbers OBJECT-TYPE
       SYNTAX Counter
       ACCESS read-only
       STATUS mandatory
       DESCRIPTION
           ""
       ::= { sonomaFRPortStatsEntry 13 }

   sonomaFRPortStatsTimeouts OBJECT-TYPE
       SYNTAX Counter
       ACCESS read-only
       STATUS mandatory
       DESCRIPTION
           ""
       ::= { sonomaFRPortStatsEntry 14 }

   sonomaFRPortStatsServAffectingConditions OBJECT-TYPE
       SYNTAX Counter
       ACCESS read-only
       STATUS mandatory
       DESCRIPTION
           ""
       ::= { sonomaFRPortStatsEntry 15 }

   -- The Sonoma Serial Port Statistics Table

   sonomaSerialPortStatsTable OBJECT-TYPE
       SYNTAX SEQUENCE OF SonomaSerialPortStatsEntry
       ACCESS not-accessible
       STATUS mandatory
       DESCRIPTION
           "Sonoma Serial Port Statistics Table.
		   The error statistics are copied from the rs232SyncPortTable.
		   "
       ::= { sonomaFR 10 }

   sonomaSerialPortStatsEntry OBJECT-TYPE
       SYNTAX SonomaSerialPortStatsEntry
       ACCESS not-accessible
       STATUS mandatory
       DESCRIPTION
           "Serial Port Statistics."
       INDEX { sonomaSerialPortStatsPort }
       ::= { sonomaSerialPortStatsTable 1 }

   SonomaSerialPortStatsEntry ::= SEQUENCE {
           sonomaSerialPortStatsPort
               INTEGER,
           sonomaSerialPortStatsRecvFrames
               Counter,
           sonomaSerialPortStatsSentFrames
               Counter,
           sonomaSerialPortStatsRecvBytes
               Counter,
           sonomaSerialPortStatsSentBytes
               Counter,
           sonomaSerialPortStatsRecvUtilization
               Counter,
           sonomaSerialPortStatsSendUtilization
               Counter,
           sonomaSerialPortStatsFrameCheckErrs
               Counter,
           sonomaSerialPortStatsTransmitUnderrunErrs
               Counter,
           sonomaSerialPortStatsReceiveOverrunErrs
               Counter,
           sonomaSerialPortStatsInterruptedFrames
               Counter,
           sonomaSerialPortStatsAbortedFrames
               Counter
       }

    sonomaSerialPortStatsPort  OBJECT-TYPE
        SYNTAX  INTEGER (1..1024)
        ACCESS  read-only
        STATUS  mandatory
        DESCRIPTION
            "The FR port index."
       ::= { sonomaSerialPortStatsEntry 1 }

   sonomaSerialPortStatsRecvFrames OBJECT-TYPE
       SYNTAX Counter
       ACCESS read-only
       STATUS mandatory
       DESCRIPTION
           ""
       ::= { sonomaSerialPortStatsEntry 2 }

   sonomaSerialPortStatsSentFrames OBJECT-TYPE
       SYNTAX Counter
       ACCESS read-only
       STATUS mandatory
       DESCRIPTION
           ""
       ::= { sonomaSerialPortStatsEntry 3 }

   sonomaSerialPortStatsRecvBytes OBJECT-TYPE
       SYNTAX Counter
       ACCESS read-only
       STATUS mandatory
       DESCRIPTION
           ""
       ::= { sonomaSerialPortStatsEntry 4 }

   sonomaSerialPortStatsSentBytes OBJECT-TYPE
       SYNTAX Counter
       ACCESS read-only
       STATUS mandatory
       DESCRIPTION
           ""
       ::= { sonomaSerialPortStatsEntry 5 }

   sonomaSerialPortStatsRecvUtilization OBJECT-TYPE
       SYNTAX Counter
       ACCESS read-only
       STATUS mandatory
       DESCRIPTION
           ""
       ::= { sonomaSerialPortStatsEntry 6 }

   sonomaSerialPortStatsSendUtilization OBJECT-TYPE
       SYNTAX Counter
       ACCESS read-only
       STATUS mandatory
       DESCRIPTION
           ""
       ::= { sonomaSerialPortStatsEntry 7 }

   sonomaSerialPortStatsFrameCheckErrs OBJECT-TYPE
       SYNTAX Counter
       ACCESS read-only
       STATUS mandatory
       DESCRIPTION
           ""
       ::= { sonomaSerialPortStatsEntry 8 }

   sonomaSerialPortStatsTransmitUnderrunErrs OBJECT-TYPE
       SYNTAX Counter
       ACCESS read-only
       STATUS mandatory
       DESCRIPTION
           ""
       ::= { sonomaSerialPortStatsEntry 9 }

   sonomaSerialPortStatsReceiveOverrunErrs OBJECT-TYPE
       SYNTAX Counter
       ACCESS read-only
       STATUS mandatory
       DESCRIPTION
           ""
       ::= { sonomaSerialPortStatsEntry 10 }

   sonomaSerialPortStatsInterruptedFrames OBJECT-TYPE
       SYNTAX Counter
       ACCESS read-only
       STATUS mandatory
       DESCRIPTION
           ""
       ::= { sonomaSerialPortStatsEntry 11 }

   sonomaSerialPortStatsAbortedFrames OBJECT-TYPE
       SYNTAX Counter
       ACCESS read-only
       STATUS mandatory
       DESCRIPTION
           ""
       ::= { sonomaSerialPortStatsEntry 12 }

   -- The Sonoma FR DLCI Statistics Table

   sonomaFRDlciStatsTable OBJECT-TYPE
       SYNTAX SEQUENCE OF SonomaFRDlciStatsEntry
       ACCESS not-accessible
       STATUS mandatory
       DESCRIPTION
           "Sonoma FR DLCI Statistics Table."
       ::= { sonomaFR 11 }

   sonomaFRDlciStatsEntry OBJECT-TYPE
       SYNTAX SonomaFRDlciStatsEntry
       ACCESS not-accessible
       STATUS mandatory
       DESCRIPTION
           "FR DLCI Statistics."
       INDEX { sonomaFRDlciStatsPort, sonomaFRDlciStatsDlci }
       ::= { sonomaFRDlciStatsTable 1 }

   SonomaFRDlciStatsEntry ::= SEQUENCE {
           sonomaFRDlciStatsPort
               INTEGER,
           sonomaFRDlciStatsDlci
               INTEGER,
           sonomaFRDlciStatsRecvFrames
               Counter,
           sonomaFRDlciStatsSentFrames
               Counter,
           sonomaFRDlciStatsRecvBytes
               Counter,
           sonomaFRDlciStatsSentBytes
               Counter,
           sonomaFRDlciStatsRecvDeFrames
               Counter,
           sonomaFRDlciStatsSentDeFrames
               Counter,
           sonomaFRDlciStatsRecvExcess
               Counter,
           sonomaFRDlciStatsSentExcess
               Counter,
           sonomaFRDlciStatsRecvDiscards
               Counter,
           sonomaFRDlciStatsSentDiscards
               Counter,
           sonomaFRDlciStatsRecvFecns
               Counter,
           sonomaFRDlciStatsSentFecns
               Counter,
           sonomaFRDlciStatsRecvBecns
               Counter,
           sonomaFRDlciStatsSentBecns
               Counter
       }

    sonomaFRDlciStatsPort  OBJECT-TYPE
        SYNTAX  INTEGER (1..1024)
        ACCESS  read-only
        STATUS  mandatory
        DESCRIPTION
            "The FR port index."
       ::= { sonomaFRDlciStatsEntry 1 }

    sonomaFRDlciStatsDlci  OBJECT-TYPE
        SYNTAX  INTEGER (1..1024)
        ACCESS  read-only
        STATUS  mandatory
        DESCRIPTION
            "The FR Dlci index."
       ::= { sonomaFRDlciStatsEntry 2 }

   sonomaFRDlciStatsRecvFrames OBJECT-TYPE
       SYNTAX Counter
       ACCESS read-only
       STATUS mandatory
       DESCRIPTION
           ""
       ::= { sonomaFRDlciStatsEntry 3 }

   sonomaFRDlciStatsSentFrames OBJECT-TYPE
       SYNTAX Counter
       ACCESS read-only
       STATUS mandatory
       DESCRIPTION
           ""
       ::= { sonomaFRDlciStatsEntry 4 }

   sonomaFRDlciStatsRecvBytes OBJECT-TYPE
       SYNTAX Counter
       ACCESS read-only
       STATUS mandatory
       DESCRIPTION
           ""
       ::= { sonomaFRDlciStatsEntry 5 }

   sonomaFRDlciStatsSentBytes OBJECT-TYPE
       SYNTAX Counter
       ACCESS read-only
       STATUS mandatory
       DESCRIPTION
           ""
       ::= { sonomaFRDlciStatsEntry 6 }

   sonomaFRDlciStatsRecvDeFrames OBJECT-TYPE
       SYNTAX Counter
       ACCESS read-only
       STATUS mandatory
       DESCRIPTION
           ""
       ::= { sonomaFRDlciStatsEntry 7 }

   sonomaFRDlciStatsSentDeFrames OBJECT-TYPE
       SYNTAX Counter
       ACCESS read-only
       STATUS mandatory
       DESCRIPTION
           ""
       ::= { sonomaFRDlciStatsEntry 8 }

   sonomaFRDlciStatsRecvExcess OBJECT-TYPE
       SYNTAX Counter
       ACCESS read-only
       STATUS mandatory
       DESCRIPTION
           ""
       ::= { sonomaFRDlciStatsEntry 9 }

   sonomaFRDlciStatsSentExcess OBJECT-TYPE
       SYNTAX Counter
       ACCESS read-only
       STATUS mandatory
       DESCRIPTION
           ""
       ::= { sonomaFRDlciStatsEntry 10 }

   sonomaFRDlciStatsRecvDiscards OBJECT-TYPE
       SYNTAX Counter
       ACCESS read-only
       STATUS mandatory
       DESCRIPTION
           ""
       ::= { sonomaFRDlciStatsEntry 11 }

   sonomaFRDlciStatsSentDiscards OBJECT-TYPE
       SYNTAX Counter
       ACCESS read-only
       STATUS mandatory
       DESCRIPTION
           ""
       ::= { sonomaFRDlciStatsEntry 12 }

   sonomaFRDlciStatsRecvFecns OBJECT-TYPE
       SYNTAX Counter
       ACCESS read-only
       STATUS mandatory
       DESCRIPTION
           ""
       ::= { sonomaFRDlciStatsEntry 13 }

   sonomaFRDlciStatsSentFecns OBJECT-TYPE
       SYNTAX Counter
       ACCESS read-only
       STATUS mandatory
       DESCRIPTION
           ""
       ::= { sonomaFRDlciStatsEntry 14 }

   sonomaFRDlciStatsRecvBecns OBJECT-TYPE
       SYNTAX Counter
       ACCESS read-only
       STATUS mandatory
       DESCRIPTION
           ""
       ::= { sonomaFRDlciStatsEntry 15 }

   sonomaFRDlciStatsSentBecns OBJECT-TYPE
       SYNTAX Counter
       ACCESS read-only
       STATUS mandatory
       DESCRIPTION
           ""
       ::= { sonomaFRDlciStatsEntry 16 }

   END
