---------------------------------------------------------------------------
-- hippiSwitchMIB MODULE-IDENTITY
--    LAST-UPDATED   "9903121120Z"
--    ORGANIZATION   "Essential/ODS Inc."
--    CONTACT-INFO   "Essential/ODS support.  E-mail support@esscom.com"
--    DESCRIPTION    "HIPPI ESS2000 32 port switch MIB v1.03"
--
-- REVISION "9901291553Z"
-- DESCRIPTION "Version 1.00 of the ESS2000 HIPPI switch MIB. SNMP v1.
-- REVISION "9902221548Z" 
-- DESCRIPTION "Version 1.01 Added more documentation to the descriptions. 
-- Enumerated types on mICHippiParityBurstError and mICSourceLastConnectAttempt."
-- DESCRIPTION "Version 1.02 Changed the module name, changed the DisplayString
-- in the entry tables for that the size isn't listed in the entry table.
-- DESCRIPTION "Version 1.03 Changed the module name to end in -MIB.
-- Removed enumerated typed and replaced with description text. 
-- Removed the ecExperimental import. 
-- Removed parens around enterprise number and removed word esscom.
---------------------------------------------------------------------------

ESSENTIAL-ODS-ESS2000-HIPPI-SWITCH-MIB DEFINITIONS ::= BEGIN

IMPORTS
   TRAP-TYPE
      FROM RFC-1215
   DisplayString
      FROM RFC1213-MIB
   Gauge,enterprises
      FROM RFC1155-SMI
   OBJECT-TYPE
      FROM RFC-1212;

---------------------------------------------------------------------------
--Main branches of the MIB.
---------------------------------------------------------------------------
essentialCommunications OBJECT IDENTIFIER ::= { enterprises 2159 }
ecRoot                  OBJECT IDENTIFIER ::= { essentialCommunications 1 }
ecProducts              OBJECT IDENTIFIER ::= { ecRoot 3 } 
ecExperimental          OBJECT IDENTIFIER ::= { ecRoot 6 } 
ess2000MIB              OBJECT IDENTIFIER ::= { ecProducts 2 }
switch                  OBJECT IDENTIFIER ::= { ess2000MIB 1 }
switchEvents            OBJECT IDENTIFIER ::= { ess2000MIB 7 } 

---------------------------------------------------------------------------
---------------------------------------------------------------------------
--First branch of this MIB containing the switch objects.
---------------------------------------------------------------------------
---------------------------------------------------------------------------

switchDescription OBJECT-TYPE
   SYNTAX      DisplayString
   ACCESS      read-only
   STATUS      mandatory
   DESCRIPTION "Returns the description, vendor, 
                and version numbers of the switch."
   ::= { switch 1 } 

switchNumOfPorts OBJECT-TYPE
   SYNTAX      Gauge
   ACCESS      read-only
   STATUS      mandatory
   DESCRIPTION   "The number of slots in this switch. 
            (Max number of media access cards)."
   ::= { switch 2 } 

switchSensors OBJECT-TYPE
   SYNTAX      DisplayString(SIZE(0..3))
   ACCESS      read-only
   STATUS      mandatory
   DESCRIPTION   "This value returns the status of the temperature and
   power supply sensors. From least to most significant byte the values 
   are power supply 1-3 with the most signficant byte being the over
   temperature sensor.
   0 indicates the sensor is autodectable and not installed.
   1 indicates the sensor is OK.
   2 indicates the sensor is not OK."
   ::= { switch 3 } 

switchControlCard  OBJECT IDENTIFIER ::= { ess2000MIB 2 }

sccDescription OBJECT-TYPE
   SYNTAX      DisplayString
   ACCESS      read-only
   STATUS       mandatory
   DESCRIPTION   "The model, vendor, and version number 
                of the switch control card."
   ::= { switchControlCard 1 }

sccDateTime OBJECT-TYPE
   SYNTAX      DisplayString
   ACCESS      read-write
   STATUS      mandatory
   DESCRIPTION   "The date/time in the real time clock. 
                Format: yyyymmddhhmmss"
   ::= { switchControlCard 2 }

sccAdminStatus OBJECT-TYPE
   SYNTAX      INTEGER 
   ACCESS      read-write
   STATUS      mandatory
   DESCRIPTION "The desired state of the switch.
   1 indicates switch is up.
   2 will make the switch reset." 
   ::= { switchControlCard 3 } 

sccOperStatus OBJECT-TYPE
   SYNTAX      INTEGER 
   ACCESS      read-only
   STATUS      mandatory
   DESCRIPTION "The current state of the switch.
   1 indicates the switch is up.
   2 indicates the switch is resetting. SNMP operations can not occur when the switch is resetting.
   3 indicates a busy switch. SNMP operations can not occur when the switch is busy.
            "
   ::= { switchControlCard 4 } 

---------------------------------------------------------------------------
--The backplane hardware description.
---------------------------------------------------------------------------
mediaInterfaceCards  OBJECT IDENTIFIER ::= { ess2000MIB 3 }

backPlaneTable    OBJECT-TYPE
   SYNTAX      SEQUENCE OF BackPlaneEntry
   ACCESS      not-accessible
   STATUS      mandatory
   DESCRIPTION
            "This table represent all of the slots in a HIPPI switch. 
            None of the rows can be added to or deleted by the user."
   ::= { mediaInterfaceCards 1 }

backPlaneEntry OBJECT-TYPE
   SYNTAX       BackPlaneEntry
   ACCESS       not-accessible
   STATUS      mandatory
   DESCRIPTION
            "A row in the table describing one slot in the switch backplane. "
   INDEX      { backPlaneIndex } --Identifies a row in the slot table.
   ::= { backPlaneTable 1 } 

BackPlaneEntry ::= SEQUENCE 
{
   backPlaneIndex              Gauge,
   backPlaneNumber             Gauge,     
   backPlaneCard               INTEGER,
   mICPowerUpInitError         Gauge,
   mICHippiParityBurstError    INTEGER,
   mICLinkReady                Gauge,
   mICSourceInterconnect       Gauge,
   mICSourceRequest            Gauge,
   mICSourceConnect            Gauge,
   mICSourceLastConnectAttempt INTEGER,
   mICDestinationInterconnect  Gauge,
   mICDestinationRequest       Gauge,
   mICDestinationConnect       Gauge,
   mICByteCounterOverflow      Gauge,
   mICNumberOfBytes            Gauge,
   mICNumberOfPackets          Gauge,
   mICConnectsSuccessful       Gauge
}
   
backPlaneIndex OBJECT-TYPE
   SYNTAX      Gauge
   ACCESS      not-accessible
   STATUS      mandatory
   DESCRIPTION   "The table index for this slot on the backplane."
   ::= { backPlaneEntry 1 }

backPlaneNumber   OBJECT-TYPE
   SYNTAX      Gauge
   ACCESS      read-only
   STATUS       mandatory
   DESCRIPTION   "The slot number as seen printed on the switch 
            (backPlaneIndex + 1)"
   ::= { backPlaneEntry 2 }

backPlaneCard OBJECT-TYPE
   SYNTAX      INTEGER 
   ACCESS      read-only
   STATUS      mandatory
   DESCRIPTION   "The type of MIC present in this slot 
            of the backplane on the switch
			0 No MIC
			1 Unknown MIC
			2 Parallel MIC
			3 Serial MIC"
   ::= { backPlaneEntry 3 }

mICPowerUpInitError OBJECT-TYPE
   SYNTAX      Gauge
   ACCESS      read-only
   STATUS      mandatory
   DESCRIPTION "1 if error detected by MIC on start-up, else 0."
   ::= { backPlaneEntry 4 }

mICHippiParityBurstError OBJECT-TYPE
   SYNTAX      INTEGER 
   ACCESS      read-only
   STATUS      mandatory
   DESCRIPTION "Type of parity error.
   0 None
   1 XDeMux (Transmitting)
   2 XMux   (Receiving)"
   ::= { backPlaneEntry 5 }

mICLinkReady OBJECT-TYPE
   SYNTAX      Gauge
   ACCESS      read-only
   STATUS      mandatory
   DESCRIPTION "Valid the SMIC only. 1 if link ready asserted, else 0."
   ::= { backPlaneEntry 6 }

mICSourceInterconnect OBJECT-TYPE
    SYNTAX      Gauge
   ACCESS      read-only
   STATUS      mandatory
   DESCRIPTION "Source interconnect is valid for the PMIC only. 
               1 if interconnect is true else 0"
   ::= { backPlaneEntry 7 }

mICSourceRequest OBJECT-TYPE
   SYNTAX      Gauge
   ACCESS      read-only
   STATUS      mandatory
   DESCRIPTION "1 if source request is asserted else 0."
   ::= { backPlaneEntry 8 }

mICSourceConnect OBJECT-TYPE
   SYNTAX      Gauge
   ACCESS      read-only
   STATUS      mandatory
   DESCRIPTION "1 if source connect is asserted else 0."
   ::= { backPlaneEntry 9 }

mICSourceLastConnectAttempt OBJECT-TYPE
   SYNTAX      INTEGER
   ACCESS      read-only
   STATUS      mandatory
   DESCRIPTION "0 if no last connect attempt.
                1 if last source request was successful or no last connect.
				2 Connection underway.
				3 if last connect was rejected downstream."
   ::= { backPlaneEntry 10 }

mICDestinationInterconnect OBJECT-TYPE
   SYNTAX      Gauge
   ACCESS      read-only
   STATUS      mandatory
   DESCRIPTION "1 if destination interconnect is asserted else 0."
   ::= { backPlaneEntry 11 }

mICDestinationRequest OBJECT-TYPE
   SYNTAX      Gauge
   ACCESS      read-only
   STATUS      mandatory
   DESCRIPTION "1 if destination request is asserted else 0."
   ::= { backPlaneEntry 12 }

mICDestinationConnect OBJECT-TYPE
   SYNTAX      Gauge
   ACCESS      read-only
   STATUS      mandatory
   DESCRIPTION "1 if destination connect is asserted else 0."
   ::= { backPlaneEntry 13 }

mICByteCounterOverflow OBJECT-TYPE
   SYNTAX      Gauge
   ACCESS      read-only
   STATUS      mandatory
   DESCRIPTION "The number of times the byte counter has over-flowed."
   ::= { backPlaneEntry 14 }

mICNumberOfBytes OBJECT-TYPE
   SYNTAX      Gauge
   ACCESS      read-only
   STATUS      mandatory
   DESCRIPTION "The number of bytes that have passed through the MIC."
   ::= { backPlaneEntry 15 }

mICNumberOfPackets OBJECT-TYPE
   SYNTAX      Gauge
   ACCESS      read-only
   STATUS      mandatory
   DESCRIPTION "The number of times packets has been asserted."
   ::= { backPlaneEntry 16 }

mICConnectsSuccessful OBJECT-TYPE
   SYNTAX      Gauge
   ACCESS      read-only
   STATUS      mandatory
   DESCRIPTION "The number of times this MIC has connected since reset."
   ::= { backPlaneEntry 17 }

---------------------------------------------------------------------------
--Source Route Table.
--A table that contains the enable/disable information for each input port-
--output port pair.
---------------------------------------------------------------------------
sourceRoutes  OBJECT IDENTIFIER ::= { ess2000MIB 4 }

srcRouteTable OBJECT-TYPE
   SYNTAX      SEQUENCE OF SrcRouteEntry
   ACCESS       not-accessible
   STATUS       mandatory
   DESCRIPTION "This table holds all of the source routes for this switch.
            FORMAT: OutputPort InputPortList Status.
            Output port is 0 to 31
            Input  port is 0 to 31
            List is NUMBER or NUMBER1-NUMBER2 where NUMBER1 < NUMBER2.
            Status is 0 (disabled) or 1 (enabled)"
   ::= { sourceRoutes 1 } 

srcRouteEntry OBJECT-TYPE
   SYNTAX       SrcRouteEntry
   ACCESS       not-accessible
   STATUS       mandatory
   DESCRIPTION "One row in the source route table."
   INDEX      { srcIndex }
   ::= { srcRouteTable 1 }

SrcRouteEntry ::= SEQUENCE
{
   srcIndex                  Gauge,
   srcRouteInPortAccess      DisplayString,
   srcRouteOutPortAccess     DisplayString
}

srcIndex OBJECT-TYPE
   SYNTAX      Gauge
   ACCESS      read-only
   STATUS      mandatory
   DESCRIPTION "The row number for this row of the table."
   ::= { srcRouteEntry 1 } 

srcRouteInPortAccess OBJECT-TYPE
   SYNTAX      DisplayString (SIZE(1..80))
   ACCESS      read-only
   STATUS      mandatory
   DESCRIPTION "
            FORMAT: Shows the input port access for 1 output port.
            Each instance is the output port number.
            Each 32 bit hex value displays the input port access for 32 ports.
            with port 32 on the left and port 0 on the right.
            Each bit is set for and enabled port, clear for a disabled one.
            For example 80000000 indicates input port 31 is enabled for this output port"
   ::= { srcRouteEntry 2 } 

srcRouteOutPortAccess OBJECT-TYPE
   SYNTAX      DisplayString (SIZE(1..80))
   ACCESS      read-only
   STATUS      mandatory
   DESCRIPTION "
            FORMAT: Shows the output port access for 1 input port.
            Each instance is the input port number.
            Each 32 bit hex value displays the output port access for 32 ports.
            with port 32 on the left and port 0 on the right.
            Each bit is set for and enabled port, clear for a disabled one.
            For example 80000000 indicates output port 31 is enabled for this input port"
   ::= { srcRouteEntry 3 } 

srcRouteWrite OBJECT-TYPE
   SYNTAX      DisplayString 
   ACCESS      read-write
   STATUS      mandatory
   DESCRIPTION "Setting this variable alters source routes.
            FORMAT: OutputPortList InputPortList Status.
            Output port is 0 to 31
            Input  port is 0 to 31
            Status is 0 (disabled) or 1 (enabled)
            List is NUMBER or NUMBER1-NUMBER2 where NUMBER1 < NUMBER2."
   ::= { sourceRoutes 2 } 

srcSaveRestore OBJECT-TYPE
   SYNTAX      INTEGER 
   ACCESS      read-write
   STATUS      mandatory
   DESCRIPTION "This will save or restore all of the source routes.
   Writting a 0 is a no operation.
   Writting a 1 saves all source routes on the switch.
   Writting a 2 restores all source routes on the switch."
   ::= { sourceRoutes 3 } 

---------------------------------------------------------------------------
--The destination routing table contains the huntgroup number 
--(if any) for each defined logical address and input port pair.
--tabel max is 4kx16. f(la,inport) = HG
---------------------------------------------------------------------------
logicalAddressRoutes  OBJECT IDENTIFIER ::= { ess2000MIB 5 }

destRouteTable OBJECT-TYPE
   SYNTAX      SEQUENCE OF DestRouteEntry
   ACCESS       not-accessible
   STATUS       mandatory
   DESCRIPTION "This table holds all of destination routes (logical
            address routes) for this switch.
            FORMAT: LogicalAddress InputPortList Huntgroup.
            LogicalAddress is 0 to 4095.
            Input  port is 0 to 31
            Huntgroup is 0 to 31.
            List is NUMBER or NUMBER1-NUMBER2 where NUMBER1 < NUMBER2."
   ::= { logicalAddressRoutes 1 } 

destRouteEntry OBJECT-TYPE
   SYNTAX      DestRouteEntry
   ACCESS       not-accessible
   STATUS       mandatory
   DESCRIPTION "A row in the destination route table."
   INDEX      { destIndex }
   ::= { destRouteTable 1 }

DestRouteEntry ::= SEQUENCE
{
   destIndex       Gauge,
   destRoute      DisplayString
}

destIndex OBJECT-TYPE
   SYNTAX      Gauge
   ACCESS      read-only
   STATUS      mandatory
   DESCRIPTION "The index for this row of the table."
   ::= { destRouteEntry 1 } 

destRoute OBJECT-TYPE
   SYNTAX      DisplayString (SIZE(1..80))
   ACCESS      read-only
   STATUS      mandatory
   DESCRIPTION "One Destination Route.
            FORMAT: LogicalAddress InputPortList Huntgroup.
            LogicalAddress is 0 to 4095.
            Input  port is 0 to 31.
            Huntgroup is 0 to 31.
            List is NUMBER or NUMBER1-NUMBER2 where NUMBER1 < NUMBER2."
   ::= { destRouteEntry 2 } 

destRouteWrite OBJECT-TYPE
   SYNTAX      DisplayString 
   ACCESS      read-write
   STATUS      mandatory
   DESCRIPTION "Setting this variable will alter the desitination routes.
            FORMAT: LogicalAddressList Huntgroup InputPortList.
            LogicalAddress is 0 to 4095.
            Huntgroup is 0 to 31. 31 will disable this route.
            Input port is 0 to 31.
            List is NUMBER or NUMBER1-NUMBER2 where NUMBER1 < NUMBER2."
   ::= { logicalAddressRoutes 2 } 

pathRouteTable OBJECT-TYPE
   SYNTAX      SEQUENCE OF PathRouteEntry
   ACCESS      not-accessible
   STATUS      mandatory
   DESCRIPTION "This table holds all of pathway routes for this switch.
            FORMAT: PathwayAddressList InputPortList outputPort
            PathwaAddress is 0 to 4095.
            Input  port is 0 to 31
            outputPort is 0 to 31.
            List is NUMBER or NUMBER1-NUMBER2 where NUMBER1 < NUMBER2."
   ::= { logicalAddressRoutes 3 } 

pathRouteEntry OBJECT-TYPE
   SYNTAX      PathRouteEntry
   ACCESS      not-accessible
   STATUS      mandatory
   DESCRIPTION "A row in the pathway route table."
   INDEX      { pathIndex }
   ::= { pathRouteTable 1 }

PathRouteEntry ::= SEQUENCE
{
   pathIndex      Gauge,
   pathRoute      DisplayString
}

pathIndex OBJECT-TYPE
   SYNTAX      Gauge
   ACCESS      read-only
   STATUS      mandatory
   DESCRIPTION "The index for this row of the table."
   ::= { pathRouteEntry 1 } 

pathRoute OBJECT-TYPE
   SYNTAX      DisplayString (SIZE(1..80))
   ACCESS      read-only
   STATUS      mandatory
   DESCRIPTION "One pathway logical address route.
            FORMAT: LogicalAddress InputPortList outputPort.
            LogicalAddress is 0 to 4095.
            Input  port is 0 to 31.
            outputPort is 0 to 31.
            List is NUMBER or NUMBER1-NUMBER2 where NUMBER1 < NUMBER2."
   ::= { pathRouteEntry 2 } 

pathRouteWrite OBJECT-TYPE
   SYNTAX      DisplayString 
   ACCESS      read-write
   STATUS      mandatory
   DESCRIPTION "Setting this variable will alter the pathway logical routes.
            FORMAT: LogicalAddressList Huntgroup InputPortList.
            LogicalAddress is 0 to 4095.
            Huntgroup is 0 to 31. 31 will disable this route.
            Input port is 0 to 31.
            List is NUMBER or NUMBER1-NUMBER2 where NUMBER1 < NUMBER2."
   ::= { logicalAddressRoutes 4 } 

routesSaveRestore OBJECT-TYPE
   SYNTAX      INTEGER 
   ACCESS      read-write
   STATUS      mandatory
   DESCRIPTION "This saves and restores the route information.
   0 is a no operation.
   1 saves all destination routes on the switch.
   2 restores all destination routes on the switch."
   ::= { logicalAddressRoutes 5 } 

routeDisable OBJECT-TYPE
   SYNTAX      DisplayString 
   ACCESS      read-write
   STATUS      mandatory
   DESCRIPTION "Setting this variable will disable logical address routes.
            FORMAT: LogicalAddressList InputPortList.
            LogicalAddress is 0 to 4095 (0x0 to 0xfff).
            Input port is 0 to 31 (0x0 to 0x1f).
            List is NUMBER or NUMBER1-NUMBER2 where NUMBER1 < NUMBER2."
   ::= { logicalAddressRoutes 6 } 

---------------------------------------------------------------------------
--Hunt Group Table (Output port sets).    
--The huntgroup table defines which output ports are in each huntgroup set.
---------------------------------------------------------------------------
huntGroups     OBJECT IDENTIFIER ::= { ess2000MIB 6 }

hGTable OBJECT-TYPE
   SYNTAX      SEQUENCE OF HGEntry
   ACCESS       not-accessible
   STATUS       mandatory
   DESCRIPTION "This table holds all of the huntgroups for this  switch.
            FORMAT: Huntgroup ( OutportList )
            Huntgroup is 0 to 31.
            OutportList is an orderd list of output ports in Huntgroup."
   ::= { huntGroups 1 } 

hGEntry OBJECT-TYPE
   SYNTAX       HGEntry
   ACCESS       not-accessible
   STATUS       mandatory
   DESCRIPTION "A row in the huntgroup table."
   INDEX      { hg }
   ::= { hGTable 1 }

HGEntry ::= SEQUENCE
{
   hg             Gauge,         
   hgList         DisplayString 
}

hg OBJECT-TYPE
   SYNTAX      Gauge
   ACCESS      read-only
   STATUS      mandatory
   DESCRIPTION "The huntgroup number." 
   ::= { hGEntry 1 } 

hgList OBJECT-TYPE
   SYNTAX      DisplayString (SIZE(1..80))
   ACCESS      read-only
   STATUS      mandatory
   DESCRIPTION "The definition of one Huntgroup.
            FORMAT: Huntgroup ( OutportList )
            Huntgroup is 0 to 31.
            OutportList is an orderd list of output ports in Huntgroup."
   ::= { hGEntry 2 } 

hgWrite OBJECT-TYPE
   SYNTAX      DisplayString 
   ACCESS      read-write
   STATUS      mandatory
   DESCRIPTION "Setting this variable will alter the huntgroup table by
            setting every huntgroup in list to include outPortList.
            FORMAT: HuntgroupList OutportList
            Huntgroup is 0 to 31.
            Outport is 0 to 31. 
            List is NUMBER or NUMBER1-NUMBER2 where NUMBER1 < NUMBER2."
   ::= { huntGroups 2 } 

hgSaveRestore OBJECT-TYPE
   SYNTAX      INTEGER 
   ACCESS      read-write
   STATUS      mandatory
   DESCRIPTION "This saves and restores the hunt groups.
   0 is a no operation.
   1 saves all hunt group information on the switch.
   2 restores all hunt group information on the switch."
   ::= { huntGroups 3 } 

---------------------------------------------------------------------------
---------------------------------------------------------------------------
--The second branch of this MIB that contains the events.
--This is here to easily translate SNMPv1 traps.
---------------------------------------------------------------------------
---------------------------------------------------------------------------

---------------------------------------------------------------------------
--This event is intended to warn the NMS when the power supply fail sensors
--(Up to 3) go off, or when the over temperature sensor goes off. 
--The value encoded in the variable includes information 
--if the sensor is installed or not.
---------------------------------------------------------------------------
switchSensorWarning TRAP-TYPE
        ENTERPRISE switchEvents 
        VARIABLES { switchSensors }
        DESCRIPTION "This warns that switch sensor(s) are changing status.
        One 32 bit hex values is returned and is ASCII encoded as follows: 
        abcd where each character is a byte (8 bit value). 
        a is the over temperature sensor. 
        b, c, and d are power sensors 3 to 1 respectively.
        Each byte contains the following information: 
        0 (30 hex) Sensor is autodetectable, but it is not installed.
        1 (32 hex) Sensor (if installed) has no problem
        2 (33 hex) Sensor (if installed) has a sensor warning.
        3-15 not defined.
        For example, the hex values 0021 means over temperature sensor is not
        installed, power supply sensor 3 is not installed, power supply sensor
        2 has indicated power supply failure, and power supply 1 is ok."
    ::= 1


END
