-->#
--># Copyright (C) Siemens AG 1998
-->#               All rights reserved
-->#
-->#protocol specification
-->%PROTOCOL SNMP
-->#
-->#configuration
-->%REMCONFIG NO
-->%REMOPERATION NO
-->#

--
-- Title:   MIB for BCAM -  version 14
-- Date:    04 September 1997
-- Authors: SNI OEC BS DC21


-- MIB-Version: 1




BCAM-MIB DEFINITIONS ::= BEGIN
IMPORTS
		DisplayString FROM SNMPv2-TC
  mgmt, NetworkAddress, IpAddress, Counter, Gauge, TimeTicks, enterprises
  FROM RFC1155-SMI

  OBJECT-TYPE
  FROM RFC-1212
  TRAP-TYPE FROM RFC-1215;

  sni            OBJECT IDENTIFIER ::= { enterprises 231 }
  sniProductMibs OBJECT IDENTIFIER ::= { sni 2 }
  sniBcam        OBJECT IDENTIFIER ::= { sniProductMibs 17 }

PhysAddress ::= OCTET STRING

-- groups in BCAM

bcamTrap       OBJECT IDENTIFIER ::= { sniBcam 1 }

bcamGlobal     OBJECT IDENTIFIER ::= { sniBcam 2 }
-- The global group contains values that are specific for BCAM and cannot be
-- assigned to one of the following groups.

bcamMemory     OBJECT IDENTIFIER ::= { sniBcam 3 }
-- The memory group contains values that describe the memory occupied by BCAM

bcamTrace      OBJECT IDENTIFIER ::= { sniBcam 4 }
-- The trace group describes the state of the BCAM traces
-- SNMPNAME:
-- ASSNAME: YYYTCONB (anchor)

bcamTsap       OBJECT IDENTIFIER ::= { sniBcam 5 }
-- The tsap group contains values that are specific for applications and is
-- divided in two sections. The common part contains values that belong to
-- applications, but cannot be assigned to a specific one. The table part
-- describes every application in more detail.

bcamCep        OBJECT IDENTIFIER ::= { sniBcam 6 }
-- The connection group contains values that are specific for connections and
-- is divided in two sections. The common part contains values that belong to
-- connections, but cannot be assigned to a specific one. The table part
-- describes every connection in more detail.

bcamRoute      OBJECT IDENTIFIER ::= { sniBcam 7 }
-- A route is defined by the pair of the addresses of two hosts.
-- The route group contains values that are specific for routes and is divided in two sections.
-- The common part contains values that belong to routes, but cannot be assigned to a specific one.
-- The table part describes every route in more detail.

bcamIf         OBJECT IDENTIFIER ::= { sniBcam 8 }
-- An interface is an access point to the network.
-- The interface group contains values that are specific for interfaces and is divided in two sections.
-- The common part contains values that belong to interfaces, but cannot be assigned to a specific one.
-- The table part describes every interface in more detail.

bcamRouter     OBJECT IDENTIFIER ::= { sniBcam 9 }
-- A router is a system known by bcam as an intermediate system.
-- The router group contains values that are specific for routers and is divided in two sections.
-- The common part contains values that belong to routers, but cannot be assigned to a specific one.
-- The table part describes every router in more detail.

bcamHost       OBJECT IDENTIFIER ::= { sniBcam 10 }
-- A host is a local endsystem (there may be more than one host).
-- The host group contains values that are specific for hosts and is divided in two sections.
-- The common part contains values that belong to hosts, but cannot be assigned to a specific one.
-- The table part describes every host in more detail.


-- the Trap Group

bcamTrapString OBJECT-TYPE
  SYNTAX DisplayString
  ACCESS not-accessible
  STATUS mandatory
  DESCRIPTION " Textual description of the trap. The trap string contains the values sent with
		the trap in printable form separated by the keywords given at the description
		of the individual traps. "
  ::= { bcamTrap 1 }
-- SNMPNAME: PSTR
-- ASSNAME:

bcamTrapOutPoolOverCurrent OBJECT-TYPE
  SYNTAX INTEGER
  ACCESS not-accessible
  STATUS mandatory
  DESCRIPTION " The number of bytes of resident memory used for output cells
		when the trap condition (output pool over maximum) has been recognized. "
  ::= { bcamTrap 2 }
-- SNMPNAME: POOC
-- ASSNAME:

bcamTrapOutPoolUnderCurrent OBJECT-TYPE
  SYNTAX INTEGER
  ACCESS not-accessible
  STATUS mandatory
  DESCRIPTION " The number of bytes of resident memory used for output cells
		when the trap condition (output pool under maximum) has been recognized. "
  ::= { bcamTrap 3 }
-- SNMPNAME: POUC
-- ASSNAME:

bcamTrapInPoolOverCurrent OBJECT-TYPE
  SYNTAX INTEGER
  ACCESS not-accessible
  STATUS mandatory
  DESCRIPTION " The number of bytes of resident memory used for input cells
		when the trap condition (input pool over maximum) has been recognized. "
  ::= { bcamTrap 4 }
-- SNMPNAME: PIOC
-- ASSNAME:

bcamTrapInPoolUnderCurrent OBJECT-TYPE
  SYNTAX INTEGER
  ACCESS not-accessible
  STATUS mandatory
  DESCRIPTION " The number of bytes of resident memory used for input cells
		when the trap condition (input pool under maximum) has been recognized. "
  ::= { bcamTrap 5 }
-- SNMPNAME: PIUC
-- ASSNAME:

bcamTrapOutPoolOver TRAP-TYPE
  ENTERPRISE sniBcam
  VARIABLES  {
    bcamGlobalUpTime,
    bcamGlobalHostName,
    bcamMemoryPoolOutputLimitTrap,
    bcamTrapOutPoolOverCurrent,
    bcamTrapString
	     }
  DESCRIPTION " This trap will be sent if the resident memory used for
		output cells exceeds the limit (bcamMemoryPoolOutputLimitTrap)
		for more than 5 seconds.
		bcamTrapString has the fields:
		$HOST$:       <hostname>
		$UPTIME$:     <bcamuptime>
		$OUTLIMIT$:   <memlimit>
		$OUTCURRENT$: <memcurrent>
		The following values will be sent together with the trap:
		bcamGlobalHostName
		bcamGlobalUpTime
		bcamMemoryPoolOutputLimitTrap
		bcamMemoryPoolOverCurrent
		bcamTrapString
	      "
  ::= 301

bcamTrapOutPoolUnder TRAP-TYPE
  ENTERPRISE sniBcam
  VARIABLES  {
    bcamGlobalUpTime,
    bcamGlobalHostName,
    bcamMemoryPoolOutputLimitTrap,
    bcamTrapOutPoolUnderCurrent,
    bcamTrapString
	     }
  DESCRIPTION " This trap will be sent if the resident memory used for
		output cells has exceeded the limit (bcamMemoryPoolOutputLimitTrap)
		and falls under the limit for more than 5 seconds.
		bcamTrapString has the fields:
		$HOST$:       <hostname>
		$UPTIME$:     <bcamuptime>
		$OUTLIMIT$:   <memlimit>
		$OUTCURRENT$: <memcurrent>
		The following values will be sent together with the trap:
		bcamGlobalHostName
		bcamGlobalUpTime
		bcamMemoryPoolOutputLimitTrap
		bcamMemoryPoolUnderCurrent
		bcamTrapString
	      "
  ::= 302

bcamTrapInPoolOver TRAP-TYPE
  ENTERPRISE sniBcam
  VARIABLES  {
    bcamGlobalUpTime,
    bcamGlobalHostName,
    bcamMemoryPoolInputLimitTrap,
    bcamTrapInPoolOverCurrent,
    bcamTrapString
	     }
  DESCRIPTION " This trap will be sent if the resident memory used for
		input cells exceeds the limit (bcamMemoryPoolInputLimitTrap)
		for more than 5 seconds.
		bcamTrapString has the fields:
		$HOST$:       <hostname>
		$UPTIME$:     <bcamuptime>
		$INLIMIT$:    <memlimit>
		$INCURRENT$:  <memcurrent>
		The following values will be sent together with the trap:
		bcamGlobalHostName
		bcamGlobalUpTime
		bcamMemoryPoolInputLimitTrap
		bcamTrapInPoolOverCurrent
		bcamTrapString
	      "
  ::= 303

bcamTrapInPoolUnder TRAP-TYPE
  ENTERPRISE sniBcam
  VARIABLES  {
    bcamGlobalUpTime,
    bcamGlobalHostName,
    bcamMemoryPoolInputLimitTrap,
    bcamTrapInPoolUnderCurrent,
    bcamTrapString
	     }
  DESCRIPTION " This trap will be sent if the resident memory used for
		input cells has exceeded the limit (bcamMemoryPoolInputLimitTrap)
		and falls under the limit for more than 5 seconds.
		bcamTrapString has the fields:
		$HOST$:       <hostname>
		$UPTIME$:     <bcamuptime>
		$INLIMIT$:    <memlimit>
		$INCURRENT$:  <memcurrent>
		The following values will be sent together with the trap:
		bcamGlobalHostName
		bcamGlobalUpTime
		bcamMemoryPoolInputLimitTrap
		bcamTrapInPoolUnderCurrent
		bcamTrapString
	      "
  ::= 304

bcamTrapLinkUp TRAP-TYPE
  ENTERPRISE sniBcam
  VARIABLES  {
    bcamGlobalUpTime,
    bcamGlobalHostName,
    bcamIfTabNumbers,
    bcamIfTabName,
    bcamTrapString
	     }
  DESCRIPTION " This trap will be sent if an interface enters the state active
		(bcamIfAdminState).
		bcamTrapString has the fields:
		$HOST$:       <hostname>
		$UPTIME$:     <bcamuptime>
		$NUMBER$:     <linknumber>
		$NAME$:       <linkname>
		The following values will be sent together with the trap:
		bcamGlobalHostName
		bcamGlobalUpTime
		bcamIfTabNumbers
		bcamIfTabName
		bcamTrapString
	      "
  ::= 305

bcamTrapLinkDown TRAP-TYPE
  ENTERPRISE sniBcam
  VARIABLES  {
    bcamGlobalUpTime,
    bcamGlobalHostName,
    bcamIfTabNumbers,
    bcamIfTabName,
    bcamTrapString
	     }
  DESCRIPTION " This trap will be sent if an interface leaves the state active
		(bcamIfAdminState).
		bcamTrapString has the fields:
		$HOST$:       <hostname>
		$UPTIME$:     <bcamuptime>
		$NUMBER$:     <linknumber>
		$NAME$:       <linkname>
		The following values will be sent together with the trap:
		bcamGlobalHostName
		bcamGlobalUpTime
		bcamIfTabNumbers
		bcamIfTabName
		bcamTrapString
	      "
  ::= 306

bcamTrapSystemUp TRAP-TYPE
  ENTERPRISE sniBcam
  VARIABLES  {
    bcamGlobalUpTime,
    bcamGlobalHostName,
    bcamTrapString
	     }
  DESCRIPTION " This trap will be sent after a successful start of BCAM.
		bcamTrapString has the fields:
		$HOST$:       <hostname>
		$UPTIME$:     <bcamuptime>
		The following values will be sent together with the trap:
		bcamGlobalHostName
		bcamGlobalUpTime
		bcamTrapString
	      "
  ::= 307



-- the Global group

bcamGlobalBcamVersion OBJECT-TYPE
  SYNTAX DisplayString (SIZE(6)) -- ASSLEN: 7 VAR
  ACCESS read-only
  STATUS mandatory
  DESCRIPTION
    "The version of BCAM in the form xx.yy
     xx: mainversion
     yy: subversion"
  ::= { bcamGlobal 1 }
-- SNMPNAME: GBCV
-- ASSNAME: YYY#BCAM

bcamGlobalMibVersion OBJECT-TYPE
  SYNTAX INTEGER
  ACCESS read-only
  STATUS mandatory
  DESCRIPTION
    "Version of BCAM specific MIB (beginning with 1).
     Will be increased with every enhancement of this MIB"
  ::= { bcamGlobal 2 }
-- SNMPNAME: GMBV
-- ASSNAME:

  bcamGlobalUpTime OBJECT-TYPE
    SYNTAX INTEGER
    ACCESS read-only
    STATUS mandatory
    DESCRIPTION
      "Time in seconds since start of BCAM"
  ::= { bcamGlobal 3 }
-- SNMPNAME: GBUT
-- ASSNAME: YBCSUTIM



  bcamGlobalPortNonpriv OBJECT-TYPE
    SYNTAX INTEGER -- ASSLEN: 2
    ACCESS read-only
    STATUS mandatory
    DESCRIPTION
      "The lowest port number that may be used by non privileged
       applications"
  ::= { bcamGlobal 4 }
-- SNMPNAME: GPNP
-- ASSNAME: YYSPORT#

  bcamGlobalPortFree OBJECT-TYPE
    SYNTAX INTEGER -- ASSLEN: 2
    ACCESS read-only
    STATUS mandatory
    DESCRIPTION
      "The lowest port number that will be assigned dynamical by BCAM"
  ::= { bcamGlobal 5 }
-- SNMPNAME: GPNF
-- ASSNAME: YYSPFPO#

  bcamGlobalNumBitmap OBJECT-TYPE
    SYNTAX INTEGER -- ASSLEN: 2
    ACCESS read-only
    STATUS mandatory
    DESCRIPTION
      "The number of bitmaps to administer slots in the data slot
       pool. Every bitmap can administer 2048 slots. So the maximum
       number of slots in a pool is bcamGlobalNumBitmap*2048"
  ::= { bcamGlobal 6 }
-- SNMPNAME: GNBM
-- ASSNAME: YFDBITM#

  bcamGlobalMaxRemoteIp OBJECT-TYPE
    SYNTAX INTEGER
    ACCESS read-only
    STATUS mandatory
    DESCRIPTION
      "The maximum length in bytes BCAM uses for an NSDU
       for an endsystem that is reached over at least one router"
  ::= { bcamGlobal 7 }
-- SNMPNAME: GMRI
-- ASSNAME: YYSPRIPN



bcamGlobalEsCreationIp OBJECT-TYPE
  SYNTAX INTEGER {
-- ASSMULTI:
	   ipOff(1),            -- ASSVAL: 0 0
	   ipInData(2),         -- ASSVAL: YBTAECID 16
	   ipOutData(4),        -- ASSVAL: YBTAECOD 32
	   ipRoutingProt(8),    -- ASSVAL: YBTAECRP 64
	   ipRoutingData(16)    -- ASSVAL: YBTAECRD 128
		 }
  ACCESS read-only
  STATUS mandatory
  DESCRIPTION
    " The types of IP protocols that will lead to automatic endsystem creation:
      ipOff (1)          : no automatic endsystem creation due to IP protocols.
      ipInData (2)       : automatic endsystem creation due to IP data received.
      ipOutData (4)      : automatic endsystem creation due to IP data sent.
      ipRoutingProt (8)  : automatic endsystem creation due to IP routing protocols.
      ipRoutingData (16) : automatic endsystem creation due to routed IP protocols.
    "
  ::= { bcamGlobal 8 }
-- SNMPNAME: GECP
-- ASSNAME: YBTAECIP

bcamGlobalEsCreationIso OBJECT-TYPE
  SYNTAX INTEGER {
-- ASSMULTI:
	   isoOff(1),          -- ASSVAL: 0 0
	   isoInData(2),       -- ASSVAL: YBTAECID 16
	   isoOutData(4),      -- ASSVAL: YBTAECOD 32
	   isoRoutingProt(8),  -- ASSVAL: YBTAECRP 64
	   isoRoutingData(16)  -- ASSVAL: YBTAECRD 128
		 }
  ACCESS read-only
  STATUS mandatory
  DESCRIPTION
    " The types of ISO 8473 and ISO 9542 protocols that will lead to automatic endsystem creation:
      isoOff (1)          : no automatic endsystem creation due to ISO protocols.
      isoInData (2)       : automatic endsystem creation due to ISO data received.
      isoOutData (4)      : automatic endsystem creation due to ISO data sent.
      isoRoutingProt (8)  : automatic endsystem creation due to ISO routing protocols.
      isoRoutingData (16) : automatic endsystem creation due to routed ISO protocols.
    "
  ::= { bcamGlobal 9 }
-- SNMPNAME: GECS
-- ASSNAME:  YBTAECIS

bcamGlobalBroadcast OBJECT-TYPE
  SYNTAX INTEGER {
-- ASSMULTI:
		 off(1), -- ASSVAL: 0 0
		 on(2)   -- ASSVAL: YBTBROAD 4
		 }
  ACCESS read-only
  STATUS mandatory
  DESCRIPTION
    "Describes how incoming broadcasts will be treated.
     on (2)  : broadcasts will be evaluated and answered if necessary.
     off (1) : broadcasts will be ignored. "
  ::= { bcamGlobal 10 }
-- SNMPNAME: GBRC
-- ASSNAME: YBTIPOPT

bcamGlobalArp OBJECT-TYPE
  SYNTAX INTEGER {
-- ASSMULTI:
		 off(1),   -- ASSVAL: YBTARPNO 128
		 quiet(2), -- ASSVAL: YBTARPQU 64
		 on(4)     -- ASSVAL: YBTARPTI 32
		 }
  ACCESS read-only
  STATUS mandatory
  DESCRIPTION
    "Describes if the address resolution protocol is used.
     off (1)   : no ARP will be used.
     quiet (2) : ARP will be used the first time a route is used and periodically if there exists a
	     transport connection to the system described by this route and there was no data transfer
	     in the last supervision interval.
     on (4)    : ARP will be used the first time a route is used and periodically after the supervision
	     interval."
  ::= { bcamGlobal 11 }
-- SNMPNAME: GARP
-- ASSNAME: YBTARPFG

bcamGlobalRarp OBJECT-TYPE
  SYNTAX INTEGER {
-- ASSMULTI:
		 off(1), -- ASSVAL: 0 0
		 on(2)   -- ASSVAL: YBTRARP 1
		 }
  ACCESS read-only
  STATUS mandatory
  DESCRIPTION
    "Describes if the reverse address resolution protocol will be supported.
     off (1) : RARP not supported.
     on (2)  : RARP supported."
  ::= { bcamGlobal 12 }
-- SNMPNAME: GRAR
-- ASSNAME: YBTIPOPT


bcamGlobalInWaitLimit1 OBJECT-TYPE
  SYNTAX INTEGER
  ACCESS read-write
  STATUS mandatory
  DESCRIPTION
    " The lowest bucket limit for the recording of the input wait times in milliseconds.
      The input wait time is the time interval between the
      announcement of a message to an application and corresponding
      receive call. Every change will reset all counters for the input wait time."
  ::= { bcamGlobal 13 }
-- SNMPNAME: GWL1
-- ASSNAME: YBTMWLI1
-- implemented

bcamGlobalInWaitLimit2 OBJECT-TYPE
  SYNTAX INTEGER
  ACCESS read-write
  STATUS mandatory
  DESCRIPTION
    " The second bucket limit for the recording of the input wait times in milliseconds.
      The input wait time is the time interval between the
      announcement of a message to an application and corresponding
      receive call. Every change will reset all counters for the input wait time."
  ::= { bcamGlobal 14 }
-- SNMPNAME: GWL2
-- ASSNAME: YBTMWLI2
-- implemented

bcamGlobalInWaitLimit3 OBJECT-TYPE
  SYNTAX INTEGER
  ACCESS read-write
  STATUS mandatory
  DESCRIPTION
    " The third bucket limit for the recording of the input wait times in milliseconds.
      The input wait time is the time interval between the
      announcement of a message to an application and corresponding
      receive call. Every change will reset all counters for the input wait time."
  ::= { bcamGlobal 15 }
-- SNMPNAME: GWL3
-- ASSNAME: YBTMWLI3
-- implemented

bcamGlobalInWaitLimit4 OBJECT-TYPE
  SYNTAX INTEGER
  ACCESS read-write
  STATUS mandatory
  DESCRIPTION
    " The highest bucket limit for the recording of the input wait times in milliseconds.
      The input wait time is the time interval between the
      announcement of a message to an application and corresponding
      receive call. Every change will reset all counters for the input wait time."
  ::= { bcamGlobal 16 }
-- SNMPNAME: GWL4
-- ASSNAME: YBTMWLI4
-- implemented

bcamGlobalInWaitChange OBJECT-TYPE
  SYNTAX INTEGER (0..255) -- ASSLEN: 1
  ACCESS read-only
  STATUS mandatory
  DESCRIPTION
    " The number of times the limits of the input wait time buckets have
      been changed."
  ::= { bcamGlobal 17 }
-- SNMPNAME: GWCT
-- ASSNAME: YBTMWCNT
-- implemented

bcamGlobalInWaitSet OBJECT-TYPE
  SYNTAX INTEGER {
-- ASSMULTI:
--                 off(0),
		 on(1),  -- ASSVAL: YBTMAWT 32
		 off(2)  -- ASSVAL: 0 0
		 }
  ACCESS read-write
  STATUS mandatory
  DESCRIPTION
    " The state of counting into the input wait time buckets.
      off (2) : the counting is stopped.
      on  (1) : the counting is running. "
  ::= { bcamGlobal 18 }
-- SNMPNAME: GWST
-- ASSNAME: YBTMESFL
-- implemented


bcamGlobalReactLimit1 OBJECT-TYPE
  SYNTAX INTEGER
  ACCESS read-write
  STATUS mandatory
  DESCRIPTION
    " The lowest bucket limit for the recording of the application reaction times in milliseconds.
      The application reaction time is the time interval between a receive call
      and a directly following send call. Every change will reset all counters for the
      application reaction time. "
  ::= { bcamGlobal 19 }
-- SNMPNAME: GRL1
-- ASSNAME: YBTMRLI1
-- implemented

bcamGlobalReactLimit2 OBJECT-TYPE
  SYNTAX INTEGER
  ACCESS read-write
  STATUS mandatory
  DESCRIPTION
    " The second bucket limit for the recording of the application reaction times in milliseconds.
      The application reaction time is the time interval between a receive call
      and a directly following send call. Every change will reset all counters for the
      application reaction time. "
  ::= { bcamGlobal 20 }
-- SNMPNAME: GRL2
-- ASSNAME: YBTMRLI2
-- implemented

bcamGlobalReactLimit3 OBJECT-TYPE
  SYNTAX INTEGER
  ACCESS read-write
  STATUS mandatory
  DESCRIPTION
    " The third bucket limit for the recording of the application reaction times in milliseconds.
      The application reaction time is the time interval between a receive call
      and a directly following send call. Every change will reset all counters for the
      application reaction time. "
  ::= { bcamGlobal 21 }
-- SNMPNAME: GRL3
-- ASSNAME: YBTMRLI3
-- implemented

bcamGlobalReactLimit4 OBJECT-TYPE
  SYNTAX INTEGER
  ACCESS read-write
  STATUS mandatory
  DESCRIPTION
    " The highest bucket limit for the recording of the application reaction times in milliseconds.
      The application reaction time is the time interval between a receive call
      and a directly following send call. Every change will reset all counters for the
      application reaction time. "
  ::= { bcamGlobal 22 }
-- SNMPNAME: GRL4
-- ASSNAME: YBTMRLI4
-- implemented

bcamGlobalReactChange OBJECT-TYPE
  SYNTAX INTEGER (0..255) -- ASSLEN: 1
  ACCESS read-only
  STATUS mandatory
  DESCRIPTION
    " The number of times the limits of the application reaction time buckets have
      been changed."
  ::= { bcamGlobal 23 }
-- SNMPNAME: GRCT
-- ASSNAME: YBTMRCNT
-- implemented

bcamGlobalReactSet OBJECT-TYPE
  SYNTAX INTEGER {
-- ASSMULTI:
--                 off(0),
		 on(1),  -- ASSVAL: YBTMART 16
		 off(2)  -- ASSVAL: 0 0
		 }
  ACCESS read-write
  STATUS mandatory
  DESCRIPTION
    " The state of counting into the application reaction time buckets.
      off (2) : the counting is stopped.
      on  (1) : the counting is running. "
  ::= { bcamGlobal 24 }
-- SNMPNAME: GRST
-- ASSNAME: YBTMESFL
-- implemented

bcamGlobalInProcLimit1 OBJECT-TYPE
  SYNTAX INTEGER
  ACCESS read-write
  STATUS mandatory
  DESCRIPTION
    " The lowest bucket limit for the recording of the inbound processing times in milliseconds.
      The inbound processing time is the time interval between the arrival
      of the first byte of a message at layer 2 and the receive of the last byte
      this message by the application. Every change will reset all counters for the
      inbound processing time. "
  ::= { bcamGlobal 25 }
-- SNMPNAME: GIL1
-- ASSNAME: YBTMILI1
-- implemented

bcamGlobalInProcLimit2 OBJECT-TYPE
  SYNTAX INTEGER
  ACCESS read-write
  STATUS mandatory
  DESCRIPTION
    " The second bucket limit for the recording of the inbound processing times in milliseconds.
      The inbound processing time is the time interval between the arrival
      of the first byte of a message at layer 2 and the receive of the last byte
      this message by the application. Every change will reset all counters for the
      inbound processing time. "
  ::= { bcamGlobal 26 }
-- SNMPNAME: GIL2
-- ASSNAME: YBTMILI2
-- implemented

bcamGlobalInProcLimit3 OBJECT-TYPE
  SYNTAX INTEGER
  ACCESS read-write
  STATUS mandatory
  DESCRIPTION
    " The third bucket limit for the recording of the inbound processing times in milliseconds.
      The inbound processing time is the time interval between the arrival
      of the first byte of a message at layer 2 and the receive of the last byte
      this message by the application. Every change will reset all counters for the
      inbound processing time. "
  ::= { bcamGlobal 27 }
-- SNMPNAME: GIL3
-- ASSNAME: YBTMILI3
-- implemented

bcamGlobalInProcLimit4 OBJECT-TYPE
  SYNTAX INTEGER
  ACCESS read-write
  STATUS mandatory
  DESCRIPTION
    " The highest bucket limit for the recording of the inbound processing times in milliseconds.
      The inbound processing time is the time interval between the arrival
      of the first byte of a message at layer 2 and the receive of the last byte
      this message by the application. Every change will reset all counters for the
      inbound processing time. "
  ::= { bcamGlobal 28 }
-- SNMPNAME: GIL4
-- ASSNAME: YBTMILI4
-- implemented

bcamGlobalInProcChange OBJECT-TYPE
  SYNTAX INTEGER (0..255) -- ASSLEN: 1
  ACCESS read-only
  STATUS mandatory
  DESCRIPTION
    " The number of times the limits of the inbound processing time buckets have
      been changed."
  ::= { bcamGlobal 29 }
-- SNMPNAME: GICT
-- ASSNAME: YBTMICNT
-- implemented

bcamGlobalInProcSet OBJECT-TYPE
  SYNTAX INTEGER {
-- ASSMULTI:
--                 off(0),
		 on(1),  -- ASSVAL: YBTMINB 4
		 off(2)  -- ASSVAL: 0 0
		 }
  ACCESS read-write
  STATUS mandatory
  DESCRIPTION
    " The state of counting into the inbound processing time buckets.
      off (2) : the counting is stopped.
      on  (1) : the counting is running. "
  ::= { bcamGlobal 30 }
-- SNMPNAME: GIST
-- ASSNAME: YBTMESFL
-- implemented

bcamGlobalOutProcLimit1 OBJECT-TYPE
  SYNTAX INTEGER
  ACCESS read-write
  STATUS mandatory
  DESCRIPTION
    " The lowest bucket limit for the recording of the outbound processing times in milliseconds.
      The outbound processing time is the time interval between the send call
      of an application and the confirmation for the processing of the
      last byte of the message by layer 1. Every change will reset all counters for the
      outbound processing time. "
  ::= { bcamGlobal 31 }
-- SNMPNAME: GOL1
-- ASSNAME: YBTMOLI1
-- implemented

bcamGlobalOutProcLimit2 OBJECT-TYPE
  SYNTAX INTEGER
  ACCESS read-write
  STATUS mandatory
  DESCRIPTION
    " The second bucket limit for the recording of the outbound processing times in milliseconds.
      The outbound processing time is the time interval between the send call
      of an application and the confirmation for the processing of the
      last byte of the message by layer 1. Every change will reset all counters for the
      outbound processing time. "
  ::= { bcamGlobal 32 }
-- SNMPNAME: GOL2
-- ASSNAME: YBTMOLI2
-- implemented

bcamGlobalOutProcLimit3 OBJECT-TYPE
  SYNTAX INTEGER
  ACCESS read-write
  STATUS mandatory
  DESCRIPTION
    " The third bucket limit for the recording of the outbound processing times in milliseconds.
      The outbound processing time is the time interval between the send call
      of an application and the confirmation for the processing of the
      last byte of the message by layer 1. Every change will reset all counters for the
      outbound processing time. "
  ::= { bcamGlobal 33 }
-- SNMPNAME: GOL3
-- ASSNAME: YBTMOLI3
-- implemented

bcamGlobalOutProcLimit4 OBJECT-TYPE
  SYNTAX INTEGER
  ACCESS read-write
  STATUS mandatory
  DESCRIPTION
    " The highest bucket limit for the recording of the outbound processing times in milliseconds.
      The outbound processing time is the time interval between the send call
      of an application and the confirmation for the processing of the
      last byte of the message by layer 1. Every change will reset all counters for the
      outbound processing time. "
  ::= { bcamGlobal 34 }
-- SNMPNAME: GOL4
-- ASSNAME: YBTMOLI4
-- implemented

bcamGlobalOutProcChange OBJECT-TYPE
  SYNTAX INTEGER (0..255) -- ASSLEN: 1
  ACCESS read-only
  STATUS mandatory
  DESCRIPTION
    " The number of times the limits of the outbound processing time buckets have
      been changed."
  ::= { bcamGlobal 35 }
-- SNMPNAME: GOCT
-- ASSNAME: YBTMOCNT
-- implemented

bcamGlobalOutProcSet OBJECT-TYPE
  SYNTAX INTEGER {
-- ASSMULTI:
--                 off(0),
		 on(1),  -- ASSVAL: YBTMOUB 8
		 off(2)  -- ASSVAL: 0 0
		 }
  ACCESS read-write
  STATUS mandatory
  DESCRIPTION
    " The state of counting into the outbound processing time buckets.
      off (2) : the counting is stopped.
      on  (1) : the counting is running. "
  ::= { bcamGlobal 36 }
-- SNMPNAME: GOST
-- ASSNAME: YBTMESFL
-- implemented

bcamGlobalSnmpRelease OBJECT-TYPE
  SYNTAX INTEGER (0..32767) -- ASSLEN: 2
  ACCESS read-write
  STATUS mandatory
  DESCRIPTION
    " The time interval in minutes for which the values for already closed connections
      and applications are still available. "
  ::= { bcamGlobal 37 }
-- SNMPNAME: GSRL
-- ASSNAME: YBCCTIM
-- implemented

bcamGlobalTrapPollInterval OBJECT-TYPE
  SYNTAX INTEGER (0..32767) -- ASSLEN: 2
  ACCESS read-write
  STATUS mandatory
  DESCRIPTION
    " The time interval in seconds after which the SNMP agent will poll for traps."
  ::= { bcamGlobal 38 }
-- SNMPNAME: GPIV
-- ASSNAME: YBCTRPIV

bcamGlobalFileApplTable  OBJECT-TYPE
  SYNTAX DisplayString (SIZE(54)) -- ASSLEN: 55 VAR
  ACCESS read-only
  STATUS mandatory
  DESCRIPTION
    "The name of the file that contains the assignments of NEA or ISO applications to the virtual
     host on which they shall run."
  ::= { bcamGlobal 39 }
-- SNMPNAME: GNAT
-- ASSNAME: YYSPNAPT

bcamGlobalFileSocketHostTable  OBJECT-TYPE
  SYNTAX DisplayString (SIZE(54)) -- ASSLEN: 55 VAR
  ACCESS read-only
  STATUS mandatory
  DESCRIPTION
    "The name of the file that contains the assignments of IP adresses to socket host names
     for automatic created endsystems."
  ::= { bcamGlobal 40 }
-- SNMPNAME: GNSH
-- ASSNAME: YYSPNSAF

bcamGlobalFileProcTable  OBJECT-TYPE
  SYNTAX DisplayString (SIZE(54)) -- ASSLEN: 55 VAR
  ACCESS read-only
  STATUS mandatory
  DESCRIPTION
    "The name of the file that contains the assignments of host names to net addresses for automatic
     created endsystems."
  ::= { bcamGlobal 41 }
-- SNMPNAME: GNPR
-- ASSNAME: YBTFNAPT

bcamGlobalAccessProcTable  OBJECT-TYPE
  SYNTAX INTEGER {
-- ASSMULTI:
		 read(1),  -- ASSVAL: YBTFACPR 1
		 update(2) -- ASSVAL: YBTFACPU 2
		 }
  ACCESS read-only
  STATUS mandatory
  DESCRIPTION
    "The access of the file named in bcamGlobalFileProcTable:
     read   (1) : only endsystems contained in the file will be created by automatic endsystem creation.
     update (2) : the file will be extended if a new endsystem is created."
  ::= { bcamGlobal 42 }
-- SNMPNAME: GAPR
-- ASSNAME: YBTFACFG

bcamGlobalHostName  OBJECT-TYPE
  SYNTAX DisplayString (SIZE(8)) -- ASSLEN: 9 VAR
  ACCESS read-only
  STATUS mandatory
  DESCRIPTION
    " NEA name of the local endsystem "
  ::= { bcamGlobal 43 }
-- SNMPNAME: GHNM
-- ASSNAME: YYYHNAME



-- the Memory group


bcamMemoryClass3 OBJECT-TYPE
  SYNTAX INTEGER
  ACCESS read-only
  STATUS mandatory
  DESCRIPTION
   " The number of bytes of class 3 memory requested by BCAM. "
  ::= { bcamMemory 1 }
-- SNMPNAME: MCL3
-- ASSNAME: YBTMCL3#
-- implemented

bcamMemoryClass4 OBJECT-TYPE
  SYNTAX INTEGER
  ACCESS read-only
  STATUS mandatory
  DESCRIPTION
   " The number of bytes of class 4 memory requested by BCAM. "
  ::= { bcamMemory 2 }
-- SNMPNAME: MCL4
-- ASSNAME: YBTMCL4#
-- implemented

bcamMemoryLenLongEventSlot OBJECT-TYPE
  SYNTAX INTEGER  -- ASSLEN: 2
  ACCESS read-only
  STATUS mandatory
  DESCRIPTION
   " The length of one long event slot in bytes. "
  ::= { bcamMemory 3 }
-- SNMPNAME: MLLS
-- ASSNAME: YBTELLNG
-- implemented

bcamMemoryOccLongEventSlot OBJECT-TYPE
  SYNTAX INTEGER
  ACCESS read-only
  STATUS mandatory
  DESCRIPTION
   " The number of long event slots currently used. "
  ::= { bcamMemory 4 }
-- SNMPNAME: MOLS
-- ASSNAME: YBTELOCC
-- implemented

bcamMemoryLenShortEventSlot OBJECT-TYPE
  SYNTAX INTEGER  -- ASSLEN: 2
  ACCESS read-only
  STATUS mandatory
  DESCRIPTION
   " The length of one short event slot in bytes. "
  ::= { bcamMemory 5 }
-- SNMPNAME: MLSS
-- ASSNAME: YBTESLNG
-- implemented

bcamMemoryOccShortEventSlot OBJECT-TYPE
  SYNTAX INTEGER
  ACCESS read-only
  STATUS mandatory
  DESCRIPTION
   " The number of short event slots currently used. "
  ::= { bcamMemory 6 }
-- SNMPNAME: MOSS
-- ASSNAME: YBTESOCC
-- implemented

bcamMemoryLenTransParamSlot OBJECT-TYPE
  SYNTAX INTEGER  -- ASSLEN: 2
  ACCESS read-only
  STATUS mandatory
  DESCRIPTION
   " The length of one transport parameter block in bytes. "
  ::= { bcamMemory 7 }
-- SNMPNAME: MLTS
-- ASSNAME: YBT4ILNG
-- implemented

bcamMemoryOccTransParamSlot OBJECT-TYPE
  SYNTAX INTEGER
  ACCESS read-only
  STATUS mandatory
  DESCRIPTION
   " The number of transport parameter blocks currently used. "
  ::= { bcamMemory 8 }
-- SNMPNAME: MOTS
-- ASSNAME: YBT4IOCC
-- implemented

bcamMemoryLenSnmpParamSlot OBJECT-TYPE
  SYNTAX INTEGER  -- ASSLEN: 2
  ACCESS read-only
  STATUS mandatory
  DESCRIPTION
   " The length of one SNMP parameter block in bytes. "
  ::= { bcamMemory 9 }
-- SNMPNAME: MLPS
-- ASSNAME: YBTSNLNG
-- implemented

bcamMemoryOccSnmpParamSlot OBJECT-TYPE
  SYNTAX INTEGER
  ACCESS read-only
  STATUS mandatory
  DESCRIPTION
   " The number of SNMP parameter blocks currently used. "
  ::= { bcamMemory 10 }
-- SNMPNAME: MOPS
-- ASSNAME: YBTSNOCC
-- implemented

bcamMemoryLenApplCb OBJECT-TYPE
  SYNTAX INTEGER  -- ASSLEN: 2
  ACCESS read-only
  STATUS mandatory
  DESCRIPTION
   " The length of one application control block in bytes. "
  ::= { bcamMemory 11 }
-- SNMPNAME: MLAC
-- ASSNAME: YBCAPLNG
-- implemented

bcamMemoryOccApplCb OBJECT-TYPE
  SYNTAX INTEGER
  ACCESS read-only
  STATUS mandatory
  DESCRIPTION
   " The number of application control blocks currently used. "
  ::= { bcamMemory 12 }
-- SNMPNAME: MOAC
-- ASSNAME: YBCAPOCC
-- implemented

bcamMemoryLenEnaCb OBJECT-TYPE
  SYNTAX INTEGER  -- ASSLEN: 2
  ACCESS read-only
  STATUS mandatory
  DESCRIPTION
   " The length of one control block in bytes. "
  ::= { bcamMemory 13 }
-- SNMPNAME: MLEC
-- ASSNAME: YBCEALNG
-- implemented

bcamMemoryOccEnaCb OBJECT-TYPE
  SYNTAX INTEGER
  ACCESS read-only
  STATUS mandatory
  DESCRIPTION
   " The number of control blocks currently used. "
  ::= { bcamMemory 14 }
-- SNMPNAME: MOEC
-- ASSNAME: YBCEAOCC
-- implemented

bcamMemoryLenExtApplCb OBJECT-TYPE
  SYNTAX INTEGER  -- ASSLEN: 2
  ACCESS read-only
  STATUS mandatory
  DESCRIPTION
   " The length of one extended application control block in bytes. "
  ::= { bcamMemory 15 }
-- SNMPNAME: MLXA
-- ASSNAME: YBCAXLNG
-- implemented

bcamMemoryOccExtApplCb OBJECT-TYPE
  SYNTAX INTEGER
  ACCESS read-only
  STATUS mandatory
  DESCRIPTION
   " The number of extended application control blocks currently used. "
  ::= { bcamMemory 16 }
-- SNMPNAME: MOXA
-- ASSNAME: YBCAXOCC
-- implemented

bcamMemoryLenShortResConn2 OBJECT-TYPE
  SYNTAX INTEGER  -- ASSLEN: 2
  ACCESS read-only
  STATUS mandatory
  DESCRIPTION
   " The length of one short resident connection control block 2 in bytes. "
  ::= { bcamMemory 17 }
-- SNMPNAME: MLR2
-- ASSNAME: YBCC1LNG
-- implemented

bcamMemoryOccShortResConn2 OBJECT-TYPE
  SYNTAX INTEGER
  ACCESS read-only
  STATUS mandatory
  DESCRIPTION
   " The number of short resident connection control blocks 2 currently used. "
  ::= { bcamMemory 18 }
-- SNMPNAME: MOR2
-- ASSNAME: YBCC1OCC
-- implemented

bcamMemoryLenLongResConn2 OBJECT-TYPE
  SYNTAX INTEGER  -- ASSLEN: 2
  ACCESS read-only
  STATUS mandatory
  DESCRIPTION
   " The length of one long resident connection control block 2 in bytes. "
  ::= { bcamMemory 19 }
-- SNMPNAME: MLS2
-- ASSNAME: YBCC2LNG
-- implemented

bcamMemoryOccLongResConn2 OBJECT-TYPE
  SYNTAX INTEGER
  ACCESS read-only
  STATUS mandatory
  DESCRIPTION
   " The number of long resident connection control blocks 2 currently used. "
  ::= { bcamMemory 20 }
-- SNMPNAME: MOS2
-- ASSNAME: YBCC2OCC
-- implemented

bcamMemoryLenShortPagConn1 OBJECT-TYPE
  SYNTAX INTEGER  -- ASSLEN: 2
  ACCESS read-only
  STATUS mandatory
  DESCRIPTION
   " The length of one short pageable connection control block 1 in bytes. "
  ::= { bcamMemory 21 }
-- SNMPNAME: MLP1
-- ASSNAME: YBCC3LNG
-- implemented

bcamMemoryOccShortPagConn1 OBJECT-TYPE
  SYNTAX INTEGER
  ACCESS read-only
  STATUS mandatory
  DESCRIPTION
   " The number of short pageable connection control blocks 1 currently used. "
  ::= { bcamMemory 22 }
-- SNMPNAME: MOP1
-- ASSNAME: YBCC3OCC
-- implemented

bcamMemoryLenSnmpConn OBJECT-TYPE
  SYNTAX INTEGER  -- ASSLEN: 2
  ACCESS read-only
  STATUS mandatory
  DESCRIPTION
   " The length of one SNMP connection control block in bytes. "
  ::= { bcamMemory 23 }
-- SNMPNAME: MLSC
-- ASSNAME: YBCC7LNG
-- implemented

bcamMemoryOccSnmpConn OBJECT-TYPE
  SYNTAX INTEGER
  ACCESS read-only
  STATUS mandatory
  DESCRIPTION
   " The number of SNMP connection control blocks currently used. "
  ::= { bcamMemory 24 }
-- SNMPNAME: MOSC
-- ASSNAME: YBCC7OCC
-- implemented

bcamMemoryLenLongPagConn1 OBJECT-TYPE
  SYNTAX INTEGER  -- ASSLEN: 2
  ACCESS read-only
  STATUS mandatory
  DESCRIPTION
   " The length of one long pageable connection control block 1 in bytes. "
  ::= { bcamMemory 25 }
-- SNMPNAME: MLQ1
-- ASSNAME: YBCC5LNG
-- implemented

bcamMemoryOccLongPagConn1 OBJECT-TYPE
  SYNTAX INTEGER
  ACCESS read-only
  STATUS mandatory
  DESCRIPTION
   " The number of long pageable connection control blocks 1 currently used. "
  ::= { bcamMemory 26 }
-- SNMPNAME: MOQ1
-- ASSNAME: YBCC5OCC
-- implemented

bcamMemoryLenShortPagConn2 OBJECT-TYPE
  SYNTAX INTEGER  -- ASSLEN: 2
  ACCESS read-only
  STATUS mandatory
  DESCRIPTION
   " The length of one short pageable connection control block 2 in bytes. "
  ::= { bcamMemory 27 }
-- SNMPNAME: MLP2
-- ASSNAME: YBCC6LNG
-- implemented

bcamMemoryOccShortPagConn2 OBJECT-TYPE
  SYNTAX INTEGER
  ACCESS read-only
  STATUS mandatory
  DESCRIPTION
   " The number of short pageable connection control blocks 2 currently used. "
  ::= { bcamMemory 28 }
-- SNMPNAME: MOP2
-- ASSNAME: YBCC6OCC
-- implemented

bcamMemoryPoolInputCurrent OBJECT-TYPE
  SYNTAX INTEGER
  ACCESS read-only
  STATUS mandatory
  DESCRIPTION
    " The number of bytes of resident memory currently used for input cells "
  ::= { bcamMemory 29 }
-- SNMPNAME: MPIC
-- ASSNAME: YFDDPOCB
-- implemented

bcamMemoryPoolInputResume OBJECT-TYPE
  SYNTAX INTEGER -- ASSLEN: 1
  ACCESS read-only
  STATUS mandatory
  DESCRIPTION
    " Describes whether an interface waits for memory for input . If zero, some
      interfaces will not have enough input buffer( A cell request was rejected
      because bcamMemoryPoolInputCurrent exceeded bcamMemoryPoolInputLimitTrap). "
  ::= { bcamMemory 30 }
-- SNMPNAME: MPIR
-- ASSNAME: YFDDPFLG
-- implemented

bcamMemoryPoolInputMonMax OBJECT-TYPE
  SYNTAX INTEGER
  ACCESS read-only
  STATUS mandatory
  DESCRIPTION
    " The maximum number of bytes of resident memory used for input cells for the
      last 5 seconds. "
  ::= { bcamMemory 31 }
-- SNMPNAME: MPIA
-- ASSNAME: YFDMONIH
-- implemented

bcamMemoryPoolInputMonMin OBJECT-TYPE
  SYNTAX INTEGER
  ACCESS read-only
  STATUS mandatory
  DESCRIPTION
    " The minimum number of bytes of resident memory used for input cells for the
      last 5 seconds. "
  ::= { bcamMemory 32 }
-- SNMPNAME: MPII
-- ASSNAME: YFDMONIL
-- implemented

bcamMemoryPoolInputLimit OBJECT-TYPE
  SYNTAX INTEGER
  ACCESS read-only
  STATUS mandatory
  DESCRIPTION
    " The maximum number of bytes of resident memory to be used for input cells. "
  ::= { bcamMemory 33 }
-- SNMPNAME: MPIL
-- ASSNAME: YFDITHRS
-- implemented

bcamMemoryPoolInputLimitTrap OBJECT-TYPE
  SYNTAX INTEGER
  ACCESS read-only
  STATUS mandatory
  DESCRIPTION
    " The trap limit for the number of bytes of resident memory for input cells
      (if bcamMemoryPoolInputMonMin is greater than bcamMemoryPoolInputLimitTrap, a trap will
      be sent). "
  ::= { bcamMemory 34 }
-- SNMPNAME: MPIT
-- ASSNAME: YFDICRIT
-- implemented

bcamMemoryPoolMaxResident OBJECT-TYPE
  SYNTAX INTEGER
  ACCESS read-write
  STATUS mandatory
  DESCRIPTION
    " The maximum number of bytes of resident memory to be used for input and output cells. "
  ::= { bcamMemory 35 }
-- SNMPNAME: MPMR
-- ASSNAME: YFDDPLEN
-- implemented

bcamMemoryPoolMaxPageable OBJECT-TYPE
  SYNTAX INTEGER
  ACCESS read-write
  STATUS mandatory
  DESCRIPTION
    " The maximum number of bytes of pageable memory to be used for input and output cells. "
  ::= { bcamMemory 36 }
-- SNMPNAME: MPMP
-- ASSNAME: YFDPGMAX

bcamMemoryPoolInputMaxPageable OBJECT-TYPE
  SYNTAX INTEGER
  ACCESS read-only
  STATUS mandatory
  DESCRIPTION
    " The maximum number of bytes of pageable memory to be used for input cells. "
  ::= { bcamMemory 37 }
-- SNMPNAME: MPIP
-- ASSNAME: YFDPGMAX
-- implemented

bcamMemoryPoolOutputCurrent OBJECT-TYPE
  SYNTAX INTEGER
  ACCESS read-only
  STATUS mandatory
  DESCRIPTION
    " The number of bytes of resident memory currently used for output cells. "
  ::= { bcamMemory 38 }
-- SNMPNAME: MPOC
-- ASSNAME: YFDPOOCB
-- implemented

bcamMemoryPoolOutputResume OBJECT-TYPE
  SYNTAX INTEGER -- ASSLEN: 1
  ACCESS read-only
  STATUS mandatory
  DESCRIPTION
    " Describes whether an interface waits for memory for output . If zero, some
      interfaces will not have enough output buffer( A cell request was rejected
      because bcamMemoryPoolOutputCurrent exceeded bcamMemoryPoolOutputLimitTrap). "
  ::= { bcamMemory 39 }
-- SNMPNAME: MPOR
-- ASSNAME: YFDPOFLG
-- implemented

bcamMemoryPoolOutputMonMax OBJECT-TYPE
  SYNTAX INTEGER
  ACCESS read-only
  STATUS mandatory
  DESCRIPTION
    " The maximum number of bytes of resident memory used for output cells for the
      last 5 seconds. "
  ::= { bcamMemory 40 }
-- SNMPNAME: MPOA
-- ASSNAME: YFDMONOH
-- implemented

bcamMemoryPoolOutputMonMin OBJECT-TYPE
  SYNTAX INTEGER
  ACCESS read-only
  STATUS mandatory
  DESCRIPTION
    " The minimum number of bytes of resident memory used for output cells for the
      last 5 seconds. "
  ::= { bcamMemory 41 }
-- SNMPNAME: MPOI
-- ASSNAME: YFDMONOL
-- implemented

bcamMemoryPoolOutputLimit OBJECT-TYPE
  SYNTAX INTEGER
  ACCESS read-only
  STATUS mandatory
  DESCRIPTION
    " The maximum number of bytes of resident memory to be used for output cells. "
  ::= { bcamMemory 42 }
-- SNMPNAME: MPOL
-- ASSNAME: YFDOTHRS
-- implemented

bcamMemoryPoolOutputLimitTrap OBJECT-TYPE
  SYNTAX INTEGER
  ACCESS read-only
  STATUS mandatory
  DESCRIPTION
    " The trap limit for the number of bytes of resident memory for output cells
      (if bcamMemoryPoolOutputMonMin is greater than bcamMemoryPoolOutputLimitTrap, a trap will
      be sent). "
  ::= { bcamMemory 43 }
-- SNMPNAME: MPOT
-- ASSNAME: YFDOREST
-- implemented

bcamMemoryPoolMaxCells OBJECT-TYPE
  SYNTAX INTEGER -- ASSLEN: 2
  ACCESS read-only
  STATUS mandatory
  DESCRIPTION
    " The maximum number of cells contained in every pool type. "
  ::= { bcamMemory 44 }
-- SNMPNAME: MPMC
-- ASSNAME: YFDBITLG
-- implemented

bcamMemoryPoolOutputMaxPageable OBJECT-TYPE
  SYNTAX INTEGER
  ACCESS read-only
  STATUS mandatory
  DESCRIPTION
    " The maximum number of bytes of pageable memory to be used for output cells. "
  ::= { bcamMemory 45 }
-- SNMPNAME: MPOP
-- ASSNAME: YFDOPTHR
-- implemented

bcamMemoryPoolRoutingCurrent OBJECT-TYPE
  SYNTAX INTEGER
  ACCESS read-only
  STATUS mandatory
  DESCRIPTION
    " The number of bytes of resident memory currently used for routing cells "
  ::= { bcamMemory 46 }
-- SNMPNAME: MPRC
-- ASSNAME: YFDROUB#
-- implemented

bcamMemoryPoolRoutingLimit OBJECT-TYPE
  SYNTAX INTEGER
  ACCESS read-only
  STATUS mandatory
  DESCRIPTION
    " The maximum number of bytes of resident memory to be used for routing cells. "
  ::= { bcamMemory 47 }
-- SNMPNAME: MPRL
-- ASSNAME: YFDROUTH
-- implemented

bcamMemoryPoolPageableCurrent OBJECT-TYPE
  SYNTAX INTEGER
  ACCESS read-only
  STATUS mandatory
  DESCRIPTION
    " The number of bytes of pageable memory currently used for pools "
  ::= { bcamMemory 48 }
-- SNMPNAME: MPPC
-- ASSNAME: YFDOCCP
-- implemented

bcamMemoryPoolPageableFixed OBJECT-TYPE
  SYNTAX INTEGER
  ACCESS read-only
  STATUS mandatory
  DESCRIPTION
    " The number of bytes of pageable fixed memory currently used for output cells. "
  ::= { bcamMemory 49 }
-- SNMPNAME: MPPF
-- ASSNAME: YFDFIXB
-- implemented

bcamMemoryCellReqSucc OBJECT-TYPE
  SYNTAX INTEGER
  ACCESS read-only
  STATUS mandatory
  DESCRIPTION
    " The number of successful cell requests. "
  ::= { bcamMemory 50 }
-- SNMPNAME: MCSU
-- ASSNAME: YFDREQ#
-- implemented

bcamMemoryCellReqResOutExceed OBJECT-TYPE
  SYNTAX INTEGER
  ACCESS read-only
  STATUS mandatory
  DESCRIPTION
    " The number of requests for resident output cells that failed
      because the limit has been reached. "
  ::= { bcamMemory 51 }
-- SNMPNAME: MCRO
-- ASSNAME: YFDTHRO#
-- implemented

bcamMemoryCellReqResInExceed OBJECT-TYPE
  SYNTAX INTEGER
  ACCESS read-only
  STATUS mandatory
  DESCRIPTION
    " The number of requests for resident input cells that failed
      because limit has been reached. "
  ::= { bcamMemory 52 }
-- SNMPNAME: MCRI
-- ASSNAME: YFDTHRI#
-- implemented

bcamMemoryCellReqTempExceed OBJECT-TYPE
  SYNTAX INTEGER
  ACCESS read-only
  STATUS mandatory
  DESCRIPTION
    " The number of cell requests failed because of temporary shortage. "
  ::= { bcamMemory 53 }
-- SNMPNAME: MCTE
-- ASSNAME: YFDTEMP#
-- implemented

bcamMemoryCellReqBitmapFull OBJECT-TYPE
  SYNTAX INTEGER
  ACCESS read-only
  STATUS mandatory
  DESCRIPTION
    " The number of cell requests failed because bitmap was full. "
  ::= { bcamMemory 54 }
-- SNMPNAME: MCBF
-- ASSNAME: YFDBIFU#
-- implemented

bcamMemoryCellReqNoMemory OBJECT-TYPE
  SYNTAX INTEGER
  ACCESS read-only
  STATUS mandatory
  DESCRIPTION
    " The number of cell requests failed because memory request failed. "
  ::= { bcamMemory 55 }
-- SNMPNAME: MCNM
-- ASSNAME: YFD$REQ#
-- implemented

bcamMemoryCellReqPagInExceed OBJECT-TYPE
  SYNTAX INTEGER
  ACCESS read-only
  STATUS mandatory
  DESCRIPTION
    " The number of requests for pageable input cells that failed
      because limit has been reached. "
  ::= { bcamMemory 56 }
-- SNMPNAME: MCPI
-- ASSNAME: YFDPGLI#
-- implemented

bcamMemoryCellReqPagOutExceed OBJECT-TYPE
  SYNTAX INTEGER
  ACCESS read-only
  STATUS mandatory
  DESCRIPTION
    " The number of requests for pageable output cells that failed
      because limit has been reached. "
  ::= { bcamMemory 57 }
-- SNMPNAME: MCPO
-- ASSNAME: YFDPGLO#
-- implemented




-- the Trace group


bcamTraceSavingState OBJECT-TYPE
  SYNTAX INTEGER {
-- ASSMULTI:
--                 noSaving(0),   ASSVAL: 0 0
		 initiated(1), -- ASSVAL: YTCSAVIN 1
		 active(2),    -- ASSVAL: YTCSAVAC 2
		 shutting(4),  -- ASSVAL: YTCTSHUT 4
		 passive(8),   -- ASSVAL: YTCSAVPA 40
		 waiting(16),  -- ASSVAL: YTCSAVWT 80
		 noSaving(32)  -- ASSVAL: 0 0
		 }
  ACCESS read-only
  STATUS mandatory
  DESCRIPTION
    " Describes if any of the running BCAM traces are saved to a file.
		 noSaving (32) : no trace will be written
		 initiated (1) : the trace saving task has been created
		 active    (2) : the trace saving task is active
		 shutting  (4) : the trace saving task is terminating
		 passive   (8) : the trace file has been closed
		 waiting  (16) : the trace saving task is waiting for trace data to write
      Several bits may be set simultaneous."
  ::= { bcamTrace 1 }
-- SNMPNAME: TSST
-- ASSNAME: YTCTFLAG
-- implemented

bcamTraceFilename OBJECT-TYPE
  SYNTAX DisplayString (SIZE(54)) -- ASSLEN: 55 VAR
  ACCESS read-only
  STATUS mandatory
  DESCRIPTION
    " The name of the file currently used for saving BCAM traces."
  ::= { bcamTrace 2 }
-- SNMPNAME: TSFN
-- ASSNAME: YTCTFPAT
-- implemented

bcamTraceMaxFilesize OBJECT-TYPE
  SYNTAX INTEGER
  ACCESS read-only
  STATUS mandatory
  DESCRIPTION
    " The maximum size of one file used for saving BCAM traces in bytes. "
  ::= { bcamTrace 3 }
-- SNMPNAME: TSFS
-- ASSNAME: YTCTFSIZ
-- implemented

bcamTraceNumberFiles OBJECT-TYPE
  SYNTAX INTEGER
  ACCESS read-only
  STATUS mandatory
  DESCRIPTION
    " The number of files used for saving BCAM traces. "
  ::= { bcamTrace 4 }
-- SNMPNAME: TSNF
-- ASSNAME: YTCTF#
-- implemented

bcamTraceAdmState OBJECT-TYPE
  SYNTAX INTEGER {
-- ASSMULTI:
--                 stopped(0),  ASSVAL: 0 0
		 running(1), -- ASSVAL: YTETALLO 1
		 save(2),    -- ASSVAL: YTESAVRQ 2
		 hold(4),    -- ASSVAL: YTEHLDRQ 4
		 stopped(8)  -- ASSVAL: 0 0
		 }
  ACCESS read-only
  STATUS mandatory
  DESCRIPTION
    " The current state of the trace.
      stopped (8) : the trace is not running.
      running (1) : the trace is running.
      save    (2) : the trace is running and saved to a file.
      hold    (4) : the trace data will be kept in case of an error.
      Several bits may be set simultaneous."
  ::= { bcamTrace 5 }
-- SNMPNAME: TADS
-- ASSNAME: YTETFLAG
-- implemented

bcamTraceAdmNumberBuffer OBJECT-TYPE
  SYNTAX INTEGER (1..16) -- ASSLEN: 2
  ACCESS read-only
  STATUS mandatory
  DESCRIPTION
    " The number of buffers used for the trace"
  ::= { bcamTrace 6 }
-- SNMPNAME: TADB
-- ASSNAME: YTEACBFN
-- implemented

bcamTraceAdmBufferLen OBJECT-TYPE
  SYNTAX INTEGER (512..16384) -- ASSLEN: 2
  ACCESS read-only
  STATUS mandatory
  DESCRIPTION
    " The length of one trace buffer in bytes (rounded up to multiples of 256). "
  ::= { bcamTrace 7 }
-- SNMPNAME: TADL
-- ASSNAME: YTEACBFL
-- implemented

bcamTraceBasicState OBJECT-TYPE
  SYNTAX INTEGER {
-- ASSMULTI:
--                 stopped(0),  ASSVAL: 0 0
		 running(1), -- ASSVAL: YTETALLO 1
		 save(2),    -- ASSVAL: YTESAVRQ 2
		 hold(4),    -- ASSVAL: YTEHLDRQ 4
		 stopped(8)  -- ASSVAL: 0 0
		 }
  ACCESS read-only
  STATUS mandatory
  DESCRIPTION
    " The current state of the trace.
      stopped (8) : the trace is not running.
      running (1) : the trace is running.
      save    (2) : the trace is running and saved to a file.
      hold    (4) : the trace data will be kept in case of an error.
      Several bits may be set simultaneous."
  ::= { bcamTrace 8 }
-- SNMPNAME: TBAS
-- ASSNAME: YTETFLAG
-- implemented

bcamTraceBasicNumberBuffer OBJECT-TYPE
  SYNTAX INTEGER (1..16) -- ASSLEN: 2
  ACCESS read-only
  STATUS mandatory
  DESCRIPTION
    " The number of buffers used for the trace"
  ::= { bcamTrace 9 }
-- SNMPNAME: TBAB
-- ASSNAME: YTEACBFN
-- implemented

bcamTraceBasicBufferLen OBJECT-TYPE
  SYNTAX INTEGER (512..16384) -- ASSLEN: 2
  ACCESS read-only
  STATUS mandatory
  DESCRIPTION
    " The length of one trace buffer in bytes (rounded up to multiples of 256). "
  ::= { bcamTrace 10 }
-- SNMPNAME: TBAL
-- ASSNAME: YTEACBFL
-- implemented

bcamTraceConnState OBJECT-TYPE
  SYNTAX INTEGER {
-- ASSMULTI:
--                 stopped(0),  ASSVAL: 0 0
		 running(1), -- ASSVAL: YTETALLO 1
		 save(2),    -- ASSVAL: YTESAVRQ 2
		 hold(4),    -- ASSVAL: YTEHLDRQ 4
		 stopped(8)  -- ASSVAL: 0 0
		 }
  ACCESS read-only
  STATUS mandatory
  DESCRIPTION
    " The current state of the trace.
      stopped (8) : the trace is not running.
      running (1) : the trace is running.
      save    (2) : the trace is running and saved to a file.
      hold    (4) : the trace data will be kept in case of an error.
      Several bits may be set simultaneous."
  ::= { bcamTrace 11 }
-- SNMPNAME: TCOS
-- ASSNAME: YTETFLAG
-- implemented

bcamTraceConnNumberBuffer OBJECT-TYPE
  SYNTAX INTEGER (1..16) -- ASSLEN: 2
  ACCESS read-only
  STATUS mandatory
  DESCRIPTION
    " The number of buffers used for the trace"
  ::= { bcamTrace 12 }
-- SNMPNAME: TCOB
-- ASSNAME: YTEACBFN
-- implemented

bcamTraceConnBufferLen OBJECT-TYPE
  SYNTAX INTEGER (512..16384) -- ASSLEN: 2
  ACCESS read-only
  STATUS mandatory
  DESCRIPTION
    " The length of one trace buffer in bytes (rounded up to multiples of 256). "
  ::= { bcamTrace 13 }
-- SNMPNAME: TCOL
-- ASSNAME: YTEACBFL
-- implemented

bcamTraceLocalState OBJECT-TYPE
  SYNTAX INTEGER {
-- ASSMULTI:
--                 stopped(0),  ASSVAL: 0 0
		 running(1), -- ASSVAL: YTETALLO 1
		 save(2),    -- ASSVAL: YTESAVRQ 2
		 hold(4),    -- ASSVAL: YTEHLDRQ 4
		 stopped(8)  -- ASSVAL: 0 0
		 }
  ACCESS read-only
  STATUS mandatory
  DESCRIPTION
    " The current state of the trace.
      stopped (8) : the trace is not running.
      running (1) : the trace is running.
      save    (2) : the trace is running and saved to a file.
      hold    (4) : the trace data will be kept in case of an error.
      Several bits may be set simultaneous."
  ::= { bcamTrace 14 }
-- SNMPNAME: TLOS
-- ASSNAME: YTETFLAG
-- implemented

bcamTraceLocalNumberBuffer OBJECT-TYPE
  SYNTAX INTEGER (1..16) -- ASSLEN: 2
  ACCESS read-only
  STATUS mandatory
  DESCRIPTION
    " The number of buffers used for the trace"
  ::= { bcamTrace 15 }
-- SNMPNAME: TLOB
-- ASSNAME: YTEACBFN
-- implemented

bcamTraceLocalBufferLen OBJECT-TYPE
  SYNTAX INTEGER (512..16384) -- ASSLEN: 2
  ACCESS read-only
  STATUS mandatory
  DESCRIPTION
    " The length of one trace buffer in bytes (rounded up to multiples of 256). "
  ::= { bcamTrace 16 }
-- SNMPNAME: TLOL
-- ASSNAME: YTEACBFL
-- implemented

bcamTraceMappingState OBJECT-TYPE
  SYNTAX INTEGER {
-- ASSMULTI:
--                 stopped(0),  ASSVAL: 0 0
		 running(1), -- ASSVAL: YTETALLO 1
		 save(2),    -- ASSVAL: YTESAVRQ 2
		 hold(4),    -- ASSVAL: YTEHLDRQ 4
		 stopped(8)  -- ASSVAL: 0 0
		 }
  ACCESS read-only
  STATUS mandatory
  DESCRIPTION
    " The current state of the trace.
      stopped (8) : the trace is not running.
      running (1) : the trace is running.
      save    (2) : the trace is running and saved to a file.
      hold    (4) : the trace data will be kept in case of an error.
      Several bits may be set simultaneous."
  ::= { bcamTrace 17 }
-- SNMPNAME: TMAS
-- ASSNAME: YTETFLAG
-- implemented

bcamTraceMappingNumberBuffer OBJECT-TYPE
  SYNTAX INTEGER (1..16) -- ASSLEN: 2
  ACCESS read-only
  STATUS mandatory
  DESCRIPTION
    " The number of buffers used for the trace"
  ::= { bcamTrace 18 }
-- SNMPNAME: TMAB
-- ASSNAME: YTEACBFN
-- implemented

bcamTraceMappingBufferLen OBJECT-TYPE
  SYNTAX INTEGER (512..16384) -- ASSLEN: 2
  ACCESS read-only
  STATUS mandatory
  DESCRIPTION
    " The length of one trace buffer in bytes (rounded up to multiples of 256). "
  ::= { bcamTrace 19 }
-- SNMPNAME: TMAL
-- ASSNAME: YTEACBFL
-- implemented

bcamTraceMgmtState OBJECT-TYPE
  SYNTAX INTEGER {
-- ASSMULTI:
--                 stopped(0),  ASSVAL: 0 0
		 running(1), -- ASSVAL: YTETALLO 1
		 save(2),    -- ASSVAL: YTESAVRQ 2
		 hold(4),    -- ASSVAL: YTEHLDRQ 4
		 stopped(8)  -- ASSVAL: 0 0
		 }
  ACCESS read-only
  STATUS mandatory
  DESCRIPTION
    " The current state of the trace.
      stopped (8) : the trace is not running.
      running (1) : the trace is running.
      save    (2) : the trace is running and saved to a file.
      hold    (4) : the trace data will be kept in case of an error.
      Several bits may be set simultaneous."
  ::= { bcamTrace 20 }
-- SNMPNAME: TMGS
-- ASSNAME: YTETFLAG
-- implemented

bcamTraceMgmtNumberBuffer OBJECT-TYPE
  SYNTAX INTEGER (1..16) -- ASSLEN: 2
  ACCESS read-only
  STATUS mandatory
  DESCRIPTION
    " The number of buffers used for the trace"
  ::= { bcamTrace 21 }
-- SNMPNAME: TMGB
-- ASSNAME: YTEACBFN
-- implemented

bcamTraceMgmtBufferLen OBJECT-TYPE
  SYNTAX INTEGER (512..16384) -- ASSLEN: 2
  ACCESS read-only
  STATUS mandatory
  DESCRIPTION
    " The length of one trace buffer in bytes (rounded up to multiples of 256). "
  ::= { bcamTrace 22 }
-- SNMPNAME: TMGL
-- ASSNAME: YTEACBFL
-- implemented

bcamTraceNetState OBJECT-TYPE
  SYNTAX INTEGER {
-- ASSMULTI:
--                 stopped(0),  ASSVAL: 0 0
		 running(1), -- ASSVAL: YTETALLO 1
		 save(2),    -- ASSVAL: YTESAVRQ 2
		 hold(4),    -- ASSVAL: YTEHLDRQ 4
		 stopped(8)  -- ASSVAL: 0 0
		 }
  ACCESS read-only
  STATUS mandatory
  DESCRIPTION
    " The current state of the trace.
      stopped (8) : the trace is not running.
      running (1) : the trace is running.
      save    (2) : the trace is running and saved to a file.
      hold    (4) : the trace data will be kept in case of an error.
      Several bits may be set simultaneous."
  ::= { bcamTrace 23 }
-- SNMPNAME: TNES
-- ASSNAME: YTETFLAG
-- implemented

bcamTraceNetNumberBuffer OBJECT-TYPE
  SYNTAX INTEGER (1..16) -- ASSLEN: 2
  ACCESS read-only
  STATUS mandatory
  DESCRIPTION
    " The number of buffers used for the trace"
  ::= { bcamTrace 24 }
-- SNMPNAME: TNEB
-- ASSNAME: YTEACBFN
-- implemented

bcamTraceNetBufferLen OBJECT-TYPE
  SYNTAX INTEGER (512..16384) -- ASSLEN: 2
  ACCESS read-only
  STATUS mandatory
  DESCRIPTION
    " The length of one trace buffer in bytes (rounded up to multiples of 256). "
  ::= { bcamTrace 25 }
-- SNMPNAME: TNEL
-- ASSNAME: YTEACBFL
-- implemented

bcamTraceSnmpState OBJECT-TYPE
  SYNTAX INTEGER {
-- ASSMULTI:
--                 stopped(0),  ASSVAL: 0 0
		 running(1), -- ASSVAL: YTETALLO 1
		 save(2),    -- ASSVAL: YTESAVRQ 2
		 hold(4),    -- ASSVAL: YTEHLDRQ 4
		 stopped(8)  -- ASSVAL: 0 0
		 }
  ACCESS read-only
  STATUS mandatory
  DESCRIPTION
    " The current state of the trace.
      stopped (8) : the trace is not running.
      running (1) : the trace is running.
      save    (2) : the trace is running and saved to a file.
      hold    (4) : the trace data will be kept in case of an error.
      Several bits may be set simultaneous."
  ::= { bcamTrace 26 }
-- SNMPNAME: TSNS
-- ASSNAME: YTETFLAG
-- implemented

bcamTraceSnmpNumberBuffer OBJECT-TYPE
  SYNTAX INTEGER (1..16) -- ASSLEN: 2
  ACCESS read-only
  STATUS mandatory
  DESCRIPTION
    " The number of buffers used for the trace"
  ::= { bcamTrace 27 }
-- SNMPNAME: TSNB
-- ASSNAME: YTEACBFN
-- implemented

bcamTraceSnmpBufferLen OBJECT-TYPE
  SYNTAX INTEGER (512..16384) -- ASSLEN: 2
  ACCESS read-only
  STATUS mandatory
  DESCRIPTION
    " The length of one trace buffer in bytes (rounded up to multiples of 256). "
  ::= { bcamTrace 28 }
-- SNMPNAME: TSNL
-- ASSNAME: YTEACBFL
-- implemented

bcamTraceTransState OBJECT-TYPE
  SYNTAX INTEGER {
-- ASSMULTI:
--                 stopped(0),  ASSVAL: 0 0
		 running(1), -- ASSVAL: YTETALLO 1
		 save(2),    -- ASSVAL: YTESAVRQ 2
		 hold(4),    -- ASSVAL: YTEHLDRQ 4
		 stopped(8)  -- ASSVAL: 0 0
		 }
  ACCESS read-only
  STATUS mandatory
  DESCRIPTION
    " The current state of the trace.
      stopped (8) : the trace is not running.
      running (1) : the trace is running.
      save    (2) : the trace is running and saved to a file.
      hold    (4) : the trace data will be kept in case of an error.
      Several bits may be set simultaneous."
  ::= { bcamTrace 29 }
-- SNMPNAME: TTRS
-- ASSNAME: YTETFLAG
-- implemented

bcamTraceTransNumberBuffer OBJECT-TYPE
  SYNTAX INTEGER (1..16) -- ASSLEN: 2
  ACCESS read-only
  STATUS mandatory
  DESCRIPTION
    " The number of buffers used for the trace"
  ::= { bcamTrace 30 }
-- SNMPNAME: TTRB
-- ASSNAME: YTEACBFN
-- implemented

bcamTraceTransBufferLen OBJECT-TYPE
  SYNTAX INTEGER (512..16384) -- ASSLEN: 2
  ACCESS read-only
  STATUS mandatory
  DESCRIPTION
    " The length of one trace buffer in bytes (rounded up to multiples of 256). "
  ::= { bcamTrace 31 }
-- SNMPNAME: TTRL
-- ASSNAME: YTEACBFL
-- implemented

bcamTraceInfoState OBJECT-TYPE
  SYNTAX INTEGER {
-- ASSMULTI:
--                 stopped(0),  ASSVAL: 0 0
		 running(1), -- ASSVAL: YTETALLO 1
		 save(2),    -- ASSVAL: YTESAVRQ 2
		 hold(4),    -- ASSVAL: YTEHLDRQ 4
		 stopped(8)  -- ASSVAL: 0 0
		 }
  ACCESS read-only
  STATUS mandatory
  DESCRIPTION
    " The current state of the trace.
      stopped (8) : the trace is not running.
      running (1) : the trace is running.
      save    (2) : the trace is running and saved to a file.
      hold    (4) : the trace data will be kept in case of an error.
      Several bits may be set simultaneous."
  ::= { bcamTrace 32 }
-- SNMPNAME: TINS
-- ASSNAME: YTETFLAG
-- implemented

bcamTraceInfoNumberBuffer OBJECT-TYPE
  SYNTAX INTEGER (1..16) -- ASSLEN: 2
  ACCESS read-only
  STATUS mandatory
  DESCRIPTION
    " The number of buffers used for the trace"
  ::= { bcamTrace 33 }
-- SNMPNAME: TINB
-- ASSNAME: YTEACBFN
-- implemented

bcamTraceInfoBufferLen OBJECT-TYPE
  SYNTAX INTEGER (512..16384) -- ASSLEN: 2
  ACCESS read-only
  STATUS mandatory
  DESCRIPTION
    " The length of one trace buffer in bytes (rounded up to multiples of 256). "
  ::= { bcamTrace 34 }
-- SNMPNAME: TINL
-- ASSNAME: YTEACBFL
-- implemented







-- the Tsap group


bcamTsapCurrOpen OBJECT-TYPE
  SYNTAX INTEGER
  ACCESS read-only
  STATUS mandatory
  DESCRIPTION
    "The number of currently active TSAPs (including BCAM internal applications). "
  ::= { bcamTsap 1 }
-- SNMPNAME: ACUO
-- ASSNAME: YBCNOAPP
-- implemented

bcamTsapTotOpen OBJECT-TYPE
  SYNTAX INTEGER
  ACCESS read-only
  STATUS mandatory
  DESCRIPTION
    "The number of TSAPs opened since start of BCAM (excluding the active TSAPs). "
  ::= { bcamTsap 2 }
-- SNMPNAME: ATOO
-- ASSNAME: YBC#APPC
-- implemented

bcamTsapSendCall OBJECT-TYPE
  SYNTAX INTEGER
  ACCESS read-only
  STATUS mandatory
  DESCRIPTION
    "Number of successful send calls of all TSAPs since start of BCAM"
  ::= { bcamTsap 3 }
-- SNMPNAME: ASNC
-- ASSNAME: YBCSUOUT YBCSULOC
-- implemented

bcamTsapSendByteHigh OBJECT-TYPE
  SYNTAX INTEGER -- ASSLEN: 4
  ACCESS read-only
  STATUS mandatory
  DESCRIPTION
    "Number of bytes given to BCAM-interface to send from all TSAPs
     since start of BCAM (high word, multiply by 4294967296)."
  ::= { bcamTsap 4 }
-- SNMPNAME: ASBH
-- ASSNAME: YBCSBYTE YBCSBYTL
-- implemented

bcamTsapSendByteLow OBJECT-TYPE
  SYNTAX INTEGER -- ASSLEN: 4
  ACCESS read-only
  STATUS mandatory
  DESCRIPTION
    "Number of bytes given to BCAM-interface to send from all TSAPs
     since start of BCAM (low word, add to high word). "
  ::= { bcamTsap 5 }
-- SNMPNAME: ASBL
-- ASSNAME: YBCSBYTE+4 YBCSBYTL+4
-- implemented

bcamTsapRecvCall OBJECT-TYPE
  SYNTAX INTEGER
  ACCESS read-only
  STATUS mandatory
  DESCRIPTION
    "Number of successful receive calls of all TSAPs since start of BCAM"
  ::= { bcamTsap 6 }
-- SNMPNAME: ARVC
-- ASSNAME: YBCSUIN
-- implemented

bcamTsapRecvByteHigh OBJECT-TYPE
  SYNTAX INTEGER -- ASSLEN: 4
  ACCESS read-only
  STATUS mandatory
  DESCRIPTION
    "Number of bytes given from BCAM to all TSAPs since start of BCAM (high word, multiply by 4294967296)."
  ::= { bcamTsap 7 }
-- SNMPNAME: ARBH
-- ASSNAME: YBCRBYTE YBCRBYTL
-- implemented

bcamTsapRecvByteLow OBJECT-TYPE
  SYNTAX INTEGER -- ASSLEN: 4
  ACCESS read-only
  STATUS mandatory
  DESCRIPTION
    "Number of bytes given from BCAM to all TSAPs since start of BCAM (low word, add to high word)."
  ::= { bcamTsap 8 }
-- SNMPNAME: ARBL
-- ASSNAME: YBCRBYTE+4 YBCRBYTL+4
-- implemented

bcamTsapSendCallCless OBJECT-TYPE
  SYNTAX INTEGER
  ACCESS read-only
  STATUS mandatory
  DESCRIPTION
    " The number of successful send calls for connectionless data of all TSAPs since start of BCAM"
  ::= { bcamTsap 9 }
-- SNMPNAME: ASCC
-- ASSNAME: YBCUDPSD
-- implemented

bcamTsapSendByteClessHigh OBJECT-TYPE
  SYNTAX INTEGER -- ASSLEN: 4
  ACCESS read-only
  STATUS mandatory
  DESCRIPTION
    " The number of bytes given to BCAM-interface to send connectionless from all TSAPs
     since start of BCAM (high word, multiply by 4294967296). "
  ::= { bcamTsap 10 }
-- SNMPNAME: ASCH
-- ASSNAME: YBCUDSBY
-- implemented

bcamTsapSendByteClessLow OBJECT-TYPE
  SYNTAX INTEGER -- ASSLEN: 4
  ACCESS read-only
  STATUS mandatory
  DESCRIPTION
    " The number of bytes given to BCAM-interface to send connectionless from all TSAPs
     since start of BCAM (low word, add to high word). "
  ::= { bcamTsap 11 }
-- SNMPNAME: ASCL
-- ASSNAME: YBCUDSBY+4
-- implemented

bcamTsapRecvCallCless OBJECT-TYPE
  SYNTAX INTEGER
  ACCESS read-only
  STATUS mandatory
  DESCRIPTION
    " The number of successful send calls for connectionless data of all TSAPs since start of BCAM"
  ::= { bcamTsap 12 }
-- SNMPNAME: ARCC
-- ASSNAME: YBCUDPRC
-- implemented

bcamTsapRecvByteClessHigh OBJECT-TYPE
  SYNTAX INTEGER -- ASSLEN: 4
  ACCESS read-only
  STATUS mandatory
  DESCRIPTION
    " The number of bytes received connectionless given from BCAM to all TSAPs
     since start of BCAM (high word, multiply by 4294967296). "
  ::= { bcamTsap 13 }
-- SNMPNAME: ARCH
-- ASSNAME: YBCUDRBY
-- implemented

bcamTsapRecvByteClessLow OBJECT-TYPE
  SYNTAX INTEGER -- ASSLEN: 4
  ACCESS read-only
  STATUS mandatory
  DESCRIPTION
    " The number of bytes received connectionless given from BCAM to all TSAPs
     since start of BCAM (low word, add to high word). "
  ::= { bcamTsap 14 }
-- SNMPNAME: ARCL
-- ASSNAME: YBCUDRBY+4
-- implemented

bcamTsapNumTable OBJECT-TYPE
  SYNTAX INTEGER -- ASSLEN: 4
  ACCESS read-only
  STATUS mandatory
  DESCRIPTION
    " The number of table entries. "
  ::= { bcamTsap 15 }
-- SNMPNAME: ANTE
-- ASSNAME: YBCAXOCC
-- implemented

bcamTsapMaxTsap OBJECT-TYPE
  SYNTAX INTEGER -- ASSLEN: 4
  ACCESS read-only
  STATUS mandatory
  DESCRIPTION
    " The maximum number of not predefined applications that may be opened
      simultaneously.  "
  ::= { bcamTsap 16 }
-- SNMPNAME: AMTS
-- ASSNAME: YYSPMNPA
-- The number of rejected tsap openings because of reached maximum (see ...)

bcamTsapMaxTsapTask OBJECT-TYPE
  SYNTAX INTEGER -- ASSLEN: 4
  ACCESS read-only
  STATUS mandatory
  DESCRIPTION
    " The maximum number of not predefined applications that may be opened
      simultaneously by one task.  "
  ::= { bcamTsap 17 }
-- SNMPNAME: AMTT
-- ASSNAME: YYSPMNPT
-- The number of rejected tsap openings because of reached maximum for one task (see ...)


bcamTsapMaxCepTsap OBJECT-TYPE
  SYNTAX INTEGER -- ASSLEN: 4
  ACCESS read-only
  STATUS mandatory
  DESCRIPTION
    " The maximum number of connections a non system application may have opened concurrently. "
  ::= { bcamTsap 18 }
-- SNMPNAME: AMCT
-- ASSNAME: YYSPMCNN
-- The number of connection requests rejected because the maximum number of connections for a tsap
-- has been reached

bcamTsapRejTsap OBJECT-TYPE
  SYNTAX INTEGER -- ASSLEN: 4
  ACCESS read-only
  STATUS mandatory
  DESCRIPTION
    " The number of rejected tsap openings because of reached maximum (see bcamTsapMaxTsap).
  "
  ::= { bcamTsap 19 }
-- SNMPNAME: ARTS
-- ASSNAME: YBC#AMAP

bcamTsapRejTsapTask OBJECT-TYPE
  SYNTAX INTEGER -- ASSLEN: 4
  ACCESS read-only
  STATUS mandatory
  DESCRIPTION
    " The number of rejected tsap openings because of reached maximum for one task (see bcamTsapMaxTsapTask). "
  ::= { bcamTsap 20 }
-- SNMPNAME: ARTT
-- ASSNAME: YBC#AMTA

bcamTsapRejCepTsap OBJECT-TYPE
  SYNTAX INTEGER -- ASSLEN: 4
  ACCESS read-only
  STATUS mandatory
  DESCRIPTION
    " The number of connection requests rejected because the maximum number of connections for this tsap
      has been reached (see bcamTsapMaxCepTsap). "
  ::= { bcamTsap 21 }
-- SNMPNAME: ARCT
-- ASSNAME: YBC#AMCO

bcamTsapTab OBJECT-TYPE
  SYNTAX SEQUENCE OF TsapEntry
  ACCESS not-accessible
  STATUS mandatory
  DESCRIPTION
    " Table of all active TSAPs "
  ::= { bcamTsap 22 }
-- SNMPNAME:
-- ASSNAME:

bcamTsapTabEntry OBJECT-TYPE
  SYNTAX TsapEntry
  ACCESS not-accessible
  STATUS mandatory
  DESCRIPTION
    " Information about a current active TSAP "
  INDEX {
    bcamTsapTabNumbers
    }
  ::= { bcamTsapTab 1 }
-- SNMPNAME:
-- ASSNAME:




TsapEntry ::=
  SEQUENCE {
    bcamTsapTabNumbers Counter ,
    bcamTsapTabState INTEGER ,
    bcamTsapTabDuration Gauge ,
    bcamTsapTabDateApplEnable DisplayString (SIZE(8)),
    bcamTsapTabTimeApplEnable DisplayString (SIZE(6)),
    bcamTsapTabTypName INTEGER ,
    bcamTsapTabName DisplayString (SIZE(0..78)),
    bcamTsapTabPortnumber INTEGER (0..65535),
    bcamTsapTabOsiTsel OCTET STRING (SIZE(0..32)),
    bcamTsapTabNeaTsel OCTET STRING (SIZE(8)),
    bcamTsapTabHost DisplayString (SIZE(8)),
    bcamTsapTabDiagnostic OCTET STRING (SIZE(4)),
    bcamTsapTabTsduSends Counter ,
    bcamTsapTabByteSends Counter ,
    bcamTsapTabTsduReceiveds Counter ,
    bcamTsapTabByteReceiveds Counter ,
    bcamTsapTabSendCallOverMaxs Counter ,
    bcamTsapTabLetterTimeouts Counter ,
    bcamTsapTabInWaitBuck1Hist INTEGER (0..65535),
    bcamTsapTabInWaitBuck2Hist INTEGER (0..65535),
    bcamTsapTabInWaitBuck3Hist INTEGER (0..65535),
    bcamTsapTabInWaitBuck4Hist INTEGER (0..65535),
    bcamTsapTabInWaitBuck5Hist INTEGER (0..65535),
    bcamTsapTabReactBuck1Hist INTEGER (0..65535),
    bcamTsapTabReactBuck2Hist INTEGER (0..65535),
    bcamTsapTabReactBuck3Hist INTEGER (0..65535),
    bcamTsapTabReactBuck4Hist INTEGER (0..65535),
    bcamTsapTabReactBuck5Hist INTEGER (0..65535),
    bcamTsapTabInWaitBuck1 INTEGER (0..65535),
    bcamTsapTabInWaitBuck2 INTEGER (0..65535),
    bcamTsapTabInWaitBuck3 INTEGER (0..65535),
    bcamTsapTabInWaitBuck4 INTEGER (0..65535),
    bcamTsapTabInWaitBuck5 INTEGER (0..65535),
    bcamTsapTabReactBuck1 INTEGER (0..65535),
    bcamTsapTabReactBuck2 INTEGER (0..65535),
    bcamTsapTabReactBuck3 INTEGER (0..65535),
    bcamTsapTabReactBuck4 INTEGER (0..65535),
    bcamTsapTabReactBuck5 INTEGER (0..65535),
    bcamTsapTabTsduSendHists Counter ,
    bcamTsapTabByteSendHists Counter ,
    bcamTsapTabTsduReceivedHists Counter ,
    bcamTsapTabByteReceivedHists Counter ,
    bcamTsapTabSendCallOverMaxHists Counter ,
    bcamTsapTabLetterTimeoutHists Counter ,
    bcamTsapTabFunction INTEGER ,
    bcamTsapTabCurrConn Gauge ,
    bcamTsapTabCloseConns Counter ,
    bcamTsapTabClessSendBytes Counter ,
    bcamTsapTabClessRecvBytes Counter ,
    bcamTsapTabClessSendCalls Counter ,
    bcamTsapTabClessRecvCalls Counter ,
    bcamTsapTabOutbufTsdu Gauge ,
    bcamTsapTabOutbufByte Gauge ,
    bcamTsapTabInbufTsdu Gauge ,
    bcamTsapTabInbufByte Gauge ,
    bcamTsapTabOutbufTsduCless Gauge ,
    bcamTsapTabOutbufByteCless Gauge ,
    bcamTsapTabInbufTsduCless Gauge ,
    bcamTsapTabInbufByteCless Gauge ,
    bcamTsapTabClessTimeout INTEGER
    }

bcamTsapTabNumbers OBJECT-TYPE
  SYNTAX Counter
  ACCESS read-only
  STATUS mandatory
  DESCRIPTION
    " The definite identifier for this application. Even if the same application is disabled and then
      reenabled, the identfier will get a new value. "
  ::= { bcamTsapTabEntry 1 }
-- SNMPNAME: AANR
-- ASSNAME: YAP2@KEY
-- implemented

bcamTsapTabState OBJECT-TYPE
  SYNTAX INTEGER {
-- ASSSINGLE:
		 opening(1), -- ASSVAL: YAP2OPNG 2
		 open(2),    -- ASSVAL: YAP2OPEN 3
		 closing(3), -- ASSVAL: YAP2CLNG 4
		 closed(4),  -- ASSVAL: YAP2CLOS 1
		 stopped(8)  -- ASSVAL: 0 0
		 }
  ACCESS read-only
  STATUS mandatory
  DESCRIPTION
    " The current state of this application.
      opening (1) : the application enableing is in progress.
      open    (2): the application is ready for requesting or accepting connections.
      closing (3): the termination of the application is in progress.
      closed  (4): the application has been closed.
      Several bits may be set simultaneous."
  ::= { bcamTsapTabEntry 2 }
-- SNMPNAME: ASTA
-- ASSNAME: YAP2STAT
-- implemented

bcamTsapTabDuration OBJECT-TYPE
  SYNTAX Gauge
  ACCESS read-only
  STATUS mandatory
  DESCRIPTION
    " The time in seconds the application was enabled. "
  ::= { bcamTsapTabEntry 3 }
-- SNMPNAME: ADUR
-- ASSNAME: YAP2ODUR
-- implemented

bcamTsapTabDateApplEnable OBJECT-TYPE
  SYNTAX DisplayString (SIZE(8)) -- ASSLEN: 9 VAR
  ACCESS read-only
  STATUS mandatory
  DESCRIPTION
    " The date of the application enableing.
      Format: YYYYMMDD "
  ::= { bcamTsapTabEntry 4 }
-- SNMPNAME: ADAE
-- ASSNAME: YAP2DATE
-- implemented

bcamTsapTabTimeApplEnable OBJECT-TYPE
  SYNTAX DisplayString (SIZE(6)) -- ASSLEN: 7 VAR
  ACCESS read-only
  STATUS mandatory
  DESCRIPTION
    " The time of the application enableing.
      Format: HHMMSS "
  ::= { bcamTsapTabEntry 5 }
-- SNMPNAME: ATAE
-- ASSNAME: YAP2TIME
-- implemented

bcamTsapTabTypName OBJECT-TYPE
  SYNTAX INTEGER {
-- ASSSINGLE:
		 neaName(1),    -- ASSVAL: YAP2NAPP 2
		 socketName(2), -- ASSVAL: YAP2NPT# 6
		 isoName(3)     -- ASSVAL: YAP2NISO 7
		 }
  ACCESS read-only
  STATUS mandatory
  DESCRIPTION
    " The type of name of this application.
      NeaName    (1) : the name consists of 8 byte application name and 8 byte name of endsystem.
      SocketName (2) : the name consists of up to 32 byte socket name.
      IsoName    (3) : the name consists of up to 78 byte iso name. "
  ::= { bcamTsapTabEntry 6 }
-- SNMPNAME: ATNM
-- ASSNAME: YAP2NTYP
-- implemented

bcamTsapTabName OBJECT-TYPE
  SYNTAX DisplayString (SIZE(0..78)) -- ASSLEN: 79 VAR
  ACCESS read-only
  STATUS mandatory
  DESCRIPTION
    " The name of this application according the type of the name (bcamTsapTabTypName). "
  ::= { bcamTsapTabEntry 7 }
-- SNMPNAME: ANAM
-- ASSNAME: YAP2NNAI
-- implemented

bcamTsapTabPortnumber OBJECT-TYPE
  SYNTAX INTEGER (0..65535) -- ASSLEN: 2
  ACCESS read-only
  STATUS mandatory
  DESCRIPTION
    " The port number used by this application (if known). "
  ::= { bcamTsapTabEntry 8 }
-- SNMPNAME: APOR
-- ASSNAME: YAP2OPO#
-- implemented

bcamTsapTabOsiTsel OBJECT-TYPE
  SYNTAX OCTET STRING (SIZE(0..32)) -- ASSLEN: 34 VAR
  ACCESS read-only
  STATUS mandatory
  DESCRIPTION
    " The OSI transport selector of this application (if known). "
  ::= { bcamTsapTabEntry 9 }
-- SNMPNAME: AOTS
-- ASSNAME: YAP2OTO
-- implemented

bcamTsapTabNeaTsel OBJECT-TYPE
  SYNTAX OCTET STRING (SIZE(8)) -- ASSLEN: 9 VAR
  ACCESS read-only
  STATUS mandatory
  DESCRIPTION
    " The NEA transport selector of this application (if known). "
  ::= { bcamTsapTabEntry 10 }
-- SNMPNAME: ANTS
-- ASSNAME: YAP2OTN
-- implemented

bcamTsapTabHost OBJECT-TYPE
  SYNTAX DisplayString (SIZE(8)) -- ASSLEN: 9 VAR
  ACCESS read-only
  STATUS mandatory
  DESCRIPTION
    " The name of the host in which the application resides. "
  ::= { bcamTsapTabEntry 11 }
-- SNMPNAME: AHOS
-- ASSNAME: YAP2OHOS
-- implemented

bcamTsapTabDiagnostic OBJECT-TYPE
  SYNTAX OCTET STRING (SIZE(4)) -- ASSLEN: 5 VAR
  ACCESS read-only
  STATUS mandatory
  DESCRIPTION
    " The reason why the application was disabled (for diagnostic purposes only). "
  ::= { bcamTsapTabEntry 12 }
-- SNMPNAME: ADIA
-- ASSNAME: YAP2DIAG
-- implemented

bcamTsapTabTsduSends OBJECT-TYPE
  SYNTAX Counter
  ACCESS read-only
  STATUS mandatory
  DESCRIPTION
    " The number of packets to send given to BCAM at the TSAP by this application. "
  ::= { bcamTsapTabEntry 13 }
-- SNMPNAME: ATSE
-- ASSNAME: YC1STDE
-- implemented

bcamTsapTabByteSends OBJECT-TYPE
  SYNTAX Counter
  ACCESS read-only
  STATUS mandatory
  DESCRIPTION
    " The number of bytes to send given to BCAM at the TSAP by this application. "
  ::= { bcamTsapTabEntry 14 }
-- SNMPNAME: ABSE
-- ASSNAME: YC1SBYTE
-- implemented

bcamTsapTabTsduReceiveds OBJECT-TYPE
  SYNTAX Counter
  ACCESS read-only
  STATUS mandatory
  DESCRIPTION
    " The number of packets received at the TSAP by this application. "
  ::= { bcamTsapTabEntry 15 }
-- SNMPNAME: ATRE
-- ASSNAME: YC1RTDE
-- implemented

bcamTsapTabByteReceiveds OBJECT-TYPE
  SYNTAX Counter
  ACCESS read-only
  STATUS mandatory
  DESCRIPTION
    " The number of bytes received at the TSAP by this application. "
  ::= { bcamTsapTabEntry 16 }
-- SNMPNAME: ABRE
-- ASSNAME: YC1RBYTE
-- implemented

bcamTsapTabSendCallOverMaxs OBJECT-TYPE
  SYNTAX Counter
  ACCESS read-only
  STATUS mandatory
  DESCRIPTION
    " The number of send calls of this application while BCAM limits have been reached. "
  ::= { bcamTsapTabEntry 17 }
-- SNMPNAME: ASCM
-- ASSNAME: YC1SOVMA
-- implemented

bcamTsapTabLetterTimeouts OBJECT-TYPE
  SYNTAX Counter
  ACCESS read-only
  STATUS mandatory
  DESCRIPTION
    " The number of packets that were deleted without being delivered to the application due
      to timeout of the letter timer. "
  ::= { bcamTsapTabEntry 18 }
-- SNMPNAME: ALTI
-- ASSNAME: YC1LTIMO
-- implemented

bcamTsapTabInWaitBuck1Hist OBJECT-TYPE
  SYNTAX INTEGER (0..65535) -- ASSLEN: 2
  ACCESS read-only
  STATUS mandatory
  DESCRIPTION
    " The number of times the input wait time was in the time interval between
      zero and bcamGlobalInWaitLimit1 for meanwhile closed applications. "
  ::= { bcamTsapTabEntry 19 }
-- SNMPNAME: AWH1
-- ASSNAME: YAP2WTB1
-- implemented

bcamTsapTabInWaitBuck2Hist OBJECT-TYPE
  SYNTAX INTEGER (0..65535) -- ASSLEN: 2
  ACCESS read-only
  STATUS mandatory
  DESCRIPTION
    " The number of times the input wait time was in the time interval between
      bcamGlobalInWaitLimit1 and bcamGlobalInWaitLimit2 for meanwhile closed applications. "
  ::= { bcamTsapTabEntry 20 }
-- SNMPNAME: AWH2
-- ASSNAME: YAP2WTB2
-- implemented

bcamTsapTabInWaitBuck3Hist OBJECT-TYPE
  SYNTAX INTEGER (0..65535) -- ASSLEN: 2
  ACCESS read-only
  STATUS mandatory
  DESCRIPTION
    " The number of times the input wait time was in the time interval between
      bcamGlobalInWaitLimit2 and bcamGlobalInWaitLimit3 for meanwhile closed applications. "
  ::= { bcamTsapTabEntry 21 }
-- SNMPNAME: AWH3
-- ASSNAME: YAP2WTB3
-- implemented

bcamTsapTabInWaitBuck4Hist OBJECT-TYPE
  SYNTAX INTEGER (0..65535) -- ASSLEN: 2
  ACCESS read-only
  STATUS mandatory
  DESCRIPTION
    " The number of times the input wait time was in the time interval between
      bcamGlobalInWaitLimit3 and bcamGlobalInWaitLimit4 for meanwhile closed applications. "
  ::= { bcamTsapTabEntry 22 }
-- SNMPNAME: AWH4
-- ASSNAME: YAP2WTB4
-- implemented

bcamTsapTabInWaitBuck5Hist OBJECT-TYPE
  SYNTAX INTEGER (0..65535) -- ASSLEN: 2
  ACCESS read-only
  STATUS mandatory
  DESCRIPTION
    " The number of times the input wait time was longer than
      bcamGlobalInWaitLimit4 for meanwhile closed applications. "
  ::= { bcamTsapTabEntry 23 }
-- SNMPNAME: AWH5
-- ASSNAME: YAP2WTB5
-- implemented

bcamTsapTabReactBuck1Hist OBJECT-TYPE
  SYNTAX INTEGER (0..65535) -- ASSLEN: 2
  ACCESS read-only
  STATUS mandatory
  DESCRIPTION
    " The number of times the application reaction time was in the time interval between
      zero and bcamGlobalReactLimit1 for meanwhile closed applications. "
  ::= { bcamTsapTabEntry 24 }
-- SNMPNAME: ARH1
-- ASSNAME: YAP2RSB1
-- implemented

bcamTsapTabReactBuck2Hist OBJECT-TYPE
  SYNTAX INTEGER (0..65535) -- ASSLEN: 2
  ACCESS read-only
  STATUS mandatory
  DESCRIPTION
    " The number of times the application reaction time was in the time interval between
      bcamGlobalReactLimit1 and bcamGlobalReactLimit2 for meanwhile closed applications. "
  ::= { bcamTsapTabEntry 25 }
-- SNMPNAME: ARH2
-- ASSNAME: YAP2RSB2
-- implemented

bcamTsapTabReactBuck3Hist OBJECT-TYPE
  SYNTAX INTEGER (0..65535) -- ASSLEN: 2
  ACCESS read-only
  STATUS mandatory
  DESCRIPTION
    " The number of times the application reaction time was in the time interval between
      bcamGlobalReactLimit2 and bcamGlobalReactLimit3 for meanwhile closed applications. "
  ::= { bcamTsapTabEntry 26 }
-- SNMPNAME: ARH3
-- ASSNAME: YAP2RSB3
-- implemented

bcamTsapTabReactBuck4Hist OBJECT-TYPE
  SYNTAX INTEGER (0..65535) -- ASSLEN: 2
  ACCESS read-only
  STATUS mandatory
  DESCRIPTION
    " The number of times the application reaction time was in the time interval between
      bcamGlobalReactLimit3 and bcamGlobalReactLimit4 for meanwhile closed applications. "
  ::= { bcamTsapTabEntry 27 }
-- SNMPNAME: ARH4
-- ASSNAME: YAP2RSB4
-- implemented

bcamTsapTabReactBuck5Hist OBJECT-TYPE
  SYNTAX INTEGER (0..65535) -- ASSLEN: 2
  ACCESS read-only
  STATUS mandatory
  DESCRIPTION
    " The number of times the application reaction time was longer than
      bcamGlobalReactLimit4 for meanwhile closed applications. "
  ::= { bcamTsapTabEntry 28 }
-- SNMPNAME: ARH5
-- ASSNAME: YAP2RSB5
-- implemented

bcamTsapTabInWaitBuck1 OBJECT-TYPE
  SYNTAX INTEGER (0..65535) -- ASSLEN: 2
  ACCESS read-only
  STATUS mandatory
  DESCRIPTION
    " The number of times the input wait time was in the time interval between
      zero and bcamGlobalInWaitLimit1 for opened applications. "
  ::= { bcamTsapTabEntry 29 }
-- SNMPNAME: AWC1
-- ASSNAME: YC1WTB1
-- implemented

bcamTsapTabInWaitBuck2 OBJECT-TYPE
  SYNTAX INTEGER (0..65535) -- ASSLEN: 2
  ACCESS read-only
  STATUS mandatory
  DESCRIPTION
    " The number of times the input wait time was in the time interval between
      bcamGlobalInWaitLimit1 and bcamGlobalInWaitLimit2 for opened applications. "
  ::= { bcamTsapTabEntry 30 }
-- SNMPNAME: AWC2
-- ASSNAME: YC1WTB2
-- implemented

bcamTsapTabInWaitBuck3 OBJECT-TYPE
  SYNTAX INTEGER (0..65535) -- ASSLEN: 2
  ACCESS read-only
  STATUS mandatory
  DESCRIPTION
    " The number of times the input wait time was in the time interval between
      bcamGlobalInWaitLimit2 and bcamGlobalInWaitLimit3 for opened applications. "
  ::= { bcamTsapTabEntry 31 }
-- SNMPNAME: AWC3
-- ASSNAME: YC1WTB3
-- implemented

bcamTsapTabInWaitBuck4 OBJECT-TYPE
  SYNTAX INTEGER (0..65535) -- ASSLEN: 2
  ACCESS read-only
  STATUS mandatory
  DESCRIPTION
    " The number of times the input wait time was in the time interval between
      bcamGlobalInWaitLimit3 and bcamGlobalInWaitLimit4 for opened applications. "
  ::= { bcamTsapTabEntry 32 }
-- SNMPNAME: AWC4
-- ASSNAME: YC1WTB4
-- implemented

bcamTsapTabInWaitBuck5 OBJECT-TYPE
  SYNTAX INTEGER (0..65535) -- ASSLEN: 2
  ACCESS read-only
  STATUS mandatory
  DESCRIPTION
    " The number of times the input wait time was longer than
      bcamGlobalInWaitLimit4 for opened applications. "
  ::= { bcamTsapTabEntry 33 }
-- SNMPNAME: AWC5
-- ASSNAME: YC1WTB5
-- implemented

bcamTsapTabReactBuck1 OBJECT-TYPE
  SYNTAX INTEGER (0..65535) -- ASSLEN: 2
  ACCESS read-only
  STATUS mandatory
  DESCRIPTION
    " The number of times the application reaction time was in the time interval between
      zero and bcamGlobalReactLimit1 for opened applications. "
  ::= { bcamTsapTabEntry 34 }
-- SNMPNAME: ARC1
-- ASSNAME: YC1RSB1
-- implemented

bcamTsapTabReactBuck2 OBJECT-TYPE
  SYNTAX INTEGER (0..65535) -- ASSLEN: 2
  ACCESS read-only
  STATUS mandatory
  DESCRIPTION
    " The number of times the application reaction time was in the time interval between
      bcamGlobalReactLimit1 and bcamGlobalReactLimit2 for opened applications. "
  ::= { bcamTsapTabEntry 35 }
-- SNMPNAME: ARC2
-- ASSNAME: YC1RSB2
-- implemented

bcamTsapTabReactBuck3 OBJECT-TYPE
  SYNTAX INTEGER (0..65535) -- ASSLEN: 2
  ACCESS read-only
  STATUS mandatory
  DESCRIPTION
    " The number of times the application reaction time was in the time interval between
      bcamGlobalReactLimit2 and bcamGlobalReactLimit3 for opened applications. "
  ::= { bcamTsapTabEntry 36 }
-- SNMPNAME: ARC3
-- ASSNAME: YC1RSB3
-- implemented

bcamTsapTabReactBuck4 OBJECT-TYPE
  SYNTAX INTEGER (0..65535) -- ASSLEN: 2
  ACCESS read-only
  STATUS mandatory
  DESCRIPTION
    " The number of times the application reaction time was in the time interval between
      bcamGlobalReactLimit3 and bcamGlobalReactLimit4 for opened applications. "
  ::= { bcamTsapTabEntry 37 }
-- SNMPNAME: ARC4
-- ASSNAME: YC1RSB4
-- implemented

bcamTsapTabReactBuck5 OBJECT-TYPE
  SYNTAX INTEGER (0..65535) -- ASSLEN: 2
  ACCESS read-only
  STATUS mandatory
  DESCRIPTION
    " The number of times the application reaction time was longer than
      bcamGlobalReactLimit4 for opened applications. "
  ::= { bcamTsapTabEntry 38 }
-- SNMPNAME: ARC5
-- ASSNAME: YC1RSB5
-- implemented

bcamTsapTabTsduSendHists OBJECT-TYPE
  SYNTAX Counter
  ACCESS read-only
  STATUS mandatory
  DESCRIPTION
    " The number of packets to send given to BCAM at the TSAP by this application for meanwhile closed connections. "
  ::= { bcamTsapTabEntry 39 }
-- SNMPNAME: ATSH
-- ASSNAME: YAP2STDE
-- implemented

bcamTsapTabByteSendHists OBJECT-TYPE
  SYNTAX Counter
  ACCESS read-only
  STATUS mandatory
  DESCRIPTION
    " The number of bytes to send given to BCAM at the TSAP by this application for meanwhile closed connections. "
  ::= { bcamTsapTabEntry 40 }
-- SNMPNAME: ABSH
-- ASSNAME: YAP2SBYT
-- implemented

bcamTsapTabTsduReceivedHists OBJECT-TYPE
  SYNTAX Counter
  ACCESS read-only
  STATUS mandatory
  DESCRIPTION
    " The number of packets received at the TSAP by this application for meanwhile closed connections. "
  ::= { bcamTsapTabEntry 41 }
-- SNMPNAME: ATRH
-- ASSNAME: YAP2RTDE
-- implemented

bcamTsapTabByteReceivedHists OBJECT-TYPE
  SYNTAX Counter
  ACCESS read-only
  STATUS mandatory
  DESCRIPTION
    " The number of bytes received at the TSAP by this application for meanwhile closed connections. "
  ::= { bcamTsapTabEntry 42 }
-- SNMPNAME: ABRH
-- ASSNAME: YAP2RBYT
-- implemented

bcamTsapTabSendCallOverMaxHists OBJECT-TYPE
  SYNTAX Counter
  ACCESS read-only
  STATUS mandatory
  DESCRIPTION
    " The number of send calls of this application while BCAM limits have been reached for meanwhile closed connections. "
  ::= { bcamTsapTabEntry 43 }
-- SNMPNAME: ASMH
-- ASSNAME: YAP2SOVM
-- implemented

bcamTsapTabLetterTimeoutHists OBJECT-TYPE
  SYNTAX Counter
  ACCESS read-only
  STATUS mandatory
  DESCRIPTION
    " The number of packets that were deleted without being delivered to the application due
      to timeout of the letter timer for meanwhile closed connections. "
  ::= { bcamTsapTabEntry 44 }
-- SNMPNAME: ALTH
-- ASSNAME: YAP2LTIM
-- implemented

bcamTsapTabFunction OBJECT-TYPE
  SYNTAX INTEGER {
-- ASSSINGLE:
		 nea(1),    -- ASSVAL: YAPIFNEA 20
		 iso(2),    -- ASSVAL: YAPIFISO 40
		 streams(3) -- ASSVAL: YAPIFTCP 80
		 }
  ACCESS read-only
  STATUS mandatory
  DESCRIPTION
    "Interfacefunctionality of TSAP.
     nea     (1) : functionality according proprietary NEA .
     iso     (2) : functionality according ISO IS 8072.
     streams (3) : functionality according the one defined in the INTERNET. "
  ::= { bcamTsapTabEntry 45 }
-- SNMPNAME: AFCT
-- ASSNAME: YAPIFCT
-- implemented

bcamTsapTabCurrConn OBJECT-TYPE
    SYNTAX Gauge
    ACCESS read-only
    STATUS mandatory
    DESCRIPTION
      "Number of connections of this TSAP not in the connection state closed."
  ::= { bcamTsapTabEntry 46 }
-- SNMPNAME: ACCN
-- ASSNAME: YAPNOCON
-- implemented

bcamTsapTabCloseConns OBJECT-TYPE
    SYNTAX Counter
    ACCESS read-only
    STATUS mandatory
    DESCRIPTION
      "Number of connections of this TSAP that have been opened and are now
       in the connection state closing or closed."
  ::= { bcamTsapTabEntry 47 }
-- SNMPNAME: ACLC
-- ASSNAME: YAP2#COA
-- implemented

bcamTsapTabClessSendBytes OBJECT-TYPE
  SYNTAX Counter
  ACCESS read-only
  STATUS mandatory
  DESCRIPTION
      "Number of bytes sent connectionless by this application"
  ::= { bcamTsapTabEntry 48 }
-- SNMPNAME: ALSB
-- ASSNAME: YAP2CLSB
-- implemented

bcamTsapTabClessRecvBytes OBJECT-TYPE
  SYNTAX Counter
  ACCESS read-only
  STATUS mandatory
  DESCRIPTION
    "Number of bytes received connectionless by this application"
  ::= { bcamTsapTabEntry 49 }
-- SNMPNAME: ALRB
-- ASSNAME: YAP2CLRB YAPCLRB
-- implemented

bcamTsapTabClessSendCalls OBJECT-TYPE
  SYNTAX Counter
  ACCESS read-only
  STATUS mandatory
  DESCRIPTION
    "Number of successful send calls for connectionless data"
  ::= { bcamTsapTabEntry 50 }
-- SNMPNAME: ALSC
-- ASSNAME: YAP2CLSC
-- implemented

bcamTsapTabClessRecvCalls OBJECT-TYPE
  SYNTAX Counter
  ACCESS read-only
  STATUS mandatory
  DESCRIPTION
    "Number of successful receive calls for connectionless data"
  ::= { bcamTsapTabEntry 51 }
-- SNMPNAME: ALRC
-- ASSNAME: YAP2CLRC YAPCLRC
-- implemented

bcamTsapTabOutbufTsdu OBJECT-TYPE
  SYNTAX Gauge -- ASSLEN: 1
  ACCESS read-only
  STATUS mandatory
  DESCRIPTION
    " The number of packets to send connectionoriented that are currently buffered by BCAM for this application. "
  ::= { bcamTsapTabEntry 52 }
-- SNMPNAME: AOBT
-- ASSNAME: YC2#TSDU
-- implemented

bcamTsapTabOutbufByte OBJECT-TYPE
  SYNTAX Gauge -- ASSLEN: 3
  ACCESS read-only
  STATUS mandatory
  DESCRIPTION
    " The number of bytes to send connectionoriented that are currently buffered by BCAM for this application. "
  ::= { bcamTsapTabEntry 53 }
-- SNMPNAME: AOBB
-- ASSNAME: YC2OUTBF
-- implemented

bcamTsapTabInbufTsdu OBJECT-TYPE
  SYNTAX Gauge -- ASSLEN: 1
  ACCESS read-only
  STATUS mandatory
  DESCRIPTION
    " The number of packets to receive connectionoriented that are currently buffered by BCAM for this application. "
  ::= { bcamTsapTabEntry 54 }
-- SNMPNAME: AIBT
-- ASSNAME: YC2ITSDU
-- implemented

bcamTsapTabInbufByte OBJECT-TYPE
  SYNTAX Gauge -- ASSLEN: 3
  ACCESS read-only
  STATUS mandatory
  DESCRIPTION
    " The number of bytes to receive connectionoriented that are currently buffered by BCAM for this application. "
  ::= { bcamTsapTabEntry 55 }
-- SNMPNAME: AIBB
-- ASSNAME: YC2IBYTE
-- implemented

bcamTsapTabOutbufTsduCless OBJECT-TYPE
  SYNTAX Gauge -- ASSLEN: 1
  ACCESS read-only
  STATUS mandatory
  DESCRIPTION
    " The number of packets to send connectionless that are currently buffered by BCAM for this application. "
  ::= { bcamTsapTabEntry 56 }
-- SNMPNAME: AOBU
-- ASSNAME: YAPCLOS#
-- implemented

bcamTsapTabOutbufByteCless OBJECT-TYPE
  SYNTAX Gauge -- ASSLEN: 3
  ACCESS read-only
  STATUS mandatory
  DESCRIPTION
    " The number of bytes to send connectionless that are currently buffered by BCAM for this application. "
  ::= { bcamTsapTabEntry 57 }
-- SNMPNAME: AOBC
-- ASSNAME: YAPCLOB#
-- implemented

bcamTsapTabInbufTsduCless OBJECT-TYPE
  SYNTAX Gauge -- ASSLEN: 1
  ACCESS read-only
  STATUS mandatory
  DESCRIPTION
    " The number of packets to receive connectionless that are currently buffered by BCAM for this application. "
  ::= { bcamTsapTabEntry 58 }
-- SNMPNAME: AIBU
-- ASSNAME: YAPCLIS#
-- implemented

bcamTsapTabInbufByteCless OBJECT-TYPE
  SYNTAX Gauge -- ASSLEN: 3
  ACCESS read-only
  STATUS mandatory
  DESCRIPTION
    " The number of bytes to receive connectionless that are currently buffered by BCAM for this application. "
  ::= { bcamTsapTabEntry 59 }
-- SNMPNAME: AIBC
-- ASSNAME: YAPCLIB#
-- implemented

bcamTsapTabClessTimeout OBJECT-TYPE
  SYNTAX INTEGER
  ACCESS read-only
  STATUS mandatory
  DESCRIPTION
    " The number of packets discarded because the datagram timer elapsed. "
  ::= { bcamTsapTabEntry 60 }
-- SNMPNAME: ACLT
-- ASSNAME: YAP2CLTI
-- implemented







-- the Connection group


bcamCepCurrent OBJECT-TYPE
  SYNTAX INTEGER
  ACCESS read-only
  STATUS mandatory
  DESCRIPTION
    "The number of connections in the state open. "
  ::= { bcamCep 1 }
-- SNMPNAME: CCCU
-- ASSNAME: YBC#CONA
-- implemented

bcamCepClosed OBJECT-TYPE
  SYNTAX INTEGER
  ACCESS read-only
  STATUS mandatory
  DESCRIPTION
    "The number of connections that had reached the state open and are now in the state closing or closed. "
  ::= { bcamCep 2 }
-- SNMPNAME: CCLO
-- ASSNAME: YBC#CONC
-- implemented

bcamCepNotClosed OBJECT-TYPE
  SYNTAX INTEGER
  ACCESS read-only
  STATUS mandatory
  DESCRIPTION
    "The number of connections in the states opening, open, or closing. "
  ::= { bcamCep 3 }
-- SNMPNAME: CCNC
-- ASSNAME: YBC#CONL
-- implemented

bcamCepRerouting OBJECT-TYPE
  SYNTAX INTEGER
  ACCESS read-only
  STATUS mandatory
  DESCRIPTION
    "The number of times an alternative route has been tried. "
  ::= { bcamCep 4 }
-- SNMPNAME: CCRR
-- ASSNAME: YBC#CONR
-- implemented

bcamCepActiveTrials OBJECT-TYPE
  SYNTAX Counter
  ACCESS read-only
  STATUS mandatory
  DESCRIPTION
    " The number of active trials of connection establishment. "
  ::= { bcamCep 5 }
-- SNMPNAME: CATR
-- ASSNAME: YBC#CAA

bcamCepActiveTrialFailures OBJECT-TYPE
  SYNTAX Counter
  ACCESS read-only
  STATUS mandatory
  DESCRIPTION
    " The number of active trials of connection establishment that failed. "
  ::= { bcamCep 6 }
-- SNMPNAME: CATF
-- ASSNAME: YBC#CAAF

bcamCepPassiveTrials OBJECT-TYPE
  SYNTAX Counter
  ACCESS read-only
  STATUS mandatory
  DESCRIPTION
    " The number of passive trials of connection establishment. "
  ::= { bcamCep 7 }
-- SNMPNAME: CPTR
-- ASSNAME: YBC#CPA

bcamCepPassiveTrialFailures OBJECT-TYPE
  SYNTAX Counter
  ACCESS read-only
  STATUS mandatory
  DESCRIPTION
    " The number of passive trials of connection establishment that failed. "
  ::= { bcamCep 8 }
-- SNMPNAME: CPTF
-- ASSNAME: YBC#CPAF


bcamCepNumTable OBJECT-TYPE
  SYNTAX INTEGER
  ACCESS read-only
  STATUS mandatory
  DESCRIPTION
    "The number of table entries. "
  ::= { bcamCep 9 }
-- SNMPNAME: CNTB
-- ASSNAME: YBCC7OCC
-- implemented

  bcamCepTab OBJECT-TYPE
    SYNTAX SEQUENCE OF ConnEntry
    ACCESS not-accessible
    STATUS mandatory
    DESCRIPTION
      "Table of all active connections"
  ::= { bcamCep 10 }
-- SNMPNAME:
-- ASSNAME:

  bcamCepTabEntry OBJECT-TYPE
    SYNTAX ConnEntry
    ACCESS not-accessible
    STATUS mandatory
    DESCRIPTION
      "Information about a connection"
    INDEX {
	  bcamCepTabConnectionNumbers
	  }
  ::= { bcamCepTab 1 }
-- SNMPNAME:
-- ASSNAME:

ConnEntry ::=
  SEQUENCE {
    bcamCepTabProtocolClass INTEGER ,
    bcamCepTabConnectionNumbers Counter ,
    bcamCepTabDisconCommand OCTET STRING (SIZE(4)),
    bcamCepTabDisconInfoWord OCTET STRING (SIZE(4)),
    bcamCepTabTsduSends Counter ,
    bcamCepTabByteSends Counter ,
    bcamCepTabTsduReceiveds Counter ,
    bcamCepTabByteReceiveds Counter ,
    bcamCepTabSendCallOverMaxs Counter ,
    bcamCepTabLetterTimeouts Counter ,
    bcamCepTabOutbufTsduSend Gauge ,
    bcamCepTabOutbufByteSend Gauge ,
    bcamCepTabOutbufMaxTsduSend Gauge ,
    bcamCepTabOutbufMaxByteSend Gauge ,
    bcamCepTabInbufTsdu Gauge ,
    bcamCepTabInbufByte Gauge ,
    bcamCepTabInbufMaxTsduReceived Gauge ,
    bcamCepTabInbufMaxByteReceived Gauge ,
    bcamCepTabPacketsDataSends Counter ,
    bcamCepTabPacketsWindowSends Counter ,
    bcamCepTabPacketsDataReceiveds Counter ,
    bcamCepTabPacketsWindowReceiveds Counter ,
    bcamCepTabGlobalZeroWindowSends Counter ,
    bcamCepTabConnectionZeroWindowSends Counter ,
    bcamCepTabZeroWindowReceiveds Counter ,
    bcamCepTabRoundTripTime INTEGER (0..65535),
    bcamCepTabRetransmitPacketsSends Counter ,
    bcamCepTabDetectedGapsReceiveds Counter ,
    bcamCepTabDuplicatePacketsReceiveds Counter ,
    bcamCepTabErrorPacketsReceiveds Counter ,
    bcamCepTabConnectionState INTEGER ,
    bcamCepTabApplicationNumber INTEGER ,
    bcamCepTabRouteNumber INTEGER ,
    bcamCepTabDuration Gauge ,
    bcamCepTabDateConnectionEstablishment DisplayString (SIZE(8)),
    bcamCepTabTimeConnectionEstablishment DisplayString (SIZE(6)),
    bcamCepTabTypPartnerName INTEGER ,
    bcamCepTabPartnerName DisplayString (SIZE(0..78)),
    bcamCepTabLocalName DisplayString (SIZE(0..78)),
    bcamCepTabTypeL4Addr INTEGER ,
    bcamCepTabL4AddrPartner OCTET STRING (SIZE(0..32)),
    bcamCepTabL4AddrLocal OCTET STRING (SIZE(0..32)),
    bcamCepTabPartnerEndsystem DisplayString (SIZE(8)),
    bcamCepTabInWaitBuck1 INTEGER (0..65535),
    bcamCepTabInWaitBuck2 INTEGER (0..65535),
    bcamCepTabInWaitBuck3 INTEGER (0..65535),
    bcamCepTabInWaitBuck4 INTEGER (0..65535),
    bcamCepTabInWaitBuck5 INTEGER (0..65535),
    bcamCepTabReactBuck1 INTEGER (0..65535),
    bcamCepTabReactBuck2 INTEGER (0..65535),
    bcamCepTabReactBuck3 INTEGER (0..65535),
    bcamCepTabReactBuck4 INTEGER (0..65535),
    bcamCepTabReactBuck5 INTEGER (0..65535),
    bcamCepTabOutProcBuck1 INTEGER (0..65535),
    bcamCepTabOutProcBuck2 INTEGER (0..65535),
    bcamCepTabOutProcBuck3 INTEGER (0..65535),
    bcamCepTabOutProcBuck4 INTEGER (0..65535),
    bcamCepTabOutProcBuck5 INTEGER (0..65535),
    bcamCepTabInProcBuck1 INTEGER (0..65535),
    bcamCepTabInProcBuck2 INTEGER (0..65535),
    bcamCepTabInProcBuck3 INTEGER (0..65535),
    bcamCepTabInProcBuck4 INTEGER (0..65535),
    bcamCepTabInProcBuck5 INTEGER (0..65535),
    bcamCepTabMaxSendLen INTEGER ,
    bcamCepTabMaxIndLen INTEGER ,
    bcamCepTabLocalEndsystem DisplayString (SIZE(8))
    }

bcamCepTabProtocolClass OBJECT-TYPE
  SYNTAX INTEGER {
-- ASSMULTI:
		 local(1), -- ASSVAL: YC1LOCCN 2
		 nea(2),   -- ASSVAL: YC1NEACN 32
		 iso(3),   -- ASSVAL: YC1ISOCN 64
		 tcp(4)    -- ASSVAL: YC1TCPCN 128
		 }
  ACCESS read-only
  STATUS mandatory
  DESCRIPTION
    " The protocol class used for this connection.
      local (1) : the partner application resides in the same host.
      nea   (2) : the proprietary NEA protocol is used as transport protocol.
      iso   (3) : the ISO protocol is used as transport protocol.
      tcp   (4) : the TCP protocol is used as transport protocol."
  ::= { bcamCepTabEntry 1 }
-- SNMPNAME: CPCL
-- ASSNAME: YC1PRTCL
-- implemented
-- how about convergence protocols ?

bcamCepTabConnectionNumbers OBJECT-TYPE
  SYNTAX Counter
  ACCESS read-only
  STATUS mandatory
  DESCRIPTION
    " The definite identifier for this connection. Even if a connection is closed and then
      reopened between the same applications, the identfier will get a new value. "
  ::= { bcamCepTabEntry 2 }
-- SNMPNAME: CCNR
-- ASSNAME: YC1CON#
-- implemented

bcamCepTabDisconCommand OBJECT-TYPE
  SYNTAX OCTET STRING (SIZE(4)) -- ASSLEN: 5 VAR
  ACCESS read-only
  STATUS mandatory
  DESCRIPTION
    " First word that contains the reason for the closing of the connection (for diagnostic purposes only). "
  ::= { bcamCepTabEntry 3 }
-- SNMPNAME: CDI1
-- ASSNAME: YC1DISRS
-- implemented

bcamCepTabDisconInfoWord OBJECT-TYPE
  SYNTAX OCTET STRING (SIZE(4)) -- ASSLEN: 5 VAR
  ACCESS read-only
  STATUS mandatory
  DESCRIPTION
    " Second word that contains the reason for the closing of the connection (for diagnostic purposes only). "
  ::= { bcamCepTabEntry 4 }
-- SNMPNAME: CDI2
-- ASSNAME: YC1IBIW
-- implemented

bcamCepTabTsduSends OBJECT-TYPE
  SYNTAX Counter
  ACCESS read-only
  STATUS mandatory
  DESCRIPTION
    " The number of packets to send given to BCAM at the TSAP for this connection. "
  ::= { bcamCepTabEntry 5 }
-- SNMPNAME: CTSE
-- ASSNAME: YC1STDE
-- implemented

bcamCepTabByteSends OBJECT-TYPE
  SYNTAX Counter
  ACCESS read-only
  STATUS mandatory
  DESCRIPTION
    " The number of bytes to send given to BCAM at the TSAP for this connection. "
  ::= { bcamCepTabEntry 6 }
-- SNMPNAME: CBSE
-- ASSNAME: YC1SBYTE
-- implemented

bcamCepTabTsduReceiveds OBJECT-TYPE
  SYNTAX Counter
  ACCESS read-only
  STATUS mandatory
  DESCRIPTION
    " The number of packets received by BCAM for this connection. "
  ::= { bcamCepTabEntry 7 }
-- SNMPNAME: CTRE
-- ASSNAME: YC1RTDE
-- implemented

bcamCepTabByteReceiveds OBJECT-TYPE
  SYNTAX Counter
  ACCESS read-only
  STATUS mandatory
  DESCRIPTION
    " The number of bytes received by BCAM for this connection. "
  ::= { bcamCepTabEntry 8 }
-- SNMPNAME: CBRE
-- ASSNAME: YC1RBYTE
-- implemented

bcamCepTabSendCallOverMaxs OBJECT-TYPE
  SYNTAX Counter
  ACCESS read-only
  STATUS mandatory
  DESCRIPTION
    " The number of send calls at the TSAP for this connection when connection specific
      limits have been reached. "
  ::= { bcamCepTabEntry 9 }
-- SNMPNAME: CSCM
-- ASSNAME: YC1SOVMA
-- implemented

bcamCepTabLetterTimeouts OBJECT-TYPE
  SYNTAX Counter
  ACCESS read-only
  STATUS mandatory
  DESCRIPTION
    " The number of packets that have been deleted without delivering to the application
      due to the timeout of the letter timer. "
  ::= { bcamCepTabEntry 10 }
-- SNMPNAME: CLTI
-- ASSNAME: YC1LTIMO
-- implemented

bcamCepTabOutbufTsduSend OBJECT-TYPE
  SYNTAX Gauge -- ASSLEN: 1
  ACCESS read-only
  STATUS mandatory
  DESCRIPTION
    " The number of packets to send that are currently buffered by BCAM for this connection. "
  ::= { bcamCepTabEntry 11 }
-- SNMPNAME: COBT
-- ASSNAME: YC2#TSDU
-- implemented

bcamCepTabOutbufByteSend OBJECT-TYPE
  SYNTAX Gauge -- ASSLEN: 3
  ACCESS read-only
  STATUS mandatory
  DESCRIPTION
    " The number of bytes to send that are currently buffered by BCAM for this connection. "
  ::= { bcamCepTabEntry 12 }
-- SNMPNAME: COBB
-- ASSNAME: YC2OUTBF
-- implemented

bcamCepTabOutbufMaxTsduSend OBJECT-TYPE
  SYNTAX Gauge -- ASSLEN: 1
  ACCESS read-only
  STATUS mandatory
  DESCRIPTION
    " The maximum number of packets to send that will be buffered by BCAM for this connection. "
  ::= { bcamCepTabEntry 13 }
-- SNMPNAME: COMT
-- ASSNAME: YC2MTSDU
-- implemented

bcamCepTabOutbufMaxByteSend OBJECT-TYPE
  SYNTAX Gauge -- ASSLEN: 3
  ACCESS read-only
  STATUS mandatory
  DESCRIPTION
    " The maximum number of bytes to send that will be buffered by BCAM for this connection. "
  ::= { bcamCepTabEntry 14 }
-- SNMPNAME: COMB
-- ASSNAME: YC2MXBUF
-- implemented

bcamCepTabInbufTsdu OBJECT-TYPE
  SYNTAX Gauge -- ASSLEN: 1
  ACCESS read-only
  STATUS mandatory
  DESCRIPTION
    " The number of packets to receive that are currently buffered by BCAM for this connection. "
  ::= { bcamCepTabEntry 15 }
-- SNMPNAME: CIBT
-- ASSNAME: YC2ITSDU
-- implemented

bcamCepTabInbufByte OBJECT-TYPE
  SYNTAX Gauge -- ASSLEN: 3
  ACCESS read-only
  STATUS mandatory
  DESCRIPTION
    " The number of bytes to receive that are currently buffered by BCAM for this connection. "
  ::= { bcamCepTabEntry 16 }
-- SNMPNAME: CIBB
-- ASSNAME: YC2IBYTE
-- implemented

bcamCepTabInbufMaxTsduReceived OBJECT-TYPE
  SYNTAX Gauge -- ASSLEN: 1
  ACCESS read-only
  STATUS mandatory
  DESCRIPTION
    " The maximum number of packets to receive that will be buffered by BCAM for this connection. "
  ::= { bcamCepTabEntry 17 }
-- SNMPNAME: CIMT
-- ASSNAME: YC2ITSDM
-- implemented

bcamCepTabInbufMaxByteReceived OBJECT-TYPE
  SYNTAX Gauge -- ASSLEN: 3
  ACCESS read-only
  STATUS mandatory
  DESCRIPTION
    " The maximum number of bytes to receive that will be buffered by BCAM for this connection. "
  ::= { bcamCepTabEntry 18 }
-- SNMPNAME: CIMB
-- ASSNAME: YC2IBYTM
-- implemented

bcamCepTabPacketsDataSends OBJECT-TYPE
  SYNTAX Counter
  ACCESS read-only
  STATUS mandatory
  DESCRIPTION
    " The number of packets sent by BCAM that contained at least one byte of user data. "
  ::= { bcamCepTabEntry 19 }
-- SNMPNAME: CPDS
-- ASSNAME: YC2ODAPK
-- implemented

bcamCepTabPacketsWindowSends OBJECT-TYPE
  SYNTAX Counter
  ACCESS read-only
  STATUS mandatory
  DESCRIPTION
    " The number of packets sent by BCAM that contained only window information. "
  ::= { bcamCepTabEntry 20 }
-- SNMPNAME: CPWS
-- ASSNAME: YC2OWIPK
-- implemented

bcamCepTabPacketsDataReceiveds OBJECT-TYPE
  SYNTAX Counter
  ACCESS read-only
  STATUS mandatory
  DESCRIPTION
    " The number of packets received by BCAM that contained at least one byte of user data. "
  ::= { bcamCepTabEntry 21 }
-- SNMPNAME: CPDR
-- ASSNAME: YC2IDAPK
-- implemented

bcamCepTabPacketsWindowReceiveds OBJECT-TYPE
  SYNTAX Counter
  ACCESS read-only
  STATUS mandatory
  DESCRIPTION
    " The number of packets received by BCAM that contained only window information. "
  ::= { bcamCepTabEntry 22 }
-- SNMPNAME: CPWR
-- ASSNAME: YC2IWIPK
-- implemented

bcamCepTabGlobalZeroWindowSends OBJECT-TYPE
  SYNTAX Counter
  ACCESS read-only
  STATUS mandatory
  DESCRIPTION
    " The number of packets sent by BCAM that contained zero window due to global shortage of ressources. "
  ::= { bcamCepTabEntry 23 }
-- SNMPNAME: CGZS
-- ASSNAME: YC2OWI0G
-- implemented

bcamCepTabConnectionZeroWindowSends OBJECT-TYPE
  SYNTAX Counter
  ACCESS read-only
  STATUS mandatory
  DESCRIPTION
    " The number of packets sent by BCAM that contained zero window due to shortage of connection specific ressources. "
  ::= { bcamCepTabEntry 24 }
-- SNMPNAME: CCZS
-- ASSNAME: YC2OWI0C
-- implemented

bcamCepTabZeroWindowReceiveds OBJECT-TYPE
  SYNTAX Counter
  ACCESS read-only
  STATUS mandatory
  DESCRIPTION
    " The number of packets received that contained zero window. "
  ::= { bcamCepTabEntry 25 }
-- SNMPNAME: CZWR
-- ASSNAME: YC2IWI0
-- implemented

bcamCepTabRoundTripTime OBJECT-TYPE
  SYNTAX INTEGER (0..65535) -- ASSLEN: 2
  ACCESS read-only
  STATUS mandatory
  DESCRIPTION
    " The round trip time for this connection in milliseconds. "
  ::= { bcamCepTabEntry 26 }
-- SNMPNAME: CRTT
-- ASSNAME: YC2RTT
-- implemented

bcamCepTabRetransmitPacketsSends OBJECT-TYPE
  SYNTAX Counter
  ACCESS read-only
  STATUS mandatory
  DESCRIPTION
    " The number of packets sent that contain at least one byte of data that have been already sent. "
  ::= { bcamCepTabEntry 27 }
-- SNMPNAME: CRPS
-- ASSNAME: YC2RETR
-- implemented

bcamCepTabDetectedGapsReceiveds OBJECT-TYPE
  SYNTAX Counter
  ACCESS read-only
  STATUS mandatory
  DESCRIPTION
    " The number of packets received where there is a gap between the highest already received byte
      and the lowest byte in the packet.  "
  ::= { bcamCepTabEntry 28 }
-- SNMPNAME: CDGR
-- ASSNAME: YC2GAPS
-- implemented

bcamCepTabDuplicatePacketsReceiveds OBJECT-TYPE
  SYNTAX Counter
  ACCESS read-only
  STATUS mandatory
  DESCRIPTION
    " The number of packets received that contain at least one byte of user data which has already been
      received. "
  ::= { bcamCepTabEntry 29 }
-- SNMPNAME: CDPR
-- ASSNAME: YC2DUPL
-- implemented

bcamCepTabErrorPacketsReceiveds OBJECT-TYPE
  SYNTAX Counter
  ACCESS read-only
  STATUS mandatory
  DESCRIPTION
    " The number of packets received that were discarded because of weak protocol violations."
  ::= { bcamCepTabEntry 30 }
-- SNMPNAME: CEPR
-- ASSNAME: YC2IERPK
-- implemented

bcamCepTabConnectionState OBJECT-TYPE
  SYNTAX INTEGER {
-- ASSSINGLE:
		 opening(1), -- ASSVAL: YC3COPNG 2
		 open(2),    -- ASSVAL: YC3COPEN 3
		 closing(3), -- ASSVAL: YC3CCLNG 4
		 closed(4)   -- ASSVAL: YC3CCLOS 1
		 }
  ACCESS read-only
  STATUS mandatory
  DESCRIPTION
    " The current state of the connection.
      opening (1) : the connection establishment is in progress.
      open    (2) : the connection is ready for data transfer.
      closing (3) : the connection is terminating.
      closed  (4) : the connection has been closed."
  ::= { bcamCepTabEntry 31 }
-- SNMPNAME: CCST
-- ASSNAME: YC3CSTAT
-- implemented

bcamCepTabApplicationNumber OBJECT-TYPE
  SYNTAX INTEGER
  ACCESS read-only
  STATUS mandatory
  DESCRIPTION
    " The definite identifier of the local application the connection belongs to. "
  ::= { bcamCepTabEntry 32 }
-- SNMPNAME: CANR
-- ASSNAME: YC3APPL#
-- implemented

bcamCepTabRouteNumber OBJECT-TYPE
  SYNTAX INTEGER
  ACCESS read-only
  STATUS mandatory
  DESCRIPTION
    " The definite identifier of the route that is used for the connection. "
  ::= { bcamCepTabEntry 33 }
-- SNMPNAME: CRNR
-- ASSNAME: YC3ROUT#
-- implemented

bcamCepTabDuration OBJECT-TYPE
  SYNTAX Gauge
  ACCESS read-only
  STATUS mandatory
  DESCRIPTION
    " The time the connection was in the state open. "
  ::= { bcamCepTabEntry 34 }
-- SNMPNAME: CDUR
-- ASSNAME: YC3CODUR
-- implemented

bcamCepTabDateConnectionEstablishment OBJECT-TYPE
  SYNTAX DisplayString (SIZE(8)) -- ASSLEN: 9 VAR
  ACCESS read-only
  STATUS mandatory
  DESCRIPTION
    " The date of the connection establishment.
      Format: YYYYMMDD "
  ::= { bcamCepTabEntry 35 }
-- SNMPNAME: CDCE
-- ASSNAME: YC3CDATE
-- implemented

bcamCepTabTimeConnectionEstablishment OBJECT-TYPE
  SYNTAX DisplayString (SIZE(6)) -- ASSLEN: 7 VAR
  ACCESS read-only
  STATUS mandatory
  DESCRIPTION
    " The time of the connection establishment.
      Format: HHMMSS "
  ::= { bcamCepTabEntry 36 }
-- SNMPNAME: CTCE
-- ASSNAME: YC3CTIME
-- implemented

bcamCepTabTypPartnerName OBJECT-TYPE
  SYNTAX INTEGER {
-- ASSSINGLE:
		 neaName(1),    -- ASSVAL: YC3PAPP 2
		 socketName(2), -- ASSVAL: YC3PPT# 6
		 isoName(3)     -- ASSVAL: YC3PISO 7
		 }
  ACCESS read-only
  STATUS mandatory
  DESCRIPTION
    " The type of name used for the partner application.
      neaName    (1) : the name consists of 8 byte application name and 8 byte name of endsystem.
      socketName (2) : the name consists of up to 32 byte socket name.
      isoName    (3) : the name consists of up to 78 byte iso name. "
  ::= { bcamCepTabEntry 37 }
-- SNMPNAME: CTPN
-- ASSNAME: YC3PTYP
-- implemented

bcamCepTabPartnerName OBJECT-TYPE
  SYNTAX DisplayString (SIZE(0..78)) -- ASSLEN: 79 VAR
  ACCESS read-only
  STATUS mandatory
  DESCRIPTION
    " The name of the partner application according the type of the name (bcamCepTabTypPartnerName). "
  ::= { bcamCepTabEntry 38 }
-- SNMPNAME: CPNM
-- ASSNAME: YC3PID YC3PNAI YC3PNAI
-- implemented

bcamCepTabLocalName OBJECT-TYPE
  SYNTAX DisplayString (SIZE(0..78)) -- ASSLEN: 79 VAR
  ACCESS read-only
  STATUS mandatory
  DESCRIPTION
    " The name of the local application according the type of the name (bcamCepTabTypPartnerName). "
  ::= { bcamCepTabEntry 39 }
-- SNMPNAME: CLNM
-- ASSNAME: YAP2NID YAP2NNAI YAP2NNAI
-- implemented

bcamCepTabTypeL4Addr OBJECT-TYPE
  SYNTAX INTEGER {
-- ASSSINGLE:
		 portNumber(1), -- ASSVAL: YC3PFIN 1
		 neaTsel(2),    -- ASSVAL: YC3PFNE 128
		 osiTsel(3)     -- ASSVAL: YC3PFOS 16
		 }
  ACCESS read-only
  STATUS mandatory
  DESCRIPTION
    " The type of layer 4 addresses used for this connection.
      portNumber (1) : the address consists of 2 byte port number.
      neaTsel    (2) : the address consists of 8 byte NEA transport selector.
      osiTsel    (3) : the address consists of up to 33 byte OSI transport selector."
  ::= { bcamCepTabEntry 40 }
-- SNMPNAME: CTL4
-- ASSNAME: YC3PFLG
-- implemented

bcamCepTabL4AddrPartner OBJECT-TYPE
  SYNTAX OCTET STRING (SIZE(0..32)) -- ASSLEN: 34 VAR
  ACCESS read-only
  STATUS mandatory
  DESCRIPTION
    " The layer 4 address of the partner application according the type of the address (bcamCepTabTypeL4Addr)."
  ::= { bcamCepTabEntry 41 }
-- SNMPNAME: CL4P
-- ASSNAME: YC3PPO# YC3PTN YC3PTO
-- implemented

bcamCepTabL4AddrLocal OBJECT-TYPE
  SYNTAX OCTET STRING (SIZE(0..32)) -- ASSLEN: 34 VAR
  ACCESS read-only
  STATUS mandatory
  DESCRIPTION
    " The layer 4 address of the partner application according the type of the address (bcamCepTabTypeL4Addr)."
  ::= { bcamCepTabEntry 42 }
-- SNMPNAME: CL4L
-- ASSNAME: YAP2OPO# YAP2OTN YAP2OTO
-- implemented

bcamCepTabPartnerEndsystem OBJECT-TYPE
  SYNTAX DisplayString (SIZE(8)) -- ASSLEN: 9 VAR
  ACCESS read-only
  STATUS mandatory
  DESCRIPTION
    " The name of the host where the partner application resides. "
  ::= { bcamCepTabEntry 43 }
-- SNMPNAME: CPES
-- ASSNAME: YC3PNES
-- implemented

bcamCepTabInWaitBuck1 OBJECT-TYPE
  SYNTAX INTEGER (0..65535) -- ASSLEN: 2
  ACCESS read-only
  STATUS mandatory
  DESCRIPTION
    " The number of times the input wait time was in the time interval between
      zero and bcamGlobalInWaitLimit1. "
  ::= { bcamCepTabEntry 44 }
-- SNMPNAME: CWB1
-- ASSNAME: YC1WTB1
-- implemented

bcamCepTabInWaitBuck2 OBJECT-TYPE
  SYNTAX INTEGER (0..65535) -- ASSLEN: 2
  ACCESS read-only
  STATUS mandatory
  DESCRIPTION
    " The number of times the input wait time was in the time interval between
      bcamGlobalInWaitLimit1 and bcamGlobalInWaitLimit2. "
  ::= { bcamCepTabEntry 45 }
-- SNMPNAME: CWB2
-- ASSNAME: YC1WTB2
-- implemented

bcamCepTabInWaitBuck3 OBJECT-TYPE
  SYNTAX INTEGER (0..65535) -- ASSLEN: 2
  ACCESS read-only
  STATUS mandatory
  DESCRIPTION
    " The number of times the input wait time was in the time interval between
      bcamGlobalInWaitLimit2 and bcamGlobalInWaitLimit3. "
  ::= { bcamCepTabEntry 46 }
-- SNMPNAME: CWB3
-- ASSNAME: YC1WTB3
-- implemented

bcamCepTabInWaitBuck4 OBJECT-TYPE
  SYNTAX INTEGER (0..65535) -- ASSLEN: 2
  ACCESS read-only
  STATUS mandatory
  DESCRIPTION
    " The number of times the input wait time was in the time interval between
      bcamGlobalInWaitLimit3 and bcamGlobalInWaitLimit4. "
  ::= { bcamCepTabEntry 47 }
-- SNMPNAME: CWB4
-- ASSNAME: YC1WTB4
-- implemented

bcamCepTabInWaitBuck5 OBJECT-TYPE
  SYNTAX INTEGER (0..65535) -- ASSLEN: 2
  ACCESS read-only
  STATUS mandatory
  DESCRIPTION
    " The number of times the input wait time was longer than
      bcamGlobalInWaitLimit4. "
  ::= { bcamCepTabEntry 48 }
-- SNMPNAME: CWB5
-- ASSNAME: YC1WTB5
-- implemented

bcamCepTabReactBuck1 OBJECT-TYPE
  SYNTAX INTEGER (0..65535) -- ASSLEN: 2
  ACCESS read-only
  STATUS mandatory
  DESCRIPTION
    " The number of times the application reaction time was in the time interval between
      zero and bcamGlobalReactLimit1. "
  ::= { bcamCepTabEntry 49 }
-- SNMPNAME: CRB1
-- ASSNAME: YC1RSB1
-- implemented

bcamCepTabReactBuck2 OBJECT-TYPE
  SYNTAX INTEGER (0..65535) -- ASSLEN: 2
  ACCESS read-only
  STATUS mandatory
  DESCRIPTION
    " The number of times the application reaction time was in the time interval between
      bcamGlobalReactLimit1 and bcamGlobalReactLimit2. "
  ::= { bcamCepTabEntry 50 }
-- SNMPNAME: CRB2
-- ASSNAME: YC1RSB2
-- implemented

bcamCepTabReactBuck3 OBJECT-TYPE
  SYNTAX INTEGER (0..65535) -- ASSLEN: 2
  ACCESS read-only
  STATUS mandatory
  DESCRIPTION
    " The number of times the application reaction time was in the time interval between
      bcamGlobalReactLimit2 and bcamGlobalReactLimit3 "
  ::= { bcamCepTabEntry 51 }
-- SNMPNAME: CRB3
-- ASSNAME: YC1RSB3
-- implemented

bcamCepTabReactBuck4 OBJECT-TYPE
  SYNTAX INTEGER (0..65535) -- ASSLEN: 2
  ACCESS read-only
  STATUS mandatory
  DESCRIPTION
    " The number of times the application reaction time was in the time interval between
      bcamGlobalReactLimit3 and bcamGlobalReactLimit4. "
  ::= { bcamCepTabEntry 52 }
-- SNMPNAME: CRB4
-- ASSNAME: YC1RSB4
-- implemented

bcamCepTabReactBuck5 OBJECT-TYPE
  SYNTAX INTEGER (0..65535) -- ASSLEN: 2
  ACCESS read-only
  STATUS mandatory
  DESCRIPTION
    " The number of times the application reaction time was longer than
      bcamGlobalReactLimit4. "
  ::= { bcamCepTabEntry 53 }
-- SNMPNAME: CRB5
-- ASSNAME: YC1RSB5
-- implemented

bcamCepTabOutProcBuck1 OBJECT-TYPE
  SYNTAX INTEGER (0..65535) -- ASSLEN: 2
  ACCESS read-only
  STATUS mandatory
  DESCRIPTION
    " The number of times the outbound processing time was in the time interval between
      zero and bcamGlobalOutProcLimit1. "
  ::= { bcamCepTabEntry 54 }
-- SNMPNAME: COB1
-- ASSNAME: YC2OTB1
-- implemented

bcamCepTabOutProcBuck2 OBJECT-TYPE
  SYNTAX INTEGER (0..65535) -- ASSLEN: 2
  ACCESS read-only
  STATUS mandatory
  DESCRIPTION
    " The number of times the outbound processing time was in the time interval between
      bcamGlobalOutProcLimit1 and bcamGlobalOutProcLimit2. "
  ::= { bcamCepTabEntry 55 }
-- SNMPNAME: COB2
-- ASSNAME: YC2OTB2
-- implemented

bcamCepTabOutProcBuck3 OBJECT-TYPE
  SYNTAX INTEGER (0..65535) -- ASSLEN: 2
  ACCESS read-only
  STATUS mandatory
  DESCRIPTION
    " The number of times the outbound processing time was in the time interval between
      bcamGlobalOutProcLimit2 and bcamGlobalOutProcLimit3. "
  ::= { bcamCepTabEntry 56 }
-- SNMPNAME: COB3
-- ASSNAME: YC2OTB3
-- implemented


bcamCepTabOutProcBuck4 OBJECT-TYPE
  SYNTAX INTEGER (0..65535) -- ASSLEN: 2
  ACCESS read-only
  STATUS mandatory
  DESCRIPTION
    " The number of times the outbound processing time was in the time interval between
      bcamGlobalOutProcLimit3 and bcamGlobalOutProcLimit4. "
  ::= { bcamCepTabEntry 57 }
-- SNMPNAME: COB4
-- ASSNAME: YC2OTB4
-- implemented

bcamCepTabOutProcBuck5 OBJECT-TYPE
  SYNTAX INTEGER (0..65535) -- ASSLEN: 2
  ACCESS read-only
  STATUS mandatory
  DESCRIPTION
    " The number of times the outbound processing time was longer than
      bcamGlobalOutProcLimit4. "
  ::= { bcamCepTabEntry 58 }
-- SNMPNAME: COB5
-- ASSNAME: YC2OTB5
-- implemented

bcamCepTabInProcBuck1 OBJECT-TYPE
  SYNTAX INTEGER (0..65535) -- ASSLEN: 2
  ACCESS read-only
  STATUS mandatory
  DESCRIPTION
    " The number of times the inbound processing time was in the time interval between
      zero and bcamGlobalInProcLimit1. "
  ::= { bcamCepTabEntry 59 }
-- SNMPNAME: CIB1
-- ASSNAME: YC2ITB1
-- implemented

bcamCepTabInProcBuck2 OBJECT-TYPE
  SYNTAX INTEGER (0..65535) -- ASSLEN: 2
  ACCESS read-only
  STATUS mandatory
  DESCRIPTION
    " The number of times the inbound processing time was in the time interval between
      bcamGlobalInProcLimit1 and bcamGlobalInProcLimit2. "
  ::= { bcamCepTabEntry 60 }
-- SNMPNAME: CIB2
-- ASSNAME: YC2ITB2
-- implemented

bcamCepTabInProcBuck3 OBJECT-TYPE
  SYNTAX INTEGER (0..65535) -- ASSLEN: 2
  ACCESS read-only
  STATUS mandatory
  DESCRIPTION
    " The number of times the inbound processing time was in the time interval between
      bcamGlobalInProcLimit2 and bcamGlobalInProcLimit3. "
  ::= { bcamCepTabEntry 61 }
-- SNMPNAME: CIB3
-- ASSNAME: YC2ITB3
-- implemented

bcamCepTabInProcBuck4 OBJECT-TYPE
  SYNTAX INTEGER (0..65535) -- ASSLEN: 2
  ACCESS read-only
  STATUS mandatory
  DESCRIPTION
    " The number of times the inbound processing time was in the time interval between
      bcamGlobalInProcLimit3 and bcamGlobalInProcLimit4. "
  ::= { bcamCepTabEntry 62 }
-- SNMPNAME: CIB4
-- ASSNAME: YC2ITB4
-- implemented

bcamCepTabInProcBuck5 OBJECT-TYPE
  SYNTAX INTEGER (0..65535) -- ASSLEN: 2
  ACCESS read-only
  STATUS mandatory
  DESCRIPTION
    " The number of times the inbound processing time was longer than
      bcamGlobalInProcLimit4. "
  ::= { bcamCepTabEntry 63 }
-- SNMPNAME: CIB5
-- ASSNAME: YC2ITB5
-- implemented

bcamCepTabMaxSendLen OBJECT-TYPE
  SYNTAX INTEGER
  ACCESS read-only
  STATUS mandatory
  DESCRIPTION
    " The maximum number of bytes per send call that can be given to BCAM at the interface. "
  ::= { bcamCepTabEntry 64 }
-- SNMPNAME: CMSL
-- ASSNAME: YC2LTDES
-- implemented

bcamCepTabMaxIndLen OBJECT-TYPE
  SYNTAX INTEGER
  ACCESS read-only
  STATUS mandatory
  DESCRIPTION
    " The maximum number of bytes BCAM will announce per data indication. "
  ::= { bcamCepTabEntry 65 }
-- SNMPNAME: CMIL
-- ASSNAME: YC2LTDER
-- implemented

bcamCepTabLocalEndsystem OBJECT-TYPE
  SYNTAX DisplayString (SIZE(8)) -- ASSLEN: 9 VAR
  ACCESS read-only
  STATUS mandatory
  DESCRIPTION
    " The name of the host where the local application resides. "
  ::= { bcamCepTabEntry 66 }
-- SNMPNAME: CLES
-- ASSNAME: YAP2OHOS
-- implemented



-- the Route group


bcamRouteNumTable OBJECT-TYPE
    SYNTAX INTEGER
    ACCESS read-only
    STATUS mandatory
    DESCRIPTION
      "The number of all routes known by BCAM"
  ::= { bcamRoute 1 }
-- SNMPNAME: RNTB
-- ASSNAME:

  bcamRouteActive OBJECT-TYPE
    SYNTAX INTEGER
    ACCESS read-only
    STATUS mandatory
    DESCRIPTION
      "The number of active routes"
  ::= { bcamRoute 2 }
-- SNMPNAME: RRAT
-- ASSNAME:

bcamRouteArpDefault OBJECT-TYPE
  SYNTAX INTEGER {
-- ASSMULTI:
		 off(1),  -- ASSVAL: YBTARPNO 128
		 on(2),   -- ASSVAL: YBTARPTI 32
		 quiet(4) -- ASSVAL: YBTARPQU 64
		 }
  ACCESS read-only
  STATUS mandatory
  DESCRIPTION
    " The ARP state to use as default when a route of type node (bcamRouteTabTyp) is activated.
      Several bits may be set simultaneous.
      off   (1) : No usage of ARP.
      on    (2) :  periodic usage of ARP.
      quiet (4) : ARP will only be used if no connection oriented data were transferred during the
		  last ARP period."
  ::= { bcamRoute 3 }
-- SNMPNAME: RADS
-- ASSNAME: YBTARPFG

bcamRouteRoutingReqIp OBJECT-TYPE
    SYNTAX INTEGER
    ACCESS read-only
    STATUS mandatory
    DESCRIPTION
      " The number of forwarding requests for IP "
  ::= { bcamRoute 4 }
-- SNMPNAME: RRRP
-- ASSNAME: YBTIPFDT

bcamRouteRoutingReqIso OBJECT-TYPE
    SYNTAX INTEGER
    ACCESS read-only
    STATUS mandatory
    DESCRIPTION
      " The number of forwarding requests for ISO "
  ::= { bcamRoute 5 }
-- SNMPNAME: RRRS
-- ASSNAME: YBT3#RSQ

bcamRouteRoutingReqNea OBJECT-TYPE
    SYNTAX INTEGER
    ACCESS read-only
    STATUS mandatory
    DESCRIPTION
      " The number of forwarding requests for NEA "
  ::= { bcamRoute 6 }
-- SNMPNAME: RRRN
-- ASSNAME: YBT3#RNE
-- # Routing requests IP,NEA,ISO            YBTIPFDT, YBT3#RNE, YBT3#RSQ

bcamRouteSuccRoutingReqIp OBJECT-TYPE
    SYNTAX INTEGER
    ACCESS read-only
    STATUS mandatory
    DESCRIPTION
      " The number of successful forwarding requests for IP "
  ::= { bcamRoute 7 }
-- SNMPNAME: RSRP
-- ASSNAME: YBT3#RPS

bcamRouteSuccRoutingReqIso OBJECT-TYPE
    SYNTAX INTEGER
    ACCESS read-only
    STATUS mandatory
    DESCRIPTION
      " The number of successful forwarding requests for ISO "
  ::= { bcamRoute 8 }
-- SNMPNAME: RSRS
-- ASSNAME: YBT3#RSS

bcamRouteSuccRoutingReqNea OBJECT-TYPE
    SYNTAX INTEGER
    ACCESS read-only
    STATUS mandatory
    DESCRIPTION
      " The number of successful forwarding requests for NEA "
  ::= { bcamRoute 9 }
-- SNMPNAME: RSRN
-- ASSNAME: YBT3#RNE


  bcamRouteTab OBJECT-TYPE
    SYNTAX SEQUENCE OF RoutEntry
    ACCESS not-accessible
    STATUS mandatory
    DESCRIPTION
      "Table of all Routes"
  ::= { bcamRoute 10 }
-- SNMPNAME:
-- ASSNAME:

  bcamRouteTabEntry OBJECT-TYPE
    SYNTAX RoutEntry
    ACCESS not-accessible
    STATUS mandatory
    DESCRIPTION
      "Information about a route"
    INDEX {
      bcamRouteTabNumbers
      }
  ::= { bcamRouteTab 1 }
-- SNMPNAME:
-- ASSNAME:

  RoutEntry ::=
    SEQUENCE {
    bcamRouteTabNumbers Counter ,
    bcamRouteTabName DisplayString (SIZE(8)),
    bcamRouteTabNumNeaConn Gauge ,
    bcamRouteTabNumIsoConn Gauge ,
    bcamRouteTabMaxNeaConn Gauge ,
    bcamRouteTabMaxIsoConn Gauge ,
    bcamRouteTabBadNeaElems Counter ,
    bcamRouteTabBadIsoElems Counter ,
    bcamRouteTabMaxL4Conn Gauge ,
    bcamRouteTabMaxUnackTpdu Gauge ,
    bcamRouteTabRouteNetTyp INTEGER ,
    bcamRouteTabNumberIsoIpRouter INTEGER ,
    bcamRouteTabNumberNeaRouter INTEGER ,
    bcamRouteTabNumberGateway INTEGER ,
    bcamRouteTabFunction INTEGER ,
    bcamRouteTabProcNetTyp INTEGER ,
    bcamRouteTabMaxTsduLen Gauge ,
    bcamRouteTabNameEndsystem DisplayString (SIZE(8)),
    bcamRouteTabIso4WindowTimer Gauge ,
    bcamRouteTabIso4RetransTimer Gauge ,
    bcamRouteTabAckTimer Gauge ,
    bcamRouteTabErrorRecovTimer Gauge ,
    bcamRouteTabRejectTimer Gauge ,
    bcamRouteTabExpedRetransTimer Gauge ,
    bcamRouteTabNameGateway DisplayString (SIZE(8)),
    bcamRouteTabNameX25Station DisplayString (SIZE(8)),
    bcamRouteTabL3InputProfil INTEGER ,
    bcamRouteTabTransState INTEGER ,
    bcamRouteTabOption INTEGER ,
    bcamRouteTabTyp INTEGER ,
    bcamRouteTabUsage INTEGER ,
    bcamRouteTabL3Subprofile INTEGER ,
    bcamRouteTabCommandState INTEGER ,
    bcamRouteTabChangeState INTEGER ,
    bcamRouteTabIso9542 INTEGER ,
    bcamRouteTabMaxNetLength INTEGER ,
    bcamRouteTabState2 INTEGER ,
    bcamRouteTabDeactReason INTEGER ,
    bcamRouteTabSwitchType INTEGER ,
    bcamRouteTabReasonCreation INTEGER ,
    bcamRouteTabOrigLanAddress PhysAddress ,
    bcamRouteTabLanAddress PhysAddress ,
    bcamRouteTabTypAddress INTEGER ,
    bcamRouteTabLocalAddr OCTET STRING (SIZE(0..20)),
    bcamRouteTabRemoteAddr OCTET STRING (SIZE(0..20)),
    bcamRouteTabOutPacketsDatas Counter ,
    bcamRouteTabOutPacketsFlowControls Counter ,
    bcamRouteTabInPacketsDatas Counter ,
    bcamRouteTabInPacketsFlowControls Counter ,
    bcamRouteTabOutRetransPackets Counter ,
    bcamRouteTabInDetectedGaps Counter ,
    bcamRouteTabInDuplicatedPackets Counter ,
    bcamRouteTabInIncorrectPackets Counter ,
    bcamRouteTabRoundTripTimeClosed INTEGER (0..65535),
    bcamRouteTabRoundTripTimeCurrent INTEGER (0..65535),
    bcamRouteTabArpReqSend INTEGER ,
    bcamRouteTabArpRepSend INTEGER ,
    bcamRouteTabArpReqRec INTEGER ,
    bcamRouteTabArpRepRec INTEGER ,
    bcamRouteTabIcmpReq INTEGER ,
    bcamRouteTabIcmpReply INTEGER ,
    bcamRouteTabIcmpRedirect INTEGER ,
    bcamRouteTabSwitched INTEGER ,
    bcamRouteTabDown INTEGER ,
    bcamRouteTabOspfHello INTEGER ,
    bcamRouteTabPacketNoConn INTEGER (0..65535),
    bcamRouteTabPacketInternDiscon INTEGER (0..65535),
    bcamRouteTabPacketBadProtocol INTEGER (0..65535),
    bcamRouteTabConnReqOut INTEGER (0..65535),
    bcamRouteTabConnReqOutAck INTEGER (0..65535),
    bcamRouteTabConnReqOutRej INTEGER (0..65535),
    bcamRouteTabConnReqIn INTEGER (0..65535),
    bcamRouteTabConnReqInAck INTEGER (0..65535),
    bcamRouteTabConnReqInRej INTEGER (0..65535),
    bcamRouteTabDisconnOut INTEGER (0..65535),
    bcamRouteTabDisconnOutAck INTEGER (0..65535),
    bcamRouteTabDisconnIn INTEGER (0..65535),
    bcamRouteTabDisconnInAck INTEGER (0..65535),
    bcamRouteTabNumberLink INTEGER,
    bcamRouteTabArpFlag INTEGER,
    bcamRouteTabNsduLen INTEGER,
    bcamRouteTabMinNsduLen INTEGER,
    bcamRouteTabMaxNsduLen INTEGER

      }

bcamRouteTabNumbers OBJECT-TYPE
  SYNTAX Counter
  ACCESS read-only
  STATUS mandatory
  DESCRIPTION
    " The definite identifier for this route. "
  ::= { bcamRouteTabEntry 1 }
-- SNMPNAME: RRNR
-- ASSNAME: YRROZKEY
-- implemented

bcamRouteTabName OBJECT-TYPE
  SYNTAX DisplayString (SIZE(8)) -- ASSLEN: 9 VAR
  ACCESS read-only
  STATUS mandatory
  DESCRIPTION
    " The name of this route. "
  ::= { bcamRouteTabEntry 2 }
-- SNMPNAME: RNAM
-- ASSNAME: YRRONAME
-- implemented

bcamRouteTabNumNeaConn OBJECT-TYPE
  SYNTAX Gauge
  ACCESS read-only
  STATUS mandatory
  DESCRIPTION
    " The current number of NEA connections using this route. "
  ::= { bcamRouteTabEntry 3 }
-- SNMPNAME: RNNC
-- ASSNAME: YRROCO#N
-- implemented

bcamRouteTabNumIsoConn OBJECT-TYPE
  SYNTAX Gauge
  ACCESS read-only
  STATUS mandatory
  DESCRIPTION
    " The current number of ISO and TCP connections using this route. "
  ::= { bcamRouteTabEntry 4 }
-- SNMPNAME: RNIC
-- ASSNAME: YRROCO#I
-- implemented

bcamRouteTabMaxNeaConn OBJECT-TYPE
  SYNTAX Gauge
  ACCESS read-only
  STATUS mandatory
  DESCRIPTION
    " The maximum number of NEA connections allowed for this route. "
  ::= { bcamRouteTabEntry 5 }
-- SNMPNAME: RMNC
-- ASSNAME: YRROMX#N
-- implemented

bcamRouteTabMaxIsoConn OBJECT-TYPE
  SYNTAX Gauge
  ACCESS read-only
  STATUS mandatory
  DESCRIPTION
    " The maximum number of ISO and TCP connections allowed for this route. "
  ::= { bcamRouteTabEntry 6 }
-- SNMPNAME: RMIC
-- ASSNAME: YRROMX#I
-- implemented

bcamRouteTabBadNeaElems OBJECT-TYPE
  SYNTAX Counter
  ACCESS read-only
  STATUS mandatory
  DESCRIPTION
    " The number of erroneous NEA fragments received on this route. "
  ::= { bcamRouteTabEntry 7 }
-- SNMPNAME: RBNE
-- ASSNAME: YRROBNEA
-- implemented

bcamRouteTabBadIsoElems OBJECT-TYPE
  SYNTAX Counter
  ACCESS read-only
  STATUS mandatory
  DESCRIPTION
    " The number of erroneous ISO and TCP fragments received on this route. "
  ::= { bcamRouteTabEntry 8 }
-- SNMPNAME: RBIS
-- ASSNAME: YRROBISO
-- implemented

bcamRouteTabMaxL4Conn OBJECT-TYPE
  SYNTAX Gauge
  ACCESS read-only
  STATUS mandatory
  DESCRIPTION
    " The maximum number of layer 4 connections per layer 3 connection for this route. "
  ::= { bcamRouteTabEntry 9 }
-- SNMPNAME: RML4
-- ASSNAME: YRROM#43
-- implemented

bcamRouteTabMaxUnackTpdu OBJECT-TYPE
  SYNTAX Gauge -- ASSLEN: 2
  ACCESS read-only
  STATUS mandatory
  DESCRIPTION
    " The maximum number of unacknowledged TPDUs per layer 3 connection that may be sent over this route. "
  ::= { bcamRouteTabEntry 10 }
-- SNMPNAME: RMUT
-- ASSNAME: YRROM#TN
-- implemented

bcamRouteTabRouteNetTyp OBJECT-TYPE
  SYNTAX INTEGER {
-- ASSMULTI:
		 gatewayRouter(1), -- ASSVAL: YRRORNGR 1
		 neaRouter(2),     -- ASSVAL: YRRORNNR 2
		 intfIpRouter(4),  -- ASSVAL: YRRORNRR 16
		 int0Router(8)     -- ASSVAL: YRRORN0R 128
		 }
  ACCESS read-only
  STATUS mandatory
  DESCRIPTION
    " Describes whether there are other intermediate routes necessary to be known by
      BCAM to reach the system described by this route.
      gatewayRouter (1) : the system is reached via a gateway route.
      neaRouter     (2) : the system is reached via a NEA router route.
      intfIpRouter  (4) : the system is reached via an INTF or IP router route.
      int0Router    (8) : the system is reached via an INT0 router route.
      Several bits may be set simultaneous."
  ::= { bcamRouteTabEntry 11 }
-- SNMPNAME: RRNT
--  ASSNAME: YRRORNTY
-- implemented

bcamRouteTabNumberIsoIpRouter OBJECT-TYPE
  SYNTAX INTEGER
  ACCESS read-only
  STATUS mandatory
  DESCRIPTION
    " The number of the route which describes the INT0, INTF or IP router used to
      reach the system described by this route. "
  ::= { bcamRouteTabEntry 12 }
-- SNMPNAME: RIRN
-- ASSNAME: YRROROUR
-- implemented

bcamRouteTabNumberNeaRouter OBJECT-TYPE
  SYNTAX INTEGER
  ACCESS read-only
  STATUS mandatory
  DESCRIPTION
    " The number of the route which describes the NEA router used to
      reach the system described by this route. "
  ::= { bcamRouteTabEntry 13 }
-- SNMPNAME: RNRN
-- ASSNAME: YRROROUN
-- implemented

bcamRouteTabNumberGateway OBJECT-TYPE
  SYNTAX INTEGER
  ACCESS read-only
  STATUS mandatory
  DESCRIPTION
    " The number of the route which describes the gateway used to
      reach the system described by this route. "
  ::= { bcamRouteTabEntry 14 }
-- SNMPNAME: RGAN
-- ASSNAME: YRROROUG
-- implemented

bcamRouteTabFunction OBJECT-TYPE
  SYNTAX INTEGER {
-- ASSMULTI:
		 onlyServerAccess(1), -- ASSVAL: YRROFSRV 80
		 transportRoute(2)    -- ASSVAL: YRROFTRA 1
		 }
  ACCESS read-only
  STATUS mandatory
  DESCRIPTION
    " Describes the function of the route:
      onlyServerAccess (1) : the route is used for access to a specified server
			 port only.
      transportRoute  (2)  : the route leads to an endsystem
      Several bits may be set simultaneous."
  ::= { bcamRouteTabEntry 15 }
-- SNMPNAME: RFCT
-- ASSNAME: YRROFFLG
-- implemented

bcamRouteTabProcNetTyp OBJECT-TYPE
  SYNTAX INTEGER {
-- ASSMULTI:
		 gatewayProc(1), -- ASSVAL: YRROPNGP 1
		 neaProc(2),     -- ASSVAL: YRROPNNP 4
		 isoIpProc(4)    -- ASSVAL: YRROPNRP 16
		 }
  ACCESS read-only
  STATUS mandatory
  DESCRIPTION
    " Describes whether there are other intermediate systems necessary to be known by
      BCAM to reach the system described by this route.
      gatewayProc  (1) : an intermediate gateway system is used.
      neaProc      (2) : an intermediate NEA system is used.
      isoIpProc    (4) : an intermediate ISO or IP system is used.
      Several bits may be set simultaneous."
  ::= { bcamRouteTabEntry 16 }
-- SNMPNAME: RPNT
--  ASSNAME: YRROPNTY
-- implemented

bcamRouteTabMaxTsduLen OBJECT-TYPE
  SYNTAX Gauge
  ACCESS read-only
  STATUS mandatory
  DESCRIPTION
    " The maximum length of packets that can be sent over this route. "
  ::= { bcamRouteTabEntry 17 }
-- SNMPNAME: RMTL
-- ASSNAME: YRROTSDU
-- implemented

bcamRouteTabNameEndsystem OBJECT-TYPE
  SYNTAX DisplayString (SIZE(8)) -- ASSLEN: 9 VAR
  ACCESS read-only
  STATUS mandatory
  DESCRIPTION
    " The name of the remote system described by this route. "
  ::= { bcamRouteTabEntry 18 }
-- SNMPNAME: RNES
-- ASSNAME: YRROESNA
-- implemented

bcamRouteTabIso4WindowTimer OBJECT-TYPE
  SYNTAX Gauge -- ASSLEN: 2
  ACCESS read-only
  STATUS mandatory
  DESCRIPTION
    " The current value of the window timer for this route in seconds. "
  ::= { bcamRouteTabEntry 19 }
-- SNMPNAME: RIWT
-- ASSNAME: YRROWPER
-- implemented

bcamRouteTabIso4RetransTimer OBJECT-TYPE
  SYNTAX Gauge -- ASSLEN: 2
  ACCESS read-only
  STATUS mandatory
  DESCRIPTION
    " The current value of the retransmit timer for this route in seconds. "
  ::= { bcamRouteTabEntry 20 }
-- SNMPNAME: RIRT
-- ASSNAME: YRRORPER
-- implemented

bcamRouteTabAckTimer OBJECT-TYPE
  SYNTAX Gauge -- ASSLEN: 2
  ACCESS read-only
  STATUS mandatory
  DESCRIPTION
    " The current value of the acknowledgement timer for this route in seconds. "
  ::= { bcamRouteTabEntry 21 }
-- SNMPNAME: RACT
-- ASSNAME: YRROAKPE
-- implemented

bcamRouteTabErrorRecovTimer OBJECT-TYPE
  SYNTAX Gauge -- ASSLEN: 2
  ACCESS read-only
  STATUS mandatory
  DESCRIPTION
    " The current value of the error recovery timer for this route in seconds. "
  ::= { bcamRouteTabEntry 22 }
-- SNMPNAME: RERT
-- ASSNAME: YRROERPE
-- implemented

bcamRouteTabRejectTimer OBJECT-TYPE
  SYNTAX Gauge -- ASSLEN: 2
  ACCESS read-only
  STATUS mandatory
  DESCRIPTION
    " The current value of the reject timer for this route in seconds. "
  ::= { bcamRouteTabEntry 23 }
-- SNMPNAME: RRET
-- ASSNAME: YRRORJPE
-- implemented

bcamRouteTabExpedRetransTimer OBJECT-TYPE
  SYNTAX Gauge -- ASSLEN: 2
  ACCESS read-only
  STATUS mandatory
  DESCRIPTION
    " The current value of the expedited retransmit timer for this route in seconds. "
  ::= { bcamRouteTabEntry 24 }
-- SNMPNAME: REXT
-- ASSNAME: YRROEXPE
-- implemented

bcamRouteTabNameGateway OBJECT-TYPE
  SYNTAX DisplayString (SIZE(8)) -- ASSLEN: 9 VAR
  ACCESS read-only
  STATUS mandatory
  DESCRIPTION
    " The name of the intermediate system where protocol transitions, if necessary for this route, are done. "
  ::= { bcamRouteTabEntry 25 }
-- SNMPNAME: RNGA
-- ASSNAME: YRROGATE
-- implemented

bcamRouteTabNameX25Station OBJECT-TYPE
  SYNTAX DisplayString (SIZE(8)) -- ASSLEN: 9 VAR
  ACCESS read-only
  STATUS mandatory
  DESCRIPTION
    " The name of the station which performs the X25 net access. "
  ::= { bcamRouteTabEntry 26 }
-- SNMPNAME: RNXS
-- ASSNAME: YRROX25S
-- implemented

bcamRouteTabL3InputProfil OBJECT-TYPE
  SYNTAX INTEGER {
-- ASSSINGLE:
		 nea(1),     -- ASSVAL: YRRO3PNE 1
		 int0(2),    -- ASSVAL: YRRO3PI0 2
		 intf(3),    -- ASSVAL: YRRO3PIF 3
		 gateway(4), -- ASSVAL: YRRO3PGA 4
		 ip(5)       -- ASSVAL: YRRO3PIP 5
		 }
  ACCESS read-only
  STATUS mandatory
  DESCRIPTION
    " The input profile used on the network layer.
      nea       (1) : proprietary NEAN protocol.
      int0      (2) : protocol according ISO 8473 (inactive network layer).
      intf      (3) : protocol according ISO 8473.
      gateway   (4) : no network layer protocol used.
      ip        (5) : proctocol according RFC 791."

  ::= { bcamRouteTabEntry 27 }
-- SNMPNAME: RL3I
-- ASSNAME: YRRO3PRF
-- implemented

bcamRouteTabTransState OBJECT-TYPE
  SYNTAX INTEGER {
-- ASSSINGLE:
--                 notReady(0),                ASSVAL: YBAPSNOT 0
		 waitForTransferInit(1),    -- ASSVAL: YBAPSWIN 1
		 waitForReadyToTransfer(2), -- ASSVAL: YBAPSWAR 2
		 ready(3),                  -- ASSVAL: YBAPSRDY 3
		 notReady(4)                -- ASSVAL: YBAPSNOT 0
		 }
  ACCESS read-only
  STATUS mandatory
  DESCRIPTION
    " The current transfer state of this route as viewed by transport layer.
      notReady               (4) : no packets can be sent.
      waitForTransferInit    (1) : route may be initialised.
      waitForReadyToTransfer (2) : address resolution running
      ready                  (3) : packets may be sent "
  ::= { bcamRouteTabEntry 28 }
-- SNMPNAME: RTST
-- ASSNAME: YRROTSTA
-- implemented


bcamRouteTabOption OBJECT-TYPE
  SYNTAX INTEGER {
-- ASSMULTI:
		 delayedAckAllowed(1),   -- ASSVAL: YRROODAN 128
		 optimalSegmentSizeOn(2) -- ASSVAL: YRROOSSN 64
		 }
  ACCESS read-only
  STATUS mandatory
  DESCRIPTION
    " The currently valid options for this route (only valid for TCP).
      delayedAckAllowed    (1) : do not try do minimize the number of outgoing acknowledgements
      optimalSegmentSizeOn (2) : do not try do minimize the number of incoming acknowledgements
      Several bits may be set simultaneous."
  ::= { bcamRouteTabEntry 29 }
-- SNMPNAME: ROPT
-- ASSNAME: YRROOFLG
-- implemented

bcamRouteTabTyp OBJECT-TYPE
  SYNTAX INTEGER {
-- ASSSINGLE:
		 direct(1), -- ASSVAL: YRROTDIR 196
		 remote(2),  -- ASSVAL: YRROTREM 217
		 node(3)    -- ASSVAL: YRROTNOD 213
		 }
  ACCESS read-only
  STATUS mandatory
  DESCRIPTION
    " Describes how the remote system described by this route is reached.
      direct (1) : the remote system is connected directly to the local system (e.g via DAST).
      remote (2) : the remote system is reached via at least one router.
      node   (3) : the remote system is connected directly to ethernet or fddi node. "
  ::= { bcamRouteTabEntry 30 }
-- SNMPNAME: RRTY
-- ASSNAME: YRROTYPE
-- implemented

bcamRouteTabUsage OBJECT-TYPE
  SYNTAX INTEGER {
-- ASSMULTI:
--                 noIntermediate(0),  ASSVAL: NONE 0
		 gatewayRoute(1),   -- ASSVAL: YRROUFUG 2
		 intfIpRouter(2),   -- ASSVAL: YRROUFUR 4
		 neaRouter(4),      -- ASSVAL: YRROUFUN 8
		 int0Router(8),     -- ASSVAL: YRROUFU0 16
		 noIntermediate(16) -- ASSVAL: 0 0
		 }
  ACCESS read-only
  STATUS mandatory
  DESCRIPTION
    " Describes whether this route describes an intermediate system.
      noIntermediate (16) : no intermediate route
      gatewayRouter   (1) : route describes an intermediate system used as gateway
      intfIpRouter    (2) : route describes an INTF or an IP router
      neaRouter       (4) : route describes a NEA router
      int0Router      (8) : route describes an INT0 router

      Several bits may be set simultaneous."
  ::= { bcamRouteTabEntry 31 }
-- SNMPNAME: RRUS
-- ASSNAME: YRROUFLG
-- implemented

bcamRouteTabL3Subprofile OBJECT-TYPE
  SYNTAX INTEGER {
-- ASSMULTI:
		 rfc1042(1),     -- ASSVAL: YRRO3SIS 1
		 netConnLess(2), -- ASSVAL: YRRO3SCL 4
		 neaNetConn(4),  -- ASSVAL: YRRO3SNC 128
		 neattNetConn(8) -- ASSVAL: YRRO3STT 64
		 }
  ACCESS read-only
  STATUS mandatory
  DESCRIPTION
    " rfc1042      (1) : a layer 3 subprotocol according RFC1042 is used on this route.
      netConnLess  (2) : a connectionless layer 3 protocol is used on this route.
      neaNetConn   (4) : a NEA net connection is used on this route.
      neattNetConn (8) : a NEATT net connection is used on this route.
      Several bits may be set simultaneous."
  ::= { bcamRouteTabEntry 32 }
-- SNMPNAME: RL3S
-- ASSNAME: YRRO3SPF
-- implemented

bcamRouteTabCommandState OBJECT-TYPE
  SYNTAX INTEGER {
-- ASSMULTI:
-- ASSVAL: 0 means excluded
		 included(1), -- ASSVAL: YRROSINC 16
		 active(2)    -- ASSVAL: YRROSACT 128
		 }
  ACCESS read-only
  STATUS mandatory
  DESCRIPTION
    " The current state of this route caused by route specific commands.
      included   (1)  : a BCIN command was given successfully for this route.
      active     (2)  : a BCACT command was given successfully for this route.
      Several bits may be set simultaneous."
  ::= { bcamRouteTabEntry 33 }
-- SNMPNAME: RCST
-- ASSNAME: YRROSTAT
-- implemented

bcamRouteTabChangeState OBJECT-TYPE
  SYNTAX INTEGER {
-- ASSMULTI:
--                 generated(0),         ASSVAL: YRROCHGE 0
		 dynamic(1),          -- ASSVAL: YRROCHDY 1
		 defByProtocol(2),    -- ASSVAL: YRROCHRP 2
		 switchByProtocol(4), -- ASSVAL: YRROCHSW 4
		 changed(8),          -- ASSVAL: YRROCHCH 128
		 generated(16)        -- ASSVAL: YRROCHGE 0
		 }
  ACCESS read-only
  STATUS mandatory
  DESCRIPTION
    " Describes how the route was defined or modified.
      generated        (16) : the route has been defined by KOGS and not been modified.
      dynamic           (1) : the route was created dynamically by a BCIN command.
      defByProtocol     (2) : the route was defined by routing protocol.
      switchByProtocol  (4) : the route has been switched by routing protocol.
      changed           (8) : the route has been modified.

      Several bits may be set simultaneous."
  ::= { bcamRouteTabEntry 34 }
-- SNMPNAME: RCHS
-- ASSNAME: YRROCHST
-- implemented

bcamRouteTabIso9542 OBJECT-TYPE
  SYNTAX INTEGER {
-- ASSMULTI:
		 eshReceived(1),          -- ASSVAL: YRRORESH 1
		 ishReceived(2),          -- ASSVAL: YRRORISH 2
		 iso8473QueryReceived(4), -- ASSVAL: YRROQUCF 8
		 refreshRequired(8)       -- ASSVAL: YRROREFR 128
		 }
  ACCESS read-only
  STATUS mandatory
  DESCRIPTION
    " Describes the ISO9542 processing, if this route is an INTF route
      eshReceived          (1) : endsystem hello received
      ishReceived          (2) : intermediate system hello received.
      iso8473QueryReceived (4) : ISO 8473 query configuration request received.
      refreshRequired      (8) : refreshing of routing information is required.
      Several bits may be set simultaneous."
  ::= { bcamRouteTabEntry 35 }
-- SNMPNAME: RI95
-- ASSNAME: YRRO9542
-- implemented

bcamRouteTabMaxNetLength OBJECT-TYPE
  SYNTAX INTEGER {
-- ASSSINGLE:
		 ethernet(1), -- ASSVAL: YWRYMXNE 1
		 fddi(2)     -- ASSVAL: YWRYMXNF 2
		 }
  ACCESS read-only
  STATUS mandatory
  DESCRIPTION
    " The maximum length of a packet used on layer 3 (only valid for FDDI routes).
      ethernet (1) : the length will be limited to the maximum length for ethernet.
      fddi     (2) : the length will be limited to the maximum length for FDDI.
    "
  ::= { bcamRouteTabEntry 36 }
-- SNMPNAME: RMNL
-- ASSNAME: YRROMXN
-- implemented

bcamRouteTabState2 OBJECT-TYPE
  SYNTAX INTEGER {
-- ASSMULTI:
--                 silent(0),                  ASSVAL: YRROSSIL 0
		 testing(1),                -- ASSVAL: YRROSTST 16
		 working(2),                -- ASSVAL: YRROSWOR 32
		 waitAddrResolution(4),     -- ASSVAL: YRROSARP 64
		 lifeSupervisionFailed(8),  -- ASSVAL: YRROSFAI 128
		 silent(16)                 -- ASSVAL: YRROSSIL 0
		 }
  ACCESS read-only
  STATUS mandatory
  DESCRIPTION
    " Describes the state of the route viewed by routing protocols.
      silent                  (16) : route not yet or no more used.
      testing                  (1) : delivery problems on route detected.
      working                  (2) : route working.
      waitAddressResolution    (4) : waiting for address resolution.
      lifetimeSupervsionFailed (8) : lifetime supervision failed.
      Several bits may be set simultaneous."
  ::= { bcamRouteTabEntry 37 }
-- SNMPNAME: RST2
-- ASSNAME: YRROSTA2
-- implemented

bcamRouteTabDeactReason OBJECT-TYPE
  SYNTAX INTEGER {
-- ASSMULTI:
		 flush(1),        -- ASSVAL: YRRODFLR 1
		 supposedDown(2), -- ASSVAL: YRRODRSD 16
		 noArpReply(4)    -- ASSVAL: YRRODNAR 32
		 }
  ACCESS read-only
  STATUS mandatory
  DESCRIPTION
    " The reason for the deactivation of the route.
      flush        (1) : an ISO9542 protocol element that requests the invalidation of
			 the routing information has been received.
      supposedDown (2) : the route is supposed to be down (derived from state of TCP
			 protocol machine or ICMP message received).
      noArpReply   (4) : no arp reply has been received.

      Several bits may be set simultaneous."
  ::= { bcamRouteTabEntry 38 }
-- SNMPNAME: RDAR
-- ASSNAME: YRRODREA
-- implemented

bcamRouteTabSwitchType OBJECT-TYPE
  SYNTAX INTEGER {
-- ASSMULTI:
		 localRemote(1),     -- ASSVAL: YRROSWLR 1
		 remoteLocal(2),     -- ASSVAL: YRROSWRL 2
		 remoteRemote(4),    -- ASSVAL: YRROSWRR 4
		 lsapChanged(8),     -- ASSVAL: YRROSWLS 8
		 lanAddrChanged(16)  -- ASSVAL: YRROSWLL 16
		 }
  ACCESS read-only
  STATUS mandatory
  DESCRIPTION
    " The type of the last performed route switching.
      localRemote     (1) : the route has been changed from local to remote route.
      remoteLocal     (2) : the route has been changed from remote to local route.
      remoteRemote    (4) : the route has been changed from remote to remote route.
      lsapChanged     (8) : the route has been switched to another LSAPCB.
      lanAddrChanged (16) : the lan address of the route has been changed.
      Several bits may be set simultaneous."
  ::= { bcamRouteTabEntry 39 }
-- SNMPNAME: RSWT
-- ASSNAME: YRROSWTY
-- implemented

bcamRouteTabReasonCreation OBJECT-TYPE
  SYNTAX INTEGER {
-- ASSMULTI:
-- ASSVAL: 0 means route has been defined by generation
		 incomingData(1),    -- ASSVAL: YBTAECID 16
		 outgoingData(2),    -- ASSVAL: YBTAECOD 32
		 routingProtocol(4), -- ASSVAL: YBTAECRP 64
		 routingData(8)      -- ASSVAL: YBTAECRD 128
		 }
  ACCESS read-only
  STATUS mandatory
  DESCRIPTION
    " Describes the reason for the automatic creation of the route.
      incomingData    (1) : the route has been created because of incoming data.
      outgoingData    (2) : the route has been created because of outgoing data.
      routingProtocol (4) : the route has been created because of incoming routing protocol.
      routingData     (8) : the route has been created because of data to be routed.
      Several bits may be set simultaneous."
  ::= { bcamRouteTabEntry 40 }
-- SNMPNAME: RRAC
-- ASSNAME: YRROREAF
-- implemented

bcamRouteTabOrigLanAddress OBJECT-TYPE
  SYNTAX PhysAddress
  ACCESS read-only
  STATUS mandatory
  DESCRIPTION
    " The MAC address (if known) of the remote endsystem or the first intermediate
      system of this route as used when the route has been created. "
  ::= { bcamRouteTabEntry 41 }
-- SNMPNAME: ROLA
-- ASSNAME: YRROOLAN
-- implemented

bcamRouteTabLanAddress OBJECT-TYPE
  SYNTAX PhysAddress
  ACCESS read-only
  STATUS mandatory
  DESCRIPTION
    " The current MAC address (if known) of the remote endsystem or the first
      intermediate system of this route. "
  ::= { bcamRouteTabEntry 42 }
-- SNMPNAME: RLAA
-- ASSNAME: YRROLANA
-- implemented

bcamRouteTabTypAddress OBJECT-TYPE
  SYNTAX INTEGER {
-- ASSSINGLE:
		 nea(1),     -- ASSVAL: YRRO3PNE 1
		 intf(2),    -- ASSVAL: YRRO3PIF 3
		 streams(3), -- ASSVAL: YRRO3PIP 5
		 int0(4)     -- ASSVAL: YRRO3PI0 2
		 }
  ACCESS read-only
  STATUS mandatory
  DESCRIPTION
    "The type of address used for this route.
     nea     (1) : 2 byte (processor number and region number)
     intf    (2) : up to 20 byte full internet address
     streams (3) : 4 byte IP address
     int0    (4) : 6 byte MAC address"
  ::= { bcamRouteTabEntry 43 }
-- SNMPNAME: RTYA
-- ASSNAME: YRRO3PRF
-- implemented

bcamRouteTabLocalAddr OBJECT-TYPE
  SYNTAX OCTET STRING (SIZE(0..20)) -- ASSLEN: 22 VAR
  ACCESS read-only
  STATUS mandatory
  DESCRIPTION
    "The layer 3 address of the local system described by this route according to bcamRouteTabTypAddress."
  ::= { bcamRouteTabEntry 44 }
-- SNMPNAME: RLOA
-- ASSNAME: YRROLINK
-- implemented

bcamRouteTabRemoteAddr OBJECT-TYPE
  SYNTAX OCTET STRING (SIZE(0..20)) -- ASSLEN: 22 VAR
  ACCESS read-only
  STATUS mandatory
  DESCRIPTION
    "The layer 3 address of the remote system described by this route according to bcamRouteTabTypAddress."
  ::= { bcamRouteTabEntry 45 }
-- SNMPNAME: RREA
-- ASSNAME: YRRONPN# YRROOSA YRROIPA YRROLANA
-- implemented


bcamRouteTabOutPacketsDatas OBJECT-TYPE
  SYNTAX Counter
  ACCESS read-only
  STATUS mandatory
  DESCRIPTION
    " The number of packets sent over this route that contained at least one byte of user data. "
  ::= { bcamRouteTabEntry 46 }
-- SNMPNAME: ROPD
-- ASSNAME: YRROODAP
-- implemented

bcamRouteTabOutPacketsFlowControls OBJECT-TYPE
  SYNTAX Counter
  ACCESS read-only
  STATUS mandatory
  DESCRIPTION
    " The number of packets sent over this route that contained only flow control information. "
  ::= { bcamRouteTabEntry 47 }
-- SNMPNAME: ROPF
-- ASSNAME: YRROOWIP
-- implemented

bcamRouteTabInPacketsDatas OBJECT-TYPE
  SYNTAX Counter
  ACCESS read-only
  STATUS mandatory
  DESCRIPTION
    " The number of packets received on this route that contained at least one byte of user data. "
  ::= { bcamRouteTabEntry 48 }
-- SNMPNAME: RIPD
-- ASSNAME: YRROIDAP
-- implemented

bcamRouteTabInPacketsFlowControls OBJECT-TYPE
  SYNTAX Counter
  ACCESS read-only
  STATUS mandatory
  DESCRIPTION
    " The number of packets received on this route that contained only flow control information. "
  ::= { bcamRouteTabEntry 49 }
-- SNMPNAME: RIPF
-- ASSNAME: YRROIWIP
-- implemented

bcamRouteTabOutRetransPackets OBJECT-TYPE
  SYNTAX Counter
  ACCESS read-only
  STATUS mandatory
  DESCRIPTION
    " The number of packets sent over this route that contained at least one byte of user data that
      were already sent. "
  ::= { bcamRouteTabEntry 50 }
-- SNMPNAME: RORP
-- ASSNAME: YRRORETR
-- implemented

bcamRouteTabInDetectedGaps OBJECT-TYPE
  SYNTAX Counter
  ACCESS read-only
  STATUS mandatory
  DESCRIPTION
    " The number of packets received where there was a gap between the highest already received byte
      and the lowest byte in the packet.  "
  ::= { bcamRouteTabEntry 51 }
-- SNMPNAME: RIDG
-- ASSNAME: YRROGAPS
-- implemented

bcamRouteTabInDuplicatedPackets OBJECT-TYPE
  SYNTAX Counter
  ACCESS read-only
  STATUS mandatory
  DESCRIPTION
    " The number of packets received that contained at least one byte of user data that has already been received  "
  ::= { bcamRouteTabEntry 52 }
-- SNMPNAME: RIDP
-- ASSNAME: YRRODUPL
-- implemented

bcamRouteTabInIncorrectPackets OBJECT-TYPE
  SYNTAX Counter
  ACCESS read-only
  STATUS mandatory
  DESCRIPTION
    " The number of erroneous packets received on this route. "
  ::= { bcamRouteTabEntry 53 }
-- SNMPNAME: RIIP
-- ASSNAME: YRROIERP
-- implemented

bcamRouteTabRoundTripTimeClosed OBJECT-TYPE
  SYNTAX INTEGER (0..65535)
  ACCESS read-only
  STATUS mandatory
  DESCRIPTION
    " The average round trip time on this route for meanwhile closed connections. "
  ::= { bcamRouteTabEntry 54 }
-- SNMPNAME: RRTT
-- ASSNAME: YRRORTT
-- implemented

bcamRouteTabRoundTripTimeCurrent OBJECT-TYPE
  SYNTAX INTEGER (0..65535)
  ACCESS read-only
  STATUS mandatory
  DESCRIPTION
    " The average round trip time on this route for currently open connections. "
  ::= { bcamRouteTabEntry 55 }
-- SNMPNAME: RRTC
-- ASSNAME: YC2RTT
-- implemented

bcamRouteTabArpReqSend OBJECT-TYPE
  SYNTAX INTEGER
  ACCESS read-only
  STATUS mandatory
  DESCRIPTION
    "The number of ARP requests sent for this route."
  ::= { bcamRouteTabEntry 56 }
-- SNMPNAME: RARS
-- ASSNAME: YRRO#SAQ
-- implemented

bcamRouteTabArpRepSend OBJECT-TYPE
  SYNTAX INTEGER
  ACCESS read-only
  STATUS mandatory
  DESCRIPTION
    "The number of ARP replies sent for this route."
  ::= { bcamRouteTabEntry 57 }
-- SNMPNAME: RAPS
-- ASSNAME: YRRO#SAP
-- implemented

bcamRouteTabArpReqRec OBJECT-TYPE
  SYNTAX INTEGER
  ACCESS read-only
  STATUS mandatory
  DESCRIPTION
    "The number of ARP requests received for this route."
  ::= { bcamRouteTabEntry 58 }
-- SNMPNAME: RARR
-- ASSNAME: YRRO#RAQ
-- implemented

bcamRouteTabArpRepRec OBJECT-TYPE
  SYNTAX INTEGER
  ACCESS read-only
  STATUS mandatory
  DESCRIPTION
    "The number of ARP replies received for this route."
  ::= { bcamRouteTabEntry 59 }
-- SNMPNAME: RAPR
-- ASSNAME: YRRO#RAP
-- implemented

bcamRouteTabIcmpReq OBJECT-TYPE
  SYNTAX INTEGER
  ACCESS read-only
  STATUS mandatory
  DESCRIPTION
    "The number of ICMP ECHO requests sent for this route."
  ::= { bcamRouteTabEntry 60 }
-- SNMPNAME: RICQ
-- ASSNAME: YRRO#SIQ
-- implemented

bcamRouteTabIcmpReply OBJECT-TYPE
  SYNTAX INTEGER
  ACCESS read-only
  STATUS mandatory
  DESCRIPTION
    "The number of ICMP ECHO replies received for this route."
  ::= { bcamRouteTabEntry 61 }
-- SNMPNAME: RICR
-- ASSNAME: YRRO#RIP
-- implemented

bcamRouteTabIcmpRedirect OBJECT-TYPE
  SYNTAX INTEGER
  ACCESS read-only
  STATUS mandatory
  DESCRIPTION
    "The number of ICMP redirects received for this route."
  ::= { bcamRouteTabEntry 62 }
-- SNMPNAME: RICD
-- ASSNAME: YRRO#RIR
-- implemented

bcamRouteTabSwitched OBJECT-TYPE
  SYNTAX INTEGER
  ACCESS read-only
  STATUS mandatory
  DESCRIPTION
    "The number of route switchings performed for this route."
  ::= { bcamRouteTabEntry 63 }
-- SNMPNAME: RSWI
-- ASSNAME: YRRO#SWT
-- implemented

bcamRouteTabDown OBJECT-TYPE
  SYNTAX INTEGER
  ACCESS read-only
  STATUS mandatory
  DESCRIPTION
    "The number of times the state of the route has changed to not working."
  ::= { bcamRouteTabEntry 64 }
-- SNMPNAME: RRDW
-- ASSNAME: YRRO#DWN
-- implemented

bcamRouteTabOspfHello OBJECT-TYPE
  SYNTAX INTEGER
  ACCESS read-only
  STATUS mandatory
  DESCRIPTION
    "The number of OSPF HELLOs received for this route."
  ::= { bcamRouteTabEntry 65 }
-- SNMPNAME: ROSH
-- ASSNAME: YRRO#ROH
-- implemented

bcamRouteTabPacketNoConn OBJECT-TYPE
  SYNTAX INTEGER (0..65535) -- ASSLEN: 2
  ACCESS read-only
  STATUS mandatory
  DESCRIPTION
    "The number of packets received on this route that could not be assigned to a connection."
  ::= { bcamRouteTabEntry 66 }
-- SNMPNAME: RRNC
-- ASSNAME: YBAPNCEP
-- implemented

bcamRouteTabPacketInternDiscon OBJECT-TYPE
  SYNTAX INTEGER (0..65535) -- ASSLEN: 2
  ACCESS read-only
  STATUS mandatory
  DESCRIPTION
    "The number of packets received on this route that resulted in an abortion of a connection."
  ::= { bcamRouteTabEntry 67 }
-- SNMPNAME: RRID
-- ASSNAME: YBAPTDIS
-- implemented

bcamRouteTabPacketBadProtocol OBJECT-TYPE
  SYNTAX INTEGER (0..65535) -- ASSLEN: 2
  ACCESS read-only
  STATUS mandatory
  DESCRIPTION
    "The number of packets received on this route that were invalid."
  ::= { bcamRouteTabEntry 68 }
-- SNMPNAME: RRBP
-- ASSNAME: YBAPPERR
-- implemented

bcamRouteTabConnReqOut OBJECT-TYPE
  SYNTAX INTEGER (0..65535) -- ASSLEN: 2
  ACCESS read-only
  STATUS mandatory
  DESCRIPTION
    "The number of connection requests sent on this route."
  ::= { bcamRouteTabEntry 69 }
-- SNMPNAME: RSCR
-- ASSNAME: YRROCROU
-- implemented

bcamRouteTabConnReqOutAck OBJECT-TYPE
  SYNTAX INTEGER (0..65535) -- ASSLEN: 2
  ACCESS read-only
  STATUS mandatory
  DESCRIPTION
    "The number of connection requests sent on this route that have been acknowledeged by the remote transport system."
  ::= { bcamRouteTabEntry 70 }
-- SNMPNAME: RSCA
-- ASSNAME: YRROCRAK
-- implemented

bcamRouteTabConnReqOutRej OBJECT-TYPE
  SYNTAX INTEGER (0..65535) -- ASSLEN: 2
  ACCESS read-only
  STATUS mandatory
  DESCRIPTION
    "The number of connection requests sent on this route that have been rejected by the remote transport system."
  ::= { bcamRouteTabEntry 71 }
-- SNMPNAME: RSCJ
-- ASSNAME: YRROCRJI
-- implemented

bcamRouteTabConnReqIn OBJECT-TYPE
  SYNTAX INTEGER (0..65535) -- ASSLEN: 2
  ACCESS read-only
  STATUS mandatory
  DESCRIPTION
    "The number of connection requests received on this route."
  ::= { bcamRouteTabEntry 72 }
-- SNMPNAME: RRCR
-- ASSNAME: YRROCRIN
-- implemented

bcamRouteTabConnReqInAck OBJECT-TYPE
  SYNTAX INTEGER (0..65535) -- ASSLEN: 2
  ACCESS read-only
  STATUS mandatory
  DESCRIPTION
    "The number of connection requests received on this route that have been acknowledged by the local transport system."
  ::= { bcamRouteTabEntry 73 }
-- SNMPNAME: RRCA
-- ASSNAME: YRROCCOU
-- implemented

bcamRouteTabConnReqInRej OBJECT-TYPE
  SYNTAX INTEGER (0..65535) -- ASSLEN: 2
  ACCESS read-only
  STATUS mandatory
  DESCRIPTION
    "The number of connection requests received on this route that have been rejected by the local transport system."
  ::= { bcamRouteTabEntry 74 }
-- SNMPNAME: RRCJ
-- ASSNAME: YRROCRJO
-- implemented

bcamRouteTabDisconnOut OBJECT-TYPE
  SYNTAX INTEGER (0..65535) -- ASSLEN: 2
  ACCESS read-only
  STATUS mandatory
  DESCRIPTION
    "The number of disconnect requests sent."
  ::= { bcamRouteTabEntry 75 }
-- SNMPNAME: RSDR
-- ASSNAME: YRRODROU
-- implemented

bcamRouteTabDisconnOutAck OBJECT-TYPE
  SYNTAX INTEGER (0..65535) -- ASSLEN: 2
  ACCESS read-only
  STATUS mandatory
  DESCRIPTION
    "The number of disconnect requests sent that have been acknowledged by the remote transport system."
  ::= { bcamRouteTabEntry 76 }
-- SNMPNAME: RSDA
-- ASSNAME: YRRODRAK
-- implemented

bcamRouteTabDisconnIn OBJECT-TYPE
  SYNTAX INTEGER (0..65535) -- ASSLEN: 2
  ACCESS read-only
  STATUS mandatory
  DESCRIPTION
    "The number of disconnect requests received."
  ::= { bcamRouteTabEntry 77 }
-- SNMPNAME: RRDR
-- ASSNAME: YRRODRIN
-- implemented

bcamRouteTabDisconnInAck OBJECT-TYPE
  SYNTAX INTEGER (0..65535) -- ASSLEN: 2
  ACCESS read-only
  STATUS mandatory
  DESCRIPTION
    "The number of disconnect requests received that have been acknowledged by the local transport system."
  ::= { bcamRouteTabEntry 78 }
-- SNMPNAME: RRDA
-- ASSNAME: YRRODCOU
-- implemented

bcamRouteTabNumberLink OBJECT-TYPE
  SYNTAX INTEGER
  ACCESS read-only
  STATUS mandatory
  DESCRIPTION
    " The number of the interface that is used for this route. "
  ::= { bcamRouteTabEntry 79 }
-- SNMPNAME: RNLI
-- ASSNAME: YRROLSAP

bcamRouteTabArpFlag OBJECT-TYPE
  SYNTAX INTEGER {
-- ASSMULTI:
		 off(1),  -- ASSVAL: YBTARPNO 128
		 on(2),   -- ASSVAL: YBTARPTI 32
		 quiet(4) -- ASSVAL: YBTARPQU 64
		 }
  ACCESS read-only
  STATUS mandatory
  DESCRIPTION
    " The ARP state of the route.
      off   (1) : no usage of ARP.
      on    (2) : periodic usage of ARP.
      quiet (4) : ARP will only be used if no connection oriented data were transferred during the
		  last ARP period.
      Several bits may be set simultaneous."
  ::= { bcamRouteTabEntry 80 }
-- SNMPNAME: RAST
-- ASSNAME: YRROARPF

bcamRouteTabNsduLen OBJECT-TYPE
  SYNTAX INTEGER
  ACCESS read-only
  STATUS mandatory
  DESCRIPTION
    " The length of a network service data unit used on this route "
  ::= { bcamRouteTabEntry 81 }
-- SNMPNAME: RCNL
-- ASSNAME: YRRONSDU
-- NSDU Len YRRONSDU

bcamRouteTabMinNsduLen OBJECT-TYPE
  SYNTAX INTEGER
  ACCESS read-only
  STATUS mandatory
  DESCRIPTION
    " The minimum maximal length of a network service data unit used on this route "
  ::= { bcamRouteTabEntry 82 }
-- SNMPNAME: RNNL
-- ASSNAME: YRRONSMI

bcamRouteTabMaxNsduLen OBJECT-TYPE
  SYNTAX INTEGER
  ACCESS read-only
  STATUS mandatory
  DESCRIPTION
    " The maximum maximal length of a network service data unit used on this route "
  ::= { bcamRouteTabEntry 83 }
-- SNMPNAME: RXNL
-- ASSNAME: YRRONSMX



-- the Interface group

  bcamIfNumTable OBJECT-TYPE
    SYNTAX INTEGER
    ACCESS read-only
    STATUS mandatory
    DESCRIPTION
      "  "
  ::= { bcamIf 1 }
-- SNMPNAME: LNTB
-- ASSNAME:


  bcamIfTab OBJECT-TYPE
    SYNTAX SEQUENCE OF LinkEntry
    ACCESS not-accessible
    STATUS mandatory
    DESCRIPTION
      "Table of all interfaces"
  ::= { bcamIf 2 }
-- SNMPNAME:
-- ASSNAME:

  bcamIfTabEntry OBJECT-TYPE
    SYNTAX LinkEntry
    ACCESS not-accessible
    STATUS mandatory
    DESCRIPTION
      "Information about an interface"
    INDEX {
      bcamIfTabNumbers
      }
  ::= { bcamIfTab 1 }
-- SNMPNAME:
-- ASSNAME:

  LinkEntry ::=
    SEQUENCE {
    bcamIfTabNumbers Counter ,
    bcamIfTabName DisplayString (SIZE(8)),
    bcamIfTabProfile INTEGER ,
    bcamIfTabMnemonicWrite DisplayString (SIZE(4)),
    bcamIfTabMnemonicRead DisplayString (SIZE(4)),
    bcamIfTabLanAddress PhysAddress ,
    bcamIfTabConfigUpdate INTEGER ,
    bcamIfTabMaxLpdu INTEGER ,
    bcamIfTabL2Monitoring INTEGER ,
    bcamIfTabDevice INTEGER ,
    bcamIfTabAdminState INTEGER ,
    bcamIfTabCurrentState INTEGER ,
    bcamIfTabMode INTEGER ,
    bcamIfTabPortName DisplayString (SIZE(8)),
    bcamIfTabLenTraceOut INTEGER (0..4096),
    bcamIfTabLenTraceIn INTEGER (0..4096),
    bcamIfTabNumRouteSwitchings INTEGER ,
    bcamIfTabTimeLastChange INTEGER ,
    bcamIfTabMnemonicDiag DisplayString (SIZE(4)),
    bcamIfTabNumMulticastAddr INTEGER ,
    bcamIfTabMulticastAddr1 PhysAddress ,
    bcamIfTabMulticastAddr2 PhysAddress ,
    bcamIfTabMulticastAddr3 PhysAddress ,
    bcamIfTabMulticastAddr4 PhysAddress ,
    bcamIfTabMulticastAddr5 PhysAddress ,
    bcamIfTabMulticastAddr6 PhysAddress ,
    bcamIfTabMulticastAddr7 PhysAddress ,
    bcamIfTabMulticastAddr8 PhysAddress ,
    bcamIfTabMulticastAddr9 PhysAddress ,
    bcamIfTabMulticastAddr10 PhysAddress ,
    bcamIfTabNumNeaAddress INTEGER ,
    bcamIfTabNeaAddress1 OCTET STRING (SIZE(2)),
    bcamIfTabNeaAddress2 OCTET STRING (SIZE(2)),
    bcamIfTabNeaAddress3 OCTET STRING (SIZE(2)),
    bcamIfTabNeaAddress4 OCTET STRING (SIZE(2)),
    bcamIfTabNeaAddress5 OCTET STRING (SIZE(2)),
    bcamIfTabNeaAddress6 OCTET STRING (SIZE(2)),
    bcamIfTabNumIpAddress INTEGER ,
    bcamIfTabIpAddress1 IpAddress ,
    bcamIfTabIpAddress2 IpAddress ,
    bcamIfTabIpAddress3 IpAddress ,
    bcamIfTabIpAddress4 IpAddress ,
    bcamIfTabIpAddress5 IpAddress ,
    bcamIfTabIpAddress6 IpAddress ,
    bcamIfTabNumInt0Address INTEGER ,
    bcamIfTabInt0Address1 PhysAddress ,
    bcamIfTabInt0Address2 PhysAddress ,
    bcamIfTabInt0Address3 PhysAddress ,
    bcamIfTabInt0Address4 PhysAddress ,
    bcamIfTabInt0Address5 PhysAddress ,
    bcamIfTabInt0Address6 PhysAddress ,
    bcamIfTabNumIntfAddress INTEGER ,
    bcamIfTabIntfAddress1 OCTET STRING (SIZE(0..20)),
    bcamIfTabIntfAddress2 OCTET STRING (SIZE(0..20)),
    bcamIfTabIntfAddress3 OCTET STRING (SIZE(0..20)),
    bcamIfTabIntfAddress4 OCTET STRING (SIZE(0..20)),
    bcamIfTabIntfAddress5 OCTET STRING (SIZE(0..20)),
    bcamIfTabIntfAddress6 OCTET STRING (SIZE(0..20)),
    bcamIfTabBytesOutHighs Counter ,
    bcamIfTabBytesOutLows Counter ,
    bcamIfTabBytesInHighs Counter ,
    bcamIfTabBytesInLows Counter ,
    bcamIfTabIOsOutHighs Counter ,
    bcamIfTabIOsOutLows Counter ,
    bcamIfTabIOsInHighs Counter ,
    bcamIfTabIOsInLows Counter ,
    bcamIfTabOutputStops Counter ,
    bcamIfTabInputStops Counter ,
    bcamIfTabIOErrorOuts Counter ,
    bcamIfTabIOErrorIns Counter ,
    bcamIfTabPacketsNotReceiveds Counter ,
    bcamIfTabInPacketsLanHighs Counter ,
    bcamIfTabInPacketsLanLows Counter ,
    bcamIfTabOutPacketsLanHighs Counter ,
    bcamIfTabOutPacketsLanLows Counter ,
    bcamIfTabUnicastInHighs Counter ,
    bcamIfTabUnicastInLows Counter ,
    bcamIfTabUnicastOutHighs Counter ,
    bcamIfTabUnicastOutLows Counter ,
    bcamIfTabMulticastInHighs Counter ,
    bcamIfTabMulticastInLows Counter ,
    bcamIfTabMulticastOutHighs Counter ,
    bcamIfTabMulticastOutLows Counter ,
    bcamIfTabErrorPacketIns Counter ,
    bcamIfTabErrorPacketOuts Counter ,
    bcamIfTabDiscardIns Counter ,
    bcamIfTabDiscardOuts Counter ,
    bcamIfTabUnknownProtoIns Counter,
    bcamIfTabTraceState INTEGER,
    bcamIfTabTraceNumberBuffer INTEGER,
    bcamIfTabTraceBufferLen INTEGER


      }

bcamIfTabNumbers OBJECT-TYPE
  SYNTAX INTEGER -- ASSLEN: 2
  ACCESS read-only
  STATUS mandatory
  DESCRIPTION
    "A definite identifier for the interface.
     Serves for references from other tables"
  ::= { bcamIfTabEntry 1 }
-- SNMPNAME: LNUM
-- ASSNAME: YRLSNID
-- implemented

bcamIfTabName OBJECT-TYPE
  SYNTAX DisplayString (SIZE(8)) -- ASSLEN: 9 VAR
  ACCESS read-only
  STATUS mandatory
  DESCRIPTION
    " The name of this interface "
  ::= { bcamIfTabEntry 2 }
-- SNMPNAME: LNAM
-- ASSNAME: YRLSLTGN
-- implemented

bcamIfTabProfile OBJECT-TYPE
  SYNTAX INTEGER {
-- ASSSINGLE:
		 nealkp(1),  -- ASSVAL: YRLS2PNP 1
		 nealke(2),  -- ASSVAL: YRLS2PNE 2
		 nealkeS(3), -- ASSVAL: YRLS2PN3 3
		 nealkh(4),  -- ASSVAL: YRLS2PNH 4
		 llc1(5),    -- ASSVAL: YRLS2PL1 5
		 sinix(6),   -- ASSVAL: YRLS2PSI 6
		 fddi(7)     -- ASSVAL: YRLS2PLF 7
		 }
  ACCESS read-only
  STATUS mandatory
  DESCRIPTION
    " The layer 2 profile of this interface
      nealkp  (1) : proprietary link protocol with permanent dialog.
      nealke  (2) : proprietary event driven link protocol to BS2000 system.
      nealkeS (3) : proprietary event driven link protocol to System 6000.
      nealkh  (4) : a HDLC balanced link protocol (duplex mode).
      llc1    (5) : CSMA/CD link protocol.
      sinix   (6) : proprietary link protocol to SINIX port.
      fddi    (7) : FDDI link protocol.
    "
  ::= { bcamIfTabEntry 3 }
-- SNMPNAME: LPRF
-- ASSNAME: YRLS2PRF
-- implemented

bcamIfTabMnemonicWrite OBJECT-TYPE
  SYNTAX DisplayString (SIZE(4)) -- ASSLEN: 5 VAR
  ACCESS read-only
  STATUS mandatory
  DESCRIPTION
    " The device mnemonic for write operations "
  ::= { bcamIfTabEntry 4 }
-- SNMPNAME: LMWR
-- ASSNAME: YRLSDVWR
-- implemented

bcamIfTabMnemonicRead OBJECT-TYPE
  SYNTAX DisplayString (SIZE(4)) -- ASSLEN: 5 VAR
  ACCESS read-only
  STATUS mandatory
  DESCRIPTION
    " The device mnemonic for read operations "
  ::= { bcamIfTabEntry 5 }
-- SNMPNAME: LMRE
-- ASSNAME: YRLSDVRE
-- implemented

bcamIfTabLanAddress OBJECT-TYPE
  SYNTAX PhysAddress
  ACCESS read-only
  STATUS mandatory
  DESCRIPTION
    " The MAC address (if supported) "
  ::= { bcamIfTabEntry 6 }
-- SNMPNAME: LLAD
-- ASSNAME: YRLSLANA
-- implemented

bcamIfTabConfigUpdate OBJECT-TYPE
  SYNTAX INTEGER {
-- ASSMULTI:
--                 updateAllowed(0),     ASSVAL: YRLSCNAL 0
		 updateForbidden(1),  -- ASSVAL: YRLSCNNO 1
		 primaryRequested(2), -- ASSVAL: YRLSCNPR 2
		 updateAllowed(4)     -- ASSVAL: YRLSCNAL 0
		 }
  ACCESS read-only
  STATUS mandatory
  DESCRIPTION
    "Describes whether assigned routes are allowed to be switched from this to an alternative interface.
     updateAllowed    (4) : switching allowed
     updateForbidden  (1) : switching forbidden
     primaryRequested (2) : switch back of all routes original assigned to this interface requested

      Several bits may be set simultaneous."
  ::= { bcamIfTabEntry 7 }
-- SNMPNAME: LCFU
-- ASSNAME: YRLSCNUP
-- implemented

bcamIfTabMaxLpdu OBJECT-TYPE
  SYNTAX INTEGER {
-- ASSSINGLE :
		 ethernet(1514),  -- ASSVAL: YRLSLPDE 1514
		 fddi(4494),      -- ASSVAL: YRLSLPDF 4494
		 atm(65535),      -- ASSVAL: YRLSLPDA 65535
		 nealkh(65549),   -- ASSVAL: YRLSLPDN 65549
		 nealkp(4113),    -- ASSVAL: YRLSLPDP 4113
--                 oclink(65535),    ASSVAL: YRLSLPDO 65535
--                 sinix(4113),      ASSVAL: YRLSLPDS 4113
		 maxReass(16392)  -- ASSVAL: YRLSLPDR 16392
		 }
  ACCESS read-only
  STATUS mandatory
  DESCRIPTION
    " The maximum length of a link protocol data unit depending on bcamIfTabProfile.
      ethernet  (1514) :  1514 bytes
      fddi      (4494) :  4494 bytes
      atm      (65535) : 65535 bytes
      nealkh   (65549) : 65549 bytes
      nealkp    (4113) :  4113 bytes
      maxReass (16392) : 16392 bytes

    "
  ::= { bcamIfTabEntry 8 }
-- SNMPNAME: LMLP
-- ASSNAME: YRLSLPDU
-- implemented

bcamIfTabL2Monitoring OBJECT-TYPE
  SYNTAX INTEGER {
-- ASSMULTI:
--                 off(0),  ASSVAL: 0 0
		 on(1),  -- ASSVAL: YRLSMMO2 2
		 off(2)  -- ASSVAL: 0 0
		 }
  ACCESS read-only
  STATUS mandatory
  DESCRIPTION
    " The state of the layer 2 monitoring.
      on  (1) : layer 2 monitoring is running.
      off (2) : layer 2 monitoring is not running."
  ::= { bcamIfTabEntry 9 }
-- SNMPNAME: LMON
-- ASSNAME: YRLSMFLG
-- implemented

bcamIfTabDevice OBJECT-TYPE
  SYNTAX INTEGER {
-- ASSMULTI:
		 esconCtc(1) -- ASSVAL: YRLSDVES 128
		 }
  ACCESS read-only
  STATUS mandatory
  DESCRIPTION
    " Describes whether the interface is an ESCON channel to channel adapter.
      esconCtc (1) : the interface is an ESCON channel to channel adapter.
  "
  ::= { bcamIfTabEntry 10 }
-- SNMPNAME: LDEV
-- ASSNAME: YRLSDVFG
-- implemented

bcamIfTabAdminState OBJECT-TYPE
  SYNTAX INTEGER {
-- ASSSINGLE:
--                 none(0),      ASSVAL: YRLSS1NO 0
		 included(1), -- ASSVAL: YRLSSINC 201
		 active(2),   -- ASSVAL: YRLSSACT 193
		 excluded(4)  -- ASSVAL: YRLSSEXC 0
		 }
  ACCESS read-only
  STATUS mandatory
  DESCRIPTION
    " The administrative state of this interface requested by commands.
      excluded (4) : no BCIN command given
      included (1) : BCIN command given
      active   (2) : BCACT command given

      "
  ::= { bcamIfTabEntry 11 }
-- SNMPNAME: LAST
-- ASSNAME: YRLSSTAT
-- implemented

bcamIfTabCurrentState OBJECT-TYPE
  SYNTAX INTEGER {
-- ASSMULTI:
--                 none(0),          ASSVAL: YRLSS2NO X'00'
		 waitForAct(1),   -- ASSVAL: YRLSSWFA X'01'
		 working(2),      -- ASSVAL: YRLSSWOR X'02'
		 waitForDeact(4), -- ASSVAL: YRLSSWFD X'04'
		 none(8)          -- ASSVAL: YRLSS2NO X'00'
		 }
  ACCESS read-only
  STATUS mandatory
  DESCRIPTION
    " The actual working state of this interface
      none         (8) : interface not working
      waitForAct   (1) : activation in progress
      working      (2) : interface working
      waitForDeact (4) : deactivation in progress

      Several bits may be set simultaneous."
  ::= { bcamIfTabEntry 12 }
-- SNMPNAME: LCST
-- ASSNAME: YRLSSTA2
-- implemented

bcamIfTabMode OBJECT-TYPE
  SYNTAX INTEGER {
-- ASSMULTI:
		 stopModeOn(16), -- ASSVAL: YRLSMSTO 128
		 slowPollOn(8),  -- ASSVAL: YRLSMSLO 8
		 shortWaitOn(4), -- ASSVAL: YRLSMSAW 4
		 multicastOn(2), -- ASSVAL: YRLSMMCO 2
		 broadcastOn(1)  -- ASSVAL: YRLSMBCO 1
		 }
  ACCESS read-only
  STATUS mandatory
  DESCRIPTION
    "Describes the operational parameters of this interface
     stopModeOn  (16) : stop PDN in case of abnormal deactivation
     slowPollOn   (8) : automatic reactivation shall be tried
     shortWaitOn  (4) : stop activation after timeout
     multicastOn  (2) : evaluate multicasts
     broadcastOn  (1) : evaluate broadcasts

      Several bits may be set simultaneous."
  ::= { bcamIfTabEntry 13 }
-- SNMPNAME: LMOD
-- ASSNAME: YRLSLSMF
-- implemented

bcamIfTabPortName OBJECT-TYPE
  SYNTAX DisplayString (SIZE(8)) -- ASSLEN: 9 VAR
  ACCESS read-only
  STATUS mandatory
  DESCRIPTION
    "The port name of this interface "
  ::= { bcamIfTabEntry 14 }
-- SNMPNAME: LPNM
-- ASSNAME: YRLSPNAM
-- implemented

bcamIfTabLenTraceOut OBJECT-TYPE
  SYNTAX INTEGER (0..4096) -- ASSLEN: 2
  ACCESS read-only
  STATUS mandatory
  DESCRIPTION
    " The maximum length of layer 2 data to be traced in a trace entry for output. "
  ::= { bcamIfTabEntry 15 }
-- SNMPNAME: LLTO
-- ASSNAME: YRLSTDLO
-- implemented

bcamIfTabLenTraceIn OBJECT-TYPE
  SYNTAX INTEGER (0..4096) -- ASSLEN: 2
  ACCESS read-only
  STATUS mandatory
  DESCRIPTION
    " The maximum length of layer 2 data to be traced in a trace entry for input. "
  ::= { bcamIfTabEntry 16 }
-- SNMPNAME: LLTI
-- ASSNAME: YRLSTDLI
-- implemented

bcamIfTabNumRouteSwitchings OBJECT-TYPE
  SYNTAX INTEGER
  ACCESS read-only
  STATUS mandatory
  DESCRIPTION
    " The number of route switchings performed for this interface "
  ::= { bcamIfTabEntry 17 }
-- SNMPNAME: LNSW
-- ASSNAME: YRLS#SWT
-- implemented

bcamIfTabTimeLastChange OBJECT-TYPE
  SYNTAX INTEGER
  ACCESS read-only
  STATUS mandatory
  DESCRIPTION
    " The time interval (in seconds) since the last change of the working state of this interface "
  ::= { bcamIfTabEntry 18 }
-- SNMPNAME: LTLC
-- ASSNAME: YRLSTILC
-- implemented

bcamIfTabMnemonicDiag OBJECT-TYPE
  SYNTAX DisplayString (SIZE(4)) -- ASSLEN: 5 VAR
  ACCESS read-only
  STATUS mandatory
  DESCRIPTION
    " The device mnemonic for diagnosis. "
  ::= { bcamIfTabEntry 19 }
-- SNMPNAME: LMDI
-- ASSNAME: YRLSDVDI
-- implemented

bcamIfTabNumMulticastAddr OBJECT-TYPE
  SYNTAX INTEGER  -- ASSLEN: 1
  ACCESS read-only
  STATUS mandatory
  DESCRIPTION
    " The number of multicast addresses enabled for this interface. "
  ::= { bcamIfTabEntry 20 }
-- SNMPNAME: LNMC
-- ASSNAME: YRLS#MUL
-- implemented

bcamIfTabMulticastAddr1 OBJECT-TYPE
  SYNTAX PhysAddress
  ACCESS read-only
  STATUS mandatory
  DESCRIPTION
    " multicast address 1 or zero "
  ::= { bcamIfTabEntry 21 }
-- SNMPNAME: LMC1
-- ASSNAME: YRLSMUL1
-- implemented

bcamIfTabMulticastAddr2 OBJECT-TYPE
  SYNTAX PhysAddress
  ACCESS read-only
  STATUS mandatory
  DESCRIPTION
    " multicast address 2 "
  ::= { bcamIfTabEntry 22 }
-- SNMPNAME: LMC2
-- ASSNAME: YRLSMUL2
-- implemented

bcamIfTabMulticastAddr3 OBJECT-TYPE
  SYNTAX PhysAddress
  ACCESS read-only
  STATUS mandatory
  DESCRIPTION
    " multicast address 3 "
  ::= { bcamIfTabEntry 23 }
-- SNMPNAME: LMC3
-- ASSNAME: YRLSMUL3
-- implemented

bcamIfTabMulticastAddr4 OBJECT-TYPE
  SYNTAX PhysAddress
  ACCESS read-only
  STATUS mandatory
  DESCRIPTION
    " multicast address 4 "
  ::= { bcamIfTabEntry 24 }
-- SNMPNAME: LMC4
-- ASSNAME: YRLSMUL4
-- implemented

bcamIfTabMulticastAddr5 OBJECT-TYPE
  SYNTAX PhysAddress
  ACCESS read-only
  STATUS mandatory
  DESCRIPTION
    " multicast address 5 "
  ::= { bcamIfTabEntry 25 }
-- SNMPNAME: LMC5
-- ASSNAME: YRLSMUL5
-- implemented

bcamIfTabMulticastAddr6 OBJECT-TYPE
  SYNTAX PhysAddress
  ACCESS read-only
  STATUS mandatory
  DESCRIPTION
    " multicast address 6 "
  ::= { bcamIfTabEntry 26 }
-- SNMPNAME: LMC6
-- ASSNAME: YRLSMUL6
-- implemented

bcamIfTabMulticastAddr7 OBJECT-TYPE
  SYNTAX PhysAddress
  ACCESS read-only
  STATUS mandatory
  DESCRIPTION
    " multicast address 7 "
  ::= { bcamIfTabEntry 27 }
-- SNMPNAME: LMC7
-- ASSNAME: YRLSMUL7
-- implemented

bcamIfTabMulticastAddr8 OBJECT-TYPE
  SYNTAX PhysAddress
  ACCESS read-only
  STATUS mandatory
  DESCRIPTION
    " multicast address 8 "
  ::= { bcamIfTabEntry 28 }
-- SNMPNAME: LMC8
-- ASSNAME: YRLSMUL8
-- implemented

bcamIfTabMulticastAddr9 OBJECT-TYPE
  SYNTAX PhysAddress
  ACCESS read-only
  STATUS mandatory
  DESCRIPTION
    " multicast address 9 "
  ::= { bcamIfTabEntry 29 }
-- SNMPNAME: LMC9
-- ASSNAME: YRLSMUL9
-- implemented

bcamIfTabMulticastAddr10 OBJECT-TYPE
  SYNTAX PhysAddress
  ACCESS read-only
  STATUS mandatory
  DESCRIPTION
    " multicast address 10 "
  ::= { bcamIfTabEntry 30 }
-- SNMPNAME: LMCA
-- ASSNAME: YRLSMULA
-- implemented

bcamIfTabNumNeaAddress OBJECT-TYPE
  SYNTAX INTEGER
  ACCESS read-only
  STATUS mandatory
  DESCRIPTION
    " The number of NEA addresses enabled for this interface. "
  ::= { bcamIfTabEntry 31 }
-- SNMPNAME: LNNA
-- ASSNAME: YRLSFLNK
-- implemented

bcamIfTabNeaAddress1 OBJECT-TYPE
  SYNTAX OCTET STRING (SIZE(2)) -- ASSLEN: 3 VAR
  ACCESS read-only
  STATUS mandatory
  DESCRIPTION
    " NEA address 1 "
  ::= { bcamIfTabEntry 32 }
-- SNMPNAME: LNA1
-- ASSNAME: YRLSFLNK
-- implemented

bcamIfTabNeaAddress2 OBJECT-TYPE
  SYNTAX OCTET STRING (SIZE(2)) -- ASSLEN: 3 VAR
  ACCESS read-only
  STATUS mandatory
  DESCRIPTION
    " NEA address 2 "
  ::= { bcamIfTabEntry 33 }
-- SNMPNAME: LNA2
-- ASSNAME: YRLSFLNK
-- implemented

bcamIfTabNeaAddress3 OBJECT-TYPE
  SYNTAX OCTET STRING (SIZE(2)) -- ASSLEN: 3 VAR
  ACCESS read-only
  STATUS mandatory
  DESCRIPTION
    " NEA address 3 "
  ::= { bcamIfTabEntry 34 }
-- SNMPNAME: LNA3
-- ASSNAME: YRLSFLNK
-- implemented

bcamIfTabNeaAddress4 OBJECT-TYPE
  SYNTAX OCTET STRING (SIZE(2)) -- ASSLEN: 3 VAR
  ACCESS read-only
  STATUS mandatory
  DESCRIPTION
    " NEA address 4 "
  ::= { bcamIfTabEntry 35 }
-- SNMPNAME: LNA4
-- ASSNAME: YRLSFLNK
-- implemented

bcamIfTabNeaAddress5 OBJECT-TYPE
  SYNTAX OCTET STRING (SIZE(2)) -- ASSLEN: 3 VAR
  ACCESS read-only
  STATUS mandatory
  DESCRIPTION
    " NEA address 5 "
  ::= { bcamIfTabEntry 36 }
-- SNMPNAME: LNA5
-- ASSNAME: YRLSFLNK
-- implemented

bcamIfTabNeaAddress6 OBJECT-TYPE
  SYNTAX OCTET STRING (SIZE(2)) -- ASSLEN: 3 VAR
  ACCESS read-only
  STATUS mandatory
  DESCRIPTION
    " NEA address 6 "
  ::= { bcamIfTabEntry 37 }
-- SNMPNAME: LNA6
-- ASSNAME: YRLSFLNK
-- implemented

bcamIfTabNumIpAddress OBJECT-TYPE
  SYNTAX INTEGER
  ACCESS read-only
  STATUS mandatory
  DESCRIPTION
    " The number of IP addresses enabled for this interface. "
  ::= { bcamIfTabEntry 38 }
-- SNMPNAME: LNIP
-- ASSNAME: YRLSFLNK
-- implemented

bcamIfTabIpAddress1 OBJECT-TYPE
  SYNTAX IpAddress
  ACCESS read-only
  STATUS mandatory
  DESCRIPTION
    " IP address 1 or zero"
  ::= { bcamIfTabEntry 39 }
-- SNMPNAME: LIP1
-- ASSNAME: YRLSFLNK
-- implemented

bcamIfTabIpAddress2 OBJECT-TYPE
  SYNTAX IpAddress
  ACCESS read-only
  STATUS mandatory
  DESCRIPTION
    " IP address 2 "
  ::= { bcamIfTabEntry 40 }
-- SNMPNAME: LIP2
-- ASSNAME: YRLSFLNK
-- implemented

bcamIfTabIpAddress3 OBJECT-TYPE
  SYNTAX IpAddress
  ACCESS read-only
  STATUS mandatory
  DESCRIPTION
    " IP address 3 "
  ::= { bcamIfTabEntry 41 }
-- SNMPNAME: LIP3
-- ASSNAME: YRLSFLNK
-- implemented

bcamIfTabIpAddress4 OBJECT-TYPE
  SYNTAX IpAddress
  ACCESS read-only
  STATUS mandatory
  DESCRIPTION
    " IP address 4 "
  ::= { bcamIfTabEntry 42 }
-- SNMPNAME: LIP4
-- ASSNAME: YRLSFLNK
-- implemented

bcamIfTabIpAddress5 OBJECT-TYPE
  SYNTAX IpAddress
  ACCESS read-only
  STATUS mandatory
  DESCRIPTION
    " IP address 5 "
  ::= { bcamIfTabEntry 43 }
-- SNMPNAME: LIP5
-- ASSNAME: YRLSFLNK
-- implemented

bcamIfTabIpAddress6 OBJECT-TYPE
  SYNTAX IpAddress
  ACCESS read-only
  STATUS mandatory
  DESCRIPTION
    " IP address 6 "
  ::= { bcamIfTabEntry 44 }
-- SNMPNAME: LIP6
-- ASSNAME: YRLSFLNK
-- implemented

bcamIfTabNumInt0Address OBJECT-TYPE
  SYNTAX INTEGER
  ACCESS read-only
  STATUS mandatory
  DESCRIPTION
    " The number of INT0 addresses enabled for this interface. "
  ::= { bcamIfTabEntry 45 }
-- SNMPNAME: LNI0
-- ASSNAME: YRLSFLNK
-- implemented

bcamIfTabInt0Address1 OBJECT-TYPE
  SYNTAX PhysAddress
  ACCESS read-only
  STATUS mandatory
  DESCRIPTION
    " INT0 address 1 or zero"
  ::= { bcamIfTabEntry 46 }
-- SNMPNAME: LI01
-- ASSNAME: YRLSFLNK
-- implemented

bcamIfTabInt0Address2 OBJECT-TYPE
  SYNTAX PhysAddress
  ACCESS read-only
  STATUS mandatory
  DESCRIPTION
    " INT0 address 2 "
  ::= { bcamIfTabEntry 47 }
-- SNMPNAME: LI02
-- ASSNAME: YRLSFLNK
-- implemented

bcamIfTabInt0Address3 OBJECT-TYPE
  SYNTAX PhysAddress
  ACCESS read-only
  STATUS mandatory
  DESCRIPTION
    " INT0 address 3 "
  ::= { bcamIfTabEntry 48 }
-- SNMPNAME: LI03
-- ASSNAME: YRLSFLNK
-- implemented

bcamIfTabInt0Address4 OBJECT-TYPE
  SYNTAX PhysAddress
  ACCESS read-only
  STATUS mandatory
  DESCRIPTION
    " INT0 address 4 "
  ::= { bcamIfTabEntry 49 }
-- SNMPNAME: LI04
-- ASSNAME: YRLSFLNK
-- implemented

bcamIfTabInt0Address5 OBJECT-TYPE
  SYNTAX PhysAddress
  ACCESS read-only
  STATUS mandatory
  DESCRIPTION
    " INT0 address 5 "
  ::= { bcamIfTabEntry 50 }
-- SNMPNAME: LI05
-- ASSNAME: YRLSFLNK
-- implemented

bcamIfTabInt0Address6 OBJECT-TYPE
  SYNTAX PhysAddress
  ACCESS read-only
  STATUS mandatory
  DESCRIPTION
    " INT0 address 6 "
  ::= { bcamIfTabEntry 51 }
-- SNMPNAME: LI06
-- ASSNAME: YRLSFLNK
-- implemented

bcamIfTabNumIntfAddress OBJECT-TYPE
  SYNTAX INTEGER
  ACCESS read-only
  STATUS mandatory
  DESCRIPTION
    " The number of INTF addresses enabled for this interface. "
  ::= { bcamIfTabEntry 52 }
-- SNMPNAME: LNIF
-- ASSNAME: YRLSFLNK
-- implemented

bcamIfTabIntfAddress1 OBJECT-TYPE
  SYNTAX OCTET STRING (SIZE(0..20)) -- ASSLEN: 22 VAR
  ACCESS read-only
  STATUS mandatory
  DESCRIPTION
    " INTF address 1 "
  ::= { bcamIfTabEntry 53 }
-- SNMPNAME: LIF1
-- ASSNAME: YRLSFLNK
-- implemented

bcamIfTabIntfAddress2 OBJECT-TYPE
  SYNTAX OCTET STRING (SIZE(0..20)) -- ASSLEN: 22 VAR
  ACCESS read-only
  STATUS mandatory
  DESCRIPTION
    " INTF address 2 "
  ::= { bcamIfTabEntry 54 }
-- SNMPNAME: LIF2
-- ASSNAME: YRLSFLNK
-- implemented

bcamIfTabIntfAddress3 OBJECT-TYPE
  SYNTAX OCTET STRING (SIZE(0..20)) -- ASSLEN: 22 VAR
  ACCESS read-only
  STATUS mandatory
  DESCRIPTION
    " INTF address 3 "
  ::= { bcamIfTabEntry 55 }
-- SNMPNAME: LIF3
-- ASSNAME: YRLSFLNK
-- implemented

bcamIfTabIntfAddress4 OBJECT-TYPE
  SYNTAX OCTET STRING (SIZE(0..20)) -- ASSLEN: 22 VAR
  ACCESS read-only
  STATUS mandatory
  DESCRIPTION
    " INTF address 4 "
  ::= { bcamIfTabEntry 56 }
-- SNMPNAME: LIF4
-- ASSNAME: YRLSFLNK
-- implemented

bcamIfTabIntfAddress5 OBJECT-TYPE
  SYNTAX OCTET STRING (SIZE(0..20)) -- ASSLEN: 22 VAR
  ACCESS read-only
  STATUS mandatory
  DESCRIPTION
    " INTF address 5 "
  ::= { bcamIfTabEntry 57 }
-- SNMPNAME: LIF5
-- ASSNAME: YRLSFLNK
-- implemented

bcamIfTabIntfAddress6 OBJECT-TYPE
  SYNTAX OCTET STRING (SIZE(0..20)) -- ASSLEN: 22 VAR
  ACCESS read-only
  STATUS mandatory
  DESCRIPTION
    " INTF address 6 "
  ::= { bcamIfTabEntry 58 }
-- SNMPNAME: LIF6
-- ASSNAME: YRLSFLNK
-- implemented

bcamIfTabBytesOutHighs OBJECT-TYPE
  SYNTAX Counter
  ACCESS read-only
  STATUS mandatory
  DESCRIPTION
    " The number of bytes sent (high word, multiply by 4294967296) "
  ::= { bcamIfTabEntry 59 }
-- SNMPNAME: LBOH
-- ASSNAME: YRL#BYO1
-- implemented

bcamIfTabBytesOutLows OBJECT-TYPE
  SYNTAX Counter
  ACCESS read-only
  STATUS mandatory
  DESCRIPTION
    " The number of bytes sent (low word, add to high word) "
  ::= { bcamIfTabEntry 60 }
-- SNMPNAME: LBOL
-- ASSNAME: YRL#BYO2
-- implemented

bcamIfTabBytesInHighs OBJECT-TYPE
  SYNTAX Counter
  ACCESS read-only
  STATUS mandatory
  DESCRIPTION
    " The number of bytes received (high word, multiply by 4294967296) "
  ::= { bcamIfTabEntry 61 }
-- SNMPNAME: LBIH
-- ASSNAME: YRL#BYI1
-- implemented

bcamIfTabBytesInLows OBJECT-TYPE
  SYNTAX Counter
  ACCESS read-only
  STATUS mandatory
  DESCRIPTION
    " The number of bytes received (low word, add to high word) "
  ::= { bcamIfTabEntry 62 }
-- SNMPNAME: LBIL
-- ASSNAME: YRL#BYI2
-- implemented

bcamIfTabIOsOutHighs OBJECT-TYPE
  SYNTAX Counter
  ACCESS read-only
  STATUS mandatory
  DESCRIPTION
    " The number of IO operations for output (high word, multiply by 4294967296) "
  ::= { bcamIfTabEntry 63 }
-- SNMPNAME: LIOH
-- ASSNAME: YRL#IOO1
-- implemented

bcamIfTabIOsOutLows OBJECT-TYPE
  SYNTAX Counter
  ACCESS read-only
  STATUS mandatory
  DESCRIPTION
    " The number of IO operations for output (low word, add to high word) "
  ::= { bcamIfTabEntry 64 }
-- SNMPNAME: LIOL
-- ASSNAME: YRL#IOO2
-- implemented

bcamIfTabIOsInHighs OBJECT-TYPE
  SYNTAX Counter
  ACCESS read-only
  STATUS mandatory
  DESCRIPTION
    " The number of IO operations for input (high word, multiply by 4294967296) "
  ::= { bcamIfTabEntry 65 }
-- SNMPNAME: LIIH
-- ASSNAME: YRL#IOI1
-- implemented

bcamIfTabIOsInLows OBJECT-TYPE
  SYNTAX Counter
  ACCESS read-only
  STATUS mandatory
  DESCRIPTION
    " The number of IO operations for input (low word, add to high word) "
  ::= { bcamIfTabEntry 66 }
-- SNMPNAME: LIIL
-- ASSNAME: YRL#IOI2
-- implemented

bcamIfTabOutputStops OBJECT-TYPE
  SYNTAX Counter
  ACCESS read-only
  STATUS mandatory
  DESCRIPTION
    " The number of times BCAM sent a RNR (Receive Not Ready) HDLC frame. "
  ::= { bcamIfTabEntry 67 }
-- SNMPNAME: LOPS
-- ASSNAME: YRL#RNRO
-- implemented

bcamIfTabInputStops OBJECT-TYPE
  SYNTAX Counter
  ACCESS read-only
  STATUS mandatory
  DESCRIPTION
    " The number of times BCAM received a RNR (Receive Not Ready) HDLC frame. "
  ::= { bcamIfTabEntry 68 }
-- SNMPNAME: LIPS
-- ASSNAME: YRL#RNRI
-- implemented

bcamIfTabIOErrorOuts OBJECT-TYPE
  SYNTAX Counter
  ACCESS read-only
  STATUS mandatory
  DESCRIPTION
    " The number of IO errors for output operations "
  ::= { bcamIfTabEntry 69 }
-- SNMPNAME: LIEO
-- ASSNAME: YRL#ERRO
-- implemented

bcamIfTabIOErrorIns OBJECT-TYPE
  SYNTAX Counter
  ACCESS read-only
  STATUS mandatory
  DESCRIPTION
    " The number of IO errors for input operations "
  ::= { bcamIfTabEntry 70 }
-- SNMPNAME: LIEI
-- ASSNAME: YRL#ERRI
-- implemented

bcamIfTabPacketsNotReceiveds OBJECT-TYPE
  SYNTAX Counter
  ACCESS read-only
  STATUS mandatory
  DESCRIPTION
    " The number of packets not received due to receive not ready "
  ::= { bcamIfTabEntry 71 }
-- SNMPNAME: LRNR
-- ASSNAME: YRL#NRID
-- implemented

bcamIfTabInPacketsLanHighs OBJECT-TYPE
  SYNTAX Counter
  ACCESS read-only
  STATUS mandatory
  DESCRIPTION
    " The number of input packets (only valid for ethernet or FDDI) (high word, multiply by 4294967296) "
  ::= { bcamIfTabEntry 72 }
-- SNMPNAME: LPIH
-- ASSNAME: YRL#PAI1
-- implemented

bcamIfTabInPacketsLanLows OBJECT-TYPE
  SYNTAX Counter
  ACCESS read-only
  STATUS mandatory
  DESCRIPTION
    " The number of input packets (only valid for ethernet or FDDI) (low word, add to high word)"
  ::= { bcamIfTabEntry 73 }
-- SNMPNAME: LPIL
-- ASSNAME: YRL#PAI2
-- implemented

bcamIfTabOutPacketsLanHighs OBJECT-TYPE
  SYNTAX Counter
  ACCESS read-only
  STATUS mandatory
  DESCRIPTION
    " The number of output packets (only valid for ethernet or FDDI) (high word, multiply by 4294967296) "
  ::= { bcamIfTabEntry 74 }
-- SNMPNAME: LPOH
-- ASSNAME: YRL#PAO1
-- implemented

bcamIfTabOutPacketsLanLows OBJECT-TYPE
  SYNTAX Counter
  ACCESS read-only
  STATUS mandatory
  DESCRIPTION
    " The number of output packets (only valid for ethernet or FDDI) (low word, add to high word)"
  ::= { bcamIfTabEntry 75 }
-- SNMPNAME: LPOL
-- ASSNAME: YRL#PAO2
-- implemented

bcamIfTabUnicastInHighs OBJECT-TYPE
  SYNTAX Counter
  ACCESS read-only
  STATUS mandatory
  DESCRIPTION
    " The number of unicasts received (high word, multiply by 4294967296) "
  ::= { bcamIfTabEntry 76 }
-- SNMPNAME: LUIH
-- ASSNAME: YRL#UNI1
-- implemented

bcamIfTabUnicastInLows OBJECT-TYPE
  SYNTAX Counter
  ACCESS read-only
  STATUS mandatory
  DESCRIPTION
    " The number of unicasts received (low word, add to high word) "
  ::= { bcamIfTabEntry 77 }
-- SNMPNAME: LUIL
-- ASSNAME: YRL#UNI2
-- implemented

bcamIfTabUnicastOutHighs OBJECT-TYPE
  SYNTAX Counter
  ACCESS read-only
  STATUS mandatory
  DESCRIPTION
    " The number of unicasts sent (high word, multiply by 4294967296) "
  ::= { bcamIfTabEntry 78 }
-- SNMPNAME: LUOH
-- ASSNAME: YRL#UNO1
-- implemented

bcamIfTabUnicastOutLows OBJECT-TYPE
  SYNTAX Counter
  ACCESS read-only
  STATUS mandatory
  DESCRIPTION
    " The number of unicasts sent (low word, add to high word) "
  ::= { bcamIfTabEntry 79 }
-- SNMPNAME: LUOL
-- ASSNAME: YRL#UNO2
-- implemented

bcamIfTabMulticastInHighs OBJECT-TYPE
  SYNTAX Counter
  ACCESS read-only
  STATUS mandatory
  DESCRIPTION
    " The number of multicasts received (high word, multiply by 4294967296) "
  ::= { bcamIfTabEntry 80 }
-- SNMPNAME: LMIH
-- ASSNAME: YRL#MUI1
-- implemented

bcamIfTabMulticastInLows OBJECT-TYPE
  SYNTAX Counter
  ACCESS read-only
  STATUS mandatory
  DESCRIPTION
    " The number of multicasts received (low word, add to high word) "
  ::= { bcamIfTabEntry 81 }
-- SNMPNAME: LMIL
-- ASSNAME: YRL#MUI2
-- implemented

bcamIfTabMulticastOutHighs OBJECT-TYPE
  SYNTAX Counter
  ACCESS read-only
  STATUS mandatory
  DESCRIPTION
    " The number of multicasts sent (high word, multiply by 4294967296) "
  ::= { bcamIfTabEntry 82 }
-- SNMPNAME: LMOH
-- ASSNAME: YRL#MUO1
-- implemented

bcamIfTabMulticastOutLows OBJECT-TYPE
  SYNTAX Counter
  ACCESS read-only
  STATUS mandatory
  DESCRIPTION
    " The number of multicasts sent (low word, add to high word) "
  ::= { bcamIfTabEntry 83 }
-- SNMPNAME: LMOL
-- ASSNAME: YRL#MUO2
-- implemented

bcamIfTabErrorPacketIns OBJECT-TYPE
  SYNTAX Counter
  ACCESS read-only
  STATUS mandatory
  DESCRIPTION
    " The number of erroneous packets received."
  ::= { bcamIfTabEntry 84 }
-- SNMPNAME: LEPI
-- ASSNAME: YRL#PEI
-- implemented

bcamIfTabErrorPacketOuts OBJECT-TYPE
  SYNTAX Counter
  ACCESS read-only
  STATUS mandatory
  DESCRIPTION
    " The number of erroneous packets sent."
  ::= { bcamIfTabEntry 85 }
-- SNMPNAME: LEPO
-- ASSNAME: YRL#PEO
-- implemented

bcamIfTabDiscardIns OBJECT-TYPE
  SYNTAX Counter
  ACCESS read-only
  STATUS mandatory
  DESCRIPTION
    " The number of packets received that were discarded. "
  ::= { bcamIfTabEntry 86 }
-- SNMPNAME: LDCI
-- ASSNAME: YRL#DISI
-- implemented

bcamIfTabDiscardOuts OBJECT-TYPE
  SYNTAX Counter
  ACCESS read-only
  STATUS mandatory
  DESCRIPTION
    " The number of packets that were discarded before sending. "
  ::= { bcamIfTabEntry 87 }
-- SNMPNAME: LDCO
-- ASSNAME: YRL#DISO
-- implemented

bcamIfTabUnknownProtoIns OBJECT-TYPE
  SYNTAX Counter
  ACCESS read-only
  STATUS mandatory
  DESCRIPTION
    " The number of packets received that were discarded because of unknown protocol. "
  ::= { bcamIfTabEntry 88 }
-- SNMPNAME: LUPI
-- ASSNAME: YRL#UPRI
-- implemented

bcamIfTabTraceState OBJECT-TYPE
  SYNTAX INTEGER {
-- ASSMULTI:
--                 stopped(0),  ASSVAL: 0 0
		 running(1), -- ASSVAL: YTETALLO 1
		 save(2),    -- ASSVAL: YTESAVRQ 2
		 hold(4),    -- ASSVAL: YTEHLDRQ 4
		 stopped(8)  -- ASSVAL: 0 0
		 }
  ACCESS read-only
  STATUS mandatory
  DESCRIPTION
    " The current state of the trace.
      stopped (8) : the trace is not running.
      running (1) : the trace is running.
      save    (2) : the trace is running and saved to a file.
      hold    (4) : the trace data will be kept in case of an error.
      Several bits may be set simultaneous."
  ::= { bcamIfTabEntry 89 }
-- SNMPNAME: LTST
-- ASSNAME: YTETFLAG

bcamIfTabTraceNumberBuffer OBJECT-TYPE
  SYNTAX INTEGER (1..16) -- ASSLEN: 2
  ACCESS read-only
  STATUS mandatory
  DESCRIPTION
    " The number of buffers used for the trace"
  ::= { bcamIfTabEntry 90 }
-- SNMPNAME: LTNB
-- ASSNAME: YTEACBFN

bcamIfTabTraceBufferLen OBJECT-TYPE
  SYNTAX INTEGER (512..16384) -- ASSLEN: 2
  ACCESS read-only
  STATUS mandatory
  DESCRIPTION
    " The length of one trace buffer in bytes (rounded up to multiples of 256). "
  ::= { bcamIfTabEntry 91 }
-- SNMPNAME: LTBL
-- ASSNAME: YTEACBFL











-- the Router Group

bcamRouterNumTable OBJECT-TYPE
  SYNTAX INTEGER
  ACCESS read-only
  STATUS mandatory
  DESCRIPTION
    " The number of table entries in the router table "
  ::= { bcamRouter 1 }
-- SNMPNAME: UNTB
-- ASSNAME:

bcamRouterTab OBJECT-TYPE
  SYNTAX SEQUENCE OF RouterEntry
  ACCESS not-accessible
  STATUS mandatory
  DESCRIPTION
    "Table of all routers"
  ::= { bcamRouter 2 }
-- SNMPNAME:
-- ASSNAME:

bcamRouterTabEntry OBJECT-TYPE
  SYNTAX RouterEntry
  ACCESS not-accessible
  STATUS mandatory
  DESCRIPTION
    "Information about a router"
  INDEX {
	bcamRouterTabIpLow,
	bcamRouterTabIpHigh,
	bcamRouterTabIpLocal
	}
  ::= { bcamRouterTab 1 }
-- SNMPNAME:
-- ASSNAME:

  RouterEntry ::=
    SEQUENCE {
	     bcamRouterTabIpLow IpAddress,
	     bcamRouterTabIpHigh IpAddress,
	     bcamRouterTabIpLocal IpAddress,
	     bcamRouterTabIpRouter IpAddress,
	     bcamRouterTabNumRouter INTEGER
	     }


bcamRouterTabIpLow OBJECT-TYPE
  SYNTAX IpAddress
  ACCESS read-only
  STATUS mandatory
  DESCRIPTION
    " The lower IP address limit of the IP address range reachable via this router. "
  ::= { bcamRouterTabEntry 1 }
-- SNMPNAME: UTIL
-- ASSNAME: YRGTIPA

bcamRouterTabIpHigh OBJECT-TYPE
  SYNTAX IpAddress
  ACCESS read-only
  STATUS mandatory
  DESCRIPTION
    " The upper IP address limit of the IP address range reachable via this router. "
  ::= { bcamRouterTabEntry 2 }
-- SNMPNAME: UTIH
-- ASSNAME: YRGTUPA

bcamRouterTabIpLocal OBJECT-TYPE
  SYNTAX IpAddress
  ACCESS read-only
  STATUS mandatory
  DESCRIPTION
    " The local IP address used for this endsystem. "
  ::= { bcamRouterTabEntry 3 }
-- SNMPNAME: UTIC
-- ASSNAME:

bcamRouterTabIpRouter OBJECT-TYPE
  SYNTAX IpAddress
  ACCESS read-only
  STATUS mandatory
  DESCRIPTION
    " The IP address of the router "
  ::= { bcamRouterTabEntry 4 }
-- SNMPNAME: UTIR
-- ASSNAME: YRROIPA

bcamRouterTabNumRouter OBJECT-TYPE
  SYNTAX INTEGER
  ACCESS read-only
  STATUS mandatory
  DESCRIPTION
    " The route number of the router. "
  ::= { bcamRouterTabEntry 5 }
-- SNMPNAME: UTNR
-- ASSNAME: YRROZKEY


-- the Host Group

bcamHostNumTable OBJECT-TYPE
  SYNTAX INTEGER
  ACCESS read-only
  STATUS mandatory
  DESCRIPTION
    " The number of table entries in the host table "
  ::= { bcamHost 1 }
-- SNMPNAME: HNTB
-- ASSNAME: YBCHOSTF

bcamHostTab OBJECT-TYPE
  SYNTAX SEQUENCE OF HostEntry
  ACCESS not-accessible
  STATUS mandatory
  DESCRIPTION
    "Table of all Hosts"
  ::= { bcamHost 2 }
-- SNMPNAME:
-- ASSNAME:

bcamHostTabEntry OBJECT-TYPE
  SYNTAX HostEntry
  ACCESS not-accessible
  STATUS mandatory
  DESCRIPTION
    "Information about a Host"
  INDEX {
	bcamHostTabNumber
	}
  ::= { bcamHostTab 1 }
-- SNMPNAME:
-- ASSNAME:

  HostEntry ::=
    SEQUENCE {
	     bcamHostTabNumber INTEGER ,
	     bcamHostTabName DisplayString (SIZE(8)) ,
	     bcamHostTabSocketName DisplayString (SIZE(0..32)) ,
	     bcamHostTabTyp INTEGER ,
	     bcamHostTabState INTEGER
	     }


bcamHostTabNumber OBJECT-TYPE
  SYNTAX INTEGER
  ACCESS read-only
  STATUS mandatory
  DESCRIPTION
    " The definite identifier for this host. "
  ::= { bcamHostTabEntry 1 }
-- SNMPNAME: HNUM
-- ASSNAME: YRHONUMB

bcamHostTabName OBJECT-TYPE
  SYNTAX DisplayString (SIZE(8)) -- ASSLEN: 9 VAR
  ACCESS read-only
  STATUS mandatory
  DESCRIPTION
    " The NEA name of the host. "
  ::= { bcamHostTabEntry 2 }
-- SNMPNAME: HNAM
-- ASSNAME: YRHOHNAM

bcamHostTabSocketName OBJECT-TYPE
  SYNTAX DisplayString (SIZE(0..32)) -- ASSLEN: 33 VAR
  ACCESS read-only
  STATUS mandatory
  DESCRIPTION
    " The socket name of the host. "
  ::= { bcamHostTabEntry 3 }
-- SNMPNAME: HSON
-- ASSNAME: YRHOSHON

bcamHostTabTyp OBJECT-TYPE
  SYNTAX INTEGER {
-- ASSSINGLE:
		 normal(1),  -- ASSVAL: YRHOTYNO 213
		 virtual(2)  -- ASSVAL: YRHOTYVI 229
		 }
  ACCESS read-only
  STATUS mandatory
  DESCRIPTION
    " The type of the host.
      normal  (1) : the host is the BCAM standard host.
      virtual (2) : the host is a virtual host. "
  ::= { bcamHostTabEntry 4 }
-- SNMPNAME: HTYP
-- ASSNAME: YRHOTYPE

bcamHostTabState OBJECT-TYPE
  SYNTAX INTEGER {
-- ASSMULTI:
		 active(1),       -- ASSVAL: YRHOFACT 128
		 included(2)      -- ASSVAL: YRHOFINC 64
		 }
  ACCESS read-only
  STATUS mandatory
  DESCRIPTION
    " The current state of the host:
      active   (1) : the host is working.
      included (2) : the host is known by BCAM.
      Several bits may be set simultaneous."
  ::= { bcamHostTabEntry 5 }
-- SNMPNAME: HSTA
-- ASSNAME: YRHOFLAG


END
