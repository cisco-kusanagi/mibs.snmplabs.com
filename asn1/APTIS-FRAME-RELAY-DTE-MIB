--	Aptis Enterprise MIB
--
--	Nortel Networks
--	11 Elizabeth Drive
--	Chelmsford, MA 01824
--
--	Copyright (c) 1997-2000 Nortel Networks
--	All Rights Reserved.
--

APTIS-FRAME-RELAY-DTE-MIB DEFINITIONS ::= BEGIN

     IMPORTS
             OBJECT-TYPE
                     FROM RFC-1212
--           transmission
--                   FROM RFC1213-MIB
             Counter, TimeTicks
                     FROM RFC1155-SMI
             aptis-generic
                     FROM APTIS-MIB;

     aptisFrameRelay     OBJECT IDENTIFIER ::= { aptis-generic 6 }

     --
     --      the range of ifIndex
     --
     Index ::= INTEGER       -- 1..ifNumber

     --
     --      the range of a Data Link Connection Identifier
     --
     DLCI ::= INTEGER        -- 0..DLCINumber

        -- This begins Aptis extensions to the Frame Relay MIB

        --
        -- Here are a few extended frame relay parameters
        -- They COULD be incorporated into the frame-relay sub-tree
        --

        aptisDlcmiTable    OBJECT-TYPE
                SYNTAX  SEQUENCE OF AptisDlcmiEntry
                ACCESS  not-accessible
                STATUS  mandatory
                DESCRIPTION
                        "The Parameters for the Data Link Connection Management
                        Interface corresponding to any given ifEntry.

                        These parameters are logical extensions to those in
                        object frDlcmiTable."
                REFERENCE
                        "Draft American National Standard T1.617-1991, Annex D"
                ::= { aptisFrameRelay 1 }

        aptisDlcmiEntry    OBJECT-TYPE
                SYNTAX  AptisDlcmiEntry
                ACCESS  not-accessible
                STATUS  mandatory
                DESCRIPTION
                        "The Parameters for the  Data  Link  Connection
                        Management Interface."
                INDEX   { aptisDlcmiIfIndex }
                ::= { aptisDlcmiTable 1 }

        AptisDlcmiEntry ::= SEQUENCE {
                        aptisDlcmiIfIndex                 Index,
                        aptisDlcmiXmtFramesDropped        Counter,
                        aptisDlcmiXmtOctetsDropped        Counter,
                        aptisDlcmiRcvFramesDropped        Counter,
                        aptisDlcmiRcvOctetsDropped        Counter,
                        aptisDlcmiRcvInvFrames            Counter,
                        aptisDlcmiRcvShortFrames          Counter,
                        aptisDlcmiRcvLongFrames           Counter,
                        aptisDlcmiRcvInvalidDLCI          Counter,
                        aptisDlcmiRcvUnknownDLCI          Counter,
                        aptisDlcmiRcvUnknownErrs          Counter,
                        aptisDlcmiLMIStatusEnquiries      Counter,
                        aptisDlcmiLMIFullStatusEnquiries  Counter,
                        aptisDlcmiLMIStatusResponses      Counter,
                        aptisDlcmiLMIFullStatusResponses  Counter,
                        aptisDlcmiLMIUpdates              Counter,
                        aptisDlcmiUnknownLMIMessagesRcvd  Counter,
                        aptisDlcmiBadLMIMessagesRcvd      Counter,
                        aptisDlcmiLostLMISequences        Counter,
                        aptisDlcmiMissingLMIResponses     Counter,
                        aptisDlcmiUpTime                  TimeTicks
                }
        aptisDlcmiIfIndex  OBJECT-TYPE
                SYNTAX  Index
                ACCESS  read-only
                STATUS  mandatory
                DESCRIPTION
                        "The ifIndex value of the  corresponding
                        ifEntry."
                ::= { aptisDlcmiEntry 1 }

        aptisDlcmiXmtFramesDropped OBJECT-TYPE
             SYNTAX   Counter
             ACCESS   read-only
             STATUS   mandatory
             DESCRIPTION
                "The number of Tranmsitted frames dropped on this
                interface."
            ::= { aptisDlcmiEntry 2 }

        aptisDlcmiXmtOctetsDropped OBJECT-TYPE
             SYNTAX   Counter
             ACCESS   read-only
             STATUS   mandatory
             DESCRIPTION
                "The number of Tranmsitted octets dropped on this
                interface."
            ::= { aptisDlcmiEntry 3 }

        aptisDlcmiRcvFramesDropped OBJECT-TYPE
             SYNTAX   Counter
             ACCESS   read-only
             STATUS   mandatory
             DESCRIPTION
                "The number of Received frames dropped on this
                interface."
            ::= { aptisDlcmiEntry 4 }

        aptisDlcmiRcvOctetsDropped OBJECT-TYPE
             SYNTAX   Counter
             ACCESS   read-only
             STATUS   mandatory
             DESCRIPTION
                "The number of Received octets dropped on this
                interface."
            ::= { aptisDlcmiEntry 5 }

        aptisDlcmiRcvInvFrames OBJECT-TYPE
             SYNTAX   Counter
             ACCESS   read-only
             STATUS   mandatory
             DESCRIPTION
                "The number of invalid frames received on this
                interface."
            ::= { aptisDlcmiEntry 6 }

        aptisDlcmiRcvShortFrames OBJECT-TYPE
             SYNTAX   Counter
             ACCESS   read-only
             STATUS   mandatory
             DESCRIPTION
                "The number of frames containing less than 5
                 octets received on this interface."
            ::= { aptisDlcmiEntry 7 }

        aptisDlcmiRcvLongFrames OBJECT-TYPE
             SYNTAX   Counter
             ACCESS   read-only
             STATUS   mandatory
             DESCRIPTION
                "The number of frames containing greater than 8193
                 octets received on this interface."
            ::= { aptisDlcmiEntry 8 }

        aptisDlcmiRcvInvalidDLCI OBJECT-TYPE
             SYNTAX   Counter
             ACCESS   read-only
             STATUS   mandatory
             DESCRIPTION
                "The number of frames with an invalid DLCI received
                 on this interface."
            ::= { aptisDlcmiEntry 9 }

        aptisDlcmiRcvUnknownDLCI OBJECT-TYPE
             SYNTAX   Counter
             ACCESS   read-only
             STATUS   mandatory
             DESCRIPTION
                "The number of frames with an unknown DLCI received
                 on this interface."
            ::= { aptisDlcmiEntry 10 }

        aptisDlcmiRcvUnknownErrs OBJECT-TYPE
             SYNTAX   Counter
             ACCESS   read-only
             STATUS   mandatory
             DESCRIPTION
                "The number of frames with other errors received
                 on this interface."
            ::= { aptisDlcmiEntry 11 }

        aptisDlcmiLMIStatusEnquiries OBJECT-TYPE
             SYNTAX   Counter
             ACCESS   read-only
             STATUS   mandatory
             DESCRIPTION
                "The total number of LMI status enquiries sent by the
                 DTE or received by the DCE on this interface."
            ::= { aptisDlcmiEntry 12 }

        aptisDlcmiLMIFullStatusEnquiries OBJECT-TYPE
             SYNTAX   Counter
             ACCESS   read-only
             STATUS   mandatory
             DESCRIPTION
                "The total number of LMI full status enquiries sent 
                 by the DTE or received by the DCE on this interface."
            ::= { aptisDlcmiEntry 13 }

        aptisDlcmiLMIStatusResponses OBJECT-TYPE
             SYNTAX   Counter
             ACCESS   read-only
             STATUS   mandatory
             DESCRIPTION
                "The total number of LMI status responses received
                 by the DTE or sent by the DCE on this interface."
            ::= { aptisDlcmiEntry 14 }

        aptisDlcmiLMIFullStatusResponses OBJECT-TYPE
             SYNTAX   Counter
             ACCESS   read-only
             STATUS   mandatory
             DESCRIPTION
                "The total number of LMI full status responses received
                 by the DTE or sent by the DCE on this interface."
            ::= { aptisDlcmiEntry 15 }

        aptisDlcmiLMIUpdates OBJECT-TYPE
             SYNTAX   Counter
             ACCESS   read-only
             STATUS   mandatory
             DESCRIPTION
                "The total number of LMI status updates received
                 by the DTE or sent by the DCE on this interface."
            ::= { aptisDlcmiEntry 16 }

        aptisDlcmiUnknownLMIMessagesRcvd OBJECT-TYPE
             SYNTAX   Counter
             ACCESS   read-only
             STATUS   mandatory
             DESCRIPTION
                "The total number of unknown LMI messages received
                 on this interface."
            ::= { aptisDlcmiEntry 17 }

        aptisDlcmiBadLMIMessagesRcvd OBJECT-TYPE
             SYNTAX   Counter
             ACCESS   read-only
             STATUS   mandatory
             DESCRIPTION
                "The total number of LMI messages received
                 with unknown or missing required Information Elements."
            ::= { aptisDlcmiEntry 18 }

        aptisDlcmiLostLMISequences OBJECT-TYPE
             SYNTAX   Counter
             ACCESS   read-only
             STATUS   mandatory
             DESCRIPTION
                "The total number of times a loss of sequencing 
                 in received LMI messages was detected
                 by the DTE on this interface."
            ::= { aptisDlcmiEntry 19 }

        aptisDlcmiMissingLMIResponses OBJECT-TYPE
             SYNTAX   Counter
             ACCESS   read-only
             STATUS   mandatory
             DESCRIPTION
                "The total number of times a timeout occurred without 
                 receiving a response to an LMI request
                 by the DTE on this interface."
            ::= { aptisDlcmiEntry 20 }

        aptisDlcmiUpTime OBJECT-TYPE
             SYNTAX   TimeTicks
             ACCESS   read-only
             STATUS   mandatory
             DESCRIPTION
                "The duration that this data link has existed.
                 This is the difference between the value of
                 sysUpTime at the time of a 'get' and the
                 value of sysUpTime at the time that the
                 link level object was initialized."
            ::= { aptisDlcmiEntry 21 }

        aptisCircuitTable  OBJECT-TYPE
                SYNTAX   SEQUENCE OF AptisCircuitEntry
                ACCESS   not-accessible
                STATUS   mandatory
                DESCRIPTION
                        "A table containing information about specific Data
                        Link Connection Identifiers and corresponding virtual
                        circuits.

                        These parameters are logical extensions to those in 
                        object frCircuitTable."
                ::= { aptisFrameRelay 2 }

        aptisCircuitEntry OBJECT-TYPE
                SYNTAX   AptisCircuitEntry
                ACCESS   not-accessible
                STATUS   mandatory
                DESCRIPTION
                        "The information regarding a single  Data  Link
                        Connection Identifier."
                INDEX   {       aptisCircuitIfIndex, 
                                aptisCircuitDlci
                        }
                ::= { aptisCircuitTable 1 }

        AptisCircuitEntry ::=
                SEQUENCE {
                        aptisCircuitIfIndex
                                Index,
                        aptisCircuitDlci
                                DLCI,
                        aptisCircuitReceivedRBits
                                Counter,
                        aptisCircuitRateFallbacks
                                Counter,
                        aptisCircuitRateFallforwards
                                Counter,
                        aptisCircuitFramesDroppedQueueFull
                                Counter,
                        aptisCircuitNormalSentOctets
                                Counter,
                        aptisCircuitExcessSentOctets
                                Counter,
                        aptisCircuitFramesQueuedBandwidth
                                Counter,
                        aptisCircuitOctetsQueuedBandwidth
                                Counter,
                        aptisCircuitFramesOnQueue
                                INTEGER,
                        aptisCircuitReceivedUnknownProtocol
                                Counter,
                        aptisCircuitSentUnknownProtocol
                                Counter,
                        aptisCircuitReceivedUnknownFrame
                                Counter,
                        aptisCircuitReceivedUnknownOrg
                                Counter,
                        aptisCircuitNormalSentFrames
                                Counter,
                        aptisCircuitExcessSentFrames
                                Counter,
                        aptisCircuitOctetsDroppedQueueFull
                                Counter
                }

        aptisCircuitIfIndex OBJECT-TYPE
                SYNTAX  Index
                ACCESS  read-only
                STATUS  mandatory
                DESCRIPTION
                        "The ifIndex Value of the ifEntry this  virtual
                        circuit is layered onto."
                ::= { aptisCircuitEntry 1 }

        aptisCircuitDlci OBJECT-TYPE
                SYNTAX  DLCI
                ACCESS  read-only
                STATUS  mandatory
                DESCRIPTION
                        "The Data Link Connection Identifier  for  this
                        virtual circuit."
                REFERENCE
                        "Draft American National  Standard  T1.618-1991,
                        Section 3.3.6"
                ::= { aptisCircuitEntry 2 }


        aptisCircuitReceivedRBits OBJECT-TYPE
                SYNTAX  Counter
                ACCESS  read-only
                STATUS  mandatory
                DESCRIPTION
                        "Number of times a status report for this 
                        circuit was received with the R-bit (congestion)
                        set since the circuit was created."
                ::= { aptisCircuitEntry 3 }

        aptisCircuitRateFallbacks OBJECT-TYPE
                SYNTAX  Counter
                ACCESS  read-only
                STATUS  mandatory
                DESCRIPTION
                        "The number of times that the insertion rate was
                        lowered (due to network congestion reports) since
                        the circuit was created."
                ::= { aptisCircuitEntry 4 }

        aptisCircuitRateFallforwards OBJECT-TYPE
                SYNTAX  Counter
                ACCESS  read-only
                STATUS  mandatory
                DESCRIPTION
                        "The number of times that the insertion rate was
                        lowered (due to lack of network congestion reports) 
                        since the circuit was created."
                ::= { aptisCircuitEntry 5 }

        aptisCircuitFramesDroppedQueueFull OBJECT-TYPE
                SYNTAX  Counter
                ACCESS  read-only
                STATUS  mandatory
                DESCRIPTION
                        "Number of frames which were dropped on this circuit
                        because the hold queue was full."
                ::= { aptisCircuitEntry 6 }

        aptisCircuitNormalSentOctets OBJECT-TYPE
                SYNTAX  Counter
                ACCESS  read-only
                STATUS  mandatory
                DESCRIPTION
                        "Number of octets sent on this virtual circuit
                         within the Commited Information Rate since the
                         circuit was created."
                ::= { aptisCircuitEntry 7 }

        aptisCircuitExcessSentOctets OBJECT-TYPE
                SYNTAX  Counter
                ACCESS  read-only
                STATUS  mandatory
                DESCRIPTION
                        "Number of octets sent on this virtual circuit
                         above the Commited Information Rate, but below
                         the Excess Information Rate since the
                         circuit was created."
                ::= { aptisCircuitEntry 8 }

        aptisCircuitFramesQueuedBandwidth OBJECT-TYPE
                SYNTAX  Counter
                ACCESS  read-only
                STATUS  mandatory
                DESCRIPTION
                        "Number of frames which were queued by the circuit
                        in preference to exceeding the allowed burst rate
                        on this circuit since the circuit was created."
                ::= { aptisCircuitEntry 9 }

        aptisCircuitOctetsQueuedBandwidth OBJECT-TYPE
                SYNTAX  Counter
                ACCESS  read-only
                STATUS  mandatory
                DESCRIPTION
                        "Number of octets placed on the hold queue
                         since the circuit was created.  Data is placed
                         on the hold queue when the data would exceed the
                         Excess Information Rate during a given time period."
                ::= { aptisCircuitEntry 10 }

        aptisCircuitFramesOnQueue OBJECT-TYPE
                SYNTAX  INTEGER
                ACCESS  read-only
                STATUS  mandatory
                DESCRIPTION
                        "Number of frames currently on the transmit 
                         hold queue."
                ::= { aptisCircuitEntry 11 }

        aptisCircuitReceivedUnknownProtocol OBJECT-TYPE
                SYNTAX  Counter
                ACCESS  read-only
                STATUS  mandatory
                DESCRIPTION
                        "Number of frames received and discarded due to unkown
                         protocol ID."
                ::= { aptisCircuitEntry 12 }

        aptisCircuitSentUnknownProtocol OBJECT-TYPE
                SYNTAX  Counter
                ACCESS  read-only
                STATUS  mandatory
                DESCRIPTION
                        "Number of frames requested to be sent but were
                         discarded due to an unknown protocol ID."
                ::= { aptisCircuitEntry 13 }

        aptisCircuitReceivedUnknownFrame OBJECT-TYPE
                SYNTAX  Counter
                ACCESS  read-only
                STATUS  mandatory
                DESCRIPTION
                        "Number of frames received and dropped due to an unknown
                         frame type."
                ::= { aptisCircuitEntry 14 }

        aptisCircuitReceivedUnknownOrg OBJECT-TYPE
                SYNTAX  Counter
                ACCESS  read-only
                STATUS  mandatory
                DESCRIPTION
                        "Number of frames received and dropped due to an unknown
                         organization unique identifier."
                ::= { aptisCircuitEntry 15 }

        aptisCircuitNormalSentFrames OBJECT-TYPE
                SYNTAX  Counter
                ACCESS  read-only
                STATUS  mandatory
                DESCRIPTION
                        "Number of frames sent on this virtual circuit
                         within the Commited Information Rate since the
                         circuit was created."
                ::= { aptisCircuitEntry 16 }

        aptisCircuitExcessSentFrames OBJECT-TYPE
                SYNTAX  Counter
                ACCESS  read-only
                STATUS  mandatory
                DESCRIPTION
                        "Number of frames sent on this virtual circuit
                         above the Commited Information Rate, but below
                         the Excess Information Rate since the
                         circuit was created."
                ::= { aptisCircuitEntry 17 }

        aptisCircuitOctetsDroppedQueueFull OBJECT-TYPE
                SYNTAX  Counter
                ACCESS  read-only
                STATUS  mandatory
                DESCRIPTION
                        "Number of octets which were dropped on this circuit
                        because the hold queue was full."
                ::= { aptisCircuitEntry 18 }

     END
