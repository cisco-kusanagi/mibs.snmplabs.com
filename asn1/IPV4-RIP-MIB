IPV4-RIP-MIB

   --FORCE-INCLUDE <mib.h>
   --FORCE-INCLUDE <snmpdefs.h>
   --FORCE-INCLUDE <snmpstat.h>
   --FORCE-INCLUDE "mibproto.h"
 
   DEFINITIONS ::= BEGIN

	IMPORTS
		MODULE-IDENTITY, OBJECT-TYPE, IpAddress
			FROM SNMPv2-SMI
		RowStatus, TruthValue
			FROM SNMPv2-TC
		apIpv4Rip
			FROM APENT-MIB;


    apIpv4RipMib MODULE-IDENTITY
	   LAST-UPDATED "9805112000Z" -- Mon May 11 20:00:00 EST 1998
	   ORGANIZATION "ArrowPoint Communications Inc."
	   CONTACT-INFO
	   "Postal:               ArrowPoint Communications Inc.
				                 50 Nagog Park
				                 Acton, Massachusetts 01720
	   Tel:                   +1 978-206-3000  option 1
	   E-Mail:                support@arrowpoint.com"
       DESCRIPTION
	"This MIB module describes the ArrowPoint enterprise
	 MIB support for the Routing Information Protocol"
      ::= { apIpv4Rip 1}

--arrowpoint
-- apmgmt
--  ipv4Ext
--   apIpv4RoutingProtocols
--     apIpv4Rip

-- RIP global configuration information

apIpv4RipRedistributeStatic OBJECT-TYPE
	SYNTAX      INTEGER {
			    enable (1),
			    disable (2)
			    }
	MAX-ACCESS  read-write
	STATUS      current
	DESCRIPTION
	       "If enabled, static routes will be advertised by RIP."
	DEFVAL {2}
	--DEFAULT apjam-group apIpv4GlobalRipInst, apIpv4RipRedistributeStatic
	--DEFAULT apjam-popup-def apIpv4GlobalRipInst, Properties, local
	--DEFAULT ap-display-name Redistribute Static Routes
	--DEFAULT apjam-popup-ref apIpv4GlobalRipInst, Properties
	::= {apIpv4Rip 2}

apIpv4RipStaticMetric OBJECT-TYPE
    SYNTAX      INTEGER ( 1..15 )
	MAX-ACCESS  read-write
	STATUS      current
	DESCRIPTION
	       "If static routes are advertised by RIP, this is the metric
            to use when advertising the routes."
	DEFVAL {1}
	--DEFAULT ap-display-name Static Route Metric
	--DEFAULT apjam-popup-ref apIpv4GlobalRipInst, Properties
	::= {apIpv4Rip 3}

apIpv4RipRedistributeOspf OBJECT-TYPE
	SYNTAX      INTEGER {
			    enable (1),
			    disable (2)
			    }
	MAX-ACCESS  read-write
	STATUS      current
	DESCRIPTION
	       "If enabled, OSPF routes will be advertised by RIP."
	DEFVAL {2}
	--DEFAULT ap-display-name Redistribute OSPF Routes
	--DEFAULT apjam-popup-ref apIpv4GlobalRipInst, Properties
	::= {apIpv4Rip 4}

apIpv4RipOspfMetric OBJECT-TYPE
    SYNTAX      INTEGER ( 1..15 )
	MAX-ACCESS  read-write
	STATUS      current
	DESCRIPTION
	       "If OSPF routes are advertised by RIP, this is the metric
            to use when advertising the routes."
	DEFVAL {1}
	--DEFAULT ap-display-name OSPF Route Metric
	--DEFAULT apjam-popup-ref apIpv4GlobalRipInst, Properties
	::= {apIpv4Rip 5}

apIpv4RipRedistributeLocal OBJECT-TYPE
	SYNTAX      INTEGER {
			    enable (1),
			    disable (2)
			    }
	MAX-ACCESS  read-write
	STATUS      current
	DESCRIPTION
	       "If enabled, local routes will be advertised by RIP."
	DEFVAL {2}
	--DEFAULT ap-display-name Redistribute Local Routes
	--DEFAULT apjam-popup-ref apIpv4GlobalRipInst, Properties
	::= {apIpv4Rip 6}

apIpv4RipLocalMetric OBJECT-TYPE
    SYNTAX      INTEGER ( 1..15 )
	MAX-ACCESS  read-write
	STATUS      current
	DESCRIPTION
	       "If local routes are advertised by RIP, this is the metric
            to use when advertising the routes."
	DEFVAL {1}
	--DEFAULT ap-display-name Local Route Metric
	--DEFAULT apjam-popup-ref apIpv4GlobalRipInst, Properties
	::= {apIpv4Rip 7}

apIpv4RipEqualCostRoutes OBJECT-TYPE
    SYNTAX      INTEGER ( 1..15 )
	MAX-ACCESS  read-write
	STATUS      current
	DESCRIPTION
	       "The maximum number of equal-cost routes RIP can use."
	DEFVAL {1}
	--DEFAULT ap-display-name Equal Cost Routes
	--DEFAULT apjam-popup-ref apIpv4GlobalRipInst, Properties
	::= {apIpv4Rip 11}

apIpv4RipRedistributeFirewall OBJECT-TYPE
	SYNTAX      INTEGER {
			    enable (1),
			    disable (2)
			    }
	MAX-ACCESS  read-write
	STATUS      current
	DESCRIPTION
	       "If enabled, firewall routes will be advertised by RIP."
	DEFVAL {2}
	::= {apIpv4Rip 12}

apIpv4RipFirewallMetric OBJECT-TYPE
    SYNTAX      INTEGER ( 1..15 )
	MAX-ACCESS  read-write
	STATUS      current
	DESCRIPTION
	       "If firewall routes are advertised by RIP, this is the metric
            to use when advertising the routes."
	DEFVAL {1}
	::= {apIpv4Rip 13}


-- RIP route advertisement table.  This table contains routes that
-- are advertised out all RIP interfaces, even if the route does not
-- exist in the routing table.

apIpv4RipAdvRouteTable OBJECT-TYPE
    SYNTAX   SEQUENCE OF ApIpv4RipAdvRouteEntry
    MAX-ACCESS   not-accessible
    STATUS   current
    DESCRIPTION
       "A list of routes that are advertised via all RIP interfaces."
    ::= { apIpv4Rip 8 }

apIpv4RipAdvRouteEntry OBJECT-TYPE
    SYNTAX   ApIpv4RipAdvRouteEntry
    MAX-ACCESS   not-accessible
    STATUS   current
    DESCRIPTION
        "A single route to advertise via all RIP interfaces."
    INDEX { apIpv4RipAdvRoutePrefix, apIpv4RipAdvRoutePrefixLen }
	--DEFAULT apjam-group apIpv4RipAdvRouteInst, apIpv4RipAdvRoutePrefix
	--DEFAULT apjam-popup-def apIpv4RipAdvRouteInst, Properties, local
	--DEFAULT apjam-popup-def apIpv4RipAdvRouteInst, Delete, special, apIpv4AdvRouteStatus
	--DEFAULT apjam-wizard	RIP Global Route Wizard, 1, images/arrowlogo.gif, "RIP global route setup wizard."
    ::= { apIpv4RipAdvRouteTable 1 }

ApIpv4RipAdvRouteEntry ::=
    SEQUENCE {
        apIpv4RipAdvRoutePrefix     IpAddress,
        apIpv4RipAdvRoutePrefixLen  INTEGER,
        apIpv4RipAdvRouteMetric     INTEGER,
        apIpv4RipAdvRouteStatus     RowStatus
    }

apIpv4RipAdvRoutePrefix OBJECT-TYPE
    SYNTAX   IpAddress
    MAX-ACCESS   read-only
    STATUS   current
    DESCRIPTION
        "The route prefix to be advertised."
	--DEFAULT ap-display-name	IP Address
	--DEFAULT apjam-popup-ref apIpv4RipAdvRouteInst, Properties
	--DEFAULT apjam-wizard-field	1, normal
	--DEFAULT apjam-noedit-dlg	True
    ::= { apIpv4RipAdvRouteEntry 1 }

apIpv4RipAdvRoutePrefixLen OBJECT-TYPE
	SYNTAX      INTEGER (1..32)
	MAX-ACCESS  read-only
	STATUS      current
	DESCRIPTION
	       "The network prefix length associated with this route."
	--DEFAULT ap-display-name	Prefix Length
	--DEFAULT apjam-popup-ref apIpv4RipAdvRouteInst, Properties
	--DEFAULT apjam-wizard-field	1, normal
	--DEFAULT apjam-noedit-dlg	True
	::= { apIpv4RipAdvRouteEntry 2 }

apIpv4RipAdvRouteMetric OBJECT-TYPE
	SYNTAX      INTEGER (1..15)
	MAX-ACCESS  read-create
	STATUS      current
	DESCRIPTION
	       "The metric to use when advertising this route."
	DEFVAL {1}
	--DEFAULT ap-display-name	Metric
	--DEFAULT apjam-popup-ref apIpv4RipAdvRouteInst, Properties
	--DEFAULT apjam-wizard-field	1, normal
	::= { apIpv4RipAdvRouteEntry 3 }

apIpv4RipAdvRouteStatus OBJECT-TYPE
	SYNTAX      RowStatus
	MAX-ACCESS  read-create
	STATUS      current
	DESCRIPTION
	       "(fill in later)"
	::= { apIpv4RipAdvRouteEntry 4 }

-- RIP per-interface route advertisement table.  This table contains routes
-- that are advertised out a specific RIP interface, even if the route does not
-- exist in the routing table.

apIpv4RipIfAdvRouteTable OBJECT-TYPE
    SYNTAX   SEQUENCE OF ApIpv4RipIfAdvRouteEntry
    MAX-ACCESS   not-accessible
    STATUS   current
    DESCRIPTION
       "A list of routes that are advertised via a specific RIP interface."
    ::= { apIpv4Rip 9 }

apIpv4RipIfAdvRouteEntry OBJECT-TYPE
    SYNTAX   ApIpv4RipIfAdvRouteEntry
    MAX-ACCESS   not-accessible
    STATUS   current
    DESCRIPTION
        "A single route to advertise via a specific RIP interface."
    INDEX { apIpv4RipIfAdvRouteAddress, apIpv4RipIfAdvRoutePrefix,
            apIpv4RipIfAdvRoutePrefixLen }
	--DEFAULT apjam-group apIpv4RipIfAdvRouteInst, apIpv4RipIfAdvRoutePrefix
	--DEFAULT apjam-popup-def apIpv4RipIfAdvRouteInst, Properties, local
	--DEFAULT apjam-popup-def apIpv4RipIfAdvRouteInst, Delete, special, apIpv4IfAdvRouteStatus
	--DEFAULT apjam-wizard	RIP Global Route Wizard, 1, images/arrowlogo.gif, "RIP Per interface route setup wizard."
    ::= { apIpv4RipIfAdvRouteTable 1 }

ApIpv4RipIfAdvRouteEntry ::=
    SEQUENCE {
        apIpv4RipIfAdvRouteAddress    IpAddress,
        apIpv4RipIfAdvRoutePrefix     IpAddress,
        apIpv4RipIfAdvRoutePrefixLen  INTEGER,
        apIpv4RipIfAdvRouteMetric     INTEGER,
        apIpv4RipIfAdvRouteStatus     RowStatus
    }

apIpv4RipIfAdvRouteAddress OBJECT-TYPE
    SYNTAX   IpAddress
    MAX-ACCESS   read-only
    STATUS   current
    DESCRIPTION
        "The address of the RIP interface.  If this is a valid unicast
         IP address, the interface is numbered.  Otherwise, it indicates
         the ifIndex of an unnumbered interface."
	--DEFAULT ap-display-name	Interface Address
	--DEFAULT apjam-popup-ref apIpv4RipIfAdvRouteInst, Properties
	--DEFAULT apjam-wizard-field	1, choice, rip2IfConfAddress( ), nodepend
	--DEFAULT apjam-noedit-dlg	True
    ::= { apIpv4RipIfAdvRouteEntry 1 }

apIpv4RipIfAdvRoutePrefix OBJECT-TYPE
    SYNTAX   IpAddress
    MAX-ACCESS   read-only
    STATUS   current
    DESCRIPTION
        "The route prefix to be advertised."
	--DEFAULT ap-display-name	IP Address
	--DEFAULT apjam-popup-ref apIpv4RipIfAdvRouteInst, Properties
	--DEFAULT apjam-wizard-field	1, normal
	--DEFAULT apjam-noedit-dlg	True
    ::= { apIpv4RipIfAdvRouteEntry 2 }

apIpv4RipIfAdvRoutePrefixLen OBJECT-TYPE
	SYNTAX      INTEGER (1..32)
	MAX-ACCESS  read-only
	STATUS      current
	DESCRIPTION
	       "The network prefix length associated with this route."
	--DEFAULT ap-display-name	Prefix Length
	--DEFAULT apjam-popup-ref apIpv4RipIfAdvRouteInst, Properties
	--DEFAULT apjam-wizard-field	1, normal
	--DEFAULT apjam-noedit-dlg	True
	::= { apIpv4RipIfAdvRouteEntry 3 }

apIpv4RipIfAdvRouteMetric OBJECT-TYPE
	SYNTAX      INTEGER (1..15)
	MAX-ACCESS  read-create
	STATUS      current
	DESCRIPTION
	       "The metric to use when advertising this route."
	DEFVAL {1}
	--DEFAULT ap-display-name	Metric
	--DEFAULT apjam-popup-ref apIpv4RipIfAdvRouteInst, Properties
	--DEFAULT apjam-wizard-field	1, normal
	::= { apIpv4RipIfAdvRouteEntry 4 }

apIpv4RipIfAdvRouteStatus OBJECT-TYPE
	SYNTAX      RowStatus
	MAX-ACCESS  read-create
	STATUS      current
	DESCRIPTION
	       "(fill in later)"
	::= { apIpv4RipIfAdvRouteEntry 5 }


-- RIP non-standard per-interface info table.

apIpv4RipIfTable OBJECT-TYPE
    SYNTAX   SEQUENCE OF ApIpv4RipIfEntry
    MAX-ACCESS   not-accessible
    STATUS   current
    DESCRIPTION
       "Per-interface RIP information."
    ::= { apIpv4Rip 10 }

apIpv4RipIfEntry OBJECT-TYPE
    SYNTAX   ApIpv4RipIfEntry
    MAX-ACCESS   not-accessible
    STATUS   current
    DESCRIPTION
        "Information for a single RIP interface."
    INDEX { apIpv4RipIfAddress }
    ::= { apIpv4RipIfTable 1 }

ApIpv4RipIfEntry ::=
    SEQUENCE {
        apIpv4RipIfAddress          IpAddress,
        apIpv4RipIfLogTx            TruthValue,
        apIpv4RipIfLogRx            TruthValue
    }

apIpv4RipIfAddress OBJECT-TYPE
    SYNTAX   IpAddress
    MAX-ACCESS   read-only
    STATUS   current
    DESCRIPTION
        "The address of the RIP interface.  If this is a valid unicast
         IP address, the interface is numbered.  Otherwise, it indicates
         the ifIndex of an unnumbered interface."
    ::= { apIpv4RipIfEntry 1 }

apIpv4RipIfLogTx OBJECT-TYPE
    SYNTAX   TruthValue
    MAX-ACCESS   read-create
    STATUS   current
    DESCRIPTION
        "If true, information will be written to the system log for each
         RIP packet transmitted."
    ::= { apIpv4RipIfEntry 2 }

apIpv4RipIfLogRx OBJECT-TYPE
    SYNTAX   TruthValue
    MAX-ACCESS   read-create
    STATUS   current
    DESCRIPTION
        "If true, information will be written to the system log for each
         RIP packet received."
    ::= { apIpv4RipIfEntry 3 }

END
