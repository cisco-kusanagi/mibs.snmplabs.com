--$Id: FLARION-FOAM-TRAP-MIB.txt,v 1.1.2.1 2004/11/01 21:56:19 mkanaka Exp $ 

FLARION-FOAM-TRAP-MIB DEFINITIONS ::= BEGIN

IMPORTS
        NOTIFICATION-TYPE
                FROM SNMPv2-SMI
       
        rrTrapSpecific, rrTimeStamp, rrSeqNum, rrSeverity,
        rrMoType, rrMoId, rrAddtlInfo
                FROM FLARION-TRAP-MIB;

--
-- Foam Releted Traps (specific 400 - 410)
--

foamDcgHeartbeat  NOTIFICATION-TYPE
    OBJECTS     { rrTimeStamp,
                  rrSeqNum,
                  rrSeverity,
                  rrMoType,
                  rrMoId,
                  rrAddtlInfo  
                }
    STATUS      current
    DESCRIPTION "Foam receive or miss heartbeat message from DCG."
    ::= { rrTrapSpecific 400 }

foamTxPowerEvent  NOTIFICATION-TYPE
    OBJECTS     { rrTimeStamp,
                  rrSeqNum,
                  rrSeverity,
                  rrMoType,
                  rrMoId,
                  rrAddtlInfo  
                }
    STATUS      current
    DESCRIPTION "Foam tx power threshold crossing event."
    ::= { rrTrapSpecific 401 }

foamRxOffsetFault  NOTIFICATION-TYPE
    OBJECTS     { rrTimeStamp,
                  rrSeqNum,
                  rrSeverity,
                  rrMoType,
                  rrMoId,
                  rrAddtlInfo 
                }
    STATUS      current
    DESCRIPTION "Foam rx offset fault condition."
    ::= { rrTrapSpecific 402 }

foamRxParityFault  NOTIFICATION-TYPE
    OBJECTS     { rrTimeStamp,
                  rrSeqNum,
                  rrSeverity,
                  rrMoType,
                  rrMoId,
                  rrAddtlInfo  
                }
    STATUS      current
    DESCRIPTION "Foam rx parity fault condition."
    ::= { rrTrapSpecific 403 }

foamDcgMessageInvalid  NOTIFICATION-TYPE
    OBJECTS     { rrTimeStamp,
                  rrSeqNum,
                  rrSeverity,
                  rrMoType,
                  rrMoId,
                  rrAddtlInfo  
                }
    STATUS      current
    DESCRIPTION "Message parameter from Dcg is invalid or missing."
    ::= { rrTrapSpecific 404 }

foamMissingTODMessage  NOTIFICATION-TYPE
    OBJECTS     { rrTimeStamp,
                  rrSeqNum,
                  rrSeverity,
                  rrMoType,
                  rrMoId,
                  rrAddtlInfo  
                }
    STATUS      current
    DESCRIPTION "Foam did not receive time-of-day message from DCG 
    			for the past 30 seconds."
    ::= { rrTrapSpecific 405 }

foamTODDeviation  NOTIFICATION-TYPE
    OBJECTS     { rrTimeStamp,
                  rrSeqNum,
                  rrSeverity,
                  rrMoType,
                  rrMoId,
                  rrAddtlInfo  
                }
    STATUS      current
    DESCRIPTION "The difference of time-of-day received from DCG and from NTP 
            is more than 1 second."
    ::= { rrTrapSpecific 406 }
 
foamHsspcCriticalFault   NOTIFICATION-TYPE
    OBJECTS     { rrTimeStamp,
                  rrSeqNum,
                  rrSeverity,
                  rrMoType,
                  rrMoId,
                  rrAddtlInfo  
                }
    STATUS      current
    DESCRIPTION "A critical hsspc fault has been detected."
    ::= { rrTrapSpecific 410 }

foamHsspcMajorFault   	NOTIFICATION-TYPE
    OBJECTS     { rrTimeStamp,
                  rrSeqNum,
                  rrSeverity,
                  rrMoType,
                  rrMoId,
                  rrAddtlInfo  
                }
    STATUS      current
    DESCRIPTION "A major hsspc fault has been detected."
    ::= { rrTrapSpecific 411 }

foamHsspcMinorFault   NOTIFICATION-TYPE
    OBJECTS     { rrTimeStamp,
                  rrSeqNum,
                  rrSeverity,
                  rrMoType,
                  rrMoId,
                  rrAddtlInfo  
                }
    STATUS      current
    DESCRIPTION "A minor hsspc fault has been detected."
    ::= { rrTrapSpecific 412 }


foamHsspcEvent  NOTIFICATION-TYPE
    OBJECTS     { rrTimeStamp,
                  rrSeqNum,
                  rrSeverity,
                  rrMoType,
                  rrMoId,
                  rrAddtlInfo  
                }
    STATUS      current
    DESCRIPTION "A hsspc event has been detected."
    ::= { rrTrapSpecific 413 }

foamBackplaneTempStatus  NOTIFICATION-TYPE
    OBJECTS     { rrTimeStamp,
                  rrSeqNum,
                  rrSeverity,
                  rrMoType,
                  rrMoId,
                  rrAddtlInfo  
                }
    STATUS      current
    DESCRIPTION "Foam backplane temperature status."
    ::= { rrTrapSpecific 420 }


END
