-- *********************************************************************
-- CISCO-UNIFIED-COMPUTING-FABRIC-MIB.my
-- 
-- MIB representation of the Cisco Unified Computing System
-- FABRIC management information model package
-- 
-- Created January 2016 by Charles Bullis
-- 
-- Copyright (c) 2005-2016 Cisco Systems, Inc. All rights reserved.
-- 
-- *********************************************************************

CISCO-UNIFIED-COMPUTING-FABRIC-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoUnifiedComputingMIBObjects,
    CucsManagedObjectId,
    CucsManagedObjectDn
        FROM CISCO-UNIFIED-COMPUTING-MIB
    CucsComputeDiscovery,
    CucsConditionRemoteInvRslt,
    CucsEquipmentBoardAggregationRole,
    CucsEquipmentConfigIssues,
    CucsEquipmentConnectionStatus,
    CucsEquipmentEvacState,
    CucsEquipmentFabricEpType,
    CucsEquipmentSlotStatus,
    CucsFabricADceSwSrvEpTransport,
    CucsFabricAEthEstcEpIfRole,
    CucsFabricAEthEstcEpTransport,
    CucsFabricAEthEstcEpType,
    CucsFabricAEthLanEpTransport,
    CucsFabricAFcEstcEpTransport,
    CucsFabricAFcEstcEpType,
    CucsFabricAFcSanEpTransport,
    CucsFabricAFcoeEstcEpIfRole,
    CucsFabricAFcoeEstcEpTransport,
    CucsFabricAFcoeEstcEpType,
    CucsFabricAFcoeSanEpTransport,
    CucsFabricAVlanAssocPrimaryVlanSwitchId,
    CucsFabricAVlanSharing,
    CucsFabricAVlanTransport,
    CucsFabricAVlanType,
    CucsFabricAVsanTransport,
    CucsFabricAVsanType,
    CucsFabricAccessType,
    CucsFabricAdminState,
    CucsFabricBHVlanSwitchId,
    CucsFabricBladeLifeCycle,
    CucsFabricBreakoutPortId,
    CucsFabricBreakoutSlotId,
    CucsFabricBreakoutType,
    CucsFabricCIoEpAdminState,
    CucsFabricCIoEpIfType,
    CucsFabricCartridgeSlotEpFsmCurrentFsm,
    CucsFabricCartridgeSlotEpFsmStageName,
    CucsFabricCartridgeSlotEpFsmTaskItem,
    CucsFabricCartridgeSlotEpSlotId,
    CucsFabricCdpLinkPolicyAdminState,
    CucsFabricCloudType,
    CucsFabricComputeEpIfRole,
    CucsFabricComputeEpType,
    CucsFabricComputeMSlotEpFsmCurrentFsm,
    CucsFabricComputeMSlotEpFsmStageName,
    CucsFabricComputeMSlotEpFsmTaskItem,
    CucsFabricComputeMSlotEpServerInstanceId,
    CucsFabricComputeMSlotEpSlotId,
    CucsFabricComputePhEpAdminState,
    CucsFabricComputeSlotEpFsmCurrentFsm,
    CucsFabricComputeSlotEpFsmStageName,
    CucsFabricComputeSlotEpFsmTaskItem,
    CucsFabricComputeSlotEpSlotId,
    CucsFabricConfMode,
    CucsFabricConfState,
    CucsFabricConfigState,
    CucsFabricDceSwSrvEpPortId,
    CucsFabricDceSwSrvEpSlotId,
    CucsFabricDceSwSrvPcAdminState,
    CucsFabricDceSwSrvPcEpPortId,
    CucsFabricDceSwSrvPcEpSlotId,
    CucsFabricDceSwSrvPcPortId,
    CucsFabricDceSwSrvPcTransport,
    CucsFabricDefaultZoningState,
    CucsFabricDirection,
    CucsFabricEpMgrFsmCurrentFsm,
    CucsFabricEpMgrFsmStageName,
    CucsFabricEpMgrFsmTaskFlags,
    CucsFabricEpMgrFsmTaskItem,
    CucsFabricEquipmentEpIfRole,
    CucsFabricEquipmentEpType,
    CucsFabricEstcEpIfRole,
    CucsFabricEstcPcIfRole,
    CucsFabricEstcPcType,
    CucsFabricEthCdpPolicyProtocol,
    CucsFabricEthEstcEpPortId,
    CucsFabricEthEstcEpPrio,
    CucsFabricEthEstcEpSlotId,
    CucsFabricEthEstcEpTransport,
    CucsFabricEthEstcEpType,
    CucsFabricEthEstcOperPortMode,
    CucsFabricEthEstcPcEpPortId,
    CucsFabricEthEstcPcEpSlotId,
    CucsFabricEthEstcPcTransport,
    CucsFabricEthEstcPortMode,
    CucsFabricEthEstcTransport,
    CucsFabricEthEstcType,
    CucsFabricEthFlowMonLanTransport,
    CucsFabricEthFlowMonLanType,
    CucsFabricEthFlowMonSourceType,
    CucsFabricEthFlowMonSrcRefType,
    CucsFabricEthLanEpVlanStatus,
    CucsFabricEthLanFlowMonCollectorTransport,
    CucsFabricEthLanFlowMonExporterTransport,
    CucsFabricEthLanFlowMonSrcEpTransport,
    CucsFabricEthLanFlowMonTransport,
    CucsFabricEthLanFlowMonitorTransport,
    CucsFabricEthLanFlowMonitoringType,
    CucsFabricEthLanPcTransport,
    CucsFabricEthLanPcVlanStatus,
    CucsFabricEthLanTransport,
    CucsFabricEthLinkPolicyType,
    CucsFabricEthMonDestEpAdminSpeed,
    CucsFabricEthMonDestEpIfRole,
    CucsFabricEthMonDestEpPortId,
    CucsFabricEthMonDestEpSlotId,
    CucsFabricEthMonDestEpType,
    CucsFabricEthMonFiltEpType,
    CucsFabricEthMonFiltRefType,
    CucsFabricEthMonLanTransport,
    CucsFabricEthMonLanType,
    CucsFabricEthMonSrcEpType,
    CucsFabricEthMonSrcRefType,
    CucsFabricEthMonTransport,
    CucsFabricEthMonType,
    CucsFabricEthPcProtocol,
    CucsFabricEthSourceType,
    CucsFabricEthTargetEpTransport,
    CucsFabricEthUdldPolicyProtocol,
    CucsFabricEthVlanPcTransport,
    CucsFabricExternalEpAdminState,
    CucsFabricExternalEpLocale,
    CucsFabricExternalLocale,
    CucsFabricExternalPcLocale,
    CucsFabricFcEstcEpPortId,
    CucsFabricFcEstcEpSlotId,
    CucsFabricFcEstcTransport,
    CucsFabricFcEstcType,
    CucsFabricFcMonDestEpAdminSpeed,
    CucsFabricFcMonDestEpIfRole,
    CucsFabricFcMonDestEpPortId,
    CucsFabricFcMonDestEpSlotId,
    CucsFabricFcMonDestEpType,
    CucsFabricFcMonFiltEpType,
    CucsFabricFcMonFiltRefType,
    CucsFabricFcMonSanTransport,
    CucsFabricFcMonSanType,
    CucsFabricFcMonSrcEpType,
    CucsFabricFcMonSrcRefType,
    CucsFabricFcMonTransport,
    CucsFabricFcMonType,
    CucsFabricFcSanEpPortId,
    CucsFabricFcSanEpSlotId,
    CucsFabricFcSanPcEpPortId,
    CucsFabricFcSanPcEpSlotId,
    CucsFabricFcSanPcTransport,
    CucsFabricFcSanTransport,
    CucsFabricFcSanUplinkTrunking,
    CucsFabricFcSourceType,
    CucsFabricFcVsanPcTransport,
    CucsFabricFcVsanPortEpPortId,
    CucsFabricFcVsanPortEpSlotId,
    CucsFabricFcZoneSharingMode,
    CucsFabricFcoeEstcEpPortId,
    CucsFabricFcoeEstcEpSlotId,
    CucsFabricFcoeSanEpPortId,
    CucsFabricFcoeSanEpSlotId,
    CucsFabricFcoeSanPcEpPortId,
    CucsFabricFcoeSanPcEpSlotId,
    CucsFabricFcoeSanPcTransport,
    CucsFabricFcoeVsanPcTransport,
    CucsFabricFcoeVsanPortEpPortId,
    CucsFabricFcoeVsanPortEpSlotId,
    CucsFabricFillPattern,
    CucsFabricFlowMonCollectorLocale,
    CucsFabricFlowMonDefType,
    CucsFabricFlowMonIpv4Keys,
    CucsFabricFlowMonIpv6Keys,
    CucsFabricFlowMonKeyType,
    CucsFabricFlowMonL2Keys,
    CucsFabricFlowMonNonKeys,
    CucsFabricFlowMonitoringCategoryAdminState,
    CucsFabricInternalDceSrvTransport,
    CucsFabricInternalDceSrvType,
    CucsFabricInternalEpAdminState,
    CucsFabricInternalEpLocale,
    CucsFabricInternalLocale,
    CucsFabricInternalPcLocale,
    CucsFabricLacpRate,
    CucsFabricLacpSuspend,
    CucsFabricLanCloudFsmCurrentFsm,
    CucsFabricLanCloudFsmStageName,
    CucsFabricLanCloudFsmTaskItem,
    CucsFabricLanCloudPolicyVlanCompression,
    CucsFabricLanCloudVlanCompression,
    CucsFabricLanConfigIssues,
    CucsFabricLanEpIfRole,
    CucsFabricLanEpType,
    CucsFabricLanFlowMonCollectorType,
    CucsFabricLanFlowMonExporterType,
    CucsFabricLanFlowMonSrcEpType,
    CucsFabricLanFlowMonType,
    CucsFabricLanFlowMonitorType,
    CucsFabricLanPcIfRole,
    CucsFabricLanPcType,
    CucsFabricLanType,
    CucsFabricLifeCycle,
    CucsFabricMemberStatus,
    CucsFabricMembershipStatus,
    CucsFabricMonAdminState,
    CucsFabricMonOperState,
    CucsFabricMonOperStateReason,
    CucsFabricNFExporterVersion,
    CucsFabricNFTransport,
    CucsFabricNetGroupConfigIssues,
    CucsFabricNetGroupSwitchId,
    CucsFabricNetGroupType,
    CucsFabricNetflowCollectorFlowProtocol,
    CucsFabricNetflowConfigIssues,
    CucsFabricNetflowMonExporterProtocol,
    CucsFabricNetflowMonSessionAdminState,
    CucsFabricNetflowMonSessionProtocol,
    CucsFabricNetflowMonSrcEpProtocol,
    CucsFabricNetflowMonSrcRefProtocol,
    CucsFabricNetflowMonitorFlowMonProtocol,
    CucsFabricOwner,
    CucsFabricPIoEpIfType,
    CucsFabricPIoEpOperState,
    CucsFabricPIoEpPortId,
    CucsFabricPIoEpSlotId,
    CucsFabricPathEpIfType,
    CucsFabricPathEpLocale,
    CucsFabricPcConfigStatus,
    CucsFabricPinTargetAggrPortId,
    CucsFabricPinTargetPortId,
    CucsFabricPinTargetSlotId,
    CucsFabricPolicyConfigIssues,
    CucsFabricPoolMemberConfigIssues,
    CucsFabricQuerierType,
    CucsFabricRecoveryAction,
    CucsFabricReqIssues,
    CucsFabricSanCloudFsmCurrentFsm,
    CucsFabricSanCloudFsmStageName,
    CucsFabricSanCloudFsmTaskItem,
    CucsFabricSanConfigIssues,
    CucsFabricSanEpIfRole,
    CucsFabricSanEpType,
    CucsFabricSanPcIfRole,
    CucsFabricSanPcType,
    CucsFabricSanType,
    CucsFabricSlotAdminState,
    CucsFabricSnoopingType,
    CucsFabricStatus,
    CucsFabricSubGroupAggrPortId,
    CucsFabricSubGroupConfigState,
    CucsFabricSubGroupSlotId,
    CucsFabricSwChEpIfRole,
    CucsFabricSwChEpType,
    CucsFabricSwChPhEpAdminState,
    CucsFabricSwSrvEpIfRole,
    CucsFabricSwSrvEpType,
    CucsFabricSwSrvPcIfRole,
    CucsFabricSwSrvPcType,
    CucsFabricSwSubGroupAggrPortId,
    CucsFabricSwSubGroupConfigState,
    CucsFabricSwSubGroupSlotId,
    CucsFabricSwitchingMode,
    CucsFabricTargetEpType,
    CucsFabricTargetStatus,
    CucsFabricTrafficDirection,
    CucsFabricUdldLinkPolicyAdminState,
    CucsFabricUdldLinkPolicyMode,
    CucsFabricUdldOperState,
    CucsFabricVConInstType,
    CucsFabricVConMappingScheme,
    CucsFabricVConPlacementPref,
    CucsFabricVConSelectPref,
    CucsFabricVConSharePref,
    CucsFabricVConTransportPref,
    CucsFabricVlanAssocPrimaryVlanState,
    CucsFabricVlanCompType,
    CucsFabricVlanConfigIssues,
    CucsFabricVlanOperState,
    CucsFabricVlanOverlapState,
    CucsFabricVlanSwitchId,
    CucsFabricVnetEpIfRole,
    CucsFabricVnetEpLocale,
    CucsFabricVnetEpPolicyOwner,
    CucsFabricVnetEpSyncEpFsmCurrentFsm,
    CucsFabricVnetEpSyncEpFsmStageName,
    CucsFabricVnetEpSyncEpFsmTaskItem,
    CucsFabricVsanOperState,
    CucsFabricVsanSwitchId,
    CucsFabricWarnings,
    CucsFabricZoningState,
    CucsFsmCompletion,
    CucsFsmFlags,
    CucsFsmFsmStageStatus,
    CucsLicenseState,
    CucsNetworkConnectionType,
    CucsNetworkLocale,
    CucsNetworkPortOperState,
    CucsNetworkPortRole,
    CucsNetworkSide,
    CucsNetworkSwitchId,
    CucsNetworkTransport,
    CucsNetworkVnetEpIfType,
    CucsPolicyPolicyOwner,
    CucsPoolPoolAssignmentOrder,
    CucsPortEthAdminSpeed,
    CucsPortEthSpeed,
    CucsPortSpeed,
    CucsQosPriority
        FROM CISCO-UNIFIED-COMPUTING-TC-MIB;

cucsFabricObjects MODULE-IDENTITY
    LAST-UPDATED    "201601180000Z"
    ORGANIZATION    "Cisco Systems Inc."
    CONTACT-INFO
        "Cisco Systems
        Customer Service
        
        Postal: 170 W Tasman Drive
        San Jose, CA  95134
        USA
        
        Tel: +1 800 553 -NETS
        
        E-mail: cs-san@cisco.com, cs-lan-switch-snmp@cisco.com"
    DESCRIPTION
        "MIB representation of the Cisco Unified Computing System
        FABRIC management information model package"
    ::= { ciscoUnifiedComputingMIBObjects 19 }

cucsFabricBHVlanTable OBJECT-TYPE
    SYNTAX           SEQUENCE OF CucsFabricBHVlanEntry
    MAX-ACCESS       not-accessible
    STATUS           current
    DESCRIPTION
        "Cisco UCS fabric:BHVlan managed object table"
    ::= { cucsFabricObjects 66 }

cucsFabricBHVlanEntry OBJECT-TYPE
    SYNTAX           CucsFabricBHVlanEntry
    MAX-ACCESS       not-accessible
    STATUS           current
    DESCRIPTION
        "Entry for the cucsFabricBHVlanTable table."
    INDEX { cucsFabricBHVlanInstanceId }
    ::= { cucsFabricBHVlanTable 1 }

CucsFabricBHVlanEntry ::= SEQUENCE {
    cucsFabricBHVlanInstanceId                                       CucsManagedObjectId,
    cucsFabricBHVlanDn                                               CucsManagedObjectDn,
    cucsFabricBHVlanRn                                               SnmpAdminString,
    cucsFabricBHVlanEpDn                                             SnmpAdminString,
    cucsFabricBHVlanId                                               Gauge32,
    cucsFabricBHVlanIfRole                                           CucsFabricVnetEpIfRole,
    cucsFabricBHVlanIfType                                           CucsNetworkVnetEpIfType,
    cucsFabricBHVlanLocale                                           CucsFabricVnetEpLocale,
    cucsFabricBHVlanName                                             SnmpAdminString,
    cucsFabricBHVlanPeerDn                                           SnmpAdminString,
    cucsFabricBHVlanPubNwDn                                          SnmpAdminString,
    cucsFabricBHVlanPubNwId                                          Gauge32,
    cucsFabricBHVlanPubNwName                                        SnmpAdminString,
    cucsFabricBHVlanSharing                                          CucsFabricAVlanSharing,
    cucsFabricBHVlanSwitchId                                         CucsFabricBHVlanSwitchId,
    cucsFabricBHVlanTransport                                        CucsFabricAVlanTransport,
    cucsFabricBHVlanType                                             CucsFabricAVlanType,
    cucsFabricBHVlanOperState                                        CucsFabricVlanOperState,
    cucsFabricBHVlanPolicyOwner                                      CucsFabricVnetEpPolicyOwner,
    cucsFabricBHVlanAssocPrimaryVlanState                            CucsFabricVlanAssocPrimaryVlanState,
    cucsFabricBHVlanAssocPrimaryVlanSwitchId                         CucsFabricAVlanAssocPrimaryVlanSwitchId,
    cucsFabricBHVlanOverlapStateForA                                 CucsFabricVlanOverlapState,
    cucsFabricBHVlanOverlapStateForB                                 CucsFabricVlanOverlapState
}

cucsFabricBHVlanInstanceId OBJECT-TYPE
    SYNTAX       CucsManagedObjectId
    MAX-ACCESS   not-accessible
    STATUS       current
    DESCRIPTION
        "Instance identifier of the managed object."
    ::= { cucsFabricBHVlanEntry 1 }

cucsFabricBHVlanDn OBJECT-TYPE
    SYNTAX       CucsManagedObjectDn
    MAX-ACCESS   read-only
    STATUS       current
    DESCRIPTION
        "Cisco UCS fabric:BHVlan:dn managed object property"
    ::= { cucsFabricBHVlanEntry 2 }

cucsFabricBHVlanRn OBJECT-TYPE
    SYNTAX       SnmpAdminString
    MAX-ACCESS   read-only
    STATUS       current
    DESCRIPTION
        "Cisco UCS fabric:BHVlan:rn managed object property"
    ::= { cucsFabricBHVlanEntry 3 }

cucsFabricBHVlanEpDn OBJECT-TYPE
    SYNTAX       SnmpAdminString
    MAX-ACCESS   read-only
    STATUS       current
    DESCRIPTION
        "Cisco UCS fabric:BHVlan:epDn managed object property"
    ::= { cucsFabricBHVlanEntry 4 }

cucsFabricBHVlanId OBJECT-TYPE
    SYNTAX       Gauge32
    MAX-ACCESS   read-only
    STATUS       current
    DESCRIPTION
        "Cisco UCS fabric:BHVlan:id managed object property"
    ::= { cucsFabricBHVlanEntry 5 }

cucsFabricBHVlanIfRole OBJECT-TYPE
    SYNTAX       CucsFabricVnetEpIfRole
    MAX-ACCESS   read-only
    STATUS       current
    DESCRIPTION
        "Cisco UCS fabric:BHVlan:ifRole managed object property"
    ::= { cucsFabricBHVlanEntry 6 }

cucsFabricBHVlanIfType OBJECT-TYPE
    SYNTAX       CucsNetworkVnetEpIfType
    MAX-ACCESS   read-only
    STATUS       current
    DESCRIPTION
        "Cisco UCS fabric:BHVlan:ifType managed object property"
    ::= { cucsFabricBHVlanEntry 7 }

cucsFabricBHVlanLocale OBJECT-TYPE
    SYNTAX       CucsFabricVnetEpLocale
    MAX-ACCESS   read-only
    STATUS       current
    DESCRIPTION
        "Cisco UCS fabric:BHVlan:locale managed object property"
    ::= { cucsFabricBHVlanEntry 8 }

cucsFabricBHVlanName OBJECT-TYPE
    SYNTAX       SnmpAdminString
    MAX-ACCESS   read-only
    STATUS       current
    DESCRIPTION
        "Cisco UCS fabric:BHVlan:name managed object property"
    ::= { cucsFabricBHVlanEntry 9 }

cucsFabricBHVlanPeerDn OBJECT-TYPE
    SYNTAX       SnmpAdminString
    MAX-ACCESS   read-only
    STATUS       current
    DESCRIPTION
        "Cisco UCS fabric:BHVlan:peerDn managed object property"
    ::= { cucsFabricBHVlanEntry 10 }

cucsFabricBHVlanPubNwDn OBJECT-TYPE
    SYNTAX       SnmpAdminString
    MAX-ACCESS   read-only
    STATUS       current
    DESCRIPTION
        "Cisco UCS fabric:BHVlan:pubNwDn managed object property"
    ::= { cucsFabricBHVlanEntry 11 }

cucsFabricBHVlanPubNwId OBJECT-TYPE
    SYNTAX       Gauge32
    MAX-ACCESS   read-only
    STATUS       current
    DESCRIPTION
        "Cisco UCS fabric:BHVlan:pubNwId managed object property"
    ::= { cucsFabricBHVlanEntry 12 }

cucsFabricBHVlanPubNwName OBJECT-TYPE
    SYNTAX       SnmpAdminString
    MAX-ACCESS   read-only
    STATUS       current
    DESCRIPTION
        "Cisco UCS fabric:BHVlan:pubNwName managed object property"
    ::= { cucsFabricBHVlanEntry 13 }

cucsFabricBHVlanSharing OBJECT-TYPE
    SYNTAX       CucsFabricAVlanSharing
    MAX-ACCESS   read-only
    STATUS       current
    DESCRIPTION
        "Cisco UCS fabric:BHVlan:sharing managed object property"
    ::= { cucsFabricBHVlanEntry 14 }

cucsFabricBHVlanSwitchId OBJECT-TYPE
    SYNTAX       CucsFabricBHVlanSwitchId
    MAX-ACCESS   read-only
    STATUS       current
    DESCRIPTION
        "Cisco UCS fabric:BHVlan:switchId managed object property"
    ::= { cucsFabricBHVlanEntry 15 }

cucsFabricBHVlanTransport OBJECT-TYPE
    SYNTAX       CucsFabricAVlanTransport
    MAX-ACCESS   read-only
    STATUS       current
    DESCRIPTION
        "Cisco UCS fabric:BHVlan:transport managed object property"
    ::= { cucsFabricBHVlanEntry 16 }

cucsFabricBHVlanType OBJECT-TYPE
    SYNTAX       CucsFabricAVlanType
    MAX-ACCESS   read-only
    STATUS       current
    DESCRIPTION
        "Cisco UCS fabric:BHVlan:type managed object property"
    ::= { cucsFabricBHVlanEntry 17 }

cucsFabricBHVlanOperState OBJECT-TYPE
    SYNTAX       CucsFabricVlanOperState
    MAX-ACCESS   read-only
    STATUS       current
    DESCRIPTION
        "Cisco UCS fabric:BHVlan:operState managed object property"
    ::= { cucsFabricBHVlanEntry 18 }

cucsFabricBHVlanPolicyOwner OBJECT-TYPE
    SYNTAX       CucsFabricVnetEpPolicyOwner
    MAX-ACCESS   read-only
    STATUS       current
    DESCRIPTION
        "Cisco UCS fabric:BHVlan:policyOwner managed object property"
    ::= { cucsFabricBHVlanEntry 20 }

cucsFabricBHVlanAssocPrimaryVlanState OBJECT-TYPE
    SYNTAX       CucsFabricVlanAssocPrimaryVlanState
    MAX-ACCESS   read-only
    STATUS       current
    DESCRIPTION
        "Cisco UCS fabric:BHVlan:assocPrimaryVlanState
        managed object property"
    ::= { cucsFabricBHVlanEntry 21 }

cucsFabricBHVlanAssocPrimaryVlanSwitchId OBJECT-TYPE
    SYNTAX       CucsFabricAVlanAssocPrimaryVlanSwitchId
    MAX-ACCESS   read-only
    STATUS       current
    DESCRIPTION
        "Cisco UCS fabric:BHVlan:assocPrimaryVlanSwitchId
        managed object property"
    ::= { cucsFabricBHVlanEntry 22 }

cucsFabricBHVlanOverlapStateForA OBJECT-TYPE
    SYNTAX       CucsFabricVlanOverlapState
    MAX-ACCESS   read-only
    STATUS       current
    DESCRIPTION
        "Cisco UCS fabric:BHVlan:overlapStateForA managed object property"
    ::= { cucsFabricBHVlanEntry 23 }

cucsFabricBHVlanOverlapStateForB OBJECT-TYPE
    SYNTAX       CucsFabricVlanOverlapState
    MAX-ACCESS   read-only
    STATUS       current
    DESCRIPTION
        "Cisco UCS fabric:BHVlan:overlapStateForB managed object property"
    ::= { cucsFabricBHVlanEntry 24 }

cucsFabricBreakoutTable OBJECT-TYPE
    SYNTAX           SEQUENCE OF CucsFabricBreakoutEntry
    MAX-ACCESS       not-accessible
    STATUS           current
    DESCRIPTION
        "Cisco UCS fabric:Breakout managed object table"
    ::= { cucsFabricObjects 135 }

cucsFabricBreakoutEntry OBJECT-TYPE
    SYNTAX           CucsFabricBreakoutEntry
    MAX-ACCESS       not-accessible
    STATUS           current
    DESCRIPTION
        "Entry for the cucsFabricBreakoutTable table."
    INDEX { cucsFabricBreakoutInstanceId }
    ::= { cucsFabricBreakoutTable 1 }

CucsFabricBreakoutEntry ::= SEQUENCE {
    cucsFabricBreakoutInstanceId                                     CucsManagedObjectId,
    cucsFabricBreakoutDn                                             CucsManagedObjectDn,
    cucsFabricBreakoutRn                                             SnmpAdminString,
    cucsFabricBreakoutBreakoutType                                   CucsFabricBreakoutType,
    cucsFabricBreakoutPortId                                         CucsFabricBreakoutPortId,
    cucsFabricBreakoutSlotId                                         CucsFabricBreakoutSlotId
}

cucsFabricBreakoutInstanceId OBJECT-TYPE
    SYNTAX       CucsManagedObjectId
    MAX-ACCESS   not-accessible
    STATUS       current
    DESCRIPTION
        "Instance identifier of the managed object."
    ::= { cucsFabricBreakoutEntry 1 }

cucsFabricBreakoutDn OBJECT-TYPE
    SYNTAX       CucsManagedObjectDn
    MAX-ACCESS   read-only
    STATUS       current
    DESCRIPTION
        "Cisco UCS fabric:Breakout:dn managed object property"
    ::= { cucsFabricBreakoutEntry 2 }

cucsFabricBreakoutRn OBJECT-TYPE
    SYNTAX       SnmpAdminString
    MAX-ACCESS   read-only
    STATUS       current
    DESCRIPTION
        "Cisco UCS fabric:Breakout:rn managed object property"
    ::= { cucsFabricBreakoutEntry 3 }

cucsFabricBreakoutBreakoutType OBJECT-TYPE
    SYNTAX       CucsFabricBreakoutType
    MAX-ACCESS   read-only
    STATUS       current
    DESCRIPTION
        "Cisco UCS fabric:Breakout:breakoutType managed object property"
    ::= { cucsFabricBreakoutEntry 4 }

cucsFabricBreakoutPortId OBJECT-TYPE
    SYNTAX       CucsFabricBreakoutPortId
    MAX-ACCESS   read-only
    STATUS       current
    DESCRIPTION
        "Cisco UCS fabric:Breakout:portId managed object property"
    ::= { cucsFabricBreakoutEntry 5 }

cucsFabricBreakoutSlotId OBJECT-TYPE
    SYNTAX       CucsFabricBreakoutSlotId
    MAX-ACCESS   read-only
    STATUS       current
    DESCRIPTION
        "Cisco UCS fabric:Breakout:slotId managed object property"
    ::= { cucsFabricBreakoutEntry 6 }

cucsFabricCablingTable OBJECT-TYPE
    SYNTAX           SEQUENCE OF CucsFabricCablingEntry
    MAX-ACCESS       not-accessible
    STATUS           current
    DESCRIPTION
        "Cisco UCS fabric:Cabling managed object table"
    ::= { cucsFabricObjects 137 }

cucsFabricCablingEntry OBJECT-TYPE
    SYNTAX           CucsFabricCablingEntry
    MAX-ACCESS       not-accessible
    STATUS           current
    DESCRIPTION
        "Entry for the cucsFabricCablingTable table."
    INDEX { cucsFabricCablingInstanceId }
    ::= { cucsFabricCablingTable 1 }

CucsFabricCablingEntry ::= SEQUENCE {
    cucsFabricCablingInstanceId                                      CucsManagedObjectId,
    cucsFabricCablingDn                                              CucsManagedObjectDn,
    cucsFabricCablingRn                                              SnmpAdminString
}

cucsFabricCablingInstanceId OBJECT-TYPE
    SYNTAX       CucsManagedObjectId
    MAX-ACCESS   not-accessible
    STATUS       current
    DESCRIPTION
        "Instance identifier of the managed object."
    ::= { cucsFabricCablingEntry 1 }

cucsFabricCablingDn OBJECT-TYPE
    SYNTAX       CucsManagedObjectDn
    MAX-ACCESS   read-only
    STATUS       current
    DESCRIPTION
        "Cisco UCS fabric:Cabling:dn managed object property"
    ::= { cucsFabricCablingEntry 2 }

cucsFabricCablingRn OBJECT-TYPE
    SYNTAX       SnmpAdminString
    MAX-ACCESS   read-only
    STATUS       current
    DESCRIPTION
        "Cisco UCS fabric:Cabling:rn managed object property"
    ::= { cucsFabricCablingEntry 3 }

cucsFabricCablingSwTable OBJECT-TYPE
    SYNTAX           SEQUENCE OF CucsFabricCablingSwEntry
    MAX-ACCESS       not-accessible
    STATUS           current
    DESCRIPTION
        "Cisco UCS fabric:CablingSw managed object table"
    ::= { cucsFabricObjects 138 }

cucsFabricCablingSwEntry OBJECT-TYPE
    SYNTAX           CucsFabricCablingSwEntry
    MAX-ACCESS       not-accessible
    STATUS           current
    DESCRIPTION
        "Entry for the cucsFabricCablingSwTable table."
    INDEX { cucsFabricCablingSwInstanceId }
    ::= { cucsFabricCablingSwTable 1 }

CucsFabricCablingSwEntry ::= SEQUENCE {
    cucsFabricCablingSwInstanceId                                    CucsManagedObjectId,
    cucsFabricCablingSwDn                                            CucsManagedObjectDn,
    cucsFabricCablingSwRn                                            SnmpAdminString,
    cucsFabricCablingSwId                                            CucsNetworkSwitchId,
    cucsFabricCablingSwLocale                                        CucsFabricExternalLocale,
    cucsFabricCablingSwName                                          SnmpAdminString,
    cucsFabricCablingSwTransport                                     CucsNetworkTransport,
    cucsFabricCablingSwType                                          CucsNetworkConnectionType
}

cucsFabricCablingSwInstanceId OBJECT-TYPE
    SYNTAX       CucsManagedObjectId
    MAX-ACCESS   not-accessible
    STATUS       current
    DESCRIPTION
        "Instance identifier of the managed object."
    ::= { cucsFabricCablingSwEntry 1 }

cucsFabricCablingSwDn OBJECT-TYPE
    SYNTAX       CucsManagedObjectDn
    MAX-ACCESS   read-only
    STATUS       current
    DESCRIPTION
        "Cisco UCS fabric:CablingSw:dn managed object property"
    ::= { cucsFabricCablingSwEntry 2 }

cucsFabricCablingSwRn OBJECT-TYPE
    SYNTAX       SnmpAdminString
    MAX-ACCESS   read-only
    STATUS       current
    DESCRIPTION
        "Cisco UCS fabric:CablingSw:rn managed object property"
    ::= { cucsFabricCablingSwEntry 3 }

cucsFabricCablingSwId OBJECT-TYPE
    SYNTAX       CucsNetworkSwitchId
    MAX-ACCESS   read-only
    STATUS       current
    DESCRIPTION
        "Cisco UCS fabric:CablingSw:id managed object property"
    ::= { cucsFabricCablingSwEntry 4 }

cucsFabricCablingSwLocale OBJECT-TYPE
    SYNTAX       CucsFabricExternalLocale
    MAX-ACCESS   read-only
    STATUS       current
    DESCRIPTION
        "Cisco UCS fabric:CablingSw:locale managed object property"
    ::= { cucsFabricCablingSwEntry 5 }

cucsFabricCablingSwName OBJECT-TYPE
    SYNTAX       SnmpAdminString
    MAX-ACCESS   read-only
    STATUS       current
    DESCRIPTION
        "Cisco UCS fabric:CablingSw:name managed object property"
    ::= { cucsFabricCablingSwEntry 6 }

cucsFabricCablingSwTransport OBJECT-TYPE
    SYNTAX       CucsNetworkTransport
    MAX-ACCESS   read-only
    STATUS       current
    DESCRIPTION
        "Cisco UCS fabric:CablingSw:transport managed object property"
    ::= { cucsFabricCablingSwEntry 7 }

cucsFabricCablingSwType OBJECT-TYPE
    SYNTAX       CucsNetworkConnectionType
    MAX-ACCESS   read-only
    STATUS       current
    DESCRIPTION
        "Cisco UCS fabric:CablingSw:type managed object property"
    ::= { cucsFabricCablingSwEntry 8 }

cucsFabricCartridgePhEpTable OBJECT-TYPE
    SYNTAX           SEQUENCE OF CucsFabricCartridgePhEpEntry
    MAX-ACCESS       not-accessible
    STATUS           current
    DESCRIPTION
        "Cisco UCS fabric:CartridgePhEp managed object table"
    ::= { cucsFabricObjects 126 }

cucsFabricCartridgePhEpEntry OBJECT-TYPE
    SYNTAX           CucsFabricCartridgePhEpEntry
    MAX-ACCESS       not-accessible
    STATUS           current
    DESCRIPTION
        "Entry for the cucsFabricCartridgePhEpTable table."
    INDEX { cucsFabricCartridgePhEpInstanceId }
    ::= { cucsFabricCartridgePhEpTable 1 }

CucsFabricCartridgePhEpEntry ::= SEQUENCE {
    cucsFabricCartridgePhEpInstanceId                                CucsManagedObjectId,
    cucsFabricCartridgePhEpDn                                        CucsManagedObjectDn,
    cucsFabricCartridgePhEpRn                                        SnmpAdminString,
    cucsFabricCartridgePhEpAdminState                                CucsFabricInternalEpAdminState,
    cucsFabricCartridgePhEpChassisId                                 Gauge32,
    cucsFabricCartridgePhEpEpDn                                      SnmpAdminString,
    cucsFabricCartridgePhEpFltAggr                                   Unsigned64,
    cucsFabricCartridgePhEpIfRole                                    CucsFabricComputeEpIfRole,
    cucsFabricCartridgePhEpIfType                                    CucsFabricPIoEpIfType,
    cucsFabricCartridgePhEpLc                                        CucsFabricBladeLifeCycle,
    cucsFabricCartridgePhEpLicGP                                     Unsigned64,
    cucsFabricCartridgePhEpLicState                                  CucsLicenseState,
    cucsFabricCartridgePhEpLocale                                    CucsFabricInternalEpLocale,
    cucsFabricCartridgePhEpModel                                     SnmpAdminString,
    cucsFabricCartridgePhEpName                                      SnmpAdminString,
    cucsFabricCartridgePhEpOperState                                 CucsFabricPIoEpOperState,
    cucsFabricCartridgePhEpOperStateReason                           SnmpAdminString,
    cucsFabricCartridgePhEpPeerChassisId                             Gauge32,
    cucsFabricCartridgePhEpPeerDn                                    SnmpAdminString,
    cucsFabricCartridgePhEpPeerPortId                                Gauge32,
    cucsFabricCartridgePhEpPeerSlotId                                Gauge32,
    cucsFabricCartridgePhEpPortId                                    CucsFabricPIoEpPortId,
    cucsFabricCartridgePhEpRevision                                  SnmpAdminString,
    cucsFabricCartridgePhEpSerial                                    SnmpAdminString,
    cucsFabricCartridgePhEpSlotId                                    CucsFabricPIoEpSlotId,
    cucsFabricCartridgePhEpSwitchId                                  CucsNetworkSwitchId,
    cucsFabricCartridgePhEpTransport                                 CucsNetworkTransport,
    cucsFabricCartridgePhEpType                                      CucsFabricComputeEpType,
    cucsFabricCartridgePhEpVendor                                    SnmpAdminString,
    cucsFabricCartridgePhEpAggrPortId                                Gauge32,
    cucsFabricCartridgePhEpAutoNegotiate                             TruthValue,
    cucsFabricCartridgePhEpPeerAggrPortId                            Gauge32
}

cucsFabricCartridgePhEpInstanceId OBJECT-TYPE
    SYNTAX       CucsManagedObjectId
    MAX-ACCESS   not-accessible
    STATUS       current
    DESCRIPTION
        "Instance identifier of the managed object."
    ::= { cucsFabricCartridgePhEpEntry 1 }

cucsFabricCartridgePhEpDn OBJECT-TYPE
    SYNTAX       CucsManagedObjectDn
    MAX-ACCESS   read-only
    STATUS       current
    DESCRIPTION
        "Cisco UCS fabric:CartridgePhEp:dn managed object property"
    ::= { cucsFabricCartridgePhEpEntry 2 }

cucsFabricCartridgePhEpRn OBJECT-TYPE
    SYNTAX       SnmpAdminString
    MAX-ACCESS   read-only
    STATUS       current
    DESCRIPTION
        "Cisco UCS fabric:CartridgePhEp:rn managed object property"
    ::= { cucsFabricCartridgePhEpEntry 3 }

cucsFabricCartridgePhEpAdminState OBJECT-TYPE
    SYNTAX       CucsFabricInternalEpAdminState
    MAX-ACCESS   read-only
    STATUS       current
    DESCRIPTION
        "Cisco UCS fabric:CartridgePhEp:adminState managed
        object property"
    ::= { cucsFabricCartridgePhEpEntry 4 }

cucsFabricCartridgePhEpChassisId OBJECT-TYPE
    SYNTAX       Gauge32
    MAX-ACCESS   read-only
    STATUS       current
    DESCRIPTION
        "Cisco UCS fabric:CartridgePhEp:chassisId managed object property"
    ::= { cucsFabricCartridgePhEpEntry 5 }

cucsFabricCartridgePhEpEpDn OBJECT-TYPE
    SYNTAX       SnmpAdminString
    MAX-ACCESS   read-only
    STATUS       current
    DESCRIPTION
        "Cisco UCS fabric:CartridgePhEp:epDn managed object property"
    ::= { cucsFabricCartridgePhEpEntry 6 }

cucsFabricCartridgePhEpFltAggr OBJECT-TYPE
    SYNTAX       Unsigned64
    MAX-ACCESS   read-only
    STATUS       current
    DESCRIPTION
        "Cisco UCS fabric:CartridgePhEp:fltAggr managed object property"
    ::= { cucsFabricCartridgePhEpEntry 7 }

cucsFabricCartridgePhEpIfRole OBJECT-TYPE
    SYNTAX       CucsFabricComputeEpIfRole
    MAX-ACCESS   read-only
    STATUS       current
    DESCRIPTION
        "Cisco UCS fabric:CartridgePhEp:ifRole managed object property"
    ::= { cucsFabricCartridgePhEpEntry 8 }

cucsFabricCartridgePhEpIfType OBJECT-TYPE
    SYNTAX       CucsFabricPIoEpIfType
    MAX-ACCESS   read-only
    STATUS       current
    DESCRIPTION
        "Cisco UCS fabric:CartridgePhEp:ifType managed object property"
    ::= { cucsFabricCartridgePhEpEntry 9 }

cucsFabricCartridgePhEpLc OBJECT-TYPE
    SYNTAX       CucsFabricBladeLifeCycle
    MAX-ACCESS   read-only
    STATUS       current
    DESCRIPTION
        "Cisco UCS fabric:CartridgePhEp:lc managed object property"
    ::= { cucsFabricCartridgePhEpEntry 10 }

cucsFabricCartridgePhEpLicGP OBJECT-TYPE
    SYNTAX       Unsigned64
    MAX-ACCESS   read-only
    STATUS       current
    DESCRIPTION
        "Cisco UCS fabric:CartridgePhEp:licGP managed object property"
    ::= { cucsFabricCartridgePhEpEntry 11 }

cucsFabricCartridgePhEpLicState OBJECT-TYPE
    SYNTAX       CucsLicenseState
    MAX-ACCESS   read-only
    STATUS       current
    DESCRIPTION
        "Cisco UCS fabric:CartridgePhEp:licState managed object property"
    ::= { cucsFabricCartridgePhEpEntry 12 }

cucsFabricCartridgePhEpLocale OBJECT-TYPE
    SYNTAX       CucsFabricInternalEpLocale
    MAX-ACCESS   read-only
    STATUS       current
    DESCRIPTION
        "Cisco UCS fabric:CartridgePhEp:locale managed object property"
    ::= { cucsFabricCartridgePhEpEntry 13 }

cucsFabricCartridgePhEpModel OBJECT-TYPE
    SYNTAX       SnmpAdminString
    MAX-ACCESS   read-only
    STATUS       current
    DESCRIPTION
        "Cisco UCS fabric:CartridgePhEp:model managed object property"
    ::= { cucsFabricCartridgePhEpEntry 14 }

cucsFabricCartridgePhEpName OBJECT-TYPE
    SYNTAX       SnmpAdminString
    MAX-ACCESS   read-only
    STATUS       current
    DESCRIPTION
        "Cisco UCS fabric:CartridgePhEp:name managed object property"
    ::= { cucsFabricCartridgePhEpEntry 15 }

cucsFabricCartridgePhEpOperState OBJECT-TYPE
    SYNTAX       CucsFabricPIoEpOperState
    MAX-ACCESS   read-only
    STATUS       current
    DESCRIPTION
        "Cisco UCS fabric:CartridgePhEp:operState managed object property"
    ::= { cucsFabricCartridgePhEpEntry 16 }

cucsFabricCartridgePhEpOperStateReason OBJECT-TYPE
    SYNTAX       SnmpAdminString
    MAX-ACCESS   read-only
    STATUS       current
    DESCRIPTION
        "Cisco UCS fabric:CartridgePhEp:operStateReason
        managed object property"
    ::= { cucsFabricCartridgePhEpEntry 17 }

cucsFabricCartridgePhEpPeerChassisId OBJECT-TYPE
    SYNTAX       Gauge32
    MAX-ACCESS   read-only
    STATUS       current
    DESCRIPTION
        "Cisco UCS fabric:CartridgePhEp:peerChassisId managed
        object property"
    ::= { cucsFabricCartridgePhEpEntry 18 }

cucsFabricCartridgePhEpPeerDn OBJECT-TYPE
    SYNTAX       SnmpAdminString
    MAX-ACCESS   read-only
    STATUS       current
    DESCRIPTION
        "Cisco UCS fabric:CartridgePhEp:peerDn managed object property"
    ::= { cucsFabricCartridgePhEpEntry 19 }

cucsFabricCartridgePhEpPeerPortId OBJECT-TYPE
    SYNTAX       Gauge32
    MAX-ACCESS   read-only
    STATUS       current
    DESCRIPTION
        "Cisco UCS fabric:CartridgePhEp:peerPortId managed
        object property"
    ::= { cucsFabricCartridgePhEpEntry 20 }

cucsFabricCartridgePhEpPeerSlotId OBJECT-TYPE
    SYNTAX       Gauge32
    MAX-ACCESS   read-only
    STATUS       current
    DESCRIPTION
        "Cisco UCS fabric:CartridgePhEp:peerSlotId managed
        object property"
    ::= { cucsFabricCartridgePhEpEntry 21 }

cucsFabricCartridgePhEpPortId OBJECT-TYPE
    SYNTAX       CucsFabricPIoEpPortId
    MAX-ACCESS   read-only
    STATUS       current
    DESCRIPTION
        "Cisco UCS fabric:CartridgePhEp:portId managed object property"
    ::= { cucsFabricCartridgePhEpEntry 22 }

cucsFabricCartridgePhEpRevision OBJECT-TYPE
    SYNTAX       SnmpAdminString
    MAX-ACCESS   read-only
    STATUS       current
    DESCRIPTION
        "Cisco UCS fabric:CartridgePhEp:revision managed object property"
    ::= { cucsFabricCartridgePhEpEntry 23 }

cucsFabricCartridgePhEpSerial OBJECT-TYPE
    SYNTAX       SnmpAdminString
    MAX-ACCESS   read-only
    STATUS       current
    DESCRIPTION
        "Cisco UCS fabric:CartridgePhEp:serial managed object property"
    ::= { cucsFabricCartridgePhEpEntry 24 }

cucsFabricCartridgePhEpSlotId OBJECT-TYPE
    SYNTAX       CucsFabricPIoEpSlotId
    MAX-ACCESS   read-only
    STATUS       current
    DESCRIPTION
        "Cisco UCS fabric:CartridgePhEp:slotId managed object property"
    ::= { cucsFabricCartridgePhEpEntry 25 }

cucsFabricCartridgePhEpSwitchId OBJECT-TYPE
    SYNTAX       CucsNetworkSwitchId
    MAX-ACCESS   read-only
    STATUS       current
    DESCRIPTION
        "Cisco UCS fabric:CartridgePhEp:switchId managed object property"
    ::= { cucsFabricCartridgePhEpEntry 26 }

cucsFabricCartridgePhEpTransport OBJECT-TYPE
    SYNTAX       CucsNetworkTransport
    MAX-ACCESS   read-only
    STATUS       current
    DESCRIPTION
        "Cisco UCS fabric:CartridgePhEp:transport managed object property"
    ::= { cucsFabricCartridgePhEpEntry 27 }

cucsFabricCartridgePhEpType OBJECT-TYPE
    SYNTAX       CucsFabricComputeEpType
    MAX-ACCESS   read-only
    STATUS       current
    DESCRIPTION
        "Cisco UCS fabric:CartridgePhEp:type managed object property"
    ::= { cucsFabricCartridgePhEpEntry 28 }

cucsFabricCartridgePhEpVendor OBJECT-TYPE
    SYNTAX       SnmpAdminString
    MAX-ACCESS   read-only
    STATUS       current
    DESCRIPTION
        "Cisco UCS fabric:CartridgePhEp:vendor managed object property"
    ::= { cucsFabricCartridgePhEpEntry 29 }

cucsFabricCartridgePhEpAggrPortId OBJECT-TYPE
    SYNTAX       Gauge32
    MAX-ACCESS   read-only
    STATUS       current
    DESCRIPTION
        "Cisco UCS fabric:CartridgePhEp:aggrPortId managed
        object property"
    ::= { cucsFabricCartridgePhEpEntry 30 }

cucsFabricCartridgePhEpAutoNegotiate OBJECT-TYPE
    SYNTAX       TruthValue
    MAX-ACCESS   read-only
    STATUS       current
    DESCRIPTION
        "Cisco UCS fabric:CartridgePhEp:autoNegotiate managed
        object property"
    ::= { cucsFabricCartridgePhEpEntry 31 }

cucsFabricCartridgePhEpPeerAggrPortId OBJECT-TYPE
    SYNTAX       Gauge32
    MAX-ACCESS   read-only
    STATUS       current
    DESCRIPTION
        "Cisco UCS fabric:CartridgePhEp:peerAggrPortId
        managed object property"
    ::= { cucsFabricCartridgePhEpEntry 32 }

cucsFabricCartridgeSlotEpTable OBJECT-TYPE
    SYNTAX           SEQUENCE OF CucsFabricCartridgeSlotEpEntry
    MAX-ACCESS       not-accessible
    STATUS           current
    DESCRIPTION
        "Cisco UCS fabric:CartridgeSlotEp managed object table"
    ::= { cucsFabricObjects 127 }

cucsFabricCartridgeSlotEpEntry OBJECT-TYPE
    SYNTAX           CucsFabricCartridgeSlotEpEntry
    MAX-ACCESS       not-accessible
    STATUS           current
    DESCRIPTION
        "Entry for the cucsFabricCartridgeSlotEpTable table."
    INDEX { cucsFabricCartridgeSlotEpInstanceId }
    ::= { cucsFabricCartridgeSlotEpTable 1 }

CucsFabricCartridgeSlotEpEntry ::= SEQUENCE {
    cucsFabricCartridgeSlotEpInstanceId                              CucsManagedObjectId,
    cucsFabricCartridgeSlotEpDn                                      CucsManagedObjectDn,
    cucsFabricCartridgeSlotEpRn                                      SnmpAdminString,
    cucsFabricCartridgeSlotEpAdminState                              CucsFabricInternalEpAdminState,
    cucsFabricCartridgeSlotEpChassisId                               Gauge32,
    cucsFabricCartridgeSlotEpConnPath                                CucsEquipmentConnectionStatus,
    cucsFabricCartridgeSlotEpConnStatus                              CucsEquipmentConnectionStatus,
    cucsFabricCartridgeSlotEpDiscovery                               CucsComputeDiscovery,
    cucsFabricCartridgeSlotEpDiscoveryStatus                         CucsEquipmentConnectionStatus,
    cucsFabricCartridgeSlotEpEpDn                                    SnmpAdminString,
    cucsFabricCartridgeSlotEpFltAggr                                 Unsigned64,
    cucsFabricCartridgeSlotEpFruIdentTrigTs                          Unsigned64,
    cucsFabricCartridgeSlotEpFsmDescr                                SnmpAdminString,
    cucsFabricCartridgeSlotEpFsmPrev                                 SnmpAdminString,
    cucsFabricCartridgeSlotEpFsmProgr                                Gauge32,
    cucsFabricCartridgeSlotEpFsmRmtInvErrCode                        Gauge32,
    cucsFabricCartridgeSlotEpFsmRmtInvErrDescr                       SnmpAdminString,
    cucsFabricCartridgeSlotEpFsmRmtInvRslt                           CucsConditionRemoteInvRslt,
    cucsFabricCartridgeSlotEpFsmStageDescr                           SnmpAdminString,
    cucsFabricCartridgeSlotEpFsmStamp                                DateAndTime,
    cucsFabricCartridgeSlotEpFsmStatus                               SnmpAdminString,
    cucsFabricCartridgeSlotEpFsmTry                                  Gauge32,
    cucsFabricCartridgeSlotEpIfRole                                  CucsFabricEquipmentEpIfRole,
    cucsFabricCartridgeSlotEpIfType                                  CucsFabricPIoEpIfType,
    cucsFabricCartridgeSlotEpLicGP                                   Unsigned64,
    cucsFabricCartridgeSlotEpLicState                                CucsLicenseState,
    cucsFabricCartridgeSlotEpLocale                                  CucsFabricInternalEpLocale,
    cucsFabricCartridgeSlotEpManagingInst                            CucsNetworkSwitchId,
    cucsFabricCartridgeSlotEpModel                                   SnmpAdminString,
    cucsFabricCartridgeSlotEpName                                    SnmpAdminString,
    cucsFabricCartridgeSlotEpOperState                               CucsFabricPIoEpOperState,
    cucsFabricCartridgeSlotEpOperStateReason                         SnmpAdminString,
    cucsFabricCartridgeSlotEpPeerChassisId                           Gauge32,
    cucsFabricCartridgeSlotEpPeerDn                                  SnmpAdminString,
    cucsFabricCartridgeSlotEpPeerPortId                              Gauge32,
    cucsFabricCartridgeSlotEpPeerSlotId                              Gauge32,
    cucsFabricCartridgeSlotEpPortId                                  CucsFabricPIoEpPortId,
    cucsFabricCartridgeSlotEpPresence                                CucsEquipmentSlotStatus,
    cucsFabricCartridgeSlotEpRevision                                SnmpAdminString,
    cucsFabricCartridgeSlotEpSerial                                  SnmpAdminString,
    cucsFabricCartridgeSlotEpSlotAdminState                          CucsFabricSlotAdminState,
    cucsFabricCartridgeSlotEpSlotId                                  CucsFabricCartridgeSlotEpSlotId,
    cucsFabricCartridgeSlotEpSwitchId                                CucsNetworkSwitchId,
    cucsFabricCartridgeSlotEpTransport                               CucsNetworkTransport,
    cucsFabricCartridgeSlotEpType                                    CucsFabricEquipmentEpType,
    cucsFabricCartridgeSlotEpVendor                                  SnmpAdminString,
    cucsFabricCartridgeSlotEpAggrPortId                              Gauge32,
    cucsFabricCartridgeSlotEpAutoNegotiate                           TruthValue,
    cucsFabricCartridgeSlotEpPeerAggrPortId                          Gauge32
}

cucsFabricCartridgeSlotEpInstanceId OBJECT-TYPE
    SYNTAX       CucsManagedObjectId
    MAX-ACCESS   not-accessible
    STATUS       current
    DESCRIPTION
        "Instance identifier of the managed object."
    ::= { cucsFabricCartridgeSlotEpEntry 1 }

cucsFabricCartridgeSlotEpDn OBJECT-TYPE
    SYNTAX       CucsManagedObjectDn
    MAX-ACCESS   read-only
    STATUS       current
    DESCRIPTION
        "Cisco UCS fabric:CartridgeSlotEp:dn managed object property"
    ::= { cucsFabricCartridgeSlotEpEntry 2 }

cucsFabricCartridgeSlotEpRn OBJECT-TYPE
    SYNTAX       SnmpAdminString
    MAX-ACCESS   read-only
    STATUS       current
    DESCRIPTION
        "Cisco UCS fabric:CartridgeSlotEp:rn managed object property"
    ::= { cucsFabricCartridgeSlotEpEntry 3 }

cucsFabricCartridgeSlotEpAdminState OBJECT-TYPE
    SYNTAX       CucsFabricInternalEpAdminState
    MAX-ACCESS   read-only
    STATUS       current
    DESCRIPTION
        "Cisco UCS fabric:CartridgeSlotEp:adminState managed
        object property"
    ::= { cucsFabricCartridgeSlotEpEntry 4 }

cucsFabricCartridgeSlotEpChassisId OBJECT-TYPE
    SYNTAX       Gauge32
    MAX-ACCESS   read-only
    STATUS       current
    DESCRIPTION
        "Cisco UCS fabric:CartridgeSlotEp:chassisId managed
        object property"
    ::= { cucsFabricCartridgeSlotEpEntry 5 }

cucsFabricCartridgeSlotEpConnPath OBJECT-TYPE
    SYNTAX       CucsEquipmentConnectionStatus
    MAX-ACCESS   read-only
    STATUS       current
    DESCRIPTION
        "Cisco UCS fabric:CartridgeSlotEp:connPath managed
        object property"
    ::= { cucsFabricCartridgeSlotEpEntry 6 }

cucsFabricCartridgeSlotEpConnStatus OBJECT-TYPE
    SYNTAX       CucsEquipmentConnectionStatus
    MAX-ACCESS   read-only
    STATUS       current
    DESCRIPTION
        "Cisco UCS fabric:CartridgeSlotEp:connStatus managed
        object property"
    ::= { cucsFabricCartridgeSlotEpEntry 7 }

cucsFabricCartridgeSlotEpDiscovery OBJECT-TYPE
    SYNTAX       CucsComputeDiscovery
    MAX-ACCESS   read-only
    STATUS       current
    DESCRIPTION
        "Cisco UCS fabric:CartridgeSlotEp:discovery managed
        object property"
    ::= { cucsFabricCartridgeSlotEpEntry 8 }

cucsFabricCartridgeSlotEpDiscoveryStatus OBJECT-TYPE
    SYNTAX       CucsEquipmentConnectionStatus
    MAX-ACCESS   read-only
    STATUS       current
    DESCRIPTION
        "Cisco UCS fabric:CartridgeSlotEp:discoveryStatus
        managed object property"
    ::= { cucsFabricCartridgeSlotEpEntry 9 }

cucsFabricCartridgeSlotEpEpDn OBJECT-TYPE
    SYNTAX       SnmpAdminString
    MAX-ACCESS   read-only
    STATUS       current
    DESCRIPTION
        "Cisco UCS fabric:CartridgeSlotEp:epDn managed object property"
    ::= { cucsFabricCartridgeSlotEpEntry 10 }

cucsFabricCartridgeSlotEpFltAggr OBJECT-TYPE
    SYNTAX       Unsigned64
    MAX-ACCESS   read-only
    STATUS       current
    DESCRIPTION
        "Cisco UCS fabric:CartridgeSlotEp:fltAggr managed object property"
    ::= { cucsFabricCartridgeSlotEpEntry 11 }

cucsFabricCartridgeSlotEpFruIdentTrigTs OBJECT-TYPE
    SYNTAX       Unsigned64
    MAX-ACCESS   read-only
    STATUS       current
    DESCRIPTION
        "Cisco UCS fabric:CartridgeSlotEp:fruIdentTrigTs
        managed object property"
    ::= { cucsFabricCartridgeSlotEpEntry 12 }

cucsFabricCartridgeSlotEpFsmDescr OBJECT-TYPE
    SYNTAX       SnmpAdminString
    MAX-ACCESS   read-only
    STATUS       current
    DESCRIPTION
        "Cisco UCS fabric:CartridgeSlotEp:fsmDescr managed
        object property"
    ::= { cucsFabricCartridgeSlotEpEntry 13 }

cucsFabricCartridgeSlotEpFsmPrev OBJECT-TYPE
    SYNTAX       SnmpAdminString
    MAX-ACCESS   read-only
    STATUS       current
    DESCRIPTION
        "Cisco UCS fabric:CartridgeSlotEp:fsmPrev managed object property"
    ::= { cucsFabricCartridgeSlotEpEntry 14 }

cucsFabricCartridgeSlotEpFsmProgr OBJECT-TYPE
    SYNTAX       Gauge32
    MAX-ACCESS   read-only
    STATUS       current
    DESCRIPTION
        "Cisco UCS fabric:CartridgeSlotEp:fsmProgr managed
        object property"
    ::= { cucsFabricCartridgeSlotEpEntry 15 }

cucsFabricCartridgeSlotEpFsmRmtInvErrCode OBJECT-TYPE
    SYNTAX       Gauge32
    MAX-ACCESS   read-only
    STATUS       current
    DESCRIPTION
        "Cisco UCS fabric:CartridgeSlotEp:fsmRmtInvErrCode
        managed object property"
    ::= { cucsFabricCartridgeSlotEpEntry 16 }

cucsFabricCartridgeSlotEpFsmRmtInvErrDescr OBJECT-TYPE
    SYNTAX       SnmpAdminString
    MAX-ACCESS   read-only
    STATUS       current
    DESCRIPTION
        "Cisco UCS fabric:CartridgeSlotEp:fsmRmtInvErrDescr
        managed object property"
    ::= { cucsFabricCartridgeSlotEpEntry 17 }

cucsFabricCartridgeSlotEpFsmRmtInvRslt OBJECT-TYPE
    SYNTAX       CucsConditionRemoteInvRslt
    MAX-ACCESS   read-only
    STATUS       current
    DESCRIPTION
        "Cisco UCS fabric:CartridgeSlotEp:fsmRmtInvRslt
        managed object property"
    ::= { cucsFabricCartridgeSlotEpEntry 18 }

cucsFabricCartridgeSlotEpFsmStageDescr OBJECT-TYPE
    SYNTAX       SnmpAdminString
    MAX-ACCESS   read-only
    STATUS       current
    DESCRIPTION
        "Cisco UCS fabric:CartridgeSlotEp:fsmStageDescr
        managed object property"
    ::= { cucsFabricCartridgeSlotEpEntry 19 }

cucsFabricCartridgeSlotEpFsmStamp OBJECT-TYPE
    SYNTAX       DateAndTime
    MAX-ACCESS   read-only
    STATUS       current
    DESCRIPTION
        "Cisco UCS fabric:CartridgeSlotEp:fsmStamp managed
        object property"
    ::= { cucsFabricCartridgeSlotEpEntry 20 }

cucsFabricCartridgeSlotEpFsmStatus OBJECT-TYPE
    SYNTAX       SnmpAdminString
    MAX-ACCESS   read-only
    STATUS       current
    DESCRIPTION
        "Cisco UCS fabric:CartridgeSlotEp:fsmStatus managed
        object property"
    ::= { cucsFabricCartridgeSlotEpEntry 21 }

cucsFabricCartridgeSlotEpFsmTry OBJECT-TYPE
    SYNTAX       Gauge32
    MAX-ACCESS   read-only
    STATUS       current
    DESCRIPTION
        "Cisco UCS fabric:CartridgeSlotEp:fsmTry managed object property"
    ::= { cucsFabricCartridgeSlotEpEntry 22 }

cucsFabricCartridgeSlotEpIfRole OBJECT-TYPE
    SYNTAX       CucsFabricEquipmentEpIfRole
    MAX-ACCESS   read-only
    STATUS       current
    DESCRIPTION
        "Cisco UCS fabric:CartridgeSlotEp:ifRole managed object property"
    ::= { cucsFabricCartridgeSlotEpEntry 23 }

cucsFabricCartridgeSlotEpIfType OBJECT-TYPE
    SYNTAX       CucsFabricPIoEpIfType
    MAX-ACCESS   read-only
    STATUS       current
    DESCRIPTION
        "Cisco UCS fabric:CartridgeSlotEp:ifType managed object property"
    ::= { cucsFabricCartridgeSlotEpEntry 24 }

cucsFabricCartridgeSlotEpLicGP OBJECT-TYPE
    SYNTAX       Unsigned64
    MAX-ACCESS   read-only
    STATUS       current
    DESCRIPTION
        "Cisco UCS fabric:CartridgeSlotEp:licGP managed object property"
    ::= { cucsFabricCartridgeSlotEpEntry 25 }

cucsFabricCartridgeSlotEpLicState OBJECT-TYPE
    SYNTAX       CucsLicenseState
    MAX-ACCESS   read-only
    STATUS       current
    DESCRIPTION
        "Cisco UCS fabric:CartridgeSlotEp:licState managed
        object property"
    ::= { cucsFabricCartridgeSlotEpEntry 26 }

cucsFabricCartridgeSlotEpLocale OBJECT-TYPE
    SYNTAX       CucsFabricInternalEpLocale
    MAX-ACCESS   read-only
    STATUS       current
    DESCRIPTION
        "Cisco UCS fabric:CartridgeSlotEp:locale managed object property"
    ::= { cucsFabricCartridgeSlotEpEntry 27 }

cucsFabricCartridgeSlotEpManagingInst OBJECT-TYPE
    SYNTAX       CucsNetworkSwitchId
    MAX-ACCESS   read-only
    STATUS       current
    DESCRIPTION
        "Cisco UCS fabric:CartridgeSlotEp:managingInst
        managed object property"
    ::= { cucsFabricCartridgeSlotEpEntry 28 }

cucsFabricCartridgeSlotEpModel OBJECT-TYPE
    SYNTAX       SnmpAdminString
    MAX-ACCESS   read-only
    STATUS       current
    DESCRIPTION
        "Cisco UCS fabric:CartridgeSlotEp:model managed object property"
    ::= { cucsFabricCartridgeSlotEpEntry 29 }

cucsFabricCartridgeSlotEpName OBJECT-TYPE
    SYNTAX       SnmpAdminString
    MAX-ACCESS   read-only
    STATUS       current
    DESCRIPTION
        "Cisco UCS fabric:CartridgeSlotEp:name managed object property"
    ::= { cucsFabricCartridgeSlotEpEntry 30 }

cucsFabricCartridgeSlotEpOperState OBJECT-TYPE
    SYNTAX       CucsFabricPIoEpOperState
    MAX-ACCESS   read-only
    STATUS       current
    DESCRIPTION
        "Cisco UCS fabric:CartridgeSlotEp:operState managed
        object property"
    ::= { cucsFabricCartridgeSlotEpEntry 31 }

cucsFabricCartridgeSlotEpOperStateReason OBJECT-TYPE
    SYNTAX       SnmpAdminString
    MAX-ACCESS   read-only
    STATUS       current
    DESCRIPTION
        "Cisco UCS fabric:CartridgeSlotEp:operStateReason
        managed object property"
    ::= { cucsFabricCartridgeSlotEpEntry 32 }

cucsFabricCartridgeSlotEpPeerChassisId OBJECT-TYPE
    SYNTAX       Gauge32
    MAX-ACCESS   read-only
    STATUS       current
    DESCRIPTION
        "Cisco UCS fabric:CartridgeSlotEp:peerChassisId
        managed object property"
    ::= { cucsFabricCartridgeSlotEpEntry 33 }

cucsFabricCartridgeSlotEpPeerDn OBJECT-TYPE
    SYNTAX       SnmpAdminString
    MAX-ACCESS   read-only
    STATUS       current
    DESCRIPTION
        "Cisco UCS fabric:CartridgeSlotEp:peerDn managed object property"
    ::= { cucsFabricCartridgeSlotEpEntry 34 }

cucsFabricCartridgeSlotEpPeerPortId OBJECT-TYPE
    SYNTAX       Gauge32
    MAX-ACCESS   read-only
    STATUS       current
    DESCRIPTION
        "Cisco UCS fabric:CartridgeSlotEp:peerPortId managed
        object property"
    ::= { cucsFabricCartridgeSlotEpEntry 35 }

cucsFabricCartridgeSlotEpPeerSlotId OBJECT-TYPE
    SYNTAX       Gauge32
    MAX-ACCESS   read-only
    STATUS       current
    DESCRIPTION
        "Cisco UCS fabric:CartridgeSlotEp:peerSlotId managed
        object property"
    ::= { cucsFabricCartridgeSlotEpEntry 36 }

cucsFabricCartridgeSlotEpPortId OBJECT-TYPE
    SYNTAX       CucsFabricPIoEpPortId
    MAX-ACCESS   read-only
    STATUS       current
    DESCRIPTION
        "Cisco UCS fabric:CartridgeSlotEp:portId managed object property"
    ::= { cucsFabricCartridgeSlotEpEntry 37 }

cucsFabricCartridgeSlotEpPresence OBJECT-TYPE
    SYNTAX       CucsEquipmentSlotStatus
    MAX-ACCESS   read-only
    STATUS       current
    DESCRIPTION
        "Cisco UCS fabric:CartridgeSlotEp:presence managed
        object property"
    ::= { cucsFabricCartridgeSlotEpEntry 38 }

cucsFabricCartridgeSlotEpRevision OBJECT-TYPE
    SYNTAX       SnmpAdminString
    MAX-ACCESS   read-only
    STATUS       current
    DESCRIPTION
        "Cisco UCS fabric:CartridgeSlotEp:revision managed
        object property"
    ::= { cucsFabricCartridgeSlotEpEntry 39 }

cucsFabricCartridgeSlotEpSerial OBJECT-TYPE
    SYNTAX       SnmpAdminString
    MAX-ACCESS   read-only
    STATUS       current
    DESCRIPTION
        "Cisco UCS fabric:CartridgeSlotEp:serial managed object property"
    ::= { cucsFabricCartridgeSlotEpEntry 40 }

cucsFabricCartridgeSlotEpSlotAdminState OBJECT-TYPE
    SYNTAX       CucsFabricSlotAdminState
    MAX-ACCESS   read-only
    STATUS       current
    DESCRIPTION
        "Cisco UCS fabric:CartridgeSlotEp:slotAdminState
        managed object property"
    ::= { cucsFabricCartridgeSlotEpEntry 41 }

cucsFabricCartridgeSlotEpSlotId OBJECT-TYPE
    SYNTAX       CucsFabricCartridgeSlotEpSlotId
    MAX-ACCESS   read-only
    STATUS       current
    DESCRIPTION
        "Cisco UCS fabric:CartridgeSlotEp:slotId managed object property"
    ::= { cucsFabricCartridgeSlotEpEntry 42 }

cucsFabricCartridgeSlotEpSwitchId OBJECT-TYPE
    SYNTAX       CucsNetworkSwitchId
    MAX-ACCESS   read-only
    STATUS       current
    DESCRIPTION
        "Cisco UCS fabric:CartridgeSlotEp:switchId managed
        object property"
    ::= { cucsFabricCartridgeSlotEpEntry 43 }

cucsFabricCartridgeSlotEpTransport OBJECT-TYPE
    SYNTAX       CucsNetworkTransport
    MAX-ACCESS   read-only
    STATUS       current
    DESCRIPTION
        "Cisco UCS fabric:CartridgeSlotEp:transport managed
        object property"
    ::= { cucsFabricCartridgeSlotEpEntry 44 }

cucsFabricCartridgeSlotEpType OBJECT-TYPE
    SYNTAX       CucsFabricEquipmentEpType
    MAX-ACCESS   read-only
    STATUS       current
    DESCRIPTION
        "Cisco UCS fabric:CartridgeSlotEp:type managed object property"
    ::= { cucsFabricCartridgeSlotEpEntry 45 }

cucsFabricCartridgeSlotEpVendor OBJECT-TYPE
    SYNTAX       SnmpAdminString
    MAX-ACCESS   read-only
    STATUS       current
    DESCRIPTION
        "Cisco UCS fabric:CartridgeSlotEp:vendor managed object property"
    ::= { cucsFabricCartridgeSlotEpEntry 46 }

cucsFabricCartridgeSlotEpAggrPortId OBJECT-TYPE
    SYNTAX       Gauge32
    MAX-ACCESS   read-only
    STATUS       current
    DESCRIPTION
        "Cisco UCS fabric:CartridgeSlotEp:aggrPortId managed
        object property"
    ::= { cucsFabricCartridgeSlotEpEntry 47 }

cucsFabricCartridgeSlotEpAutoNegotiate OBJECT-TYPE
    SYNTAX       TruthValue
    MAX-ACCESS   read-only
    STATUS       current
    DESCRIPTION
        "Cisco UCS fabric:CartridgeSlotEp:autoNegotiate
        managed object property"
    ::= { cucsFabricCartridgeSlotEpEntry 48 }

cucsFabricCartridgeSlotEpPeerAggrPortId OBJECT-TYPE
    SYNTAX       Gauge32
    MAX-ACCESS   read-only
    STATUS       current
    DESCRIPTION
        "Cisco UCS fabric:CartridgeSlotEp:peerAggrPortId
        managed object property"
    ::= { cucsFabricCartridgeSlotEpEntry 49 }

cucsFabricCartridgeSlotEpFsmTable OBJECT-TYPE
    SYNTAX           SEQUENCE OF CucsFabricCartridgeSlotEpFsmEntry
    MAX-ACCESS       not-accessible
    STATUS           current
    DESCRIPTION
        "Cisco UCS fabric:CartridgeSlotEpFsm managed object table"
    ::= { cucsFabricObjects 128 }

cucsFabricCartridgeSlotEpFsmEntry OBJECT-TYPE
    SYNTAX           CucsFabricCartridgeSlotEpFsmEntry
    MAX-ACCESS       not-accessible
    STATUS           current
    DESCRIPTION
        "Entry for the cucsFabricCartridgeSlotEpFsmTable table."
    INDEX { cucsFabricCartridgeSlotEpFsmInstanceId }
    ::= { cucsFabricCartridgeSlotEpFsmTable 1 }

CucsFabricCartridgeSlotEpFsmEntry ::= SEQUENCE {
    cucsFabricCartridgeSlotEpFsmInstanceId                           CucsManagedObjectId,
    cucsFabricCartridgeSlotEpFsmDn                                   CucsManagedObjectDn,
    cucsFabricCartridgeSlotEpFsmRn                                   SnmpAdminString,
    cucsFabricCartridgeSlotEpFsmCompletionTime                       DateAndTime,
    cucsFabricCartridgeSlotEpFsmCurrentFsm                           CucsFabricCartridgeSlotEpFsmCurrentFsm,
    cucsFabricCartridgeSlotEpFsmDescrData                            SnmpAdminString,
    cucsFabricCartridgeSlotEpFsmFsmStatus                            CucsFsmFsmStageStatus,
    cucsFabricCartridgeSlotEpFsmProgress                             Gauge32,
    cucsFabricCartridgeSlotEpFsmRmtErrCode                           Gauge32,
    cucsFabricCartridgeSlotEpFsmRmtErrDescr                          SnmpAdminString,
    cucsFabricCartridgeSlotEpFsmRmtRslt                              CucsConditionRemoteInvRslt
}

cucsFabricCartridgeSlotEpFsmInstanceId OBJECT-TYPE
    SYNTAX       CucsManagedObjectId
    MAX-ACCESS   not-accessible
    STATUS       current
    DESCRIPTION
        "Instance identifier of the managed object."
    ::= { cucsFabricCartridgeSlotEpFsmEntry 1 }

cucsFabricCartridgeSlotEpFsmDn OBJECT-TYPE
    SYNTAX       CucsManagedObjectDn
    MAX-ACCESS   read-only
    STATUS       current
    DESCRIPTION
        "Cisco UCS fabric:CartridgeSlotEpFsm:dn managed object property"
    ::= { cucsFabricCartridgeSlotEpFsmEntry 2 }

cucsFabricCartridgeSlotEpFsmRn OBJECT-TYPE
    SYNTAX       SnmpAdminString
    MAX-ACCESS   read-only
    STATUS       current
    DESCRIPTION
        "Cisco UCS fabric:CartridgeSlotEpFsm:rn managed object property"
    ::= { cucsFabricCartridgeSlotEpFsmEntry 3 }

cucsFabricCartridgeSlotEpFsmCompletionTime OBJECT-TYPE
    SYNTAX       DateAndTime
    MAX-ACCESS   read-only
    STATUS       current
    DESCRIPTION
        "Cisco UCS fabric:CartridgeSlotEpFsm:completionTime
        managed object property"
    ::= { cucsFabricCartridgeSlotEpFsmEntry 4 }

cucsFabricCartridgeSlotEpFsmCurrentFsm OBJECT-TYPE
    SYNTAX       CucsFabricCartridgeSlotEpFsmCurrentFsm
    MAX-ACCESS   read-only
    STATUS       current
    DESCRIPTION
        "Cisco UCS fabric:CartridgeSlotEpFsm:currentFsm
        managed object property"
    ::= { cucsFabricCartridgeSlotEpFsmEntry 5 }

cucsFabricCartridgeSlotEpFsmDescrData OBJECT-TYPE
    SYNTAX       SnmpAdminString
    MAX-ACCESS   read-only
    STATUS       current
    DESCRIPTION
        "Cisco UCS fabric:CartridgeSlotEpFsm:descr managed
        object property"
    ::= { cucsFabricCartridgeSlotEpFsmEntry 6 }

cucsFabricCartridgeSlotEpFsmFsmStatus OBJECT-TYPE
    SYNTAX       CucsFsmFsmStageStatus
    MAX-ACCESS   read-only
    STATUS       current
    DESCRIPTION
        "Cisco UCS fabric:CartridgeSlotEpFsm:fsmStatus
        managed object property"
    ::= { cucsFabricCartridgeSlotEpFsmEntry 7 }

cucsFabricCartridgeSlotEpFsmProgress OBJECT-TYPE
    SYNTAX       Gauge32
    MAX-ACCESS   read-only
    STATUS       current
    DESCRIPTION
        "Cisco UCS fabric:CartridgeSlotEpFsm:progress managed
        object property"
    ::= { cucsFabricCartridgeSlotEpFsmEntry 8 }

cucsFabricCartridgeSlotEpFsmRmtErrCode OBJECT-TYPE
    SYNTAX       Gauge32
    MAX-ACCESS   read-only
    STATUS       current
    DESCRIPTION
        "Cisco UCS fabric:CartridgeSlotEpFsm:rmtErrCode
        managed object property"
    ::= { cucsFabricCartridgeSlotEpFsmEntry 9 }

cucsFabricCartridgeSlotEpFsmRmtErrDescr OBJECT-TYPE
    SYNTAX       SnmpAdminString
    MAX-ACCESS   read-only
    STATUS       current
    DESCRIPTION
        "Cisco UCS fabric:CartridgeSlotEpFsm:rmtErrDescr
        managed object property"
    ::= { cucsFabricCartridgeSlotEpFsmEntry 10 }

cucsFabricCartridgeSlotEpFsmRmtRslt OBJECT-TYPE
    SYNTAX       CucsConditionRemoteInvRslt
    MAX-ACCESS   read-only
    STATUS       current
    DESCRIPTION
        "Cisco UCS fabric:CartridgeSlotEpFsm:rmtRslt managed
        object property"
    ::= { cucsFabricCartridgeSlotEpFsmEntry 11 }

cucsFabricCartridgeSlotEpFsmStageTable OBJECT-TYPE
    SYNTAX           SEQUENCE OF CucsFabricCartridgeSlotEpFsmStageEntry
    MAX-ACCESS       not-accessible
    STATUS           current
    DESCRIPTION
        "Cisco UCS fabric:CartridgeSlotEpFsmStage managed object table"
    ::= { cucsFabricObjects 129 }

cucsFabricCartridgeSlotEpFsmStageEntry OBJECT-TYPE
    SYNTAX           CucsFabricCartridgeSlotEpFsmStageEntry
    MAX-ACCESS       not-accessible
    STATUS           current
    DESCRIPTION
        "Entry for the cucsFabricCartridgeSlotEpFsmStageTable table."
    INDEX { cucsFabricCartridgeSlotEpFsmStageInstanceId }
    ::= { cucsFabricCartridgeSlotEpFsmStageTable 1 }

CucsFabricCartridgeSlotEpFsmStageEntry ::= SEQUENCE {
    cucsFabricCartridgeSlotEpFsmStageInstanceId                      CucsManagedObjectId,
    cucsFabricCartridgeSlotEpFsmStageDn                              CucsManagedObjectDn,
    cucsFabricCartridgeSlotEpFsmStageRn                              SnmpAdminString,
    cucsFabricCartridgeSlotEpFsmStageDescrData                       SnmpAdminString,
    cucsFabricCartridgeSlotEpFsmStageLastUpdateTime                  DateAndTime,
    cucsFabricCartridgeSlotEpFsmStageName                            CucsFabricCartridgeSlotEpFsmStageName,
    cucsFabricCartridgeSlotEpFsmStageOrder                           Gauge32,
    cucsFabricCartridgeSlotEpFsmStageRetry                           Gauge32,
    cucsFabricCartridgeSlotEpFsmStageStageStatus                     CucsFsmFsmStageStatus
}

cucsFabricCartridgeSlotEpFsmStageInstanceId OBJECT-TYPE
    SYNTAX       CucsManagedObjectId
    MAX-ACCESS   not-accessible
    STATUS       current
    DESCRIPTION
        "Instance identifier of the managed object."
    ::= { cucsFabricCartridgeSlotEpFsmStageEntry 1 }

cucsFabricCartridgeSlotEpFsmStageDn OBJECT-TYPE
    SYNTAX       CucsManagedObjectDn
    MAX-ACCESS   read-only
    STATUS       current
    DESCRIPTION
        "Cisco UCS fabric:CartridgeSlotEpFsmStage:dn managed
        object property"
    ::= { cucsFabricCartridgeSlotEpFsmStageEntry 2 }

cucsFabricCartridgeSlotEpFsmStageRn OBJECT-TYPE
    SYNTAX       SnmpAdminString
    MAX-ACCESS   read-only
    STATUS       current
    DESCRIPTION
        "Cisco UCS fabric:CartridgeSlotEpFsmStage:rn managed
        object property"
    ::= { cucsFabricCartridgeSlotEpFsmStageEntry 3 }

cucsFabricCartridgeSlotEpFsmStageDescrData OBJECT-TYPE
    SYNTAX       SnmpAdminString
    MAX-ACCESS   read-only
    STATUS       current
    DESCRIPTION
        "Cisco UCS fabric:CartridgeSlotEpFsmStage:descr
        managed object property"
    ::= { cucsFabricCartridgeSlotEpFsmStageEntry 4 }

cucsFabricCartridgeSlotEpFsmStageLastUpdateTime OBJECT-TYPE
    SYNTAX       DateAndTime
    MAX-ACCESS   read-only
    STATUS       current
    DESCRIPTION
        "Cisco UCS fabric:CartridgeSlotEpFsmStage:lastUpdateTime
        managed object property"
    ::= { cucsFabricCartridgeSlotEpFsmStageEntry 5 }

cucsFabricCartridgeSlotEpFsmStageName OBJECT-TYPE
    SYNTAX       CucsFabricCartridgeSlotEpFsmStageName
    MAX-ACCESS   read-only
    STATUS       current
    DESCRIPTION
        "Cisco UCS fabric:CartridgeSlotEpFsmStage:name
        managed object property"
    ::= { cucsFabricCartridgeSlotEpFsmStageEntry 6 }

cucsFabricCartridgeSlotEpFsmStageOrder OBJECT-TYPE
    SYNTAX       Gauge32
    MAX-ACCESS   read-only
    STATUS       current
    DESCRIPTION
        "Cisco UCS fabric:CartridgeSlotEpFsmStage:order
        managed object property"
    ::= { cucsFabricCartridgeSlotEpFsmStageEntry 7 }

cucsFabricCartridgeSlotEpFsmStageRetry OBJECT-TYPE
    SYNTAX       Gauge32
    MAX-ACCESS   read-only
    STATUS       current
    DESCRIPTION
        "Cisco UCS fabric:CartridgeSlotEpFsmStage:retry
        managed object property"
    ::= { cucsFabricCartridgeSlotEpFsmStageEntry 8 }

cucsFabricCartridgeSlotEpFsmStageStageStatus OBJECT-TYPE
    SYNTAX       CucsFsmFsmStageStatus
    MAX-ACCESS   read-only
    STATUS       current
    DESCRIPTION
        "Cisco UCS fabric:CartridgeSlotEpFsmStage:stageStatus
        managed object property"
    ::= { cucsFabricCartridgeSlotEpFsmStageEntry 9 }

cucsFabricCartridgeSlotEpFsmTaskTable OBJECT-TYPE
    SYNTAX           SEQUENCE OF CucsFabricCartridgeSlotEpFsmTaskEntry
    MAX-ACCESS       not-accessible
    STATUS           current
    DESCRIPTION
        "Cisco UCS fabric:CartridgeSlotEpFsmTask managed object table"
    ::= { cucsFabricObjects 130 }

cucsFabricCartridgeSlotEpFsmTaskEntry OBJECT-TYPE
    SYNTAX           CucsFabricCartridgeSlotEpFsmTaskEntry
    MAX-ACCESS       not-accessible
    STATUS           current
    DESCRIPTION
        "Entry for the cucsFabricCartridgeSlotEpFsmTaskTable table."
    INDEX { cucsFabricCartridgeSlotEpFsmTaskInstanceId }
    ::= { cucsFabricCartridgeSlotEpFsmTaskTable 1 }

CucsFabricCartridgeSlotEpFsmTaskEntry ::= SEQUENCE {
    cucsFabricCartridgeSlotEpFsmTaskInstanceId                       CucsManagedObjectId,
    cucsFabricCartridgeSlotEpFsmTaskDn                               CucsManagedObjectDn,
    cucsFabricCartridgeSlotEpFsmTaskRn                               SnmpAdminString,
    cucsFabricCartridgeSlotEpFsmTaskCompletion                       CucsFsmCompletion,
    cucsFabricCartridgeSlotEpFsmTaskFlags                            CucsFsmFlags,
    cucsFabricCartridgeSlotEpFsmTaskItem                             CucsFabricCartridgeSlotEpFsmTaskItem,
    cucsFabricCartridgeSlotEpFsmTaskSeqId                            Gauge32
}

cucsFabricCartridgeSlotEpFsmTaskInstanceId OBJECT-TYPE
    SYNTAX       CucsManagedObjectId
    MAX-ACCESS   not-accessible
    STATUS       current
    DESCRIPTION
        "Instance identifier of the managed object."
    ::= { cucsFabricCartridgeSlotEpFsmTaskEntry 1 }

cucsFabricCartridgeSlotEpFsmTaskDn OBJECT-TYPE
    SYNTAX       CucsManagedObjectDn
    MAX-ACCESS   read-only
    STATUS       current
    DESCRIPTION
        "Cisco UCS fabric:CartridgeSlotEpFsmTask:dn managed
        object property"
    ::= { cucsFabricCartridgeSlotEpFsmTaskEntry 2 }

cucsFabricCartridgeSlotEpFsmTaskRn OBJECT-TYPE
    SYNTAX       SnmpAdminString
    MAX-ACCESS   read-only
    STATUS       current
    DESCRIPTION
        "Cisco UCS fabric:CartridgeSlotEpFsmTask:rn managed
        object property"
    ::= { cucsFabricCartridgeSlotEpFsmTaskEntry 3 }

cucsFabricCartridgeSlotEpFsmTaskCompletion OBJECT-TYPE
    SYNTAX       CucsFsmCompletion
    MAX-ACCESS   read-only
    STATUS       current
    DESCRIPTION
        "Cisco UCS fabric:CartridgeSlotEpFsmTask:completion
        managed object property"
    ::= { cucsFabricCartridgeSlotEpFsmTaskEntry 4 }

cucsFabricCartridgeSlotEpFsmTaskFlags OBJECT-TYPE
    SYNTAX       CucsFsmFlags
    MAX-ACCESS   read-only
    STATUS       current
    DESCRIPTION
        "Cisco UCS fabric:CartridgeSlotEpFsmTask:flags
        managed object property"
    ::= { cucsFabricCartridgeSlotEpFsmTaskEntry 5 }

cucsFabricCartridgeSlotEpFsmTaskItem OBJECT-TYPE
    SYNTAX       CucsFabricCartridgeSlotEpFsmTaskItem
    MAX-ACCESS   read-only
    STATUS       current
    DESCRIPTION
        "Cisco UCS fabric:CartridgeSlotEpFsmTask:item managed
        object property"
    ::= { cucsFabricCartridgeSlotEpFsmTaskEntry 6 }

cucsFabricCartridgeSlotEpFsmTaskSeqId OBJECT-TYPE
    SYNTAX       Gauge32
    MAX-ACCESS   read-only
    STATUS       current
    DESCRIPTION
        "Cisco UCS fabric:CartridgeSlotEpFsmTask:seqId
        managed object property"
    ::= { cucsFabricCartridgeSlotEpFsmTaskEntry 7 }

cucsFabricCdpLinkPolicyTable OBJECT-TYPE
    SYNTAX           SEQUENCE OF CucsFabricCdpLinkPolicyEntry
    MAX-ACCESS       not-accessible
    STATUS           current
    DESCRIPTION
        "Cisco UCS fabric:CdpLinkPolicy managed object table"
    ::= { cucsFabricObjects 103 }

cucsFabricCdpLinkPolicyEntry OBJECT-TYPE
    SYNTAX           CucsFabricCdpLinkPolicyEntry
    MAX-ACCESS       not-accessible
    STATUS           current
    DESCRIPTION
        "Entry for the cucsFabricCdpLinkPolicyTable table."
    INDEX { cucsFabricCdpLinkPolicyInstanceId }
    ::= { cucsFabricCdpLinkPolicyTable 1 }

CucsFabricCdpLinkPolicyEntry ::= SEQUENCE {
    cucsFabricCdpLinkPolicyInstanceId                                CucsManagedObjectId,
    cucsFabricCdpLinkPolicyDn                                        CucsManagedObjectDn,
    cucsFabricCdpLinkPolicyRn                                        SnmpAdminString,
    cucsFabricCdpLinkPolicyAdminState                                CucsFabricCdpLinkPolicyAdminState,
    cucsFabricCdpLinkPolicyDescr                                     SnmpAdminString,
    cucsFabricCdpLinkPolicyIntId                                     SnmpAdminString,
    cucsFabricCdpLinkPolicyName                                      SnmpAdminString,
    cucsFabricCdpLinkPolicyPolicyLevel                               Gauge32,
    cucsFabricCdpLinkPolicyPolicyOwner                               CucsPolicyPolicyOwner,
    cucsFabricCdpLinkPolicyProtocol                                  CucsFabricEthCdpPolicyProtocol,
    cucsFabricCdpLinkPolicyType                                      CucsFabricEthLinkPolicyType
}

cucsFabricCdpLinkPolicyInstanceId OBJECT-TYPE
    SYNTAX       CucsManagedObjectId
    MAX-ACCESS   not-accessible
    STATUS       current
    DESCRIPTION
        "Instance identifier of the managed object."
    ::= { cucsFabricCdpLinkPolicyEntry 1 }

cucsFabricCdpLinkPolicyDn OBJECT-TYPE
    SYNTAX       CucsManagedObjectDn
    MAX-ACCESS   read-only
    STATUS       current
    DESCRIPTION
        "Cisco UCS fabric:CdpLinkPolicy:dn managed object property"
    ::= { cucsFabricCdpLinkPolicyEntry 2 }

cucsFabricCdpLinkPolicyRn OBJECT-TYPE
    SYNTAX       SnmpAdminString
    MAX-ACCESS   read-only
    STATUS       current
    DESCRIPTION
        "Cisco UCS fabric:CdpLinkPolicy:rn managed object property"
    ::= { cucsFabricCdpLinkPolicyEntry 3 }

cucsFabricCdpLinkPolicyAdminState OBJECT-TYPE
    SYNTAX       CucsFabricCdpLinkPolicyAdminState
    MAX-ACCESS   read-only
    STATUS       current
    DESCRIPTION
        "Cisco UCS fabric:CdpLinkPolicy:adminState managed
        object property"
    ::= { cucsFabricCdpLinkPolicyEntry 4 }

cucsFabricCdpLinkPolicyDescr OBJECT-TYPE
    SYNTAX       SnmpAdminString
    MAX-ACCESS   read-only
    STATUS       current
    DESCRIPTION
        "Cisco UCS fabric:CdpLinkPolicy:descr managed object property"
    ::= { cucsFabricCdpLinkPolicyEntry 5 }

cucsFabricCdpLinkPolicyIntId OBJECT-TYPE
    SYNTAX       SnmpAdminString
    MAX-ACCESS   read-only
    STATUS       current
    DESCRIPTION
        "Cisco UCS fabric:CdpLinkPolicy:intId managed object property"
    ::= { cucsFabricCdpLinkPolicyEntry 6 }

cucsFabricCdpLinkPolicyName OBJECT-TYPE
    SYNTAX       SnmpAdminString
    MAX-ACCESS   read-only
    STATUS       current
    DESCRIPTION
        "Cisco UCS fabric:CdpLinkPolicy:name managed object property"
    ::= { cucsFabricCdpLinkPolicyEntry 7 }

cucsFabricCdpLinkPolicyPolicyLevel OBJECT-TYPE
    SYNTAX       Gauge32
    MAX-ACCESS   read-only
    STATUS       current
    DESCRIPTION
        "Cisco UCS fabric:CdpLinkPolicy:policyLevel managed
        object property"
    ::= { cucsFabricCdpLinkPolicyEntry 8 }

cucsFabricCdpLinkPolicyPolicyOwner OBJECT-TYPE
    SYNTAX       CucsPolicyPolicyOwner
    MAX-ACCESS   read-only
    STATUS       current
    DESCRIPTION
        "Cisco UCS fabric:CdpLinkPolicy:policyOwner managed
        object property"
    ::= { cucsFabricCdpLinkPolicyEntry 9 }

cucsFabricCdpLinkPolicyProtocol OBJECT-TYPE
    SYNTAX       CucsFabricEthCdpPolicyProtocol
    MAX-ACCESS   read-only
    STATUS       current
    DESCRIPTION
        "Cisco UCS fabric:CdpLinkPolicy:protocol managed object property"
    ::= { cucsFabricCdpLinkPolicyEntry 10 }

cucsFabricCdpLinkPolicyType OBJECT-TYPE
    SYNTAX       CucsFabricEthLinkPolicyType
    MAX-ACCESS   read-only
    STATUS       current
    DESCRIPTION
        "Cisco UCS fabric:CdpLinkPolicy:type managed object property"
    ::= { cucsFabricCdpLinkPolicyEntry 11 }

cucsFabricChangedObjectRefTable OBJECT-TYPE
    SYNTAX           SEQUENCE OF CucsFabricChangedObjectRefEntry
    MAX-ACCESS       not-accessible
    STATUS           current
    DESCRIPTION
        "Cisco UCS fabric:ChangedObjectRef managed object table"
    ::= { cucsFabricObjects 97 }

cucsFabricChangedObjectRefEntry OBJECT-TYPE
    SYNTAX           CucsFabricChangedObjectRefEntry
    MAX-ACCESS       not-accessible
    STATUS           current
    DESCRIPTION
        "Entry for the cucsFabricChangedObjectRefTable table."
    INDEX { cucsFabricChangedObjectRefInstanceId }
    ::= { cucsFabricChangedObjectRefTable 1 }

CucsFabricChangedObjectRefEntry ::= SEQUENCE {
    cucsFabricChangedObjectRefInstanceId                             CucsManagedObjectId,
    cucsFabricChangedObjectRefDn                                     CucsManagedObjectDn,
    cucsFabricChangedObjectRefRn                                     SnmpAdminString,
    cucsFabricChangedObjectRefCentraleVnetEpDn                       SnmpAdminString,
    cucsFabricChangedObjectRefId                                     Gauge32,
    cucsFabricChangedObjectRefOldCentraleVnetEpDn                    SnmpAdminString,
    cucsFabricChangedObjectRefRefObjStatus                           CucsFabricStatus,
    cucsFabricChangedObjectRefUcsmVnetEpDn                           SnmpAdminString
}

cucsFabricChangedObjectRefInstanceId OBJECT-TYPE
    SYNTAX       CucsManagedObjectId
    MAX-ACCESS   not-accessible
    STATUS       current
    DESCRIPTION
        "Instance identifier of the managed object."
    ::= { cucsFabricChangedObjectRefEntry 1 }

cucsFabricChangedObjectRefDn OBJECT-TYPE
    SYNTAX       CucsManagedObjectDn
    MAX-ACCESS   read-only
    STATUS       current
    DESCRIPTION
        "Cisco UCS fabric:ChangedObjectRef:dn managed object property"
    ::= { cucsFabricChangedObjectRefEntry 2 }

cucsFabricChangedObjectRefRn OBJECT-TYPE
    SYNTAX       SnmpAdminString
    MAX-ACCESS   read-only
    STATUS       current
    DESCRIPTION
        "Cisco UCS fabric:ChangedObjectRef:rn managed object property"
    ::= { cucsFabricChangedObjectRefEntry 3 }

cucsFabricChangedObjectRefCentraleVnetEpDn OBJECT-TYPE
    SYNTAX       SnmpAdminString
    MAX-ACCESS   read-only
    STATUS       current
    DESCRIPTION
        "Cisco UCS fabric:ChangedObjectRef:centraleVnetEpDn
        managed object property"
    ::= { cucsFabricChangedObjectRefEntry 4 }

cucsFabricChangedObjectRefId OBJECT-TYPE
    SYNTAX       Gauge32
    MAX-ACCESS   read-only
    STATUS       current
    DESCRIPTION
        "Cisco UCS fabric:ChangedObjectRef:id managed object property"
    ::= { cucsFabricChangedObjectRefEntry 5 }

cucsFabricChangedObjectRefOldCentraleVnetEpDn OBJECT-TYPE
    SYNTAX       SnmpAdminString
    MAX-ACCESS   read-only
    STATUS       current
    DESCRIPTION
        "Cisco UCS fabric:ChangedObjectRef:oldCentraleVnetEpDn
        managed object property"
    ::= { cucsFabricChangedObjectRefEntry 6 }

cucsFabricChangedObjectRefRefObjStatus OBJECT-TYPE
    SYNTAX       CucsFabricStatus
    MAX-ACCESS   read-only
    STATUS       current
    DESCRIPTION
        "Cisco UCS fabric:ChangedObjectRef:refObjStatus
        managed object property"
    ::= { cucsFabricChangedObjectRefEntry 7 }

cucsFabricChangedObjectRefUcsmVnetEpDn OBJECT-TYPE
    SYNTAX       SnmpAdminString
    MAX-ACCESS   read-only
    STATUS       current
    DESCRIPTION
        "Cisco UCS fabric:ChangedObjectRef:ucsmVnetEpDn
        managed object property"
    ::= { cucsFabricChangedObjectRefEntry 8 }

cucsFabricChassisEpTable OBJECT-TYPE
    SYNTAX           SEQUENCE OF CucsFabricChassisEpEntry
    MAX-ACCESS       not-accessible
    STATUS           current
    DESCRIPTION
        "Cisco UCS fabric:ChassisEp managed object table"
    ::= { cucsFabricObjects 1 }

cucsFabricChassisEpEntry OBJECT-TYPE
    SYNTAX           CucsFabricChassisEpEntry
    MAX-ACCESS       not-accessible
    STATUS           current
    DESCRIPTION
        "Entry for the cucsFabricChassisEpTable table."
    INDEX { cucsFabricChassisEpInstanceId }
    ::= { cucsFabricChassisEpTable 1 }

CucsFabricChassisEpEntry ::= SEQUENCE {
    cucsFabricChassisEpInstanceId                                    CucsManagedObjectId,
    cucsFabricChassisEpDn                                            CucsManagedObjectDn,
    cucsFabricChassisEpRn                                            SnmpAdminString,
    cucsFabricChassisEpAdminState                                    CucsFabricInternalEpAdminState,
    cucsFabricChassisEpChassisDn                                     SnmpAdminString,
    cucsFabricChassisEpChassisId                                     Gauge32,
    cucsFabricChassisEpEpDn                                          SnmpAdminString,
    cucsFabricChassisEpIfRole                                        CucsFabricComputeEpIfRole,
    cucsFabricChassisEpIfType                                        CucsFabricPIoEpIfType,
    cucsFabricChassisEpLicGP                                         Unsigned64,
    cucsFabricChassisEpLicState                                      CucsLicenseState,
    cucsFabricChassisEpLocale                                        CucsFabricInternalEpLocale,
    cucsFabricChassisEpModel                                         SnmpAdminString,
    cucsFabricChassisEpName                                          SnmpAdminString,
    cucsFabricChassisEpPeerDn                                        SnmpAdminString,
    cucsFabricChassisEpPeerPortId                                    Gauge32,
    cucsFabricChassisEpPeerSlotId                                    Gauge32,
    cucsFabricChassisEpPortId                                        CucsFabricPIoEpPortId,
    cucsFabricChassisEpRevision                                      SnmpAdminString,
    cucsFabricChassisEpSerial                                        SnmpAdminString,
    cucsFabricChassisEpSlotId                                        CucsFabricPIoEpSlotId,
    cucsFabricChassisEpSwitchId                                      CucsNetworkSwitchId,
    cucsFabricChassisEpTransport                                     CucsNetworkTransport,
    cucsFabricChassisEpType                                          CucsFabricComputeEpType,
    cucsFabricChassisEpVendor                                        SnmpAdminString,
    cucsFabricChassisEpPeerChassisId                                 Gauge32,
    cucsFabricChassisEpFltAggr                                       Unsigned64,
    cucsFabricChassisEpOperState                                     CucsFabricPIoEpOperState,
    cucsFabricChassisEpOperStateReason                               SnmpAdminString,
    cucsFabricChassisEpAggrPortId                                    Gauge32,
    cucsFabricChassisEpPeerAggrPortId                                Gauge32,
    cucsFabricChassisEpAutoNegotiate                                 TruthValue
}

cucsFabricChassisEpInstanceId OBJECT-TYPE
    SYNTAX       CucsManagedObjectId
    MAX-ACCESS   not-accessible
    STATUS       current
    DESCRIPTION
        "Instance identifier of the managed object."
    ::= { cucsFabricChassisEpEntry 1 }

cucsFabricChassisEpDn OBJECT-TYPE
    SYNTAX       CucsManagedObjectDn
    MAX-ACCESS   read-only
    STATUS       current
    DESCRIPTION
        "Cisco UCS fabric:ChassisEp:dn managed object property"
    ::= { cucsFabricChassisEpEntry 2 }

cucsFabricChassisEpRn OBJECT-TYPE
    SYNTAX       SnmpAdminString
    MAX-ACCESS   read-only
    STATUS       current
    DESCRIPTION
        "Cisco UCS fabric:ChassisEp:rn managed object property"
    ::= { cucsFabricChassisEpEntry 3 }

cucsFabricChassisEpAdminState OBJECT-TYPE
    SYNTAX       CucsFabricInternalEpAdminState
    MAX-ACCESS   read-only
    STATUS       current
    DESCRIPTION
        "Cisco UCS fabric:ChassisEp:adminState managed object property"
    ::= { cucsFabricChassisEpEntry 4 }

cucsFabricChassisEpChassisDn OBJECT-TYPE
    SYNTAX       SnmpAdminString
    MAX-ACCESS   read-only
    STATUS       current
    DESCRIPTION
        "Cisco UCS fabric:ChassisEp:chassisDn managed object property"
    ::= { cucsFabricChassisEpEntry 5 }

cucsFabricChassisEpChassisId OBJECT-TYPE
    SYNTAX       Gauge32
    MAX-ACCESS   read-only
    STATUS       current
    DESCRIPTION
        "Cisco UCS fabric:ChassisEp:chassisId managed object property"
    ::= { cucsFabricChassisEpEntry 6 }

cucsFabricChassisEpEpDn OBJECT-TYPE
    SYNTAX       SnmpAdminString
    MAX-ACCESS   read-only
    STATUS       current
    DESCRIPTION
        "Cisco UCS fabric:ChassisEp:epDn managed object property"
    ::= { cucsFabricChassisEpEntry 7 }

cucsFabricChassisEpIfRole OBJECT-TYPE
    SYNTAX       CucsFabricComputeEpIfRole
    MAX-ACCESS   read-only
    STATUS       current
    DESCRIPTION
        "Cisco UCS fabric:ChassisEp:ifRole managed object property"
    ::= { cucsFabricChassisEpEntry 8 }

cucsFabricChassisEpIfType OBJECT-TYPE
    SYNTAX       CucsFabricPIoEpIfType
    MAX-ACCESS   read-only
    STATUS       current
    DESCRIPTION
        "Cisco UCS fabric:ChassisEp:ifType managed object property"
    ::= { cucsFabricChassisEpEntry 9 }

cucsFabricChassisEpLicGP OBJECT-TYPE
    SYNTAX       Unsigned64
    MAX-ACCESS   read-only
    STATUS       current
    DESCRIPTION
        "Cisco UCS fabric:ChassisEp:licGP managed object property"
    ::= { cucsFabricChassisEpEntry 10 }

cucsFabricChassisEpLicState OBJECT-TYPE
    SYNTAX       CucsLicenseState
    MAX-ACCESS   read-only
    STATUS       current
    DESCRIPTION
        "Cisco UCS fabric:ChassisEp:licState managed object property"
    ::= { cucsFabricChassisEpEntry 11 }

cucsFabricChassisEpLocale OBJECT-TYPE
    SYNTAX       CucsFabricInternalEpLocale
    MAX-ACCESS   read-only
    STATUS       current
    DESCRIPTION
        "Cisco UCS fabric:ChassisEp:locale managed object property"
    ::= { cucsFabricChassisEpEntry 12 }

cucsFabricChassisEpModel OBJECT-TYPE
    SYNTAX       SnmpAdminString
    MAX-ACCESS   read-only
    STATUS       current
    DESCRIPTION
        "Cisco UCS fabric:ChassisEp:model managed object property"
    ::= { cucsFabricChassisEpEntry 13 }

cucsFabricChassisEpName OBJECT-TYPE
    SYNTAX       SnmpAdminString
    MAX-ACCESS   read-only
    STATUS       current
    DESCRIPTION
        "Cisco UCS fabric:ChassisEp:name managed object property"
    ::= { cucsFabricChassisEpEntry 14 }

cucsFabricChassisEpPeerDn OBJECT-TYPE
    SYNTAX       SnmpAdminString
    MAX-ACCESS   read-only
    STATUS       current
    DESCRIPTION
        "Cisco UCS fabric:ChassisEp:peerDn managed object property"
    ::= { cucsFabricChassisEpEntry 15 }

cucsFabricChassisEpPeerPortId OBJECT-TYPE
    SYNTAX       Gauge32
    MAX-ACCESS   read-only
    STATUS       current
    DESCRIPTION
        "Cisco UCS fabric:ChassisEp:peerPortId managed object property"
    ::= { cucsFabricChassisEpEntry 16 }

cucsFabricChassisEpPeerSlotId OBJECT-TYPE
    SYNTAX       Gauge32
    MAX-ACCESS   read-only
    STATUS       current
    DESCRIPTION
        "Cisco UCS fabric:ChassisEp:peerSlotId managed object property"
    ::= { cucsFabricChassisEpEntry 17 }

cucsFabricChassisEpPortId OBJECT-TYPE
    SYNTAX       CucsFabricPIoEpPortId
    MAX-ACCESS   read-only
    STATUS       current
    DESCRIPTION
        "Cisco UCS fabric:ChassisEp:portId managed object property"
    ::= { cucsFabricChassisEpEntry 18 }

cucsFabricChassisEpRevision OBJECT-TYPE
    SYNTAX       SnmpAdminString
    MAX-ACCESS   read-only
    STATUS       current
    DESCRIPTION
        "Cisco UCS fabric:ChassisEp:revision managed object property"
    ::= { cucsFabricChassisEpEntry 19 }

cucsFabricChassisEpSerial OBJECT-TYPE
    SYNTAX       SnmpAdminString
    MAX-ACCESS   read-only
    STATUS       current
    DESCRIPTION
        "Cisco UCS fabric:ChassisEp:serial managed object property"
    ::= { cucsFabricChassisEpEntry 20 }

cucsFabricChassisEpSlotId OBJECT-TYPE
    SYNTAX       CucsFabricPIoEpSlotId
    MAX-ACCESS   read-only
    STATUS       current
    DESCRIPTION
        "Cisco UCS fabric:ChassisEp:slotId managed object property"
    ::= { cucsFabricChassisEpEntry 21 }

cucsFabricChassisEpSwitchId OBJECT-TYPE
    SYNTAX       CucsNetworkSwitchId
    MAX-ACCESS   read-only
    STATUS       current
    DESCRIPTION
        "Cisco UCS fabric:ChassisEp:switchId managed object property"
    ::= { cucsFabricChassisEpEntry 22 }

cucsFabricChassisEpTransport OBJECT-TYPE
    SYNTAX       CucsNetworkTransport
    MAX-ACCESS   read-only
    STATUS       current
    DESCRIPTION
        "Cisco UCS fabric:ChassisEp:transport managed object property"
    ::= { cucsFabricChassisEpEntry 23 }

cucsFabricChassisEpType OBJECT-TYPE
    SYNTAX       CucsFabricComputeEpType
    MAX-ACCESS   read-only
    STATUS       current
    DESCRIPTION
        "Cisco UCS fabric:ChassisEp:type managed object property"
    ::= { cucsFabricChassisEpEntry 24 }

cucsFabricChassisEpVendor OBJECT-TYPE
    SYNTAX       SnmpAdminString
    MAX-ACCESS   read-only
    STATUS       current
    DESCRIPTION
        "Cisco UCS fabric:ChassisEp:vendor managed object property"
    ::= { cucsFabricChassisEpEntry 25 }

cucsFabricChassisEpPeerChassisId OBJECT-TYPE
    SYNTAX       Gauge32
    MAX-ACCESS   read-only
    STATUS       current
    DESCRIPTION
        "Cisco UCS fabric:ChassisEp:peerChassisId managed object property"
    ::= { cucsFabricChassisEpEntry 26 }

cucsFabricChassisEpFltAggr OBJECT-TYPE
    SYNTAX       Unsigned64
    MAX-ACCESS   read-only
    STATUS       current
    DESCRIPTION
        "Cisco UCS fabric:ChassisEp:fltAggr managed object property"
    ::= { cucsFabricChassisEpEntry 27 }

cucsFabricChassisEpOperState OBJECT-TYPE
    SYNTAX       CucsFabricPIoEpOperState
    MAX-ACCESS   read-only
    STATUS       current
    DESCRIPTION
        "Cisco UCS fabric:ChassisEp:operState managed object property"
    ::= { cucsFabricChassisEpEntry 28 }

cucsFabricChassisEpOperStateReason OBJECT-TYPE
    SYNTAX       SnmpAdminString
    MAX-ACCESS   read-only
    STATUS       current
    DESCRIPTION
        "Cisco UCS fabric:ChassisEp:operStateReason managed
        object property"
    ::= { cucsFabricChassisEpEntry 29 }

cucsFabricChassisEpAggrPortId OBJECT-TYPE
    SYNTAX       Gauge32
    MAX-ACCESS   read-only
    STATUS       current
    DESCRIPTION
        "Cisco UCS fabric:ChassisEp:aggrPortId managed object property"
    ::= { cucsFabricChassisEpEntry 30 }

cucsFabricChassisEpPeerAggrPortId OBJECT-TYPE
    SYNTAX       Gauge32
    MAX-ACCESS   read-only
    STATUS       current
    DESCRIPTION
        "Cisco UCS fabric:ChassisEp:peerAggrPortId managed
        object property"
    ::= { cucsFabricChassisEpEntry 31 }

cucsFabricChassisEpAutoNegotiate OBJECT-TYPE
    SYNTAX       TruthValue
    MAX-ACCESS   read-only
    STATUS       current
    DESCRIPTION
        "Cisco UCS fabric:ChassisEp:autoNegotiate managed object property"
    ::= { cucsFabricChassisEpEntry 32 }

cucsFabricComputeMSlotEpTable OBJECT-TYPE
    SYNTAX           SEQUENCE OF CucsFabricComputeMSlotEpEntry
    MAX-ACCESS       not-accessible
    STATUS           current
    DESCRIPTION
        "Cisco UCS fabric:ComputeMSlotEp managed object table"
    ::= { cucsFabricObjects 131 }

cucsFabricComputeMSlotEpEntry OBJECT-TYPE
    SYNTAX           CucsFabricComputeMSlotEpEntry
    MAX-ACCESS       not-accessible
    STATUS           current
    DESCRIPTION
        "Entry for the cucsFabricComputeMSlotEpTable table."
    INDEX { cucsFabricComputeMSlotEpInstanceId }
    ::= { cucsFabricComputeMSlotEpTable 1 }

CucsFabricComputeMSlotEpEntry ::= SEQUENCE {
    cucsFabricComputeMSlotEpInstanceId                               CucsManagedObjectId,
    cucsFabricComputeMSlotEpDn                                       CucsManagedObjectDn,
    cucsFabricComputeMSlotEpRn                                       SnmpAdminString,
    cucsFabricComputeMSlotEpAdminState                               CucsFabricInternalEpAdminState,
    cucsFabricComputeMSlotEpChassisId                                Gauge32,
    cucsFabricComputeMSlotEpConnPath                                 CucsEquipmentConnectionStatus,
    cucsFabricComputeMSlotEpConnStatus                               CucsEquipmentConnectionStatus,
    cucsFabricComputeMSlotEpDiscovery                                CucsComputeDiscovery,
    cucsFabricComputeMSlotEpDiscoveryStatus                          CucsEquipmentConnectionStatus,
    cucsFabricComputeMSlotEpEpDn                                     SnmpAdminString,
    cucsFabricComputeMSlotEpFltAggr                                  Unsigned64,
    cucsFabricComputeMSlotEpFruIdentTrigTs                           Unsigned64,
    cucsFabricComputeMSlotEpFsmDescr                                 SnmpAdminString,
    cucsFabricComputeMSlotEpFsmPrev                                  SnmpAdminString,
    cucsFabricComputeMSlotEpFsmProgr                                 Gauge32,
    cucsFabricComputeMSlotEpFsmRmtInvErrCode                         Gauge32,
    cucsFabricComputeMSlotEpFsmRmtInvErrDescr                        SnmpAdminString,
    cucsFabricComputeMSlotEpFsmRmtInvRslt                            CucsConditionRemoteInvRslt,
    cucsFabricComputeMSlotEpFsmStageDescr                            SnmpAdminString,
    cucsFabricComputeMSlotEpFsmStamp                                 DateAndTime,
    cucsFabricComputeMSlotEpFsmStatus                                SnmpAdminString,
    cucsFabricComputeMSlotEpFsmTry                                   Gauge32,
    cucsFabricComputeMSlotEpIfRole                                   CucsFabricComputeEpIfRole,
    cucsFabricComputeMSlotEpIfType                                   CucsFabricPIoEpIfType,
    cucsFabricComputeMSlotEpLcTs                                     DateAndTime,
    cucsFabricComputeMSlotEpLicGP                                    Unsigned64,
    cucsFabricComputeMSlotEpLicState                                 CucsLicenseState,
    cucsFabricComputeMSlotEpLocale                                   CucsFabricInternalEpLocale,
    cucsFabricComputeMSlotEpManagingInst                             CucsNetworkSwitchId,
    cucsFabricComputeMSlotEpModel                                    SnmpAdminString,
    cucsFabricComputeMSlotEpName                                     SnmpAdminString,
    cucsFabricComputeMSlotEpOperState                                CucsFabricPIoEpOperState,
    cucsFabricComputeMSlotEpOperStateReason                          SnmpAdminString,
    cucsFabricComputeMSlotEpPeerChassisId                            Gauge32,
    cucsFabricComputeMSlotEpPeerDn                                   SnmpAdminString,
    cucsFabricComputeMSlotEpPeerPortId                               Gauge32,
    cucsFabricComputeMSlotEpPeerSlotId                               Gauge32,
    cucsFabricComputeMSlotEpPortId                                   CucsFabricPIoEpPortId,
    cucsFabricComputeMSlotEpPresence                                 CucsEquipmentSlotStatus,
    cucsFabricComputeMSlotEpRevision                                 SnmpAdminString,
    cucsFabricComputeMSlotEpSerial                                   SnmpAdminString,
    cucsFabricComputeMSlotEpServerInstanceId                         CucsFabricComputeMSlotEpServerInstanceId,
    cucsFabricComputeMSlotEpSlotAdminState                           CucsFabricSlotAdminState,
    cucsFabricComputeMSlotEpSlotId                                   CucsFabricComputeMSlotEpSlotId,
    cucsFabricComputeMSlotEpSwitchId                                 CucsNetworkSwitchId,
    cucsFabricComputeMSlotEpTransport                                CucsNetworkTransport,
    cucsFabricComputeMSlotEpType                                     CucsFabricComputeEpType,
    cucsFabricComputeMSlotEpVendor                                   SnmpAdminString,
    cucsFabricComputeMSlotEpAggrPortId                               Gauge32,
    cucsFabricComputeMSlotEpAutoNegotiate                            TruthValue,
    cucsFabricComputeMSlotEpPeerAggrPortId                           Gauge32
}

cucsFabricComputeMSlotEpInstanceId OBJECT-TYPE
    SYNTAX       CucsManagedObjectId
    MAX-ACCESS   not-accessible
    STATUS       current
    DESCRIPTION
        "Instance identifier of the managed object."
    ::= { cucsFabricComputeMSlotEpEntry 1 }

cucsFabricComputeMSlotEpDn OBJECT-TYPE
    SYNTAX       CucsManagedObjectDn
    MAX-ACCESS   read-only
    STATUS       current
    DESCRIPTION
        "Cisco UCS fabric:ComputeMSlotEp:dn managed object property"
    ::= { cucsFabricComputeMSlotEpEntry 2 }

cucsFabricComputeMSlotEpRn OBJECT-TYPE
    SYNTAX       SnmpAdminString
    MAX-ACCESS   read-only
    STATUS       current
    DESCRIPTION
        "Cisco UCS fabric:ComputeMSlotEp:rn managed object property"
    ::= { cucsFabricComputeMSlotEpEntry 3 }

cucsFabricComputeMSlotEpAdminState OBJECT-TYPE
    SYNTAX       CucsFabricInternalEpAdminState
    MAX-ACCESS   read-only
    STATUS       current
    DESCRIPTION
        "Cisco UCS fabric:ComputeMSlotEp:adminState managed
        object property"
    ::= { cucsFabricComputeMSlotEpEntry 4 }

cucsFabricComputeMSlotEpChassisId OBJECT-TYPE
    SYNTAX       Gauge32
    MAX-ACCESS   read-only
    STATUS       current
    DESCRIPTION
        "Cisco UCS fabric:ComputeMSlotEp:chassisId managed
        object property"
    ::= { cucsFabricComputeMSlotEpEntry 5 }

cucsFabricComputeMSlotEpConnPath OBJECT-TYPE
    SYNTAX       CucsEquipmentConnectionStatus
    MAX-ACCESS   read-only
    STATUS       current
    DESCRIPTION
        "Cisco UCS fabric:ComputeMSlotEp:connPath managed object property"
    ::= { cucsFabricComputeMSlotEpEntry 6 }

cucsFabricComputeMSlotEpConnStatus OBJECT-TYPE
    SYNTAX       CucsEquipmentConnectionStatus
    MAX-ACCESS   read-only
    STATUS       current
    DESCRIPTION
        "Cisco UCS fabric:ComputeMSlotEp:connStatus managed
        object property"
    ::= { cucsFabricComputeMSlotEpEntry 7 }

cucsFabricComputeMSlotEpDiscovery OBJECT-TYPE
    SYNTAX       CucsComputeDiscovery
    MAX-ACCESS   read-only
    STATUS       current
    DESCRIPTION
        "Cisco UCS fabric:ComputeMSlotEp:discovery managed
        object property"
    ::= { cucsFabricComputeMSlotEpEntry 8 }

cucsFabricComputeMSlotEpDiscoveryStatus OBJECT-TYPE
    SYNTAX       CucsEquipmentConnectionStatus
    MAX-ACCESS   read-only
    STATUS       current
    DESCRIPTION
        "Cisco UCS fabric:ComputeMSlotEp:discoveryStatus
        managed object property"
    ::= { cucsFabricComputeMSlotEpEntry 9 }

cucsFabricComputeMSlotEpEpDn OBJECT-TYPE
    SYNTAX       SnmpAdminString
    MAX-ACCESS   read-only
    STATUS       current
    DESCRIPTION
        "Cisco UCS fabric:ComputeMSlotEp:epDn managed object property"
    ::= { cucsFabricComputeMSlotEpEntry 10 }

cucsFabricComputeMSlotEpFltAggr OBJECT-TYPE
    SYNTAX       Unsigned64
    MAX-ACCESS   read-only
    STATUS       current
    DESCRIPTION
        "Cisco UCS fabric:ComputeMSlotEp:fltAggr managed object property"
    ::= { cucsFabricComputeMSlotEpEntry 11 }

cucsFabricComputeMSlotEpFruIdentTrigTs OBJECT-TYPE
    SYNTAX       Unsigned64
    MAX-ACCESS   read-only
    STATUS       current
    DESCRIPTION
        "Cisco UCS fabric:ComputeMSlotEp:fruIdentTrigTs
        managed object property"
    ::= { cucsFabricComputeMSlotEpEntry 12 }

cucsFabricComputeMSlotEpFsmDescr OBJECT-TYPE
    SYNTAX       SnmpAdminString
    MAX-ACCESS   read-only
    STATUS       current
    DESCRIPTION
        "Cisco UCS fabric:ComputeMSlotEp:fsmDescr managed object property"
    ::= { cucsFabricComputeMSlotEpEntry 13 }

cucsFabricComputeMSlotEpFsmPrev OBJECT-TYPE
    SYNTAX       SnmpAdminString
    MAX-ACCESS   read-only
    STATUS       current
    DESCRIPTION
        "Cisco UCS fabric:ComputeMSlotEp:fsmPrev managed object property"
    ::= { cucsFabricComputeMSlotEpEntry 14 }

cucsFabricComputeMSlotEpFsmProgr OBJECT-TYPE
    SYNTAX       Gauge32
    MAX-ACCESS   read-only
    STATUS       current
    DESCRIPTION
        "Cisco UCS fabric:ComputeMSlotEp:fsmProgr managed object property"
    ::= { cucsFabricComputeMSlotEpEntry 15 }

cucsFabricComputeMSlotEpFsmRmtInvErrCode OBJECT-TYPE
    SYNTAX       Gauge32
    MAX-ACCESS   read-only
    STATUS       current
    DESCRIPTION
        "Cisco UCS fabric:ComputeMSlotEp:fsmRmtInvErrCode
        managed object property"
    ::= { cucsFabricComputeMSlotEpEntry 16 }

cucsFabricComputeMSlotEpFsmRmtInvErrDescr OBJECT-TYPE
    SYNTAX       SnmpAdminString
    MAX-ACCESS   read-only
    STATUS       current
    DESCRIPTION
        "Cisco UCS fabric:ComputeMSlotEp:fsmRmtInvErrDescr
        managed object property"
    ::= { cucsFabricComputeMSlotEpEntry 17 }

cucsFabricComputeMSlotEpFsmRmtInvRslt OBJECT-TYPE
    SYNTAX       CucsConditionRemoteInvRslt
    MAX-ACCESS   read-only
    STATUS       current
    DESCRIPTION
        "Cisco UCS fabric:ComputeMSlotEp:fsmRmtInvRslt
        managed object property"
    ::= { cucsFabricComputeMSlotEpEntry 18 }

cucsFabricComputeMSlotEpFsmStageDescr OBJECT-TYPE
    SYNTAX       SnmpAdminString
    MAX-ACCESS   read-only
    STATUS       current
    DESCRIPTION
        "Cisco UCS fabric:ComputeMSlotEp:fsmStageDescr
        managed object property"
    ::= { cucsFabricComputeMSlotEpEntry 19 }

cucsFabricComputeMSlotEpFsmStamp OBJECT-TYPE
    SYNTAX       DateAndTime
    MAX-ACCESS   read-only
    STATUS       current
    DESCRIPTION
        "Cisco UCS fabric:ComputeMSlotEp:fsmStamp managed object property"
    ::= { cucsFabricComputeMSlotEpEntry 20 }

cucsFabricComputeMSlotEpFsmStatus OBJECT-TYPE
    SYNTAX       SnmpAdminString
    MAX-ACCESS   read-only
    STATUS       current
    DESCRIPTION
        "Cisco UCS fabric:ComputeMSlotEp:fsmStatus managed
        object property"
    ::= { cucsFabricComputeMSlotEpEntry 21 }

cucsFabricComputeMSlotEpFsmTry OBJECT-TYPE
    SYNTAX       Gauge32
    MAX-ACCESS   read-only
    STATUS       current
    DESCRIPTION
        "Cisco UCS fabric:ComputeMSlotEp:fsmTry managed object property"
    ::= { cucsFabricComputeMSlotEpEntry 22 }

cucsFabricComputeMSlotEpIfRole OBJECT-TYPE
    SYNTAX       CucsFabricComputeEpIfRole
    MAX-ACCESS   read-only
    STATUS       current
    DESCRIPTION
        "Cisco UCS fabric:ComputeMSlotEp:ifRole managed object property"
    ::= { cucsFabricComputeMSlotEpEntry 23 }

cucsFabricComputeMSlotEpIfType OBJECT-TYPE
    SYNTAX       CucsFabricPIoEpIfType
    MAX-ACCESS   read-only
    STATUS       current
    DESCRIPTION
        "Cisco UCS fabric:ComputeMSlotEp:ifType managed object property"
    ::= { cucsFabricComputeMSlotEpEntry 24 }

cucsFabricComputeMSlotEpLcTs OBJECT-TYPE
    SYNTAX       DateAndTime
    MAX-ACCESS   read-only
    STATUS       current
    DESCRIPTION
        "Cisco UCS fabric:ComputeMSlotEp:lcTs managed object property"
    ::= { cucsFabricComputeMSlotEpEntry 25 }

cucsFabricComputeMSlotEpLicGP OBJECT-TYPE
    SYNTAX       Unsigned64
    MAX-ACCESS   read-only
    STATUS       current
    DESCRIPTION
        "Cisco UCS fabric:ComputeMSlotEp:licGP managed object property"
    ::= { cucsFabricComputeMSlotEpEntry 26 }

cucsFabricComputeMSlotEpLicState OBJECT-TYPE
    SYNTAX       CucsLicenseState
    MAX-ACCESS   read-only
    STATUS       current
    DESCRIPTION
        "Cisco UCS fabric:ComputeMSlotEp:licState managed object property"
    ::= { cucsFabricComputeMSlotEpEntry 27 }

cucsFabricComputeMSlotEpLocale OBJECT-TYPE
    SYNTAX       CucsFabricInternalEpLocale
    MAX-ACCESS   read-only
    STATUS       current
    DESCRIPTION
        "Cisco UCS fabric:ComputeMSlotEp:locale managed object property"
    ::= { cucsFabricComputeMSlotEpEntry 28 }

cucsFabricComputeMSlotEpManagingInst OBJECT-TYPE
    SYNTAX       CucsNetworkSwitchId
    MAX-ACCESS   read-only
    STATUS       current
    DESCRIPTION
        "Cisco UCS fabric:ComputeMSlotEp:managingInst managed
        object property"
    ::= { cucsFabricComputeMSlotEpEntry 29 }

cucsFabricComputeMSlotEpModel OBJECT-TYPE
    SYNTAX       SnmpAdminString
    MAX-ACCESS   read-only
    STATUS       current
    DESCRIPTION
        "Cisco UCS fabric:ComputeMSlotEp:model managed object property"
    ::= { cucsFabricComputeMSlotEpEntry 30 }

cucsFabricComputeMSlotEpName OBJECT-TYPE
    SYNTAX       SnmpAdminString
    MAX-ACCESS   read-only
    STATUS       current
    DESCRIPTION
        "Cisco UCS fabric:ComputeMSlotEp:name managed object property"
    ::= { cucsFabricComputeMSlotEpEntry 31 }

cucsFabricComputeMSlotEpOperState OBJECT-TYPE
    SYNTAX       CucsFabricPIoEpOperState
    MAX-ACCESS   read-only
    STATUS       current
    DESCRIPTION
        "Cisco UCS fabric:ComputeMSlotEp:operState managed
        object property"
    ::= { cucsFabricComputeMSlotEpEntry 32 }

cucsFabricComputeMSlotEpOperStateReason OBJECT-TYPE
    SYNTAX       SnmpAdminString
    MAX-ACCESS   read-only
    STATUS       current
    DESCRIPTION
        "Cisco UCS fabric:ComputeMSlotEp:operStateReason
        managed object property"
    ::= { cucsFabricComputeMSlotEpEntry 33 }

cucsFabricComputeMSlotEpPeerChassisId OBJECT-TYPE
    SYNTAX       Gauge32
    MAX-ACCESS   read-only
    STATUS       current
    DESCRIPTION
        "Cisco UCS fabric:ComputeMSlotEp:peerChassisId
        managed object property"
    ::= { cucsFabricComputeMSlotEpEntry 34 }

cucsFabricComputeMSlotEpPeerDn OBJECT-TYPE
    SYNTAX       SnmpAdminString
    MAX-ACCESS   read-only
    STATUS       current
    DESCRIPTION
        "Cisco UCS fabric:ComputeMSlotEp:peerDn managed object property"
    ::= { cucsFabricComputeMSlotEpEntry 35 }

cucsFabricComputeMSlotEpPeerPortId OBJECT-TYPE
    SYNTAX       Gauge32
    MAX-ACCESS   read-only
    STATUS       current
    DESCRIPTION
        "Cisco UCS fabric:ComputeMSlotEp:peerPortId managed
        object property"
    ::= { cucsFabricComputeMSlotEpEntry 36 }

cucsFabricComputeMSlotEpPeerSlotId OBJECT-TYPE
    SYNTAX       Gauge32
    MAX-ACCESS   read-only
    STATUS       current
    DESCRIPTION
        "Cisco UCS fabric:ComputeMSlotEp:peerSlotId managed
        object property"
    ::= { cucsFabricComputeMSlotEpEntry 37 }

cucsFabricComputeMSlotEpPortId OBJECT-TYPE
    SYNTAX       CucsFabricPIoEpPortId
    MAX-ACCESS   read-only
    STATUS       current
    DESCRIPTION
        "Cisco UCS fabric:ComputeMSlotEp:portId managed object property"
    ::= { cucsFabricComputeMSlotEpEntry 38 }

cucsFabricComputeMSlotEpPresence OBJECT-TYPE
    SYNTAX       CucsEquipmentSlotStatus
    MAX-ACCESS   read-only
    STATUS       current
    DESCRIPTION
        "Cisco UCS fabric:ComputeMSlotEp:presence managed object property"
    ::= { cucsFabricComputeMSlotEpEntry 39 }

cucsFabricComputeMSlotEpRevision OBJECT-TYPE
    SYNTAX       SnmpAdminString
    MAX-ACCESS   read-only
    STATUS       current
    DESCRIPTION
        "Cisco UCS fabric:ComputeMSlotEp:revision managed object property"
    ::= { cucsFabricComputeMSlotEpEntry 40 }

cucsFabricComputeMSlotEpSerial OBJECT-TYPE
    SYNTAX       SnmpAdminString
    MAX-ACCESS   read-only
    STATUS       current
    DESCRIPTION
        "Cisco UCS fabric:ComputeMSlotEp:serial managed object property"
    ::= { cucsFabricComputeMSlotEpEntry 41 }

cucsFabricComputeMSlotEpServerInstanceId OBJECT-TYPE
    SYNTAX       CucsFabricComputeMSlotEpServerInstanceId
    MAX-ACCESS   read-only
    STATUS       current
    DESCRIPTION
        "Cisco UCS fabric:ComputeMSlotEp:serverInstanceId
        managed object property"
    ::= { cucsFabricComputeMSlotEpEntry 42 }

cucsFabricComputeMSlotEpSlotAdminState OBJECT-TYPE
    SYNTAX       CucsFabricSlotAdminState
    MAX-ACCESS   read-only
    STATUS       current
    DESCRIPTION
        "Cisco UCS fabric:ComputeMSlotEp:slotAdminState
        managed object property"
    ::= { cucsFabricComputeMSlotEpEntry 43 }

cucsFabricComputeMSlotEpSlotId OBJECT-TYPE
    SYNTAX       CucsFabricComputeMSlotEpSlotId
    MAX-ACCESS   read-only
    STATUS       current
    DESCRIPTION
        "Cisco UCS fabric:ComputeMSlotEp:slotId managed object property"
    ::= { cucsFabricComputeMSlotEpEntry 44 }

cucsFabricComputeMSlotEpSwitchId OBJECT-TYPE
    SYNTAX       CucsNetworkSwitchId
    MAX-ACCESS   read-only
    STATUS       current
    DESCRIPTION
        "Cisco UCS fabric:ComputeMSlotEp:switchId managed object property"
    ::= { cucsFabricComputeMSlotEpEntry 45 }

cucsFabricComputeMSlotEpTransport OBJECT-TYPE
    SYNTAX       CucsNetworkTransport
    MAX-ACCESS   read-only
    STATUS       current
    DESCRIPTION
        "Cisco UCS fabric:ComputeMSlotEp:transport managed
        object property"
    ::= { cucsFabricComputeMSlotEpEntry 46 }

cucsFabricComputeMSlotEpType OBJECT-TYPE
    SYNTAX       CucsFabricComputeEpType
    MAX-ACCESS   read-only
    STATUS       current
    DESCRIPTION
        "Cisco UCS fabric:ComputeMSlotEp:type managed object property"
    ::= { cucsFabricComputeMSlotEpEntry 47 }

cucsFabricComputeMSlotEpVendor OBJECT-TYPE
    SYNTAX       SnmpAdminString
    MAX-ACCESS   read-only
    STATUS       current
    DESCRIPTION
        "Cisco UCS fabric:ComputeMSlotEp:vendor managed object property"
    ::= { cucsFabricComputeMSlotEpEntry 48 }

cucsFabricComputeMSlotEpAggrPortId OBJECT-TYPE
    SYNTAX       Gauge32
    MAX-ACCESS   read-only
    STATUS       current
    DESCRIPTION
        "Cisco UCS fabric:ComputeMSlotEp:aggrPortId managed
        object property"
    ::= { cucsFabricComputeMSlotEpEntry 49 }

cucsFabricComputeMSlotEpAutoNegotiate OBJECT-TYPE
    SYNTAX       TruthValue
    MAX-ACCESS   read-only
    STATUS       current
    DESCRIPTION
        "Cisco UCS fabric:ComputeMSlotEp:autoNegotiate
        managed object property"
    ::= { cucsFabricComputeMSlotEpEntry 50 }

cucsFabricComputeMSlotEpPeerAggrPortId OBJECT-TYPE
    SYNTAX       Gauge32
    MAX-ACCESS   read-only
    STATUS       current
    DESCRIPTION
        "Cisco UCS fabric:ComputeMSlotEp:peerAggrPortId
        managed object property"
    ::= { cucsFabricComputeMSlotEpEntry 51 }

cucsFabricComputeMSlotEpFsmTable OBJECT-TYPE
    SYNTAX           SEQUENCE OF CucsFabricComputeMSlotEpFsmEntry
    MAX-ACCESS       not-accessible
    STATUS           current
    DESCRIPTION
        "Cisco UCS fabric:ComputeMSlotEpFsm managed object table"
    ::= { cucsFabricObjects 132 }

cucsFabricComputeMSlotEpFsmEntry OBJECT-TYPE
    SYNTAX           CucsFabricComputeMSlotEpFsmEntry
    MAX-ACCESS       not-accessible
    STATUS           current
    DESCRIPTION
        "Entry for the cucsFabricComputeMSlotEpFsmTable table."
    INDEX { cucsFabricComputeMSlotEpFsmInstanceId }
    ::= { cucsFabricComputeMSlotEpFsmTable 1 }

CucsFabricComputeMSlotEpFsmEntry ::= SEQUENCE {
    cucsFabricComputeMSlotEpFsmInstanceId                            CucsManagedObjectId,
    cucsFabricComputeMSlotEpFsmDn                                    CucsManagedObjectDn,
    cucsFabricComputeMSlotEpFsmRn                                    SnmpAdminString,
    cucsFabricComputeMSlotEpFsmCompletionTime                        DateAndTime,
    cucsFabricComputeMSlotEpFsmCurrentFsm                            CucsFabricComputeMSlotEpFsmCurrentFsm,
    cucsFabricComputeMSlotEpFsmDescrData                             SnmpAdminString,
    cucsFabricComputeMSlotEpFsmFsmStatus                             CucsFsmFsmStageStatus,
    cucsFabricComputeMSlotEpFsmProgress                              Gauge32,
    cucsFabricComputeMSlotEpFsmRmtErrCode                            Gauge32,
    cucsFabricComputeMSlotEpFsmRmtErrDescr                           SnmpAdminString,
    cucsFabricComputeMSlotEpFsmRmtRslt                               CucsConditionRemoteInvRslt
}

cucsFabricComputeMSlotEpFsmInstanceId OBJECT-TYPE
    SYNTAX       CucsManagedObjectId
    MAX-ACCESS   not-accessible
    STATUS       current
    DESCRIPTION
        "Instance identifier of the managed object."
    ::= { cucsFabricComputeMSlotEpFsmEntry 1 }

cucsFabricComputeMSlotEpFsmDn OBJECT-TYPE
    SYNTAX       CucsManagedObjectDn
    MAX-ACCESS   read-only
    STATUS       current
    DESCRIPTION
        "Cisco UCS fabric:ComputeMSlotEpFsm:dn managed object property"
    ::= { cucsFabricComputeMSlotEpFsmEntry 2 }

cucsFabricComputeMSlotEpFsmRn OBJECT-TYPE
    SYNTAX       SnmpAdminString
    MAX-ACCESS   read-only
    STATUS       current
    DESCRIPTION
        "Cisco UCS fabric:ComputeMSlotEpFsm:rn managed object property"
    ::= { cucsFabricComputeMSlotEpFsmEntry 3 }

cucsFabricComputeMSlotEpFsmCompletionTime OBJECT-TYPE
    SYNTAX       DateAndTime
    MAX-ACCESS   read-only
    STATUS       current
    DESCRIPTION
        "Cisco UCS fabric:ComputeMSlotEpFsm:completionTime
        managed object property"
    ::= { cucsFabricComputeMSlotEpFsmEntry 4 }

cucsFabricComputeMSlotEpFsmCurrentFsm OBJECT-TYPE
    SYNTAX       CucsFabricComputeMSlotEpFsmCurrentFsm
    MAX-ACCESS   read-only
    STATUS       current
    DESCRIPTION
        "Cisco UCS fabric:ComputeMSlotEpFsm:currentFsm
        managed object property"
    ::= { cucsFabricComputeMSlotEpFsmEntry 5 }

cucsFabricComputeMSlotEpFsmDescrData OBJECT-TYPE
    SYNTAX       SnmpAdminString
    MAX-ACCESS   read-only
    STATUS       current
    DESCRIPTION
        "Cisco UCS fabric:ComputeMSlotEpFsm:descr managed object property"
    ::= { cucsFabricComputeMSlotEpFsmEntry 6 }

cucsFabricComputeMSlotEpFsmFsmStatus OBJECT-TYPE
    SYNTAX       CucsFsmFsmStageStatus
    MAX-ACCESS   read-only
    STATUS       current
    DESCRIPTION
        "Cisco UCS fabric:ComputeMSlotEpFsm:fsmStatus managed
        object property"
    ::= { cucsFabricComputeMSlotEpFsmEntry 7 }

cucsFabricComputeMSlotEpFsmProgress OBJECT-TYPE
    SYNTAX       Gauge32
    MAX-ACCESS   read-only
    STATUS       current
    DESCRIPTION
        "Cisco UCS fabric:ComputeMSlotEpFsm:progress managed
        object property"
    ::= { cucsFabricComputeMSlotEpFsmEntry 8 }

cucsFabricComputeMSlotEpFsmRmtErrCode OBJECT-TYPE
    SYNTAX       Gauge32
    MAX-ACCESS   read-only
    STATUS       current
    DESCRIPTION
        "Cisco UCS fabric:ComputeMSlotEpFsm:rmtErrCode
        managed object property"
    ::= { cucsFabricComputeMSlotEpFsmEntry 9 }

cucsFabricComputeMSlotEpFsmRmtErrDescr OBJECT-TYPE
    SYNTAX       SnmpAdminString
    MAX-ACCESS   read-only
    STATUS       current
    DESCRIPTION
        "Cisco UCS fabric:ComputeMSlotEpFsm:rmtErrDescr
        managed object property"
    ::= { cucsFabricComputeMSlotEpFsmEntry 10 }

cucsFabricComputeMSlotEpFsmRmtRslt OBJECT-TYPE
    SYNTAX       CucsConditionRemoteInvRslt
    MAX-ACCESS   read-only
    STATUS       current
    DESCRIPTION
        "Cisco UCS fabric:ComputeMSlotEpFsm:rmtRslt managed
        object property"
    ::= { cucsFabricComputeMSlotEpFsmEntry 11 }

cucsFabricComputeMSlotEpFsmStageTable OBJECT-TYPE
    SYNTAX           SEQUENCE OF CucsFabricComputeMSlotEpFsmStageEntry
    MAX-ACCESS       not-accessible
    STATUS           current
    DESCRIPTION
        "Cisco UCS fabric:ComputeMSlotEpFsmStage managed object table"
    ::= { cucsFabricObjects 133 }

cucsFabricComputeMSlotEpFsmStageEntry OBJECT-TYPE
    SYNTAX           CucsFabricComputeMSlotEpFsmStageEntry
    MAX-ACCESS       not-accessible
    STATUS           current
    DESCRIPTION
        "Entry for the cucsFabricComputeMSlotEpFsmStageTable table."
    INDEX { cucsFabricComputeMSlotEpFsmStageInstanceId }
    ::= { cucsFabricComputeMSlotEpFsmStageTable 1 }

CucsFabricComputeMSlotEpFsmStageEntry ::= SEQUENCE {
    cucsFabricComputeMSlotEpFsmStageInstanceId                       CucsManagedObjectId,
    cucsFabricComputeMSlotEpFsmStageDn                               CucsManagedObjectDn,
    cucsFabricComputeMSlotEpFsmStageRn                               SnmpAdminString,
    cucsFabricComputeMSlotEpFsmStageDescrData                        SnmpAdminString,
    cucsFabricComputeMSlotEpFsmStageLastUpdateTime                   DateAndTime,
    cucsFabricComputeMSlotEpFsmStageName                             CucsFabricComputeMSlotEpFsmStageName,
    cucsFabricComputeMSlotEpFsmStageOrder                            Gauge32,
    cucsFabricComputeMSlotEpFsmStageRetry                            Gauge32,
    cucsFabricComputeMSlotEpFsmStageStageStatus                      CucsFsmFsmStageStatus
}

cucsFabricComputeMSlotEpFsmStageInstanceId OBJECT-TYPE
    SYNTAX       CucsManagedObjectId
    MAX-ACCESS   not-accessible
    STATUS       current
    DESCRIPTION
        "Instance identifier of the managed object."
    ::= { cucsFabricComputeMSlotEpFsmStageEntry 1 }

cucsFabricComputeMSlotEpFsmStageDn OBJECT-TYPE
    SYNTAX       CucsManagedObjectDn
    MAX-ACCESS   read-only
    STATUS       current
    DESCRIPTION
        "Cisco UCS fabric:ComputeMSlotEpFsmStage:dn managed
        object property"
    ::= { cucsFabricComputeMSlotEpFsmStageEntry 2 }

cucsFabricComputeMSlotEpFsmStageRn OBJECT-TYPE
    SYNTAX       SnmpAdminString
    MAX-ACCESS   read-only
    STATUS       current
    DESCRIPTION
        "Cisco UCS fabric:ComputeMSlotEpFsmStage:rn managed
        object property"
    ::= { cucsFabricComputeMSlotEpFsmStageEntry 3 }

cucsFabricComputeMSlotEpFsmStageDescrData OBJECT-TYPE
    SYNTAX       SnmpAdminString
    MAX-ACCESS   read-only
    STATUS       current
    DESCRIPTION
        "Cisco UCS fabric:ComputeMSlotEpFsmStage:descr
        managed object property"
    ::= { cucsFabricComputeMSlotEpFsmStageEntry 4 }

cucsFabricComputeMSlotEpFsmStageLastUpdateTime OBJECT-TYPE
    SYNTAX       DateAndTime
    MAX-ACCESS   read-only
    STATUS       current
    DESCRIPTION
        "Cisco UCS fabric:ComputeMSlotEpFsmStage:lastUpdateTime
        managed object property"
    ::= { cucsFabricComputeMSlotEpFsmStageEntry 5 }

cucsFabricComputeMSlotEpFsmStageName OBJECT-TYPE
    SYNTAX       CucsFabricComputeMSlotEpFsmStageName
    MAX-ACCESS   read-only
    STATUS       current
    DESCRIPTION
        "Cisco UCS fabric:ComputeMSlotEpFsmStage:name managed
        object property"
    ::= { cucsFabricComputeMSlotEpFsmStageEntry 6 }

cucsFabricComputeMSlotEpFsmStageOrder OBJECT-TYPE
    SYNTAX       Gauge32
    MAX-ACCESS   read-only
    STATUS       current
    DESCRIPTION
        "Cisco UCS fabric:ComputeMSlotEpFsmStage:order
        managed object property"
    ::= { cucsFabricComputeMSlotEpFsmStageEntry 7 }

cucsFabricComputeMSlotEpFsmStageRetry OBJECT-TYPE
    SYNTAX       Gauge32
    MAX-ACCESS   read-only
    STATUS       current
    DESCRIPTION
        "Cisco UCS fabric:ComputeMSlotEpFsmStage:retry
        managed object property"
    ::= { cucsFabricComputeMSlotEpFsmStageEntry 8 }

cucsFabricComputeMSlotEpFsmStageStageStatus OBJECT-TYPE
    SYNTAX       CucsFsmFsmStageStatus
    MAX-ACCESS   read-only
    STATUS       current
    DESCRIPTION
        "Cisco UCS fabric:ComputeMSlotEpFsmStage:stageStatus
        managed object property"
    ::= { cucsFabricComputeMSlotEpFsmStageEntry 9 }

cucsFabricComputeMSlotEpFsmTaskTable OBJECT-TYPE
    SYNTAX           SEQUENCE OF CucsFabricComputeMSlotEpFsmTaskEntry
    MAX-ACCESS       not-accessible
    STATUS           current
    DESCRIPTION
        "Cisco UCS fabric:ComputeMSlotEpFsmTask managed object table"
    ::= { cucsFabricObjects 134 }

cucsFabricComputeMSlotEpFsmTaskEntry OBJECT-TYPE
    SYNTAX           CucsFabricComputeMSlotEpFsmTaskEntry
    MAX-ACCESS       not-accessible
    STATUS           current
    DESCRIPTION
        "Entry for the cucsFabricComputeMSlotEpFsmTaskTable table."
    INDEX { cucsFabricComputeMSlotEpFsmTaskInstanceId }
    ::= { cucsFabricComputeMSlotEpFsmTaskTable 1 }

CucsFabricComputeMSlotEpFsmTaskEntry ::= SEQUENCE {
    cucsFabricComputeMSlotEpFsmTaskInstanceId                        CucsManagedObjectId,
    cucsFabricComputeMSlotEpFsmTaskDn                                CucsManagedObjectDn,
    cucsFabricComputeMSlotEpFsmTaskRn                                SnmpAdminString,
    cucsFabricComputeMSlotEpFsmTaskCompletion                        CucsFsmCompletion,
    cucsFabricComputeMSlotEpFsmTaskFlags                             CucsFsmFlags,
    cucsFabricComputeMSlotEpFsmTaskItem                              CucsFabricComputeMSlotEpFsmTaskItem,
    cucsFabricComputeMSlotEpFsmTaskSeqId                             Gauge32
}

cucsFabricComputeMSlotEpFsmTaskInstanceId OBJECT-TYPE
    SYNTAX       CucsManagedObjectId
    MAX-ACCESS   not-accessible
    STATUS       current
    DESCRIPTION
        "Instance identifier of the managed object."
    ::= { cucsFabricComputeMSlotEpFsmTaskEntry 1 }

cucsFabricComputeMSlotEpFsmTaskDn OBJECT-TYPE
    SYNTAX       CucsManagedObjectDn
    MAX-ACCESS   read-only
    STATUS       current
    DESCRIPTION
        "Cisco UCS fabric:ComputeMSlotEpFsmTask:dn managed
        object property"
    ::= { cucsFabricComputeMSlotEpFsmTaskEntry 2 }

cucsFabricComputeMSlotEpFsmTaskRn OBJECT-TYPE
    SYNTAX       SnmpAdminString
    MAX-ACCESS   read-only
    STATUS       current
    DESCRIPTION
        "Cisco UCS fabric:ComputeMSlotEpFsmTask:rn managed
        object property"
    ::= { cucsFabricComputeMSlotEpFsmTaskEntry 3 }

cucsFabricComputeMSlotEpFsmTaskCompletion OBJECT-TYPE
    SYNTAX       CucsFsmCompletion
    MAX-ACCESS   read-only
    STATUS       current
    DESCRIPTION
        "Cisco UCS fabric:ComputeMSlotEpFsmTask:completion
        managed object property"
    ::= { cucsFabricComputeMSlotEpFsmTaskEntry 4 }

cucsFabricComputeMSlotEpFsmTaskFlags OBJECT-TYPE
    SYNTAX       CucsFsmFlags
    MAX-ACCESS   read-only
    STATUS       current
    DESCRIPTION
        "Cisco UCS fabric:ComputeMSlotEpFsmTask:flags managed
        object property"
    ::= { cucsFabricComputeMSlotEpFsmTaskEntry 5 }

cucsFabricComputeMSlotEpFsmTaskItem OBJECT-TYPE
    SYNTAX       CucsFabricComputeMSlotEpFsmTaskItem
    MAX-ACCESS   read-only
    STATUS       current
    DESCRIPTION
        "Cisco UCS fabric:ComputeMSlotEpFsmTask:item managed
        object property"
    ::= { cucsFabricComputeMSlotEpFsmTaskEntry 6 }

cucsFabricComputeMSlotEpFsmTaskSeqId OBJECT-TYPE
    SYNTAX       Gauge32
    MAX-ACCESS   read-only
    STATUS       current
    DESCRIPTION
        "Cisco UCS fabric:ComputeMSlotEpFsmTask:seqId managed
        object property"
    ::= { cucsFabricComputeMSlotEpFsmTaskEntry 7 }

cucsFabricComputePhEpTable OBJECT-TYPE
    SYNTAX           SEQUENCE OF CucsFabricComputePhEpEntry
    MAX-ACCESS       not-accessible
    STATUS           current
    DESCRIPTION
        "Cisco UCS fabric:ComputePhEp managed object table"
    ::= { cucsFabricObjects 2 }

cucsFabricComputePhEpEntry OBJECT-TYPE
    SYNTAX           CucsFabricComputePhEpEntry
    MAX-ACCESS       not-accessible
    STATUS           current
    DESCRIPTION
        "Entry for the cucsFabricComputePhEpTable table."
    INDEX { cucsFabricComputePhEpInstanceId }
    ::= { cucsFabricComputePhEpTable 1 }

CucsFabricComputePhEpEntry ::= SEQUENCE {
    cucsFabricComputePhEpInstanceId                                  CucsManagedObjectId,
    cucsFabricComputePhEpDn                                          CucsManagedObjectDn,
    cucsFabricComputePhEpRn                                          SnmpAdminString,
    cucsFabricComputePhEpAdminState                                  CucsFabricComputePhEpAdminState,
    cucsFabricComputePhEpChassisId                                   Gauge32,
    cucsFabricComputePhEpEpDn                                        SnmpAdminString,
    cucsFabricComputePhEpEqType                                      CucsEquipmentFabricEpType,
    cucsFabricComputePhEpIfRole                                      CucsFabricComputeEpIfRole,
    cucsFabricComputePhEpIfType                                      CucsFabricPIoEpIfType,
    cucsFabricComputePhEpLc                                          CucsFabricBladeLifeCycle,
    cucsFabricComputePhEpLicGP                                       Unsigned64,
    cucsFabricComputePhEpLicState                                    CucsLicenseState,
    cucsFabricComputePhEpLocale                                      CucsFabricInternalEpLocale,
    cucsFabricComputePhEpModel                                       SnmpAdminString,
    cucsFabricComputePhEpName                                        SnmpAdminString,
    cucsFabricComputePhEpPeerDn                                      SnmpAdminString,
    cucsFabricComputePhEpPeerPortId                                  Gauge32,
    cucsFabricComputePhEpPeerSlotId                                  Gauge32,
    cucsFabricComputePhEpPortId                                      CucsFabricPIoEpPortId,
    cucsFabricComputePhEpProfileDn                                   SnmpAdminString,
    cucsFabricComputePhEpRevision                                    SnmpAdminString,
    cucsFabricComputePhEpSerial                                      SnmpAdminString,
    cucsFabricComputePhEpSlotId                                      CucsFabricPIoEpSlotId,
    cucsFabricComputePhEpSwitchId                                    CucsNetworkSwitchId,
    cucsFabricComputePhEpTransport                                   CucsNetworkTransport,
    cucsFabricComputePhEpType                                        CucsFabricComputeEpType,
    cucsFabricComputePhEpVendor                                      SnmpAdminString,
    cucsFabricComputePhEpPeerChassisId                               Gauge32,
    cucsFabricComputePhEpCheckpointTrigTs                            Unsigned64,
    cucsFabricComputePhEpDeepCheckpointTrigTs                        Unsigned64,
    cucsFabricComputePhEpDiscTrigTs                                  Unsigned64,
    cucsFabricComputePhEpFltAggr                                     Unsigned64,
    cucsFabricComputePhEpOperState                                   CucsFabricPIoEpOperState,
    cucsFabricComputePhEpOperStateReason                             SnmpAdminString,
    cucsFabricComputePhEpBoardAggregationRole                        CucsEquipmentBoardAggregationRole,
    cucsFabricComputePhEpAggrPortId                                  Gauge32,
    cucsFabricComputePhEpPeerAggrPortId                              Gauge32,
    cucsFabricComputePhEpAutoNegotiate                               TruthValue
}

cucsFabricComputePhEpInstanceId OBJECT-TYPE
    SYNTAX       CucsManagedObjectId
    MAX-ACCESS   not-accessible
    STATUS       current
    DESCRIPTION
        "Instance identifier of the managed object."
    ::= { cucsFabricComputePhEpEntry 1 }

cucsFabricComputePhEpDn OBJECT-TYPE
    SYNTAX       CucsManagedObjectDn
    MAX-ACCESS   read-only
    STATUS       current
    DESCRIPTION
        "Cisco UCS fabric:ComputePhEp:dn managed object property"
    ::= { cucsFabricComputePhEpEntry 2 }

cucsFabricComputePhEpRn OBJECT-TYPE
    SYNTAX       SnmpAdminString
    MAX-ACCESS   read-only
    STATUS       current
    DESCRIPTION
        "Cisco UCS fabric:ComputePhEp:rn managed object property"
    ::= { cucsFabricComputePhEpEntry 3 }

cucsFabricComputePhEpAdminState OBJECT-TYPE
    SYNTAX       CucsFabricComputePhEpAdminState
    MAX-ACCESS   read-only
    STATUS       current
    DESCRIPTION
        "Cisco UCS fabric:ComputePhEp:adminState managed object property"
    ::= { cucsFabricComputePhEpEntry 4 }

cucsFabricComputePhEpChassisId OBJECT-TYPE
    SYNTAX       Gauge32
    MAX-ACCESS   read-only
    STATUS       current
    DESCRIPTION
        "Cisco UCS fabric:ComputePhEp:chassisId managed object property"
    ::= { cucsFabricComputePhEpEntry 5 }

cucsFabricComputePhEpEpDn OBJECT-TYPE
    SYNTAX       SnmpAdminString
    MAX-ACCESS   read-only
    STATUS       current
    DESCRIPTION
        "Cisco UCS fabric:ComputePhEp:epDn managed object property"
    ::= { cucsFabricComputePhEpEntry 6 }

cucsFabricComputePhEpEqType OBJECT-TYPE
    SYNTAX       CucsEquipmentFabricEpType
    MAX-ACCESS   read-only
    STATUS       current
    DESCRIPTION
        "Cisco UCS fabric:ComputePhEp:eqType managed object property"
    ::= { cucsFabricComputePhEpEntry 7 }

cucsFabricComputePhEpIfRole OBJECT-TYPE
    SYNTAX       CucsFabricComputeEpIfRole
    MAX-ACCESS   read-only
    STATUS       current
    DESCRIPTION
        "Cisco UCS fabric:ComputePhEp:ifRole managed object property"
    ::= { cucsFabricComputePhEpEntry 8 }

cucsFabricComputePhEpIfType OBJECT-TYPE
    SYNTAX       CucsFabricPIoEpIfType
    MAX-ACCESS   read-only
    STATUS       current
    DESCRIPTION
        "Cisco UCS fabric:ComputePhEp:ifType managed object property"
    ::= { cucsFabricComputePhEpEntry 9 }

cucsFabricComputePhEpLc OBJECT-TYPE
    SYNTAX       CucsFabricBladeLifeCycle
    MAX-ACCESS   read-only
    STATUS       current
    DESCRIPTION
        "Cisco UCS fabric:ComputePhEp:lc managed object property"
    ::= { cucsFabricComputePhEpEntry 10 }

cucsFabricComputePhEpLicGP OBJECT-TYPE
    SYNTAX       Unsigned64
    MAX-ACCESS   read-only
    STATUS       current
    DESCRIPTION
        "Cisco UCS fabric:ComputePhEp:licGP managed object property"
    ::= { cucsFabricComputePhEpEntry 11 }

cucsFabricComputePhEpLicState OBJECT-TYPE
    SYNTAX       CucsLicenseState
    MAX-ACCESS   read-only
    STATUS       current
    DESCRIPTION
        "Cisco UCS fabric:ComputePhEp:licState managed object property"
    ::= { cucsFabricComputePhEpEntry 12 }

cucsFabricComputePhEpLocale OBJECT-TYPE
    SYNTAX       CucsFabricInternalEpLocale
    MAX-ACCESS   read-only
    STATUS       current
    DESCRIPTION
        "Cisco UCS fabric:ComputePhEp:locale managed object property"
    ::= { cucsFabricComputePhEpEntry 13 }

cucsFabricComputePhEpModel OBJECT-TYPE
    SYNTAX       SnmpAdminString
    MAX-ACCESS   read-only
    STATUS       current
    DESCRIPTION
        "Cisco UCS fabric:ComputePhEp:model managed object property"
    ::= { cucsFabricComputePhEpEntry 14 }

cucsFabricComputePhEpName OBJECT-TYPE
    SYNTAX       SnmpAdminString
    MAX-ACCESS   read-only
    STATUS       current
    DESCRIPTION
        "Cisco UCS fabric:ComputePhEp:name managed object property"
    ::= { cucsFabricComputePhEpEntry 15 }

cucsFabricComputePhEpPeerDn OBJECT-TYPE
    SYNTAX       SnmpAdminString
    MAX-ACCESS   read-only
    STATUS       current
    DESCRIPTION
        "Cisco UCS fabric:ComputePhEp:peerDn managed object property"
    ::= { cucsFabricComputePhEpEntry 16 }

cucsFabricComputePhEpPeerPortId OBJECT-TYPE
    SYNTAX       Gauge32
    MAX-ACCESS   read-only
    STATUS       current
    DESCRIPTION
        "Cisco UCS fabric:ComputePhEp:peerPortId managed object property"
    ::= { cucsFabricComputePhEpEntry 17 }

cucsFabricComputePhEpPeerSlotId OBJECT-TYPE
    SYNTAX       Gauge32
    MAX-ACCESS   read-only
    STATUS       current
    DESCRIPTION
        "Cisco UCS fabric:ComputePhEp:peerSlotId managed object property"
    ::= { cucsFabricComputePhEpEntry 18 }

cucsFabricComputePhEpPortId OBJECT-TYPE
    SYNTAX       CucsFabricPIoEpPortId
    MAX-ACCESS   read-only
    STATUS       current
    DESCRIPTION
        "Cisco UCS fabric:ComputePhEp:portId managed object property"
    ::= { cucsFabricComputePhEpEntry 19 }

cucsFabricComputePhEpProfileDn OBJECT-TYPE
    SYNTAX       SnmpAdminString
    MAX-ACCESS   read-only
    STATUS       current
    DESCRIPTION
        "Cisco UCS fabric:ComputePhEp:profileDn managed object property"
    ::= { cucsFabricComputePhEpEntry 20 }

cucsFabricComputePhEpRevision OBJECT-TYPE
    SYNTAX       SnmpAdminString
    MAX-ACCESS   read-only
    STATUS       current
    DESCRIPTION
        "Cisco UCS fabric:ComputePhEp:revision managed object property"
    ::= { cucsFabricComputePhEpEntry 21 }

cucsFabricComputePhEpSerial OBJECT-TYPE
    SYNTAX       SnmpAdminString
    MAX-ACCESS   read-only
    STATUS       current
    DESCRIPTION
        "Cisco UCS fabric:ComputePhEp:serial managed object property"
    ::= { cucsFabricComputePhEpEntry 22 }

cucsFabricComputePhEpSlotId OBJECT-TYPE
    SYNTAX       CucsFabricPIoEpSlotId
    MAX-ACCESS   read-only
    STATUS       current
    DESCRIPTION
        "Cisco UCS fabric:ComputePhEp:slotId managed object property"
    ::= { cucsFabricComputePhEpEntry 23 }

cucsFabricComputePhEpSwitchId OBJECT-TYPE
    SYNTAX       CucsNetworkSwitchId
    MAX-ACCESS   read-only
    STATUS       current
    DESCRIPTION
        "Cisco UCS fabric:ComputePhEp:switchId managed object property"
    ::= { cucsFabricComputePhEpEntry 24 }

cucsFabricComputePhEpTransport OBJECT-TYPE
    SYNTAX       CucsNetworkTransport
    MAX-ACCESS   read-only
    STATUS       current
    DESCRIPTION
        "Cisco UCS fabric:ComputePhEp:transport managed object property"
    ::= { cucsFabricComputePhEpEntry 25 }

cucsFabricComputePhEpType OBJECT-TYPE
    SYNTAX       CucsFabricComputeEpType
    MAX-ACCESS   read-only
    STATUS       current
    DESCRIPTION
        "Cisco UCS fabric:ComputePhEp:type managed object property"
    ::= { cucsFabricComputePhEpEntry 26 }

cucsFabricComputePhEpVendor OBJECT-TYPE
    SYNTAX       SnmpAdminString
    MAX-ACCESS   read-only
    STATUS       current
    DESCRIPTION
        "Cisco UCS fabric:ComputePhEp:vendor managed object property"
    ::= { cucsFabricComputePhEpEntry 27 }

cucsFabricComputePhEpPeerChassisId OBJECT-TYPE
    SYNTAX       Gauge32
    MAX-ACCESS   read-only
    STATUS       current
    DESCRIPTION
        "Cisco UCS fabric:ComputePhEp:peerChassisId managed
        object property"
    ::= { cucsFabricComputePhEpEntry 28 }

cucsFabricComputePhEpCheckpointTrigTs OBJECT-TYPE
    SYNTAX       Unsigned64
    MAX-ACCESS   read-only
    STATUS       current
    DESCRIPTION
        "Cisco UCS fabric:ComputePhEp:checkpointTrigTs
        managed object property"
    ::= { cucsFabricComputePhEpEntry 29 }

cucsFabricComputePhEpDeepCheckpointTrigTs OBJECT-TYPE
    SYNTAX       Unsigned64
    MAX-ACCESS   read-only
    STATUS       current
    DESCRIPTION
        "Cisco UCS fabric:ComputePhEp:deepCheckpointTrigTs
        managed object property"
    ::= { cucsFabricComputePhEpEntry 30 }

cucsFabricComputePhEpDiscTrigTs OBJECT-TYPE
    SYNTAX       Unsigned64
    MAX-ACCESS   read-only
    STATUS       current
    DESCRIPTION
        "Cisco UCS fabric:ComputePhEp:discTrigTs managed object property"
    ::= { cucsFabricComputePhEpEntry 31 }

cucsFabricComputePhEpFltAggr OBJECT-TYPE
    SYNTAX       Unsigned64
    MAX-ACCESS   read-only
    STATUS       current
    DESCRIPTION
        "Cisco UCS fabric:ComputePhEp:fltAggr managed object property"
    ::= { cucsFabricComputePhEpEntry 32 }

cucsFabricComputePhEpOperState OBJECT-TYPE
    SYNTAX       CucsFabricPIoEpOperState
    MAX-ACCESS   read-only
    STATUS       current
    DESCRIPTION
        "Cisco UCS fabric:ComputePhEp:operState managed object property"
    ::= { cucsFabricComputePhEpEntry 33 }

cucsFabricComputePhEpOperStateReason OBJECT-TYPE
    SYNTAX       SnmpAdminString
    MAX-ACCESS   read-only
    STATUS       current
    DESCRIPTION
        "Cisco UCS fabric:ComputePhEp:operStateReason managed
        object property"
    ::= { cucsFabricComputePhEpEntry 34 }

cucsFabricComputePhEpBoardAggregationRole OBJECT-TYPE
    SYNTAX       CucsEquipmentBoardAggregationRole
    MAX-ACCESS   read-only
    STATUS       current
    DESCRIPTION
        "Cisco UCS fabric:ComputePhEp:boardAggregationRole
        managed object property"
    ::= { cucsFabricComputePhEpEntry 35 }

cucsFabricComputePhEpAggrPortId OBJECT-TYPE
    SYNTAX       Gauge32
    MAX-ACCESS   read-only
    STATUS       current
    DESCRIPTION
        "Cisco UCS fabric:ComputePhEp:aggrPortId managed object property"
    ::= { cucsFabricComputePhEpEntry 36 }

cucsFabricComputePhEpPeerAggrPortId OBJECT-TYPE
    SYNTAX       Gauge32
    MAX-ACCESS   read-only
    STATUS       current
    DESCRIPTION
        "Cisco UCS fabric:ComputePhEp:peerAggrPortId managed
        object property"
    ::= { cucsFabricComputePhEpEntry 37 }

cucsFabricComputePhEpAutoNegotiate OBJECT-TYPE
    SYNTAX       TruthValue
    MAX-ACCESS   read-only
    STATUS       current
    DESCRIPTION
        "Cisco UCS fabric:ComputePhEp:autoNegotiate managed
        object property"
    ::= { cucsFabricComputePhEpEntry 39 }

cucsFabricComputeSlotEpTable OBJECT-TYPE
    SYNTAX           SEQUENCE OF CucsFabricComputeSlotEpEntry
    MAX-ACCESS       not-accessible
    STATUS           current
    DESCRIPTION
        "Cisco UCS fabric:ComputeSlotEp managed object table"
    ::= { cucsFabricObjects 3 }

cucsFabricComputeSlotEpEntry OBJECT-TYPE
    SYNTAX           CucsFabricComputeSlotEpEntry
    MAX-ACCESS       not-accessible
    STATUS           current
    DESCRIPTION
        "Entry for the cucsFabricComputeSlotEpTable table."
    INDEX { cucsFabricComputeSlotEpInstanceId }
    ::= { cucsFabricComputeSlotEpTable 1 }

CucsFabricComputeSlotEpEntry ::= SEQUENCE {
    cucsFabricComputeSlotEpInstanceId                                CucsManagedObjectId,
    cucsFabricComputeSlotEpDn                                        CucsManagedObjectDn,
    cucsFabricComputeSlotEpRn                                        SnmpAdminString,
    cucsFabricComputeSlotEpAdminState                                CucsFabricSlotAdminState,
    cucsFabricComputeSlotEpChassisId                                 Gauge32,
    cucsFabricComputeSlotEpConnPath                                  CucsEquipmentConnectionStatus,
    cucsFabricComputeSlotEpConnStatus                                CucsEquipmentConnectionStatus,
    cucsFabricComputeSlotEpDiscovery                                 CucsComputeDiscovery,
    cucsFabricComputeSlotEpEpDn                                      SnmpAdminString,
    cucsFabricComputeSlotEpFltAggr                                   Unsigned64,
    cucsFabricComputeSlotEpFsmDescr                                  SnmpAdminString,
    cucsFabricComputeSlotEpFsmPrev                                   SnmpAdminString,
    cucsFabricComputeSlotEpFsmProgr                                  Gauge32,
    cucsFabricComputeSlotEpFsmRmtInvErrCode                          Gauge32,
    cucsFabricComputeSlotEpFsmRmtInvErrDescr                         SnmpAdminString,
    cucsFabricComputeSlotEpFsmRmtInvRslt                             CucsConditionRemoteInvRslt,
    cucsFabricComputeSlotEpFsmStageDescr                             SnmpAdminString,
    cucsFabricComputeSlotEpFsmStamp                                  DateAndTime,
    cucsFabricComputeSlotEpFsmStatus                                 SnmpAdminString,
    cucsFabricComputeSlotEpFsmTry                                    Gauge32,
    cucsFabricComputeSlotEpIfRole                                    CucsFabricComputeEpIfRole,
    cucsFabricComputeSlotEpIfType                                    CucsFabricPIoEpIfType,
    cucsFabricComputeSlotEpLcTs                                      DateAndTime,
    cucsFabricComputeSlotEpLicGP                                     Unsigned64,
    cucsFabricComputeSlotEpLicState                                  CucsLicenseState,
    cucsFabricComputeSlotEpLocale                                    CucsFabricInternalEpLocale,
    cucsFabricComputeSlotEpManagingInst                              CucsNetworkSwitchId,
    cucsFabricComputeSlotEpModel                                     SnmpAdminString,
    cucsFabricComputeSlotEpName                                      SnmpAdminString,
    cucsFabricComputeSlotEpPeerDn                                    SnmpAdminString,
    cucsFabricComputeSlotEpPeerPortId                                Gauge32,
    cucsFabricComputeSlotEpPeerSlotId                                Gauge32,
    cucsFabricComputeSlotEpPortId                                    CucsFabricPIoEpPortId,
    cucsFabricComputeSlotEpPresence                                  CucsEquipmentSlotStatus,
    cucsFabricComputeSlotEpRevision                                  SnmpAdminString,
    cucsFabricComputeSlotEpSerial                                    SnmpAdminString,
    cucsFabricComputeSlotEpSlotId                                    CucsFabricComputeSlotEpSlotId,
    cucsFabricComputeSlotEpSwitchId                                  CucsNetworkSwitchId,
    cucsFabricComputeSlotEpTransport                                 CucsNetworkTransport,
    cucsFabricComputeSlotEpType                                      CucsFabricComputeEpType,
    cucsFabricComputeSlotEpVendor                                    SnmpAdminString,
    cucsFabricComputeSlotEpPeerChassisId                             Gauge32,
    cucsFabricComputeSlotEpFruIdentTrigTs                            Unsigned64,
    cucsFabricComputeSlotEpOperState                                 CucsFabricPIoEpOperState,
    cucsFabricComputeSlotEpOperStateReason                           SnmpAdminString,
    cucsFabricComputeSlotEpBoardAggregationRole                      CucsEquipmentBoardAggregationRole,
    cucsFabricComputeSlotEpPeerSlotEpDn                              SnmpAdminString,
    cucsFabricComputeSlotEpPresencePath                              CucsEquipmentConnectionStatus,
    cucsFabricComputeSlotEpAggrPortId                                Gauge32,
    cucsFabricComputeSlotEpPeerAggrPortId                            Gauge32,
    cucsFabricComputeSlotEpDiscoveryStatus                           CucsEquipmentConnectionStatus,
    cucsFabricComputeSlotEpAutoNegotiate                             TruthValue
}

cucsFabricComputeSlotEpInstanceId OBJECT-TYPE
    SYNTAX       CucsManagedObjectId
    MAX-ACCESS   not-accessible
    STATUS       current
    DESCRIPTION
        "Instance identifier of the managed object."
    ::= { cucsFabricComputeSlotEpEntry 1 }

cucsFabricComputeSlotEpDn OBJECT-TYPE
    SYNTAX       CucsManagedObjectDn
    MAX-ACCESS   read-only
    STATUS       current
    DESCRIPTION
        "Cisco UCS fabric:ComputeSlotEp:dn managed object property"
    ::= { cucsFabricComputeSlotEpEntry 2 }

cucsFabricComputeSlotEpRn OBJECT-TYPE
    SYNTAX       SnmpAdminString
    MAX-ACCESS   read-only
    STATUS       current
    DESCRIPTION
        "Cisco UCS fabric:ComputeSlotEp:rn managed object property"
    ::= { cucsFabricComputeSlotEpEntry 3 }

cucsFabricComputeSlotEpAdminState OBJECT-TYPE
    SYNTAX       CucsFabricSlotAdminState
    MAX-ACCESS   read-only
    STATUS       current
    DESCRIPTION
        "Cisco UCS fabric:ComputeSlotEp:adminState managed
        object property"
    ::= { cucsFabricComputeSlotEpEntry 4 }

cucsFabricComputeSlotEpChassisId OBJECT-TYPE
    SYNTAX       Gauge32
    MAX-ACCESS   read-only
    STATUS       current
    DESCRIPTION
        "Cisco UCS fabric:ComputeSlotEp:chassisId managed object property"
    ::= { cucsFabricComputeSlotEpEntry 5 }

cucsFabricComputeSlotEpConnPath OBJECT-TYPE
    SYNTAX       CucsEquipmentConnectionStatus
    MAX-ACCESS   read-only
    STATUS       current
    DESCRIPTION
        "Cisco UCS fabric:ComputeSlotEp:connPath managed object property"
    ::= { cucsFabricComputeSlotEpEntry 6 }

cucsFabricComputeSlotEpConnStatus OBJECT-TYPE
    SYNTAX       CucsEquipmentConnectionStatus
    MAX-ACCESS   read-only
    STATUS       current
    DESCRIPTION
        "Cisco UCS fabric:ComputeSlotEp:connStatus managed
        object property"
    ::= { cucsFabricComputeSlotEpEntry 7 }

cucsFabricComputeSlotEpDiscovery OBJECT-TYPE
    SYNTAX       CucsComputeDiscovery
    MAX-ACCESS   read-only
    STATUS       current
    DESCRIPTION
        "Cisco UCS fabric:ComputeSlotEp:discovery managed object property"
    ::= { cucsFabricComputeSlotEpEntry 8 }

cucsFabricComputeSlotEpEpDn OBJECT-TYPE
    SYNTAX       SnmpAdminString
    MAX-ACCESS   read-only
    STATUS       current
    DESCRIPTION
        "Cisco UCS fabric:ComputeSlotEp:epDn managed object property"
    ::= { cucsFabricComputeSlotEpEntry 9 }

cucsFabricComputeSlotEpFltAggr OBJECT-TYPE
    SYNTAX       Unsigned64
    MAX-ACCESS   read-only
    STATUS       current
    DESCRIPTION
        "Cisco UCS fabric:ComputeSlotEp:fltAggr managed object property"
    ::= { cucsFabricComputeSlotEpEntry 10 }

cucsFabricComputeSlotEpFsmDescr OBJECT-TYPE
    SYNTAX       SnmpAdminString
    MAX-ACCESS   read-only
    STATUS       current
    DESCRIPTION
        "Cisco UCS fabric:ComputeSlotEp:fsmDescr managed object property"
    ::= { cucsFabricComputeSlotEpEntry 11 }

cucsFabricComputeSlotEpFsmPrev OBJECT-TYPE
    SYNTAX       SnmpAdminString
    MAX-ACCESS   read-only
    STATUS       current
    DESCRIPTION
        "Cisco UCS fabric:ComputeSlotEp:fsmPrev managed object property"
    ::= { cucsFabricComputeSlotEpEntry 12 }

cucsFabricComputeSlotEpFsmProgr OBJECT-TYPE
    SYNTAX       Gauge32
    MAX-ACCESS   read-only
    STATUS       current
    DESCRIPTION
        "Cisco UCS fabric:ComputeSlotEp:fsmProgr managed object property"
    ::= { cucsFabricComputeSlotEpEntry 13 }

cucsFabricComputeSlotEpFsmRmtInvErrCode OBJECT-TYPE
    SYNTAX       Gauge32
    MAX-ACCESS   read-only
    STATUS       current
    DESCRIPTION
        "Cisco UCS fabric:ComputeSlotEp:fsmRmtInvErrCode
        managed object property"
    ::= { cucsFabricComputeSlotEpEntry 14 }

cucsFabricComputeSlotEpFsmRmtInvErrDescr OBJECT-TYPE
    SYNTAX       SnmpAdminString
    MAX-ACCESS   read-only
    STATUS       current
    DESCRIPTION
        "Cisco UCS fabric:ComputeSlotEp:fsmRmtInvErrDescr
        managed object property"
    ::= { cucsFabricComputeSlotEpEntry 15 }

cucsFabricComputeSlotEpFsmRmtInvRslt OBJECT-TYPE
    SYNTAX       CucsConditionRemoteInvRslt
    MAX-ACCESS   read-only
    STATUS       current
    DESCRIPTION
        "Cisco UCS fabric:ComputeSlotEp:fsmRmtInvRslt managed
        object property"
    ::= { cucsFabricComputeSlotEpEntry 16 }

cucsFabricComputeSlotEpFsmStageDescr OBJECT-TYPE
    SYNTAX       SnmpAdminString
    MAX-ACCESS   read-only
    STATUS       current
    DESCRIPTION
        "Cisco UCS fabric:ComputeSlotEp:fsmStageDescr managed
        object property"
    ::= { cucsFabricComputeSlotEpEntry 17 }

cucsFabricComputeSlotEpFsmStamp OBJECT-TYPE
    SYNTAX       DateAndTime
    MAX-ACCESS   read-only
    STATUS       current
    DESCRIPTION
        "Cisco UCS fabric:ComputeSlotEp:fsmStamp managed object property"
    ::= { cucsFabricComputeSlotEpEntry 18 }

cucsFabricComputeSlotEpFsmStatus OBJECT-TYPE
    SYNTAX       SnmpAdminString
    MAX-ACCESS   read-only
    STATUS       current
    DESCRIPTION
        "Cisco UCS fabric:ComputeSlotEp:fsmStatus managed object property"
    ::= { cucsFabricComputeSlotEpEntry 19 }

cucsFabricComputeSlotEpFsmTry OBJECT-TYPE
    SYNTAX       Gauge32
    MAX-ACCESS   read-only
    STATUS       current
    DESCRIPTION
        "Cisco UCS fabric:ComputeSlotEp:fsmTry managed object property"
    ::= { cucsFabricComputeSlotEpEntry 20 }

cucsFabricComputeSlotEpIfRole OBJECT-TYPE
    SYNTAX       CucsFabricComputeEpIfRole
    MAX-ACCESS   read-only
    STATUS       current
    DESCRIPTION
        "Cisco UCS fabric:ComputeSlotEp:ifRole managed object property"
    ::= { cucsFabricComputeSlotEpEntry 21 }

cucsFabricComputeSlotEpIfType OBJECT-TYPE
    SYNTAX       CucsFabricPIoEpIfType
    MAX-ACCESS   read-only
    STATUS       current
    DESCRIPTION
        "Cisco UCS fabric:ComputeSlotEp:ifType managed object property"
    ::= { cucsFabricComputeSlotEpEntry 22 }

cucsFabricComputeSlotEpLcTs OBJECT-TYPE
    SYNTAX       DateAndTime
    MAX-ACCESS   read-only
    STATUS       current
    DESCRIPTION
        "Cisco UCS fabric:ComputeSlotEp:lcTs managed object property"
    ::= { cucsFabricComputeSlotEpEntry 23 }

cucsFabricComputeSlotEpLicGP OBJECT-TYPE
    SYNTAX       Unsigned64
    MAX-ACCESS   read-only
    STATUS       current
    DESCRIPTION
        "Cisco UCS fabric:ComputeSlotEp:licGP managed object property"
    ::= { cucsFabricComputeSlotEpEntry 24 }

cucsFabricComputeSlotEpLicState OBJECT-TYPE
    SYNTAX       CucsLicenseState
    MAX-ACCESS   read-only
    STATUS       current
    DESCRIPTION
        "Cisco UCS fabric:ComputeSlotEp:licState managed object property"
    ::= { cucsFabricComputeSlotEpEntry 25 }

cucsFabricComputeSlotEpLocale OBJECT-TYPE
    SYNTAX       CucsFabricInternalEpLocale
    MAX-ACCESS   read-only
    STATUS       current
    DESCRIPTION
        "Cisco UCS fabric:ComputeSlotEp:locale managed object property"
    ::= { cucsFabricComputeSlotEpEntry 26 }

cucsFabricComputeSlotEpManagingInst OBJECT-TYPE
    SYNTAX       CucsNetworkSwitchId
    MAX-ACCESS   read-only
    STATUS       current
    DESCRIPTION
        "Cisco UCS fabric:ComputeSlotEp:managingInst managed
        object property"
    ::= { cucsFabricComputeSlotEpEntry 27 }

cucsFabricComputeSlotEpModel OBJECT-TYPE
    SYNTAX       SnmpAdminString
    MAX-ACCESS   read-only
    STATUS       current
    DESCRIPTION
        "Cisco UCS fabric:ComputeSlotEp:model managed object property"
    ::= { cucsFabricComputeSlotEpEntry 28 }

cucsFabricComputeSlotEpName OBJECT-TYPE
    SYNTAX       SnmpAdminString
    MAX-ACCESS   read-only
    STATUS       current
    DESCRIPTION
        "Cisco UCS fabric:ComputeSlotEp:name managed object property"
    ::= { cucsFabricComputeSlotEpEntry 29 }

cucsFabricComputeSlotEpPeerDn OBJECT-TYPE
    SYNTAX       SnmpAdminString
    MAX-ACCESS   read-only
    STATUS       current
    DESCRIPTION
        "Cisco UCS fabric:ComputeSlotEp:peerDn managed object property"
    ::= { cucsFabricComputeSlotEpEntry 30 }

cucsFabricComputeSlotEpPeerPortId OBJECT-TYPE
    SYNTAX       Gauge32
    MAX-ACCESS   read-only
    STATUS       current
    DESCRIPTION
        "Cisco UCS fabric:ComputeSlotEp:peerPortId managed
        object property"
    ::= { cucsFabricComputeSlotEpEntry 31 }

cucsFabricComputeSlotEpPeerSlotId OBJECT-TYPE
    SYNTAX       Gauge32
    MAX-ACCESS   read-only
    STATUS       current
    DESCRIPTION
        "Cisco UCS fabric:ComputeSlotEp:peerSlotId managed
        object property"
    ::= { cucsFabricComputeSlotEpEntry 32 }

cucsFabricComputeSlotEpPortId OBJECT-TYPE
    SYNTAX       CucsFabricPIoEpPortId
    MAX-ACCESS   read-only
    STATUS       current
    DESCRIPTION
        "Cisco UCS fabric:ComputeSlotEp:portId managed object property"
    ::= { cucsFabricComputeSlotEpEntry 33 }

cucsFabricComputeSlotEpPresence OBJECT-TYPE
    SYNTAX       CucsEquipmentSlotStatus
    MAX-ACCESS   read-only
    STATUS       current
    DESCRIPTION
        "Cisco UCS fabric:ComputeSlotEp:presence managed object property"
    ::= { cucsFabricComputeSlotEpEntry 34 }

cucsFabricComputeSlotEpRevision OBJECT-TYPE
    SYNTAX       SnmpAdminString
    MAX-ACCESS   read-only
    STATUS       current
    DESCRIPTION
        "Cisco UCS fabric:ComputeSlotEp:revision managed object property"
    ::= { cucsFabricComputeSlotEpEntry 35 }

cucsFabricComputeSlotEpSerial OBJECT-TYPE
    SYNTAX       SnmpAdminString
    MAX-ACCESS   read-only
    STATUS       current
    DESCRIPTION
        "Cisco UCS fabric:ComputeSlotEp:serial managed object property"
    ::= { cucsFabricComputeSlotEpEntry 36 }

cucsFabricComputeSlotEpSlotId OBJECT-TYPE
    SYNTAX       CucsFabricComputeSlotEpSlotId
    MAX-ACCESS   read-only
    STATUS       current
    DESCRIPTION
        "Cisco UCS fabric:ComputeSlotEp:slotId managed object property"
    ::= { cucsFabricComputeSlotEpEntry 37 }

cucsFabricComputeSlotEpSwitchId OBJECT-TYPE
    SYNTAX       CucsNetworkSwitchId
    MAX-ACCESS   read-only
    STATUS       current
    DESCRIPTION
        "Cisco UCS fabric:ComputeSlotEp:switchId managed object property"
    ::= { cucsFabricComputeSlotEpEntry 38 }

cucsFabricComputeSlotEpTransport OBJECT-TYPE
    SYNTAX       CucsNetworkTransport
    MAX-ACCESS   read-only
    STATUS       current
    DESCRIPTION
        "Cisco UCS fabric:ComputeSlotEp:transport managed object property"
    ::= { cucsFabricComputeSlotEpEntry 39 }

cucsFabricComputeSlotEpType OBJECT-TYPE
    SYNTAX       CucsFabricComputeEpType
    MAX-ACCESS   read-only
    STATUS       current
    DESCRIPTION
        "Cisco UCS fabric:ComputeSlotEp:type managed object property"
    ::= { cucsFabricComputeSlotEpEntry 40 }

cucsFabricComputeSlotEpVendor OBJECT-TYPE
    SYNTAX       SnmpAdminString
    MAX-ACCESS   read-only
    STATUS       current
    DESCRIPTION
        "Cisco UCS fabric:ComputeSlotEp:vendor managed object property"
    ::= { cucsFabricComputeSlotEpEntry 41 }

cucsFabricComputeSlotEpPeerChassisId OBJECT-TYPE
    SYNTAX       Gauge32
    MAX-ACCESS   read-only
    STATUS       current
    DESCRIPTION
        "Cisco UCS fabric:ComputeSlotEp:peerChassisId managed
        object property"
    ::= { cucsFabricComputeSlotEpEntry 42 }

cucsFabricComputeSlotEpFruIdentTrigTs OBJECT-TYPE
    SYNTAX       Unsigned64
    MAX-ACCESS   read-only
    STATUS       current
    DESCRIPTION
        "Cisco UCS fabric:ComputeSlotEp:fruIdentTrigTs
        managed object property"
    ::= { cucsFabricComputeSlotEpEntry 43 }

cucsFabricComputeSlotEpOperState OBJECT-TYPE
    SYNTAX       CucsFabricPIoEpOperState
    MAX-ACCESS   read-only
    STATUS       current
    DESCRIPTION
        "Cisco UCS fabric:ComputeSlotEp:operState managed object property"
    ::= { cucsFabricComputeSlotEpEntry 44 }

cucsFabricComputeSlotEpOperStateReason OBJECT-TYPE
    SYNTAX       SnmpAdminString
    MAX-ACCESS   read-only
    STATUS       current
    DESCRIPTION
        "Cisco UCS fabric:ComputeSlotEp:operStateReason
        managed object property"
    ::= { cucsFabricComputeSlotEpEntry 45 }

cucsFabricComputeSlotEpBoardAggregationRole OBJECT-TYPE
    SYNTAX       CucsEquipmentBoardAggregationRole
    MAX-ACCESS   read-only
    STATUS       current
    DESCRIPTION
        "Cisco UCS fabric:ComputeSlotEp:boardAggregationRole
        managed object property"
    ::= { cucsFabricComputeSlotEpEntry 46 }

cucsFabricComputeSlotEpPeerSlotEpDn OBJECT-TYPE
    SYNTAX       SnmpAdminString
    MAX-ACCESS   read-only
    STATUS       current
    DESCRIPTION
        "Cisco UCS fabric:ComputeSlotEp:peerSlotEpDn managed
        object property"
    ::= { cucsFabricComputeSlotEpEntry 47 }

cucsFabricComputeSlotEpPresencePath OBJECT-TYPE
    SYNTAX       CucsEquipmentConnectionStatus
    MAX-ACCESS   read-only
    STATUS       current
    DESCRIPTION
        "Cisco UCS fabric:ComputeSlotEp:presencePath managed
        object property"
    ::= { cucsFabricComputeSlotEpEntry 48 }

cucsFabricComputeSlotEpAggrPortId OBJECT-TYPE
    SYNTAX       Gauge32
    MAX-ACCESS   read-only
    STATUS       current
    DESCRIPTION
        "Cisco UCS fabric:ComputeSlotEp:aggrPortId managed
        object property"
    ::= { cucsFabricComputeSlotEpEntry 49 }

cucsFabricComputeSlotEpPeerAggrPortId OBJECT-TYPE
    SYNTAX       Gauge32
    MAX-ACCESS   read-only
    STATUS       current
    DESCRIPTION
        "Cisco UCS fabric:ComputeSlotEp:peerAggrPortId
        managed object property"
    ::= { cucsFabricComputeSlotEpEntry 50 }

cucsFabricComputeSlotEpDiscoveryStatus OBJECT-TYPE
    SYNTAX       CucsEquipmentConnectionStatus
    MAX-ACCESS   read-only
    STATUS       current
    DESCRIPTION
        "Cisco UCS fabric:ComputeSlotEp:discoveryStatus
        managed object property"
    ::= { cucsFabricComputeSlotEpEntry 51 }

cucsFabricComputeSlotEpAutoNegotiate OBJECT-TYPE
    SYNTAX       TruthValue
    MAX-ACCESS   read-only
    STATUS       current
    DESCRIPTION
        "Cisco UCS fabric:ComputeSlotEp:autoNegotiate managed
        object property"
    ::= { cucsFabricComputeSlotEpEntry 52 }

cucsFabricComputeSlotEpFsmTable OBJECT-TYPE
    SYNTAX           SEQUENCE OF CucsFabricComputeSlotEpFsmEntry
    MAX-ACCESS       not-accessible
    STATUS           current
    DESCRIPTION
        "Cisco UCS fabric:ComputeSlotEpFsm managed object table"
    ::= { cucsFabricObjects 74 }

cucsFabricComputeSlotEpFsmEntry OBJECT-TYPE
    SYNTAX           CucsFabricComputeSlotEpFsmEntry
    MAX-ACCESS       not-accessible
    STATUS           current
    DESCRIPTION
        "Entry for the cucsFabricComputeSlotEpFsmTable table."
    INDEX { cucsFabricComputeSlotEpFsmInstanceId }
    ::= { cucsFabricComputeSlotEpFsmTable 1 }

CucsFabricComputeSlotEpFsmEntry ::= SEQUENCE {
    cucsFabricComputeSlotEpFsmInstanceId                             CucsManagedObjectId,
    cucsFabricComputeSlotEpFsmDn                                     CucsManagedObjectDn,
    cucsFabricComputeSlotEpFsmRn                                     SnmpAdminString,
    cucsFabricComputeSlotEpFsmCompletionTime                         DateAndTime,
    cucsFabricComputeSlotEpFsmCurrentFsm                             CucsFabricComputeSlotEpFsmCurrentFsm,
    cucsFabricComputeSlotEpFsmDescrData                              SnmpAdminString,
    cucsFabricComputeSlotEpFsmFsmStatus                              CucsFsmFsmStageStatus,
    cucsFabricComputeSlotEpFsmProgress                               Gauge32,
    cucsFabricComputeSlotEpFsmRmtErrCode                             Gauge32,
    cucsFabricComputeSlotEpFsmRmtErrDescr                            SnmpAdminString,
    cucsFabricComputeSlotEpFsmRmtRslt                                CucsConditionRemoteInvRslt
}

cucsFabricComputeSlotEpFsmInstanceId OBJECT-TYPE
    SYNTAX       CucsManagedObjectId
    MAX-ACCESS   not-accessible
    STATUS       current
    DESCRIPTION
        "Instance identifier of the managed object."
    ::= { cucsFabricComputeSlotEpFsmEntry 1 }

cucsFabricComputeSlotEpFsmDn OBJECT-TYPE
    SYNTAX       CucsManagedObjectDn
    MAX-ACCESS   read-only
    STATUS       current
    DESCRIPTION
        "Cisco UCS fabric:ComputeSlotEpFsm:dn managed object property"
    ::= { cucsFabricComputeSlotEpFsmEntry 2 }

cucsFabricComputeSlotEpFsmRn OBJECT-TYPE
    SYNTAX       SnmpAdminString
    MAX-ACCESS   read-only
    STATUS       current
    DESCRIPTION
        "Cisco UCS fabric:ComputeSlotEpFsm:rn managed object property"
    ::= { cucsFabricComputeSlotEpFsmEntry 3 }

cucsFabricComputeSlotEpFsmCompletionTime OBJECT-TYPE
    SYNTAX       DateAndTime
    MAX-ACCESS   read-only
    STATUS       current
    DESCRIPTION
        "Cisco UCS fabric:ComputeSlotEpFsm:completionTime
        managed object property"
    ::= { cucsFabricComputeSlotEpFsmEntry 4 }

cucsFabricComputeSlotEpFsmCurrentFsm OBJECT-TYPE
    SYNTAX       CucsFabricComputeSlotEpFsmCurrentFsm
    MAX-ACCESS   read-only
    STATUS       current
    DESCRIPTION
        "Cisco UCS fabric:ComputeSlotEpFsm:currentFsm managed
        object property"
    ::= { cucsFabricComputeSlotEpFsmEntry 5 }

cucsFabricComputeSlotEpFsmDescrData OBJECT-TYPE
    SYNTAX       SnmpAdminString
    MAX-ACCESS   read-only
    STATUS       current
    DESCRIPTION
        "Cisco UCS fabric:ComputeSlotEpFsm:descr managed object property"
    ::= { cucsFabricComputeSlotEpFsmEntry 6 }

cucsFabricComputeSlotEpFsmFsmStatus OBJECT-TYPE
    SYNTAX       CucsFsmFsmStageStatus
    MAX-ACCESS   read-only
    STATUS       current
    DESCRIPTION
        "Cisco UCS fabric:ComputeSlotEpFsm:fsmStatus managed
        object property"
    ::= { cucsFabricComputeSlotEpFsmEntry 7 }

cucsFabricComputeSlotEpFsmProgress OBJECT-TYPE
    SYNTAX       Gauge32
    MAX-ACCESS   read-only
    STATUS       current
    DESCRIPTION
        "Cisco UCS fabric:ComputeSlotEpFsm:progress managed
        object property"
    ::= { cucsFabricComputeSlotEpFsmEntry 8 }

cucsFabricComputeSlotEpFsmRmtErrCode OBJECT-TYPE
    SYNTAX       Gauge32
    MAX-ACCESS   read-only
    STATUS       current
    DESCRIPTION
        "Cisco UCS fabric:ComputeSlotEpFsm:rmtErrCode managed
        object property"
    ::= { cucsFabricComputeSlotEpFsmEntry 9 }

cucsFabricComputeSlotEpFsmRmtErrDescr OBJECT-TYPE
    SYNTAX       SnmpAdminString
    MAX-ACCESS   read-only
    STATUS       current
    DESCRIPTION
        "Cisco UCS fabric:ComputeSlotEpFsm:rmtErrDescr
        managed object property"
    ::= { cucsFabricComputeSlotEpFsmEntry 10 }

cucsFabricComputeSlotEpFsmRmtRslt OBJECT-TYPE
    SYNTAX       CucsConditionRemoteInvRslt
    MAX-ACCESS   read-only
    STATUS       current
    DESCRIPTION
        "Cisco UCS fabric:ComputeSlotEpFsm:rmtRslt managed
        object property"
    ::= { cucsFabricComputeSlotEpFsmEntry 11 }

cucsFabricComputeSlotEpFsmStageTable OBJECT-TYPE
    SYNTAX           SEQUENCE OF CucsFabricComputeSlotEpFsmStageEntry
    MAX-ACCESS       not-accessible
    STATUS           current
    DESCRIPTION
        "Cisco UCS fabric:ComputeSlotEpFsmStage managed object table"
    ::= { cucsFabricObjects 75 }

cucsFabricComputeSlotEpFsmStageEntry OBJECT-TYPE
    SYNTAX           CucsFabricComputeSlotEpFsmStageEntry
    MAX-ACCESS       not-accessible
    STATUS           current
    DESCRIPTION
        "Entry for the cucsFabricComputeSlotEpFsmStageTable table."
    INDEX { cucsFabricComputeSlotEpFsmStageInstanceId }
    ::= { cucsFabricComputeSlotEpFsmStageTable 1 }

CucsFabricComputeSlotEpFsmStageEntry ::= SEQUENCE {
    cucsFabricComputeSlotEpFsmStageInstanceId                        CucsManagedObjectId,
    cucsFabricComputeSlotEpFsmStageDn                                CucsManagedObjectDn,
    cucsFabricComputeSlotEpFsmStageRn                                SnmpAdminString,
    cucsFabricComputeSlotEpFsmStageDescrData                         SnmpAdminString,
    cucsFabricComputeSlotEpFsmStageLastUpdateTime                    DateAndTime,
    cucsFabricComputeSlotEpFsmStageName                              CucsFabricComputeSlotEpFsmStageName,
    cucsFabricComputeSlotEpFsmStageOrder                             Gauge32,
    cucsFabricComputeSlotEpFsmStageRetry                             Gauge32,
    cucsFabricComputeSlotEpFsmStageStageStatus                       CucsFsmFsmStageStatus
}

cucsFabricComputeSlotEpFsmStageInstanceId OBJECT-TYPE
    SYNTAX       CucsManagedObjectId
    MAX-ACCESS   not-accessible
    STATUS       current
    DESCRIPTION
        "Instance identifier of the managed object."
    ::= { cucsFabricComputeSlotEpFsmStageEntry 1 }

cucsFabricComputeSlotEpFsmStageDn OBJECT-TYPE
    SYNTAX       CucsManagedObjectDn
    MAX-ACCESS   read-only
    STATUS       current
    DESCRIPTION
        "Cisco UCS fabric:ComputeSlotEpFsmStage:dn managed
        object property"
    ::= { cucsFabricComputeSlotEpFsmStageEntry 2 }

cucsFabricComputeSlotEpFsmStageRn OBJECT-TYPE
    SYNTAX       SnmpAdminString
    MAX-ACCESS   read-only
    STATUS       current
    DESCRIPTION
        "Cisco UCS fabric:ComputeSlotEpFsmStage:rn managed
        object property"
    ::= { cucsFabricComputeSlotEpFsmStageEntry 3 }

cucsFabricComputeSlotEpFsmStageDescrData OBJECT-TYPE
    SYNTAX       SnmpAdminString
    MAX-ACCESS   read-only
    STATUS       current
    DESCRIPTION
        "Cisco UCS fabric:ComputeSlotEpFsmStage:descr managed
        object property"
    ::= { cucsFabricComputeSlotEpFsmStageEntry 4 }

cucsFabricComputeSlotEpFsmStageLastUpdateTime OBJECT-TYPE
    SYNTAX       DateAndTime
    MAX-ACCESS   read-only
    STATUS       current
    DESCRIPTION
        "Cisco UCS fabric:ComputeSlotEpFsmStage:lastUpdateTime
        managed object property"
    ::= { cucsFabricComputeSlotEpFsmStageEntry 5 }

cucsFabricComputeSlotEpFsmStageName OBJECT-TYPE
    SYNTAX       CucsFabricComputeSlotEpFsmStageName
    MAX-ACCESS   read-only
    STATUS       current
    DESCRIPTION
        "Cisco UCS fabric:ComputeSlotEpFsmStage:name managed
        object property"
    ::= { cucsFabricComputeSlotEpFsmStageEntry 6 }

cucsFabricComputeSlotEpFsmStageOrder OBJECT-TYPE
    SYNTAX       Gauge32
    MAX-ACCESS   read-only
    STATUS       current
    DESCRIPTION
        "Cisco UCS fabric:ComputeSlotEpFsmStage:order managed
        object property"
    ::= { cucsFabricComputeSlotEpFsmStageEntry 7 }

cucsFabricComputeSlotEpFsmStageRetry OBJECT-TYPE
    SYNTAX       Gauge32
    MAX-ACCESS   read-only
    STATUS       current
    DESCRIPTION
        "Cisco UCS fabric:ComputeSlotEpFsmStage:retry managed
        object property"
    ::= { cucsFabricComputeSlotEpFsmStageEntry 8 }

cucsFabricComputeSlotEpFsmStageStageStatus OBJECT-TYPE
    SYNTAX       CucsFsmFsmStageStatus
    MAX-ACCESS   read-only
    STATUS       current
    DESCRIPTION
        "Cisco UCS fabric:ComputeSlotEpFsmStage:stageStatus
        managed object property"
    ::= { cucsFabricComputeSlotEpFsmStageEntry 9 }

cucsFabricComputeSlotEpFsmTaskTable OBJECT-TYPE
    SYNTAX           SEQUENCE OF CucsFabricComputeSlotEpFsmTaskEntry
    MAX-ACCESS       not-accessible
    STATUS           current
    DESCRIPTION
        "Cisco UCS fabric:ComputeSlotEpFsmTask managed object table"
    ::= { cucsFabricObjects 4 }

cucsFabricComputeSlotEpFsmTaskEntry OBJECT-TYPE
    SYNTAX           CucsFabricComputeSlotEpFsmTaskEntry
    MAX-ACCESS       not-accessible
    STATUS           current
    DESCRIPTION
        "Entry for the cucsFabricComputeSlotEpFsmTaskTable table."
    INDEX { cucsFabricComputeSlotEpFsmTaskInstanceId }
    ::= { cucsFabricComputeSlotEpFsmTaskTable 1 }

CucsFabricComputeSlotEpFsmTaskEntry ::= SEQUENCE {
    cucsFabricComputeSlotEpFsmTaskInstanceId                         CucsManagedObjectId,
    cucsFabricComputeSlotEpFsmTaskDn                                 CucsManagedObjectDn,
    cucsFabricComputeSlotEpFsmTaskRn                                 SnmpAdminString,
    cucsFabricComputeSlotEpFsmTaskCompletion                         CucsFsmCompletion,
    cucsFabricComputeSlotEpFsmTaskFlags                              CucsFsmFlags,
    cucsFabricComputeSlotEpFsmTaskItem                               CucsFabricComputeSlotEpFsmTaskItem,
    cucsFabricComputeSlotEpFsmTaskSeqId                              Gauge32
}

cucsFabricComputeSlotEpFsmTaskInstanceId OBJECT-TYPE
    SYNTAX       CucsManagedObjectId
    MAX-ACCESS   not-accessible
    STATUS       current
    DESCRIPTION
        "Instance identifier of the managed object."
    ::= { cucsFabricComputeSlotEpFsmTaskEntry 1 }

cucsFabricComputeSlotEpFsmTaskDn OBJECT-TYPE
    SYNTAX       CucsManagedObjectDn
    MAX-ACCESS   read-only
    STATUS       current
    DESCRIPTION
        "Cisco UCS fabric:ComputeSlotEpFsmTask:dn managed object property"
    ::= { cucsFabricComputeSlotEpFsmTaskEntry 2 }

cucsFabricComputeSlotEpFsmTaskRn OBJECT-TYPE
    SYNTAX       SnmpAdminString
    MAX-ACCESS   read-only
    STATUS       current
    DESCRIPTION
        "Cisco UCS fabric:ComputeSlotEpFsmTask:rn managed object property"
    ::= { cucsFabricComputeSlotEpFsmTaskEntry 3 }

cucsFabricComputeSlotEpFsmTaskCompletion OBJECT-TYPE
    SYNTAX       CucsFsmCompletion
    MAX-ACCESS   read-only
    STATUS       current
    DESCRIPTION
        "Cisco UCS fabric:ComputeSlotEpFsmTask:completion
        managed object property"
    ::= { cucsFabricComputeSlotEpFsmTaskEntry 4 }

cucsFabricComputeSlotEpFsmTaskFlags OBJECT-TYPE
    SYNTAX       CucsFsmFlags
    MAX-ACCESS   read-only
    STATUS       current
    DESCRIPTION
        "Cisco UCS fabric:ComputeSlotEpFsmTask:flags managed
        object property"
    ::= { cucsFabricComputeSlotEpFsmTaskEntry 5 }

cucsFabricComputeSlotEpFsmTaskItem OBJECT-TYPE
    SYNTAX       CucsFabricComputeSlotEpFsmTaskItem
    MAX-ACCESS   read-only
    STATUS       current
    DESCRIPTION
        "Cisco UCS fabric:ComputeSlotEpFsmTask:item managed
        object property"
    ::= { cucsFabricComputeSlotEpFsmTaskEntry 6 }

cucsFabricComputeSlotEpFsmTaskSeqId OBJECT-TYPE
    SYNTAX       Gauge32
    MAX-ACCESS   read-only
    STATUS       current
    DESCRIPTION
        "Cisco UCS fabric:ComputeSlotEpFsmTask:seqId managed
        object property"
    ::= { cucsFabricComputeSlotEpFsmTaskEntry 7 }

cucsFabricDceSrvTable OBJECT-TYPE
    SYNTAX           SEQUENCE OF CucsFabricDceSrvEntry
    MAX-ACCESS       not-accessible
    STATUS           current
    DESCRIPTION
        "Cisco UCS fabric:DceSrv managed object table"
    ::= { cucsFabricObjects 5 }

cucsFabricDceSrvEntry OBJECT-TYPE
    SYNTAX           CucsFabricDceSrvEntry
    MAX-ACCESS       not-accessible
    STATUS           current
    DESCRIPTION
        "Entry for the cucsFabricDceSrvTable table."
    INDEX { cucsFabricDceSrvInstanceId }
    ::= { cucsFabricDceSrvTable 1 }

CucsFabricDceSrvEntry ::= SEQUENCE {
    cucsFabricDceSrvInstanceId                                       CucsManagedObjectId,
    cucsFabricDceSrvDn                                               CucsManagedObjectDn,
    cucsFabricDceSrvRn                                               SnmpAdminString,
    cucsFabricDceSrvId                                               CucsNetworkSwitchId,
    cucsFabricDceSrvLocale                                           CucsFabricInternalLocale,
    cucsFabricDceSrvName                                             SnmpAdminString,
    cucsFabricDceSrvTransport                                        CucsFabricInternalDceSrvTransport,
    cucsFabricDceSrvType                                             CucsFabricInternalDceSrvType
}

cucsFabricDceSrvInstanceId OBJECT-TYPE
    SYNTAX       CucsManagedObjectId
    MAX-ACCESS   not-accessible
    STATUS       current
    DESCRIPTION
        "Instance identifier of the managed object."
    ::= { cucsFabricDceSrvEntry 1 }

cucsFabricDceSrvDn OBJECT-TYPE
    SYNTAX       CucsManagedObjectDn
    MAX-ACCESS   read-only
    STATUS       current
    DESCRIPTION
        "Cisco UCS fabric:DceSrv:dn managed object property"
    ::= { cucsFabricDceSrvEntry 2 }

cucsFabricDceSrvRn OBJECT-TYPE
    SYNTAX       SnmpAdminString
    MAX-ACCESS   read-only
    STATUS       current
    DESCRIPTION
        "Cisco UCS fabric:DceSrv:rn managed object property"
    ::= { cucsFabricDceSrvEntry 3 }

cucsFabricDceSrvId OBJECT-TYPE
    SYNTAX       CucsNetworkSwitchId
    MAX-ACCESS   read-only
    STATUS       current
    DESCRIPTION
        "Cisco UCS fabric:DceSrv:id managed object property"
    ::= { cucsFabricDceSrvEntry 4 }

cucsFabricDceSrvLocale OBJECT-TYPE
    SYNTAX       CucsFabricInternalLocale
    MAX-ACCESS   read-only
    STATUS       current
    DESCRIPTION
        "Cisco UCS fabric:DceSrv:locale managed object property"
    ::= { cucsFabricDceSrvEntry 5 }

cucsFabricDceSrvName OBJECT-TYPE
    SYNTAX       SnmpAdminString
    MAX-ACCESS   read-only
    STATUS       current
    DESCRIPTION
        "Cisco UCS fabric:DceSrv:name managed object property"
    ::= { cucsFabricDceSrvEntry 6 }

cucsFabricDceSrvTransport OBJECT-TYPE
    SYNTAX       CucsFabricInternalDceSrvTransport
    MAX-ACCESS   read-only
    STATUS       current
    DESCRIPTION
        "Cisco UCS fabric:DceSrv:transport managed object property"
    ::= { cucsFabricDceSrvEntry 7 }

cucsFabricDceSrvType OBJECT-TYPE
    SYNTAX       CucsFabricInternalDceSrvType
    MAX-ACCESS   read-only
    STATUS       current
    DESCRIPTION
        "Cisco UCS fabric:DceSrv:type managed object property"
    ::= { cucsFabricDceSrvEntry 8 }

cucsFabricDceSwSrvTable OBJECT-TYPE
    SYNTAX           SEQUENCE OF CucsFabricDceSwSrvEntry
    MAX-ACCESS       not-accessible
    STATUS           current
    DESCRIPTION
        "Cisco UCS fabric:DceSwSrv managed object table"
    ::= { cucsFabricObjects 6 }

cucsFabricDceSwSrvEntry OBJECT-TYPE
    SYNTAX           CucsFabricDceSwSrvEntry
    MAX-ACCESS       not-accessible
    STATUS           current
    DESCRIPTION
        "Entry for the cucsFabricDceSwSrvTable table."
    INDEX { cucsFabricDceSwSrvInstanceId }
    ::= { cucsFabricDceSwSrvTable 1 }

CucsFabricDceSwSrvEntry ::= SEQUENCE {
    cucsFabricDceSwSrvInstanceId                                     CucsManagedObjectId,
    cucsFabricDceSwSrvDn                                             CucsManagedObjectDn,
    cucsFabricDceSwSrvRn                                             SnmpAdminString,
    cucsFabricDceSwSrvId                                             CucsNetworkSwitchId,
    cucsFabricDceSwSrvLocale                                         CucsFabricInternalLocale,
    cucsFabricDceSwSrvName                                           SnmpAdminString,
    cucsFabricDceSwSrvTransport                                      CucsFabricInternalDceSrvTransport,
    cucsFabricDceSwSrvType                                           CucsFabricInternalDceSrvType
}

cucsFabricDceSwSrvInstanceId OBJECT-TYPE
    SYNTAX       CucsManagedObjectId
    MAX-ACCESS   not-accessible
    STATUS       current
    DESCRIPTION
        "Instance identifier of the managed object."
    ::= { cucsFabricDceSwSrvEntry 1 }

cucsFabricDceSwSrvDn OBJECT-TYPE
    SYNTAX       CucsManagedObjectDn
    MAX-ACCESS   read-only
    STATUS       current
    DESCRIPTION
        "Cisco UCS fabric:DceSwSrv:dn managed object property"
    ::= { cucsFabricDceSwSrvEntry 2 }

cucsFabricDceSwSrvRn OBJECT-TYPE
    SYNTAX       SnmpAdminString
    MAX-ACCESS   read-only
    STATUS       current
    DESCRIPTION
        "Cisco UCS fabric:DceSwSrv:rn managed object property"
    ::= { cucsFabricDceSwSrvEntry 3 }

cucsFabricDceSwSrvId OBJECT-TYPE
    SYNTAX       CucsNetworkSwitchId
    MAX-ACCESS   read-only
    STATUS       current
    DESCRIPTION
        "Cisco UCS fabric:DceSwSrv:id managed object property"
    ::= { cucsFabricDceSwSrvEntry 4 }

cucsFabricDceSwSrvLocale OBJECT-TYPE
    SYNTAX       CucsFabricInternalLocale
    MAX-ACCESS   read-only
    STATUS       current
    DESCRIPTION
        "Cisco UCS fabric:DceSwSrv:locale managed object property"
    ::= { cucsFabricDceSwSrvEntry 5 }

cucsFabricDceSwSrvName OBJECT-TYPE
    SYNTAX       SnmpAdminString
    MAX-ACCESS   read-only
    STATUS       current
    DESCRIPTION
        "Cisco UCS fabric:DceSwSrv:name managed object property"
    ::= { cucsFabricDceSwSrvEntry 6 }

cucsFabricDceSwSrvTransport OBJECT-TYPE
    SYNTAX       CucsFabricInternalDceSrvTransport
    MAX-ACCESS   read-only
    STATUS       current
    DESCRIPTION
        "Cisco UCS fabric:DceSwSrv:transport managed object property"
    ::= { cucsFabricDceSwSrvEntry 7 }

cucsFabricDceSwSrvType OBJECT-TYPE
    SYNTAX       CucsFabricInternalDceSrvType
    MAX-ACCESS   read-only
    STATUS       current
    DESCRIPTION
        "Cisco UCS fabric:DceSwSrv:type managed object property"
    ::= { cucsFabricDceSwSrvEntry 8 }

cucsFabricDceSwSrvEpTable OBJECT-TYPE
    SYNTAX           SEQUENCE OF CucsFabricDceSwSrvEpEntry
    MAX-ACCESS       not-accessible
    STATUS           current
    DESCRIPTION
        "Cisco UCS fabric:DceSwSrvEp managed object table"
    ::= { cucsFabricObjects 7 }

cucsFabricDceSwSrvEpEntry OBJECT-TYPE
    SYNTAX           CucsFabricDceSwSrvEpEntry
    MAX-ACCESS       not-accessible
    STATUS           current
    DESCRIPTION
        "Entry for the cucsFabricDceSwSrvEpTable table."
    INDEX { cucsFabricDceSwSrvEpInstanceId }
    ::= { cucsFabricDceSwSrvEpTable 1 }

CucsFabricDceSwSrvEpEntry ::= SEQUENCE {
    cucsFabricDceSwSrvEpInstanceId                                   CucsManagedObjectId,
    cucsFabricDceSwSrvEpDn                                           CucsManagedObjectDn,
    cucsFabricDceSwSrvEpRn                                           SnmpAdminString,
    cucsFabricDceSwSrvEpAdminState                                   CucsFabricInternalEpAdminState,
    cucsFabricDceSwSrvEpChassisId                                    Gauge32,
    cucsFabricDceSwSrvEpEpDn                                         SnmpAdminString,
    cucsFabricDceSwSrvEpIfRole                                       CucsFabricSwSrvEpIfRole,
    cucsFabricDceSwSrvEpIfType                                       CucsFabricPIoEpIfType,
    cucsFabricDceSwSrvEpLicGP                                        Unsigned64,
    cucsFabricDceSwSrvEpLicState                                     CucsLicenseState,
    cucsFabricDceSwSrvEpLocale                                       CucsFabricInternalEpLocale,
    cucsFabricDceSwSrvEpName                                         SnmpAdminString,
    cucsFabricDceSwSrvEpPeerDn                                       SnmpAdminString,
    cucsFabricDceSwSrvEpPeerPortId                                   Gauge32,
    cucsFabricDceSwSrvEpPeerSlotId                                   Gauge32,
    cucsFabricDceSwSrvEpPortId                                       CucsFabricDceSwSrvEpPortId,
    cucsFabricDceSwSrvEpSlotId                                       CucsFabricDceSwSrvEpSlotId,
    cucsFabricDceSwSrvEpSwitchId                                     CucsNetworkSwitchId,
    cucsFabricDceSwSrvEpTransport                                    CucsFabricADceSwSrvEpTransport,
    cucsFabricDceSwSrvEpType                                         CucsFabricSwSrvEpType,
    cucsFabricDceSwSrvEpUsrLbl                                       SnmpAdminString,
    cucsFabricDceSwSrvEpPeerChassisId                                Gauge32,
    cucsFabricDceSwSrvEpFltAggr                                      Unsigned64,
    cucsFabricDceSwSrvEpOperState                                    CucsFabricPIoEpOperState,
    cucsFabricDceSwSrvEpOperStateReason                              SnmpAdminString,
    cucsFabricDceSwSrvEpAggrPortId                                   Gauge32,
    cucsFabricDceSwSrvEpPeerAggrPortId                               Gauge32,
    cucsFabricDceSwSrvEpAutoNegotiate                                TruthValue
}

cucsFabricDceSwSrvEpInstanceId OBJECT-TYPE
    SYNTAX       CucsManagedObjectId
    MAX-ACCESS   not-accessible
    STATUS       current
    DESCRIPTION
        "Instance identifier of the managed object."
    ::= { cucsFabricDceSwSrvEpEntry 1 }

cucsFabricDceSwSrvEpDn OBJECT-TYPE
    SYNTAX       CucsManagedObjectDn
    MAX-ACCESS   read-only
    STATUS       current
    DESCRIPTION
        "Cisco UCS fabric:DceSwSrvEp:dn managed object property"
    ::= { cucsFabricDceSwSrvEpEntry 2 }

cucsFabricDceSwSrvEpRn OBJECT-TYPE
    SYNTAX       SnmpAdminString
    MAX-ACCESS   read-only
    STATUS       current
    DESCRIPTION
        "Cisco UCS fabric:DceSwSrvEp:rn managed object property"
    ::= { cucsFabricDceSwSrvEpEntry 3 }

cucsFabricDceSwSrvEpAdminState OBJECT-TYPE
    SYNTAX       CucsFabricInternalEpAdminState
    MAX-ACCESS   read-only
    STATUS       current
    DESCRIPTION
        "Cisco UCS fabric:DceSwSrvEp:adminState managed object property"
    ::= { cucsFabricDceSwSrvEpEntry 4 }

cucsFabricDceSwSrvEpChassisId OBJECT-TYPE
    SYNTAX       Gauge32
    MAX-ACCESS   read-only
    STATUS       current
    DESCRIPTION
        "Cisco UCS fabric:DceSwSrvEp:chassisId managed object property"
    ::= { cucsFabricDceSwSrvEpEntry 5 }

cucsFabricDceSwSrvEpEpDn OBJECT-TYPE
    SYNTAX       SnmpAdminString
    MAX-ACCESS   read-only
    STATUS       current
    DESCRIPTION
        "Cisco UCS fabric:DceSwSrvEp:epDn managed object property"
    ::= { cucsFabricDceSwSrvEpEntry 6 }

cucsFabricDceSwSrvEpIfRole OBJECT-TYPE
    SYNTAX       CucsFabricSwSrvEpIfRole
    MAX-ACCESS   read-only
    STATUS       current
    DESCRIPTION
        "Cisco UCS fabric:DceSwSrvEp:ifRole managed object property"
    ::= { cucsFabricDceSwSrvEpEntry 7 }

cucsFabricDceSwSrvEpIfType OBJECT-TYPE
    SYNTAX       CucsFabricPIoEpIfType
    MAX-ACCESS   read-only
    STATUS       current
    DESCRIPTION
        "Cisco UCS fabric:DceSwSrvEp:ifType managed object property"
    ::= { cucsFabricDceSwSrvEpEntry 8 }

cucsFabricDceSwSrvEpLicGP OBJECT-TYPE
    SYNTAX       Unsigned64
    MAX-ACCESS   read-only
    STATUS       current
    DESCRIPTION
        "Cisco UCS fabric:DceSwSrvEp:licGP managed object property"
    ::= { cucsFabricDceSwSrvEpEntry 9 }

cucsFabricDceSwSrvEpLicState OBJECT-TYPE
    SYNTAX       CucsLicenseState
    MAX-ACCESS   read-only
    STATUS       current
    DESCRIPTION
        "Cisco UCS fabric:DceSwSrvEp:licState managed object property"
    ::= { cucsFabricDceSwSrvEpEntry 10 }

cucsFabricDceSwSrvEpLocale OBJECT-TYPE
    SYNTAX       CucsFabricInternalEpLocale
    MAX-ACCESS   read-only
    STATUS       current
    DESCRIPTION
        "Cisco UCS fabric:DceSwSrvEp:locale managed object property"
    ::= { cucsFabricDceSwSrvEpEntry 11 }

cucsFabricDceSwSrvEpName OBJECT-TYPE
    SYNTAX       SnmpAdminString
    MAX-ACCESS   read-only
    STATUS       current
    DESCRIPTION
        "Cisco UCS fabric:DceSwSrvEp:name managed object property"
    ::= { cucsFabricDceSwSrvEpEntry 12 }

cucsFabricDceSwSrvEpPeerDn OBJECT-TYPE
    SYNTAX       SnmpAdminString
    MAX-ACCESS   read-only
    STATUS       current
    DESCRIPTION
        "Cisco UCS fabric:DceSwSrvEp:peerDn managed object property"
    ::= { cucsFabricDceSwSrvEpEntry 13 }

cucsFabricDceSwSrvEpPeerPortId OBJECT-TYPE
    SYNTAX       Gauge32
    MAX-ACCESS   read-only
    STATUS       current
    DESCRIPTION
        "Cisco UCS fabric:DceSwSrvEp:peerPortId managed object property"
    ::= { cucsFabricDceSwSrvEpEntry 14 }

cucsFabricDceSwSrvEpPeerSlotId OBJECT-TYPE
    SYNTAX       Gauge32
    MAX-ACCESS   read-only
    STATUS       current
    DESCRIPTION
        "Cisco UCS fabric:DceSwSrvEp:peerSlotId managed object property"
    ::= { cucsFabricDceSwSrvEpEntry 15 }

cucsFabricDceSwSrvEpPortId OBJECT-TYPE
    SYNTAX       CucsFabricDceSwSrvEpPortId
    MAX-ACCESS   read-only
    STATUS       current
    DESCRIPTION
        "Cisco UCS fabric:DceSwSrvEp:portId managed object property"
    ::= { cucsFabricDceSwSrvEpEntry 16 }

cucsFabricDceSwSrvEpSlotId OBJECT-TYPE
    SYNTAX       CucsFabricDceSwSrvEpSlotId
    MAX-ACCESS   read-only
    STATUS       current
    DESCRIPTION
        "Cisco UCS fabric:DceSwSrvEp:slotId managed object property"
    ::= { cucsFabricDceSwSrvEpEntry 17 }

cucsFabricDceSwSrvEpSwitchId OBJECT-TYPE
    SYNTAX       CucsNetworkSwitchId
    MAX-ACCESS   read-only
    STATUS       current
    DESCRIPTION
        "Cisco UCS fabric:DceSwSrvEp:switchId managed object property"
    ::= { cucsFabricDceSwSrvEpEntry 18 }

cucsFabricDceSwSrvEpTransport OBJECT-TYPE
    SYNTAX       CucsFabricADceSwSrvEpTransport
    MAX-ACCESS   read-only
    STATUS       current
    DESCRIPTION
        "Cisco UCS fabric:DceSwSrvEp:transport managed object property"
    ::= { cucsFabricDceSwSrvEpEntry 19 }

cucsFabricDceSwSrvEpType OBJECT-TYPE
    SYNTAX       CucsFabricSwSrvEpType
    MAX-ACCESS   read-only
    STATUS       current
    DESCRIPTION
        "Cisco UCS fabric:DceSwSrvEp:type managed object property"
    ::= { cucsFabricDceSwSrvEpEntry 20 }

cucsFabricDceSwSrvEpUsrLbl OBJECT-TYPE
    SYNTAX       SnmpAdminString
    MAX-ACCESS   read-only
    STATUS       current
    DESCRIPTION
        "Cisco UCS fabric:DceSwSrvEp:usrLbl managed object property"
    ::= { cucsFabricDceSwSrvEpEntry 21 }

cucsFabricDceSwSrvEpPeerChassisId OBJECT-TYPE
    SYNTAX       Gauge32
    MAX-ACCESS   read-only
    STATUS       current
    DESCRIPTION
        "Cisco UCS fabric:DceSwSrvEp:peerChassisId managed
        object property"
    ::= { cucsFabricDceSwSrvEpEntry 22 }

cucsFabricDceSwSrvEpFltAggr OBJECT-TYPE
    SYNTAX       Unsigned64
    MAX-ACCESS   read-only
    STATUS       current
    DESCRIPTION
        "Cisco UCS fabric:DceSwSrvEp:fltAggr managed object property"
    ::= { cucsFabricDceSwSrvEpEntry 23 }

cucsFabricDceSwSrvEpOperState OBJECT-TYPE
    SYNTAX       CucsFabricPIoEpOperState
    MAX-ACCESS   read-only
    STATUS       current
    DESCRIPTION
        "Cisco UCS fabric:DceSwSrvEp:operState managed object property"
    ::= { cucsFabricDceSwSrvEpEntry 24 }

cucsFabricDceSwSrvEpOperStateReason OBJECT-TYPE
    SYNTAX       SnmpAdminString
    MAX-ACCESS   read-only
    STATUS       current
    DESCRIPTION
        "Cisco UCS fabric:DceSwSrvEp:operStateReason managed
        object property"
    ::= { cucsFabricDceSwSrvEpEntry 25 }

cucsFabricDceSwSrvEpAggrPortId OBJECT-TYPE
    SYNTAX       Gauge32
    MAX-ACCESS   read-only
    STATUS       current
    DESCRIPTION
        "Cisco UCS fabric:DceSwSrvEp:aggrPortId managed object property"
    ::= { cucsFabricDceSwSrvEpEntry 26 }

cucsFabricDceSwSrvEpPeerAggrPortId OBJECT-TYPE
    SYNTAX       Gauge32
    MAX-ACCESS   read-only
    STATUS       current
    DESCRIPTION
        "Cisco UCS fabric:DceSwSrvEp:peerAggrPortId managed
        object property"
    ::= { cucsFabricDceSwSrvEpEntry 27 }

cucsFabricDceSwSrvEpAutoNegotiate OBJECT-TYPE
    SYNTAX       TruthValue
    MAX-ACCESS   read-only
    STATUS       current
    DESCRIPTION
        "Cisco UCS fabric:DceSwSrvEp:autoNegotiate managed
        object property"
    ::= { cucsFabricDceSwSrvEpEntry 28 }

cucsFabricDceSwSrvPcTable OBJECT-TYPE
    SYNTAX           SEQUENCE OF CucsFabricDceSwSrvPcEntry
    MAX-ACCESS       not-accessible
    STATUS           current
    DESCRIPTION
        "Cisco UCS fabric:DceSwSrvPc managed object table"
    ::= { cucsFabricObjects 70 }

cucsFabricDceSwSrvPcEntry OBJECT-TYPE
    SYNTAX           CucsFabricDceSwSrvPcEntry
    MAX-ACCESS       not-accessible
    STATUS           current
    DESCRIPTION
        "Entry for the cucsFabricDceSwSrvPcTable table."
    INDEX { cucsFabricDceSwSrvPcInstanceId }
    ::= { cucsFabricDceSwSrvPcTable 1 }

CucsFabricDceSwSrvPcEntry ::= SEQUENCE {
    cucsFabricDceSwSrvPcInstanceId                                   CucsManagedObjectId,
    cucsFabricDceSwSrvPcDn                                           CucsManagedObjectDn,
    cucsFabricDceSwSrvPcRn                                           SnmpAdminString,
    cucsFabricDceSwSrvPcAdminState                                   CucsFabricDceSwSrvPcAdminState,
    cucsFabricDceSwSrvPcChassisId                                    Gauge32,
    cucsFabricDceSwSrvPcEpDn                                         SnmpAdminString,
    cucsFabricDceSwSrvPcFltAggr                                      Unsigned64,
    cucsFabricDceSwSrvPcIfRole                                       CucsFabricSwSrvPcIfRole,
    cucsFabricDceSwSrvPcIfType                                       CucsFabricCIoEpIfType,
    cucsFabricDceSwSrvPcLocale                                       CucsFabricInternalPcLocale,
    cucsFabricDceSwSrvPcName                                         SnmpAdminString,
    cucsFabricDceSwSrvPcOperSpeed                                    CucsPortEthSpeed,
    cucsFabricDceSwSrvPcOperState                                    CucsNetworkPortOperState,
    cucsFabricDceSwSrvPcPeerDn                                       SnmpAdminString,
    cucsFabricDceSwSrvPcPortId                                       CucsFabricDceSwSrvPcPortId,
    cucsFabricDceSwSrvPcStateQual                                    SnmpAdminString,
    cucsFabricDceSwSrvPcSwitchId                                     CucsNetworkSwitchId,
    cucsFabricDceSwSrvPcTransport                                    CucsFabricDceSwSrvPcTransport,
    cucsFabricDceSwSrvPcType                                         CucsFabricSwSrvPcType,
    cucsFabricDceSwSrvPcDescr                                        SnmpAdminString
}

cucsFabricDceSwSrvPcInstanceId OBJECT-TYPE
    SYNTAX       CucsManagedObjectId
    MAX-ACCESS   not-accessible
    STATUS       current
    DESCRIPTION
        "Instance identifier of the managed object."
    ::= { cucsFabricDceSwSrvPcEntry 1 }

cucsFabricDceSwSrvPcDn OBJECT-TYPE
    SYNTAX       CucsManagedObjectDn
    MAX-ACCESS   read-only
    STATUS       current
    DESCRIPTION
        "Cisco UCS fabric:DceSwSrvPc:dn managed object property"
    ::= { cucsFabricDceSwSrvPcEntry 2 }

cucsFabricDceSwSrvPcRn OBJECT-TYPE
    SYNTAX       SnmpAdminString
    MAX-ACCESS   read-only
    STATUS       current
    DESCRIPTION
        "Cisco UCS fabric:DceSwSrvPc:rn managed object property"
    ::= { cucsFabricDceSwSrvPcEntry 3 }

cucsFabricDceSwSrvPcAdminState OBJECT-TYPE
    SYNTAX       CucsFabricDceSwSrvPcAdminState
    MAX-ACCESS   read-only
    STATUS       current
    DESCRIPTION
        "Cisco UCS fabric:DceSwSrvPc:adminState managed object property"
    ::= { cucsFabricDceSwSrvPcEntry 4 }

cucsFabricDceSwSrvPcChassisId OBJECT-TYPE
    SYNTAX       Gauge32
    MAX-ACCESS   read-only
    STATUS       current
    DESCRIPTION
        "Cisco UCS fabric:DceSwSrvPc:chassisId managed object property"
    ::= { cucsFabricDceSwSrvPcEntry 5 }

cucsFabricDceSwSrvPcEpDn OBJECT-TYPE
    SYNTAX       SnmpAdminString
    MAX-ACCESS   read-only
    STATUS       current
    DESCRIPTION
        "Cisco UCS fabric:DceSwSrvPc:epDn managed object property"
    ::= { cucsFabricDceSwSrvPcEntry 6 }

cucsFabricDceSwSrvPcFltAggr OBJECT-TYPE
    SYNTAX       Unsigned64
    MAX-ACCESS   read-only
    STATUS       current
    DESCRIPTION
        "Cisco UCS fabric:DceSwSrvPc:fltAggr managed object property"
    ::= { cucsFabricDceSwSrvPcEntry 7 }

cucsFabricDceSwSrvPcIfRole OBJECT-TYPE
    SYNTAX       CucsFabricSwSrvPcIfRole
    MAX-ACCESS   read-only
    STATUS       current
    DESCRIPTION
        "Cisco UCS fabric:DceSwSrvPc:ifRole managed object property"
    ::= { cucsFabricDceSwSrvPcEntry 8 }

cucsFabricDceSwSrvPcIfType OBJECT-TYPE
    SYNTAX       CucsFabricCIoEpIfType
    MAX-ACCESS   read-only
    STATUS       current
    DESCRIPTION
        "Cisco UCS fabric:DceSwSrvPc:ifType managed object property"
    ::= { cucsFabricDceSwSrvPcEntry 9 }

cucsFabricDceSwSrvPcLocale OBJECT-TYPE
    SYNTAX       CucsFabricInternalPcLocale
    MAX-ACCESS   read-only
    STATUS       current
    DESCRIPTION
        "Cisco UCS fabric:DceSwSrvPc:locale managed object property"
    ::= { cucsFabricDceSwSrvPcEntry 10 }

cucsFabricDceSwSrvPcName OBJECT-TYPE
    SYNTAX       SnmpAdminString
    MAX-ACCESS   read-only
    STATUS       current
    DESCRIPTION
        "Cisco UCS fabric:DceSwSrvPc:name managed object property"
    ::= { cucsFabricDceSwSrvPcEntry 11 }

cucsFabricDceSwSrvPcOperSpeed OBJECT-TYPE
    SYNTAX       CucsPortEthSpeed
    MAX-ACCESS   read-only
    STATUS       current
    DESCRIPTION
        "Cisco UCS fabric:DceSwSrvPc:operSpeed managed object property"
    ::= { cucsFabricDceSwSrvPcEntry 12 }

cucsFabricDceSwSrvPcOperState OBJECT-TYPE
    SYNTAX       CucsNetworkPortOperState
    MAX-ACCESS   read-only
    STATUS       current
    DESCRIPTION
        "Cisco UCS fabric:DceSwSrvPc:operState managed object property"
    ::= { cucsFabricDceSwSrvPcEntry 13 }

cucsFabricDceSwSrvPcPeerDn OBJECT-TYPE
    SYNTAX       SnmpAdminString
    MAX-ACCESS   read-only
    STATUS       current
    DESCRIPTION
        "Cisco UCS fabric:DceSwSrvPc:peerDn managed object property"
    ::= { cucsFabricDceSwSrvPcEntry 14 }

cucsFabricDceSwSrvPcPortId OBJECT-TYPE
    SYNTAX       CucsFabricDceSwSrvPcPortId
    MAX-ACCESS   read-only
    STATUS       current
    DESCRIPTION
        "Cisco UCS fabric:DceSwSrvPc:portId managed object property"
    ::= { cucsFabricDceSwSrvPcEntry 15 }

cucsFabricDceSwSrvPcStateQual OBJECT-TYPE
    SYNTAX       SnmpAdminString
    MAX-ACCESS   read-only
    STATUS       current
    DESCRIPTION
        "Cisco UCS fabric:DceSwSrvPc:stateQual managed object property"
    ::= { cucsFabricDceSwSrvPcEntry 16 }

cucsFabricDceSwSrvPcSwitchId OBJECT-TYPE
    SYNTAX       CucsNetworkSwitchId
    MAX-ACCESS   read-only
    STATUS       current
    DESCRIPTION
        "Cisco UCS fabric:DceSwSrvPc:switchId managed object property"
    ::= { cucsFabricDceSwSrvPcEntry 17 }

cucsFabricDceSwSrvPcTransport OBJECT-TYPE
    SYNTAX       CucsFabricDceSwSrvPcTransport
    MAX-ACCESS   read-only
    STATUS       current
    DESCRIPTION
        "Cisco UCS fabric:DceSwSrvPc:transport managed object property"
    ::= { cucsFabricDceSwSrvPcEntry 18 }

cucsFabricDceSwSrvPcType OBJECT-TYPE
    SYNTAX       CucsFabricSwSrvPcType
    MAX-ACCESS   read-only
    STATUS       current
    DESCRIPTION
        "Cisco UCS fabric:DceSwSrvPc:type managed object property"
    ::= { cucsFabricDceSwSrvPcEntry 19 }

cucsFabricDceSwSrvPcDescr OBJECT-TYPE
    SYNTAX       SnmpAdminString
    MAX-ACCESS   read-only
    STATUS       current
    DESCRIPTION
        "Cisco UCS fabric:DceSwSrvPc:descr managed object property"
    ::= { cucsFabricDceSwSrvPcEntry 20 }

cucsFabricDceSwSrvPcEpTable OBJECT-TYPE
    SYNTAX           SEQUENCE OF CucsFabricDceSwSrvPcEpEntry
    MAX-ACCESS       not-accessible
    STATUS           current
    DESCRIPTION
        "Cisco UCS fabric:DceSwSrvPcEp managed object table"
    ::= { cucsFabricObjects 71 }

cucsFabricDceSwSrvPcEpEntry OBJECT-TYPE
    SYNTAX           CucsFabricDceSwSrvPcEpEntry
    MAX-ACCESS       not-accessible
    STATUS           current
    DESCRIPTION
        "Entry for the cucsFabricDceSwSrvPcEpTable table."
    INDEX { cucsFabricDceSwSrvPcEpInstanceId }
    ::= { cucsFabricDceSwSrvPcEpTable 1 }

CucsFabricDceSwSrvPcEpEntry ::= SEQUENCE {
    cucsFabricDceSwSrvPcEpInstanceId                                 CucsManagedObjectId,
    cucsFabricDceSwSrvPcEpDnData                                     CucsManagedObjectDn,
    cucsFabricDceSwSrvPcEpRn                                         SnmpAdminString,
    cucsFabricDceSwSrvPcEpAdminState                                 CucsFabricInternalEpAdminState,
    cucsFabricDceSwSrvPcEpChassisId                                  Gauge32,
    cucsFabricDceSwSrvPcEpEpDn                                       SnmpAdminString,
    cucsFabricDceSwSrvPcEpFltAggr                                    Unsigned64,
    cucsFabricDceSwSrvPcEpIfRole                                     CucsFabricSwSrvEpIfRole,
    cucsFabricDceSwSrvPcEpIfType                                     CucsFabricPIoEpIfType,
    cucsFabricDceSwSrvPcEpLicGP                                      Unsigned64,
    cucsFabricDceSwSrvPcEpLicState                                   CucsLicenseState,
    cucsFabricDceSwSrvPcEpLocale                                     CucsFabricInternalEpLocale,
    cucsFabricDceSwSrvPcEpMembership                                 CucsFabricMembershipStatus,
    cucsFabricDceSwSrvPcEpName                                       SnmpAdminString,
    cucsFabricDceSwSrvPcEpPeerChassisId                              Gauge32,
    cucsFabricDceSwSrvPcEpPeerDn                                     SnmpAdminString,
    cucsFabricDceSwSrvPcEpPeerPortId                                 Gauge32,
    cucsFabricDceSwSrvPcEpPeerSlotId                                 Gauge32,
    cucsFabricDceSwSrvPcEpPortId                                     CucsFabricDceSwSrvPcEpPortId,
    cucsFabricDceSwSrvPcEpSlotId                                     CucsFabricDceSwSrvPcEpSlotId,
    cucsFabricDceSwSrvPcEpSwitchId                                   CucsNetworkSwitchId,
    cucsFabricDceSwSrvPcEpTransport                                  CucsFabricADceSwSrvEpTransport,
    cucsFabricDceSwSrvPcEpType                                       CucsFabricSwSrvEpType,
    cucsFabricDceSwSrvPcEpOperState                                  CucsFabricPIoEpOperState,
    cucsFabricDceSwSrvPcEpOperStateReason                            SnmpAdminString,
    cucsFabricDceSwSrvPcEpUsrLbl                                     SnmpAdminString,
    cucsFabricDceSwSrvPcEpAggrPortId                                 Gauge32,
    cucsFabricDceSwSrvPcEpPeerAggrPortId                             Gauge32,
    cucsFabricDceSwSrvPcEpAutoNegotiate                              TruthValue
}

cucsFabricDceSwSrvPcEpInstanceId OBJECT-TYPE
    SYNTAX       CucsManagedObjectId
    MAX-ACCESS   not-accessible
    STATUS       current
    DESCRIPTION
        "Instance identifier of the managed object."
    ::= { cucsFabricDceSwSrvPcEpEntry 1 }

cucsFabricDceSwSrvPcEpDnData OBJECT-TYPE
    SYNTAX       CucsManagedObjectDn
    MAX-ACCESS   read-only
    STATUS       current
    DESCRIPTION
        "Cisco UCS fabric:DceSwSrvPcEp:dn managed object property"
    ::= { cucsFabricDceSwSrvPcEpEntry 2 }

cucsFabricDceSwSrvPcEpRn OBJECT-TYPE
    SYNTAX       SnmpAdminString
    MAX-ACCESS   read-only
    STATUS       current
    DESCRIPTION
        "Cisco UCS fabric:DceSwSrvPcEp:rn managed object property"
    ::= { cucsFabricDceSwSrvPcEpEntry 3 }

cucsFabricDceSwSrvPcEpAdminState OBJECT-TYPE
    SYNTAX       CucsFabricInternalEpAdminState
    MAX-ACCESS   read-only
    STATUS       current
    DESCRIPTION
        "Cisco UCS fabric:DceSwSrvPcEp:adminState managed object property"
    ::= { cucsFabricDceSwSrvPcEpEntry 4 }

cucsFabricDceSwSrvPcEpChassisId OBJECT-TYPE
    SYNTAX       Gauge32
    MAX-ACCESS   read-only
    STATUS       current
    DESCRIPTION
        "Cisco UCS fabric:DceSwSrvPcEp:chassisId managed object property"
    ::= { cucsFabricDceSwSrvPcEpEntry 5 }

cucsFabricDceSwSrvPcEpEpDn OBJECT-TYPE
    SYNTAX       SnmpAdminString
    MAX-ACCESS   read-only
    STATUS       current
    DESCRIPTION
        "Cisco UCS fabric:DceSwSrvPcEp:epDn managed object property"
    ::= { cucsFabricDceSwSrvPcEpEntry 6 }

cucsFabricDceSwSrvPcEpFltAggr OBJECT-TYPE
    SYNTAX       Unsigned64
    MAX-ACCESS   read-only
    STATUS       current
    DESCRIPTION
        "Cisco UCS fabric:DceSwSrvPcEp:fltAggr managed object property"
    ::= { cucsFabricDceSwSrvPcEpEntry 7 }

cucsFabricDceSwSrvPcEpIfRole OBJECT-TYPE
    SYNTAX       CucsFabricSwSrvEpIfRole
    MAX-ACCESS   read-only
    STATUS       current
    DESCRIPTION
        "Cisco UCS fabric:DceSwSrvPcEp:ifRole managed object property"
    ::= { cucsFabricDceSwSrvPcEpEntry 8 }

cucsFabricDceSwSrvPcEpIfType OBJECT-TYPE
    SYNTAX       CucsFabricPIoEpIfType
    MAX-ACCESS   read-only
    STATUS       current
    DESCRIPTION
        "Cisco UCS fabric:DceSwSrvPcEp:ifType managed object property"
    ::= { cucsFabricDceSwSrvPcEpEntry 9 }

cucsFabricDceSwSrvPcEpLicGP OBJECT-TYPE
    SYNTAX       Unsigned64
    MAX-ACCESS   read-only
    STATUS       current
    DESCRIPTION
        "Cisco UCS fabric:DceSwSrvPcEp:licGP managed object property"
    ::= { cucsFabricDceSwSrvPcEpEntry 10 }

cucsFabricDceSwSrvPcEpLicState OBJECT-TYPE
    SYNTAX       CucsLicenseState
    MAX-ACCESS   read-only
    STATUS       current
    DESCRIPTION
        "Cisco UCS fabric:DceSwSrvPcEp:licState managed object property"
    ::= { cucsFabricDceSwSrvPcEpEntry 11 }

cucsFabricDceSwSrvPcEpLocale OBJECT-TYPE
    SYNTAX       CucsFabricInternalEpLocale
    MAX-ACCESS   read-only
    STATUS       current
    DESCRIPTION
        "Cisco UCS fabric:DceSwSrvPcEp:locale managed object property"
    ::= { cucsFabricDceSwSrvPcEpEntry 12 }

cucsFabricDceSwSrvPcEpMembership OBJECT-TYPE
    SYNTAX       CucsFabricMembershipStatus
    MAX-ACCESS   read-only
    STATUS       current
    DESCRIPTION
        "Cisco UCS fabric:DceSwSrvPcEp:membership managed object property"
    ::= { cucsFabricDceSwSrvPcEpEntry 13 }

cucsFabricDceSwSrvPcEpName OBJECT-TYPE
    SYNTAX       SnmpAdminString
    MAX-ACCESS   read-only
    STATUS       current
    DESCRIPTION
        "Cisco UCS fabric:DceSwSrvPcEp:name managed object property"
    ::= { cucsFabricDceSwSrvPcEpEntry 14 }

cucsFabricDceSwSrvPcEpPeerChassisId OBJECT-TYPE
    SYNTAX       Gauge32
    MAX-ACCESS   read-only
    STATUS       current
    DESCRIPTION
        "Cisco UCS fabric:DceSwSrvPcEp:peerChassisId managed
        object property"
    ::= { cucsFabricDceSwSrvPcEpEntry 15 }

cucsFabricDceSwSrvPcEpPeerDn OBJECT-TYPE
    SYNTAX       SnmpAdminString
    MAX-ACCESS   read-only
    STATUS       current
    DESCRIPTION
        "Cisco UCS fabric:DceSwSrvPcEp:peerDn managed object property"
    ::= { cucsFabricDceSwSrvPcEpEntry 16 }

cucsFabricDceSwSrvPcEpPeerPortId OBJECT-TYPE
    SYNTAX       Gauge32
    MAX-ACCESS   read-only
    STATUS       current
    DESCRIPTION
        "Cisco UCS fabric:DceSwSrvPcEp:peerPortId managed object property"
    ::= { cucsFabricDceSwSrvPcEpEntry 17 }

cucsFabricDceSwSrvPcEpPeerSlotId OBJECT-TYPE
    SYNTAX       Gauge32
    MAX-ACCESS   read-only
    STATUS       current
    DESCRIPTION
        "Cisco UCS fabric:DceSwSrvPcEp:peerSlotId managed object property"
    ::= { cucsFabricDceSwSrvPcEpEntry 18 }

cucsFabricDceSwSrvPcEpPortId OBJECT-TYPE
    SYNTAX       CucsFabricDceSwSrvPcEpPortId
    MAX-ACCESS   read-only
    STATUS       current
    DESCRIPTION
        "Cisco UCS fabric:DceSwSrvPcEp:portId managed object property"
    ::= { cucsFabricDceSwSrvPcEpEntry 19 }

cucsFabricDceSwSrvPcEpSlotId OBJECT-TYPE
    SYNTAX       CucsFabricDceSwSrvPcEpSlotId
    MAX-ACCESS   read-only
    STATUS       current
    DESCRIPTION
        "Cisco UCS fabric:DceSwSrvPcEp:slotId managed object property"
    ::= { cucsFabricDceSwSrvPcEpEntry 20 }

cucsFabricDceSwSrvPcEpSwitchId OBJECT-TYPE
    SYNTAX       CucsNetworkSwitchId
    MAX-ACCESS   read-only
    STATUS       current
    DESCRIPTION
        "Cisco UCS fabric:DceSwSrvPcEp:switchId managed object property"
    ::= { cucsFabricDceSwSrvPcEpEntry 21 }

cucsFabricDceSwSrvPcEpTransport OBJECT-TYPE
    SYNTAX       CucsFabricADceSwSrvEpTransport
    MAX-ACCESS   read-only
    STATUS       current
    DESCRIPTION
        "Cisco UCS fabric:DceSwSrvPcEp:transport managed object property"
    ::= { cucsFabricDceSwSrvPcEpEntry 22 }

cucsFabricDceSwSrvPcEpType OBJECT-TYPE
    SYNTAX       CucsFabricSwSrvEpType
    MAX-ACCESS   read-only
    STATUS       current
    DESCRIPTION
        "Cisco UCS fabric:DceSwSrvPcEp:type managed object property"
    ::= { cucsFabricDceSwSrvPcEpEntry 23 }

cucsFabricDceSwSrvPcEpOperState OBJECT-TYPE
    SYNTAX       CucsFabricPIoEpOperState
    MAX-ACCESS   read-only
    STATUS       current
    DESCRIPTION
        "Cisco UCS fabric:DceSwSrvPcEp:operState managed object property"
    ::= { cucsFabricDceSwSrvPcEpEntry 24 }

cucsFabricDceSwSrvPcEpOperStateReason OBJECT-TYPE
    SYNTAX       SnmpAdminString
    MAX-ACCESS   read-only
    STATUS       current
    DESCRIPTION
        "Cisco UCS fabric:DceSwSrvPcEp:operStateReason
        managed object property"
    ::= { cucsFabricDceSwSrvPcEpEntry 25 }

cucsFabricDceSwSrvPcEpUsrLbl OBJECT-TYPE
    SYNTAX       SnmpAdminString
    MAX-ACCESS   read-only
    STATUS       current
    DESCRIPTION
        "Cisco UCS fabric:DceSwSrvPcEp:usrLbl managed object property"
    ::= { cucsFabricDceSwSrvPcEpEntry 26 }

cucsFabricDceSwSrvPcEpAggrPortId OBJECT-TYPE
    SYNTAX       Gauge32
    MAX-ACCESS   read-only
    STATUS       current
    DESCRIPTION
        "Cisco UCS fabric:DceSwSrvPcEp:aggrPortId managed object property"
    ::= { cucsFabricDceSwSrvPcEpEntry 27 }

cucsFabricDceSwSrvPcEpPeerAggrPortId OBJECT-TYPE
    SYNTAX       Gauge32
    MAX-ACCESS   read-only
    STATUS       current
    DESCRIPTION
        "Cisco UCS fabric:DceSwSrvPcEp:peerAggrPortId managed
        object property"
    ::= { cucsFabricDceSwSrvPcEpEntry 28 }

cucsFabricDceSwSrvPcEpAutoNegotiate OBJECT-TYPE
    SYNTAX       TruthValue
    MAX-ACCESS   read-only
    STATUS       current
    DESCRIPTION
        "Cisco UCS fabric:DceSwSrvPcEp:autoNegotiate managed
        object property"
    ::= { cucsFabricDceSwSrvPcEpEntry 29 }

cucsFabricEpTable OBJECT-TYPE
    SYNTAX           SEQUENCE OF CucsFabricEpEntry
    MAX-ACCESS       not-accessible
    STATUS           current
    DESCRIPTION
        "Cisco UCS fabric:Ep managed object table"
    ::= { cucsFabricObjects 8 }

cucsFabricEpEntry OBJECT-TYPE
    SYNTAX           CucsFabricEpEntry
    MAX-ACCESS       not-accessible
    STATUS           current
    DESCRIPTION
        "Entry for the cucsFabricEpTable table."
    INDEX { cucsFabricEpInstanceId }
    ::= { cucsFabricEpTable 1 }

CucsFabricEpEntry ::= SEQUENCE {
    cucsFabricEpInstanceId                                           CucsManagedObjectId,
    cucsFabricEpDn                                                   CucsManagedObjectDn,
    cucsFabricEpRn                                                   SnmpAdminString
}

cucsFabricEpInstanceId OBJECT-TYPE
    SYNTAX       CucsManagedObjectId
    MAX-ACCESS   not-accessible
    STATUS       current
    DESCRIPTION
        "Instance identifier of the managed object."
    ::= { cucsFabricEpEntry 1 }

cucsFabricEpDn OBJECT-TYPE
    SYNTAX       CucsManagedObjectDn
    MAX-ACCESS   read-only
    STATUS       current
    DESCRIPTION
        "Cisco UCS fabric:Ep:dn managed object property"
    ::= { cucsFabricEpEntry 2 }

cucsFabricEpRn OBJECT-TYPE
    SYNTAX       SnmpAdminString
    MAX-ACCESS   read-only
    STATUS       current
    DESCRIPTION
        "Cisco UCS fabric:Ep:rn managed object property"
    ::= { cucsFabricEpEntry 3 }

cucsFabricEpMgrTable OBJECT-TYPE
    SYNTAX           SEQUENCE OF CucsFabricEpMgrEntry
    MAX-ACCESS       not-accessible
    STATUS           current
    DESCRIPTION
        "Cisco UCS fabric:EpMgr managed object table"
    ::= { cucsFabricObjects 72 }

cucsFabricEpMgrEntry OBJECT-TYPE
    SYNTAX           CucsFabricEpMgrEntry
    MAX-ACCESS       not-accessible
    STATUS           current
    DESCRIPTION
        "Entry for the cucsFabricEpMgrTable table."
    INDEX { cucsFabricEpMgrInstanceId }
    ::= { cucsFabricEpMgrTable 1 }

CucsFabricEpMgrEntry ::= SEQUENCE {
    cucsFabricEpMgrInstanceId                                        CucsManagedObjectId,
    cucsFabricEpMgrDn                                                CucsManagedObjectDn,
    cucsFabricEpMgrRn                                                SnmpAdminString,
    cucsFabricEpMgrConfMode                                          CucsFabricConfMode,
    cucsFabricEpMgrFltAggr                                           Unsigned64,
    cucsFabricEpMgrFsmDescr                                          SnmpAdminString,
    cucsFabricEpMgrFsmFlags                                          SnmpAdminString,
    cucsFabricEpMgrFsmPrev                                           SnmpAdminString,
    cucsFabricEpMgrFsmProgr                                          Gauge32,
    cucsFabricEpMgrFsmRmtInvErrCode                                  Gauge32,
    cucsFabricEpMgrFsmRmtInvErrDescr                                 SnmpAdminString,
    cucsFabricEpMgrFsmRmtInvRslt                                     CucsConditionRemoteInvRslt,
    cucsFabricEpMgrFsmStageDescr                                     SnmpAdminString,
    cucsFabricEpMgrFsmStamp                                          DateAndTime,
    cucsFabricEpMgrFsmStatus                                         SnmpAdminString,
    cucsFabricEpMgrFsmTry                                            Gauge32,
    cucsFabricEpMgrId                                                CucsNetworkSwitchId,
    cucsFabricEpMgrConfQual                                          SnmpAdminString,
    cucsFabricEpMgrConfState                                         CucsFabricConfState
}

cucsFabricEpMgrInstanceId OBJECT-TYPE
    SYNTAX       CucsManagedObjectId
    MAX-ACCESS   not-accessible
    STATUS       current
    DESCRIPTION
        "Instance identifier of the managed object."
    ::= { cucsFabricEpMgrEntry 1 }

cucsFabricEpMgrDn OBJECT-TYPE
    SYNTAX       CucsManagedObjectDn
    MAX-ACCESS   read-only
    STATUS       current
    DESCRIPTION
        "Cisco UCS fabric:EpMgr:dn managed object property"
    ::= { cucsFabricEpMgrEntry 2 }

cucsFabricEpMgrRn OBJECT-TYPE
    SYNTAX       SnmpAdminString
    MAX-ACCESS   read-only
    STATUS       current
    DESCRIPTION
        "Cisco UCS fabric:EpMgr:rn managed object property"
    ::= { cucsFabricEpMgrEntry 3 }

cucsFabricEpMgrConfMode OBJECT-TYPE
    SYNTAX       CucsFabricConfMode
    MAX-ACCESS   read-only
    STATUS       current
    DESCRIPTION
        "Cisco UCS fabric:EpMgr:confMode managed object property"
    ::= { cucsFabricEpMgrEntry 5 }

cucsFabricEpMgrFltAggr OBJECT-TYPE
    SYNTAX       Unsigned64
    MAX-ACCESS   read-only
    STATUS       current
    DESCRIPTION
        "Cisco UCS fabric:EpMgr:fltAggr managed object property"
    ::= { cucsFabricEpMgrEntry 6 }

cucsFabricEpMgrFsmDescr OBJECT-TYPE
    SYNTAX       SnmpAdminString
    MAX-ACCESS   read-only
    STATUS       current
    DESCRIPTION
        "Cisco UCS fabric:EpMgr:fsmDescr managed object property"
    ::= { cucsFabricEpMgrEntry 7 }

cucsFabricEpMgrFsmFlags OBJECT-TYPE
    SYNTAX       SnmpAdminString
    MAX-ACCESS   read-only
    STATUS       current
    DESCRIPTION
        "Cisco UCS fabric:EpMgr:fsmFlags managed object property"
    ::= { cucsFabricEpMgrEntry 8 }

cucsFabricEpMgrFsmPrev OBJECT-TYPE
    SYNTAX       SnmpAdminString
    MAX-ACCESS   read-only
    STATUS       current
    DESCRIPTION
        "Cisco UCS fabric:EpMgr:fsmPrev managed object property"
    ::= { cucsFabricEpMgrEntry 9 }

cucsFabricEpMgrFsmProgr OBJECT-TYPE
    SYNTAX       Gauge32
    MAX-ACCESS   read-only
    STATUS       current
    DESCRIPTION
        "Cisco UCS fabric:EpMgr:fsmProgr managed object property"
    ::= { cucsFabricEpMgrEntry 10 }

cucsFabricEpMgrFsmRmtInvErrCode OBJECT-TYPE
    SYNTAX       Gauge32
    MAX-ACCESS   read-only
    STATUS       current
    DESCRIPTION
        "Cisco UCS fabric:EpMgr:fsmRmtInvErrCode managed object property"
    ::= { cucsFabricEpMgrEntry 11 }

cucsFabricEpMgrFsmRmtInvErrDescr OBJECT-TYPE
    SYNTAX       SnmpAdminString
    MAX-ACCESS   read-only
    STATUS       current
    DESCRIPTION
        "Cisco UCS fabric:EpMgr:fsmRmtInvErrDescr managed object property"
    ::= { cucsFabricEpMgrEntry 12 }

cucsFabricEpMgrFsmRmtInvRslt OBJECT-TYPE
    SYNTAX       CucsConditionRemoteInvRslt
    MAX-ACCESS   read-only
    STATUS       current
    DESCRIPTION
        "Cisco UCS fabric:EpMgr:fsmRmtInvRslt managed object property"
    ::= { cucsFabricEpMgrEntry 13 }

cucsFabricEpMgrFsmStageDescr OBJECT-TYPE
    SYNTAX       SnmpAdminString
    MAX-ACCESS   read-only
    STATUS       current
    DESCRIPTION
        "Cisco UCS fabric:EpMgr:fsmStageDescr managed object property"
    ::= { cucsFabricEpMgrEntry 14 }

cucsFabricEpMgrFsmStamp OBJECT-TYPE
    SYNTAX       DateAndTime
    MAX-ACCESS   read-only
    STATUS       current
    DESCRIPTION
        "Cisco UCS fabric:EpMgr:fsmStamp managed object property"
    ::= { cucsFabricEpMgrEntry 15 }

cucsFabricEpMgrFsmStatus OBJECT-TYPE
    SYNTAX       SnmpAdminString
    MAX-ACCESS   read-only
    STATUS       current
    DESCRIPTION
        "Cisco UCS fabric:EpMgr:fsmStatus managed object property"
    ::= { cucsFabricEpMgrEntry 16 }

cucsFabricEpMgrFsmTry OBJECT-TYPE
    SYNTAX       Gauge32
    MAX-ACCESS   read-only
    STATUS       current
    DESCRIPTION
        "Cisco UCS fabric:EpMgr:fsmTry managed object property"
    ::= { cucsFabricEpMgrEntry 17 }

cucsFabricEpMgrId OBJECT-TYPE
    SYNTAX       CucsNetworkSwitchId
    MAX-ACCESS   read-only
    STATUS       current
    DESCRIPTION
        "Cisco UCS fabric:EpMgr:id managed object property"
    ::= { cucsFabricEpMgrEntry 18 }

cucsFabricEpMgrConfQual OBJECT-TYPE
    SYNTAX       SnmpAdminString
    MAX-ACCESS   read-only
    STATUS       current
    DESCRIPTION
        "Cisco UCS fabric:EpMgr:confQual managed object property"
    ::= { cucsFabricEpMgrEntry 19 }

cucsFabricEpMgrConfState OBJECT-TYPE
    SYNTAX       CucsFabricConfState
    MAX-ACCESS   read-only
    STATUS       current
    DESCRIPTION
        "Cisco UCS fabric:EpMgr:confState managed object property"
    ::= { cucsFabricEpMgrEntry 20 }

cucsFabricEpMgrFsmTable OBJECT-TYPE
    SYNTAX           SEQUENCE OF CucsFabricEpMgrFsmEntry
    MAX-ACCESS       not-accessible
    STATUS           current
    DESCRIPTION
        "Cisco UCS fabric:EpMgrFsm managed object table"
    ::= { cucsFabricObjects 76 }

cucsFabricEpMgrFsmEntry OBJECT-TYPE
    SYNTAX           CucsFabricEpMgrFsmEntry
    MAX-ACCESS       not-accessible
    STATUS           current
    DESCRIPTION
        "Entry for the cucsFabricEpMgrFsmTable table."
    INDEX { cucsFabricEpMgrFsmInstanceId }
    ::= { cucsFabricEpMgrFsmTable 1 }

CucsFabricEpMgrFsmEntry ::= SEQUENCE {
    cucsFabricEpMgrFsmInstanceId                                     CucsManagedObjectId,
    cucsFabricEpMgrFsmDn                                             CucsManagedObjectDn,
    cucsFabricEpMgrFsmRn                                             SnmpAdminString,
    cucsFabricEpMgrFsmCompletionTime                                 DateAndTime,
    cucsFabricEpMgrFsmCurrentFsm                                     CucsFabricEpMgrFsmCurrentFsm,
    cucsFabricEpMgrFsmDescrData                                      SnmpAdminString,
    cucsFabricEpMgrFsmFsmStatus                                      CucsFsmFsmStageStatus,
    cucsFabricEpMgrFsmProgress                                       Gauge32,
    cucsFabricEpMgrFsmRmtErrCode                                     Gauge32,
    cucsFabricEpMgrFsmRmtErrDescr                                    SnmpAdminString,
    cucsFabricEpMgrFsmRmtRslt                                        CucsConditionRemoteInvRslt
}

cucsFabricEpMgrFsmInstanceId OBJECT-TYPE
    SYNTAX       CucsManagedObjectId
    MAX-ACCESS   not-accessible
    STATUS       current
    DESCRIPTION
        "Instance identifier of the managed object."
    ::= { cucsFabricEpMgrFsmEntry 1 }

cucsFabricEpMgrFsmDn OBJECT-TYPE
    SYNTAX       CucsManagedObjectDn
    MAX-ACCESS   read-only
    STATUS       current
    DESCRIPTION
        "Cisco UCS fabric:EpMgrFsm:dn managed object property"
    ::= { cucsFabricEpMgrFsmEntry 2 }

cucsFabricEpMgrFsmRn OBJECT-TYPE
    SYNTAX       SnmpAdminString
    MAX-ACCESS   read-only
    STATUS       current
    DESCRIPTION
        "Cisco UCS fabric:EpMgrFsm:rn managed object property"
    ::= { cucsFabricEpMgrFsmEntry 3 }

cucsFabricEpMgrFsmCompletionTime OBJECT-TYPE
    SYNTAX       DateAndTime
    MAX-ACCESS   read-only
    STATUS       current
    DESCRIPTION
        "Cisco UCS fabric:EpMgrFsm:completionTime managed object property"
    ::= { cucsFabricEpMgrFsmEntry 4 }

cucsFabricEpMgrFsmCurrentFsm OBJECT-TYPE
    SYNTAX       CucsFabricEpMgrFsmCurrentFsm
    MAX-ACCESS   read-only
    STATUS       current
    DESCRIPTION
        "Cisco UCS fabric:EpMgrFsm:currentFsm managed object property"
    ::= { cucsFabricEpMgrFsmEntry 5 }

cucsFabricEpMgrFsmDescrData OBJECT-TYPE
    SYNTAX       SnmpAdminString
    MAX-ACCESS   read-only
    STATUS       current
    DESCRIPTION
        "Cisco UCS fabric:EpMgrFsm:descr managed object property"
    ::= { cucsFabricEpMgrFsmEntry 6 }

cucsFabricEpMgrFsmFsmStatus OBJECT-TYPE
    SYNTAX       CucsFsmFsmStageStatus
    MAX-ACCESS   read-only
    STATUS       current
    DESCRIPTION
        "Cisco UCS fabric:EpMgrFsm:fsmStatus managed object property"
    ::= { cucsFabricEpMgrFsmEntry 7 }

cucsFabricEpMgrFsmProgress OBJECT-TYPE
    SYNTAX       Gauge32
    MAX-ACCESS   read-only
    STATUS       current
    DESCRIPTION
        "Cisco UCS fabric:EpMgrFsm:progress managed object property"
    ::= { cucsFabricEpMgrFsmEntry 8 }

cucsFabricEpMgrFsmRmtErrCode OBJECT-TYPE
    SYNTAX       Gauge32
    MAX-ACCESS   read-only
    STATUS       current
    DESCRIPTION
        "Cisco UCS fabric:EpMgrFsm:rmtErrCode managed object property"
    ::= { cucsFabricEpMgrFsmEntry 9 }

cucsFabricEpMgrFsmRmtErrDescr OBJECT-TYPE
    SYNTAX       SnmpAdminString
    MAX-ACCESS   read-only
    STATUS       current
    DESCRIPTION
        "Cisco UCS fabric:EpMgrFsm:rmtErrDescr managed object property"
    ::= { cucsFabricEpMgrFsmEntry 10 }

cucsFabricEpMgrFsmRmtRslt OBJECT-TYPE
    SYNTAX       CucsConditionRemoteInvRslt
    MAX-ACCESS   read-only
    STATUS       current
    DESCRIPTION
        "Cisco UCS fabric:EpMgrFsm:rmtRslt managed object property"
    ::= { cucsFabricEpMgrFsmEntry 11 }

cucsFabricEpMgrFsmStageTable OBJECT-TYPE
    SYNTAX           SEQUENCE OF CucsFabricEpMgrFsmStageEntry
    MAX-ACCESS       not-accessible
    STATUS           current
    DESCRIPTION
        "Cisco UCS fabric:EpMgrFsmStage managed object table"
    ::= { cucsFabricObjects 77 }

cucsFabricEpMgrFsmStageEntry OBJECT-TYPE
    SYNTAX           CucsFabricEpMgrFsmStageEntry
    MAX-ACCESS       not-accessible
    STATUS           current
    DESCRIPTION
        "Entry for the cucsFabricEpMgrFsmStageTable table."
    INDEX { cucsFabricEpMgrFsmStageInstanceId }
    ::= { cucsFabricEpMgrFsmStageTable 1 }

CucsFabricEpMgrFsmStageEntry ::= SEQUENCE {
    cucsFabricEpMgrFsmStageInstanceId                                CucsManagedObjectId,
    cucsFabricEpMgrFsmStageDn                                        CucsManagedObjectDn,
    cucsFabricEpMgrFsmStageRn                                        SnmpAdminString,
    cucsFabricEpMgrFsmStageDescrData                                 SnmpAdminString,
    cucsFabricEpMgrFsmStageLastUpdateTime                            DateAndTime,
    cucsFabricEpMgrFsmStageName                                      CucsFabricEpMgrFsmStageName,
    cucsFabricEpMgrFsmStageOrder                                     Gauge32,
    cucsFabricEpMgrFsmStageRetry                                     Gauge32,
    cucsFabricEpMgrFsmStageStageStatus                               CucsFsmFsmStageStatus
}

cucsFabricEpMgrFsmStageInstanceId OBJECT-TYPE
    SYNTAX       CucsManagedObjectId
    MAX-ACCESS   not-accessible
    STATUS       current
    DESCRIPTION
        "Instance identifier of the managed object."
    ::= { cucsFabricEpMgrFsmStageEntry 1 }

cucsFabricEpMgrFsmStageDn OBJECT-TYPE
    SYNTAX       CucsManagedObjectDn
    MAX-ACCESS   read-only
    STATUS       current
    DESCRIPTION
        "Cisco UCS fabric:EpMgrFsmStage:dn managed object property"
    ::= { cucsFabricEpMgrFsmStageEntry 2 }

cucsFabricEpMgrFsmStageRn OBJECT-TYPE
    SYNTAX       SnmpAdminString
    MAX-ACCESS   read-only
    STATUS       current
    DESCRIPTION
        "Cisco UCS fabric:EpMgrFsmStage:rn managed object property"
    ::= { cucsFabricEpMgrFsmStageEntry 3 }

cucsFabricEpMgrFsmStageDescrData OBJECT-TYPE
    SYNTAX       SnmpAdminString
    MAX-ACCESS   read-only
    STATUS       current
    DESCRIPTION
        "Cisco UCS fabric:EpMgrFsmStage:descr managed object property"
    ::= { cucsFabricEpMgrFsmStageEntry 4 }

cucsFabricEpMgrFsmStageLastUpdateTime OBJECT-TYPE
    SYNTAX       DateAndTime
    MAX-ACCESS   read-only
    STATUS       current
    DESCRIPTION
        "Cisco UCS fabric:EpMgrFsmStage:lastUpdateTime
        managed object property"
    ::= { cucsFabricEpMgrFsmStageEntry 5 }

cucsFabricEpMgrFsmStageName OBJECT-TYPE
    SYNTAX       CucsFabricEpMgrFsmStageName
    MAX-ACCESS   read-only
    STATUS       current
    DESCRIPTION
        "Cisco UCS fabric:EpMgrFsmStage:name managed object property"
    ::= { cucsFabricEpMgrFsmStageEntry 6 }

cucsFabricEpMgrFsmStageOrder OBJECT-TYPE
    SYNTAX       Gauge32
    MAX-ACCESS   read-only
    STATUS       current
    DESCRIPTION
        "Cisco UCS fabric:EpMgrFsmStage:order managed object property"
    ::= { cucsFabricEpMgrFsmStageEntry 7 }

cucsFabricEpMgrFsmStageRetry OBJECT-TYPE
    SYNTAX       Gauge32
    MAX-ACCESS   read-only
    STATUS       current
    DESCRIPTION
        "Cisco UCS fabric:EpMgrFsmStage:retry managed object property"
    ::= { cucsFabricEpMgrFsmStageEntry 8 }

cucsFabricEpMgrFsmStageStageStatus OBJECT-TYPE
    SYNTAX       CucsFsmFsmStageStatus
    MAX-ACCESS   read-only
    STATUS       current
    DESCRIPTION
        "Cisco UCS fabric:EpMgrFsmStage:stageStatus managed
        object property"
    ::= { cucsFabricEpMgrFsmStageEntry 9 }

cucsFabricEpMgrFsmTaskTable OBJECT-TYPE
    SYNTAX           SEQUENCE OF CucsFabricEpMgrFsmTaskEntry
    MAX-ACCESS       not-accessible
    STATUS           current
    DESCRIPTION
        "Cisco UCS fabric:EpMgrFsmTask managed object table"
    ::= { cucsFabricObjects 73 }

cucsFabricEpMgrFsmTaskEntry OBJECT-TYPE
    SYNTAX           CucsFabricEpMgrFsmTaskEntry
    MAX-ACCESS       not-accessible
    STATUS           current
    DESCRIPTION
        "Entry for the cucsFabricEpMgrFsmTaskTable table."
    INDEX { cucsFabricEpMgrFsmTaskInstanceId }
    ::= { cucsFabricEpMgrFsmTaskTable 1 }

CucsFabricEpMgrFsmTaskEntry ::= SEQUENCE {
    cucsFabricEpMgrFsmTaskInstanceId                                 CucsManagedObjectId,
    cucsFabricEpMgrFsmTaskDn                                         CucsManagedObjectDn,
    cucsFabricEpMgrFsmTaskRn                                         SnmpAdminString,
    cucsFabricEpMgrFsmTaskCompletion                                 CucsFsmCompletion,
    cucsFabricEpMgrFsmTaskFlags                                      CucsFabricEpMgrFsmTaskFlags,
    cucsFabricEpMgrFsmTaskItem                                       CucsFabricEpMgrFsmTaskItem,
    cucsFabricEpMgrFsmTaskSeqId                                      Gauge32
}

cucsFabricEpMgrFsmTaskInstanceId OBJECT-TYPE
    SYNTAX       CucsManagedObjectId
    MAX-ACCESS   not-accessible
    STATUS       current
    DESCRIPTION
        "Instance identifier of the managed object."
    ::= { cucsFabricEpMgrFsmTaskEntry 1 }

cucsFabricEpMgrFsmTaskDn OBJECT-TYPE
    SYNTAX       CucsManagedObjectDn
    MAX-ACCESS   read-only
    STATUS       current
    DESCRIPTION
        "Cisco UCS fabric:EpMgrFsmTask:dn managed object property"
    ::= { cucsFabricEpMgrFsmTaskEntry 2 }

cucsFabricEpMgrFsmTaskRn OBJECT-TYPE
    SYNTAX       SnmpAdminString
    MAX-ACCESS   read-only
    STATUS       current
    DESCRIPTION
        "Cisco UCS fabric:EpMgrFsmTask:rn managed object property"
    ::= { cucsFabricEpMgrFsmTaskEntry 3 }

cucsFabricEpMgrFsmTaskCompletion OBJECT-TYPE
    SYNTAX       CucsFsmCompletion
    MAX-ACCESS   read-only
    STATUS       current
    DESCRIPTION
        "Cisco UCS fabric:EpMgrFsmTask:completion managed object property"
    ::= { cucsFabricEpMgrFsmTaskEntry 4 }

cucsFabricEpMgrFsmTaskFlags OBJECT-TYPE
    SYNTAX       CucsFabricEpMgrFsmTaskFlags
    MAX-ACCESS   read-only
    STATUS       current
    DESCRIPTION
        "Cisco UCS fabric:EpMgrFsmTask:flags managed object property"
    ::= { cucsFabricEpMgrFsmTaskEntry 5 }

cucsFabricEpMgrFsmTaskItem OBJECT-TYPE
    SYNTAX       CucsFabricEpMgrFsmTaskItem
    MAX-ACCESS   read-only
    STATUS       current
    DESCRIPTION
        "Cisco UCS fabric:EpMgrFsmTask:item managed object property"
    ::= { cucsFabricEpMgrFsmTaskEntry 6 }

cucsFabricEpMgrFsmTaskSeqId OBJECT-TYPE
    SYNTAX       Gauge32
    MAX-ACCESS   read-only
    STATUS       current
    DESCRIPTION
        "Cisco UCS fabric:EpMgrFsmTask:seqId managed object property"
    ::= { cucsFabricEpMgrFsmTaskEntry 7 }

cucsFabricEthEstcTable OBJECT-TYPE
    SYNTAX           SEQUENCE OF CucsFabricEthEstcEntry
    MAX-ACCESS       not-accessible
    STATUS           current
    DESCRIPTION
        "Cisco UCS fabric:EthEstc managed object table"
    ::= { cucsFabricObjects 9 }

cucsFabricEthEstcEntry OBJECT-TYPE
    SYNTAX           CucsFabricEthEstcEntry
    MAX-ACCESS       not-accessible
    STATUS           current
    DESCRIPTION
        "Entry for the cucsFabricEthEstcTable table."
    INDEX { cucsFabricEthEstcInstanceId }
    ::= { cucsFabricEthEstcTable 1 }

CucsFabricEthEstcEntry ::= SEQUENCE {
    cucsFabricEthEstcInstanceId                                      CucsManagedObjectId,
    cucsFabricEthEstcDn                                              CucsManagedObjectDn,
    cucsFabricEthEstcRn                                              SnmpAdminString,
    cucsFabricEthEstcId                                              CucsNetworkSwitchId,
    cucsFabricEthEstcLocale                                          CucsFabricExternalLocale,
    cucsFabricEthEstcName                                            SnmpAdminString,
    cucsFabricEthEstcTransport                                       CucsFabricEthEstcTransport,
    cucsFabricEthEstcType                                            CucsFabricEthEstcType
}

cucsFabricEthEstcInstanceId OBJECT-TYPE
    SYNTAX       CucsManagedObjectId
    MAX-ACCESS   not-accessible
    STATUS       current
    DESCRIPTION
        "Instance identifier of the managed object."
    ::= { cucsFabricEthEstcEntry 1 }

cucsFabricEthEstcDn OBJECT-TYPE
    SYNTAX       CucsManagedObjectDn
    MAX-ACCESS   read-only
    STATUS       current
    DESCRIPTION
        "Cisco UCS fabric:EthEstc:dn managed object property"
    ::= { cucsFabricEthEstcEntry 2 }

cucsFabricEthEstcRn OBJECT-TYPE
    SYNTAX       SnmpAdminString
    MAX-ACCESS   read-only
    STATUS       current
    DESCRIPTION
        "Cisco UCS fabric:EthEstc:rn managed object property"
    ::= { cucsFabricEthEstcEntry 3 }

cucsFabricEthEstcId OBJECT-TYPE
    SYNTAX       CucsNetworkSwitchId
    MAX-ACCESS   read-only
    STATUS       current
    DESCRIPTION
        "Cisco UCS fabric:EthEstc:id managed object property"
    ::= { cucsFabricEthEstcEntry 4 }

cucsFabricEthEstcLocale OBJECT-TYPE
    SYNTAX       CucsFabricExternalLocale
    MAX-ACCESS   read-only
    STATUS       current
    DESCRIPTION
        "Cisco UCS fabric:EthEstc:locale managed object property"
    ::= { cucsFabricEthEstcEntry 5 }

cucsFabricEthEstcName OBJECT-TYPE
    SYNTAX       SnmpAdminString
    MAX-ACCESS   read-only
    STATUS       current
    DESCRIPTION
        "Cisco UCS fabric:EthEstc:name managed object property"
    ::= { cucsFabricEthEstcEntry 6 }

cucsFabricEthEstcTransport OBJECT-TYPE
    SYNTAX       CucsFabricEthEstcTransport
    MAX-ACCESS   read-only
    STATUS       current
    DESCRIPTION
        "Cisco UCS fabric:EthEstc:transport managed object property"
    ::= { cucsFabricEthEstcEntry 7 }

cucsFabricEthEstcType OBJECT-TYPE
    SYNTAX       CucsFabricEthEstcType
    MAX-ACCESS   read-only
    STATUS       current
    DESCRIPTION
        "Cisco UCS fabric:EthEstc:type managed object property"
    ::= { cucsFabricEthEstcEntry 8 }

cucsFabricEthEstcCloudTable OBJECT-TYPE
    SYNTAX           SEQUENCE OF CucsFabricEthEstcCloudEntry
    MAX-ACCESS       not-accessible
    STATUS           current
    DESCRIPTION
        "Cisco UCS fabric:EthEstcCloud managed object table"
    ::= { cucsFabricObjects 10 }

cucsFabricEthEstcCloudEntry OBJECT-TYPE
    SYNTAX           CucsFabricEthEstcCloudEntry
    MAX-ACCESS       not-accessible
    STATUS           current
    DESCRIPTION
        "Entry for the cucsFabricEthEstcCloudTable table."
    INDEX { cucsFabricEthEstcCloudInstanceId }
    ::= { cucsFabricEthEstcCloudTable 1 }

CucsFabricEthEstcCloudEntry ::= SEQUENCE {
    cucsFabricEthEstcCloudInstanceId                                 CucsManagedObjectId,
    cucsFabricEthEstcCloudDn                                         CucsManagedObjectDn,
    cucsFabricEthEstcCloudRn                                         SnmpAdminString
}

cucsFabricEthEstcCloudInstanceId OBJECT-TYPE
    SYNTAX       CucsManagedObjectId
    MAX-ACCESS   not-accessible
    STATUS       current
    DESCRIPTION
        "Instance identifier of the managed object."
    ::= { cucsFabricEthEstcCloudEntry 1 }

cucsFabricEthEstcCloudDn OBJECT-TYPE
    SYNTAX       CucsManagedObjectDn
    MAX-ACCESS   read-only
    STATUS       current
    DESCRIPTION
        "Cisco UCS fabric:EthEstcCloud:dn managed object property"
    ::= { cucsFabricEthEstcCloudEntry 2 }

cucsFabricEthEstcCloudRn OBJECT-TYPE
    SYNTAX       SnmpAdminString
    MAX-ACCESS   read-only
    STATUS       current
    DESCRIPTION
        "Cisco UCS fabric:EthEstcCloud:rn managed object property"
    ::= { cucsFabricEthEstcCloudEntry 3 }

cucsFabricEthEstcEpTable OBJECT-TYPE
    SYNTAX           SEQUENCE OF CucsFabricEthEstcEpEntry
    MAX-ACCESS       not-accessible
    STATUS           current
    DESCRIPTION
        "Cisco UCS fabric:EthEstcEp managed object table"
    ::= { cucsFabricObjects 11 }

cucsFabricEthEstcEpEntry OBJECT-TYPE
    SYNTAX           CucsFabricEthEstcEpEntry
    MAX-ACCESS       not-accessible
    STATUS           current
    DESCRIPTION
        "Entry for the cucsFabricEthEstcEpTable table."
    INDEX { cucsFabricEthEstcEpInstanceId }
    ::= { cucsFabricEthEstcEpTable 1 }

CucsFabricEthEstcEpEntry ::= SEQUENCE {
    cucsFabricEthEstcEpInstanceId                                    CucsManagedObjectId,
    cucsFabricEthEstcEpDn                                            CucsManagedObjectDn,
    cucsFabricEthEstcEpRn                                            SnmpAdminString,
    cucsFabricEthEstcEpAdminState                                    CucsFabricExternalEpAdminState,
    cucsFabricEthEstcEpChassisId                                     Gauge32,
    cucsFabricEthEstcEpConfigState                                   CucsFabricConfigState,
    cucsFabricEthEstcEpEpDn                                          SnmpAdminString,
    cucsFabricEthEstcEpIfRole                                        CucsFabricAEthEstcEpIfRole,
    cucsFabricEthEstcEpIfType                                        CucsFabricPIoEpIfType,
    cucsFabricEthEstcEpLicGP                                         Unsigned64,
    cucsFabricEthEstcEpLicState                                      CucsLicenseState,
    cucsFabricEthEstcEpLocale                                        CucsFabricExternalEpLocale,
    cucsFabricEthEstcEpName                                          SnmpAdminString,
    cucsFabricEthEstcEpPeerDn                                        SnmpAdminString,
    cucsFabricEthEstcEpPeerPortId                                    Gauge32,
    cucsFabricEthEstcEpPeerSlotId                                    Gauge32,
    cucsFabricEthEstcEpPinGroupName                                  SnmpAdminString,
    cucsFabricEthEstcEpPortId                                        CucsFabricEthEstcEpPortId,
    cucsFabricEthEstcEpPortMode                                      CucsFabricEthEstcPortMode,
    cucsFabricEthEstcEpPrio                                          CucsFabricEthEstcEpPrio,
    cucsFabricEthEstcEpSlotId                                        CucsFabricEthEstcEpSlotId,
    cucsFabricEthEstcEpSwitchId                                      CucsNetworkSwitchId,
    cucsFabricEthEstcEpTransport                                     CucsFabricEthEstcEpTransport,
    cucsFabricEthEstcEpType                                          CucsFabricEthEstcEpType,
    cucsFabricEthEstcEpUsrLbl                                        SnmpAdminString,
    cucsFabricEthEstcEpAdminSpeed                                    CucsPortEthSpeed,
    cucsFabricEthEstcEpPeerChassisId                                 Gauge32,
    cucsFabricEthEstcEpFltAggr                                       Unsigned64,
    cucsFabricEthEstcEpNwCtrlPolicyName                              SnmpAdminString,
    cucsFabricEthEstcEpOperNwCtrlPolicyName                          SnmpAdminString,
    cucsFabricEthEstcEpOperState                                     CucsFabricPIoEpOperState,
    cucsFabricEthEstcEpOperStateReason                               SnmpAdminString,
    cucsFabricEthEstcEpFlowCtrlPolicy                                SnmpAdminString,
    cucsFabricEthEstcEpWarnings                                      CucsFabricWarnings,
    cucsFabricEthEstcEpOperPortMode                                  CucsFabricEthEstcOperPortMode,
    cucsFabricEthEstcEpAggrPortId                                    Gauge32,
    cucsFabricEthEstcEpPeerAggrPortId                                Gauge32,
    cucsFabricEthEstcEpAutoNegotiate                                 TruthValue
}

cucsFabricEthEstcEpInstanceId OBJECT-TYPE
    SYNTAX       CucsManagedObjectId
    MAX-ACCESS   not-accessible
    STATUS       current
    DESCRIPTION
        "Instance identifier of the managed object."
    ::= { cucsFabricEthEstcEpEntry 1 }

cucsFabricEthEstcEpDn OBJECT-TYPE
    SYNTAX       CucsManagedObjectDn
    MAX-ACCESS   read-only
    STATUS       current
    DESCRIPTION
        "Cisco UCS fabric:EthEstcEp:dn managed object property"
    ::= { cucsFabricEthEstcEpEntry 2 }

cucsFabricEthEstcEpRn OBJECT-TYPE
    SYNTAX       SnmpAdminString
    MAX-ACCESS   read-only
    STATUS       current
    DESCRIPTION
        "Cisco UCS fabric:EthEstcEp:rn managed object property"
    ::= { cucsFabricEthEstcEpEntry 3 }

cucsFabricEthEstcEpAdminState OBJECT-TYPE
    SYNTAX       CucsFabricExternalEpAdminState
    MAX-ACCESS   read-only
    STATUS       current
    DESCRIPTION
        "Cisco UCS fabric:EthEstcEp:adminState managed object property"
    ::= { cucsFabricEthEstcEpEntry 4 }

cucsFabricEthEstcEpChassisId OBJECT-TYPE
    SYNTAX       Gauge32
    MAX-ACCESS   read-only
    STATUS       current
    DESCRIPTION
        "Cisco UCS fabric:EthEstcEp:chassisId managed object property"
    ::= { cucsFabricEthEstcEpEntry 5 }

cucsFabricEthEstcEpConfigState OBJECT-TYPE
    SYNTAX       CucsFabricConfigState
    MAX-ACCESS   read-only
    STATUS       current
    DESCRIPTION
        "Cisco UCS fabric:EthEstcEp:configState managed object property"
    ::= { cucsFabricEthEstcEpEntry 6 }

cucsFabricEthEstcEpEpDn OBJECT-TYPE
    SYNTAX       SnmpAdminString
    MAX-ACCESS   read-only
    STATUS       current
    DESCRIPTION
        "Cisco UCS fabric:EthEstcEp:epDn managed object property"
    ::= { cucsFabricEthEstcEpEntry 7 }

cucsFabricEthEstcEpIfRole OBJECT-TYPE
    SYNTAX       CucsFabricAEthEstcEpIfRole
    MAX-ACCESS   read-only
    STATUS       current
    DESCRIPTION
        "Cisco UCS fabric:EthEstcEp:ifRole managed object property"
    ::= { cucsFabricEthEstcEpEntry 8 }

cucsFabricEthEstcEpIfType OBJECT-TYPE
    SYNTAX       CucsFabricPIoEpIfType
    MAX-ACCESS   read-only
    STATUS       current
    DESCRIPTION
        "Cisco UCS fabric:EthEstcEp:ifType managed object property"
    ::= { cucsFabricEthEstcEpEntry 9 }

cucsFabricEthEstcEpLicGP OBJECT-TYPE
    SYNTAX       Unsigned64
    MAX-ACCESS   read-only
    STATUS       current
    DESCRIPTION
        "Cisco UCS fabric:EthEstcEp:licGP managed object property"
    ::= { cucsFabricEthEstcEpEntry 10 }

cucsFabricEthEstcEpLicState OBJECT-TYPE
    SYNTAX       CucsLicenseState
    MAX-ACCESS   read-only
    STATUS       current
    DESCRIPTION
        "Cisco UCS fabric:EthEstcEp:licState managed object property"
    ::= { cucsFabricEthEstcEpEntry 11 }

cucsFabricEthEstcEpLocale OBJECT-TYPE
    SYNTAX       CucsFabricExternalEpLocale
    MAX-ACCESS   read-only
    STATUS       current
    DESCRIPTION
        "Cisco UCS fabric:EthEstcEp:locale managed object property"
    ::= { cucsFabricEthEstcEpEntry 12 }

cucsFabricEthEstcEpName OBJECT-TYPE
    SYNTAX       SnmpAdminString
    MAX-ACCESS   read-only
    STATUS       current
    DESCRIPTION
        "Cisco UCS fabric:EthEstcEp:name managed object property"
    ::= { cucsFabricEthEstcEpEntry 13 }

cucsFabricEthEstcEpPeerDn OBJECT-TYPE
    SYNTAX       SnmpAdminString
    MAX-ACCESS   read-only
    STATUS       current
    DESCRIPTION
        "Cisco UCS fabric:EthEstcEp:peerDn managed object property"
    ::= { cucsFabricEthEstcEpEntry 14 }

cucsFabricEthEstcEpPeerPortId OBJECT-TYPE
    SYNTAX       Gauge32
    MAX-ACCESS   read-only
    STATUS       current
    DESCRIPTION
        "Cisco UCS fabric:EthEstcEp:peerPortId managed object property"
    ::= { cucsFabricEthEstcEpEntry 15 }

cucsFabricEthEstcEpPeerSlotId OBJECT-TYPE
    SYNTAX       Gauge32
    MAX-ACCESS   read-only
    STATUS       current
    DESCRIPTION
        "Cisco UCS fabric:EthEstcEp:peerSlotId managed object property"
    ::= { cucsFabricEthEstcEpEntry 16 }

cucsFabricEthEstcEpPinGroupName OBJECT-TYPE
    SYNTAX       SnmpAdminString
    MAX-ACCESS   read-only
    STATUS       current
    DESCRIPTION
        "Cisco UCS fabric:EthEstcEp:pinGroupName managed object property"
    ::= { cucsFabricEthEstcEpEntry 17 }

cucsFabricEthEstcEpPortId OBJECT-TYPE
    SYNTAX       CucsFabricEthEstcEpPortId
    MAX-ACCESS   read-only
    STATUS       current
    DESCRIPTION
        "Cisco UCS fabric:EthEstcEp:portId managed object property"
    ::= { cucsFabricEthEstcEpEntry 18 }

cucsFabricEthEstcEpPortMode OBJECT-TYPE
    SYNTAX       CucsFabricEthEstcPortMode
    MAX-ACCESS   read-only
    STATUS       current
    DESCRIPTION
        "Cisco UCS fabric:EthEstcEp:portMode managed object property"
    ::= { cucsFabricEthEstcEpEntry 19 }

cucsFabricEthEstcEpPrio OBJECT-TYPE
    SYNTAX       CucsFabricEthEstcEpPrio
    MAX-ACCESS   read-only
    STATUS       current
    DESCRIPTION
        "Cisco UCS fabric:EthEstcEp:prio managed object property"
    ::= { cucsFabricEthEstcEpEntry 20 }

cucsFabricEthEstcEpSlotId OBJECT-TYPE
    SYNTAX       CucsFabricEthEstcEpSlotId
    MAX-ACCESS   read-only
    STATUS       current
    DESCRIPTION
        "Cisco UCS fabric:EthEstcEp:slotId managed object property"
    ::= { cucsFabricEthEstcEpEntry 21 }

cucsFabricEthEstcEpSwitchId OBJECT-TYPE
    SYNTAX       CucsNetworkSwitchId
    MAX-ACCESS   read-only
    STATUS       current
    DESCRIPTION
        "Cisco UCS fabric:EthEstcEp:switchId managed object property"
    ::= { cucsFabricEthEstcEpEntry 22 }

cucsFabricEthEstcEpTransport OBJECT-TYPE
    SYNTAX       CucsFabricEthEstcEpTransport
    MAX-ACCESS   read-only
    STATUS       current
    DESCRIPTION
        "Cisco UCS fabric:EthEstcEp:transport managed object property"
    ::= { cucsFabricEthEstcEpEntry 23 }

cucsFabricEthEstcEpType OBJECT-TYPE
    SYNTAX       CucsFabricEthEstcEpType
    MAX-ACCESS   read-only
    STATUS       current
    DESCRIPTION
        "Cisco UCS fabric:EthEstcEp:type managed object property"
    ::= { cucsFabricEthEstcEpEntry 24 }

cucsFabricEthEstcEpUsrLbl OBJECT-TYPE
    SYNTAX       SnmpAdminString
    MAX-ACCESS   read-only
    STATUS       current
    DESCRIPTION
        "Cisco UCS fabric:EthEstcEp:usrLbl managed object property"
    ::= { cucsFabricEthEstcEpEntry 25 }

cucsFabricEthEstcEpAdminSpeed OBJECT-TYPE
    SYNTAX       CucsPortEthSpeed
    MAX-ACCESS   read-only
    STATUS       current
    DESCRIPTION
        "Cisco UCS fabric:EthEstcEp:adminSpeed managed object property"
    ::= { cucsFabricEthEstcEpEntry 26 }

cucsFabricEthEstcEpPeerChassisId OBJECT-TYPE
    SYNTAX       Gauge32
    MAX-ACCESS   read-only
    STATUS       current
    DESCRIPTION
        "Cisco UCS fabric:EthEstcEp:peerChassisId managed object property"
    ::= { cucsFabricEthEstcEpEntry 27 }

cucsFabricEthEstcEpFltAggr OBJECT-TYPE
    SYNTAX       Unsigned64
    MAX-ACCESS   read-only
    STATUS       current
    DESCRIPTION
        "Cisco UCS fabric:EthEstcEp:fltAggr managed object property"
    ::= { cucsFabricEthEstcEpEntry 28 }

cucsFabricEthEstcEpNwCtrlPolicyName OBJECT-TYPE
    SYNTAX       SnmpAdminString
    MAX-ACCESS   read-only
    STATUS       current
    DESCRIPTION
        "Cisco UCS fabric:EthEstcEp:nwCtrlPolicyName managed
        object property"
    ::= { cucsFabricEthEstcEpEntry 29 }

cucsFabricEthEstcEpOperNwCtrlPolicyName OBJECT-TYPE
    SYNTAX       SnmpAdminString
    MAX-ACCESS   read-only
    STATUS       current
    DESCRIPTION
        "Cisco UCS fabric:EthEstcEp:operNwCtrlPolicyName
        managed object property"
    ::= { cucsFabricEthEstcEpEntry 30 }

cucsFabricEthEstcEpOperState OBJECT-TYPE
    SYNTAX       CucsFabricPIoEpOperState
    MAX-ACCESS   read-only
    STATUS       current
    DESCRIPTION
        "Cisco UCS fabric:EthEstcEp:operState managed object property"
    ::= { cucsFabricEthEstcEpEntry 31 }

cucsFabricEthEstcEpOperStateReason OBJECT-TYPE
    SYNTAX       SnmpAdminString
    MAX-ACCESS   read-only
    STATUS       current
    DESCRIPTION
        "Cisco UCS fabric:EthEstcEp:operStateReason managed
        object property"
    ::= { cucsFabricEthEstcEpEntry 32 }

cucsFabricEthEstcEpFlowCtrlPolicy OBJECT-TYPE
    SYNTAX       SnmpAdminString
    MAX-ACCESS   read-only
    STATUS       current
    DESCRIPTION
        "Cisco UCS fabric:EthEstcEp:flowCtrlPolicy managed
        object property"
    ::= { cucsFabricEthEstcEpEntry 33 }

cucsFabricEthEstcEpWarnings OBJECT-TYPE
    SYNTAX       CucsFabricWarnings
    MAX-ACCESS   read-only
    STATUS       current
    DESCRIPTION
        "Cisco UCS fabric:EthEstcEp:warnings managed object property"
    ::= { cucsFabricEthEstcEpEntry 34 }

cucsFabricEthEstcEpOperPortMode OBJECT-TYPE
    SYNTAX       CucsFabricEthEstcOperPortMode
    MAX-ACCESS   read-only
    STATUS       current
    DESCRIPTION
        "Cisco UCS fabric:EthEstcEp:operPortMode managed object property"
    ::= { cucsFabricEthEstcEpEntry 35 }

cucsFabricEthEstcEpAggrPortId OBJECT-TYPE
    SYNTAX       Gauge32
    MAX-ACCESS   read-only
    STATUS       current
    DESCRIPTION
        "Cisco UCS fabric:EthEstcEp:aggrPortId managed object property"
    ::= { cucsFabricEthEstcEpEntry 36 }

cucsFabricEthEstcEpPeerAggrPortId OBJECT-TYPE
    SYNTAX       Gauge32
    MAX-ACCESS   read-only
    STATUS       current
    DESCRIPTION
        "Cisco UCS fabric:EthEstcEp:peerAggrPortId managed
        object property"
    ::= { cucsFabricEthEstcEpEntry 37 }

cucsFabricEthEstcEpAutoNegotiate OBJECT-TYPE
    SYNTAX       TruthValue
    MAX-ACCESS   read-only
    STATUS       current
    DESCRIPTION
        "Cisco UCS fabric:EthEstcEp:autoNegotiate managed object property"
    ::= { cucsFabricEthEstcEpEntry 38 }

cucsFabricEthEstcPcTable OBJECT-TYPE
    SYNTAX           SEQUENCE OF CucsFabricEthEstcPcEntry
    MAX-ACCESS       not-accessible
    STATUS           current
    DESCRIPTION
        "Cisco UCS fabric:EthEstcPc managed object table"
    ::= { cucsFabricObjects 67 }

cucsFabricEthEstcPcEntry OBJECT-TYPE
    SYNTAX           CucsFabricEthEstcPcEntry
    MAX-ACCESS       not-accessible
    STATUS           current
    DESCRIPTION
        "Entry for the cucsFabricEthEstcPcTable table."
    INDEX { cucsFabricEthEstcPcInstanceId }
    ::= { cucsFabricEthEstcPcTable 1 }

CucsFabricEthEstcPcEntry ::= SEQUENCE {
    cucsFabricEthEstcPcInstanceId                                    CucsManagedObjectId,
    cucsFabricEthEstcPcDn                                            CucsManagedObjectDn,
    cucsFabricEthEstcPcRn                                            SnmpAdminString,
    cucsFabricEthEstcPcAdminSpeed                                    CucsPortEthAdminSpeed,
    cucsFabricEthEstcPcAdminState                                    CucsFabricCIoEpAdminState,
    cucsFabricEthEstcPcEpDn                                          SnmpAdminString,
    cucsFabricEthEstcPcFltAggr                                       Unsigned64,
    cucsFabricEthEstcPcIfRole                                        CucsFabricEstcPcIfRole,
    cucsFabricEthEstcPcIfType                                        CucsFabricCIoEpIfType,
    cucsFabricEthEstcPcLocale                                        CucsFabricExternalPcLocale,
    cucsFabricEthEstcPcName                                          SnmpAdminString,
    cucsFabricEthEstcPcOperSpeed                                     CucsPortEthSpeed,
    cucsFabricEthEstcPcOperState                                     CucsNetworkPortOperState,
    cucsFabricEthEstcPcPeerDn                                        SnmpAdminString,
    cucsFabricEthEstcPcPinGroupName                                  SnmpAdminString,
    cucsFabricEthEstcPcPortId                                        Gauge32,
    cucsFabricEthEstcPcPortMode                                      CucsFabricEthEstcPortMode,
    cucsFabricEthEstcPcPrio                                          CucsQosPriority,
    cucsFabricEthEstcPcStateQual                                     SnmpAdminString,
    cucsFabricEthEstcPcSwitchId                                      CucsNetworkSwitchId,
    cucsFabricEthEstcPcTransport                                     CucsFabricEthEstcPcTransport,
    cucsFabricEthEstcPcType                                          CucsFabricEstcPcType,
    cucsFabricEthEstcPcNwCtrlPolicyName                              SnmpAdminString,
    cucsFabricEthEstcPcOperNwCtrlPolicyName                          SnmpAdminString,
    cucsFabricEthEstcPcProtocol                                      CucsFabricEthPcProtocol,
    cucsFabricEthEstcPcFlowCtrlPolicy                                SnmpAdminString,
    cucsFabricEthEstcPcWarnings                                      CucsFabricWarnings,
    cucsFabricEthEstcPcDescr                                         SnmpAdminString,
    cucsFabricEthEstcPcLacpPolicyName                                SnmpAdminString,
    cucsFabricEthEstcPcOperLacpPolicyName                            SnmpAdminString
}

cucsFabricEthEstcPcInstanceId OBJECT-TYPE
    SYNTAX       CucsManagedObjectId
    MAX-ACCESS   not-accessible
    STATUS       current
    DESCRIPTION
        "Instance identifier of the managed object."
    ::= { cucsFabricEthEstcPcEntry 1 }

cucsFabricEthEstcPcDn OBJECT-TYPE
    SYNTAX       CucsManagedObjectDn
    MAX-ACCESS   read-only
    STATUS       current
    DESCRIPTION
        "Cisco UCS fabric:EthEstcPc:dn managed object property"
    ::= { cucsFabricEthEstcPcEntry 2 }

cucsFabricEthEstcPcRn OBJECT-TYPE
    SYNTAX       SnmpAdminString
    MAX-ACCESS   read-only
    STATUS       current
    DESCRIPTION
        "Cisco UCS fabric:EthEstcPc:rn managed object property"
    ::= { cucsFabricEthEstcPcEntry 3 }

cucsFabricEthEstcPcAdminSpeed OBJECT-TYPE
    SYNTAX       CucsPortEthAdminSpeed
    MAX-ACCESS   read-only
    STATUS       current
    DESCRIPTION
        "Cisco UCS fabric:EthEstcPc:adminSpeed managed object property"
    ::= { cucsFabricEthEstcPcEntry 4 }

cucsFabricEthEstcPcAdminState OBJECT-TYPE
    SYNTAX       CucsFabricCIoEpAdminState
    MAX-ACCESS   read-only
    STATUS       current
    DESCRIPTION
        "Cisco UCS fabric:EthEstcPc:adminState managed object property"
    ::= { cucsFabricEthEstcPcEntry 5 }

cucsFabricEthEstcPcEpDn OBJECT-TYPE
    SYNTAX       SnmpAdminString
    MAX-ACCESS   read-only
    STATUS       current
    DESCRIPTION
        "Cisco UCS fabric:EthEstcPc:epDn managed object property"
    ::= { cucsFabricEthEstcPcEntry 6 }

cucsFabricEthEstcPcFltAggr OBJECT-TYPE
    SYNTAX       Unsigned64
    MAX-ACCESS   read-only
    STATUS       current
    DESCRIPTION
        "Cisco UCS fabric:EthEstcPc:fltAggr managed object property"
    ::= { cucsFabricEthEstcPcEntry 7 }

cucsFabricEthEstcPcIfRole OBJECT-TYPE
    SYNTAX       CucsFabricEstcPcIfRole
    MAX-ACCESS   read-only
    STATUS       current
    DESCRIPTION
        "Cisco UCS fabric:EthEstcPc:ifRole managed object property"
    ::= { cucsFabricEthEstcPcEntry 8 }

cucsFabricEthEstcPcIfType OBJECT-TYPE
    SYNTAX       CucsFabricCIoEpIfType
    MAX-ACCESS   read-only
    STATUS       current
    DESCRIPTION
        "Cisco UCS fabric:EthEstcPc:ifType managed object property"
    ::= { cucsFabricEthEstcPcEntry 9 }

cucsFabricEthEstcPcLocale OBJECT-TYPE
    SYNTAX       CucsFabricExternalPcLocale
    MAX-ACCESS   read-only
    STATUS       current
    DESCRIPTION
        "Cisco UCS fabric:EthEstcPc:locale managed object property"
    ::= { cucsFabricEthEstcPcEntry 10 }

cucsFabricEthEstcPcName OBJECT-TYPE
    SYNTAX       SnmpAdminString
    MAX-ACCESS   read-only
    STATUS       current
    DESCRIPTION
        "Cisco UCS fabric:EthEstcPc:name managed object property"
    ::= { cucsFabricEthEstcPcEntry 11 }

cucsFabricEthEstcPcOperSpeed OBJECT-TYPE
    SYNTAX       CucsPortEthSpeed
    MAX-ACCESS   read-only
    STATUS       current
    DESCRIPTION
        "Cisco UCS fabric:EthEstcPc:operSpeed managed object property"
    ::= { cucsFabricEthEstcPcEntry 12 }

cucsFabricEthEstcPcOperState OBJECT-TYPE
    SYNTAX       CucsNetworkPortOperState
    MAX-ACCESS   read-only
    STATUS       current
    DESCRIPTION
        "Cisco UCS fabric:EthEstcPc:operState managed object property"
    ::= { cucsFabricEthEstcPcEntry 13 }

cucsFabricEthEstcPcPeerDn OBJECT-TYPE
    SYNTAX       SnmpAdminString
    MAX-ACCESS   read-only
    STATUS       current
    DESCRIPTION
        "Cisco UCS fabric:EthEstcPc:peerDn managed object property"
    ::= { cucsFabricEthEstcPcEntry 14 }

cucsFabricEthEstcPcPinGroupName OBJECT-TYPE
    SYNTAX       SnmpAdminString
    MAX-ACCESS   read-only
    STATUS       current
    DESCRIPTION
        "Cisco UCS fabric:EthEstcPc:pinGroupName managed object property"
    ::= { cucsFabricEthEstcPcEntry 15 }

cucsFabricEthEstcPcPortId OBJECT-TYPE
    SYNTAX       Gauge32
    MAX-ACCESS   read-only
    STATUS       current
    DESCRIPTION
        "Cisco UCS fabric:EthEstcPc:portId managed object property"
    ::= { cucsFabricEthEstcPcEntry 16 }

cucsFabricEthEstcPcPortMode OBJECT-TYPE
    SYNTAX       CucsFabricEthEstcPortMode
    MAX-ACCESS   read-only
    STATUS       current
    DESCRIPTION
        "Cisco UCS fabric:EthEstcPc:portMode managed object property"
    ::= { cucsFabricEthEstcPcEntry 17 }

cucsFabricEthEstcPcPrio OBJECT-TYPE
    SYNTAX       CucsQosPriority
    MAX-ACCESS   read-only
    STATUS       current
    DESCRIPTION
        "Cisco UCS fabric:EthEstcPc:prio managed object property"
    ::= { cucsFabricEthEstcPcEntry 18 }

cucsFabricEthEstcPcStateQual OBJECT-TYPE
    SYNTAX       SnmpAdminString
    MAX-ACCESS   read-only
    STATUS       current
    DESCRIPTION
        "Cisco UCS fabric:EthEstcPc:stateQual managed object property"
    ::= { cucsFabricEthEstcPcEntry 19 }

cucsFabricEthEstcPcSwitchId OBJECT-TYPE
    SYNTAX       CucsNetworkSwitchId
    MAX-ACCESS   read-only
    STATUS       current
    DESCRIPTION
        "Cisco UCS fabric:EthEstcPc:switchId managed object property"
    ::= { cucsFabricEthEstcPcEntry 20 }

cucsFabricEthEstcPcTransport OBJECT-TYPE
    SYNTAX       CucsFabricEthEstcPcTransport
    MAX-ACCESS   read-only
    STATUS       current
    DESCRIPTION
        "Cisco UCS fabric:EthEstcPc:transport managed object property"
    ::= { cucsFabricEthEstcPcEntry 21 }

cucsFabricEthEstcPcType OBJECT-TYPE
    SYNTAX       CucsFabricEstcPcType
    MAX-ACCESS   read-only
    STATUS       current
    DESCRIPTION
        "Cisco UCS fabric:EthEstcPc:type managed object property"
    ::= { cucsFabricEthEstcPcEntry 22 }

cucsFabricEthEstcPcNwCtrlPolicyName OBJECT-TYPE
    SYNTAX       SnmpAdminString
    MAX-ACCESS   read-only
    STATUS       current
    DESCRIPTION
        "Cisco UCS fabric:EthEstcPc:nwCtrlPolicyName managed
        object property"
    ::= { cucsFabricEthEstcPcEntry 23 }

cucsFabricEthEstcPcOperNwCtrlPolicyName OBJECT-TYPE
    SYNTAX       SnmpAdminString
    MAX-ACCESS   read-only
    STATUS       current
    DESCRIPTION
        "Cisco UCS fabric:EthEstcPc:operNwCtrlPolicyName
        managed object property"
    ::= { cucsFabricEthEstcPcEntry 24 }

cucsFabricEthEstcPcProtocol OBJECT-TYPE
    SYNTAX       CucsFabricEthPcProtocol
    MAX-ACCESS   read-only
    STATUS       current
    DESCRIPTION
        "Cisco UCS fabric:EthEstcPc:protocol managed object property"
    ::= { cucsFabricEthEstcPcEntry 25 }

cucsFabricEthEstcPcFlowCtrlPolicy OBJECT-TYPE
    SYNTAX       SnmpAdminString
    MAX-ACCESS   read-only
    STATUS       current
    DESCRIPTION
        "Cisco UCS fabric:EthEstcPc:flowCtrlPolicy managed
        object property"
    ::= { cucsFabricEthEstcPcEntry 26 }

cucsFabricEthEstcPcWarnings OBJECT-TYPE
    SYNTAX       CucsFabricWarnings
    MAX-ACCESS   read-only
    STATUS       current
    DESCRIPTION
        "Cisco UCS fabric:EthEstcPc:warnings managed object property"
    ::= { cucsFabricEthEstcPcEntry 27 }

cucsFabricEthEstcPcDescr OBJECT-TYPE
    SYNTAX       SnmpAdminString
    MAX-ACCESS   read-only
    STATUS       current
    DESCRIPTION
        "Cisco UCS fabric:EthEstcPc:descr managed object property"
    ::= { cucsFabricEthEstcPcEntry 28 }

cucsFabricEthEstcPcLacpPolicyName OBJECT-TYPE
    SYNTAX       SnmpAdminString
    MAX-ACCESS   read-only
    STATUS       current
    DESCRIPTION
        "Cisco UCS fabric:EthEstcPc:lacpPolicyName managed
        object property"
    ::= { cucsFabricEthEstcPcEntry 29 }

cucsFabricEthEstcPcOperLacpPolicyName OBJECT-TYPE
    SYNTAX       SnmpAdminString
    MAX-ACCESS   read-only
    STATUS       current
    DESCRIPTION
        "Cisco UCS fabric:EthEstcPc:operLacpPolicyName
        managed object property"
    ::= { cucsFabricEthEstcPcEntry 30 }

cucsFabricEthEstcPcEpTable OBJECT-TYPE
    SYNTAX           SEQUENCE OF CucsFabricEthEstcPcEpEntry
    MAX-ACCESS       not-accessible
    STATUS           current
    DESCRIPTION
        "Cisco UCS fabric:EthEstcPcEp managed object table"
    ::= { cucsFabricObjects 68 }

cucsFabricEthEstcPcEpEntry OBJECT-TYPE
    SYNTAX           CucsFabricEthEstcPcEpEntry
    MAX-ACCESS       not-accessible
    STATUS           current
    DESCRIPTION
        "Entry for the cucsFabricEthEstcPcEpTable table."
    INDEX { cucsFabricEthEstcPcEpInstanceId }
    ::= { cucsFabricEthEstcPcEpTable 1 }

CucsFabricEthEstcPcEpEntry ::= SEQUENCE {
    cucsFabricEthEstcPcEpInstanceId                                  CucsManagedObjectId,
    cucsFabricEthEstcPcEpDnData                                      CucsManagedObjectDn,
    cucsFabricEthEstcPcEpRn                                          SnmpAdminString,
    cucsFabricEthEstcPcEpAdminSpeed                                  CucsPortSpeed,
    cucsFabricEthEstcPcEpAdminState                                  CucsFabricExternalEpAdminState,
    cucsFabricEthEstcPcEpChassisId                                   Gauge32,
    cucsFabricEthEstcPcEpConfigState                                 CucsFabricConfigState,
    cucsFabricEthEstcPcEpEpDn                                        SnmpAdminString,
    cucsFabricEthEstcPcEpIfRole                                      CucsFabricAEthEstcEpIfRole,
    cucsFabricEthEstcPcEpIfType                                      CucsFabricPIoEpIfType,
    cucsFabricEthEstcPcEpLicGP                                       Unsigned64,
    cucsFabricEthEstcPcEpLicState                                    CucsLicenseState,
    cucsFabricEthEstcPcEpLocale                                      CucsFabricExternalEpLocale,
    cucsFabricEthEstcPcEpMembership                                  CucsFabricMembershipStatus,
    cucsFabricEthEstcPcEpName                                        SnmpAdminString,
    cucsFabricEthEstcPcEpPeerChassisId                               Gauge32,
    cucsFabricEthEstcPcEpPeerDn                                      SnmpAdminString,
    cucsFabricEthEstcPcEpPeerPortId                                  Gauge32,
    cucsFabricEthEstcPcEpPeerSlotId                                  Gauge32,
    cucsFabricEthEstcPcEpPortId                                      CucsFabricEthEstcPcEpPortId,
    cucsFabricEthEstcPcEpSlotId                                      CucsFabricEthEstcPcEpSlotId,
    cucsFabricEthEstcPcEpSwitchId                                    CucsNetworkSwitchId,
    cucsFabricEthEstcPcEpTransport                                   CucsFabricAEthEstcEpTransport,
    cucsFabricEthEstcPcEpType                                        CucsFabricAEthEstcEpType,
    cucsFabricEthEstcPcEpUsrLbl                                      SnmpAdminString,
    cucsFabricEthEstcPcEpFltAggr                                     Unsigned64,
    cucsFabricEthEstcPcEpOperState                                   CucsFabricPIoEpOperState,
    cucsFabricEthEstcPcEpOperStateReason                             SnmpAdminString,
    cucsFabricEthEstcPcEpWarnings                                    CucsFabricWarnings,
    cucsFabricEthEstcPcEpAggrPortId                                  Gauge32,
    cucsFabricEthEstcPcEpPeerAggrPortId                              Gauge32,
    cucsFabricEthEstcPcEpAutoNegotiate                               TruthValue
}

cucsFabricEthEstcPcEpInstanceId OBJECT-TYPE
    SYNTAX       CucsManagedObjectId
    MAX-ACCESS   not-accessible
    STATUS       current
    DESCRIPTION
        "Instance identifier of the managed object."
    ::= { cucsFabricEthEstcPcEpEntry 1 }

cucsFabricEthEstcPcEpDnData OBJECT-TYPE
    SYNTAX       CucsManagedObjectDn
    MAX-ACCESS   read-only
    STATUS       current
    DESCRIPTION
        "Cisco UCS fabric:EthEstcPcEp:dn managed object property"
    ::= { cucsFabricEthEstcPcEpEntry 2 }

cucsFabricEthEstcPcEpRn OBJECT-TYPE
    SYNTAX       SnmpAdminString
    MAX-ACCESS   read-only
    STATUS       current
    DESCRIPTION
        "Cisco UCS fabric:EthEstcPcEp:rn managed object property"
    ::= { cucsFabricEthEstcPcEpEntry 3 }

cucsFabricEthEstcPcEpAdminSpeed OBJECT-TYPE
    SYNTAX       CucsPortSpeed
    MAX-ACCESS   read-only
    STATUS       current
    DESCRIPTION
        "Cisco UCS fabric:EthEstcPcEp:adminSpeed managed object property"
    ::= { cucsFabricEthEstcPcEpEntry 4 }

cucsFabricEthEstcPcEpAdminState OBJECT-TYPE
    SYNTAX       CucsFabricExternalEpAdminState
    MAX-ACCESS   read-only
    STATUS       current
    DESCRIPTION
        "Cisco UCS fabric:EthEstcPcEp:adminState managed object property"
    ::= { cucsFabricEthEstcPcEpEntry 5 }

cucsFabricEthEstcPcEpChassisId OBJECT-TYPE
    SYNTAX       Gauge32
    MAX-ACCESS   read-only
    STATUS       current
    DESCRIPTION
        "Cisco UCS fabric:EthEstcPcEp:chassisId managed object property"
    ::= { cucsFabricEthEstcPcEpEntry 6 }

cucsFabricEthEstcPcEpConfigState OBJECT-TYPE
    SYNTAX       CucsFabricConfigState
    MAX-ACCESS   read-only
    STATUS       current
    DESCRIPTION
        "Cisco UCS fabric:EthEstcPcEp:configState managed object property"
    ::= { cucsFabricEthEstcPcEpEntry 7 }

cucsFabricEthEstcPcEpEpDn OBJECT-TYPE
    SYNTAX       SnmpAdminString
    MAX-ACCESS   read-only
    STATUS       current
    DESCRIPTION
        "Cisco UCS fabric:EthEstcPcEp:epDn managed object property"
    ::= { cucsFabricEthEstcPcEpEntry 8 }

cucsFabricEthEstcPcEpIfRole OBJECT-TYPE
    SYNTAX       CucsFabricAEthEstcEpIfRole
    MAX-ACCESS   read-only
    STATUS       current
    DESCRIPTION
        "Cisco UCS fabric:EthEstcPcEp:ifRole managed object property"
    ::= { cucsFabricEthEstcPcEpEntry 9 }

cucsFabricEthEstcPcEpIfType OBJECT-TYPE
    SYNTAX       CucsFabricPIoEpIfType
    MAX-ACCESS   read-only
    STATUS       current
    DESCRIPTION
        "Cisco UCS fabric:EthEstcPcEp:ifType managed object property"
    ::= { cucsFabricEthEstcPcEpEntry 10 }

cucsFabricEthEstcPcEpLicGP OBJECT-TYPE
    SYNTAX       Unsigned64
    MAX-ACCESS   read-only
    STATUS       current
    DESCRIPTION
        "Cisco UCS fabric:EthEstcPcEp:licGP managed object property"
    ::= { cucsFabricEthEstcPcEpEntry 11 }

cucsFabricEthEstcPcEpLicState OBJECT-TYPE
    SYNTAX       CucsLicenseState
    MAX-ACCESS   read-only
    STATUS       current
    DESCRIPTION
        "Cisco UCS fabric:EthEstcPcEp:licState managed object property"
    ::= { cucsFabricEthEstcPcEpEntry 12 }

cucsFabricEthEstcPcEpLocale OBJECT-TYPE
    SYNTAX       CucsFabricExternalEpLocale
    MAX-ACCESS   read-only
    STATUS       current
    DESCRIPTION
        "Cisco UCS fabric:EthEstcPcEp:locale managed object property"
    ::= { cucsFabricEthEstcPcEpEntry 13 }

cucsFabricEthEstcPcEpMembership OBJECT-TYPE
    SYNTAX       CucsFabricMembershipStatus
    MAX-ACCESS   read-only
    STATUS       current
    DESCRIPTION
        "Cisco UCS fabric:EthEstcPcEp:membership managed object property"
    ::= { cucsFabricEthEstcPcEpEntry 14 }

cucsFabricEthEstcPcEpName OBJECT-TYPE
    SYNTAX       SnmpAdminString
    MAX-ACCESS   read-only
    STATUS       current
    DESCRIPTION
        "Cisco UCS fabric:EthEstcPcEp:name managed object property"
    ::= { cucsFabricEthEstcPcEpEntry 15 }

cucsFabricEthEstcPcEpPeerChassisId OBJECT-TYPE
    SYNTAX       Gauge32
    MAX-ACCESS   read-only
    STATUS       current
    DESCRIPTION
        "Cisco UCS fabric:EthEstcPcEp:peerChassisId managed
        object property"
    ::= { cucsFabricEthEstcPcEpEntry 16 }

cucsFabricEthEstcPcEpPeerDn OBJECT-TYPE
    SYNTAX       SnmpAdminString
    MAX-ACCESS   read-only
    STATUS       current
    DESCRIPTION
        "Cisco UCS fabric:EthEstcPcEp:peerDn managed object property"
    ::= { cucsFabricEthEstcPcEpEntry 17 }

cucsFabricEthEstcPcEpPeerPortId OBJECT-TYPE
    SYNTAX       Gauge32
    MAX-ACCESS   read-only
    STATUS       current
    DESCRIPTION
        "Cisco UCS fabric:EthEstcPcEp:peerPortId managed object property"
    ::= { cucsFabricEthEstcPcEpEntry 18 }

cucsFabricEthEstcPcEpPeerSlotId OBJECT-TYPE
    SYNTAX       Gauge32
    MAX-ACCESS   read-only
    STATUS       current
    DESCRIPTION
        "Cisco UCS fabric:EthEstcPcEp:peerSlotId managed object property"
    ::= { cucsFabricEthEstcPcEpEntry 19 }

cucsFabricEthEstcPcEpPortId OBJECT-TYPE
    SYNTAX       CucsFabricEthEstcPcEpPortId
    MAX-ACCESS   read-only
    STATUS       current
    DESCRIPTION
        "Cisco UCS fabric:EthEstcPcEp:portId managed object property"
    ::= { cucsFabricEthEstcPcEpEntry 20 }

cucsFabricEthEstcPcEpSlotId OBJECT-TYPE
    SYNTAX       CucsFabricEthEstcPcEpSlotId
    MAX-ACCESS   read-only
    STATUS       current
    DESCRIPTION
        "Cisco UCS fabric:EthEstcPcEp:slotId managed object property"
    ::= { cucsFabricEthEstcPcEpEntry 21 }

cucsFabricEthEstcPcEpSwitchId OBJECT-TYPE
    SYNTAX       CucsNetworkSwitchId
    MAX-ACCESS   read-only
    STATUS       current
    DESCRIPTION
        "Cisco UCS fabric:EthEstcPcEp:switchId managed object property"
    ::= { cucsFabricEthEstcPcEpEntry 22 }

cucsFabricEthEstcPcEpTransport OBJECT-TYPE
    SYNTAX       CucsFabricAEthEstcEpTransport
    MAX-ACCESS   read-only
    STATUS       current
    DESCRIPTION
        "Cisco UCS fabric:EthEstcPcEp:transport managed object property"
    ::= { cucsFabricEthEstcPcEpEntry 23 }

cucsFabricEthEstcPcEpType OBJECT-TYPE
    SYNTAX       CucsFabricAEthEstcEpType
    MAX-ACCESS   read-only
    STATUS       current
    DESCRIPTION
        "Cisco UCS fabric:EthEstcPcEp:type managed object property"
    ::= { cucsFabricEthEstcPcEpEntry 24 }

cucsFabricEthEstcPcEpUsrLbl OBJECT-TYPE
    SYNTAX       SnmpAdminString
    MAX-ACCESS   read-only
    STATUS       current
    DESCRIPTION
        "Cisco UCS fabric:EthEstcPcEp:usrLbl managed object property"
    ::= { cucsFabricEthEstcPcEpEntry 25 }

cucsFabricEthEstcPcEpFltAggr OBJECT-TYPE
    SYNTAX       Unsigned64
    MAX-ACCESS   read-only
    STATUS       current
    DESCRIPTION
        "Cisco UCS fabric:EthEstcPcEp:fltAggr managed object property"
    ::= { cucsFabricEthEstcPcEpEntry 26 }

cucsFabricEthEstcPcEpOperState OBJECT-TYPE
    SYNTAX       CucsFabricPIoEpOperState
    MAX-ACCESS   read-only
    STATUS       current
    DESCRIPTION
        "Cisco UCS fabric:EthEstcPcEp:operState managed object property"
    ::= { cucsFabricEthEstcPcEpEntry 27 }

cucsFabricEthEstcPcEpOperStateReason OBJECT-TYPE
    SYNTAX       SnmpAdminString
    MAX-ACCESS   read-only
    STATUS       current
    DESCRIPTION
        "Cisco UCS fabric:EthEstcPcEp:operStateReason managed
        object property"
    ::= { cucsFabricEthEstcPcEpEntry 28 }

cucsFabricEthEstcPcEpWarnings OBJECT-TYPE
    SYNTAX       CucsFabricWarnings
    MAX-ACCESS   read-only
    STATUS       current
    DESCRIPTION
        "Cisco UCS fabric:EthEstcPcEp:warnings managed object property"
    ::= { cucsFabricEthEstcPcEpEntry 29 }

cucsFabricEthEstcPcEpAggrPortId OBJECT-TYPE
    SYNTAX       Gauge32
    MAX-ACCESS   read-only
    STATUS       current
    DESCRIPTION
        "Cisco UCS fabric:EthEstcPcEp:aggrPortId managed object property"
    ::= { cucsFabricEthEstcPcEpEntry 30 }

cucsFabricEthEstcPcEpPeerAggrPortId OBJECT-TYPE
    SYNTAX       Gauge32
    MAX-ACCESS   read-only
    STATUS       current
    DESCRIPTION
        "Cisco UCS fabric:EthEstcPcEp:peerAggrPortId managed
        object property"
    ::= { cucsFabricEthEstcPcEpEntry 31 }

cucsFabricEthEstcPcEpAutoNegotiate OBJECT-TYPE
    SYNTAX       TruthValue
    MAX-ACCESS   read-only
    STATUS       current
    DESCRIPTION
        "Cisco UCS fabric:EthEstcPcEp:autoNegotiate managed
        object property"
    ::= { cucsFabricEthEstcPcEpEntry 32 }

cucsFabricEthFlowMonLanTable OBJECT-TYPE
    SYNTAX           SEQUENCE OF CucsFabricEthFlowMonLanEntry
    MAX-ACCESS       not-accessible
    STATUS           current
    DESCRIPTION
        "Cisco UCS fabric:EthFlowMonLan managed object table"
    ::= { cucsFabricObjects 104 }

cucsFabricEthFlowMonLanEntry OBJECT-TYPE
    SYNTAX           CucsFabricEthFlowMonLanEntry
    MAX-ACCESS       not-accessible
    STATUS           current
    DESCRIPTION
        "Entry for the cucsFabricEthFlowMonLanTable table."
    INDEX { cucsFabricEthFlowMonLanInstanceId }
    ::= { cucsFabricEthFlowMonLanTable 1 }

CucsFabricEthFlowMonLanEntry ::= SEQUENCE {
    cucsFabricEthFlowMonLanInstanceId                                CucsManagedObjectId,
    cucsFabricEthFlowMonLanDn                                        CucsManagedObjectDn,
    cucsFabricEthFlowMonLanRn                                        SnmpAdminString,
    cucsFabricEthFlowMonLanExporterSourceMac                         MacAddress,
    cucsFabricEthFlowMonLanId                                        CucsNetworkSwitchId,
    cucsFabricEthFlowMonLanLocale                                    CucsFabricExternalLocale,
    cucsFabricEthFlowMonLanName                                      SnmpAdminString,
    cucsFabricEthFlowMonLanTransport                                 CucsFabricEthFlowMonLanTransport,
    cucsFabricEthFlowMonLanType                                      CucsFabricEthFlowMonLanType
}

cucsFabricEthFlowMonLanInstanceId OBJECT-TYPE
    SYNTAX       CucsManagedObjectId
    MAX-ACCESS   not-accessible
    STATUS       current
    DESCRIPTION
        "Instance identifier of the managed object."
    ::= { cucsFabricEthFlowMonLanEntry 1 }

cucsFabricEthFlowMonLanDn OBJECT-TYPE
    SYNTAX       CucsManagedObjectDn
    MAX-ACCESS   read-only
    STATUS       current
    DESCRIPTION
        "Cisco UCS fabric:EthFlowMonLan:dn managed object property"
    ::= { cucsFabricEthFlowMonLanEntry 2 }

cucsFabricEthFlowMonLanRn OBJECT-TYPE
    SYNTAX       SnmpAdminString
    MAX-ACCESS   read-only
    STATUS       current
    DESCRIPTION
        "Cisco UCS fabric:EthFlowMonLan:rn managed object property"
    ::= { cucsFabricEthFlowMonLanEntry 3 }

cucsFabricEthFlowMonLanExporterSourceMac OBJECT-TYPE
    SYNTAX       MacAddress
    MAX-ACCESS   read-only
    STATUS       current
    DESCRIPTION
        "Cisco UCS fabric:EthFlowMonLan:exporterSourceMac
        managed object property"
    ::= { cucsFabricEthFlowMonLanEntry 4 }

cucsFabricEthFlowMonLanId OBJECT-TYPE
    SYNTAX       CucsNetworkSwitchId
    MAX-ACCESS   read-only
    STATUS       current
    DESCRIPTION
        "Cisco UCS fabric:EthFlowMonLan:id managed object property"
    ::= { cucsFabricEthFlowMonLanEntry 5 }

cucsFabricEthFlowMonLanLocale OBJECT-TYPE
    SYNTAX       CucsFabricExternalLocale
    MAX-ACCESS   read-only
    STATUS       current
    DESCRIPTION
        "Cisco UCS fabric:EthFlowMonLan:locale managed object property"
    ::= { cucsFabricEthFlowMonLanEntry 6 }

cucsFabricEthFlowMonLanName OBJECT-TYPE
    SYNTAX       SnmpAdminString
    MAX-ACCESS   read-only
    STATUS       current
    DESCRIPTION
        "Cisco UCS fabric:EthFlowMonLan:name managed object property"
    ::= { cucsFabricEthFlowMonLanEntry 7 }

cucsFabricEthFlowMonLanTransport OBJECT-TYPE
    SYNTAX       CucsFabricEthFlowMonLanTransport
    MAX-ACCESS   read-only
    STATUS       current
    DESCRIPTION
        "Cisco UCS fabric:EthFlowMonLan:transport managed object property"
    ::= { cucsFabricEthFlowMonLanEntry 8 }

cucsFabricEthFlowMonLanType OBJECT-TYPE
    SYNTAX       CucsFabricEthFlowMonLanType
    MAX-ACCESS   read-only
    STATUS       current
    DESCRIPTION
        "Cisco UCS fabric:EthFlowMonLan:type managed object property"
    ::= { cucsFabricEthFlowMonLanEntry 9 }

cucsFabricEthLanTable OBJECT-TYPE
    SYNTAX           SEQUENCE OF CucsFabricEthLanEntry
    MAX-ACCESS       not-accessible
    STATUS           current
    DESCRIPTION
        "Cisco UCS fabric:EthLan managed object table"
    ::= { cucsFabricObjects 12 }

cucsFabricEthLanEntry OBJECT-TYPE
    SYNTAX           CucsFabricEthLanEntry
    MAX-ACCESS       not-accessible
    STATUS           current
    DESCRIPTION
        "Entry for the cucsFabricEthLanTable table."
    INDEX { cucsFabricEthLanInstanceId }
    ::= { cucsFabricEthLanTable 1 }

CucsFabricEthLanEntry ::= SEQUENCE {
    cucsFabricEthLanInstanceId                                       CucsManagedObjectId,
    cucsFabricEthLanDn                                               CucsManagedObjectDn,
    cucsFabricEthLanRn                                               SnmpAdminString,
    cucsFabricEthLanId                                               CucsNetworkSwitchId,
    cucsFabricEthLanLocale                                           CucsFabricExternalLocale,
    cucsFabricEthLanName                                             SnmpAdminString,
    cucsFabricEthLanTransport                                        CucsFabricEthLanTransport,
    cucsFabricEthLanType                                             CucsFabricLanType,
    cucsFabricEthLanConfigQualifier                                  CucsFabricLanConfigIssues
}

cucsFabricEthLanInstanceId OBJECT-TYPE
    SYNTAX       CucsManagedObjectId
    MAX-ACCESS   not-accessible
    STATUS       current
    DESCRIPTION
        "Instance identifier of the managed object."
    ::= { cucsFabricEthLanEntry 1 }

cucsFabricEthLanDn OBJECT-TYPE
    SYNTAX       CucsManagedObjectDn
    MAX-ACCESS   read-only
    STATUS       current
    DESCRIPTION
        "Cisco UCS fabric:EthLan:dn managed object property"
    ::= { cucsFabricEthLanEntry 2 }

cucsFabricEthLanRn OBJECT-TYPE
    SYNTAX       SnmpAdminString
    MAX-ACCESS   read-only
    STATUS       current
    DESCRIPTION
        "Cisco UCS fabric:EthLan:rn managed object property"
    ::= { cucsFabricEthLanEntry 3 }

cucsFabricEthLanId OBJECT-TYPE
    SYNTAX       CucsNetworkSwitchId
    MAX-ACCESS   read-only
    STATUS       current
    DESCRIPTION
        "Cisco UCS fabric:EthLan:id managed object property"
    ::= { cucsFabricEthLanEntry 4 }

cucsFabricEthLanLocale OBJECT-TYPE
    SYNTAX       CucsFabricExternalLocale
    MAX-ACCESS   read-only
    STATUS       current
    DESCRIPTION
        "Cisco UCS fabric:EthLan:locale managed object property"
    ::= { cucsFabricEthLanEntry 5 }

cucsFabricEthLanName OBJECT-TYPE
    SYNTAX       SnmpAdminString
    MAX-ACCESS   read-only
    STATUS       current
    DESCRIPTION
        "Cisco UCS fabric:EthLan:name managed object property"
    ::= { cucsFabricEthLanEntry 6 }

cucsFabricEthLanTransport OBJECT-TYPE
    SYNTAX       CucsFabricEthLanTransport
    MAX-ACCESS   read-only
    STATUS       current
    DESCRIPTION
        "Cisco UCS fabric:EthLan:transport managed object property"
    ::= { cucsFabricEthLanEntry 7 }

cucsFabricEthLanType OBJECT-TYPE
    SYNTAX       CucsFabricLanType
    MAX-ACCESS   read-only
    STATUS       current
    DESCRIPTION
        "Cisco UCS fabric:EthLan:type managed object property"
    ::= { cucsFabricEthLanEntry 8 }

cucsFabricEthLanConfigQualifier OBJECT-TYPE
    SYNTAX       CucsFabricLanConfigIssues
    MAX-ACCESS   read-only
    STATUS       current
    DESCRIPTION
        "Cisco UCS fabric:EthLan:configQualifier managed object property"
    ::= { cucsFabricEthLanEntry 9 }

cucsFabricEthLanEpTable OBJECT-TYPE
    SYNTAX           SEQUENCE OF CucsFabricEthLanEpEntry
    MAX-ACCESS       not-accessible
    STATUS           current
    DESCRIPTION
        "Cisco UCS fabric:EthLanEp managed object table"
    ::= { cucsFabricObjects 13 }

cucsFabricEthLanEpEntry OBJECT-TYPE
    SYNTAX           CucsFabricEthLanEpEntry
    MAX-ACCESS       not-accessible
    STATUS           current
    DESCRIPTION
        "Entry for the cucsFabricEthLanEpTable table."
    INDEX { cucsFabricEthLanEpInstanceId }
    ::= { cucsFabricEthLanEpTable 1 }

CucsFabricEthLanEpEntry ::= SEQUENCE {
    cucsFabricEthLanEpInstanceId                                     CucsManagedObjectId,
    cucsFabricEthLanEpDn                                             CucsManagedObjectDn,
    cucsFabricEthLanEpRn                                             SnmpAdminString,
    cucsFabricEthLanEpAdminSpeed                                     CucsPortEthSpeed,
    cucsFabricEthLanEpAdminState                                     CucsFabricExternalEpAdminState,
    cucsFabricEthLanEpChassisId                                      Gauge32,
    cucsFabricEthLanEpEpDn                                           SnmpAdminString,
    cucsFabricEthLanEpFlowCtrlPolicy                                 SnmpAdminString,
    cucsFabricEthLanEpIfRole                                         CucsFabricLanEpIfRole,
    cucsFabricEthLanEpIfType                                         CucsFabricPIoEpIfType,
    cucsFabricEthLanEpLicGP                                          Unsigned64,
    cucsFabricEthLanEpLicState                                       CucsLicenseState,
    cucsFabricEthLanEpLocale                                         CucsFabricExternalEpLocale,
    cucsFabricEthLanEpName                                           SnmpAdminString,
    cucsFabricEthLanEpPeerDn                                         SnmpAdminString,
    cucsFabricEthLanEpPeerPortId                                     Gauge32,
    cucsFabricEthLanEpPeerSlotId                                     Gauge32,
    cucsFabricEthLanEpPortId                                         Gauge32,
    cucsFabricEthLanEpSlotId                                         Gauge32,
    cucsFabricEthLanEpSwitchId                                       CucsNetworkSwitchId,
    cucsFabricEthLanEpTransport                                      CucsFabricAEthLanEpTransport,
    cucsFabricEthLanEpType                                           CucsFabricLanEpType,
    cucsFabricEthLanEpUsrLbl                                         SnmpAdminString,
    cucsFabricEthLanEpPeerChassisId                                  Gauge32,
    cucsFabricEthLanEpFltAggr                                        Unsigned64,
    cucsFabricEthLanEpOperState                                      CucsFabricPIoEpOperState,
    cucsFabricEthLanEpOperStateReason                                SnmpAdminString,
    cucsFabricEthLanEpVlanStatus                                     CucsFabricEthLanEpVlanStatus,
    cucsFabricEthLanEpOverlappingVlans                               SnmpAdminString,
    cucsFabricEthLanEpWarnings                                       CucsFabricWarnings,
    cucsFabricEthLanEpEthLinkProfileName                             SnmpAdminString,
    cucsFabricEthLanEpOperEthLinkProfileName                         SnmpAdminString,
    cucsFabricEthLanEpUdldOperState                                  CucsFabricUdldOperState,
    cucsFabricEthLanEpAggrPortId                                     Gauge32,
    cucsFabricEthLanEpPeerAggrPortId                                 Gauge32,
    cucsFabricEthLanEpAutoNegotiate                                  TruthValue
}

cucsFabricEthLanEpInstanceId OBJECT-TYPE
    SYNTAX       CucsManagedObjectId
    MAX-ACCESS   not-accessible
    STATUS       current
    DESCRIPTION
        "Instance identifier of the managed object."
    ::= { cucsFabricEthLanEpEntry 1 }

cucsFabricEthLanEpDn OBJECT-TYPE
    SYNTAX       CucsManagedObjectDn
    MAX-ACCESS   read-only
    STATUS       current
    DESCRIPTION
        "Cisco UCS fabric:EthLanEp:dn managed object property"
    ::= { cucsFabricEthLanEpEntry 2 }

cucsFabricEthLanEpRn OBJECT-TYPE
    SYNTAX       SnmpAdminString
    MAX-ACCESS   read-only
    STATUS       current
    DESCRIPTION
        "Cisco UCS fabric:EthLanEp:rn managed object property"
    ::= { cucsFabricEthLanEpEntry 3 }

cucsFabricEthLanEpAdminSpeed OBJECT-TYPE
    SYNTAX       CucsPortEthSpeed
    MAX-ACCESS   read-only
    STATUS       current
    DESCRIPTION
        "Cisco UCS fabric:EthLanEp:adminSpeed managed object property"
    ::= { cucsFabricEthLanEpEntry 4 }

cucsFabricEthLanEpAdminState OBJECT-TYPE
    SYNTAX       CucsFabricExternalEpAdminState
    MAX-ACCESS   read-only
    STATUS       current
    DESCRIPTION
        "Cisco UCS fabric:EthLanEp:adminState managed object property"
    ::= { cucsFabricEthLanEpEntry 5 }

cucsFabricEthLanEpChassisId OBJECT-TYPE
    SYNTAX       Gauge32
    MAX-ACCESS   read-only
    STATUS       current
    DESCRIPTION
        "Cisco UCS fabric:EthLanEp:chassisId managed object property"
    ::= { cucsFabricEthLanEpEntry 6 }

cucsFabricEthLanEpEpDn OBJECT-TYPE
    SYNTAX       SnmpAdminString
    MAX-ACCESS   read-only
    STATUS       current
    DESCRIPTION
        "Cisco UCS fabric:EthLanEp:epDn managed object property"
    ::= { cucsFabricEthLanEpEntry 7 }

cucsFabricEthLanEpFlowCtrlPolicy OBJECT-TYPE
    SYNTAX       SnmpAdminString
    MAX-ACCESS   read-only
    STATUS       current
    DESCRIPTION
        "Cisco UCS fabric:EthLanEp:flowCtrlPolicy managed object property"
    ::= { cucsFabricEthLanEpEntry 8 }

cucsFabricEthLanEpIfRole OBJECT-TYPE
    SYNTAX       CucsFabricLanEpIfRole
    MAX-ACCESS   read-only
    STATUS       current
    DESCRIPTION
        "Cisco UCS fabric:EthLanEp:ifRole managed object property"
    ::= { cucsFabricEthLanEpEntry 9 }

cucsFabricEthLanEpIfType OBJECT-TYPE
    SYNTAX       CucsFabricPIoEpIfType
    MAX-ACCESS   read-only
    STATUS       current
    DESCRIPTION
        "Cisco UCS fabric:EthLanEp:ifType managed object property"
    ::= { cucsFabricEthLanEpEntry 10 }

cucsFabricEthLanEpLicGP OBJECT-TYPE
    SYNTAX       Unsigned64
    MAX-ACCESS   read-only
    STATUS       current
    DESCRIPTION
        "Cisco UCS fabric:EthLanEp:licGP managed object property"
    ::= { cucsFabricEthLanEpEntry 11 }

cucsFabricEthLanEpLicState OBJECT-TYPE
    SYNTAX       CucsLicenseState
    MAX-ACCESS   read-only
    STATUS       current
    DESCRIPTION
        "Cisco UCS fabric:EthLanEp:licState managed object property"
    ::= { cucsFabricEthLanEpEntry 12 }

cucsFabricEthLanEpLocale OBJECT-TYPE
    SYNTAX       CucsFabricExternalEpLocale
    MAX-ACCESS   read-only
    STATUS       current
    DESCRIPTION
        "Cisco UCS fabric:EthLanEp:locale managed object property"
    ::= { cucsFabricEthLanEpEntry 13 }

cucsFabricEthLanEpName OBJECT-TYPE
    SYNTAX       SnmpAdminString
    MAX-ACCESS   read-only
    STATUS       current
    DESCRIPTION
        "Cisco UCS fabric:EthLanEp:name managed object property"
    ::= { cucsFabricEthLanEpEntry 14 }

cucsFabricEthLanEpPeerDn OBJECT-TYPE
    SYNTAX       SnmpAdminString
    MAX-ACCESS   read-only
    STATUS       current
    DESCRIPTION
        "Cisco UCS fabric:EthLanEp:peerDn managed object property"
    ::= { cucsFabricEthLanEpEntry 15 }

cucsFabricEthLanEpPeerPortId OBJECT-TYPE
    SYNTAX       Gauge32
    MAX-ACCESS   read-only
    STATUS       current
    DESCRIPTION
        "Cisco UCS fabric:EthLanEp:peerPortId managed object property"
    ::= { cucsFabricEthLanEpEntry 16 }

cucsFabricEthLanEpPeerSlotId OBJECT-TYPE
    SYNTAX       Gauge32
    MAX-ACCESS   read-only
    STATUS       current
    DESCRIPTION
        "Cisco UCS fabric:EthLanEp:peerSlotId managed object property"
    ::= { cucsFabricEthLanEpEntry 17 }

cucsFabricEthLanEpPortId OBJECT-TYPE
    SYNTAX       Gauge32
    MAX-ACCESS   read-only
    STATUS       current
    DESCRIPTION
        "Cisco UCS fabric:EthLanEp:portId managed object property"
    ::= { cucsFabricEthLanEpEntry 18 }

cucsFabricEthLanEpSlotId OBJECT-TYPE
    SYNTAX       Gauge32
    MAX-ACCESS   read-only
    STATUS       current
    DESCRIPTION
        "Cisco UCS fabric:EthLanEp:slotId managed object property"
    ::= { cucsFabricEthLanEpEntry 19 }

cucsFabricEthLanEpSwitchId OBJECT-TYPE
    SYNTAX       CucsNetworkSwitchId
    MAX-ACCESS   read-only
    STATUS       current
    DESCRIPTION
        "Cisco UCS fabric:EthLanEp:switchId managed object property"
    ::= { cucsFabricEthLanEpEntry 20 }

cucsFabricEthLanEpTransport OBJECT-TYPE
    SYNTAX       CucsFabricAEthLanEpTransport
    MAX-ACCESS   read-only
    STATUS       current
    DESCRIPTION
        "Cisco UCS fabric:EthLanEp:transport managed object property"
    ::= { cucsFabricEthLanEpEntry 21 }

cucsFabricEthLanEpType OBJECT-TYPE
    SYNTAX       CucsFabricLanEpType
    MAX-ACCESS   read-only
    STATUS       current
    DESCRIPTION
        "Cisco UCS fabric:EthLanEp:type managed object property"
    ::= { cucsFabricEthLanEpEntry 22 }

cucsFabricEthLanEpUsrLbl OBJECT-TYPE
    SYNTAX       SnmpAdminString
    MAX-ACCESS   read-only
    STATUS       current
    DESCRIPTION
        "Cisco UCS fabric:EthLanEp:usrLbl managed object property"
    ::= { cucsFabricEthLanEpEntry 23 }

cucsFabricEthLanEpPeerChassisId OBJECT-TYPE
    SYNTAX       Gauge32
    MAX-ACCESS   read-only
    STATUS       current
    DESCRIPTION
        "Cisco UCS fabric:EthLanEp:peerChassisId managed object property"
    ::= { cucsFabricEthLanEpEntry 24 }

cucsFabricEthLanEpFltAggr OBJECT-TYPE
    SYNTAX       Unsigned64
    MAX-ACCESS   read-only
    STATUS       current
    DESCRIPTION
        "Cisco UCS fabric:EthLanEp:fltAggr managed object property"
    ::= { cucsFabricEthLanEpEntry 25 }

cucsFabricEthLanEpOperState OBJECT-TYPE
    SYNTAX       CucsFabricPIoEpOperState
    MAX-ACCESS   read-only
    STATUS       current
    DESCRIPTION
        "Cisco UCS fabric:EthLanEp:operState managed object property"
    ::= { cucsFabricEthLanEpEntry 26 }

cucsFabricEthLanEpOperStateReason OBJECT-TYPE
    SYNTAX       SnmpAdminString
    MAX-ACCESS   read-only
    STATUS       current
    DESCRIPTION
        "Cisco UCS fabric:EthLanEp:operStateReason managed
        object property"
    ::= { cucsFabricEthLanEpEntry 27 }

cucsFabricEthLanEpVlanStatus OBJECT-TYPE
    SYNTAX       CucsFabricEthLanEpVlanStatus
    MAX-ACCESS   read-only
    STATUS       current
    DESCRIPTION
        "Cisco UCS fabric:EthLanEp:vlanStatus managed object property"
    ::= { cucsFabricEthLanEpEntry 28 }

cucsFabricEthLanEpOverlappingVlans OBJECT-TYPE
    SYNTAX       SnmpAdminString
    MAX-ACCESS   read-only
    STATUS       current
    DESCRIPTION
        "Cisco UCS fabric:EthLanEp:overlappingVlans managed
        object property"
    ::= { cucsFabricEthLanEpEntry 29 }

cucsFabricEthLanEpWarnings OBJECT-TYPE
    SYNTAX       CucsFabricWarnings
    MAX-ACCESS   read-only
    STATUS       current
    DESCRIPTION
        "Cisco UCS fabric:EthLanEp:warnings managed object property"
    ::= { cucsFabricEthLanEpEntry 30 }

cucsFabricEthLanEpEthLinkProfileName OBJECT-TYPE
    SYNTAX       SnmpAdminString
    MAX-ACCESS   read-only
    STATUS       current
    DESCRIPTION
        "Cisco UCS fabric:EthLanEp:ethLinkProfileName managed
        object property"
    ::= { cucsFabricEthLanEpEntry 31 }

cucsFabricEthLanEpOperEthLinkProfileName OBJECT-TYPE
    SYNTAX       SnmpAdminString
    MAX-ACCESS   read-only
    STATUS       current
    DESCRIPTION
        "Cisco UCS fabric:EthLanEp:operEthLinkProfileName
        managed object property"
    ::= { cucsFabricEthLanEpEntry 32 }

cucsFabricEthLanEpUdldOperState OBJECT-TYPE
    SYNTAX       CucsFabricUdldOperState
    MAX-ACCESS   read-only
    STATUS       current
    DESCRIPTION
        "Cisco UCS fabric:EthLanEp:udldOperState managed object property"
    ::= { cucsFabricEthLanEpEntry 33 }

cucsFabricEthLanEpAggrPortId OBJECT-TYPE
    SYNTAX       Gauge32
    MAX-ACCESS   read-only
    STATUS       current
    DESCRIPTION
        "Cisco UCS fabric:EthLanEp:aggrPortId managed object property"
    ::= { cucsFabricEthLanEpEntry 34 }

cucsFabricEthLanEpPeerAggrPortId OBJECT-TYPE
    SYNTAX       Gauge32
    MAX-ACCESS   read-only
    STATUS       current
    DESCRIPTION
        "Cisco UCS fabric:EthLanEp:peerAggrPortId managed object property"
    ::= { cucsFabricEthLanEpEntry 35 }

cucsFabricEthLanEpAutoNegotiate OBJECT-TYPE
    SYNTAX       TruthValue
    MAX-ACCESS   read-only
    STATUS       current
    DESCRIPTION
        "Cisco UCS fabric:EthLanEp:autoNegotiate managed object property"
    ::= { cucsFabricEthLanEpEntry 36 }

cucsFabricEthLanFlowMonitoringTable OBJECT-TYPE
    SYNTAX           SEQUENCE OF CucsFabricEthLanFlowMonitoringEntry
    MAX-ACCESS       not-accessible
    STATUS           current
    DESCRIPTION
        "Cisco UCS fabric:EthLanFlowMonitoring managed object table"
    ::= { cucsFabricObjects 105 }

cucsFabricEthLanFlowMonitoringEntry OBJECT-TYPE
    SYNTAX           CucsFabricEthLanFlowMonitoringEntry
    MAX-ACCESS       not-accessible
    STATUS           current
    DESCRIPTION
        "Entry for the cucsFabricEthLanFlowMonitoringTable table."
    INDEX { cucsFabricEthLanFlowMonitoringInstanceId }
    ::= { cucsFabricEthLanFlowMonitoringTable 1 }

CucsFabricEthLanFlowMonitoringEntry ::= SEQUENCE {
    cucsFabricEthLanFlowMonitoringInstanceId                         CucsManagedObjectId,
    cucsFabricEthLanFlowMonitoringDn                                 CucsManagedObjectDn,
    cucsFabricEthLanFlowMonitoringRn                                 SnmpAdminString,
    cucsFabricEthLanFlowMonitoringAdminState                         CucsFabricFlowMonitoringCategoryAdminState,
    cucsFabricEthLanFlowMonitoringType                               CucsFabricEthLanFlowMonitoringType
}

cucsFabricEthLanFlowMonitoringInstanceId OBJECT-TYPE
    SYNTAX       CucsManagedObjectId
    MAX-ACCESS   not-accessible
    STATUS       current
    DESCRIPTION
        "Instance identifier of the managed object."
    ::= { cucsFabricEthLanFlowMonitoringEntry 1 }

cucsFabricEthLanFlowMonitoringDn OBJECT-TYPE
    SYNTAX       CucsManagedObjectDn
    MAX-ACCESS   read-only
    STATUS       current
    DESCRIPTION
        "Cisco UCS fabric:EthLanFlowMonitoring:dn managed object property"
    ::= { cucsFabricEthLanFlowMonitoringEntry 2 }

cucsFabricEthLanFlowMonitoringRn OBJECT-TYPE
    SYNTAX       SnmpAdminString
    MAX-ACCESS   read-only
    STATUS       current
    DESCRIPTION
        "Cisco UCS fabric:EthLanFlowMonitoring:rn managed object property"
    ::= { cucsFabricEthLanFlowMonitoringEntry 3 }

cucsFabricEthLanFlowMonitoringAdminState OBJECT-TYPE
    SYNTAX       CucsFabricFlowMonitoringCategoryAdminState
    MAX-ACCESS   read-only
    STATUS       current
    DESCRIPTION
        "Cisco UCS fabric:EthLanFlowMonitoring:adminState
        managed object property"
    ::= { cucsFabricEthLanFlowMonitoringEntry 4 }

cucsFabricEthLanFlowMonitoringType OBJECT-TYPE
    SYNTAX       CucsFabricEthLanFlowMonitoringType
    MAX-ACCESS   read-only
    STATUS       current
    DESCRIPTION
        "Cisco UCS fabric:EthLanFlowMonitoring:type managed
        object property"
    ::= { cucsFabricEthLanFlowMonitoringEntry 5 }

cucsFabricEthLanPcTable OBJECT-TYPE
    SYNTAX           SEQUENCE OF CucsFabricEthLanPcEntry
    MAX-ACCESS       not-accessible
    STATUS           current
    DESCRIPTION
        "Cisco UCS fabric:EthLanPc managed object table"
    ::= { cucsFabricObjects 14 }

cucsFabricEthLanPcEntry OBJECT-TYPE
    SYNTAX           CucsFabricEthLanPcEntry
    MAX-ACCESS       not-accessible
    STATUS           current
    DESCRIPTION
        "Entry for the cucsFabricEthLanPcTable table."
    INDEX { cucsFabricEthLanPcInstanceId }
    ::= { cucsFabricEthLanPcTable 1 }

CucsFabricEthLanPcEntry ::= SEQUENCE {
    cucsFabricEthLanPcInstanceId                                     CucsManagedObjectId,
    cucsFabricEthLanPcDn                                             CucsManagedObjectDn,
    cucsFabricEthLanPcRn                                             SnmpAdminString,
    cucsFabricEthLanPcAdminSpeed                                     CucsPortEthAdminSpeed,
    cucsFabricEthLanPcAdminState                                     CucsFabricCIoEpAdminState,
    cucsFabricEthLanPcEndPtDn                                        SnmpAdminString,
    cucsFabricEthLanPcFlowCtrlPolicy                                 SnmpAdminString,
    cucsFabricEthLanPcFltAggr                                        Unsigned64,
    cucsFabricEthLanPcIfRole                                         CucsFabricLanPcIfRole,
    cucsFabricEthLanPcIfType                                         CucsFabricCIoEpIfType,
    cucsFabricEthLanPcLocale                                         CucsFabricExternalPcLocale,
    cucsFabricEthLanPcName                                           SnmpAdminString,
    cucsFabricEthLanPcOperSpeed                                      CucsPortEthSpeed,
    cucsFabricEthLanPcOperState                                      CucsNetworkPortOperState,
    cucsFabricEthLanPcPeerDn                                         SnmpAdminString,
    cucsFabricEthLanPcPortId                                         Gauge32,
    cucsFabricEthLanPcStateQual                                      SnmpAdminString,
    cucsFabricEthLanPcSwitchId                                       CucsNetworkSwitchId,
    cucsFabricEthLanPcTransport                                      CucsFabricEthLanPcTransport,
    cucsFabricEthLanPcType                                           CucsFabricLanPcType,
    cucsFabricEthLanPcVlanStatus                                     CucsFabricEthLanPcVlanStatus,
    cucsFabricEthLanPcOverlappingVlans                               SnmpAdminString,
    cucsFabricEthLanPcWarnings                                       CucsFabricWarnings,
    cucsFabricEthLanPcBandwidth                                      Gauge32,
    cucsFabricEthLanPcDescr                                          SnmpAdminString,
    cucsFabricEthLanPcLacpPolicyName                                 SnmpAdminString,
    cucsFabricEthLanPcOperLacpPolicyName                             SnmpAdminString,
    cucsFabricEthLanPcAutoNegotiate                                  TruthValue
}

cucsFabricEthLanPcInstanceId OBJECT-TYPE
    SYNTAX       CucsManagedObjectId
    MAX-ACCESS   not-accessible
    STATUS       current
    DESCRIPTION
        "Instance identifier of the managed object."
    ::= { cucsFabricEthLanPcEntry 1 }

cucsFabricEthLanPcDn OBJECT-TYPE
    SYNTAX       CucsManagedObjectDn
    MAX-ACCESS   read-only
    STATUS       current
    DESCRIPTION
        "Cisco UCS fabric:EthLanPc:dn managed object property"
    ::= { cucsFabricEthLanPcEntry 2 }

cucsFabricEthLanPcRn OBJECT-TYPE
    SYNTAX       SnmpAdminString
    MAX-ACCESS   read-only
    STATUS       current
    DESCRIPTION
        "Cisco UCS fabric:EthLanPc:rn managed object property"
    ::= { cucsFabricEthLanPcEntry 3 }

cucsFabricEthLanPcAdminSpeed OBJECT-TYPE
    SYNTAX       CucsPortEthAdminSpeed
    MAX-ACCESS   read-only
    STATUS       current
    DESCRIPTION
        "Cisco UCS fabric:EthLanPc:adminSpeed managed object property"
    ::= { cucsFabricEthLanPcEntry 4 }

cucsFabricEthLanPcAdminState OBJECT-TYPE
    SYNTAX       CucsFabricCIoEpAdminState
    MAX-ACCESS   read-only
    STATUS       current
    DESCRIPTION
        "Cisco UCS fabric:EthLanPc:adminState managed object property"
    ::= { cucsFabricEthLanPcEntry 5 }

cucsFabricEthLanPcEndPtDn OBJECT-TYPE
    SYNTAX       SnmpAdminString
    MAX-ACCESS   read-only
    STATUS       current
    DESCRIPTION
        "Cisco UCS fabric:EthLanPc:epDn managed object property"
    ::= { cucsFabricEthLanPcEntry 6 }

cucsFabricEthLanPcFlowCtrlPolicy OBJECT-TYPE
    SYNTAX       SnmpAdminString
    MAX-ACCESS   read-only
    STATUS       current
    DESCRIPTION
        "Cisco UCS fabric:EthLanPc:flowCtrlPolicy managed object property"
    ::= { cucsFabricEthLanPcEntry 7 }

cucsFabricEthLanPcFltAggr OBJECT-TYPE
    SYNTAX       Unsigned64
    MAX-ACCESS   read-only
    STATUS       current
    DESCRIPTION
        "Cisco UCS fabric:EthLanPc:fltAggr managed object property"
    ::= { cucsFabricEthLanPcEntry 8 }

cucsFabricEthLanPcIfRole OBJECT-TYPE
    SYNTAX       CucsFabricLanPcIfRole
    MAX-ACCESS   read-only
    STATUS       current
    DESCRIPTION
        "Cisco UCS fabric:EthLanPc:ifRole managed object property"
    ::= { cucsFabricEthLanPcEntry 9 }

cucsFabricEthLanPcIfType OBJECT-TYPE
    SYNTAX       CucsFabricCIoEpIfType
    MAX-ACCESS   read-only
    STATUS       current
    DESCRIPTION
        "Cisco UCS fabric:EthLanPc:ifType managed object property"
    ::= { cucsFabricEthLanPcEntry 10 }

cucsFabricEthLanPcLocale OBJECT-TYPE
    SYNTAX       CucsFabricExternalPcLocale
    MAX-ACCESS   read-only
    STATUS       current
    DESCRIPTION
        "Cisco UCS fabric:EthLanPc:locale managed object property"
    ::= { cucsFabricEthLanPcEntry 11 }

cucsFabricEthLanPcName OBJECT-TYPE
    SYNTAX       SnmpAdminString
    MAX-ACCESS   read-only
    STATUS       current
    DESCRIPTION
        "Cisco UCS fabric:EthLanPc:name managed object property"
    ::= { cucsFabricEthLanPcEntry 12 }

cucsFabricEthLanPcOperSpeed OBJECT-TYPE
    SYNTAX       CucsPortEthSpeed
    MAX-ACCESS   read-only
    STATUS       current
    DESCRIPTION
        "Cisco UCS fabric:EthLanPc:operSpeed managed object property"
    ::= { cucsFabricEthLanPcEntry 13 }

cucsFabricEthLanPcOperState OBJECT-TYPE
    SYNTAX       CucsNetworkPortOperState
    MAX-ACCESS   read-only
    STATUS       current
    DESCRIPTION
        "Cisco UCS fabric:EthLanPc:operState managed object property"
    ::= { cucsFabricEthLanPcEntry 14 }

cucsFabricEthLanPcPeerDn OBJECT-TYPE
    SYNTAX       SnmpAdminString
    MAX-ACCESS   read-only
    STATUS       current
    DESCRIPTION
        "Cisco UCS fabric:EthLanPc:peerDn managed object property"
    ::= { cucsFabricEthLanPcEntry 15 }

cucsFabricEthLanPcPortId OBJECT-TYPE
    SYNTAX       Gauge32
    MAX-ACCESS   read-only
    STATUS       current
    DESCRIPTION
        "Cisco UCS fabric:EthLanPc:portId managed object property"
    ::= { cucsFabricEthLanPcEntry 16 }

cucsFabricEthLanPcStateQual OBJECT-TYPE
    SYNTAX       SnmpAdminString
    MAX-ACCESS   read-only
    STATUS       current
    DESCRIPTION
        "Cisco UCS fabric:EthLanPc:stateQual managed object property"
    ::= { cucsFabricEthLanPcEntry 17 }

cucsFabricEthLanPcSwitchId OBJECT-TYPE
    SYNTAX       CucsNetworkSwitchId
    MAX-ACCESS   read-only
    STATUS       current
    DESCRIPTION
        "Cisco UCS fabric:EthLanPc:switchId managed object property"
    ::= { cucsFabricEthLanPcEntry 18 }

cucsFabricEthLanPcTransport OBJECT-TYPE
    SYNTAX       CucsFabricEthLanPcTransport
    MAX-ACCESS   read-only
    STATUS       current
    DESCRIPTION
        "Cisco UCS fabric:EthLanPc:transport managed object property"
    ::= { cucsFabricEthLanPcEntry 19 }

cucsFabricEthLanPcType OBJECT-TYPE
    SYNTAX       CucsFabricLanPcType
    MAX-ACCESS   read-only
    STATUS       current
    DESCRIPTION
        "Cisco UCS fabric:EthLanPc:type managed object property"
    ::= { cucsFabricEthLanPcEntry 20 }

cucsFabricEthLanPcVlanStatus OBJECT-TYPE
    SYNTAX       CucsFabricEthLanPcVlanStatus
    MAX-ACCESS   read-only
    STATUS       current
    DESCRIPTION
        "Cisco UCS fabric:EthLanPc:vlanStatus managed object property"
    ::= { cucsFabricEthLanPcEntry 21 }

cucsFabricEthLanPcOverlappingVlans OBJECT-TYPE
    SYNTAX       SnmpAdminString
    MAX-ACCESS   read-only
    STATUS       current
    DESCRIPTION
        "Cisco UCS fabric:EthLanPc:overlappingVlans managed
        object property"
    ::= { cucsFabricEthLanPcEntry 22 }

cucsFabricEthLanPcWarnings OBJECT-TYPE
    SYNTAX       CucsFabricWarnings
    MAX-ACCESS   read-only
    STATUS       current
    DESCRIPTION
        "Cisco UCS fabric:EthLanPc:warnings managed object property"
    ::= { cucsFabricEthLanPcEntry 23 }

cucsFabricEthLanPcBandwidth OBJECT-TYPE
    SYNTAX       Gauge32
    MAX-ACCESS   read-only
    STATUS       current
    DESCRIPTION
        "Cisco UCS fabric:EthLanPc:bandwidth managed object property"
    ::= { cucsFabricEthLanPcEntry 24 }

cucsFabricEthLanPcDescr OBJECT-TYPE
    SYNTAX       SnmpAdminString
    MAX-ACCESS   read-only
    STATUS       current
    DESCRIPTION
        "Cisco UCS fabric:EthLanPc:descr managed object property"
    ::= { cucsFabricEthLanPcEntry 25 }

cucsFabricEthLanPcLacpPolicyName OBJECT-TYPE
    SYNTAX       SnmpAdminString
    MAX-ACCESS   read-only
    STATUS       current
    DESCRIPTION
        "Cisco UCS fabric:EthLanPc:lacpPolicyName managed object property"
    ::= { cucsFabricEthLanPcEntry 26 }

cucsFabricEthLanPcOperLacpPolicyName OBJECT-TYPE
    SYNTAX       SnmpAdminString
    MAX-ACCESS   read-only
    STATUS       current
    DESCRIPTION
        "Cisco UCS fabric:EthLanPc:operLacpPolicyName managed
        object property"
    ::= { cucsFabricEthLanPcEntry 27 }

cucsFabricEthLanPcAutoNegotiate OBJECT-TYPE
    SYNTAX       TruthValue
    MAX-ACCESS   read-only
    STATUS       current
    DESCRIPTION
        "Cisco UCS fabric:EthLanPc:autoNegotiate managed object property"
    ::= { cucsFabricEthLanPcEntry 28 }

cucsFabricEthLanPcEpTable OBJECT-TYPE
    SYNTAX           SEQUENCE OF CucsFabricEthLanPcEpEntry
    MAX-ACCESS       not-accessible
    STATUS           current
    DESCRIPTION
        "Cisco UCS fabric:EthLanPcEp managed object table"
    ::= { cucsFabricObjects 15 }

cucsFabricEthLanPcEpEntry OBJECT-TYPE
    SYNTAX           CucsFabricEthLanPcEpEntry
    MAX-ACCESS       not-accessible
    STATUS           current
    DESCRIPTION
        "Entry for the cucsFabricEthLanPcEpTable table."
    INDEX { cucsFabricEthLanPcEpInstanceId }
    ::= { cucsFabricEthLanPcEpTable 1 }

CucsFabricEthLanPcEpEntry ::= SEQUENCE {
    cucsFabricEthLanPcEpInstanceId                                   CucsManagedObjectId,
    cucsFabricEthLanPcEpDn                                           CucsManagedObjectDn,
    cucsFabricEthLanPcEpRn                                           SnmpAdminString,
    cucsFabricEthLanPcEpAdminState                                   CucsFabricExternalEpAdminState,
    cucsFabricEthLanPcEpChassisId                                    Gauge32,
    cucsFabricEthLanPcEpEpDn                                         SnmpAdminString,
    cucsFabricEthLanPcEpIfRole                                       CucsFabricLanEpIfRole,
    cucsFabricEthLanPcEpIfType                                       CucsFabricPIoEpIfType,
    cucsFabricEthLanPcEpLicGP                                        Unsigned64,
    cucsFabricEthLanPcEpLicState                                     CucsLicenseState,
    cucsFabricEthLanPcEpLocale                                       CucsFabricExternalEpLocale,
    cucsFabricEthLanPcEpMembership                                   CucsFabricMembershipStatus,
    cucsFabricEthLanPcEpName                                         SnmpAdminString,
    cucsFabricEthLanPcEpPeerDn                                       SnmpAdminString,
    cucsFabricEthLanPcEpPeerPortId                                   Gauge32,
    cucsFabricEthLanPcEpPeerSlotId                                   Gauge32,
    cucsFabricEthLanPcEpPortId                                       Gauge32,
    cucsFabricEthLanPcEpSlotId                                       Gauge32,
    cucsFabricEthLanPcEpSwitchId                                     CucsNetworkSwitchId,
    cucsFabricEthLanPcEpTransport                                    CucsFabricAEthLanEpTransport,
    cucsFabricEthLanPcEpType                                         CucsFabricLanEpType,
    cucsFabricEthLanPcEpPeerChassisId                                Gauge32,
    cucsFabricEthLanPcEpFltAggr                                      Unsigned64,
    cucsFabricEthLanPcEpOperState                                    CucsFabricPIoEpOperState,
    cucsFabricEthLanPcEpOperStateReason                              SnmpAdminString,
    cucsFabricEthLanPcEpWarnings                                     CucsFabricWarnings,
    cucsFabricEthLanPcEpEthLinkProfileName                           SnmpAdminString,
    cucsFabricEthLanPcEpOperEthLinkProfileName                       SnmpAdminString,
    cucsFabricEthLanPcEpUdldOperState                                CucsFabricUdldOperState,
    cucsFabricEthLanPcEpAggrPortId                                   Gauge32,
    cucsFabricEthLanPcEpPeerAggrPortId                               Gauge32,
    cucsFabricEthLanPcEpAutoNegotiate                                TruthValue
}

cucsFabricEthLanPcEpInstanceId OBJECT-TYPE
    SYNTAX       CucsManagedObjectId
    MAX-ACCESS   not-accessible
    STATUS       current
    DESCRIPTION
        "Instance identifier of the managed object."
    ::= { cucsFabricEthLanPcEpEntry 1 }

cucsFabricEthLanPcEpDn OBJECT-TYPE
    SYNTAX       CucsManagedObjectDn
    MAX-ACCESS   read-only
    STATUS       current
    DESCRIPTION
        "Cisco UCS fabric:EthLanPcEp:dn managed object property"
    ::= { cucsFabricEthLanPcEpEntry 2 }

cucsFabricEthLanPcEpRn OBJECT-TYPE
    SYNTAX       SnmpAdminString
    MAX-ACCESS   read-only
    STATUS       current
    DESCRIPTION
        "Cisco UCS fabric:EthLanPcEp:rn managed object property"
    ::= { cucsFabricEthLanPcEpEntry 3 }

cucsFabricEthLanPcEpAdminState OBJECT-TYPE
    SYNTAX       CucsFabricExternalEpAdminState
    MAX-ACCESS   read-only
    STATUS       current
    DESCRIPTION
        "Cisco UCS fabric:EthLanPcEp:adminState managed object property"
    ::= { cucsFabricEthLanPcEpEntry 4 }

cucsFabricEthLanPcEpChassisId OBJECT-TYPE
    SYNTAX       Gauge32
    MAX-ACCESS   read-only
    STATUS       current
    DESCRIPTION
        "Cisco UCS fabric:EthLanPcEp:chassisId managed object property"
    ::= { cucsFabricEthLanPcEpEntry 5 }

cucsFabricEthLanPcEpEpDn OBJECT-TYPE
    SYNTAX       SnmpAdminString
    MAX-ACCESS   read-only
    STATUS       current
    DESCRIPTION
        "Cisco UCS fabric:EthLanPcEp:epDn managed object property"
    ::= { cucsFabricEthLanPcEpEntry 6 }

cucsFabricEthLanPcEpIfRole OBJECT-TYPE
    SYNTAX       CucsFabricLanEpIfRole
    MAX-ACCESS   read-only
    STATUS       current
    DESCRIPTION
        "Cisco UCS fabric:EthLanPcEp:ifRole managed object property"
    ::= { cucsFabricEthLanPcEpEntry 7 }

cucsFabricEthLanPcEpIfType OBJECT-TYPE
    SYNTAX       CucsFabricPIoEpIfType
    MAX-ACCESS   read-only
    STATUS       current
    DESCRIPTION
        "Cisco UCS fabric:EthLanPcEp:ifType managed object property"
    ::= { cucsFabricEthLanPcEpEntry 8 }

cucsFabricEthLanPcEpLicGP OBJECT-TYPE
    SYNTAX       Unsigned64
    MAX-ACCESS   read-only
    STATUS       current
    DESCRIPTION
        "Cisco UCS fabric:EthLanPcEp:licGP managed object property"
    ::= { cucsFabricEthLanPcEpEntry 9 }

cucsFabricEthLanPcEpLicState OBJECT-TYPE
    SYNTAX       CucsLicenseState
    MAX-ACCESS   read-only
    STATUS       current
    DESCRIPTION
        "Cisco UCS fabric:EthLanPcEp:licState managed object property"
    ::= { cucsFabricEthLanPcEpEntry 10 }

cucsFabricEthLanPcEpLocale OBJECT-TYPE
    SYNTAX       CucsFabricExternalEpLocale
    MAX-ACCESS   read-only
    STATUS       current
    DESCRIPTION
        "Cisco UCS fabric:EthLanPcEp:locale managed object property"
    ::= { cucsFabricEthLanPcEpEntry 11 }

cucsFabricEthLanPcEpMembership OBJECT-TYPE
    SYNTAX       CucsFabricMembershipStatus
    MAX-ACCESS   read-only
    STATUS       current
    DESCRIPTION
        "Cisco UCS fabric:EthLanPcEp:membership managed object property"
    ::= { cucsFabricEthLanPcEpEntry 12 }

cucsFabricEthLanPcEpName OBJECT-TYPE
    SYNTAX       SnmpAdminString
    MAX-ACCESS   read-only
    STATUS       current
    DESCRIPTION
        "Cisco UCS fabric:EthLanPcEp:name managed object property"
    ::= { cucsFabricEthLanPcEpEntry 13 }

cucsFabricEthLanPcEpPeerDn OBJECT-TYPE
    SYNTAX       SnmpAdminString
    MAX-ACCESS   read-only
    STATUS       current
    DESCRIPTION
        "Cisco UCS fabric:EthLanPcEp:peerDn managed object property"
    ::= { cucsFabricEthLanPcEpEntry 14 }

cucsFabricEthLanPcEpPeerPortId OBJECT-TYPE
    SYNTAX       Gauge32
    MAX-ACCESS   read-only
    STATUS       current
    DESCRIPTION
        "Cisco UCS fabric:EthLanPcEp:peerPortId managed object property"
    ::= { cucsFabricEthLanPcEpEntry 15 }

cucsFabricEthLanPcEpPeerSlotId OBJECT-TYPE
    SYNTAX       Gauge32
    MAX-ACCESS   read-only
    STATUS       current
    DESCRIPTION
        "Cisco UCS fabric:EthLanPcEp:peerSlotId managed object property"
    ::= { cucsFabricEthLanPcEpEntry 16 }

cucsFabricEthLanPcEpPortId OBJECT-TYPE
    SYNTAX       Gauge32
    MAX-ACCESS   read-only
    STATUS       current
    DESCRIPTION
        "Cisco UCS fabric:EthLanPcEp:portId managed object property"
    ::= { cucsFabricEthLanPcEpEntry 17 }

cucsFabricEthLanPcEpSlotId OBJECT-TYPE
    SYNTAX       Gauge32
    MAX-ACCESS   read-only
    STATUS       current
    DESCRIPTION
        "Cisco UCS fabric:EthLanPcEp:slotId managed object property"
    ::= { cucsFabricEthLanPcEpEntry 18 }

cucsFabricEthLanPcEpSwitchId OBJECT-TYPE
    SYNTAX       CucsNetworkSwitchId
    MAX-ACCESS   read-only
    STATUS       current
    DESCRIPTION
        "Cisco UCS fabric:EthLanPcEp:switchId managed object property"
    ::= { cucsFabricEthLanPcEpEntry 19 }

cucsFabricEthLanPcEpTransport OBJECT-TYPE
    SYNTAX       CucsFabricAEthLanEpTransport
    MAX-ACCESS   read-only
    STATUS       current
    DESCRIPTION
        "Cisco UCS fabric:EthLanPcEp:transport managed object property"
    ::= { cucsFabricEthLanPcEpEntry 20 }

cucsFabricEthLanPcEpType OBJECT-TYPE
    SYNTAX       CucsFabricLanEpType
    MAX-ACCESS   read-only
    STATUS       current
    DESCRIPTION
        "Cisco UCS fabric:EthLanPcEp:type managed object property"
    ::= { cucsFabricEthLanPcEpEntry 21 }

cucsFabricEthLanPcEpPeerChassisId OBJECT-TYPE
    SYNTAX       Gauge32
    MAX-ACCESS   read-only
    STATUS       current
    DESCRIPTION
        "Cisco UCS fabric:EthLanPcEp:peerChassisId managed
        object property"
    ::= { cucsFabricEthLanPcEpEntry 22 }

cucsFabricEthLanPcEpFltAggr OBJECT-TYPE
    SYNTAX       Unsigned64
    MAX-ACCESS   read-only
    STATUS       current
    DESCRIPTION
        "Cisco UCS fabric:EthLanPcEp:fltAggr managed object property"
    ::= { cucsFabricEthLanPcEpEntry 23 }

cucsFabricEthLanPcEpOperState OBJECT-TYPE
    SYNTAX       CucsFabricPIoEpOperState
    MAX-ACCESS   read-only
    STATUS       current
    DESCRIPTION
        "Cisco UCS fabric:EthLanPcEp:operState managed object property"
    ::= { cucsFabricEthLanPcEpEntry 24 }

cucsFabricEthLanPcEpOperStateReason OBJECT-TYPE
    SYNTAX       SnmpAdminString
    MAX-ACCESS   read-only
    STATUS       current
    DESCRIPTION
        "Cisco UCS fabric:EthLanPcEp:operStateReason managed
        object property"
    ::= { cucsFabricEthLanPcEpEntry 25 }

cucsFabricEthLanPcEpWarnings OBJECT-TYPE
    SYNTAX       CucsFabricWarnings
    MAX-ACCESS   read-only
    STATUS       current
    DESCRIPTION
        "Cisco UCS fabric:EthLanPcEp:warnings managed object property"
    ::= { cucsFabricEthLanPcEpEntry 26 }

cucsFabricEthLanPcEpEthLinkProfileName OBJECT-TYPE
    SYNTAX       SnmpAdminString
    MAX-ACCESS   read-only
    STATUS       current
    DESCRIPTION
        "Cisco UCS fabric:EthLanPcEp:ethLinkProfileName
        managed object property"
    ::= { cucsFabricEthLanPcEpEntry 27 }

cucsFabricEthLanPcEpOperEthLinkProfileName OBJECT-TYPE
    SYNTAX       SnmpAdminString
    MAX-ACCESS   read-only
    STATUS       current
    DESCRIPTION
        "Cisco UCS fabric:EthLanPcEp:operEthLinkProfileName
        managed object property"
    ::= { cucsFabricEthLanPcEpEntry 28 }

cucsFabricEthLanPcEpUdldOperState OBJECT-TYPE
    SYNTAX       CucsFabricUdldOperState
    MAX-ACCESS   read-only
    STATUS       current
    DESCRIPTION
        "Cisco UCS fabric:EthLanPcEp:udldOperState managed
        object property"
    ::= { cucsFabricEthLanPcEpEntry 29 }

cucsFabricEthLanPcEpAggrPortId OBJECT-TYPE
    SYNTAX       Gauge32
    MAX-ACCESS   read-only
    STATUS       current
    DESCRIPTION
        "Cisco UCS fabric:EthLanPcEp:aggrPortId managed object property"
    ::= { cucsFabricEthLanPcEpEntry 30 }

cucsFabricEthLanPcEpPeerAggrPortId OBJECT-TYPE
    SYNTAX       Gauge32
    MAX-ACCESS   read-only
    STATUS       current
    DESCRIPTION
        "Cisco UCS fabric:EthLanPcEp:peerAggrPortId managed
        object property"
    ::= { cucsFabricEthLanPcEpEntry 31 }

cucsFabricEthLanPcEpAutoNegotiate OBJECT-TYPE
    SYNTAX       TruthValue
    MAX-ACCESS   read-only
    STATUS       current
    DESCRIPTION
        "Cisco UCS fabric:EthLanPcEp:autoNegotiate managed
        object property"
    ::= { cucsFabricEthLanPcEpEntry 32 }

cucsFabricEthLinkProfileTable OBJECT-TYPE
    SYNTAX           SEQUENCE OF CucsFabricEthLinkProfileEntry
    MAX-ACCESS       not-accessible
    STATUS           current
    DESCRIPTION
        "Cisco UCS fabric:EthLinkProfile managed object table"
    ::= { cucsFabricObjects 106 }

cucsFabricEthLinkProfileEntry OBJECT-TYPE
    SYNTAX           CucsFabricEthLinkProfileEntry
    MAX-ACCESS       not-accessible
    STATUS           current
    DESCRIPTION
        "Entry for the cucsFabricEthLinkProfileTable table."
    INDEX { cucsFabricEthLinkProfileInstanceId }
    ::= { cucsFabricEthLinkProfileTable 1 }

CucsFabricEthLinkProfileEntry ::= SEQUENCE {
    cucsFabricEthLinkProfileInstanceId                               CucsManagedObjectId,
    cucsFabricEthLinkProfileDn                                       CucsManagedObjectDn,
    cucsFabricEthLinkProfileRn                                       SnmpAdminString,
    cucsFabricEthLinkProfileCdpLinkPolicyName                        SnmpAdminString,
    cucsFabricEthLinkProfileDescr                                    SnmpAdminString,
    cucsFabricEthLinkProfileIntId                                    SnmpAdminString,
    cucsFabricEthLinkProfileName                                     SnmpAdminString,
    cucsFabricEthLinkProfileOperCdpLinkPolicyName                    SnmpAdminString,
    cucsFabricEthLinkProfileOperUdldLinkPolicyName                   SnmpAdminString,
    cucsFabricEthLinkProfilePolicyLevel                              Gauge32,
    cucsFabricEthLinkProfilePolicyOwner                              CucsPolicyPolicyOwner,
    cucsFabricEthLinkProfileUdldLinkPolicyName                       SnmpAdminString
}

cucsFabricEthLinkProfileInstanceId OBJECT-TYPE
    SYNTAX       CucsManagedObjectId
    MAX-ACCESS   not-accessible
    STATUS       current
    DESCRIPTION
        "Instance identifier of the managed object."
    ::= { cucsFabricEthLinkProfileEntry 1 }

cucsFabricEthLinkProfileDn OBJECT-TYPE
    SYNTAX       CucsManagedObjectDn
    MAX-ACCESS   read-only
    STATUS       current
    DESCRIPTION
        "Cisco UCS fabric:EthLinkProfile:dn managed object property"
    ::= { cucsFabricEthLinkProfileEntry 2 }

cucsFabricEthLinkProfileRn OBJECT-TYPE
    SYNTAX       SnmpAdminString
    MAX-ACCESS   read-only
    STATUS       current
    DESCRIPTION
        "Cisco UCS fabric:EthLinkProfile:rn managed object property"
    ::= { cucsFabricEthLinkProfileEntry 3 }

cucsFabricEthLinkProfileCdpLinkPolicyName OBJECT-TYPE
    SYNTAX       SnmpAdminString
    MAX-ACCESS   read-only
    STATUS       current
    DESCRIPTION
        "Cisco UCS fabric:EthLinkProfile:cdpLinkPolicyName
        managed object property"
    ::= { cucsFabricEthLinkProfileEntry 4 }

cucsFabricEthLinkProfileDescr OBJECT-TYPE
    SYNTAX       SnmpAdminString
    MAX-ACCESS   read-only
    STATUS       current
    DESCRIPTION
        "Cisco UCS fabric:EthLinkProfile:descr managed object property"
    ::= { cucsFabricEthLinkProfileEntry 5 }

cucsFabricEthLinkProfileIntId OBJECT-TYPE
    SYNTAX       SnmpAdminString
    MAX-ACCESS   read-only
    STATUS       current
    DESCRIPTION
        "Cisco UCS fabric:EthLinkProfile:intId managed object property"
    ::= { cucsFabricEthLinkProfileEntry 6 }

cucsFabricEthLinkProfileName OBJECT-TYPE
    SYNTAX       SnmpAdminString
    MAX-ACCESS   read-only
    STATUS       current
    DESCRIPTION
        "Cisco UCS fabric:EthLinkProfile:name managed object property"
    ::= { cucsFabricEthLinkProfileEntry 7 }

cucsFabricEthLinkProfileOperCdpLinkPolicyName OBJECT-TYPE
    SYNTAX       SnmpAdminString
    MAX-ACCESS   read-only
    STATUS       current
    DESCRIPTION
        "Cisco UCS fabric:EthLinkProfile:operCdpLinkPolicyName
        managed object property"
    ::= { cucsFabricEthLinkProfileEntry 8 }

cucsFabricEthLinkProfileOperUdldLinkPolicyName OBJECT-TYPE
    SYNTAX       SnmpAdminString
    MAX-ACCESS   read-only
    STATUS       current
    DESCRIPTION
        "Cisco UCS fabric:EthLinkProfile:operUdldLinkPolicyName
        managed object property"
    ::= { cucsFabricEthLinkProfileEntry 9 }

cucsFabricEthLinkProfilePolicyLevel OBJECT-TYPE
    SYNTAX       Gauge32
    MAX-ACCESS   read-only
    STATUS       current
    DESCRIPTION
        "Cisco UCS fabric:EthLinkProfile:policyLevel managed
        object property"
    ::= { cucsFabricEthLinkProfileEntry 10 }

cucsFabricEthLinkProfilePolicyOwner OBJECT-TYPE
    SYNTAX       CucsPolicyPolicyOwner
    MAX-ACCESS   read-only
    STATUS       current
    DESCRIPTION
        "Cisco UCS fabric:EthLinkProfile:policyOwner managed
        object property"
    ::= { cucsFabricEthLinkProfileEntry 11 }

cucsFabricEthLinkProfileUdldLinkPolicyName OBJECT-TYPE
    SYNTAX       SnmpAdminString
    MAX-ACCESS   read-only
    STATUS       current
    DESCRIPTION
        "Cisco UCS fabric:EthLinkProfile:udldLinkPolicyName
        managed object property"
    ::= { cucsFabricEthLinkProfileEntry 12 }

cucsFabricEthMonTable OBJECT-TYPE
    SYNTAX           SEQUENCE OF CucsFabricEthMonEntry
    MAX-ACCESS       not-accessible
    STATUS           current
    DESCRIPTION
        "Cisco UCS fabric:EthMon managed object table"
    ::= { cucsFabricObjects 16 }

cucsFabricEthMonEntry OBJECT-TYPE
    SYNTAX           CucsFabricEthMonEntry
    MAX-ACCESS       not-accessible
    STATUS           current
    DESCRIPTION
        "Entry for the cucsFabricEthMonTable table."
    INDEX { cucsFabricEthMonInstanceId }
    ::= { cucsFabricEthMonTable 1 }

CucsFabricEthMonEntry ::= SEQUENCE {
    cucsFabricEthMonInstanceId                                       CucsManagedObjectId,
    cucsFabricEthMonDn                                               CucsManagedObjectDn,
    cucsFabricEthMonRn                                               SnmpAdminString,
    cucsFabricEthMonAdminState                                       CucsFabricMonAdminState,
    cucsFabricEthMonId                                               CucsNetworkSwitchId,
    cucsFabricEthMonLocale                                           CucsFabricExternalLocale,
    cucsFabricEthMonName                                             SnmpAdminString,
    cucsFabricEthMonSession                                          Gauge32,
    cucsFabricEthMonTransport                                        CucsFabricEthMonTransport,
    cucsFabricEthMonType                                             CucsFabricEthMonType,
    cucsFabricEthMonConfigFailReason                                 SnmpAdminString,
    cucsFabricEthMonIsConfigSuccess                                  TruthValue,
    cucsFabricEthMonOperState                                        CucsFabricMonOperState,
    cucsFabricEthMonOperStateReason                                  CucsFabricMonOperStateReason,
    cucsFabricEthMonPeerDn                                           SnmpAdminString
}

cucsFabricEthMonInstanceId OBJECT-TYPE
    SYNTAX       CucsManagedObjectId
    MAX-ACCESS   not-accessible
    STATUS       current
    DESCRIPTION
        "Instance identifier of the managed object."
    ::= { cucsFabricEthMonEntry 1 }

cucsFabricEthMonDn OBJECT-TYPE
    SYNTAX       CucsManagedObjectDn
    MAX-ACCESS   read-only
    STATUS       current
    DESCRIPTION
        "Cisco UCS fabric:EthMon:dn managed object property"
    ::= { cucsFabricEthMonEntry 2 }

cucsFabricEthMonRn OBJECT-TYPE
    SYNTAX       SnmpAdminString
    MAX-ACCESS   read-only
    STATUS       current
    DESCRIPTION
        "Cisco UCS fabric:EthMon:rn managed object property"
    ::= { cucsFabricEthMonEntry 3 }

cucsFabricEthMonAdminState OBJECT-TYPE
    SYNTAX       CucsFabricMonAdminState
    MAX-ACCESS   read-only
    STATUS       current
    DESCRIPTION
        "Cisco UCS fabric:EthMon:adminState managed object property"
    ::= { cucsFabricEthMonEntry 4 }

cucsFabricEthMonId OBJECT-TYPE
    SYNTAX       CucsNetworkSwitchId
    MAX-ACCESS   read-only
    STATUS       current
    DESCRIPTION
        "Cisco UCS fabric:EthMon:id managed object property"
    ::= { cucsFabricEthMonEntry 5 }

cucsFabricEthMonLocale OBJECT-TYPE
    SYNTAX       CucsFabricExternalLocale
    MAX-ACCESS   read-only
    STATUS       current
    DESCRIPTION
        "Cisco UCS fabric:EthMon:locale managed object property"
    ::= { cucsFabricEthMonEntry 6 }

cucsFabricEthMonName OBJECT-TYPE
    SYNTAX       SnmpAdminString
    MAX-ACCESS   read-only
    STATUS       current
    DESCRIPTION
        "Cisco UCS fabric:EthMon:name managed object property"
    ::= { cucsFabricEthMonEntry 7 }

cucsFabricEthMonSession OBJECT-TYPE
    SYNTAX       Gauge32
    MAX-ACCESS   read-only
    STATUS       current
    DESCRIPTION
        "Cisco UCS fabric:EthMon:session managed object property"
    ::= { cucsFabricEthMonEntry 8 }

cucsFabricEthMonTransport OBJECT-TYPE
    SYNTAX       CucsFabricEthMonTransport
    MAX-ACCESS   read-only
    STATUS       current
    DESCRIPTION
        "Cisco UCS fabric:EthMon:transport managed object property"
    ::= { cucsFabricEthMonEntry 9 }

cucsFabricEthMonType OBJECT-TYPE
    SYNTAX       CucsFabricEthMonType
    MAX-ACCESS   read-only
    STATUS       current
    DESCRIPTION
        "Cisco UCS fabric:EthMon:type managed object property"
    ::= { cucsFabricEthMonEntry 10 }

cucsFabricEthMonConfigFailReason OBJECT-TYPE
    SYNTAX       SnmpAdminString
    MAX-ACCESS   read-only
    STATUS       current
    DESCRIPTION
        "Cisco UCS fabric:EthMon:configFailReason managed object property"
    ::= { cucsFabricEthMonEntry 11 }

cucsFabricEthMonIsConfigSuccess OBJECT-TYPE
    SYNTAX       TruthValue
    MAX-ACCESS   read-only
    STATUS       current
    DESCRIPTION
        "Cisco UCS fabric:EthMon:isConfigSuccess managed object property"
    ::= { cucsFabricEthMonEntry 12 }

cucsFabricEthMonOperState OBJECT-TYPE
    SYNTAX       CucsFabricMonOperState
    MAX-ACCESS   read-only
    STATUS       current
    DESCRIPTION
        "Cisco UCS fabric:EthMon:operState managed object property"
    ::= { cucsFabricEthMonEntry 13 }

cucsFabricEthMonOperStateReason OBJECT-TYPE
    SYNTAX       CucsFabricMonOperStateReason
    MAX-ACCESS   read-only
    STATUS       current
    DESCRIPTION
        "Cisco UCS fabric:EthMon:operStateReason managed object property"
    ::= { cucsFabricEthMonEntry 14 }

cucsFabricEthMonPeerDn OBJECT-TYPE
    SYNTAX       SnmpAdminString
    MAX-ACCESS   read-only
    STATUS       current
    DESCRIPTION
        "Cisco UCS fabric:EthMon:peerDn managed object property"
    ::= { cucsFabricEthMonEntry 15 }

cucsFabricEthMonDestEpTable OBJECT-TYPE
    SYNTAX           SEQUENCE OF CucsFabricEthMonDestEpEntry
    MAX-ACCESS       not-accessible
    STATUS           current
    DESCRIPTION
        "Cisco UCS fabric:EthMonDestEp managed object table"
    ::= { cucsFabricObjects 17 }

cucsFabricEthMonDestEpEntry OBJECT-TYPE
    SYNTAX           CucsFabricEthMonDestEpEntry
    MAX-ACCESS       not-accessible
    STATUS           current
    DESCRIPTION
        "Entry for the cucsFabricEthMonDestEpTable table."
    INDEX { cucsFabricEthMonDestEpInstanceId }
    ::= { cucsFabricEthMonDestEpTable 1 }

CucsFabricEthMonDestEpEntry ::= SEQUENCE {
    cucsFabricEthMonDestEpInstanceId                                 CucsManagedObjectId,
    cucsFabricEthMonDestEpDn                                         CucsManagedObjectDn,
    cucsFabricEthMonDestEpRn                                         SnmpAdminString,
    cucsFabricEthMonDestEpAdminState                                 CucsFabricExternalEpAdminState,
    cucsFabricEthMonDestEpChassisId                                  Gauge32,
    cucsFabricEthMonDestEpEpDn                                       SnmpAdminString,
    cucsFabricEthMonDestEpIfRole                                     CucsFabricEthMonDestEpIfRole,
    cucsFabricEthMonDestEpIfType                                     CucsFabricPIoEpIfType,
    cucsFabricEthMonDestEpLicGP                                      Unsigned64,
    cucsFabricEthMonDestEpLicState                                   CucsLicenseState,
    cucsFabricEthMonDestEpLocale                                     CucsFabricExternalEpLocale,
    cucsFabricEthMonDestEpName                                       SnmpAdminString,
    cucsFabricEthMonDestEpPeerDn                                     SnmpAdminString,
    cucsFabricEthMonDestEpPeerPortId                                 Gauge32,
    cucsFabricEthMonDestEpPeerSlotId                                 Gauge32,
    cucsFabricEthMonDestEpPortId                                     CucsFabricEthMonDestEpPortId,
    cucsFabricEthMonDestEpSlotId                                     CucsFabricEthMonDestEpSlotId,
    cucsFabricEthMonDestEpSwitchId                                   CucsNetworkSwitchId,
    cucsFabricEthMonDestEpTransport                                  CucsNetworkTransport,
    cucsFabricEthMonDestEpType                                       CucsFabricEthMonDestEpType,
    cucsFabricEthMonDestEpPeerChassisId                              Gauge32,
    cucsFabricEthMonDestEpFltAggr                                    Unsigned64,
    cucsFabricEthMonDestEpAdminSpeed                                 CucsFabricEthMonDestEpAdminSpeed,
    cucsFabricEthMonDestEpOperState                                  CucsFabricPIoEpOperState,
    cucsFabricEthMonDestEpOperStateReason                            SnmpAdminString,
    cucsFabricEthMonDestEpWarnings                                   CucsFabricWarnings,
    cucsFabricEthMonDestEpAggrPortId                                 Gauge32,
    cucsFabricEthMonDestEpPeerAggrPortId                             Gauge32,
    cucsFabricEthMonDestEpAutoNegotiate                              TruthValue
}

cucsFabricEthMonDestEpInstanceId OBJECT-TYPE
    SYNTAX       CucsManagedObjectId
    MAX-ACCESS   not-accessible
    STATUS       current
    DESCRIPTION
        "Instance identifier of the managed object."
    ::= { cucsFabricEthMonDestEpEntry 1 }

cucsFabricEthMonDestEpDn OBJECT-TYPE
    SYNTAX       CucsManagedObjectDn
    MAX-ACCESS   read-only
    STATUS       current
    DESCRIPTION
        "Cisco UCS fabric:EthMonDestEp:dn managed object property"
    ::= { cucsFabricEthMonDestEpEntry 2 }

cucsFabricEthMonDestEpRn OBJECT-TYPE
    SYNTAX       SnmpAdminString
    MAX-ACCESS   read-only
    STATUS       current
    DESCRIPTION
        "Cisco UCS fabric:EthMonDestEp:rn managed object property"
    ::= { cucsFabricEthMonDestEpEntry 3 }

cucsFabricEthMonDestEpAdminState OBJECT-TYPE
    SYNTAX       CucsFabricExternalEpAdminState
    MAX-ACCESS   read-only
    STATUS       current
    DESCRIPTION
        "Cisco UCS fabric:EthMonDestEp:adminState managed object property"
    ::= { cucsFabricEthMonDestEpEntry 4 }

cucsFabricEthMonDestEpChassisId OBJECT-TYPE
    SYNTAX       Gauge32
    MAX-ACCESS   read-only
    STATUS       current
    DESCRIPTION
        "Cisco UCS fabric:EthMonDestEp:chassisId managed object property"
    ::= { cucsFabricEthMonDestEpEntry 5 }

cucsFabricEthMonDestEpEpDn OBJECT-TYPE
    SYNTAX       SnmpAdminString
    MAX-ACCESS   read-only
    STATUS       current
    DESCRIPTION
        "Cisco UCS fabric:EthMonDestEp:epDn managed object property"
    ::= { cucsFabricEthMonDestEpEntry 6 }

cucsFabricEthMonDestEpIfRole OBJECT-TYPE
    SYNTAX       CucsFabricEthMonDestEpIfRole
    MAX-ACCESS   read-only
    STATUS       current
    DESCRIPTION
        "Cisco UCS fabric:EthMonDestEp:ifRole managed object property"
    ::= { cucsFabricEthMonDestEpEntry 7 }

cucsFabricEthMonDestEpIfType OBJECT-TYPE
    SYNTAX       CucsFabricPIoEpIfType
    MAX-ACCESS   read-only
    STATUS       current
    DESCRIPTION
        "Cisco UCS fabric:EthMonDestEp:ifType managed object property"
    ::= { cucsFabricEthMonDestEpEntry 8 }

cucsFabricEthMonDestEpLicGP OBJECT-TYPE
    SYNTAX       Unsigned64
    MAX-ACCESS   read-only
    STATUS       current
    DESCRIPTION
        "Cisco UCS fabric:EthMonDestEp:licGP managed object property"
    ::= { cucsFabricEthMonDestEpEntry 9 }

cucsFabricEthMonDestEpLicState OBJECT-TYPE
    SYNTAX       CucsLicenseState
    MAX-ACCESS   read-only
    STATUS       current
    DESCRIPTION
        "Cisco UCS fabric:EthMonDestEp:licState managed object property"
    ::= { cucsFabricEthMonDestEpEntry 10 }

cucsFabricEthMonDestEpLocale OBJECT-TYPE
    SYNTAX       CucsFabricExternalEpLocale
    MAX-ACCESS   read-only
    STATUS       current
    DESCRIPTION
        "Cisco UCS fabric:EthMonDestEp:locale managed object property"
    ::= { cucsFabricEthMonDestEpEntry 11 }

cucsFabricEthMonDestEpName OBJECT-TYPE
    SYNTAX       SnmpAdminString
    MAX-ACCESS   read-only
    STATUS       current
    DESCRIPTION
        "Cisco UCS fabric:EthMonDestEp:name managed object property"
    ::= { cucsFabricEthMonDestEpEntry 12 }

cucsFabricEthMonDestEpPeerDn OBJECT-TYPE
    SYNTAX       SnmpAdminString
    MAX-ACCESS   read-only
    STATUS       current
    DESCRIPTION
        "Cisco UCS fabric:EthMonDestEp:peerDn managed object property"
    ::= { cucsFabricEthMonDestEpEntry 13 }

cucsFabricEthMonDestEpPeerPortId OBJECT-TYPE
    SYNTAX       Gauge32
    MAX-ACCESS   read-only
    STATUS       current
    DESCRIPTION
        "Cisco UCS fabric:EthMonDestEp:peerPortId managed object property"
    ::= { cucsFabricEthMonDestEpEntry 14 }

cucsFabricEthMonDestEpPeerSlotId OBJECT-TYPE
    SYNTAX       Gauge32
    MAX-ACCESS   read-only
    STATUS       current
    DESCRIPTION
        "Cisco UCS fabric:EthMonDestEp:peerSlotId managed object property"
    ::= { cucsFabricEthMonDestEpEntry 15 }

cucsFabricEthMonDestEpPortId OBJECT-TYPE
    SYNTAX       CucsFabricEthMonDestEpPortId
    MAX-ACCESS   read-only
    STATUS       current
    DESCRIPTION
        "Cisco UCS fabric:EthMonDestEp:portId managed object property"
    ::= { cucsFabricEthMonDestEpEntry 16 }

cucsFabricEthMonDestEpSlotId OBJECT-TYPE
    SYNTAX       CucsFabricEthMonDestEpSlotId
    MAX-ACCESS   read-only
    STATUS       current
    DESCRIPTION
        "Cisco UCS fabric:EthMonDestEp:slotId managed object property"
    ::= { cucsFabricEthMonDestEpEntry 17 }

cucsFabricEthMonDestEpSwitchId OBJECT-TYPE
    SYNTAX       CucsNetworkSwitchId
    MAX-ACCESS   read-only
    STATUS       current
    DESCRIPTION
        "Cisco UCS fabric:EthMonDestEp:switchId managed object property"
    ::= { cucsFabricEthMonDestEpEntry 18 }

cucsFabricEthMonDestEpTransport OBJECT-TYPE
    SYNTAX       CucsNetworkTransport
    MAX-ACCESS   read-only
    STATUS       current
    DESCRIPTION
        "Cisco UCS fabric:EthMonDestEp:transport managed object property"
    ::= { cucsFabricEthMonDestEpEntry 19 }

cucsFabricEthMonDestEpType OBJECT-TYPE
    SYNTAX       CucsFabricEthMonDestEpType
    MAX-ACCESS   read-only
    STATUS       current
    DESCRIPTION
        "Cisco UCS fabric:EthMonDestEp:type managed object property"
    ::= { cucsFabricEthMonDestEpEntry 20 }

cucsFabricEthMonDestEpPeerChassisId OBJECT-TYPE
    SYNTAX       Gauge32
    MAX-ACCESS   read-only
    STATUS       current
    DESCRIPTION
        "Cisco UCS fabric:EthMonDestEp:peerChassisId managed
        object property"
    ::= { cucsFabricEthMonDestEpEntry 21 }

cucsFabricEthMonDestEpFltAggr OBJECT-TYPE
    SYNTAX       Unsigned64
    MAX-ACCESS   read-only
    STATUS       current
    DESCRIPTION
        "Cisco UCS fabric:EthMonDestEp:fltAggr managed object property"
    ::= { cucsFabricEthMonDestEpEntry 22 }

cucsFabricEthMonDestEpAdminSpeed OBJECT-TYPE
    SYNTAX       CucsFabricEthMonDestEpAdminSpeed
    MAX-ACCESS   read-only
    STATUS       current
    DESCRIPTION
        "Cisco UCS fabric:EthMonDestEp:adminSpeed managed object property"
    ::= { cucsFabricEthMonDestEpEntry 23 }

cucsFabricEthMonDestEpOperState OBJECT-TYPE
    SYNTAX       CucsFabricPIoEpOperState
    MAX-ACCESS   read-only
    STATUS       current
    DESCRIPTION
        "Cisco UCS fabric:EthMonDestEp:operState managed object property"
    ::= { cucsFabricEthMonDestEpEntry 24 }

cucsFabricEthMonDestEpOperStateReason OBJECT-TYPE
    SYNTAX       SnmpAdminString
    MAX-ACCESS   read-only
    STATUS       current
    DESCRIPTION
        "Cisco UCS fabric:EthMonDestEp:operStateReason
        managed object property"
    ::= { cucsFabricEthMonDestEpEntry 25 }

cucsFabricEthMonDestEpWarnings OBJECT-TYPE
    SYNTAX       CucsFabricWarnings
    MAX-ACCESS   read-only
    STATUS       current
    DESCRIPTION
        "Cisco UCS fabric:EthMonDestEp:warnings managed object property"
    ::= { cucsFabricEthMonDestEpEntry 26 }

cucsFabricEthMonDestEpAggrPortId OBJECT-TYPE
    SYNTAX       Gauge32
    MAX-ACCESS   read-only
    STATUS       current
    DESCRIPTION
        "Cisco UCS fabric:EthMonDestEp:aggrPortId managed object property"
    ::= { cucsFabricEthMonDestEpEntry 27 }

cucsFabricEthMonDestEpPeerAggrPortId OBJECT-TYPE
    SYNTAX       Gauge32
    MAX-ACCESS   read-only
    STATUS       current
    DESCRIPTION
        "Cisco UCS fabric:EthMonDestEp:peerAggrPortId managed
        object property"
    ::= { cucsFabricEthMonDestEpEntry 28 }

cucsFabricEthMonDestEpAutoNegotiate OBJECT-TYPE
    SYNTAX       TruthValue
    MAX-ACCESS   read-only
    STATUS       current
    DESCRIPTION
        "Cisco UCS fabric:EthMonDestEp:autoNegotiate managed
        object property"
    ::= { cucsFabricEthMonDestEpEntry 29 }

cucsFabricEthMonFiltEpTable OBJECT-TYPE
    SYNTAX           SEQUENCE OF CucsFabricEthMonFiltEpEntry
    MAX-ACCESS       not-accessible
    STATUS           current
    DESCRIPTION
        "Cisco UCS fabric:EthMonFiltEp managed object table"
    ::= { cucsFabricObjects 18 }

cucsFabricEthMonFiltEpEntry OBJECT-TYPE
    SYNTAX           CucsFabricEthMonFiltEpEntry
    MAX-ACCESS       not-accessible
    STATUS           current
    DESCRIPTION
        "Entry for the cucsFabricEthMonFiltEpTable table."
    INDEX { cucsFabricEthMonFiltEpInstanceId }
    ::= { cucsFabricEthMonFiltEpTable 1 }

CucsFabricEthMonFiltEpEntry ::= SEQUENCE {
    cucsFabricEthMonFiltEpInstanceId                                 CucsManagedObjectId,
    cucsFabricEthMonFiltEpDn                                         CucsManagedObjectDn,
    cucsFabricEthMonFiltEpRn                                         SnmpAdminString,
    cucsFabricEthMonFiltEpName                                       SnmpAdminString,
    cucsFabricEthMonFiltEpSession                                    Gauge32,
    cucsFabricEthMonFiltEpType                                       CucsFabricEthMonFiltEpType
}

cucsFabricEthMonFiltEpInstanceId OBJECT-TYPE
    SYNTAX       CucsManagedObjectId
    MAX-ACCESS   not-accessible
    STATUS       current
    DESCRIPTION
        "Instance identifier of the managed object."
    ::= { cucsFabricEthMonFiltEpEntry 1 }

cucsFabricEthMonFiltEpDn OBJECT-TYPE
    SYNTAX       CucsManagedObjectDn
    MAX-ACCESS   read-only
    STATUS       current
    DESCRIPTION
        "Cisco UCS fabric:EthMonFiltEp:dn managed object property"
    ::= { cucsFabricEthMonFiltEpEntry 2 }

cucsFabricEthMonFiltEpRn OBJECT-TYPE
    SYNTAX       SnmpAdminString
    MAX-ACCESS   read-only
    STATUS       current
    DESCRIPTION
        "Cisco UCS fabric:EthMonFiltEp:rn managed object property"
    ::= { cucsFabricEthMonFiltEpEntry 3 }

cucsFabricEthMonFiltEpName OBJECT-TYPE
    SYNTAX       SnmpAdminString
    MAX-ACCESS   read-only
    STATUS       current
    DESCRIPTION
        "Cisco UCS fabric:EthMonFiltEp:name managed object property"
    ::= { cucsFabricEthMonFiltEpEntry 4 }

cucsFabricEthMonFiltEpSession OBJECT-TYPE
    SYNTAX       Gauge32
    MAX-ACCESS   read-only
    STATUS       current
    DESCRIPTION
        "Cisco UCS fabric:EthMonFiltEp:session managed object property"
    ::= { cucsFabricEthMonFiltEpEntry 5 }

cucsFabricEthMonFiltEpType OBJECT-TYPE
    SYNTAX       CucsFabricEthMonFiltEpType
    MAX-ACCESS   read-only
    STATUS       current
    DESCRIPTION
        "Cisco UCS fabric:EthMonFiltEp:type managed object property"
    ::= { cucsFabricEthMonFiltEpEntry 6 }

cucsFabricEthMonFiltRefTable OBJECT-TYPE
    SYNTAX           SEQUENCE OF CucsFabricEthMonFiltRefEntry
    MAX-ACCESS       not-accessible
    STATUS           current
    DESCRIPTION
        "Cisco UCS fabric:EthMonFiltRef managed object table"
    ::= { cucsFabricObjects 19 }

cucsFabricEthMonFiltRefEntry OBJECT-TYPE
    SYNTAX           CucsFabricEthMonFiltRefEntry
    MAX-ACCESS       not-accessible
    STATUS           current
    DESCRIPTION
        "Entry for the cucsFabricEthMonFiltRefTable table."
    INDEX { cucsFabricEthMonFiltRefInstanceId }
    ::= { cucsFabricEthMonFiltRefTable 1 }

CucsFabricEthMonFiltRefEntry ::= SEQUENCE {
    cucsFabricEthMonFiltRefInstanceId                                CucsManagedObjectId,
    cucsFabricEthMonFiltRefDn                                        CucsManagedObjectDn,
    cucsFabricEthMonFiltRefRn                                        SnmpAdminString,
    cucsFabricEthMonFiltRefSrcFiltDn                                 SnmpAdminString,
    cucsFabricEthMonFiltRefType                                      CucsFabricEthMonFiltRefType
}

cucsFabricEthMonFiltRefInstanceId OBJECT-TYPE
    SYNTAX       CucsManagedObjectId
    MAX-ACCESS   not-accessible
    STATUS       current
    DESCRIPTION
        "Instance identifier of the managed object."
    ::= { cucsFabricEthMonFiltRefEntry 1 }

cucsFabricEthMonFiltRefDn OBJECT-TYPE
    SYNTAX       CucsManagedObjectDn
    MAX-ACCESS   read-only
    STATUS       current
    DESCRIPTION
        "Cisco UCS fabric:EthMonFiltRef:dn managed object property"
    ::= { cucsFabricEthMonFiltRefEntry 2 }

cucsFabricEthMonFiltRefRn OBJECT-TYPE
    SYNTAX       SnmpAdminString
    MAX-ACCESS   read-only
    STATUS       current
    DESCRIPTION
        "Cisco UCS fabric:EthMonFiltRef:rn managed object property"
    ::= { cucsFabricEthMonFiltRefEntry 3 }

cucsFabricEthMonFiltRefSrcFiltDn OBJECT-TYPE
    SYNTAX       SnmpAdminString
    MAX-ACCESS   read-only
    STATUS       current
    DESCRIPTION
        "Cisco UCS fabric:EthMonFiltRef:srcFiltDn managed object property"
    ::= { cucsFabricEthMonFiltRefEntry 4 }

cucsFabricEthMonFiltRefType OBJECT-TYPE
    SYNTAX       CucsFabricEthMonFiltRefType
    MAX-ACCESS   read-only
    STATUS       current
    DESCRIPTION
        "Cisco UCS fabric:EthMonFiltRef:type managed object property"
    ::= { cucsFabricEthMonFiltRefEntry 5 }

cucsFabricEthMonLanTable OBJECT-TYPE
    SYNTAX           SEQUENCE OF CucsFabricEthMonLanEntry
    MAX-ACCESS       not-accessible
    STATUS           current
    DESCRIPTION
        "Cisco UCS fabric:EthMonLan managed object table"
    ::= { cucsFabricObjects 20 }

cucsFabricEthMonLanEntry OBJECT-TYPE
    SYNTAX           CucsFabricEthMonLanEntry
    MAX-ACCESS       not-accessible
    STATUS           current
    DESCRIPTION
        "Entry for the cucsFabricEthMonLanTable table."
    INDEX { cucsFabricEthMonLanInstanceId }
    ::= { cucsFabricEthMonLanTable 1 }

CucsFabricEthMonLanEntry ::= SEQUENCE {
    cucsFabricEthMonLanInstanceId                                    CucsManagedObjectId,
    cucsFabricEthMonLanDn                                            CucsManagedObjectDn,
    cucsFabricEthMonLanRn                                            SnmpAdminString,
    cucsFabricEthMonLanId                                            CucsNetworkSwitchId,
    cucsFabricEthMonLanLocale                                        CucsFabricExternalLocale,
    cucsFabricEthMonLanName                                          SnmpAdminString,
    cucsFabricEthMonLanTransport                                     CucsFabricEthMonLanTransport,
    cucsFabricEthMonLanType                                          CucsFabricEthMonLanType
}

cucsFabricEthMonLanInstanceId OBJECT-TYPE
    SYNTAX       CucsManagedObjectId
    MAX-ACCESS   not-accessible
    STATUS       current
    DESCRIPTION
        "Instance identifier of the managed object."
    ::= { cucsFabricEthMonLanEntry 1 }

cucsFabricEthMonLanDn OBJECT-TYPE
    SYNTAX       CucsManagedObjectDn
    MAX-ACCESS   read-only
    STATUS       current
    DESCRIPTION
        "Cisco UCS fabric:EthMonLan:dn managed object property"
    ::= { cucsFabricEthMonLanEntry 2 }

cucsFabricEthMonLanRn OBJECT-TYPE
    SYNTAX       SnmpAdminString
    MAX-ACCESS   read-only
    STATUS       current
    DESCRIPTION
        "Cisco UCS fabric:EthMonLan:rn managed object property"
    ::= { cucsFabricEthMonLanEntry 3 }

cucsFabricEthMonLanId OBJECT-TYPE
    SYNTAX       CucsNetworkSwitchId
    MAX-ACCESS   read-only
    STATUS       current
    DESCRIPTION
        "Cisco UCS fabric:EthMonLan:id managed object property"
    ::= { cucsFabricEthMonLanEntry 4 }

cucsFabricEthMonLanLocale OBJECT-TYPE
    SYNTAX       CucsFabricExternalLocale
    MAX-ACCESS   read-only
    STATUS       current
    DESCRIPTION
        "Cisco UCS fabric:EthMonLan:locale managed object property"
    ::= { cucsFabricEthMonLanEntry 5 }

cucsFabricEthMonLanName OBJECT-TYPE
    SYNTAX       SnmpAdminString
    MAX-ACCESS   read-only
    STATUS       current
    DESCRIPTION
        "Cisco UCS fabric:EthMonLan:name managed object property"
    ::= { cucsFabricEthMonLanEntry 6 }

cucsFabricEthMonLanTransport OBJECT-TYPE
    SYNTAX       CucsFabricEthMonLanTransport
    MAX-ACCESS   read-only
    STATUS       current
    DESCRIPTION
        "Cisco UCS fabric:EthMonLan:transport managed object property"
    ::= { cucsFabricEthMonLanEntry 7 }

cucsFabricEthMonLanType OBJECT-TYPE
    SYNTAX       CucsFabricEthMonLanType
    MAX-ACCESS   read-only
    STATUS       current
    DESCRIPTION
        "Cisco UCS fabric:EthMonLan:type managed object property"
    ::= { cucsFabricEthMonLanEntry 8 }

cucsFabricEthMonSrcEpTable OBJECT-TYPE
    SYNTAX           SEQUENCE OF CucsFabricEthMonSrcEpEntry
    MAX-ACCESS       not-accessible
    STATUS           current
    DESCRIPTION
        "Cisco UCS fabric:EthMonSrcEp managed object table"
    ::= { cucsFabricObjects 21 }

cucsFabricEthMonSrcEpEntry OBJECT-TYPE
    SYNTAX           CucsFabricEthMonSrcEpEntry
    MAX-ACCESS       not-accessible
    STATUS           current
    DESCRIPTION
        "Entry for the cucsFabricEthMonSrcEpTable table."
    INDEX { cucsFabricEthMonSrcEpInstanceId }
    ::= { cucsFabricEthMonSrcEpTable 1 }

CucsFabricEthMonSrcEpEntry ::= SEQUENCE {
    cucsFabricEthMonSrcEpInstanceId                                  CucsManagedObjectId,
    cucsFabricEthMonSrcEpDn                                          CucsManagedObjectDn,
    cucsFabricEthMonSrcEpRn                                          SnmpAdminString,
    cucsFabricEthMonSrcEpDirection                                   CucsFabricTrafficDirection,
    cucsFabricEthMonSrcEpName                                        SnmpAdminString,
    cucsFabricEthMonSrcEpSession                                     Gauge32,
    cucsFabricEthMonSrcEpTransport                                   CucsNetworkTransport,
    cucsFabricEthMonSrcEpType                                        CucsFabricEthMonSrcEpType
}

cucsFabricEthMonSrcEpInstanceId OBJECT-TYPE
    SYNTAX       CucsManagedObjectId
    MAX-ACCESS   not-accessible
    STATUS       current
    DESCRIPTION
        "Instance identifier of the managed object."
    ::= { cucsFabricEthMonSrcEpEntry 1 }

cucsFabricEthMonSrcEpDn OBJECT-TYPE
    SYNTAX       CucsManagedObjectDn
    MAX-ACCESS   read-only
    STATUS       current
    DESCRIPTION
        "Cisco UCS fabric:EthMonSrcEp:dn managed object property"
    ::= { cucsFabricEthMonSrcEpEntry 2 }

cucsFabricEthMonSrcEpRn OBJECT-TYPE
    SYNTAX       SnmpAdminString
    MAX-ACCESS   read-only
    STATUS       current
    DESCRIPTION
        "Cisco UCS fabric:EthMonSrcEp:rn managed object property"
    ::= { cucsFabricEthMonSrcEpEntry 3 }

cucsFabricEthMonSrcEpDirection OBJECT-TYPE
    SYNTAX       CucsFabricTrafficDirection
    MAX-ACCESS   read-only
    STATUS       current
    DESCRIPTION
        "Cisco UCS fabric:EthMonSrcEp:direction managed object property"
    ::= { cucsFabricEthMonSrcEpEntry 4 }

cucsFabricEthMonSrcEpName OBJECT-TYPE
    SYNTAX       SnmpAdminString
    MAX-ACCESS   read-only
    STATUS       current
    DESCRIPTION
        "Cisco UCS fabric:EthMonSrcEp:name managed object property"
    ::= { cucsFabricEthMonSrcEpEntry 5 }

cucsFabricEthMonSrcEpSession OBJECT-TYPE
    SYNTAX       Gauge32
    MAX-ACCESS   read-only
    STATUS       current
    DESCRIPTION
        "Cisco UCS fabric:EthMonSrcEp:session managed object property"
    ::= { cucsFabricEthMonSrcEpEntry 6 }

cucsFabricEthMonSrcEpTransport OBJECT-TYPE
    SYNTAX       CucsNetworkTransport
    MAX-ACCESS   read-only
    STATUS       current
    DESCRIPTION
        "Cisco UCS fabric:EthMonSrcEp:transport managed object property"
    ::= { cucsFabricEthMonSrcEpEntry 7 }

cucsFabricEthMonSrcEpType OBJECT-TYPE
    SYNTAX       CucsFabricEthMonSrcEpType
    MAX-ACCESS   read-only
    STATUS       current
    DESCRIPTION
        "Cisco UCS fabric:EthMonSrcEp:type managed object property"
    ::= { cucsFabricEthMonSrcEpEntry 8 }

cucsFabricEthMonSrcRefTable OBJECT-TYPE
    SYNTAX           SEQUENCE OF CucsFabricEthMonSrcRefEntry
    MAX-ACCESS       not-accessible
    STATUS           current
    DESCRIPTION
        "Cisco UCS fabric:EthMonSrcRef managed object table"
    ::= { cucsFabricObjects 22 }

cucsFabricEthMonSrcRefEntry OBJECT-TYPE
    SYNTAX           CucsFabricEthMonSrcRefEntry
    MAX-ACCESS       not-accessible
    STATUS           current
    DESCRIPTION
        "Entry for the cucsFabricEthMonSrcRefTable table."
    INDEX { cucsFabricEthMonSrcRefInstanceId }
    ::= { cucsFabricEthMonSrcRefTable 1 }

CucsFabricEthMonSrcRefEntry ::= SEQUENCE {
    cucsFabricEthMonSrcRefInstanceId                                 CucsManagedObjectId,
    cucsFabricEthMonSrcRefDn                                         CucsManagedObjectDn,
    cucsFabricEthMonSrcRefRn                                         SnmpAdminString,
    cucsFabricEthMonSrcRefId                                         Unsigned64,
    cucsFabricEthMonSrcRefSourceDn                                   SnmpAdminString,
    cucsFabricEthMonSrcRefSourceType                                 CucsFabricEthSourceType,
    cucsFabricEthMonSrcRefType                                       CucsFabricEthMonSrcRefType
}

cucsFabricEthMonSrcRefInstanceId OBJECT-TYPE
    SYNTAX       CucsManagedObjectId
    MAX-ACCESS   not-accessible
    STATUS       current
    DESCRIPTION
        "Instance identifier of the managed object."
    ::= { cucsFabricEthMonSrcRefEntry 1 }

cucsFabricEthMonSrcRefDn OBJECT-TYPE
    SYNTAX       CucsManagedObjectDn
    MAX-ACCESS   read-only
    STATUS       current
    DESCRIPTION
        "Cisco UCS fabric:EthMonSrcRef:dn managed object property"
    ::= { cucsFabricEthMonSrcRefEntry 2 }

cucsFabricEthMonSrcRefRn OBJECT-TYPE
    SYNTAX       SnmpAdminString
    MAX-ACCESS   read-only
    STATUS       current
    DESCRIPTION
        "Cisco UCS fabric:EthMonSrcRef:rn managed object property"
    ::= { cucsFabricEthMonSrcRefEntry 3 }

cucsFabricEthMonSrcRefId OBJECT-TYPE
    SYNTAX       Unsigned64
    MAX-ACCESS   read-only
    STATUS       current
    DESCRIPTION
        "Cisco UCS fabric:EthMonSrcRef:id managed object property"
    ::= { cucsFabricEthMonSrcRefEntry 4 }

cucsFabricEthMonSrcRefSourceDn OBJECT-TYPE
    SYNTAX       SnmpAdminString
    MAX-ACCESS   read-only
    STATUS       current
    DESCRIPTION
        "Cisco UCS fabric:EthMonSrcRef:sourceDn managed object property"
    ::= { cucsFabricEthMonSrcRefEntry 5 }

cucsFabricEthMonSrcRefSourceType OBJECT-TYPE
    SYNTAX       CucsFabricEthSourceType
    MAX-ACCESS   read-only
    STATUS       current
    DESCRIPTION
        "Cisco UCS fabric:EthMonSrcRef:sourceType managed object property"
    ::= { cucsFabricEthMonSrcRefEntry 6 }

cucsFabricEthMonSrcRefType OBJECT-TYPE
    SYNTAX       CucsFabricEthMonSrcRefType
    MAX-ACCESS   read-only
    STATUS       current
    DESCRIPTION
        "Cisco UCS fabric:EthMonSrcRef:type managed object property"
    ::= { cucsFabricEthMonSrcRefEntry 7 }

cucsFabricEthTargetEpTable OBJECT-TYPE
    SYNTAX           SEQUENCE OF CucsFabricEthTargetEpEntry
    MAX-ACCESS       not-accessible
    STATUS           current
    DESCRIPTION
        "Cisco UCS fabric:EthTargetEp managed object table"
    ::= { cucsFabricObjects 23 }

cucsFabricEthTargetEpEntry OBJECT-TYPE
    SYNTAX           CucsFabricEthTargetEpEntry
    MAX-ACCESS       not-accessible
    STATUS           current
    DESCRIPTION
        "Entry for the cucsFabricEthTargetEpTable table."
    INDEX { cucsFabricEthTargetEpInstanceId }
    ::= { cucsFabricEthTargetEpTable 1 }

CucsFabricEthTargetEpEntry ::= SEQUENCE {
    cucsFabricEthTargetEpInstanceId                                  CucsManagedObjectId,
    cucsFabricEthTargetEpDn                                          CucsManagedObjectDn,
    cucsFabricEthTargetEpRn                                          SnmpAdminString,
    cucsFabricEthTargetEpAdminState                                  CucsFabricExternalEpAdminState,
    cucsFabricEthTargetEpChassisId                                   Gauge32,
    cucsFabricEthTargetEpEpDn                                        SnmpAdminString,
    cucsFabricEthTargetEpIfRole                                      CucsNetworkPortRole,
    cucsFabricEthTargetEpIfType                                      CucsFabricPIoEpIfType,
    cucsFabricEthTargetEpLicGP                                       Unsigned64,
    cucsFabricEthTargetEpLicState                                    CucsLicenseState,
    cucsFabricEthTargetEpLocale                                      CucsFabricExternalEpLocale,
    cucsFabricEthTargetEpMacAddress                                  MacAddress,
    cucsFabricEthTargetEpName                                        SnmpAdminString,
    cucsFabricEthTargetEpPeerDn                                      SnmpAdminString,
    cucsFabricEthTargetEpPeerPortId                                  Gauge32,
    cucsFabricEthTargetEpPeerSlotId                                  Gauge32,
    cucsFabricEthTargetEpPortId                                      CucsFabricPIoEpPortId,
    cucsFabricEthTargetEpSlotId                                      CucsFabricPIoEpSlotId,
    cucsFabricEthTargetEpSwitchId                                    CucsNetworkSwitchId,
    cucsFabricEthTargetEpTransport                                   CucsFabricEthTargetEpTransport,
    cucsFabricEthTargetEpType                                        CucsFabricTargetEpType,
    cucsFabricEthTargetEpPeerChassisId                               Gauge32,
    cucsFabricEthTargetEpFltAggr                                     Unsigned64,
    cucsFabricEthTargetEpOperState                                   CucsFabricPIoEpOperState,
    cucsFabricEthTargetEpOperStateReason                             SnmpAdminString,
    cucsFabricEthTargetEpWarnings                                    CucsFabricWarnings,
    cucsFabricEthTargetEpAggrPortId                                  Gauge32,
    cucsFabricEthTargetEpPeerAggrPortId                              Gauge32,
    cucsFabricEthTargetEpAutoNegotiate                               TruthValue
}

cucsFabricEthTargetEpInstanceId OBJECT-TYPE
    SYNTAX       CucsManagedObjectId
    MAX-ACCESS   not-accessible
    STATUS       current
    DESCRIPTION
        "Instance identifier of the managed object."
    ::= { cucsFabricEthTargetEpEntry 1 }

cucsFabricEthTargetEpDn OBJECT-TYPE
    SYNTAX       CucsManagedObjectDn
    MAX-ACCESS   read-only
    STATUS       current
    DESCRIPTION
        "Cisco UCS fabric:EthTargetEp:dn managed object property"
    ::= { cucsFabricEthTargetEpEntry 2 }

cucsFabricEthTargetEpRn OBJECT-TYPE
    SYNTAX       SnmpAdminString
    MAX-ACCESS   read-only
    STATUS       current
    DESCRIPTION
        "Cisco UCS fabric:EthTargetEp:rn managed object property"
    ::= { cucsFabricEthTargetEpEntry 3 }

cucsFabricEthTargetEpAdminState OBJECT-TYPE
    SYNTAX       CucsFabricExternalEpAdminState
    MAX-ACCESS   read-only
    STATUS       current
    DESCRIPTION
        "Cisco UCS fabric:EthTargetEp:adminState managed object property"
    ::= { cucsFabricEthTargetEpEntry 4 }

cucsFabricEthTargetEpChassisId OBJECT-TYPE
    SYNTAX       Gauge32
    MAX-ACCESS   read-only
    STATUS       current
    DESCRIPTION
        "Cisco UCS fabric:EthTargetEp:chassisId managed object property"
    ::= { cucsFabricEthTargetEpEntry 5 }

cucsFabricEthTargetEpEpDn OBJECT-TYPE
    SYNTAX       SnmpAdminString
    MAX-ACCESS   read-only
    STATUS       current
    DESCRIPTION
        "Cisco UCS fabric:EthTargetEp:epDn managed object property"
    ::= { cucsFabricEthTargetEpEntry 6 }

cucsFabricEthTargetEpIfRole OBJECT-TYPE
    SYNTAX       CucsNetworkPortRole
    MAX-ACCESS   read-only
    STATUS       current
    DESCRIPTION
        "Cisco UCS fabric:EthTargetEp:ifRole managed object property"
    ::= { cucsFabricEthTargetEpEntry 7 }

cucsFabricEthTargetEpIfType OBJECT-TYPE
    SYNTAX       CucsFabricPIoEpIfType
    MAX-ACCESS   read-only
    STATUS       current
    DESCRIPTION
        "Cisco UCS fabric:EthTargetEp:ifType managed object property"
    ::= { cucsFabricEthTargetEpEntry 8 }

cucsFabricEthTargetEpLicGP OBJECT-TYPE
    SYNTAX       Unsigned64
    MAX-ACCESS   read-only
    STATUS       current
    DESCRIPTION
        "Cisco UCS fabric:EthTargetEp:licGP managed object property"
    ::= { cucsFabricEthTargetEpEntry 9 }

cucsFabricEthTargetEpLicState OBJECT-TYPE
    SYNTAX       CucsLicenseState
    MAX-ACCESS   read-only
    STATUS       current
    DESCRIPTION
        "Cisco UCS fabric:EthTargetEp:licState managed object property"
    ::= { cucsFabricEthTargetEpEntry 10 }

cucsFabricEthTargetEpLocale OBJECT-TYPE
    SYNTAX       CucsFabricExternalEpLocale
    MAX-ACCESS   read-only
    STATUS       current
    DESCRIPTION
        "Cisco UCS fabric:EthTargetEp:locale managed object property"
    ::= { cucsFabricEthTargetEpEntry 11 }

cucsFabricEthTargetEpMacAddress OBJECT-TYPE
    SYNTAX       MacAddress
    MAX-ACCESS   read-only
    STATUS       current
    DESCRIPTION
        "Cisco UCS fabric:EthTargetEp:macAddress managed object property"
    ::= { cucsFabricEthTargetEpEntry 12 }

cucsFabricEthTargetEpName OBJECT-TYPE
    SYNTAX       SnmpAdminString
    MAX-ACCESS   read-only
    STATUS       current
    DESCRIPTION
        "Cisco UCS fabric:EthTargetEp:name managed object property"
    ::= { cucsFabricEthTargetEpEntry 13 }

cucsFabricEthTargetEpPeerDn OBJECT-TYPE
    SYNTAX       SnmpAdminString
    MAX-ACCESS   read-only
    STATUS       current
    DESCRIPTION
        "Cisco UCS fabric:EthTargetEp:peerDn managed object property"
    ::= { cucsFabricEthTargetEpEntry 14 }

cucsFabricEthTargetEpPeerPortId OBJECT-TYPE
    SYNTAX       Gauge32
    MAX-ACCESS   read-only
    STATUS       current
    DESCRIPTION
        "Cisco UCS fabric:EthTargetEp:peerPortId managed object property"
    ::= { cucsFabricEthTargetEpEntry 15 }

cucsFabricEthTargetEpPeerSlotId OBJECT-TYPE
    SYNTAX       Gauge32
    MAX-ACCESS   read-only
    STATUS       current
    DESCRIPTION
        "Cisco UCS fabric:EthTargetEp:peerSlotId managed object property"
    ::= { cucsFabricEthTargetEpEntry 16 }

cucsFabricEthTargetEpPortId OBJECT-TYPE
    SYNTAX       CucsFabricPIoEpPortId
    MAX-ACCESS   read-only
    STATUS       current
    DESCRIPTION
        "Cisco UCS fabric:EthTargetEp:portId managed object property"
    ::= { cucsFabricEthTargetEpEntry 17 }

cucsFabricEthTargetEpSlotId OBJECT-TYPE
    SYNTAX       CucsFabricPIoEpSlotId
    MAX-ACCESS   read-only
    STATUS       current
    DESCRIPTION
        "Cisco UCS fabric:EthTargetEp:slotId managed object property"
    ::= { cucsFabricEthTargetEpEntry 18 }

cucsFabricEthTargetEpSwitchId OBJECT-TYPE
    SYNTAX       CucsNetworkSwitchId
    MAX-ACCESS   read-only
    STATUS       current
    DESCRIPTION
        "Cisco UCS fabric:EthTargetEp:switchId managed object property"
    ::= { cucsFabricEthTargetEpEntry 19 }

cucsFabricEthTargetEpTransport OBJECT-TYPE
    SYNTAX       CucsFabricEthTargetEpTransport
    MAX-ACCESS   read-only
    STATUS       current
    DESCRIPTION
        "Cisco UCS fabric:EthTargetEp:transport managed object property"
    ::= { cucsFabricEthTargetEpEntry 20 }

cucsFabricEthTargetEpType OBJECT-TYPE
    SYNTAX       CucsFabricTargetEpType
    MAX-ACCESS   read-only
    STATUS       current
    DESCRIPTION
        "Cisco UCS fabric:EthTargetEp:type managed object property"
    ::= { cucsFabricEthTargetEpEntry 21 }

cucsFabricEthTargetEpPeerChassisId OBJECT-TYPE
    SYNTAX       Gauge32
    MAX-ACCESS   read-only
    STATUS       current
    DESCRIPTION
        "Cisco UCS fabric:EthTargetEp:peerChassisId managed
        object property"
    ::= { cucsFabricEthTargetEpEntry 22 }

cucsFabricEthTargetEpFltAggr OBJECT-TYPE
    SYNTAX       Unsigned64
    MAX-ACCESS   read-only
    STATUS       current
    DESCRIPTION
        "Cisco UCS fabric:EthTargetEp:fltAggr managed object property"
    ::= { cucsFabricEthTargetEpEntry 23 }

cucsFabricEthTargetEpOperState OBJECT-TYPE
    SYNTAX       CucsFabricPIoEpOperState
    MAX-ACCESS   read-only
    STATUS       current
    DESCRIPTION
        "Cisco UCS fabric:EthTargetEp:operState managed object property"
    ::= { cucsFabricEthTargetEpEntry 24 }

cucsFabricEthTargetEpOperStateReason OBJECT-TYPE
    SYNTAX       SnmpAdminString
    MAX-ACCESS   read-only
    STATUS       current
    DESCRIPTION
        "Cisco UCS fabric:EthTargetEp:operStateReason managed
        object property"
    ::= { cucsFabricEthTargetEpEntry 25 }

cucsFabricEthTargetEpWarnings OBJECT-TYPE
    SYNTAX       CucsFabricWarnings
    MAX-ACCESS   read-only
    STATUS       current
    DESCRIPTION
        "Cisco UCS fabric:EthTargetEp:warnings managed object property"
    ::= { cucsFabricEthTargetEpEntry 26 }

cucsFabricEthTargetEpAggrPortId OBJECT-TYPE
    SYNTAX       Gauge32
    MAX-ACCESS   read-only
    STATUS       current
    DESCRIPTION
        "Cisco UCS fabric:EthTargetEp:aggrPortId managed object property"
    ::= { cucsFabricEthTargetEpEntry 27 }

cucsFabricEthTargetEpPeerAggrPortId OBJECT-TYPE
    SYNTAX       Gauge32
    MAX-ACCESS   read-only
    STATUS       current
    DESCRIPTION
        "Cisco UCS fabric:EthTargetEp:peerAggrPortId managed
        object property"
    ::= { cucsFabricEthTargetEpEntry 28 }

cucsFabricEthTargetEpAutoNegotiate OBJECT-TYPE
    SYNTAX       TruthValue
    MAX-ACCESS   read-only
    STATUS       current
    DESCRIPTION
        "Cisco UCS fabric:EthTargetEp:autoNegotiate managed
        object property"
    ::= { cucsFabricEthTargetEpEntry 29 }

cucsFabricEthVlanPcTable OBJECT-TYPE
    SYNTAX           SEQUENCE OF CucsFabricEthVlanPcEntry
    MAX-ACCESS       not-accessible
    STATUS           current
    DESCRIPTION
        "Cisco UCS fabric:EthVlanPc managed object table"
    ::= { cucsFabricObjects 69 }

cucsFabricEthVlanPcEntry OBJECT-TYPE
    SYNTAX           CucsFabricEthVlanPcEntry
    MAX-ACCESS       not-accessible
    STATUS           current
    DESCRIPTION
        "Entry for the cucsFabricEthVlanPcTable table."
    INDEX { cucsFabricEthVlanPcInstanceId }
    ::= { cucsFabricEthVlanPcTable 1 }

CucsFabricEthVlanPcEntry ::= SEQUENCE {
    cucsFabricEthVlanPcInstanceId                                    CucsManagedObjectId,
    cucsFabricEthVlanPcDn                                            CucsManagedObjectDn,
    cucsFabricEthVlanPcRn                                            SnmpAdminString,
    cucsFabricEthVlanPcAdminSpeed                                    CucsPortEthAdminSpeed,
    cucsFabricEthVlanPcAdminState                                    CucsFabricCIoEpAdminState,
    cucsFabricEthVlanPcEpDn                                          SnmpAdminString,
    cucsFabricEthVlanPcFltAggr                                       Unsigned64,
    cucsFabricEthVlanPcIfRole                                        CucsFabricEstcPcIfRole,
    cucsFabricEthVlanPcIfType                                        CucsFabricCIoEpIfType,
    cucsFabricEthVlanPcIsNative                                      TruthValue,
    cucsFabricEthVlanPcLocale                                        CucsFabricExternalPcLocale,
    cucsFabricEthVlanPcName                                          SnmpAdminString,
    cucsFabricEthVlanPcOperSpeed                                     CucsPortEthSpeed,
    cucsFabricEthVlanPcOperState                                     CucsNetworkPortOperState,
    cucsFabricEthVlanPcPeerDn                                        SnmpAdminString,
    cucsFabricEthVlanPcPortId                                        Gauge32,
    cucsFabricEthVlanPcStateQual                                     SnmpAdminString,
    cucsFabricEthVlanPcSwitchId                                      CucsNetworkSwitchId,
    cucsFabricEthVlanPcTransport                                     CucsFabricEthVlanPcTransport,
    cucsFabricEthVlanPcType                                          CucsFabricEstcPcType,
    cucsFabricEthVlanPcWarnings                                      CucsFabricWarnings,
    cucsFabricEthVlanPcDescr                                         SnmpAdminString
}

cucsFabricEthVlanPcInstanceId OBJECT-TYPE
    SYNTAX       CucsManagedObjectId
    MAX-ACCESS   not-accessible
    STATUS       current
    DESCRIPTION
        "Instance identifier of the managed object."
    ::= { cucsFabricEthVlanPcEntry 1 }

cucsFabricEthVlanPcDn OBJECT-TYPE
    SYNTAX       CucsManagedObjectDn
    MAX-ACCESS   read-only
    STATUS       current
    DESCRIPTION
        "Cisco UCS fabric:EthVlanPc:dn managed object property"
    ::= { cucsFabricEthVlanPcEntry 2 }

cucsFabricEthVlanPcRn OBJECT-TYPE
    SYNTAX       SnmpAdminString
    MAX-ACCESS   read-only
    STATUS       current
    DESCRIPTION
        "Cisco UCS fabric:EthVlanPc:rn managed object property"
    ::= { cucsFabricEthVlanPcEntry 3 }

cucsFabricEthVlanPcAdminSpeed OBJECT-TYPE
    SYNTAX       CucsPortEthAdminSpeed
    MAX-ACCESS   read-only
    STATUS       current
    DESCRIPTION
        "Cisco UCS fabric:EthVlanPc:adminSpeed managed object property"
    ::= { cucsFabricEthVlanPcEntry 4 }

cucsFabricEthVlanPcAdminState OBJECT-TYPE
    SYNTAX       CucsFabricCIoEpAdminState
    MAX-ACCESS   read-only
    STATUS       current
    DESCRIPTION
        "Cisco UCS fabric:EthVlanPc:adminState managed object property"
    ::= { cucsFabricEthVlanPcEntry 5 }

cucsFabricEthVlanPcEpDn OBJECT-TYPE
    SYNTAX       SnmpAdminString
    MAX-ACCESS   read-only
    STATUS       current
    DESCRIPTION
        "Cisco UCS fabric:EthVlanPc:epDn managed object property"
    ::= { cucsFabricEthVlanPcEntry 6 }

cucsFabricEthVlanPcFltAggr OBJECT-TYPE
    SYNTAX       Unsigned64
    MAX-ACCESS   read-only
    STATUS       current
    DESCRIPTION
        "Cisco UCS fabric:EthVlanPc:fltAggr managed object property"
    ::= { cucsFabricEthVlanPcEntry 7 }

cucsFabricEthVlanPcIfRole OBJECT-TYPE
    SYNTAX       CucsFabricEstcPcIfRole
    MAX-ACCESS   read-only
    STATUS       current
    DESCRIPTION
        "Cisco UCS fabric:EthVlanPc:ifRole managed object property"
    ::= { cucsFabricEthVlanPcEntry 8 }

cucsFabricEthVlanPcIfType OBJECT-TYPE
    SYNTAX       CucsFabricCIoEpIfType
    MAX-ACCESS   read-only
    STATUS       current
    DESCRIPTION
        "Cisco UCS fabric:EthVlanPc:ifType managed object property"
    ::= { cucsFabricEthVlanPcEntry 9 }

cucsFabricEthVlanPcIsNative OBJECT-TYPE
    SYNTAX       TruthValue
    MAX-ACCESS   read-only
    STATUS       current
    DESCRIPTION
        "Cisco UCS fabric:EthVlanPc:isNative managed object property"
    ::= { cucsFabricEthVlanPcEntry 10 }

cucsFabricEthVlanPcLocale OBJECT-TYPE
    SYNTAX       CucsFabricExternalPcLocale
    MAX-ACCESS   read-only
    STATUS       current
    DESCRIPTION
        "Cisco UCS fabric:EthVlanPc:locale managed object property"
    ::= { cucsFabricEthVlanPcEntry 11 }

cucsFabricEthVlanPcName OBJECT-TYPE
    SYNTAX       SnmpAdminString
    MAX-ACCESS   read-only
    STATUS       current
    DESCRIPTION
        "Cisco UCS fabric:EthVlanPc:name managed object property"
    ::= { cucsFabricEthVlanPcEntry 12 }

cucsFabricEthVlanPcOperSpeed OBJECT-TYPE
    SYNTAX       CucsPortEthSpeed
    MAX-ACCESS   read-only
    STATUS       current
    DESCRIPTION
        "Cisco UCS fabric:EthVlanPc:operSpeed managed object property"
    ::= { cucsFabricEthVlanPcEntry 13 }

cucsFabricEthVlanPcOperState OBJECT-TYPE
    SYNTAX       CucsNetworkPortOperState
    MAX-ACCESS   read-only
    STATUS       current
    DESCRIPTION
        "Cisco UCS fabric:EthVlanPc:operState managed object property"
    ::= { cucsFabricEthVlanPcEntry 14 }

cucsFabricEthVlanPcPeerDn OBJECT-TYPE
    SYNTAX       SnmpAdminString
    MAX-ACCESS   read-only
    STATUS       current
    DESCRIPTION
        "Cisco UCS fabric:EthVlanPc:peerDn managed object property"
    ::= { cucsFabricEthVlanPcEntry 15 }

cucsFabricEthVlanPcPortId OBJECT-TYPE
    SYNTAX       Gauge32
    MAX-ACCESS   read-only
    STATUS       current
    DESCRIPTION
        "Cisco UCS fabric:EthVlanPc:portId managed object property"
    ::= { cucsFabricEthVlanPcEntry 16 }

cucsFabricEthVlanPcStateQual OBJECT-TYPE
    SYNTAX       SnmpAdminString
    MAX-ACCESS   read-only
    STATUS       current
    DESCRIPTION
        "Cisco UCS fabric:EthVlanPc:stateQual managed object property"
    ::= { cucsFabricEthVlanPcEntry 17 }

cucsFabricEthVlanPcSwitchId OBJECT-TYPE
    SYNTAX       CucsNetworkSwitchId
    MAX-ACCESS   read-only
    STATUS       current
    DESCRIPTION
        "Cisco UCS fabric:EthVlanPc:switchId managed object property"
    ::= { cucsFabricEthVlanPcEntry 18 }

cucsFabricEthVlanPcTransport OBJECT-TYPE
    SYNTAX       CucsFabricEthVlanPcTransport
    MAX-ACCESS   read-only
    STATUS       current
    DESCRIPTION
        "Cisco UCS fabric:EthVlanPc:transport managed object property"
    ::= { cucsFabricEthVlanPcEntry 19 }

cucsFabricEthVlanPcType OBJECT-TYPE
    SYNTAX       CucsFabricEstcPcType
    MAX-ACCESS   read-only
    STATUS       current
    DESCRIPTION
        "Cisco UCS fabric:EthVlanPc:type managed object property"
    ::= { cucsFabricEthVlanPcEntry 20 }

cucsFabricEthVlanPcWarnings OBJECT-TYPE
    SYNTAX       CucsFabricWarnings
    MAX-ACCESS   read-only
    STATUS       current
    DESCRIPTION
        "Cisco UCS fabric:EthVlanPc:warnings managed object property"
    ::= { cucsFabricEthVlanPcEntry 21 }

cucsFabricEthVlanPcDescr OBJECT-TYPE
    SYNTAX       SnmpAdminString
    MAX-ACCESS   read-only
    STATUS       current
    DESCRIPTION
        "Cisco UCS fabric:EthVlanPc:descr managed object property"
    ::= { cucsFabricEthVlanPcEntry 22 }

cucsFabricEthVlanPortEpTable OBJECT-TYPE
    SYNTAX           SEQUENCE OF CucsFabricEthVlanPortEpEntry
    MAX-ACCESS       not-accessible
    STATUS           current
    DESCRIPTION
        "Cisco UCS fabric:EthVlanPortEp managed object table"
    ::= { cucsFabricObjects 24 }

cucsFabricEthVlanPortEpEntry OBJECT-TYPE
    SYNTAX           CucsFabricEthVlanPortEpEntry
    MAX-ACCESS       not-accessible
    STATUS           current
    DESCRIPTION
        "Entry for the cucsFabricEthVlanPortEpTable table."
    INDEX { cucsFabricEthVlanPortEpInstanceId }
    ::= { cucsFabricEthVlanPortEpTable 1 }

CucsFabricEthVlanPortEpEntry ::= SEQUENCE {
    cucsFabricEthVlanPortEpInstanceId                                CucsManagedObjectId,
    cucsFabricEthVlanPortEpDn                                        CucsManagedObjectDn,
    cucsFabricEthVlanPortEpRn                                        SnmpAdminString,
    cucsFabricEthVlanPortEpAdminState                                CucsFabricExternalEpAdminState,
    cucsFabricEthVlanPortEpChassisId                                 Gauge32,
    cucsFabricEthVlanPortEpEpDn                                      SnmpAdminString,
    cucsFabricEthVlanPortEpIfRole                                    CucsFabricLanEpIfRole,
    cucsFabricEthVlanPortEpIfType                                    CucsFabricPIoEpIfType,
    cucsFabricEthVlanPortEpIsNative                                  TruthValue,
    cucsFabricEthVlanPortEpLicGP                                     Unsigned64,
    cucsFabricEthVlanPortEpLicState                                  CucsLicenseState,
    cucsFabricEthVlanPortEpLocale                                    CucsFabricExternalEpLocale,
    cucsFabricEthVlanPortEpName                                      SnmpAdminString,
    cucsFabricEthVlanPortEpPeerDn                                    SnmpAdminString,
    cucsFabricEthVlanPortEpPeerPortId                                Gauge32,
    cucsFabricEthVlanPortEpPeerSlotId                                Gauge32,
    cucsFabricEthVlanPortEpPortId                                    Gauge32,
    cucsFabricEthVlanPortEpSlotId                                    Gauge32,
    cucsFabricEthVlanPortEpSwitchId                                  CucsNetworkSwitchId,
    cucsFabricEthVlanPortEpTransport                                 CucsFabricAEthLanEpTransport,
    cucsFabricEthVlanPortEpType                                      CucsFabricLanEpType,
    cucsFabricEthVlanPortEpPeerChassisId                             Gauge32,
    cucsFabricEthVlanPortEpFltAggr                                   Unsigned64,
    cucsFabricEthVlanPortEpOperState                                 CucsFabricPIoEpOperState,
    cucsFabricEthVlanPortEpOperStateReason                           SnmpAdminString,
    cucsFabricEthVlanPortEpWarnings                                  CucsFabricWarnings,
    cucsFabricEthVlanPortEpAggrPortId                                Gauge32,
    cucsFabricEthVlanPortEpPeerAggrPortId                            Gauge32,
    cucsFabricEthVlanPortEpAutoNegotiate                             TruthValue
}

cucsFabricEthVlanPortEpInstanceId OBJECT-TYPE
    SYNTAX       CucsManagedObjectId
    MAX-ACCESS   not-accessible
    STATUS       current
    DESCRIPTION
        "Instance identifier of the managed object."
    ::= { cucsFabricEthVlanPortEpEntry 1 }

cucsFabricEthVlanPortEpDn OBJECT-TYPE
    SYNTAX       CucsManagedObjectDn
    MAX-ACCESS   read-only
    STATUS       current
    DESCRIPTION
        "Cisco UCS fabric:EthVlanPortEp:dn managed object property"
    ::= { cucsFabricEthVlanPortEpEntry 2 }

cucsFabricEthVlanPortEpRn OBJECT-TYPE
    SYNTAX       SnmpAdminString
    MAX-ACCESS   read-only
    STATUS       current
    DESCRIPTION
        "Cisco UCS fabric:EthVlanPortEp:rn managed object property"
    ::= { cucsFabricEthVlanPortEpEntry 3 }

cucsFabricEthVlanPortEpAdminState OBJECT-TYPE
    SYNTAX       CucsFabricExternalEpAdminState
    MAX-ACCESS   read-only
    STATUS       current
    DESCRIPTION
        "Cisco UCS fabric:EthVlanPortEp:adminState managed
        object property"
    ::= { cucsFabricEthVlanPortEpEntry 4 }

cucsFabricEthVlanPortEpChassisId OBJECT-TYPE
    SYNTAX       Gauge32
    MAX-ACCESS   read-only
    STATUS       current
    DESCRIPTION
        "Cisco UCS fabric:EthVlanPortEp:chassisId managed object property"
    ::= { cucsFabricEthVlanPortEpEntry 5 }

cucsFabricEthVlanPortEpEpDn OBJECT-TYPE
    SYNTAX       SnmpAdminString
    MAX-ACCESS   read-only
    STATUS       current
    DESCRIPTION
        "Cisco UCS fabric:EthVlanPortEp:epDn managed object property"
    ::= { cucsFabricEthVlanPortEpEntry 6 }

cucsFabricEthVlanPortEpIfRole OBJECT-TYPE
    SYNTAX       CucsFabricLanEpIfRole
    MAX-ACCESS   read-only
    STATUS       current
    DESCRIPTION
        "Cisco UCS fabric:EthVlanPortEp:ifRole managed object property"
    ::= { cucsFabricEthVlanPortEpEntry 7 }

cucsFabricEthVlanPortEpIfType OBJECT-TYPE
    SYNTAX       CucsFabricPIoEpIfType
    MAX-ACCESS   read-only
    STATUS       current
    DESCRIPTION
        "Cisco UCS fabric:EthVlanPortEp:ifType managed object property"
    ::= { cucsFabricEthVlanPortEpEntry 8 }

cucsFabricEthVlanPortEpIsNative OBJECT-TYPE
    SYNTAX       TruthValue
    MAX-ACCESS   read-only
    STATUS       current
    DESCRIPTION
        "Cisco UCS fabric:EthVlanPortEp:isNative managed object property"
    ::= { cucsFabricEthVlanPortEpEntry 9 }

cucsFabricEthVlanPortEpLicGP OBJECT-TYPE
    SYNTAX       Unsigned64
    MAX-ACCESS   read-only
    STATUS       current
    DESCRIPTION
        "Cisco UCS fabric:EthVlanPortEp:licGP managed object property"
    ::= { cucsFabricEthVlanPortEpEntry 10 }

cucsFabricEthVlanPortEpLicState OBJECT-TYPE
    SYNTAX       CucsLicenseState
    MAX-ACCESS   read-only
    STATUS       current
    DESCRIPTION
        "Cisco UCS fabric:EthVlanPortEp:licState managed object property"
    ::= { cucsFabricEthVlanPortEpEntry 11 }

cucsFabricEthVlanPortEpLocale OBJECT-TYPE
    SYNTAX       CucsFabricExternalEpLocale
    MAX-ACCESS   read-only
    STATUS       current
    DESCRIPTION
        "Cisco UCS fabric:EthVlanPortEp:locale managed object property"
    ::= { cucsFabricEthVlanPortEpEntry 12 }

cucsFabricEthVlanPortEpName OBJECT-TYPE
    SYNTAX       SnmpAdminString
    MAX-ACCESS   read-only
    STATUS       current
    DESCRIPTION
        "Cisco UCS fabric:EthVlanPortEp:name managed object property"
    ::= { cucsFabricEthVlanPortEpEntry 13 }

cucsFabricEthVlanPortEpPeerDn OBJECT-TYPE
    SYNTAX       SnmpAdminString
    MAX-ACCESS   read-only
    STATUS       current
    DESCRIPTION
        "Cisco UCS fabric:EthVlanPortEp:peerDn managed object property"
    ::= { cucsFabricEthVlanPortEpEntry 14 }

cucsFabricEthVlanPortEpPeerPortId OBJECT-TYPE
    SYNTAX       Gauge32
    MAX-ACCESS   read-only
    STATUS       current
    DESCRIPTION
        "Cisco UCS fabric:EthVlanPortEp:peerPortId managed
        object property"
    ::= { cucsFabricEthVlanPortEpEntry 15 }

cucsFabricEthVlanPortEpPeerSlotId OBJECT-TYPE
    SYNTAX       Gauge32
    MAX-ACCESS   read-only
    STATUS       current
    DESCRIPTION
        "Cisco UCS fabric:EthVlanPortEp:peerSlotId managed
        object property"
    ::= { cucsFabricEthVlanPortEpEntry 16 }

cucsFabricEthVlanPortEpPortId OBJECT-TYPE
    SYNTAX       Gauge32
    MAX-ACCESS   read-only
    STATUS       current
    DESCRIPTION
        "Cisco UCS fabric:EthVlanPortEp:portId managed object property"
    ::= { cucsFabricEthVlanPortEpEntry 17 }

cucsFabricEthVlanPortEpSlotId OBJECT-TYPE
    SYNTAX       Gauge32
    MAX-ACCESS   read-only
    STATUS       current
    DESCRIPTION
        "Cisco UCS fabric:EthVlanPortEp:slotId managed object property"
    ::= { cucsFabricEthVlanPortEpEntry 18 }

cucsFabricEthVlanPortEpSwitchId OBJECT-TYPE
    SYNTAX       CucsNetworkSwitchId
    MAX-ACCESS   read-only
    STATUS       current
    DESCRIPTION
        "Cisco UCS fabric:EthVlanPortEp:switchId managed object property"
    ::= { cucsFabricEthVlanPortEpEntry 19 }

cucsFabricEthVlanPortEpTransport OBJECT-TYPE
    SYNTAX       CucsFabricAEthLanEpTransport
    MAX-ACCESS   read-only
    STATUS       current
    DESCRIPTION
        "Cisco UCS fabric:EthVlanPortEp:transport managed object property"
    ::= { cucsFabricEthVlanPortEpEntry 20 }

cucsFabricEthVlanPortEpType OBJECT-TYPE
    SYNTAX       CucsFabricLanEpType
    MAX-ACCESS   read-only
    STATUS       current
    DESCRIPTION
        "Cisco UCS fabric:EthVlanPortEp:type managed object property"
    ::= { cucsFabricEthVlanPortEpEntry 21 }

cucsFabricEthVlanPortEpPeerChassisId OBJECT-TYPE
    SYNTAX       Gauge32
    MAX-ACCESS   read-only
    STATUS       current
    DESCRIPTION
        "Cisco UCS fabric:EthVlanPortEp:peerChassisId managed
        object property"
    ::= { cucsFabricEthVlanPortEpEntry 22 }

cucsFabricEthVlanPortEpFltAggr OBJECT-TYPE
    SYNTAX       Unsigned64
    MAX-ACCESS   read-only
    STATUS       current
    DESCRIPTION
        "Cisco UCS fabric:EthVlanPortEp:fltAggr managed object property"
    ::= { cucsFabricEthVlanPortEpEntry 23 }

cucsFabricEthVlanPortEpOperState OBJECT-TYPE
    SYNTAX       CucsFabricPIoEpOperState
    MAX-ACCESS   read-only
    STATUS       current
    DESCRIPTION
        "Cisco UCS fabric:EthVlanPortEp:operState managed object property"
    ::= { cucsFabricEthVlanPortEpEntry 25 }

cucsFabricEthVlanPortEpOperStateReason OBJECT-TYPE
    SYNTAX       SnmpAdminString
    MAX-ACCESS   read-only
    STATUS       current
    DESCRIPTION
        "Cisco UCS fabric:EthVlanPortEp:operStateReason
        managed object property"
    ::= { cucsFabricEthVlanPortEpEntry 26 }

cucsFabricEthVlanPortEpWarnings OBJECT-TYPE
    SYNTAX       CucsFabricWarnings
    MAX-ACCESS   read-only
    STATUS       current
    DESCRIPTION
        "Cisco UCS fabric:EthVlanPortEp:warnings managed object property"
    ::= { cucsFabricEthVlanPortEpEntry 27 }

cucsFabricEthVlanPortEpAggrPortId OBJECT-TYPE
    SYNTAX       Gauge32
    MAX-ACCESS   read-only
    STATUS       current
    DESCRIPTION
        "Cisco UCS fabric:EthVlanPortEp:aggrPortId managed
        object property"
    ::= { cucsFabricEthVlanPortEpEntry 28 }

cucsFabricEthVlanPortEpPeerAggrPortId OBJECT-TYPE
    SYNTAX       Gauge32
    MAX-ACCESS   read-only
    STATUS       current
    DESCRIPTION
        "Cisco UCS fabric:EthVlanPortEp:peerAggrPortId
        managed object property"
    ::= { cucsFabricEthVlanPortEpEntry 29 }

cucsFabricEthVlanPortEpAutoNegotiate OBJECT-TYPE
    SYNTAX       TruthValue
    MAX-ACCESS   read-only
    STATUS       current
    DESCRIPTION
        "Cisco UCS fabric:EthVlanPortEp:autoNegotiate managed
        object property"
    ::= { cucsFabricEthVlanPortEpEntry 30 }

cucsFabricFcEstcTable OBJECT-TYPE
    SYNTAX           SEQUENCE OF CucsFabricFcEstcEntry
    MAX-ACCESS       not-accessible
    STATUS           current
    DESCRIPTION
        "Cisco UCS fabric:FcEstc managed object table"
    ::= { cucsFabricObjects 25 }

cucsFabricFcEstcEntry OBJECT-TYPE
    SYNTAX           CucsFabricFcEstcEntry
    MAX-ACCESS       not-accessible
    STATUS           current
    DESCRIPTION
        "Entry for the cucsFabricFcEstcTable table."
    INDEX { cucsFabricFcEstcInstanceId }
    ::= { cucsFabricFcEstcTable 1 }

CucsFabricFcEstcEntry ::= SEQUENCE {
    cucsFabricFcEstcInstanceId                                       CucsManagedObjectId,
    cucsFabricFcEstcDn                                               CucsManagedObjectDn,
    cucsFabricFcEstcRn                                               SnmpAdminString,
    cucsFabricFcEstcId                                               CucsNetworkSwitchId,
    cucsFabricFcEstcLocale                                           CucsFabricExternalLocale,
    cucsFabricFcEstcName                                             SnmpAdminString,
    cucsFabricFcEstcTransport                                        CucsFabricFcEstcTransport,
    cucsFabricFcEstcType                                             CucsFabricFcEstcType
}

cucsFabricFcEstcInstanceId OBJECT-TYPE
    SYNTAX       CucsManagedObjectId
    MAX-ACCESS   not-accessible
    STATUS       current
    DESCRIPTION
        "Instance identifier of the managed object."
    ::= { cucsFabricFcEstcEntry 1 }

cucsFabricFcEstcDn OBJECT-TYPE
    SYNTAX       CucsManagedObjectDn
    MAX-ACCESS   read-only
    STATUS       current
    DESCRIPTION
        "Cisco UCS fabric:FcEstc:dn managed object property"
    ::= { cucsFabricFcEstcEntry 2 }

cucsFabricFcEstcRn OBJECT-TYPE
    SYNTAX       SnmpAdminString
    MAX-ACCESS   read-only
    STATUS       current
    DESCRIPTION
        "Cisco UCS fabric:FcEstc:rn managed object property"
    ::= { cucsFabricFcEstcEntry 3 }

cucsFabricFcEstcId OBJECT-TYPE
    SYNTAX       CucsNetworkSwitchId
    MAX-ACCESS   read-only
    STATUS       current
    DESCRIPTION
        "Cisco UCS fabric:FcEstc:id managed object property"
    ::= { cucsFabricFcEstcEntry 4 }

cucsFabricFcEstcLocale OBJECT-TYPE
    SYNTAX       CucsFabricExternalLocale
    MAX-ACCESS   read-only
    STATUS       current
    DESCRIPTION
        "Cisco UCS fabric:FcEstc:locale managed object property"
    ::= { cucsFabricFcEstcEntry 5 }

cucsFabricFcEstcName OBJECT-TYPE
    SYNTAX       SnmpAdminString
    MAX-ACCESS   read-only
    STATUS       current
    DESCRIPTION
        "Cisco UCS fabric:FcEstc:name managed object property"
    ::= { cucsFabricFcEstcEntry 6 }

cucsFabricFcEstcTransport OBJECT-TYPE
    SYNTAX       CucsFabricFcEstcTransport
    MAX-ACCESS   read-only
    STATUS       current
    DESCRIPTION
        "Cisco UCS fabric:FcEstc:transport managed object property"
    ::= { cucsFabricFcEstcEntry 7 }

cucsFabricFcEstcType OBJECT-TYPE
    SYNTAX       CucsFabricFcEstcType
    MAX-ACCESS   read-only
    STATUS       current
    DESCRIPTION
        "Cisco UCS fabric:FcEstc:type managed object property"
    ::= { cucsFabricFcEstcEntry 8 }

cucsFabricFcEstcCloudTable OBJECT-TYPE
    SYNTAX           SEQUENCE OF CucsFabricFcEstcCloudEntry
    MAX-ACCESS       not-accessible
    STATUS           current
    DESCRIPTION
        "Cisco UCS fabric:FcEstcCloud managed object table"
    ::= { cucsFabricObjects 26 }

cucsFabricFcEstcCloudEntry OBJECT-TYPE
    SYNTAX           CucsFabricFcEstcCloudEntry
    MAX-ACCESS       not-accessible
    STATUS           current
    DESCRIPTION
        "Entry for the cucsFabricFcEstcCloudTable table."
    INDEX { cucsFabricFcEstcCloudInstanceId }
    ::= { cucsFabricFcEstcCloudTable 1 }

CucsFabricFcEstcCloudEntry ::= SEQUENCE {
    cucsFabricFcEstcCloudInstanceId                                  CucsManagedObjectId,
    cucsFabricFcEstcCloudDn                                          CucsManagedObjectDn,
    cucsFabricFcEstcCloudRn                                          SnmpAdminString
}

cucsFabricFcEstcCloudInstanceId OBJECT-TYPE
    SYNTAX       CucsManagedObjectId
    MAX-ACCESS   not-accessible
    STATUS       current
    DESCRIPTION
        "Instance identifier of the managed object."
    ::= { cucsFabricFcEstcCloudEntry 1 }

cucsFabricFcEstcCloudDn OBJECT-TYPE
    SYNTAX       CucsManagedObjectDn
    MAX-ACCESS   read-only
    STATUS       current
    DESCRIPTION
        "Cisco UCS fabric:FcEstcCloud:dn managed object property"
    ::= { cucsFabricFcEstcCloudEntry 2 }

cucsFabricFcEstcCloudRn OBJECT-TYPE
    SYNTAX       SnmpAdminString
    MAX-ACCESS   read-only
    STATUS       current
    DESCRIPTION
        "Cisco UCS fabric:FcEstcCloud:rn managed object property"
    ::= { cucsFabricFcEstcCloudEntry 3 }

cucsFabricFcEstcEpTable OBJECT-TYPE
    SYNTAX           SEQUENCE OF CucsFabricFcEstcEpEntry
    MAX-ACCESS       not-accessible
    STATUS           current
    DESCRIPTION
        "Cisco UCS fabric:FcEstcEp managed object table"
    ::= { cucsFabricObjects 27 }

cucsFabricFcEstcEpEntry OBJECT-TYPE
    SYNTAX           CucsFabricFcEstcEpEntry
    MAX-ACCESS       not-accessible
    STATUS           current
    DESCRIPTION
        "Entry for the cucsFabricFcEstcEpTable table."
    INDEX { cucsFabricFcEstcEpInstanceId }
    ::= { cucsFabricFcEstcEpTable 1 }

CucsFabricFcEstcEpEntry ::= SEQUENCE {
    cucsFabricFcEstcEpInstanceId                                     CucsManagedObjectId,
    cucsFabricFcEstcEpDn                                             CucsManagedObjectDn,
    cucsFabricFcEstcEpRn                                             SnmpAdminString,
    cucsFabricFcEstcEpAdminState                                     CucsFabricExternalEpAdminState,
    cucsFabricFcEstcEpChassisId                                      Gauge32,
    cucsFabricFcEstcEpConfigState                                    CucsFabricConfigState,
    cucsFabricFcEstcEpEpDn                                           SnmpAdminString,
    cucsFabricFcEstcEpIfRole                                         CucsFabricEstcEpIfRole,
    cucsFabricFcEstcEpIfType                                         CucsFabricPIoEpIfType,
    cucsFabricFcEstcEpLicGP                                          Unsigned64,
    cucsFabricFcEstcEpLicState                                       CucsLicenseState,
    cucsFabricFcEstcEpLocale                                         CucsFabricExternalEpLocale,
    cucsFabricFcEstcEpName                                           SnmpAdminString,
    cucsFabricFcEstcEpPeerDn                                         SnmpAdminString,
    cucsFabricFcEstcEpPeerPortId                                     Gauge32,
    cucsFabricFcEstcEpPeerSlotId                                     Gauge32,
    cucsFabricFcEstcEpPortId                                         CucsFabricFcEstcEpPortId,
    cucsFabricFcEstcEpSlotId                                         CucsFabricFcEstcEpSlotId,
    cucsFabricFcEstcEpSwitchId                                       CucsNetworkSwitchId,
    cucsFabricFcEstcEpTransport                                      CucsFabricAFcEstcEpTransport,
    cucsFabricFcEstcEpType                                           CucsFabricAFcEstcEpType,
    cucsFabricFcEstcEpUsrLbl                                         SnmpAdminString,
    cucsFabricFcEstcEpPeerChassisId                                  Gauge32,
    cucsFabricFcEstcEpFltAggr                                        Unsigned64,
    cucsFabricFcEstcEpOperState                                      CucsFabricPIoEpOperState,
    cucsFabricFcEstcEpOperStateReason                                SnmpAdminString,
    cucsFabricFcEstcEpWarnings                                       CucsFabricWarnings,
    cucsFabricFcEstcEpFillPattern                                    CucsFabricFillPattern,
    cucsFabricFcEstcEpAggrPortId                                     Gauge32,
    cucsFabricFcEstcEpPeerAggrPortId                                 Gauge32,
    cucsFabricFcEstcEpAutoNegotiate                                  TruthValue
}

cucsFabricFcEstcEpInstanceId OBJECT-TYPE
    SYNTAX       CucsManagedObjectId
    MAX-ACCESS   not-accessible
    STATUS       current
    DESCRIPTION
        "Instance identifier of the managed object."
    ::= { cucsFabricFcEstcEpEntry 1 }

cucsFabricFcEstcEpDn OBJECT-TYPE
    SYNTAX       CucsManagedObjectDn
    MAX-ACCESS   read-only
    STATUS       current
    DESCRIPTION
        "Cisco UCS fabric:FcEstcEp:dn managed object property"
    ::= { cucsFabricFcEstcEpEntry 2 }

cucsFabricFcEstcEpRn OBJECT-TYPE
    SYNTAX       SnmpAdminString
    MAX-ACCESS   read-only
    STATUS       current
    DESCRIPTION
        "Cisco UCS fabric:FcEstcEp:rn managed object property"
    ::= { cucsFabricFcEstcEpEntry 3 }

cucsFabricFcEstcEpAdminState OBJECT-TYPE
    SYNTAX       CucsFabricExternalEpAdminState
    MAX-ACCESS   read-only
    STATUS       current
    DESCRIPTION
        "Cisco UCS fabric:FcEstcEp:adminState managed object property"
    ::= { cucsFabricFcEstcEpEntry 4 }

cucsFabricFcEstcEpChassisId OBJECT-TYPE
    SYNTAX       Gauge32
    MAX-ACCESS   read-only
    STATUS       current
    DESCRIPTION
        "Cisco UCS fabric:FcEstcEp:chassisId managed object property"
    ::= { cucsFabricFcEstcEpEntry 5 }

cucsFabricFcEstcEpConfigState OBJECT-TYPE
    SYNTAX       CucsFabricConfigState
    MAX-ACCESS   read-only
    STATUS       current
    DESCRIPTION
        "Cisco UCS fabric:FcEstcEp:configState managed object property"
    ::= { cucsFabricFcEstcEpEntry 6 }

cucsFabricFcEstcEpEpDn OBJECT-TYPE
    SYNTAX       SnmpAdminString
    MAX-ACCESS   read-only
    STATUS       current
    DESCRIPTION
        "Cisco UCS fabric:FcEstcEp:epDn managed object property"
    ::= { cucsFabricFcEstcEpEntry 7 }

cucsFabricFcEstcEpIfRole OBJECT-TYPE
    SYNTAX       CucsFabricEstcEpIfRole
    MAX-ACCESS   read-only
    STATUS       current
    DESCRIPTION
        "Cisco UCS fabric:FcEstcEp:ifRole managed object property"
    ::= { cucsFabricFcEstcEpEntry 8 }

cucsFabricFcEstcEpIfType OBJECT-TYPE
    SYNTAX       CucsFabricPIoEpIfType
    MAX-ACCESS   read-only
    STATUS       current
    DESCRIPTION
        "Cisco UCS fabric:FcEstcEp:ifType managed object property"
    ::= { cucsFabricFcEstcEpEntry 9 }

cucsFabricFcEstcEpLicGP OBJECT-TYPE
    SYNTAX       Unsigned64
    MAX-ACCESS   read-only
    STATUS       current
    DESCRIPTION
        "Cisco UCS fabric:FcEstcEp:licGP managed object property"
    ::= { cucsFabricFcEstcEpEntry 10 }

cucsFabricFcEstcEpLicState OBJECT-TYPE
    SYNTAX       CucsLicenseState
    MAX-ACCESS   read-only
    STATUS       current
    DESCRIPTION
        "Cisco UCS fabric:FcEstcEp:licState managed object property"
    ::= { cucsFabricFcEstcEpEntry 11 }

cucsFabricFcEstcEpLocale OBJECT-TYPE
    SYNTAX       CucsFabricExternalEpLocale
    MAX-ACCESS   read-only
    STATUS       current
    DESCRIPTION
        "Cisco UCS fabric:FcEstcEp:locale managed object property"
    ::= { cucsFabricFcEstcEpEntry 12 }

cucsFabricFcEstcEpName OBJECT-TYPE
    SYNTAX       SnmpAdminString
    MAX-ACCESS   read-only
    STATUS       current
    DESCRIPTION
        "Cisco UCS fabric:FcEstcEp:name managed object property"
    ::= { cucsFabricFcEstcEpEntry 13 }

cucsFabricFcEstcEpPeerDn OBJECT-TYPE
    SYNTAX       SnmpAdminString
    MAX-ACCESS   read-only
    STATUS       current
    DESCRIPTION
        "Cisco UCS fabric:FcEstcEp:peerDn managed object property"
    ::= { cucsFabricFcEstcEpEntry 14 }

cucsFabricFcEstcEpPeerPortId OBJECT-TYPE
    SYNTAX       Gauge32
    MAX-ACCESS   read-only
    STATUS       current
    DESCRIPTION
        "Cisco UCS fabric:FcEstcEp:peerPortId managed object property"
    ::= { cucsFabricFcEstcEpEntry 15 }

cucsFabricFcEstcEpPeerSlotId OBJECT-TYPE
    SYNTAX       Gauge32
    MAX-ACCESS   read-only
    STATUS       current
    DESCRIPTION
        "Cisco UCS fabric:FcEstcEp:peerSlotId managed object property"
    ::= { cucsFabricFcEstcEpEntry 16 }

cucsFabricFcEstcEpPortId OBJECT-TYPE
    SYNTAX       CucsFabricFcEstcEpPortId
    MAX-ACCESS   read-only
    STATUS       current
    DESCRIPTION
        "Cisco UCS fabric:FcEstcEp:portId managed object property"
    ::= { cucsFabricFcEstcEpEntry 17 }

cucsFabricFcEstcEpSlotId OBJECT-TYPE
    SYNTAX       CucsFabricFcEstcEpSlotId
    MAX-ACCESS   read-only
    STATUS       current
    DESCRIPTION
        "Cisco UCS fabric:FcEstcEp:slotId managed object property"
    ::= { cucsFabricFcEstcEpEntry 18 }

cucsFabricFcEstcEpSwitchId OBJECT-TYPE
    SYNTAX       CucsNetworkSwitchId
    MAX-ACCESS   read-only
    STATUS       current
    DESCRIPTION
        "Cisco UCS fabric:FcEstcEp:switchId managed object property"
    ::= { cucsFabricFcEstcEpEntry 19 }

cucsFabricFcEstcEpTransport OBJECT-TYPE
    SYNTAX       CucsFabricAFcEstcEpTransport
    MAX-ACCESS   read-only
    STATUS       current
    DESCRIPTION
        "Cisco UCS fabric:FcEstcEp:transport managed object property"
    ::= { cucsFabricFcEstcEpEntry 20 }

cucsFabricFcEstcEpType OBJECT-TYPE
    SYNTAX       CucsFabricAFcEstcEpType
    MAX-ACCESS   read-only
    STATUS       current
    DESCRIPTION
        "Cisco UCS fabric:FcEstcEp:type managed object property"
    ::= { cucsFabricFcEstcEpEntry 21 }

cucsFabricFcEstcEpUsrLbl OBJECT-TYPE
    SYNTAX       SnmpAdminString
    MAX-ACCESS   read-only
    STATUS       current
    DESCRIPTION
        "Cisco UCS fabric:FcEstcEp:usrLbl managed object property"
    ::= { cucsFabricFcEstcEpEntry 22 }

cucsFabricFcEstcEpPeerChassisId OBJECT-TYPE
    SYNTAX       Gauge32
    MAX-ACCESS   read-only
    STATUS       current
    DESCRIPTION
        "Cisco UCS fabric:FcEstcEp:peerChassisId managed object property"
    ::= { cucsFabricFcEstcEpEntry 23 }

cucsFabricFcEstcEpFltAggr OBJECT-TYPE
    SYNTAX       Unsigned64
    MAX-ACCESS   read-only
    STATUS       current
    DESCRIPTION
        "Cisco UCS fabric:FcEstcEp:fltAggr managed object property"
    ::= { cucsFabricFcEstcEpEntry 24 }

cucsFabricFcEstcEpOperState OBJECT-TYPE
    SYNTAX       CucsFabricPIoEpOperState
    MAX-ACCESS   read-only
    STATUS       current
    DESCRIPTION
        "Cisco UCS fabric:FcEstcEp:operState managed object property"
    ::= { cucsFabricFcEstcEpEntry 25 }

cucsFabricFcEstcEpOperStateReason OBJECT-TYPE
    SYNTAX       SnmpAdminString
    MAX-ACCESS   read-only
    STATUS       current
    DESCRIPTION
        "Cisco UCS fabric:FcEstcEp:operStateReason managed
        object property"
    ::= { cucsFabricFcEstcEpEntry 26 }

cucsFabricFcEstcEpWarnings OBJECT-TYPE
    SYNTAX       CucsFabricWarnings
    MAX-ACCESS   read-only
    STATUS       current
    DESCRIPTION
        "Cisco UCS fabric:FcEstcEp:warnings managed object property"
    ::= { cucsFabricFcEstcEpEntry 27 }

cucsFabricFcEstcEpFillPattern OBJECT-TYPE
    SYNTAX       CucsFabricFillPattern
    MAX-ACCESS   read-only
    STATUS       current
    DESCRIPTION
        "Cisco UCS fabric:FcEstcEp:fillPattern managed object property"
    ::= { cucsFabricFcEstcEpEntry 28 }

cucsFabricFcEstcEpAggrPortId OBJECT-TYPE
    SYNTAX       Gauge32
    MAX-ACCESS   read-only
    STATUS       current
    DESCRIPTION
        "Cisco UCS fabric:FcEstcEp:aggrPortId managed object property"
    ::= { cucsFabricFcEstcEpEntry 29 }

cucsFabricFcEstcEpPeerAggrPortId OBJECT-TYPE
    SYNTAX       Gauge32
    MAX-ACCESS   read-only
    STATUS       current
    DESCRIPTION
        "Cisco UCS fabric:FcEstcEp:peerAggrPortId managed object property"
    ::= { cucsFabricFcEstcEpEntry 30 }

cucsFabricFcEstcEpAutoNegotiate OBJECT-TYPE
    SYNTAX       TruthValue
    MAX-ACCESS   read-only
    STATUS       current
    DESCRIPTION
        "Cisco UCS fabric:FcEstcEp:autoNegotiate managed object property"
    ::= { cucsFabricFcEstcEpEntry 31 }

cucsFabricFcMonTable OBJECT-TYPE
    SYNTAX           SEQUENCE OF CucsFabricFcMonEntry
    MAX-ACCESS       not-accessible
    STATUS           current
    DESCRIPTION
        "Cisco UCS fabric:FcMon managed object table"
    ::= { cucsFabricObjects 28 }

cucsFabricFcMonEntry OBJECT-TYPE
    SYNTAX           CucsFabricFcMonEntry
    MAX-ACCESS       not-accessible
    STATUS           current
    DESCRIPTION
        "Entry for the cucsFabricFcMonTable table."
    INDEX { cucsFabricFcMonInstanceId }
    ::= { cucsFabricFcMonTable 1 }

CucsFabricFcMonEntry ::= SEQUENCE {
    cucsFabricFcMonInstanceId                                        CucsManagedObjectId,
    cucsFabricFcMonDn                                                CucsManagedObjectDn,
    cucsFabricFcMonRn                                                SnmpAdminString,
    cucsFabricFcMonAdminState                                        CucsFabricMonAdminState,
    cucsFabricFcMonId                                                CucsNetworkSwitchId,
    cucsFabricFcMonLocale                                            CucsFabricExternalLocale,
    cucsFabricFcMonName                                              SnmpAdminString,
    cucsFabricFcMonSession                                           Gauge32,
    cucsFabricFcMonTransport                                         CucsFabricFcMonTransport,
    cucsFabricFcMonType                                              CucsFabricFcMonType,
    cucsFabricFcMonConfigFailReason                                  SnmpAdminString,
    cucsFabricFcMonIsConfigSuccess                                   TruthValue,
    cucsFabricFcMonOperState                                         CucsFabricMonOperState,
    cucsFabricFcMonOperStateReason                                   CucsFabricMonOperStateReason,
    cucsFabricFcMonPeerDn                                            SnmpAdminString
}

cucsFabricFcMonInstanceId OBJECT-TYPE
    SYNTAX       CucsManagedObjectId
    MAX-ACCESS   not-accessible
    STATUS       current
    DESCRIPTION
        "Instance identifier of the managed object."
    ::= { cucsFabricFcMonEntry 1 }

cucsFabricFcMonDn OBJECT-TYPE
    SYNTAX       CucsManagedObjectDn
    MAX-ACCESS   read-only
    STATUS       current
    DESCRIPTION
        "Cisco UCS fabric:FcMon:dn managed object property"
    ::= { cucsFabricFcMonEntry 2 }

cucsFabricFcMonRn OBJECT-TYPE
    SYNTAX       SnmpAdminString
    MAX-ACCESS   read-only
    STATUS       current
    DESCRIPTION
        "Cisco UCS fabric:FcMon:rn managed object property"
    ::= { cucsFabricFcMonEntry 3 }

cucsFabricFcMonAdminState OBJECT-TYPE
    SYNTAX       CucsFabricMonAdminState
    MAX-ACCESS   read-only
    STATUS       current
    DESCRIPTION
        "Cisco UCS fabric:FcMon:adminState managed object property"
    ::= { cucsFabricFcMonEntry 4 }

cucsFabricFcMonId OBJECT-TYPE
    SYNTAX       CucsNetworkSwitchId
    MAX-ACCESS   read-only
    STATUS       current
    DESCRIPTION
        "Cisco UCS fabric:FcMon:id managed object property"
    ::= { cucsFabricFcMonEntry 5 }

cucsFabricFcMonLocale OBJECT-TYPE
    SYNTAX       CucsFabricExternalLocale
    MAX-ACCESS   read-only
    STATUS       current
    DESCRIPTION
        "Cisco UCS fabric:FcMon:locale managed object property"
    ::= { cucsFabricFcMonEntry 6 }

cucsFabricFcMonName OBJECT-TYPE
    SYNTAX       SnmpAdminString
    MAX-ACCESS   read-only
    STATUS       current
    DESCRIPTION
        "Cisco UCS fabric:FcMon:name managed object property"
    ::= { cucsFabricFcMonEntry 7 }

cucsFabricFcMonSession OBJECT-TYPE
    SYNTAX       Gauge32
    MAX-ACCESS   read-only
    STATUS       current
    DESCRIPTION
        "Cisco UCS fabric:FcMon:session managed object property"
    ::= { cucsFabricFcMonEntry 8 }

cucsFabricFcMonTransport OBJECT-TYPE
    SYNTAX       CucsFabricFcMonTransport
    MAX-ACCESS   read-only
    STATUS       current
    DESCRIPTION
        "Cisco UCS fabric:FcMon:transport managed object property"
    ::= { cucsFabricFcMonEntry 9 }

cucsFabricFcMonType OBJECT-TYPE
    SYNTAX       CucsFabricFcMonType
    MAX-ACCESS   read-only
    STATUS       current
    DESCRIPTION
        "Cisco UCS fabric:FcMon:type managed object property"
    ::= { cucsFabricFcMonEntry 10 }

cucsFabricFcMonConfigFailReason OBJECT-TYPE
    SYNTAX       SnmpAdminString
    MAX-ACCESS   read-only
    STATUS       current
    DESCRIPTION
        "Cisco UCS fabric:FcMon:configFailReason managed object property"
    ::= { cucsFabricFcMonEntry 11 }

cucsFabricFcMonIsConfigSuccess OBJECT-TYPE
    SYNTAX       TruthValue
    MAX-ACCESS   read-only
    STATUS       current
    DESCRIPTION
        "Cisco UCS fabric:FcMon:isConfigSuccess managed object property"
    ::= { cucsFabricFcMonEntry 12 }

cucsFabricFcMonOperState OBJECT-TYPE
    SYNTAX       CucsFabricMonOperState
    MAX-ACCESS   read-only
    STATUS       current
    DESCRIPTION
        "Cisco UCS fabric:FcMon:operState managed object property"
    ::= { cucsFabricFcMonEntry 13 }

cucsFabricFcMonOperStateReason OBJECT-TYPE
    SYNTAX       CucsFabricMonOperStateReason
    MAX-ACCESS   read-only
    STATUS       current
    DESCRIPTION
        "Cisco UCS fabric:FcMon:operStateReason managed object property"
    ::= { cucsFabricFcMonEntry 14 }

cucsFabricFcMonPeerDn OBJECT-TYPE
    SYNTAX       SnmpAdminString
    MAX-ACCESS   read-only
    STATUS       current
    DESCRIPTION
        "Cisco UCS fabric:FcMon:peerDn managed object property"
    ::= { cucsFabricFcMonEntry 15 }

cucsFabricFcMonDestEpTable OBJECT-TYPE
    SYNTAX           SEQUENCE OF CucsFabricFcMonDestEpEntry
    MAX-ACCESS       not-accessible
    STATUS           current
    DESCRIPTION
        "Cisco UCS fabric:FcMonDestEp managed object table"
    ::= { cucsFabricObjects 29 }

cucsFabricFcMonDestEpEntry OBJECT-TYPE
    SYNTAX           CucsFabricFcMonDestEpEntry
    MAX-ACCESS       not-accessible
    STATUS           current
    DESCRIPTION
        "Entry for the cucsFabricFcMonDestEpTable table."
    INDEX { cucsFabricFcMonDestEpInstanceId }
    ::= { cucsFabricFcMonDestEpTable 1 }

CucsFabricFcMonDestEpEntry ::= SEQUENCE {
    cucsFabricFcMonDestEpInstanceId                                  CucsManagedObjectId,
    cucsFabricFcMonDestEpDn                                          CucsManagedObjectDn,
    cucsFabricFcMonDestEpRn                                          SnmpAdminString,
    cucsFabricFcMonDestEpAdminState                                  CucsFabricExternalEpAdminState,
    cucsFabricFcMonDestEpChassisId                                   Gauge32,
    cucsFabricFcMonDestEpEpDn                                        SnmpAdminString,
    cucsFabricFcMonDestEpIfRole                                      CucsFabricFcMonDestEpIfRole,
    cucsFabricFcMonDestEpIfType                                      CucsFabricPIoEpIfType,
    cucsFabricFcMonDestEpLicGP                                       Unsigned64,
    cucsFabricFcMonDestEpLicState                                    CucsLicenseState,
    cucsFabricFcMonDestEpLocale                                      CucsFabricExternalEpLocale,
    cucsFabricFcMonDestEpName                                        SnmpAdminString,
    cucsFabricFcMonDestEpPeerDn                                      SnmpAdminString,
    cucsFabricFcMonDestEpPeerPortId                                  Gauge32,
    cucsFabricFcMonDestEpPeerSlotId                                  Gauge32,
    cucsFabricFcMonDestEpPortId                                      CucsFabricFcMonDestEpPortId,
    cucsFabricFcMonDestEpSlotId                                      CucsFabricFcMonDestEpSlotId,
    cucsFabricFcMonDestEpSwitchId                                    CucsNetworkSwitchId,
    cucsFabricFcMonDestEpTransport                                   CucsNetworkTransport,
    cucsFabricFcMonDestEpType                                        CucsFabricFcMonDestEpType,
    cucsFabricFcMonDestEpPeerChassisId                               Gauge32,
    cucsFabricFcMonDestEpFltAggr                                     Unsigned64,
    cucsFabricFcMonDestEpAdminSpeed                                  CucsFabricFcMonDestEpAdminSpeed,
    cucsFabricFcMonDestEpOperState                                   CucsFabricPIoEpOperState,
    cucsFabricFcMonDestEpOperStateReason                             SnmpAdminString,
    cucsFabricFcMonDestEpWarnings                                    CucsFabricWarnings,
    cucsFabricFcMonDestEpAggrPortId                                  Gauge32,
    cucsFabricFcMonDestEpPeerAggrPortId                              Gauge32,
    cucsFabricFcMonDestEpAutoNegotiate                               TruthValue
}

cucsFabricFcMonDestEpInstanceId OBJECT-TYPE
    SYNTAX       CucsManagedObjectId
    MAX-ACCESS   not-accessible
    STATUS       current
    DESCRIPTION
        "Instance identifier of the managed object."
    ::= { cucsFabricFcMonDestEpEntry 1 }

cucsFabricFcMonDestEpDn OBJECT-TYPE
    SYNTAX       CucsManagedObjectDn
    MAX-ACCESS   read-only
    STATUS       current
    DESCRIPTION
        "Cisco UCS fabric:FcMonDestEp:dn managed object property"
    ::= { cucsFabricFcMonDestEpEntry 2 }

cucsFabricFcMonDestEpRn OBJECT-TYPE
    SYNTAX       SnmpAdminString
    MAX-ACCESS   read-only
    STATUS       current
    DESCRIPTION
        "Cisco UCS fabric:FcMonDestEp:rn managed object property"
    ::= { cucsFabricFcMonDestEpEntry 3 }

cucsFabricFcMonDestEpAdminState OBJECT-TYPE
    SYNTAX       CucsFabricExternalEpAdminState
    MAX-ACCESS   read-only
    STATUS       current
    DESCRIPTION
        "Cisco UCS fabric:FcMonDestEp:adminState managed object property"
    ::= { cucsFabricFcMonDestEpEntry 4 }

cucsFabricFcMonDestEpChassisId OBJECT-TYPE
    SYNTAX       Gauge32
    MAX-ACCESS   read-only
    STATUS       current
    DESCRIPTION
        "Cisco UCS fabric:FcMonDestEp:chassisId managed object property"
    ::= { cucsFabricFcMonDestEpEntry 5 }

cucsFabricFcMonDestEpEpDn OBJECT-TYPE
    SYNTAX       SnmpAdminString
    MAX-ACCESS   read-only
    STATUS       current
    DESCRIPTION
        "Cisco UCS fabric:FcMonDestEp:epDn managed object property"
    ::= { cucsFabricFcMonDestEpEntry 6 }

cucsFabricFcMonDestEpIfRole OBJECT-TYPE
    SYNTAX       CucsFabricFcMonDestEpIfRole
    MAX-ACCESS   read-only
    STATUS       current
    DESCRIPTION
        "Cisco UCS fabric:FcMonDestEp:ifRole managed object property"
    ::= { cucsFabricFcMonDestEpEntry 7 }

cucsFabricFcMonDestEpIfType OBJECT-TYPE
    SYNTAX       CucsFabricPIoEpIfType
    MAX-ACCESS   read-only
    STATUS       current
    DESCRIPTION
        "Cisco UCS fabric:FcMonDestEp:ifType managed object property"
    ::= { cucsFabricFcMonDestEpEntry 8 }

cucsFabricFcMonDestEpLicGP OBJECT-TYPE
    SYNTAX       Unsigned64
    MAX-ACCESS   read-only
    STATUS       current
    DESCRIPTION
        "Cisco UCS fabric:FcMonDestEp:licGP managed object property"
    ::= { cucsFabricFcMonDestEpEntry 9 }

cucsFabricFcMonDestEpLicState OBJECT-TYPE
    SYNTAX       CucsLicenseState
    MAX-ACCESS   read-only
    STATUS       current
    DESCRIPTION
        "Cisco UCS fabric:FcMonDestEp:licState managed object property"
    ::= { cucsFabricFcMonDestEpEntry 10 }

cucsFabricFcMonDestEpLocale OBJECT-TYPE
    SYNTAX       CucsFabricExternalEpLocale
    MAX-ACCESS   read-only
    STATUS       current
    DESCRIPTION
        "Cisco UCS fabric:FcMonDestEp:locale managed object property"
    ::= { cucsFabricFcMonDestEpEntry 11 }

cucsFabricFcMonDestEpName OBJECT-TYPE
    SYNTAX       SnmpAdminString
    MAX-ACCESS   read-only
    STATUS       current
    DESCRIPTION
        "Cisco UCS fabric:FcMonDestEp:name managed object property"
    ::= { cucsFabricFcMonDestEpEntry 12 }

cucsFabricFcMonDestEpPeerDn OBJECT-TYPE
    SYNTAX       SnmpAdminString
    MAX-ACCESS   read-only
    STATUS       current
    DESCRIPTION
        "Cisco UCS fabric:FcMonDestEp:peerDn managed object property"
    ::= { cucsFabricFcMonDestEpEntry 13 }

cucsFabricFcMonDestEpPeerPortId OBJECT-TYPE
    SYNTAX       Gauge32
    MAX-ACCESS   read-only
    STATUS       current
    DESCRIPTION
        "Cisco UCS fabric:FcMonDestEp:peerPortId managed object property"
    ::= { cucsFabricFcMonDestEpEntry 14 }

cucsFabricFcMonDestEpPeerSlotId OBJECT-TYPE
    SYNTAX       Gauge32
    MAX-ACCESS   read-only
    STATUS       current
    DESCRIPTION
        "Cisco UCS fabric:FcMonDestEp:peerSlotId managed object property"
    ::= { cucsFabricFcMonDestEpEntry 15 }

cucsFabricFcMonDestEpPortId OBJECT-TYPE
    SYNTAX       CucsFabricFcMonDestEpPortId
    MAX-ACCESS   read-only
    STATUS       current
    DESCRIPTION
        "Cisco UCS fabric:FcMonDestEp:portId managed object property"
    ::= { cucsFabricFcMonDestEpEntry 16 }

cucsFabricFcMonDestEpSlotId OBJECT-TYPE
    SYNTAX       CucsFabricFcMonDestEpSlotId
    MAX-ACCESS   read-only
    STATUS       current
    DESCRIPTION
        "Cisco UCS fabric:FcMonDestEp:slotId managed object property"
    ::= { cucsFabricFcMonDestEpEntry 17 }

cucsFabricFcMonDestEpSwitchId OBJECT-TYPE
    SYNTAX       CucsNetworkSwitchId
    MAX-ACCESS   read-only
    STATUS       current
    DESCRIPTION
        "Cisco UCS fabric:FcMonDestEp:switchId managed object property"
    ::= { cucsFabricFcMonDestEpEntry 18 }

cucsFabricFcMonDestEpTransport OBJECT-TYPE
    SYNTAX       CucsNetworkTransport
    MAX-ACCESS   read-only
    STATUS       current
    DESCRIPTION
        "Cisco UCS fabric:FcMonDestEp:transport managed object property"
    ::= { cucsFabricFcMonDestEpEntry 19 }

cucsFabricFcMonDestEpType OBJECT-TYPE
    SYNTAX       CucsFabricFcMonDestEpType
    MAX-ACCESS   read-only
    STATUS       current
    DESCRIPTION
        "Cisco UCS fabric:FcMonDestEp:type managed object property"
    ::= { cucsFabricFcMonDestEpEntry 20 }

cucsFabricFcMonDestEpPeerChassisId OBJECT-TYPE
    SYNTAX       Gauge32
    MAX-ACCESS   read-only
    STATUS       current
    DESCRIPTION
        "Cisco UCS fabric:FcMonDestEp:peerChassisId managed
        object property"
    ::= { cucsFabricFcMonDestEpEntry 21 }

cucsFabricFcMonDestEpFltAggr OBJECT-TYPE
    SYNTAX       Unsigned64
    MAX-ACCESS   read-only
    STATUS       current
    DESCRIPTION
        "Cisco UCS fabric:FcMonDestEp:fltAggr managed object property"
    ::= { cucsFabricFcMonDestEpEntry 22 }

cucsFabricFcMonDestEpAdminSpeed OBJECT-TYPE
    SYNTAX       CucsFabricFcMonDestEpAdminSpeed
    MAX-ACCESS   read-only
    STATUS       current
    DESCRIPTION
        "Cisco UCS fabric:FcMonDestEp:adminSpeed managed object property"
    ::= { cucsFabricFcMonDestEpEntry 23 }

cucsFabricFcMonDestEpOperState OBJECT-TYPE
    SYNTAX       CucsFabricPIoEpOperState
    MAX-ACCESS   read-only
    STATUS       current
    DESCRIPTION
        "Cisco UCS fabric:FcMonDestEp:operState managed object property"
    ::= { cucsFabricFcMonDestEpEntry 24 }

cucsFabricFcMonDestEpOperStateReason OBJECT-TYPE
    SYNTAX       SnmpAdminString
    MAX-ACCESS   read-only
    STATUS       current
    DESCRIPTION
        "Cisco UCS fabric:FcMonDestEp:operStateReason managed
        object property"
    ::= { cucsFabricFcMonDestEpEntry 25 }

cucsFabricFcMonDestEpWarnings OBJECT-TYPE
    SYNTAX       CucsFabricWarnings
    MAX-ACCESS   read-only
    STATUS       current
    DESCRIPTION
        "Cisco UCS fabric:FcMonDestEp:warnings managed object property"
    ::= { cucsFabricFcMonDestEpEntry 26 }

cucsFabricFcMonDestEpAggrPortId OBJECT-TYPE
    SYNTAX       Gauge32
    MAX-ACCESS   read-only
    STATUS       current
    DESCRIPTION
        "Cisco UCS fabric:FcMonDestEp:aggrPortId managed object property"
    ::= { cucsFabricFcMonDestEpEntry 27 }

cucsFabricFcMonDestEpPeerAggrPortId OBJECT-TYPE
    SYNTAX       Gauge32
    MAX-ACCESS   read-only
    STATUS       current
    DESCRIPTION
        "Cisco UCS fabric:FcMonDestEp:peerAggrPortId managed
        object property"
    ::= { cucsFabricFcMonDestEpEntry 28 }

cucsFabricFcMonDestEpAutoNegotiate OBJECT-TYPE
    SYNTAX       TruthValue
    MAX-ACCESS   read-only
    STATUS       current
    DESCRIPTION
        "Cisco UCS fabric:FcMonDestEp:autoNegotiate managed
        object property"
    ::= { cucsFabricFcMonDestEpEntry 29 }

cucsFabricFcMonFiltEpTable OBJECT-TYPE
    SYNTAX           SEQUENCE OF CucsFabricFcMonFiltEpEntry
    MAX-ACCESS       not-accessible
    STATUS           current
    DESCRIPTION
        "Cisco UCS fabric:FcMonFiltEp managed object table"
    ::= { cucsFabricObjects 30 }

cucsFabricFcMonFiltEpEntry OBJECT-TYPE
    SYNTAX           CucsFabricFcMonFiltEpEntry
    MAX-ACCESS       not-accessible
    STATUS           current
    DESCRIPTION
        "Entry for the cucsFabricFcMonFiltEpTable table."
    INDEX { cucsFabricFcMonFiltEpInstanceId }
    ::= { cucsFabricFcMonFiltEpTable 1 }

CucsFabricFcMonFiltEpEntry ::= SEQUENCE {
    cucsFabricFcMonFiltEpInstanceId                                  CucsManagedObjectId,
    cucsFabricFcMonFiltEpDn                                          CucsManagedObjectDn,
    cucsFabricFcMonFiltEpRn                                          SnmpAdminString,
    cucsFabricFcMonFiltEpName                                        SnmpAdminString,
    cucsFabricFcMonFiltEpSession                                     Gauge32,
    cucsFabricFcMonFiltEpType                                        CucsFabricFcMonFiltEpType
}

cucsFabricFcMonFiltEpInstanceId OBJECT-TYPE
    SYNTAX       CucsManagedObjectId
    MAX-ACCESS   not-accessible
    STATUS       current
    DESCRIPTION
        "Instance identifier of the managed object."
    ::= { cucsFabricFcMonFiltEpEntry 1 }

cucsFabricFcMonFiltEpDn OBJECT-TYPE
    SYNTAX       CucsManagedObjectDn
    MAX-ACCESS   read-only
    STATUS       current
    DESCRIPTION
        "Cisco UCS fabric:FcMonFiltEp:dn managed object property"
    ::= { cucsFabricFcMonFiltEpEntry 2 }

cucsFabricFcMonFiltEpRn OBJECT-TYPE
    SYNTAX       SnmpAdminString
    MAX-ACCESS   read-only
    STATUS       current
    DESCRIPTION
        "Cisco UCS fabric:FcMonFiltEp:rn managed object property"
    ::= { cucsFabricFcMonFiltEpEntry 3 }

cucsFabricFcMonFiltEpName OBJECT-TYPE
    SYNTAX       SnmpAdminString
    MAX-ACCESS   read-only
    STATUS       current
    DESCRIPTION
        "Cisco UCS fabric:FcMonFiltEp:name managed object property"
    ::= { cucsFabricFcMonFiltEpEntry 4 }

cucsFabricFcMonFiltEpSession OBJECT-TYPE
    SYNTAX       Gauge32
    MAX-ACCESS   read-only
    STATUS       current
    DESCRIPTION
        "Cisco UCS fabric:FcMonFiltEp:session managed object property"
    ::= { cucsFabricFcMonFiltEpEntry 5 }

cucsFabricFcMonFiltEpType OBJECT-TYPE
    SYNTAX       CucsFabricFcMonFiltEpType
    MAX-ACCESS   read-only
    STATUS       current
    DESCRIPTION
        "Cisco UCS fabric:FcMonFiltEp:type managed object property"
    ::= { cucsFabricFcMonFiltEpEntry 6 }

cucsFabricFcMonFiltRefTable OBJECT-TYPE
    SYNTAX           SEQUENCE OF CucsFabricFcMonFiltRefEntry
    MAX-ACCESS       not-accessible
    STATUS           current
    DESCRIPTION
        "Cisco UCS fabric:FcMonFiltRef managed object table"
    ::= { cucsFabricObjects 31 }

cucsFabricFcMonFiltRefEntry OBJECT-TYPE
    SYNTAX           CucsFabricFcMonFiltRefEntry
    MAX-ACCESS       not-accessible
    STATUS           current
    DESCRIPTION
        "Entry for the cucsFabricFcMonFiltRefTable table."
    INDEX { cucsFabricFcMonFiltRefInstanceId }
    ::= { cucsFabricFcMonFiltRefTable 1 }

CucsFabricFcMonFiltRefEntry ::= SEQUENCE {
    cucsFabricFcMonFiltRefInstanceId                                 CucsManagedObjectId,
    cucsFabricFcMonFiltRefDn                                         CucsManagedObjectDn,
    cucsFabricFcMonFiltRefRn                                         SnmpAdminString,
    cucsFabricFcMonFiltRefSrcFiltDn                                  SnmpAdminString,
    cucsFabricFcMonFiltRefType                                       CucsFabricFcMonFiltRefType
}

cucsFabricFcMonFiltRefInstanceId OBJECT-TYPE
    SYNTAX       CucsManagedObjectId
    MAX-ACCESS   not-accessible
    STATUS       current
    DESCRIPTION
        "Instance identifier of the managed object."
    ::= { cucsFabricFcMonFiltRefEntry 1 }

cucsFabricFcMonFiltRefDn OBJECT-TYPE
    SYNTAX       CucsManagedObjectDn
    MAX-ACCESS   read-only
    STATUS       current
    DESCRIPTION
        "Cisco UCS fabric:FcMonFiltRef:dn managed object property"
    ::= { cucsFabricFcMonFiltRefEntry 2 }

cucsFabricFcMonFiltRefRn OBJECT-TYPE
    SYNTAX       SnmpAdminString
    MAX-ACCESS   read-only
    STATUS       current
    DESCRIPTION
        "Cisco UCS fabric:FcMonFiltRef:rn managed object property"
    ::= { cucsFabricFcMonFiltRefEntry 3 }

cucsFabricFcMonFiltRefSrcFiltDn OBJECT-TYPE
    SYNTAX       SnmpAdminString
    MAX-ACCESS   read-only
    STATUS       current
    DESCRIPTION
        "Cisco UCS fabric:FcMonFiltRef:srcFiltDn managed object property"
    ::= { cucsFabricFcMonFiltRefEntry 4 }

cucsFabricFcMonFiltRefType OBJECT-TYPE
    SYNTAX       CucsFabricFcMonFiltRefType
    MAX-ACCESS   read-only
    STATUS       current
    DESCRIPTION
        "Cisco UCS fabric:FcMonFiltRef:type managed object property"
    ::= { cucsFabricFcMonFiltRefEntry 5 }

cucsFabricFcMonSanTable OBJECT-TYPE
    SYNTAX           SEQUENCE OF CucsFabricFcMonSanEntry
    MAX-ACCESS       not-accessible
    STATUS           current
    DESCRIPTION
        "Cisco UCS fabric:FcMonSan managed object table"
    ::= { cucsFabricObjects 32 }

cucsFabricFcMonSanEntry OBJECT-TYPE
    SYNTAX           CucsFabricFcMonSanEntry
    MAX-ACCESS       not-accessible
    STATUS           current
    DESCRIPTION
        "Entry for the cucsFabricFcMonSanTable table."
    INDEX { cucsFabricFcMonSanInstanceId }
    ::= { cucsFabricFcMonSanTable 1 }

CucsFabricFcMonSanEntry ::= SEQUENCE {
    cucsFabricFcMonSanInstanceId                                     CucsManagedObjectId,
    cucsFabricFcMonSanDn                                             CucsManagedObjectDn,
    cucsFabricFcMonSanRn                                             SnmpAdminString,
    cucsFabricFcMonSanId                                             CucsNetworkSwitchId,
    cucsFabricFcMonSanLocale                                         CucsFabricExternalLocale,
    cucsFabricFcMonSanName                                           SnmpAdminString,
    cucsFabricFcMonSanTransport                                      CucsFabricFcMonSanTransport,
    cucsFabricFcMonSanType                                           CucsFabricFcMonSanType
}

cucsFabricFcMonSanInstanceId OBJECT-TYPE
    SYNTAX       CucsManagedObjectId
    MAX-ACCESS   not-accessible
    STATUS       current
    DESCRIPTION
        "Instance identifier of the managed object."
    ::= { cucsFabricFcMonSanEntry 1 }

cucsFabricFcMonSanDn OBJECT-TYPE
    SYNTAX       CucsManagedObjectDn
    MAX-ACCESS   read-only
    STATUS       current
    DESCRIPTION
        "Cisco UCS fabric:FcMonSan:dn managed object property"
    ::= { cucsFabricFcMonSanEntry 2 }

cucsFabricFcMonSanRn OBJECT-TYPE
    SYNTAX       SnmpAdminString
    MAX-ACCESS   read-only
    STATUS       current
    DESCRIPTION
        "Cisco UCS fabric:FcMonSan:rn managed object property"
    ::= { cucsFabricFcMonSanEntry 3 }

cucsFabricFcMonSanId OBJECT-TYPE
    SYNTAX       CucsNetworkSwitchId
    MAX-ACCESS   read-only
    STATUS       current
    DESCRIPTION
        "Cisco UCS fabric:FcMonSan:id managed object property"
    ::= { cucsFabricFcMonSanEntry 4 }

cucsFabricFcMonSanLocale OBJECT-TYPE
    SYNTAX       CucsFabricExternalLocale
    MAX-ACCESS   read-only
    STATUS       current
    DESCRIPTION
        "Cisco UCS fabric:FcMonSan:locale managed object property"
    ::= { cucsFabricFcMonSanEntry 5 }

cucsFabricFcMonSanName OBJECT-TYPE
    SYNTAX       SnmpAdminString
    MAX-ACCESS   read-only
    STATUS       current
    DESCRIPTION
        "Cisco UCS fabric:FcMonSan:name managed object property"
    ::= { cucsFabricFcMonSanEntry 6 }

cucsFabricFcMonSanTransport OBJECT-TYPE
    SYNTAX       CucsFabricFcMonSanTransport
    MAX-ACCESS   read-only
    STATUS       current
    DESCRIPTION
        "Cisco UCS fabric:FcMonSan:transport managed object property"
    ::= { cucsFabricFcMonSanEntry 7 }

cucsFabricFcMonSanType OBJECT-TYPE
    SYNTAX       CucsFabricFcMonSanType
    MAX-ACCESS   read-only
    STATUS       current
    DESCRIPTION
        "Cisco UCS fabric:FcMonSan:type managed object property"
    ::= { cucsFabricFcMonSanEntry 8 }

cucsFabricFcMonSrcEpTable OBJECT-TYPE
    SYNTAX           SEQUENCE OF CucsFabricFcMonSrcEpEntry
    MAX-ACCESS       not-accessible
    STATUS           current
    DESCRIPTION
        "Cisco UCS fabric:FcMonSrcEp managed object table"
    ::= { cucsFabricObjects 33 }

cucsFabricFcMonSrcEpEntry OBJECT-TYPE
    SYNTAX           CucsFabricFcMonSrcEpEntry
    MAX-ACCESS       not-accessible
    STATUS           current
    DESCRIPTION
        "Entry for the cucsFabricFcMonSrcEpTable table."
    INDEX { cucsFabricFcMonSrcEpInstanceId }
    ::= { cucsFabricFcMonSrcEpTable 1 }

CucsFabricFcMonSrcEpEntry ::= SEQUENCE {
    cucsFabricFcMonSrcEpInstanceId                                   CucsManagedObjectId,
    cucsFabricFcMonSrcEpDn                                           CucsManagedObjectDn,
    cucsFabricFcMonSrcEpRn                                           SnmpAdminString,
    cucsFabricFcMonSrcEpDirection                                    CucsFabricTrafficDirection,
    cucsFabricFcMonSrcEpName                                         SnmpAdminString,
    cucsFabricFcMonSrcEpSession                                      Gauge32,
    cucsFabricFcMonSrcEpTransport                                    CucsNetworkTransport,
    cucsFabricFcMonSrcEpType                                         CucsFabricFcMonSrcEpType
}

cucsFabricFcMonSrcEpInstanceId OBJECT-TYPE
    SYNTAX       CucsManagedObjectId
    MAX-ACCESS   not-accessible
    STATUS       current
    DESCRIPTION
        "Instance identifier of the managed object."
    ::= { cucsFabricFcMonSrcEpEntry 1 }

cucsFabricFcMonSrcEpDn OBJECT-TYPE
    SYNTAX       CucsManagedObjectDn
    MAX-ACCESS   read-only
    STATUS       current
    DESCRIPTION
        "Cisco UCS fabric:FcMonSrcEp:dn managed object property"
    ::= { cucsFabricFcMonSrcEpEntry 2 }

cucsFabricFcMonSrcEpRn OBJECT-TYPE
    SYNTAX       SnmpAdminString
    MAX-ACCESS   read-only
    STATUS       current
    DESCRIPTION
        "Cisco UCS fabric:FcMonSrcEp:rn managed object property"
    ::= { cucsFabricFcMonSrcEpEntry 3 }

cucsFabricFcMonSrcEpDirection OBJECT-TYPE
    SYNTAX       CucsFabricTrafficDirection
    MAX-ACCESS   read-only
    STATUS       current
    DESCRIPTION
        "Cisco UCS fabric:FcMonSrcEp:direction managed object property"
    ::= { cucsFabricFcMonSrcEpEntry 4 }

cucsFabricFcMonSrcEpName OBJECT-TYPE
    SYNTAX       SnmpAdminString
    MAX-ACCESS   read-only
    STATUS       current
    DESCRIPTION
        "Cisco UCS fabric:FcMonSrcEp:name managed object property"
    ::= { cucsFabricFcMonSrcEpEntry 5 }

cucsFabricFcMonSrcEpSession OBJECT-TYPE
    SYNTAX       Gauge32
    MAX-ACCESS   read-only
    STATUS       current
    DESCRIPTION
        "Cisco UCS fabric:FcMonSrcEp:session managed object property"
    ::= { cucsFabricFcMonSrcEpEntry 6 }

cucsFabricFcMonSrcEpTransport OBJECT-TYPE
    SYNTAX       CucsNetworkTransport
    MAX-ACCESS   read-only
    STATUS       current
    DESCRIPTION
        "Cisco UCS fabric:FcMonSrcEp:transport managed object property"
    ::= { cucsFabricFcMonSrcEpEntry 7 }

cucsFabricFcMonSrcEpType OBJECT-TYPE
    SYNTAX       CucsFabricFcMonSrcEpType
    MAX-ACCESS   read-only
    STATUS       current
    DESCRIPTION
        "Cisco UCS fabric:FcMonSrcEp:type managed object property"
    ::= { cucsFabricFcMonSrcEpEntry 8 }

cucsFabricFcMonSrcRefTable OBJECT-TYPE
    SYNTAX           SEQUENCE OF CucsFabricFcMonSrcRefEntry
    MAX-ACCESS       not-accessible
    STATUS           current
    DESCRIPTION
        "Cisco UCS fabric:FcMonSrcRef managed object table"
    ::= { cucsFabricObjects 34 }

cucsFabricFcMonSrcRefEntry OBJECT-TYPE
    SYNTAX           CucsFabricFcMonSrcRefEntry
    MAX-ACCESS       not-accessible
    STATUS           current
    DESCRIPTION
        "Entry for the cucsFabricFcMonSrcRefTable table."
    INDEX { cucsFabricFcMonSrcRefInstanceId }
    ::= { cucsFabricFcMonSrcRefTable 1 }

CucsFabricFcMonSrcRefEntry ::= SEQUENCE {
    cucsFabricFcMonSrcRefInstanceId                                  CucsManagedObjectId,
    cucsFabricFcMonSrcRefDn                                          CucsManagedObjectDn,
    cucsFabricFcMonSrcRefRn                                          SnmpAdminString,
    cucsFabricFcMonSrcRefId                                          Unsigned64,
    cucsFabricFcMonSrcRefSourceDn                                    SnmpAdminString,
    cucsFabricFcMonSrcRefSourceType                                  CucsFabricFcSourceType,
    cucsFabricFcMonSrcRefType                                        CucsFabricFcMonSrcRefType
}

cucsFabricFcMonSrcRefInstanceId OBJECT-TYPE
    SYNTAX       CucsManagedObjectId
    MAX-ACCESS   not-accessible
    STATUS       current
    DESCRIPTION
        "Instance identifier of the managed object."
    ::= { cucsFabricFcMonSrcRefEntry 1 }

cucsFabricFcMonSrcRefDn OBJECT-TYPE
    SYNTAX       CucsManagedObjectDn
    MAX-ACCESS   read-only
    STATUS       current
    DESCRIPTION
        "Cisco UCS fabric:FcMonSrcRef:dn managed object property"
    ::= { cucsFabricFcMonSrcRefEntry 2 }

cucsFabricFcMonSrcRefRn OBJECT-TYPE
    SYNTAX       SnmpAdminString
    MAX-ACCESS   read-only
    STATUS       current
    DESCRIPTION
        "Cisco UCS fabric:FcMonSrcRef:rn managed object property"
    ::= { cucsFabricFcMonSrcRefEntry 3 }

cucsFabricFcMonSrcRefId OBJECT-TYPE
    SYNTAX       Unsigned64
    MAX-ACCESS   read-only
    STATUS       current
    DESCRIPTION
        "Cisco UCS fabric:FcMonSrcRef:id managed object property"
    ::= { cucsFabricFcMonSrcRefEntry 4 }

cucsFabricFcMonSrcRefSourceDn OBJECT-TYPE
    SYNTAX       SnmpAdminString
    MAX-ACCESS   read-only
    STATUS       current
    DESCRIPTION
        "Cisco UCS fabric:FcMonSrcRef:sourceDn managed object property"
    ::= { cucsFabricFcMonSrcRefEntry 5 }

cucsFabricFcMonSrcRefSourceType OBJECT-TYPE
    SYNTAX       CucsFabricFcSourceType
    MAX-ACCESS   read-only
    STATUS       current
    DESCRIPTION
        "Cisco UCS fabric:FcMonSrcRef:sourceType managed object property"
    ::= { cucsFabricFcMonSrcRefEntry 6 }

cucsFabricFcMonSrcRefType OBJECT-TYPE
    SYNTAX       CucsFabricFcMonSrcRefType
    MAX-ACCESS   read-only
    STATUS       current
    DESCRIPTION
        "Cisco UCS fabric:FcMonSrcRef:type managed object property"
    ::= { cucsFabricFcMonSrcRefEntry 7 }

cucsFabricFcSanTable OBJECT-TYPE
    SYNTAX           SEQUENCE OF CucsFabricFcSanEntry
    MAX-ACCESS       not-accessible
    STATUS           current
    DESCRIPTION
        "Cisco UCS fabric:FcSan managed object table"
    ::= { cucsFabricObjects 35 }

cucsFabricFcSanEntry OBJECT-TYPE
    SYNTAX           CucsFabricFcSanEntry
    MAX-ACCESS       not-accessible
    STATUS           current
    DESCRIPTION
        "Entry for the cucsFabricFcSanTable table."
    INDEX { cucsFabricFcSanInstanceId }
    ::= { cucsFabricFcSanTable 1 }

CucsFabricFcSanEntry ::= SEQUENCE {
    cucsFabricFcSanInstanceId                                        CucsManagedObjectId,
    cucsFabricFcSanDn                                                CucsManagedObjectDn,
    cucsFabricFcSanRn                                                SnmpAdminString,
    cucsFabricFcSanId                                                CucsNetworkSwitchId,
    cucsFabricFcSanLocale                                            CucsFabricExternalLocale,
    cucsFabricFcSanName                                              SnmpAdminString,
    cucsFabricFcSanTransport                                         CucsFabricFcSanTransport,
    cucsFabricFcSanType                                              CucsFabricSanType,
    cucsFabricFcSanUplinkTrunking                                    CucsFabricFcSanUplinkTrunking,
    cucsFabricFcSanConfigQualifier                                   CucsFabricSanConfigIssues
}

cucsFabricFcSanInstanceId OBJECT-TYPE
    SYNTAX       CucsManagedObjectId
    MAX-ACCESS   not-accessible
    STATUS       current
    DESCRIPTION
        "Instance identifier of the managed object."
    ::= { cucsFabricFcSanEntry 1 }

cucsFabricFcSanDn OBJECT-TYPE
    SYNTAX       CucsManagedObjectDn
    MAX-ACCESS   read-only
    STATUS       current
    DESCRIPTION
        "Cisco UCS fabric:FcSan:dn managed object property"
    ::= { cucsFabricFcSanEntry 2 }

cucsFabricFcSanRn OBJECT-TYPE
    SYNTAX       SnmpAdminString
    MAX-ACCESS   read-only
    STATUS       current
    DESCRIPTION
        "Cisco UCS fabric:FcSan:rn managed object property"
    ::= { cucsFabricFcSanEntry 3 }

cucsFabricFcSanId OBJECT-TYPE
    SYNTAX       CucsNetworkSwitchId
    MAX-ACCESS   read-only
    STATUS       current
    DESCRIPTION
        "Cisco UCS fabric:FcSan:id managed object property"
    ::= { cucsFabricFcSanEntry 4 }

cucsFabricFcSanLocale OBJECT-TYPE
    SYNTAX       CucsFabricExternalLocale
    MAX-ACCESS   read-only
    STATUS       current
    DESCRIPTION
        "Cisco UCS fabric:FcSan:locale managed object property"
    ::= { cucsFabricFcSanEntry 5 }

cucsFabricFcSanName OBJECT-TYPE
    SYNTAX       SnmpAdminString
    MAX-ACCESS   read-only
    STATUS       current
    DESCRIPTION
        "Cisco UCS fabric:FcSan:name managed object property"
    ::= { cucsFabricFcSanEntry 6 }

cucsFabricFcSanTransport OBJECT-TYPE
    SYNTAX       CucsFabricFcSanTransport
    MAX-ACCESS   read-only
    STATUS       current
    DESCRIPTION
        "Cisco UCS fabric:FcSan:transport managed object property"
    ::= { cucsFabricFcSanEntry 7 }

cucsFabricFcSanType OBJECT-TYPE
    SYNTAX       CucsFabricSanType
    MAX-ACCESS   read-only
    STATUS       current
    DESCRIPTION
        "Cisco UCS fabric:FcSan:type managed object property"
    ::= { cucsFabricFcSanEntry 8 }

cucsFabricFcSanUplinkTrunking OBJECT-TYPE
    SYNTAX       CucsFabricFcSanUplinkTrunking
    MAX-ACCESS   read-only
    STATUS       current
    DESCRIPTION
        "Cisco UCS fabric:FcSan:uplinkTrunking managed object property"
    ::= { cucsFabricFcSanEntry 9 }

cucsFabricFcSanConfigQualifier OBJECT-TYPE
    SYNTAX       CucsFabricSanConfigIssues
    MAX-ACCESS   read-only
    STATUS       current
    DESCRIPTION
        "Cisco UCS fabric:FcSan:configQualifier managed object property"
    ::= { cucsFabricFcSanEntry 10 }

cucsFabricFcSanEpTable OBJECT-TYPE
    SYNTAX           SEQUENCE OF CucsFabricFcSanEpEntry
    MAX-ACCESS       not-accessible
    STATUS           current
    DESCRIPTION
        "Cisco UCS fabric:FcSanEp managed object table"
    ::= { cucsFabricObjects 36 }

cucsFabricFcSanEpEntry OBJECT-TYPE
    SYNTAX           CucsFabricFcSanEpEntry
    MAX-ACCESS       not-accessible
    STATUS           current
    DESCRIPTION
        "Entry for the cucsFabricFcSanEpTable table."
    INDEX { cucsFabricFcSanEpInstanceId }
    ::= { cucsFabricFcSanEpTable 1 }

CucsFabricFcSanEpEntry ::= SEQUENCE {
    cucsFabricFcSanEpInstanceId                                      CucsManagedObjectId,
    cucsFabricFcSanEpDn                                              CucsManagedObjectDn,
    cucsFabricFcSanEpRn                                              SnmpAdminString,
    cucsFabricFcSanEpAdminState                                      CucsFabricExternalEpAdminState,
    cucsFabricFcSanEpChassisId                                       Gauge32,
    cucsFabricFcSanEpEpDn                                            SnmpAdminString,
    cucsFabricFcSanEpIfRole                                          CucsFabricSanEpIfRole,
    cucsFabricFcSanEpIfType                                          CucsFabricPIoEpIfType,
    cucsFabricFcSanEpLicGP                                           Unsigned64,
    cucsFabricFcSanEpLicState                                        CucsLicenseState,
    cucsFabricFcSanEpLocale                                          CucsFabricExternalEpLocale,
    cucsFabricFcSanEpName                                            SnmpAdminString,
    cucsFabricFcSanEpPeerDn                                          SnmpAdminString,
    cucsFabricFcSanEpPeerPortId                                      Gauge32,
    cucsFabricFcSanEpPeerSlotId                                      Gauge32,
    cucsFabricFcSanEpPortId                                          CucsFabricFcSanEpPortId,
    cucsFabricFcSanEpSlotId                                          CucsFabricFcSanEpSlotId,
    cucsFabricFcSanEpSwitchId                                        CucsNetworkSwitchId,
    cucsFabricFcSanEpTransport                                       CucsFabricAFcSanEpTransport,
    cucsFabricFcSanEpType                                            CucsFabricSanEpType,
    cucsFabricFcSanEpUsrLbl                                          SnmpAdminString,
    cucsFabricFcSanEpPeerChassisId                                   Gauge32,
    cucsFabricFcSanEpFltAggr                                         Unsigned64,
    cucsFabricFcSanEpOperState                                       CucsFabricPIoEpOperState,
    cucsFabricFcSanEpOperStateReason                                 SnmpAdminString,
    cucsFabricFcSanEpWarnings                                        CucsFabricWarnings,
    cucsFabricFcSanEpFillPattern                                     CucsFabricFillPattern,
    cucsFabricFcSanEpAggrPortId                                      Gauge32,
    cucsFabricFcSanEpPeerAggrPortId                                  Gauge32,
    cucsFabricFcSanEpAutoNegotiate                                   TruthValue
}

cucsFabricFcSanEpInstanceId OBJECT-TYPE
    SYNTAX       CucsManagedObjectId
    MAX-ACCESS   not-accessible
    STATUS       current
    DESCRIPTION
        "Instance identifier of the managed object."
    ::= { cucsFabricFcSanEpEntry 1 }

cucsFabricFcSanEpDn OBJECT-TYPE
    SYNTAX       CucsManagedObjectDn
    MAX-ACCESS   read-only
    STATUS       current
    DESCRIPTION
        "Cisco UCS fabric:FcSanEp:dn managed object property"
    ::= { cucsFabricFcSanEpEntry 2 }

cucsFabricFcSanEpRn OBJECT-TYPE
    SYNTAX       SnmpAdminString
    MAX-ACCESS   read-only
    STATUS       current
    DESCRIPTION
        "Cisco UCS fabric:FcSanEp:rn managed object property"
    ::= { cucsFabricFcSanEpEntry 3 }

cucsFabricFcSanEpAdminState OBJECT-TYPE
    SYNTAX       CucsFabricExternalEpAdminState
    MAX-ACCESS   read-only
    STATUS       current
    DESCRIPTION
        "Cisco UCS fabric:FcSanEp:adminState managed object property"
    ::= { cucsFabricFcSanEpEntry 4 }

cucsFabricFcSanEpChassisId OBJECT-TYPE
    SYNTAX       Gauge32
    MAX-ACCESS   read-only
    STATUS       current
    DESCRIPTION
        "Cisco UCS fabric:FcSanEp:chassisId managed object property"
    ::= { cucsFabricFcSanEpEntry 5 }

cucsFabricFcSanEpEpDn OBJECT-TYPE
    SYNTAX       SnmpAdminString
    MAX-ACCESS   read-only
    STATUS       current
    DESCRIPTION
        "Cisco UCS fabric:FcSanEp:epDn managed object property"
    ::= { cucsFabricFcSanEpEntry 6 }

cucsFabricFcSanEpIfRole OBJECT-TYPE
    SYNTAX       CucsFabricSanEpIfRole
    MAX-ACCESS   read-only
    STATUS       current
    DESCRIPTION
        "Cisco UCS fabric:FcSanEp:ifRole managed object property"
    ::= { cucsFabricFcSanEpEntry 7 }

cucsFabricFcSanEpIfType OBJECT-TYPE
    SYNTAX       CucsFabricPIoEpIfType
    MAX-ACCESS   read-only
    STATUS       current
    DESCRIPTION
        "Cisco UCS fabric:FcSanEp:ifType managed object property"
    ::= { cucsFabricFcSanEpEntry 8 }

cucsFabricFcSanEpLicGP OBJECT-TYPE
    SYNTAX       Unsigned64
    MAX-ACCESS   read-only
    STATUS       current
    DESCRIPTION
        "Cisco UCS fabric:FcSanEp:licGP managed object property"
    ::= { cucsFabricFcSanEpEntry 9 }

cucsFabricFcSanEpLicState OBJECT-TYPE
    SYNTAX       CucsLicenseState
    MAX-ACCESS   read-only
    STATUS       current
    DESCRIPTION
        "Cisco UCS fabric:FcSanEp:licState managed object property"
    ::= { cucsFabricFcSanEpEntry 10 }

cucsFabricFcSanEpLocale OBJECT-TYPE
    SYNTAX       CucsFabricExternalEpLocale
    MAX-ACCESS   read-only
    STATUS       current
    DESCRIPTION
        "Cisco UCS fabric:FcSanEp:locale managed object property"
    ::= { cucsFabricFcSanEpEntry 11 }

cucsFabricFcSanEpName OBJECT-TYPE
    SYNTAX       SnmpAdminString
    MAX-ACCESS   read-only
    STATUS       current
    DESCRIPTION
        "Cisco UCS fabric:FcSanEp:name managed object property"
    ::= { cucsFabricFcSanEpEntry 12 }

cucsFabricFcSanEpPeerDn OBJECT-TYPE
    SYNTAX       SnmpAdminString
    MAX-ACCESS   read-only
    STATUS       current
    DESCRIPTION
        "Cisco UCS fabric:FcSanEp:peerDn managed object property"
    ::= { cucsFabricFcSanEpEntry 13 }

cucsFabricFcSanEpPeerPortId OBJECT-TYPE
    SYNTAX       Gauge32
    MAX-ACCESS   read-only
    STATUS       current
    DESCRIPTION
        "Cisco UCS fabric:FcSanEp:peerPortId managed object property"
    ::= { cucsFabricFcSanEpEntry 14 }

cucsFabricFcSanEpPeerSlotId OBJECT-TYPE
    SYNTAX       Gauge32
    MAX-ACCESS   read-only
    STATUS       current
    DESCRIPTION
        "Cisco UCS fabric:FcSanEp:peerSlotId managed object property"
    ::= { cucsFabricFcSanEpEntry 15 }

cucsFabricFcSanEpPortId OBJECT-TYPE
    SYNTAX       CucsFabricFcSanEpPortId
    MAX-ACCESS   read-only
    STATUS       current
    DESCRIPTION
        "Cisco UCS fabric:FcSanEp:portId managed object property"
    ::= { cucsFabricFcSanEpEntry 16 }

cucsFabricFcSanEpSlotId OBJECT-TYPE
    SYNTAX       CucsFabricFcSanEpSlotId
    MAX-ACCESS   read-only
    STATUS       current
    DESCRIPTION
        "Cisco UCS fabric:FcSanEp:slotId managed object property"
    ::= { cucsFabricFcSanEpEntry 17 }

cucsFabricFcSanEpSwitchId OBJECT-TYPE
    SYNTAX       CucsNetworkSwitchId
    MAX-ACCESS   read-only
    STATUS       current
    DESCRIPTION
        "Cisco UCS fabric:FcSanEp:switchId managed object property"
    ::= { cucsFabricFcSanEpEntry 18 }

cucsFabricFcSanEpTransport OBJECT-TYPE
    SYNTAX       CucsFabricAFcSanEpTransport
    MAX-ACCESS   read-only
    STATUS       current
    DESCRIPTION
        "Cisco UCS fabric:FcSanEp:transport managed object property"
    ::= { cucsFabricFcSanEpEntry 19 }

cucsFabricFcSanEpType OBJECT-TYPE
    SYNTAX       CucsFabricSanEpType
    MAX-ACCESS   read-only
    STATUS       current
    DESCRIPTION
        "Cisco UCS fabric:FcSanEp:type managed object property"
    ::= { cucsFabricFcSanEpEntry 20 }

cucsFabricFcSanEpUsrLbl OBJECT-TYPE
    SYNTAX       SnmpAdminString
    MAX-ACCESS   read-only
    STATUS       current
    DESCRIPTION
        "Cisco UCS fabric:FcSanEp:usrLbl managed object property"
    ::= { cucsFabricFcSanEpEntry 21 }

cucsFabricFcSanEpPeerChassisId OBJECT-TYPE
    SYNTAX       Gauge32
    MAX-ACCESS   read-only
    STATUS       current
    DESCRIPTION
        "Cisco UCS fabric:FcSanEp:peerChassisId managed object property"
    ::= { cucsFabricFcSanEpEntry 22 }

cucsFabricFcSanEpFltAggr OBJECT-TYPE
    SYNTAX       Unsigned64
    MAX-ACCESS   read-only
    STATUS       current
    DESCRIPTION
        "Cisco UCS fabric:FcSanEp:fltAggr managed object property"
    ::= { cucsFabricFcSanEpEntry 23 }

cucsFabricFcSanEpOperState OBJECT-TYPE
    SYNTAX       CucsFabricPIoEpOperState
    MAX-ACCESS   read-only
    STATUS       current
    DESCRIPTION
        "Cisco UCS fabric:FcSanEp:operState managed object property"
    ::= { cucsFabricFcSanEpEntry 24 }

cucsFabricFcSanEpOperStateReason OBJECT-TYPE
    SYNTAX       SnmpAdminString
    MAX-ACCESS   read-only
    STATUS       current
    DESCRIPTION
        "Cisco UCS fabric:FcSanEp:operStateReason managed object property"
    ::= { cucsFabricFcSanEpEntry 25 }

cucsFabricFcSanEpWarnings OBJECT-TYPE
    SYNTAX       CucsFabricWarnings
    MAX-ACCESS   read-only
    STATUS       current
    DESCRIPTION
        "Cisco UCS fabric:FcSanEp:warnings managed object property"
    ::= { cucsFabricFcSanEpEntry 26 }

cucsFabricFcSanEpFillPattern OBJECT-TYPE
    SYNTAX       CucsFabricFillPattern
    MAX-ACCESS   read-only
    STATUS       current
    DESCRIPTION
        "Cisco UCS fabric:FcSanEp:fillPattern managed object property"
    ::= { cucsFabricFcSanEpEntry 27 }

cucsFabricFcSanEpAggrPortId OBJECT-TYPE
    SYNTAX       Gauge32
    MAX-ACCESS   read-only
    STATUS       current
    DESCRIPTION
        "Cisco UCS fabric:FcSanEp:aggrPortId managed object property"
    ::= { cucsFabricFcSanEpEntry 28 }

cucsFabricFcSanEpPeerAggrPortId OBJECT-TYPE
    SYNTAX       Gauge32
    MAX-ACCESS   read-only
    STATUS       current
    DESCRIPTION
        "Cisco UCS fabric:FcSanEp:peerAggrPortId managed object property"
    ::= { cucsFabricFcSanEpEntry 29 }

cucsFabricFcSanEpAutoNegotiate OBJECT-TYPE
    SYNTAX       TruthValue
    MAX-ACCESS   read-only
    STATUS       current
    DESCRIPTION
        "Cisco UCS fabric:FcSanEp:autoNegotiate managed object property"
    ::= { cucsFabricFcSanEpEntry 30 }

cucsFabricFcSanPcTable OBJECT-TYPE
    SYNTAX           SEQUENCE OF CucsFabricFcSanPcEntry
    MAX-ACCESS       not-accessible
    STATUS           current
    DESCRIPTION
        "Cisco UCS fabric:FcSanPc managed object table"
    ::= { cucsFabricObjects 37 }

cucsFabricFcSanPcEntry OBJECT-TYPE
    SYNTAX           CucsFabricFcSanPcEntry
    MAX-ACCESS       not-accessible
    STATUS           current
    DESCRIPTION
        "Entry for the cucsFabricFcSanPcTable table."
    INDEX { cucsFabricFcSanPcInstanceId }
    ::= { cucsFabricFcSanPcTable 1 }

CucsFabricFcSanPcEntry ::= SEQUENCE {
    cucsFabricFcSanPcInstanceId                                      CucsManagedObjectId,
    cucsFabricFcSanPcDn                                              CucsManagedObjectDn,
    cucsFabricFcSanPcRn                                              SnmpAdminString,
    cucsFabricFcSanPcAdminState                                      CucsFabricCIoEpAdminState,
    cucsFabricFcSanPcEndPtDn                                         SnmpAdminString,
    cucsFabricFcSanPcFltAggr                                         Unsigned64,
    cucsFabricFcSanPcIfRole                                          CucsFabricSanPcIfRole,
    cucsFabricFcSanPcIfType                                          CucsFabricCIoEpIfType,
    cucsFabricFcSanPcLocale                                          CucsFabricExternalPcLocale,
    cucsFabricFcSanPcName                                            SnmpAdminString,
    cucsFabricFcSanPcOperState                                       CucsNetworkPortOperState,
    cucsFabricFcSanPcPeerDn                                          SnmpAdminString,
    cucsFabricFcSanPcPortId                                          Gauge32,
    cucsFabricFcSanPcStateQual                                       SnmpAdminString,
    cucsFabricFcSanPcSwitchId                                        CucsNetworkSwitchId,
    cucsFabricFcSanPcTransport                                       CucsFabricFcSanPcTransport,
    cucsFabricFcSanPcType                                            CucsFabricSanPcType,
    cucsFabricFcSanPcAdminSpeed                                      CucsPortSpeed,
    cucsFabricFcSanPcConfigStatus                                    CucsFabricPcConfigStatus,
    cucsFabricFcSanPcOperSpeed                                       Gauge32,
    cucsFabricFcSanPcConfigState                                     CucsFabricConfigState,
    cucsFabricFcSanPcWarnings                                        CucsFabricWarnings,
    cucsFabricFcSanPcDescr                                           SnmpAdminString
}

cucsFabricFcSanPcInstanceId OBJECT-TYPE
    SYNTAX       CucsManagedObjectId
    MAX-ACCESS   not-accessible
    STATUS       current
    DESCRIPTION
        "Instance identifier of the managed object."
    ::= { cucsFabricFcSanPcEntry 1 }

cucsFabricFcSanPcDn OBJECT-TYPE
    SYNTAX       CucsManagedObjectDn
    MAX-ACCESS   read-only
    STATUS       current
    DESCRIPTION
        "Cisco UCS fabric:FcSanPc:dn managed object property"
    ::= { cucsFabricFcSanPcEntry 2 }

cucsFabricFcSanPcRn OBJECT-TYPE
    SYNTAX       SnmpAdminString
    MAX-ACCESS   read-only
    STATUS       current
    DESCRIPTION
        "Cisco UCS fabric:FcSanPc:rn managed object property"
    ::= { cucsFabricFcSanPcEntry 3 }

cucsFabricFcSanPcAdminState OBJECT-TYPE
    SYNTAX       CucsFabricCIoEpAdminState
    MAX-ACCESS   read-only
    STATUS       current
    DESCRIPTION
        "Cisco UCS fabric:FcSanPc:adminState managed object property"
    ::= { cucsFabricFcSanPcEntry 4 }

cucsFabricFcSanPcEndPtDn OBJECT-TYPE
    SYNTAX       SnmpAdminString
    MAX-ACCESS   read-only
    STATUS       current
    DESCRIPTION
        "Cisco UCS fabric:FcSanPc:epDn managed object property"
    ::= { cucsFabricFcSanPcEntry 5 }

cucsFabricFcSanPcFltAggr OBJECT-TYPE
    SYNTAX       Unsigned64
    MAX-ACCESS   read-only
    STATUS       current
    DESCRIPTION
        "Cisco UCS fabric:FcSanPc:fltAggr managed object property"
    ::= { cucsFabricFcSanPcEntry 6 }

cucsFabricFcSanPcIfRole OBJECT-TYPE
    SYNTAX       CucsFabricSanPcIfRole
    MAX-ACCESS   read-only
    STATUS       current
    DESCRIPTION
        "Cisco UCS fabric:FcSanPc:ifRole managed object property"
    ::= { cucsFabricFcSanPcEntry 7 }

cucsFabricFcSanPcIfType OBJECT-TYPE
    SYNTAX       CucsFabricCIoEpIfType
    MAX-ACCESS   read-only
    STATUS       current
    DESCRIPTION
        "Cisco UCS fabric:FcSanPc:ifType managed object property"
    ::= { cucsFabricFcSanPcEntry 8 }

cucsFabricFcSanPcLocale OBJECT-TYPE
    SYNTAX       CucsFabricExternalPcLocale
    MAX-ACCESS   read-only
    STATUS       current
    DESCRIPTION
        "Cisco UCS fabric:FcSanPc:locale managed object property"
    ::= { cucsFabricFcSanPcEntry 9 }

cucsFabricFcSanPcName OBJECT-TYPE
    SYNTAX       SnmpAdminString
    MAX-ACCESS   read-only
    STATUS       current
    DESCRIPTION
        "Cisco UCS fabric:FcSanPc:name managed object property"
    ::= { cucsFabricFcSanPcEntry 10 }

cucsFabricFcSanPcOperState OBJECT-TYPE
    SYNTAX       CucsNetworkPortOperState
    MAX-ACCESS   read-only
    STATUS       current
    DESCRIPTION
        "Cisco UCS fabric:FcSanPc:operState managed object property"
    ::= { cucsFabricFcSanPcEntry 11 }

cucsFabricFcSanPcPeerDn OBJECT-TYPE
    SYNTAX       SnmpAdminString
    MAX-ACCESS   read-only
    STATUS       current
    DESCRIPTION
        "Cisco UCS fabric:FcSanPc:peerDn managed object property"
    ::= { cucsFabricFcSanPcEntry 12 }

cucsFabricFcSanPcPortId OBJECT-TYPE
    SYNTAX       Gauge32
    MAX-ACCESS   read-only
    STATUS       current
    DESCRIPTION
        "Cisco UCS fabric:FcSanPc:portId managed object property"
    ::= { cucsFabricFcSanPcEntry 13 }

cucsFabricFcSanPcStateQual OBJECT-TYPE
    SYNTAX       SnmpAdminString
    MAX-ACCESS   read-only
    STATUS       current
    DESCRIPTION
        "Cisco UCS fabric:FcSanPc:stateQual managed object property"
    ::= { cucsFabricFcSanPcEntry 14 }

cucsFabricFcSanPcSwitchId OBJECT-TYPE
    SYNTAX       CucsNetworkSwitchId
    MAX-ACCESS   read-only
    STATUS       current
    DESCRIPTION
        "Cisco UCS fabric:FcSanPc:switchId managed object property"
    ::= { cucsFabricFcSanPcEntry 15 }

cucsFabricFcSanPcTransport OBJECT-TYPE
    SYNTAX       CucsFabricFcSanPcTransport
    MAX-ACCESS   read-only
    STATUS       current
    DESCRIPTION
        "Cisco UCS fabric:FcSanPc:transport managed object property"
    ::= { cucsFabricFcSanPcEntry 16 }

cucsFabricFcSanPcType OBJECT-TYPE
    SYNTAX       CucsFabricSanPcType
    MAX-ACCESS   read-only
    STATUS       current
    DESCRIPTION
        "Cisco UCS fabric:FcSanPc:type managed object property"
    ::= { cucsFabricFcSanPcEntry 17 }

cucsFabricFcSanPcAdminSpeed OBJECT-TYPE
    SYNTAX       CucsPortSpeed
    MAX-ACCESS   read-only
    STATUS       current
    DESCRIPTION
        "Cisco UCS fabric:FcSanPc:adminSpeed managed object property"
    ::= { cucsFabricFcSanPcEntry 18 }

cucsFabricFcSanPcConfigStatus OBJECT-TYPE
    SYNTAX       CucsFabricPcConfigStatus
    MAX-ACCESS   read-only
    STATUS       current
    DESCRIPTION
        "Cisco UCS fabric:FcSanPc:configStatus managed object property"
    ::= { cucsFabricFcSanPcEntry 19 }

cucsFabricFcSanPcOperSpeed OBJECT-TYPE
    SYNTAX       Gauge32
    MAX-ACCESS   read-only
    STATUS       current
    DESCRIPTION
        "Cisco UCS fabric:FcSanPc:operSpeed managed object property"
    ::= { cucsFabricFcSanPcEntry 20 }

cucsFabricFcSanPcConfigState OBJECT-TYPE
    SYNTAX       CucsFabricConfigState
    MAX-ACCESS   read-only
    STATUS       current
    DESCRIPTION
        "Cisco UCS fabric:FcSanPc:configState managed object property"
    ::= { cucsFabricFcSanPcEntry 21 }

cucsFabricFcSanPcWarnings OBJECT-TYPE
    SYNTAX       CucsFabricWarnings
    MAX-ACCESS   read-only
    STATUS       current
    DESCRIPTION
        "Cisco UCS fabric:FcSanPc:warnings managed object property"
    ::= { cucsFabricFcSanPcEntry 22 }

cucsFabricFcSanPcDescr OBJECT-TYPE
    SYNTAX       SnmpAdminString
    MAX-ACCESS   read-only
    STATUS       current
    DESCRIPTION
        "Cisco UCS fabric:FcSanPc:descr managed object property"
    ::= { cucsFabricFcSanPcEntry 23 }

cucsFabricFcSanPcEpTable OBJECT-TYPE
    SYNTAX           SEQUENCE OF CucsFabricFcSanPcEpEntry
    MAX-ACCESS       not-accessible
    STATUS           current
    DESCRIPTION
        "Cisco UCS fabric:FcSanPcEp managed object table"
    ::= { cucsFabricObjects 38 }

cucsFabricFcSanPcEpEntry OBJECT-TYPE
    SYNTAX           CucsFabricFcSanPcEpEntry
    MAX-ACCESS       not-accessible
    STATUS           current
    DESCRIPTION
        "Entry for the cucsFabricFcSanPcEpTable table."
    INDEX { cucsFabricFcSanPcEpInstanceId }
    ::= { cucsFabricFcSanPcEpTable 1 }

CucsFabricFcSanPcEpEntry ::= SEQUENCE {
    cucsFabricFcSanPcEpInstanceId                                    CucsManagedObjectId,
    cucsFabricFcSanPcEpDn                                            CucsManagedObjectDn,
    cucsFabricFcSanPcEpRn                                            SnmpAdminString,
    cucsFabricFcSanPcEpAdminState                                    CucsFabricExternalEpAdminState,
    cucsFabricFcSanPcEpChassisId                                     Gauge32,
    cucsFabricFcSanPcEpEpDn                                          SnmpAdminString,
    cucsFabricFcSanPcEpIfRole                                        CucsFabricSanEpIfRole,
    cucsFabricFcSanPcEpIfType                                        CucsFabricPIoEpIfType,
    cucsFabricFcSanPcEpLicGP                                         Unsigned64,
    cucsFabricFcSanPcEpLicState                                      CucsLicenseState,
    cucsFabricFcSanPcEpLocale                                        CucsFabricExternalEpLocale,
    cucsFabricFcSanPcEpMembership                                    CucsFabricMembershipStatus,
    cucsFabricFcSanPcEpName                                          SnmpAdminString,
    cucsFabricFcSanPcEpPeerDn                                        SnmpAdminString,
    cucsFabricFcSanPcEpPeerPortId                                    Gauge32,
    cucsFabricFcSanPcEpPeerSlotId                                    Gauge32,
    cucsFabricFcSanPcEpPortId                                        CucsFabricFcSanPcEpPortId,
    cucsFabricFcSanPcEpSlotId                                        CucsFabricFcSanPcEpSlotId,
    cucsFabricFcSanPcEpSwitchId                                      CucsNetworkSwitchId,
    cucsFabricFcSanPcEpTransport                                     CucsFabricAFcSanEpTransport,
    cucsFabricFcSanPcEpType                                          CucsFabricSanEpType,
    cucsFabricFcSanPcEpAdminSpeed                                    CucsPortSpeed,
    cucsFabricFcSanPcEpPeerChassisId                                 Gauge32,
    cucsFabricFcSanPcEpFltAggr                                       Unsigned64,
    cucsFabricFcSanPcEpOperState                                     CucsFabricPIoEpOperState,
    cucsFabricFcSanPcEpOperStateReason                               SnmpAdminString,
    cucsFabricFcSanPcEpWarnings                                      CucsFabricWarnings,
    cucsFabricFcSanPcEpFillPattern                                   CucsFabricFillPattern,
    cucsFabricFcSanPcEpAggrPortId                                    Gauge32,
    cucsFabricFcSanPcEpPeerAggrPortId                                Gauge32,
    cucsFabricFcSanPcEpAutoNegotiate                                 TruthValue
}

cucsFabricFcSanPcEpInstanceId OBJECT-TYPE
    SYNTAX       CucsManagedObjectId
    MAX-ACCESS   not-accessible
    STATUS       current
    DESCRIPTION
        "Instance identifier of the managed object."
    ::= { cucsFabricFcSanPcEpEntry 1 }

cucsFabricFcSanPcEpDn OBJECT-TYPE
    SYNTAX       CucsManagedObjectDn
    MAX-ACCESS   read-only
    STATUS       current
    DESCRIPTION
        "Cisco UCS fabric:FcSanPcEp:dn managed object property"
    ::= { cucsFabricFcSanPcEpEntry 2 }

cucsFabricFcSanPcEpRn OBJECT-TYPE
    SYNTAX       SnmpAdminString
    MAX-ACCESS   read-only
    STATUS       current
    DESCRIPTION
        "Cisco UCS fabric:FcSanPcEp:rn managed object property"
    ::= { cucsFabricFcSanPcEpEntry 3 }

cucsFabricFcSanPcEpAdminState OBJECT-TYPE
    SYNTAX       CucsFabricExternalEpAdminState
    MAX-ACCESS   read-only
    STATUS       current
    DESCRIPTION
        "Cisco UCS fabric:FcSanPcEp:adminState managed object property"
    ::= { cucsFabricFcSanPcEpEntry 4 }

cucsFabricFcSanPcEpChassisId OBJECT-TYPE
    SYNTAX       Gauge32
    MAX-ACCESS   read-only
    STATUS       current
    DESCRIPTION
        "Cisco UCS fabric:FcSanPcEp:chassisId managed object property"
    ::= { cucsFabricFcSanPcEpEntry 5 }

cucsFabricFcSanPcEpEpDn OBJECT-TYPE
    SYNTAX       SnmpAdminString
    MAX-ACCESS   read-only
    STATUS       current
    DESCRIPTION
        "Cisco UCS fabric:FcSanPcEp:epDn managed object property"
    ::= { cucsFabricFcSanPcEpEntry 6 }

cucsFabricFcSanPcEpIfRole OBJECT-TYPE
    SYNTAX       CucsFabricSanEpIfRole
    MAX-ACCESS   read-only
    STATUS       current
    DESCRIPTION
        "Cisco UCS fabric:FcSanPcEp:ifRole managed object property"
    ::= { cucsFabricFcSanPcEpEntry 7 }

cucsFabricFcSanPcEpIfType OBJECT-TYPE
    SYNTAX       CucsFabricPIoEpIfType
    MAX-ACCESS   read-only
    STATUS       current
    DESCRIPTION
        "Cisco UCS fabric:FcSanPcEp:ifType managed object property"
    ::= { cucsFabricFcSanPcEpEntry 8 }

cucsFabricFcSanPcEpLicGP OBJECT-TYPE
    SYNTAX       Unsigned64
    MAX-ACCESS   read-only
    STATUS       current
    DESCRIPTION
        "Cisco UCS fabric:FcSanPcEp:licGP managed object property"
    ::= { cucsFabricFcSanPcEpEntry 9 }

cucsFabricFcSanPcEpLicState OBJECT-TYPE
    SYNTAX       CucsLicenseState
    MAX-ACCESS   read-only
    STATUS       current
    DESCRIPTION
        "Cisco UCS fabric:FcSanPcEp:licState managed object property"
    ::= { cucsFabricFcSanPcEpEntry 10 }

cucsFabricFcSanPcEpLocale OBJECT-TYPE
    SYNTAX       CucsFabricExternalEpLocale
    MAX-ACCESS   read-only
    STATUS       current
    DESCRIPTION
        "Cisco UCS fabric:FcSanPcEp:locale managed object property"
    ::= { cucsFabricFcSanPcEpEntry 11 }

cucsFabricFcSanPcEpMembership OBJECT-TYPE
    SYNTAX       CucsFabricMembershipStatus
    MAX-ACCESS   read-only
    STATUS       current
    DESCRIPTION
        "Cisco UCS fabric:FcSanPcEp:membership managed object property"
    ::= { cucsFabricFcSanPcEpEntry 12 }

cucsFabricFcSanPcEpName OBJECT-TYPE
    SYNTAX       SnmpAdminString
    MAX-ACCESS   read-only
    STATUS       current
    DESCRIPTION
        "Cisco UCS fabric:FcSanPcEp:name managed object property"
    ::= { cucsFabricFcSanPcEpEntry 13 }

cucsFabricFcSanPcEpPeerDn OBJECT-TYPE
    SYNTAX       SnmpAdminString
    MAX-ACCESS   read-only
    STATUS       current
    DESCRIPTION
        "Cisco UCS fabric:FcSanPcEp:peerDn managed object property"
    ::= { cucsFabricFcSanPcEpEntry 14 }

cucsFabricFcSanPcEpPeerPortId OBJECT-TYPE
    SYNTAX       Gauge32
    MAX-ACCESS   read-only
    STATUS       current
    DESCRIPTION
        "Cisco UCS fabric:FcSanPcEp:peerPortId managed object property"
    ::= { cucsFabricFcSanPcEpEntry 15 }

cucsFabricFcSanPcEpPeerSlotId OBJECT-TYPE
    SYNTAX       Gauge32
    MAX-ACCESS   read-only
    STATUS       current
    DESCRIPTION
        "Cisco UCS fabric:FcSanPcEp:peerSlotId managed object property"
    ::= { cucsFabricFcSanPcEpEntry 16 }

cucsFabricFcSanPcEpPortId OBJECT-TYPE
    SYNTAX       CucsFabricFcSanPcEpPortId
    MAX-ACCESS   read-only
    STATUS       current
    DESCRIPTION
        "Cisco UCS fabric:FcSanPcEp:portId managed object property"
    ::= { cucsFabricFcSanPcEpEntry 17 }

cucsFabricFcSanPcEpSlotId OBJECT-TYPE
    SYNTAX       CucsFabricFcSanPcEpSlotId
    MAX-ACCESS   read-only
    STATUS       current
    DESCRIPTION
        "Cisco UCS fabric:FcSanPcEp:slotId managed object property"
    ::= { cucsFabricFcSanPcEpEntry 18 }

cucsFabricFcSanPcEpSwitchId OBJECT-TYPE
    SYNTAX       CucsNetworkSwitchId
    MAX-ACCESS   read-only
    STATUS       current
    DESCRIPTION
        "Cisco UCS fabric:FcSanPcEp:switchId managed object property"
    ::= { cucsFabricFcSanPcEpEntry 19 }

cucsFabricFcSanPcEpTransport OBJECT-TYPE
    SYNTAX       CucsFabricAFcSanEpTransport
    MAX-ACCESS   read-only
    STATUS       current
    DESCRIPTION
        "Cisco UCS fabric:FcSanPcEp:transport managed object property"
    ::= { cucsFabricFcSanPcEpEntry 20 }

cucsFabricFcSanPcEpType OBJECT-TYPE
    SYNTAX       CucsFabricSanEpType
    MAX-ACCESS   read-only
    STATUS       current
    DESCRIPTION
        "Cisco UCS fabric:FcSanPcEp:type managed object property"
    ::= { cucsFabricFcSanPcEpEntry 21 }

cucsFabricFcSanPcEpAdminSpeed OBJECT-TYPE
    SYNTAX       CucsPortSpeed
    MAX-ACCESS   read-only
    STATUS       current
    DESCRIPTION
        "Cisco UCS fabric:FcSanPcEp:adminSpeed managed object property"
    ::= { cucsFabricFcSanPcEpEntry 22 }

cucsFabricFcSanPcEpPeerChassisId OBJECT-TYPE
    SYNTAX       Gauge32
    MAX-ACCESS   read-only
    STATUS       current
    DESCRIPTION
        "Cisco UCS fabric:FcSanPcEp:peerChassisId managed object property"
    ::= { cucsFabricFcSanPcEpEntry 23 }

cucsFabricFcSanPcEpFltAggr OBJECT-TYPE
    SYNTAX       Unsigned64
    MAX-ACCESS   read-only
    STATUS       current
    DESCRIPTION
        "Cisco UCS fabric:FcSanPcEp:fltAggr managed object property"
    ::= { cucsFabricFcSanPcEpEntry 24 }

cucsFabricFcSanPcEpOperState OBJECT-TYPE
    SYNTAX       CucsFabricPIoEpOperState
    MAX-ACCESS   read-only
    STATUS       current
    DESCRIPTION
        "Cisco UCS fabric:FcSanPcEp:operState managed object property"
    ::= { cucsFabricFcSanPcEpEntry 25 }

cucsFabricFcSanPcEpOperStateReason OBJECT-TYPE
    SYNTAX       SnmpAdminString
    MAX-ACCESS   read-only
    STATUS       current
    DESCRIPTION
        "Cisco UCS fabric:FcSanPcEp:operStateReason managed
        object property"
    ::= { cucsFabricFcSanPcEpEntry 26 }

cucsFabricFcSanPcEpWarnings OBJECT-TYPE
    SYNTAX       CucsFabricWarnings
    MAX-ACCESS   read-only
    STATUS       current
    DESCRIPTION
        "Cisco UCS fabric:FcSanPcEp:warnings managed object property"
    ::= { cucsFabricFcSanPcEpEntry 27 }

cucsFabricFcSanPcEpFillPattern OBJECT-TYPE
    SYNTAX       CucsFabricFillPattern
    MAX-ACCESS   read-only
    STATUS       current
    DESCRIPTION
        "Cisco UCS fabric:FcSanPcEp:fillPattern managed object property"
    ::= { cucsFabricFcSanPcEpEntry 28 }

cucsFabricFcSanPcEpAggrPortId OBJECT-TYPE
    SYNTAX       Gauge32
    MAX-ACCESS   read-only
    STATUS       current
    DESCRIPTION
        "Cisco UCS fabric:FcSanPcEp:aggrPortId managed object property"
    ::= { cucsFabricFcSanPcEpEntry 29 }

cucsFabricFcSanPcEpPeerAggrPortId OBJECT-TYPE
    SYNTAX       Gauge32
    MAX-ACCESS   read-only
    STATUS       current
    DESCRIPTION
        "Cisco UCS fabric:FcSanPcEp:peerAggrPortId managed
        object property"
    ::= { cucsFabricFcSanPcEpEntry 30 }

cucsFabricFcSanPcEpAutoNegotiate OBJECT-TYPE
    SYNTAX       TruthValue
    MAX-ACCESS   read-only
    STATUS       current
    DESCRIPTION
        "Cisco UCS fabric:FcSanPcEp:autoNegotiate managed object property"
    ::= { cucsFabricFcSanPcEpEntry 31 }

cucsFabricFcVsanPcTable OBJECT-TYPE
    SYNTAX           SEQUENCE OF CucsFabricFcVsanPcEntry
    MAX-ACCESS       not-accessible
    STATUS           current
    DESCRIPTION
        "Cisco UCS fabric:FcVsanPc managed object table"
    ::= { cucsFabricObjects 65 }

cucsFabricFcVsanPcEntry OBJECT-TYPE
    SYNTAX           CucsFabricFcVsanPcEntry
    MAX-ACCESS       not-accessible
    STATUS           current
    DESCRIPTION
        "Entry for the cucsFabricFcVsanPcTable table."
    INDEX { cucsFabricFcVsanPcInstanceId }
    ::= { cucsFabricFcVsanPcTable 1 }

CucsFabricFcVsanPcEntry ::= SEQUENCE {
    cucsFabricFcVsanPcInstanceId                                     CucsManagedObjectId,
    cucsFabricFcVsanPcDn                                             CucsManagedObjectDn,
    cucsFabricFcVsanPcRn                                             SnmpAdminString,
    cucsFabricFcVsanPcAdminState                                     CucsFabricCIoEpAdminState,
    cucsFabricFcVsanPcEpDn                                           SnmpAdminString,
    cucsFabricFcVsanPcFltAggr                                        Unsigned64,
    cucsFabricFcVsanPcIfRole                                         CucsFabricSanPcIfRole,
    cucsFabricFcVsanPcIfType                                         CucsFabricCIoEpIfType,
    cucsFabricFcVsanPcLocale                                         CucsFabricExternalPcLocale,
    cucsFabricFcVsanPcName                                           SnmpAdminString,
    cucsFabricFcVsanPcOperState                                      CucsNetworkPortOperState,
    cucsFabricFcVsanPcPeerDn                                         SnmpAdminString,
    cucsFabricFcVsanPcPortId                                         Gauge32,
    cucsFabricFcVsanPcStateQual                                      SnmpAdminString,
    cucsFabricFcVsanPcSwitchId                                       CucsNetworkSwitchId,
    cucsFabricFcVsanPcTransport                                      CucsFabricFcVsanPcTransport,
    cucsFabricFcVsanPcType                                           CucsFabricSanPcType,
    cucsFabricFcVsanPcWarnings                                       CucsFabricWarnings,
    cucsFabricFcVsanPcDescr                                          SnmpAdminString
}

cucsFabricFcVsanPcInstanceId OBJECT-TYPE
    SYNTAX       CucsManagedObjectId
    MAX-ACCESS   not-accessible
    STATUS       current
    DESCRIPTION
        "Instance identifier of the managed object."
    ::= { cucsFabricFcVsanPcEntry 1 }

cucsFabricFcVsanPcDn OBJECT-TYPE
    SYNTAX       CucsManagedObjectDn
    MAX-ACCESS   read-only
    STATUS       current
    DESCRIPTION
        "Cisco UCS fabric:FcVsanPc:dn managed object property"
    ::= { cucsFabricFcVsanPcEntry 2 }

cucsFabricFcVsanPcRn OBJECT-TYPE
    SYNTAX       SnmpAdminString
    MAX-ACCESS   read-only
    STATUS       current
    DESCRIPTION
        "Cisco UCS fabric:FcVsanPc:rn managed object property"
    ::= { cucsFabricFcVsanPcEntry 3 }

cucsFabricFcVsanPcAdminState OBJECT-TYPE
    SYNTAX       CucsFabricCIoEpAdminState
    MAX-ACCESS   read-only
    STATUS       current
    DESCRIPTION
        "Cisco UCS fabric:FcVsanPc:adminState managed object property"
    ::= { cucsFabricFcVsanPcEntry 4 }

cucsFabricFcVsanPcEpDn OBJECT-TYPE
    SYNTAX       SnmpAdminString
    MAX-ACCESS   read-only
    STATUS       current
    DESCRIPTION
        "Cisco UCS fabric:FcVsanPc:epDn managed object property"
    ::= { cucsFabricFcVsanPcEntry 5 }

cucsFabricFcVsanPcFltAggr OBJECT-TYPE
    SYNTAX       Unsigned64
    MAX-ACCESS   read-only
    STATUS       current
    DESCRIPTION
        "Cisco UCS fabric:FcVsanPc:fltAggr managed object property"
    ::= { cucsFabricFcVsanPcEntry 6 }

cucsFabricFcVsanPcIfRole OBJECT-TYPE
    SYNTAX       CucsFabricSanPcIfRole
    MAX-ACCESS   read-only
    STATUS       current
    DESCRIPTION
        "Cisco UCS fabric:FcVsanPc:ifRole managed object property"
    ::= { cucsFabricFcVsanPcEntry 7 }

cucsFabricFcVsanPcIfType OBJECT-TYPE
    SYNTAX       CucsFabricCIoEpIfType
    MAX-ACCESS   read-only
    STATUS       current
    DESCRIPTION
        "Cisco UCS fabric:FcVsanPc:ifType managed object property"
    ::= { cucsFabricFcVsanPcEntry 8 }

cucsFabricFcVsanPcLocale OBJECT-TYPE
    SYNTAX       CucsFabricExternalPcLocale
    MAX-ACCESS   read-only
    STATUS       current
    DESCRIPTION
        "Cisco UCS fabric:FcVsanPc:locale managed object property"
    ::= { cucsFabricFcVsanPcEntry 9 }

cucsFabricFcVsanPcName OBJECT-TYPE
    SYNTAX       SnmpAdminString
    MAX-ACCESS   read-only
    STATUS       current
    DESCRIPTION
        "Cisco UCS fabric:FcVsanPc:name managed object property"
    ::= { cucsFabricFcVsanPcEntry 10 }

cucsFabricFcVsanPcOperState OBJECT-TYPE
    SYNTAX       CucsNetworkPortOperState
    MAX-ACCESS   read-only
    STATUS       current
    DESCRIPTION
        "Cisco UCS fabric:FcVsanPc:operState managed object property"
    ::= { cucsFabricFcVsanPcEntry 11 }

cucsFabricFcVsanPcPeerDn OBJECT-TYPE
    SYNTAX       SnmpAdminString
    MAX-ACCESS   read-only
    STATUS       current
    DESCRIPTION
        "Cisco UCS fabric:FcVsanPc:peerDn managed object property"
    ::= { cucsFabricFcVsanPcEntry 12 }

cucsFabricFcVsanPcPortId OBJECT-TYPE
    SYNTAX       Gauge32
    MAX-ACCESS   read-only
    STATUS       current
    DESCRIPTION
        "Cisco UCS fabric:FcVsanPc:portId managed object property"
    ::= { cucsFabricFcVsanPcEntry 13 }

cucsFabricFcVsanPcStateQual OBJECT-TYPE
    SYNTAX       SnmpAdminString
    MAX-ACCESS   read-only
    STATUS       current
    DESCRIPTION
        "Cisco UCS fabric:FcVsanPc:stateQual managed object property"
    ::= { cucsFabricFcVsanPcEntry 14 }

cucsFabricFcVsanPcSwitchId OBJECT-TYPE
    SYNTAX       CucsNetworkSwitchId
    MAX-ACCESS   read-only
    STATUS       current
    DESCRIPTION
        "Cisco UCS fabric:FcVsanPc:switchId managed object property"
    ::= { cucsFabricFcVsanPcEntry 15 }

cucsFabricFcVsanPcTransport OBJECT-TYPE
    SYNTAX       CucsFabricFcVsanPcTransport
    MAX-ACCESS   read-only
    STATUS       current
    DESCRIPTION
        "Cisco UCS fabric:FcVsanPc:transport managed object property"
    ::= { cucsFabricFcVsanPcEntry 16 }

cucsFabricFcVsanPcType OBJECT-TYPE
    SYNTAX       CucsFabricSanPcType
    MAX-ACCESS   read-only
    STATUS       current
    DESCRIPTION
        "Cisco UCS fabric:FcVsanPc:type managed object property"
    ::= { cucsFabricFcVsanPcEntry 17 }

cucsFabricFcVsanPcWarnings OBJECT-TYPE
    SYNTAX       CucsFabricWarnings
    MAX-ACCESS   read-only
    STATUS       current
    DESCRIPTION
        "Cisco UCS fabric:FcVsanPc:warnings managed object property"
    ::= { cucsFabricFcVsanPcEntry 18 }

cucsFabricFcVsanPcDescr OBJECT-TYPE
    SYNTAX       SnmpAdminString
    MAX-ACCESS   read-only
    STATUS       current
    DESCRIPTION
        "Cisco UCS fabric:FcVsanPc:descr managed object property"
    ::= { cucsFabricFcVsanPcEntry 19 }

cucsFabricFcVsanPortEpTable OBJECT-TYPE
    SYNTAX           SEQUENCE OF CucsFabricFcVsanPortEpEntry
    MAX-ACCESS       not-accessible
    STATUS           current
    DESCRIPTION
        "Cisco UCS fabric:FcVsanPortEp managed object table"
    ::= { cucsFabricObjects 39 }

cucsFabricFcVsanPortEpEntry OBJECT-TYPE
    SYNTAX           CucsFabricFcVsanPortEpEntry
    MAX-ACCESS       not-accessible
    STATUS           current
    DESCRIPTION
        "Entry for the cucsFabricFcVsanPortEpTable table."
    INDEX { cucsFabricFcVsanPortEpInstanceId }
    ::= { cucsFabricFcVsanPortEpTable 1 }

CucsFabricFcVsanPortEpEntry ::= SEQUENCE {
    cucsFabricFcVsanPortEpInstanceId                                 CucsManagedObjectId,
    cucsFabricFcVsanPortEpDn                                         CucsManagedObjectDn,
    cucsFabricFcVsanPortEpRn                                         SnmpAdminString,
    cucsFabricFcVsanPortEpAdminState                                 CucsFabricExternalEpAdminState,
    cucsFabricFcVsanPortEpChassisId                                  Gauge32,
    cucsFabricFcVsanPortEpEpDn                                       SnmpAdminString,
    cucsFabricFcVsanPortEpIfRole                                     CucsFabricSanEpIfRole,
    cucsFabricFcVsanPortEpIfType                                     CucsFabricPIoEpIfType,
    cucsFabricFcVsanPortEpLicGP                                      Unsigned64,
    cucsFabricFcVsanPortEpLicState                                   CucsLicenseState,
    cucsFabricFcVsanPortEpLocale                                     CucsFabricExternalEpLocale,
    cucsFabricFcVsanPortEpName                                       SnmpAdminString,
    cucsFabricFcVsanPortEpPeerDn                                     SnmpAdminString,
    cucsFabricFcVsanPortEpPeerPortId                                 Gauge32,
    cucsFabricFcVsanPortEpPeerSlotId                                 Gauge32,
    cucsFabricFcVsanPortEpPortId                                     CucsFabricFcVsanPortEpPortId,
    cucsFabricFcVsanPortEpSlotId                                     CucsFabricFcVsanPortEpSlotId,
    cucsFabricFcVsanPortEpSwitchId                                   CucsNetworkSwitchId,
    cucsFabricFcVsanPortEpTransport                                  CucsFabricAFcSanEpTransport,
    cucsFabricFcVsanPortEpType                                       CucsFabricSanEpType,
    cucsFabricFcVsanPortEpPeerChassisId                              Gauge32,
    cucsFabricFcVsanPortEpFltAggr                                    Unsigned64,
    cucsFabricFcVsanPortEpOperState                                  CucsFabricPIoEpOperState,
    cucsFabricFcVsanPortEpOperStateReason                            SnmpAdminString,
    cucsFabricFcVsanPortEpWarnings                                   CucsFabricWarnings,
    cucsFabricFcVsanPortEpAggrPortId                                 Gauge32,
    cucsFabricFcVsanPortEpPeerAggrPortId                             Gauge32,
    cucsFabricFcVsanPortEpAutoNegotiate                              TruthValue
}

cucsFabricFcVsanPortEpInstanceId OBJECT-TYPE
    SYNTAX       CucsManagedObjectId
    MAX-ACCESS   not-accessible
    STATUS       current
    DESCRIPTION
        "Instance identifier of the managed object."
    ::= { cucsFabricFcVsanPortEpEntry 1 }

cucsFabricFcVsanPortEpDn OBJECT-TYPE
    SYNTAX       CucsManagedObjectDn
    MAX-ACCESS   read-only
    STATUS       current
    DESCRIPTION
        "Cisco UCS fabric:FcVsanPortEp:dn managed object property"
    ::= { cucsFabricFcVsanPortEpEntry 2 }

cucsFabricFcVsanPortEpRn OBJECT-TYPE
    SYNTAX       SnmpAdminString
    MAX-ACCESS   read-only
    STATUS       current
    DESCRIPTION
        "Cisco UCS fabric:FcVsanPortEp:rn managed object property"
    ::= { cucsFabricFcVsanPortEpEntry 3 }

cucsFabricFcVsanPortEpAdminState OBJECT-TYPE
    SYNTAX       CucsFabricExternalEpAdminState
    MAX-ACCESS   read-only
    STATUS       current
    DESCRIPTION
        "Cisco UCS fabric:FcVsanPortEp:adminState managed object property"
    ::= { cucsFabricFcVsanPortEpEntry 4 }

cucsFabricFcVsanPortEpChassisId OBJECT-TYPE
    SYNTAX       Gauge32
    MAX-ACCESS   read-only
    STATUS       current
    DESCRIPTION
        "Cisco UCS fabric:FcVsanPortEp:chassisId managed object property"
    ::= { cucsFabricFcVsanPortEpEntry 5 }

cucsFabricFcVsanPortEpEpDn OBJECT-TYPE
    SYNTAX       SnmpAdminString
    MAX-ACCESS   read-only
    STATUS       current
    DESCRIPTION
        "Cisco UCS fabric:FcVsanPortEp:epDn managed object property"
    ::= { cucsFabricFcVsanPortEpEntry 6 }

cucsFabricFcVsanPortEpIfRole OBJECT-TYPE
    SYNTAX       CucsFabricSanEpIfRole
    MAX-ACCESS   read-only
    STATUS       current
    DESCRIPTION
        "Cisco UCS fabric:FcVsanPortEp:ifRole managed object property"
    ::= { cucsFabricFcVsanPortEpEntry 7 }

cucsFabricFcVsanPortEpIfType OBJECT-TYPE
    SYNTAX       CucsFabricPIoEpIfType
    MAX-ACCESS   read-only
    STATUS       current
    DESCRIPTION
        "Cisco UCS fabric:FcVsanPortEp:ifType managed object property"
    ::= { cucsFabricFcVsanPortEpEntry 8 }

cucsFabricFcVsanPortEpLicGP OBJECT-TYPE
    SYNTAX       Unsigned64
    MAX-ACCESS   read-only
    STATUS       current
    DESCRIPTION
        "Cisco UCS fabric:FcVsanPortEp:licGP managed object property"
    ::= { cucsFabricFcVsanPortEpEntry 9 }

cucsFabricFcVsanPortEpLicState OBJECT-TYPE
    SYNTAX       CucsLicenseState
    MAX-ACCESS   read-only
    STATUS       current
    DESCRIPTION
        "Cisco UCS fabric:FcVsanPortEp:licState managed object property"
    ::= { cucsFabricFcVsanPortEpEntry 10 }

cucsFabricFcVsanPortEpLocale OBJECT-TYPE
    SYNTAX       CucsFabricExternalEpLocale
    MAX-ACCESS   read-only
    STATUS       current
    DESCRIPTION
        "Cisco UCS fabric:FcVsanPortEp:locale managed object property"
    ::= { cucsFabricFcVsanPortEpEntry 11 }

cucsFabricFcVsanPortEpName OBJECT-TYPE
    SYNTAX       SnmpAdminString
    MAX-ACCESS   read-only
    STATUS       current
    DESCRIPTION
        "Cisco UCS fabric:FcVsanPortEp:name managed object property"
    ::= { cucsFabricFcVsanPortEpEntry 12 }

cucsFabricFcVsanPortEpPeerDn OBJECT-TYPE
    SYNTAX       SnmpAdminString
    MAX-ACCESS   read-only
    STATUS       current
    DESCRIPTION
        "Cisco UCS fabric:FcVsanPortEp:peerDn managed object property"
    ::= { cucsFabricFcVsanPortEpEntry 13 }

cucsFabricFcVsanPortEpPeerPortId OBJECT-TYPE
    SYNTAX       Gauge32
    MAX-ACCESS   read-only
    STATUS       current
    DESCRIPTION
        "Cisco UCS fabric:FcVsanPortEp:peerPortId managed object property"
    ::= { cucsFabricFcVsanPortEpEntry 14 }

cucsFabricFcVsanPortEpPeerSlotId OBJECT-TYPE
    SYNTAX       Gauge32
    MAX-ACCESS   read-only
    STATUS       current
    DESCRIPTION
        "Cisco UCS fabric:FcVsanPortEp:peerSlotId managed object property"
    ::= { cucsFabricFcVsanPortEpEntry 15 }

cucsFabricFcVsanPortEpPortId OBJECT-TYPE
    SYNTAX       CucsFabricFcVsanPortEpPortId
    MAX-ACCESS   read-only
    STATUS       current
    DESCRIPTION
        "Cisco UCS fabric:FcVsanPortEp:portId managed object property"
    ::= { cucsFabricFcVsanPortEpEntry 16 }

cucsFabricFcVsanPortEpSlotId OBJECT-TYPE
    SYNTAX       CucsFabricFcVsanPortEpSlotId
    MAX-ACCESS   read-only
    STATUS       current
    DESCRIPTION
        "Cisco UCS fabric:FcVsanPortEp:slotId managed object property"
    ::= { cucsFabricFcVsanPortEpEntry 17 }

cucsFabricFcVsanPortEpSwitchId OBJECT-TYPE
    SYNTAX       CucsNetworkSwitchId
    MAX-ACCESS   read-only
    STATUS       current
    DESCRIPTION
        "Cisco UCS fabric:FcVsanPortEp:switchId managed object property"
    ::= { cucsFabricFcVsanPortEpEntry 18 }

cucsFabricFcVsanPortEpTransport OBJECT-TYPE
    SYNTAX       CucsFabricAFcSanEpTransport
    MAX-ACCESS   read-only
    STATUS       current
    DESCRIPTION
        "Cisco UCS fabric:FcVsanPortEp:transport managed object property"
    ::= { cucsFabricFcVsanPortEpEntry 19 }

cucsFabricFcVsanPortEpType OBJECT-TYPE
    SYNTAX       CucsFabricSanEpType
    MAX-ACCESS   read-only
    STATUS       current
    DESCRIPTION
        "Cisco UCS fabric:FcVsanPortEp:type managed object property"
    ::= { cucsFabricFcVsanPortEpEntry 20 }

cucsFabricFcVsanPortEpPeerChassisId OBJECT-TYPE
    SYNTAX       Gauge32
    MAX-ACCESS   read-only
    STATUS       current
    DESCRIPTION
        "Cisco UCS fabric:FcVsanPortEp:peerChassisId managed
        object property"
    ::= { cucsFabricFcVsanPortEpEntry 21 }

cucsFabricFcVsanPortEpFltAggr OBJECT-TYPE
    SYNTAX       Unsigned64
    MAX-ACCESS   read-only
    STATUS       current
    DESCRIPTION
        "Cisco UCS fabric:FcVsanPortEp:fltAggr managed object property"
    ::= { cucsFabricFcVsanPortEpEntry 22 }

cucsFabricFcVsanPortEpOperState OBJECT-TYPE
    SYNTAX       CucsFabricPIoEpOperState
    MAX-ACCESS   read-only
    STATUS       current
    DESCRIPTION
        "Cisco UCS fabric:FcVsanPortEp:operState managed object property"
    ::= { cucsFabricFcVsanPortEpEntry 23 }

cucsFabricFcVsanPortEpOperStateReason OBJECT-TYPE
    SYNTAX       SnmpAdminString
    MAX-ACCESS   read-only
    STATUS       current
    DESCRIPTION
        "Cisco UCS fabric:FcVsanPortEp:operStateReason
        managed object property"
    ::= { cucsFabricFcVsanPortEpEntry 24 }

cucsFabricFcVsanPortEpWarnings OBJECT-TYPE
    SYNTAX       CucsFabricWarnings
    MAX-ACCESS   read-only
    STATUS       current
    DESCRIPTION
        "Cisco UCS fabric:FcVsanPortEp:warnings managed object property"
    ::= { cucsFabricFcVsanPortEpEntry 25 }

cucsFabricFcVsanPortEpAggrPortId OBJECT-TYPE
    SYNTAX       Gauge32
    MAX-ACCESS   read-only
    STATUS       current
    DESCRIPTION
        "Cisco UCS fabric:FcVsanPortEp:aggrPortId managed object property"
    ::= { cucsFabricFcVsanPortEpEntry 26 }

cucsFabricFcVsanPortEpPeerAggrPortId OBJECT-TYPE
    SYNTAX       Gauge32
    MAX-ACCESS   read-only
    STATUS       current
    DESCRIPTION
        "Cisco UCS fabric:FcVsanPortEp:peerAggrPortId managed
        object property"
    ::= { cucsFabricFcVsanPortEpEntry 27 }

cucsFabricFcVsanPortEpAutoNegotiate OBJECT-TYPE
    SYNTAX       TruthValue
    MAX-ACCESS   read-only
    STATUS       current
    DESCRIPTION
        "Cisco UCS fabric:FcVsanPortEp:autoNegotiate managed
        object property"
    ::= { cucsFabricFcVsanPortEpEntry 28 }

cucsFabricFcoeEstcEpTable OBJECT-TYPE
    SYNTAX           SEQUENCE OF CucsFabricFcoeEstcEpEntry
    MAX-ACCESS       not-accessible
    STATUS           current
    DESCRIPTION
        "Cisco UCS fabric:FcoeEstcEp managed object table"
    ::= { cucsFabricObjects 40 }

cucsFabricFcoeEstcEpEntry OBJECT-TYPE
    SYNTAX           CucsFabricFcoeEstcEpEntry
    MAX-ACCESS       not-accessible
    STATUS           current
    DESCRIPTION
        "Entry for the cucsFabricFcoeEstcEpTable table."
    INDEX { cucsFabricFcoeEstcEpInstanceId }
    ::= { cucsFabricFcoeEstcEpTable 1 }

CucsFabricFcoeEstcEpEntry ::= SEQUENCE {
    cucsFabricFcoeEstcEpInstanceId                                   CucsManagedObjectId,
    cucsFabricFcoeEstcEpDn                                           CucsManagedObjectDn,
    cucsFabricFcoeEstcEpRn                                           SnmpAdminString,
    cucsFabricFcoeEstcEpAdminState                                   CucsFabricExternalEpAdminState,
    cucsFabricFcoeEstcEpChassisId                                    Gauge32,
    cucsFabricFcoeEstcEpConfigState                                  CucsFabricConfigState,
    cucsFabricFcoeEstcEpEpDn                                         SnmpAdminString,
    cucsFabricFcoeEstcEpIfRole                                       CucsFabricAFcoeEstcEpIfRole,
    cucsFabricFcoeEstcEpIfType                                       CucsFabricPIoEpIfType,
    cucsFabricFcoeEstcEpLicGP                                        Unsigned64,
    cucsFabricFcoeEstcEpLicState                                     CucsLicenseState,
    cucsFabricFcoeEstcEpLocale                                       CucsFabricExternalEpLocale,
    cucsFabricFcoeEstcEpName                                         SnmpAdminString,
    cucsFabricFcoeEstcEpPeerDn                                       SnmpAdminString,
    cucsFabricFcoeEstcEpPeerPortId                                   Gauge32,
    cucsFabricFcoeEstcEpPeerSlotId                                   Gauge32,
    cucsFabricFcoeEstcEpPortId                                       CucsFabricFcoeEstcEpPortId,
    cucsFabricFcoeEstcEpSlotId                                       CucsFabricFcoeEstcEpSlotId,
    cucsFabricFcoeEstcEpSwitchId                                     CucsNetworkSwitchId,
    cucsFabricFcoeEstcEpTransport                                    CucsFabricAFcoeEstcEpTransport,
    cucsFabricFcoeEstcEpType                                         CucsFabricAFcoeEstcEpType,
    cucsFabricFcoeEstcEpUsrLbl                                       SnmpAdminString,
    cucsFabricFcoeEstcEpPeerChassisId                                Gauge32,
    cucsFabricFcoeEstcEpFltAggr                                      Unsigned64,
    cucsFabricFcoeEstcEpOperState                                    CucsFabricPIoEpOperState,
    cucsFabricFcoeEstcEpOperStateReason                              SnmpAdminString,
    cucsFabricFcoeEstcEpWarnings                                     CucsFabricWarnings,
    cucsFabricFcoeEstcEpFcoeState                                    CucsNetworkPortOperState,
    cucsFabricFcoeEstcEpFcoeStateReason                              SnmpAdminString,
    cucsFabricFcoeEstcEpAggrPortId                                   Gauge32,
    cucsFabricFcoeEstcEpPeerAggrPortId                               Gauge32,
    cucsFabricFcoeEstcEpAutoNegotiate                                TruthValue
}

cucsFabricFcoeEstcEpInstanceId OBJECT-TYPE
    SYNTAX       CucsManagedObjectId
    MAX-ACCESS   not-accessible
    STATUS       current
    DESCRIPTION
        "Instance identifier of the managed object."
    ::= { cucsFabricFcoeEstcEpEntry 1 }

cucsFabricFcoeEstcEpDn OBJECT-TYPE
    SYNTAX       CucsManagedObjectDn
    MAX-ACCESS   read-only
    STATUS       current
    DESCRIPTION
        "Cisco UCS fabric:FcoeEstcEp:dn managed object property"
    ::= { cucsFabricFcoeEstcEpEntry 2 }

cucsFabricFcoeEstcEpRn OBJECT-TYPE
    SYNTAX       SnmpAdminString
    MAX-ACCESS   read-only
    STATUS       current
    DESCRIPTION
        "Cisco UCS fabric:FcoeEstcEp:rn managed object property"
    ::= { cucsFabricFcoeEstcEpEntry 3 }

cucsFabricFcoeEstcEpAdminState OBJECT-TYPE
    SYNTAX       CucsFabricExternalEpAdminState
    MAX-ACCESS   read-only
    STATUS       current
    DESCRIPTION
        "Cisco UCS fabric:FcoeEstcEp:adminState managed object property"
    ::= { cucsFabricFcoeEstcEpEntry 4 }

cucsFabricFcoeEstcEpChassisId OBJECT-TYPE
    SYNTAX       Gauge32
    MAX-ACCESS   read-only
    STATUS       current
    DESCRIPTION
        "Cisco UCS fabric:FcoeEstcEp:chassisId managed object property"
    ::= { cucsFabricFcoeEstcEpEntry 5 }

cucsFabricFcoeEstcEpConfigState OBJECT-TYPE
    SYNTAX       CucsFabricConfigState
    MAX-ACCESS   read-only
    STATUS       current
    DESCRIPTION
        "Cisco UCS fabric:FcoeEstcEp:configState managed object property"
    ::= { cucsFabricFcoeEstcEpEntry 6 }

cucsFabricFcoeEstcEpEpDn OBJECT-TYPE
    SYNTAX       SnmpAdminString
    MAX-ACCESS   read-only
    STATUS       current
    DESCRIPTION
        "Cisco UCS fabric:FcoeEstcEp:epDn managed object property"
    ::= { cucsFabricFcoeEstcEpEntry 7 }

cucsFabricFcoeEstcEpIfRole OBJECT-TYPE
    SYNTAX       CucsFabricAFcoeEstcEpIfRole
    MAX-ACCESS   read-only
    STATUS       current
    DESCRIPTION
        "Cisco UCS fabric:FcoeEstcEp:ifRole managed object property"
    ::= { cucsFabricFcoeEstcEpEntry 8 }

cucsFabricFcoeEstcEpIfType OBJECT-TYPE
    SYNTAX       CucsFabricPIoEpIfType
    MAX-ACCESS   read-only
    STATUS       current
    DESCRIPTION
        "Cisco UCS fabric:FcoeEstcEp:ifType managed object property"
    ::= { cucsFabricFcoeEstcEpEntry 9 }

cucsFabricFcoeEstcEpLicGP OBJECT-TYPE
    SYNTAX       Unsigned64
    MAX-ACCESS   read-only
    STATUS       current
    DESCRIPTION
        "Cisco UCS fabric:FcoeEstcEp:licGP managed object property"
    ::= { cucsFabricFcoeEstcEpEntry 10 }

cucsFabricFcoeEstcEpLicState OBJECT-TYPE
    SYNTAX       CucsLicenseState
    MAX-ACCESS   read-only
    STATUS       current
    DESCRIPTION
        "Cisco UCS fabric:FcoeEstcEp:licState managed object property"
    ::= { cucsFabricFcoeEstcEpEntry 11 }

cucsFabricFcoeEstcEpLocale OBJECT-TYPE
    SYNTAX       CucsFabricExternalEpLocale
    MAX-ACCESS   read-only
    STATUS       current
    DESCRIPTION
        "Cisco UCS fabric:FcoeEstcEp:locale managed object property"
    ::= { cucsFabricFcoeEstcEpEntry 12 }

cucsFabricFcoeEstcEpName OBJECT-TYPE
    SYNTAX       SnmpAdminString
    MAX-ACCESS   read-only
    STATUS       current
    DESCRIPTION
        "Cisco UCS fabric:FcoeEstcEp:name managed object property"
    ::= { cucsFabricFcoeEstcEpEntry 13 }

cucsFabricFcoeEstcEpPeerDn OBJECT-TYPE
    SYNTAX       SnmpAdminString
    MAX-ACCESS   read-only
    STATUS       current
    DESCRIPTION
        "Cisco UCS fabric:FcoeEstcEp:peerDn managed object property"
    ::= { cucsFabricFcoeEstcEpEntry 14 }

cucsFabricFcoeEstcEpPeerPortId OBJECT-TYPE
    SYNTAX       Gauge32
    MAX-ACCESS   read-only
    STATUS       current
    DESCRIPTION
        "Cisco UCS fabric:FcoeEstcEp:peerPortId managed object property"
    ::= { cucsFabricFcoeEstcEpEntry 15 }

cucsFabricFcoeEstcEpPeerSlotId OBJECT-TYPE
    SYNTAX       Gauge32
    MAX-ACCESS   read-only
    STATUS       current
    DESCRIPTION
        "Cisco UCS fabric:FcoeEstcEp:peerSlotId managed object property"
    ::= { cucsFabricFcoeEstcEpEntry 16 }

cucsFabricFcoeEstcEpPortId OBJECT-TYPE
    SYNTAX       CucsFabricFcoeEstcEpPortId
    MAX-ACCESS   read-only
    STATUS       current
    DESCRIPTION
        "Cisco UCS fabric:FcoeEstcEp:portId managed object property"
    ::= { cucsFabricFcoeEstcEpEntry 17 }

cucsFabricFcoeEstcEpSlotId OBJECT-TYPE
    SYNTAX       CucsFabricFcoeEstcEpSlotId
    MAX-ACCESS   read-only
    STATUS       current
    DESCRIPTION
        "Cisco UCS fabric:FcoeEstcEp:slotId managed object property"
    ::= { cucsFabricFcoeEstcEpEntry 18 }

cucsFabricFcoeEstcEpSwitchId OBJECT-TYPE
    SYNTAX       CucsNetworkSwitchId
    MAX-ACCESS   read-only
    STATUS       current
    DESCRIPTION
        "Cisco UCS fabric:FcoeEstcEp:switchId managed object property"
    ::= { cucsFabricFcoeEstcEpEntry 19 }

cucsFabricFcoeEstcEpTransport OBJECT-TYPE
    SYNTAX       CucsFabricAFcoeEstcEpTransport
    MAX-ACCESS   read-only
    STATUS       current
    DESCRIPTION
        "Cisco UCS fabric:FcoeEstcEp:transport managed object property"
    ::= { cucsFabricFcoeEstcEpEntry 20 }

cucsFabricFcoeEstcEpType OBJECT-TYPE
    SYNTAX       CucsFabricAFcoeEstcEpType
    MAX-ACCESS   read-only
    STATUS       current
    DESCRIPTION
        "Cisco UCS fabric:FcoeEstcEp:type managed object property"
    ::= { cucsFabricFcoeEstcEpEntry 21 }

cucsFabricFcoeEstcEpUsrLbl OBJECT-TYPE
    SYNTAX       SnmpAdminString
    MAX-ACCESS   read-only
    STATUS       current
    DESCRIPTION
        "Cisco UCS fabric:FcoeEstcEp:usrLbl managed object property"
    ::= { cucsFabricFcoeEstcEpEntry 22 }

cucsFabricFcoeEstcEpPeerChassisId OBJECT-TYPE
    SYNTAX       Gauge32
    MAX-ACCESS   read-only
    STATUS       current
    DESCRIPTION
        "Cisco UCS fabric:FcoeEstcEp:peerChassisId managed
        object property"
    ::= { cucsFabricFcoeEstcEpEntry 23 }

cucsFabricFcoeEstcEpFltAggr OBJECT-TYPE
    SYNTAX       Unsigned64
    MAX-ACCESS   read-only
    STATUS       current
    DESCRIPTION
        "Cisco UCS fabric:FcoeEstcEp:fltAggr managed object property"
    ::= { cucsFabricFcoeEstcEpEntry 24 }

cucsFabricFcoeEstcEpOperState OBJECT-TYPE
    SYNTAX       CucsFabricPIoEpOperState
    MAX-ACCESS   read-only
    STATUS       current
    DESCRIPTION
        "Cisco UCS fabric:FcoeEstcEp:operState managed object property"
    ::= { cucsFabricFcoeEstcEpEntry 25 }

cucsFabricFcoeEstcEpOperStateReason OBJECT-TYPE
    SYNTAX       SnmpAdminString
    MAX-ACCESS   read-only
    STATUS       current
    DESCRIPTION
        "Cisco UCS fabric:FcoeEstcEp:operStateReason managed
        object property"
    ::= { cucsFabricFcoeEstcEpEntry 26 }

cucsFabricFcoeEstcEpWarnings OBJECT-TYPE
    SYNTAX       CucsFabricWarnings
    MAX-ACCESS   read-only
    STATUS       current
    DESCRIPTION
        "Cisco UCS fabric:FcoeEstcEp:warnings managed object property"
    ::= { cucsFabricFcoeEstcEpEntry 28 }

cucsFabricFcoeEstcEpFcoeState OBJECT-TYPE
    SYNTAX       CucsNetworkPortOperState
    MAX-ACCESS   read-only
    STATUS       current
    DESCRIPTION
        "Cisco UCS fabric:FcoeEstcEp:fcoeState managed object property"
    ::= { cucsFabricFcoeEstcEpEntry 29 }

cucsFabricFcoeEstcEpFcoeStateReason OBJECT-TYPE
    SYNTAX       SnmpAdminString
    MAX-ACCESS   read-only
    STATUS       current
    DESCRIPTION
        "Cisco UCS fabric:FcoeEstcEp:fcoeStateReason managed
        object property"
    ::= { cucsFabricFcoeEstcEpEntry 30 }

cucsFabricFcoeEstcEpAggrPortId OBJECT-TYPE
    SYNTAX       Gauge32
    MAX-ACCESS   read-only
    STATUS       current
    DESCRIPTION
        "Cisco UCS fabric:FcoeEstcEp:aggrPortId managed object property"
    ::= { cucsFabricFcoeEstcEpEntry 31 }

cucsFabricFcoeEstcEpPeerAggrPortId OBJECT-TYPE
    SYNTAX       Gauge32
    MAX-ACCESS   read-only
    STATUS       current
    DESCRIPTION
        "Cisco UCS fabric:FcoeEstcEp:peerAggrPortId managed
        object property"
    ::= { cucsFabricFcoeEstcEpEntry 32 }

cucsFabricFcoeEstcEpAutoNegotiate OBJECT-TYPE
    SYNTAX       TruthValue
    MAX-ACCESS   read-only
    STATUS       current
    DESCRIPTION
        "Cisco UCS fabric:FcoeEstcEp:autoNegotiate managed
        object property"
    ::= { cucsFabricFcoeEstcEpEntry 33 }

cucsFabricFcoeSanEpTable OBJECT-TYPE
    SYNTAX           SEQUENCE OF CucsFabricFcoeSanEpEntry
    MAX-ACCESS       not-accessible
    STATUS           current
    DESCRIPTION
        "Cisco UCS fabric:FcoeSanEp managed object table"
    ::= { cucsFabricObjects 78 }

cucsFabricFcoeSanEpEntry OBJECT-TYPE
    SYNTAX           CucsFabricFcoeSanEpEntry
    MAX-ACCESS       not-accessible
    STATUS           current
    DESCRIPTION
        "Entry for the cucsFabricFcoeSanEpTable table."
    INDEX { cucsFabricFcoeSanEpInstanceId }
    ::= { cucsFabricFcoeSanEpTable 1 }

CucsFabricFcoeSanEpEntry ::= SEQUENCE {
    cucsFabricFcoeSanEpInstanceId                                    CucsManagedObjectId,
    cucsFabricFcoeSanEpDn                                            CucsManagedObjectDn,
    cucsFabricFcoeSanEpRn                                            SnmpAdminString,
    cucsFabricFcoeSanEpAdminState                                    CucsFabricExternalEpAdminState,
    cucsFabricFcoeSanEpChassisId                                     Gauge32,
    cucsFabricFcoeSanEpConfigState                                   CucsFabricConfigState,
    cucsFabricFcoeSanEpEpDn                                          SnmpAdminString,
    cucsFabricFcoeSanEpFltAggr                                       Unsigned64,
    cucsFabricFcoeSanEpIfRole                                        CucsFabricSanEpIfRole,
    cucsFabricFcoeSanEpIfType                                        CucsFabricPIoEpIfType,
    cucsFabricFcoeSanEpLicGP                                         Unsigned64,
    cucsFabricFcoeSanEpLicState                                      CucsLicenseState,
    cucsFabricFcoeSanEpLocale                                        CucsFabricExternalEpLocale,
    cucsFabricFcoeSanEpName                                          SnmpAdminString,
    cucsFabricFcoeSanEpOperState                                     CucsFabricPIoEpOperState,
    cucsFabricFcoeSanEpOperStateReason                               SnmpAdminString,
    cucsFabricFcoeSanEpPeerChassisId                                 Gauge32,
    cucsFabricFcoeSanEpPeerDn                                        SnmpAdminString,
    cucsFabricFcoeSanEpPeerPortId                                    Gauge32,
    cucsFabricFcoeSanEpPeerSlotId                                    Gauge32,
    cucsFabricFcoeSanEpPortId                                        CucsFabricFcoeSanEpPortId,
    cucsFabricFcoeSanEpSlotId                                        CucsFabricFcoeSanEpSlotId,
    cucsFabricFcoeSanEpSwitchId                                      CucsNetworkSwitchId,
    cucsFabricFcoeSanEpTransport                                     CucsFabricAFcoeSanEpTransport,
    cucsFabricFcoeSanEpType                                          CucsFabricSanEpType,
    cucsFabricFcoeSanEpUsrLbl                                        SnmpAdminString,
    cucsFabricFcoeSanEpWarnings                                      CucsFabricWarnings,
    cucsFabricFcoeSanEpFcoeState                                     CucsNetworkPortOperState,
    cucsFabricFcoeSanEpFcoeStateReason                               SnmpAdminString,
    cucsFabricFcoeSanEpEthLinkProfileName                            SnmpAdminString,
    cucsFabricFcoeSanEpOperEthLinkProfileName                        SnmpAdminString,
    cucsFabricFcoeSanEpUdldOperState                                 CucsFabricUdldOperState,
    cucsFabricFcoeSanEpAggrPortId                                    Gauge32,
    cucsFabricFcoeSanEpPeerAggrPortId                                Gauge32,
    cucsFabricFcoeSanEpAutoNegotiate                                 TruthValue
}

cucsFabricFcoeSanEpInstanceId OBJECT-TYPE
    SYNTAX       CucsManagedObjectId
    MAX-ACCESS   not-accessible
    STATUS       current
    DESCRIPTION
        "Instance identifier of the managed object."
    ::= { cucsFabricFcoeSanEpEntry 1 }

cucsFabricFcoeSanEpDn OBJECT-TYPE
    SYNTAX       CucsManagedObjectDn
    MAX-ACCESS   read-only
    STATUS       current
    DESCRIPTION
        "Cisco UCS fabric:FcoeSanEp:dn managed object property"
    ::= { cucsFabricFcoeSanEpEntry 2 }

cucsFabricFcoeSanEpRn OBJECT-TYPE
    SYNTAX       SnmpAdminString
    MAX-ACCESS   read-only
    STATUS       current
    DESCRIPTION
        "Cisco UCS fabric:FcoeSanEp:rn managed object property"
    ::= { cucsFabricFcoeSanEpEntry 3 }

cucsFabricFcoeSanEpAdminState OBJECT-TYPE
    SYNTAX       CucsFabricExternalEpAdminState
    MAX-ACCESS   read-only
    STATUS       current
    DESCRIPTION
        "Cisco UCS fabric:FcoeSanEp:adminState managed object property"
    ::= { cucsFabricFcoeSanEpEntry 4 }

cucsFabricFcoeSanEpChassisId OBJECT-TYPE
    SYNTAX       Gauge32
    MAX-ACCESS   read-only
    STATUS       current
    DESCRIPTION
        "Cisco UCS fabric:FcoeSanEp:chassisId managed object property"
    ::= { cucsFabricFcoeSanEpEntry 5 }

cucsFabricFcoeSanEpConfigState OBJECT-TYPE
    SYNTAX       CucsFabricConfigState
    MAX-ACCESS   read-only
    STATUS       current
    DESCRIPTION
        "Cisco UCS fabric:FcoeSanEp:configState managed object property"
    ::= { cucsFabricFcoeSanEpEntry 6 }

cucsFabricFcoeSanEpEpDn OBJECT-TYPE
    SYNTAX       SnmpAdminString
    MAX-ACCESS   read-only
    STATUS       current
    DESCRIPTION
        "Cisco UCS fabric:FcoeSanEp:epDn managed object property"
    ::= { cucsFabricFcoeSanEpEntry 7 }

cucsFabricFcoeSanEpFltAggr OBJECT-TYPE
    SYNTAX       Unsigned64
    MAX-ACCESS   read-only
    STATUS       current
    DESCRIPTION
        "Cisco UCS fabric:FcoeSanEp:fltAggr managed object property"
    ::= { cucsFabricFcoeSanEpEntry 8 }

cucsFabricFcoeSanEpIfRole OBJECT-TYPE
    SYNTAX       CucsFabricSanEpIfRole
    MAX-ACCESS   read-only
    STATUS       current
    DESCRIPTION
        "Cisco UCS fabric:FcoeSanEp:ifRole managed object property"
    ::= { cucsFabricFcoeSanEpEntry 9 }

cucsFabricFcoeSanEpIfType OBJECT-TYPE
    SYNTAX       CucsFabricPIoEpIfType
    MAX-ACCESS   read-only
    STATUS       current
    DESCRIPTION
        "Cisco UCS fabric:FcoeSanEp:ifType managed object property"
    ::= { cucsFabricFcoeSanEpEntry 10 }

cucsFabricFcoeSanEpLicGP OBJECT-TYPE
    SYNTAX       Unsigned64
    MAX-ACCESS   read-only
    STATUS       current
    DESCRIPTION
        "Cisco UCS fabric:FcoeSanEp:licGP managed object property"
    ::= { cucsFabricFcoeSanEpEntry 11 }

cucsFabricFcoeSanEpLicState OBJECT-TYPE
    SYNTAX       CucsLicenseState
    MAX-ACCESS   read-only
    STATUS       current
    DESCRIPTION
        "Cisco UCS fabric:FcoeSanEp:licState managed object property"
    ::= { cucsFabricFcoeSanEpEntry 12 }

cucsFabricFcoeSanEpLocale OBJECT-TYPE
    SYNTAX       CucsFabricExternalEpLocale
    MAX-ACCESS   read-only
    STATUS       current
    DESCRIPTION
        "Cisco UCS fabric:FcoeSanEp:locale managed object property"
    ::= { cucsFabricFcoeSanEpEntry 13 }

cucsFabricFcoeSanEpName OBJECT-TYPE
    SYNTAX       SnmpAdminString
    MAX-ACCESS   read-only
    STATUS       current
    DESCRIPTION
        "Cisco UCS fabric:FcoeSanEp:name managed object property"
    ::= { cucsFabricFcoeSanEpEntry 14 }

cucsFabricFcoeSanEpOperState OBJECT-TYPE
    SYNTAX       CucsFabricPIoEpOperState
    MAX-ACCESS   read-only
    STATUS       current
    DESCRIPTION
        "Cisco UCS fabric:FcoeSanEp:operState managed object property"
    ::= { cucsFabricFcoeSanEpEntry 15 }

cucsFabricFcoeSanEpOperStateReason OBJECT-TYPE
    SYNTAX       SnmpAdminString
    MAX-ACCESS   read-only
    STATUS       current
    DESCRIPTION
        "Cisco UCS fabric:FcoeSanEp:operStateReason managed
        object property"
    ::= { cucsFabricFcoeSanEpEntry 16 }

cucsFabricFcoeSanEpPeerChassisId OBJECT-TYPE
    SYNTAX       Gauge32
    MAX-ACCESS   read-only
    STATUS       current
    DESCRIPTION
        "Cisco UCS fabric:FcoeSanEp:peerChassisId managed object property"
    ::= { cucsFabricFcoeSanEpEntry 18 }

cucsFabricFcoeSanEpPeerDn OBJECT-TYPE
    SYNTAX       SnmpAdminString
    MAX-ACCESS   read-only
    STATUS       current
    DESCRIPTION
        "Cisco UCS fabric:FcoeSanEp:peerDn managed object property"
    ::= { cucsFabricFcoeSanEpEntry 19 }

cucsFabricFcoeSanEpPeerPortId OBJECT-TYPE
    SYNTAX       Gauge32
    MAX-ACCESS   read-only
    STATUS       current
    DESCRIPTION
        "Cisco UCS fabric:FcoeSanEp:peerPortId managed object property"
    ::= { cucsFabricFcoeSanEpEntry 20 }

cucsFabricFcoeSanEpPeerSlotId OBJECT-TYPE
    SYNTAX       Gauge32
    MAX-ACCESS   read-only
    STATUS       current
    DESCRIPTION
        "Cisco UCS fabric:FcoeSanEp:peerSlotId managed object property"
    ::= { cucsFabricFcoeSanEpEntry 21 }

cucsFabricFcoeSanEpPortId OBJECT-TYPE
    SYNTAX       CucsFabricFcoeSanEpPortId
    MAX-ACCESS   read-only
    STATUS       current
    DESCRIPTION
        "Cisco UCS fabric:FcoeSanEp:portId managed object property"
    ::= { cucsFabricFcoeSanEpEntry 22 }

cucsFabricFcoeSanEpSlotId OBJECT-TYPE
    SYNTAX       CucsFabricFcoeSanEpSlotId
    MAX-ACCESS   read-only
    STATUS       current
    DESCRIPTION
        "Cisco UCS fabric:FcoeSanEp:slotId managed object property"
    ::= { cucsFabricFcoeSanEpEntry 23 }

cucsFabricFcoeSanEpSwitchId OBJECT-TYPE
    SYNTAX       CucsNetworkSwitchId
    MAX-ACCESS   read-only
    STATUS       current
    DESCRIPTION
        "Cisco UCS fabric:FcoeSanEp:switchId managed object property"
    ::= { cucsFabricFcoeSanEpEntry 24 }

cucsFabricFcoeSanEpTransport OBJECT-TYPE
    SYNTAX       CucsFabricAFcoeSanEpTransport
    MAX-ACCESS   read-only
    STATUS       current
    DESCRIPTION
        "Cisco UCS fabric:FcoeSanEp:transport managed object property"
    ::= { cucsFabricFcoeSanEpEntry 25 }

cucsFabricFcoeSanEpType OBJECT-TYPE
    SYNTAX       CucsFabricSanEpType
    MAX-ACCESS   read-only
    STATUS       current
    DESCRIPTION
        "Cisco UCS fabric:FcoeSanEp:type managed object property"
    ::= { cucsFabricFcoeSanEpEntry 26 }

cucsFabricFcoeSanEpUsrLbl OBJECT-TYPE
    SYNTAX       SnmpAdminString
    MAX-ACCESS   read-only
    STATUS       current
    DESCRIPTION
        "Cisco UCS fabric:FcoeSanEp:usrLbl managed object property"
    ::= { cucsFabricFcoeSanEpEntry 27 }

cucsFabricFcoeSanEpWarnings OBJECT-TYPE
    SYNTAX       CucsFabricWarnings
    MAX-ACCESS   read-only
    STATUS       current
    DESCRIPTION
        "Cisco UCS fabric:FcoeSanEp:warnings managed object property"
    ::= { cucsFabricFcoeSanEpEntry 28 }

cucsFabricFcoeSanEpFcoeState OBJECT-TYPE
    SYNTAX       CucsNetworkPortOperState
    MAX-ACCESS   read-only
    STATUS       current
    DESCRIPTION
        "Cisco UCS fabric:FcoeSanEp:fcoeState managed object property"
    ::= { cucsFabricFcoeSanEpEntry 29 }

cucsFabricFcoeSanEpFcoeStateReason OBJECT-TYPE
    SYNTAX       SnmpAdminString
    MAX-ACCESS   read-only
    STATUS       current
    DESCRIPTION
        "Cisco UCS fabric:FcoeSanEp:fcoeStateReason managed
        object property"
    ::= { cucsFabricFcoeSanEpEntry 30 }

cucsFabricFcoeSanEpEthLinkProfileName OBJECT-TYPE
    SYNTAX       SnmpAdminString
    MAX-ACCESS   read-only
    STATUS       current
    DESCRIPTION
        "Cisco UCS fabric:FcoeSanEp:ethLinkProfileName
        managed object property"
    ::= { cucsFabricFcoeSanEpEntry 31 }

cucsFabricFcoeSanEpOperEthLinkProfileName OBJECT-TYPE
    SYNTAX       SnmpAdminString
    MAX-ACCESS   read-only
    STATUS       current
    DESCRIPTION
        "Cisco UCS fabric:FcoeSanEp:operEthLinkProfileName
        managed object property"
    ::= { cucsFabricFcoeSanEpEntry 32 }

cucsFabricFcoeSanEpUdldOperState OBJECT-TYPE
    SYNTAX       CucsFabricUdldOperState
    MAX-ACCESS   read-only
    STATUS       current
    DESCRIPTION
        "Cisco UCS fabric:FcoeSanEp:udldOperState managed object property"
    ::= { cucsFabricFcoeSanEpEntry 33 }

cucsFabricFcoeSanEpAggrPortId OBJECT-TYPE
    SYNTAX       Gauge32
    MAX-ACCESS   read-only
    STATUS       current
    DESCRIPTION
        "Cisco UCS fabric:FcoeSanEp:aggrPortId managed object property"
    ::= { cucsFabricFcoeSanEpEntry 34 }

cucsFabricFcoeSanEpPeerAggrPortId OBJECT-TYPE
    SYNTAX       Gauge32
    MAX-ACCESS   read-only
    STATUS       current
    DESCRIPTION
        "Cisco UCS fabric:FcoeSanEp:peerAggrPortId managed
        object property"
    ::= { cucsFabricFcoeSanEpEntry 35 }

cucsFabricFcoeSanEpAutoNegotiate OBJECT-TYPE
    SYNTAX       TruthValue
    MAX-ACCESS   read-only
    STATUS       current
    DESCRIPTION
        "Cisco UCS fabric:FcoeSanEp:autoNegotiate managed object property"
    ::= { cucsFabricFcoeSanEpEntry 36 }

cucsFabricFcoeSanPcTable OBJECT-TYPE
    SYNTAX           SEQUENCE OF CucsFabricFcoeSanPcEntry
    MAX-ACCESS       not-accessible
    STATUS           current
    DESCRIPTION
        "Cisco UCS fabric:FcoeSanPc managed object table"
    ::= { cucsFabricObjects 79 }

cucsFabricFcoeSanPcEntry OBJECT-TYPE
    SYNTAX           CucsFabricFcoeSanPcEntry
    MAX-ACCESS       not-accessible
    STATUS           current
    DESCRIPTION
        "Entry for the cucsFabricFcoeSanPcTable table."
    INDEX { cucsFabricFcoeSanPcInstanceId }
    ::= { cucsFabricFcoeSanPcTable 1 }

CucsFabricFcoeSanPcEntry ::= SEQUENCE {
    cucsFabricFcoeSanPcInstanceId                                    CucsManagedObjectId,
    cucsFabricFcoeSanPcDn                                            CucsManagedObjectDn,
    cucsFabricFcoeSanPcRn                                            SnmpAdminString,
    cucsFabricFcoeSanPcAdminState                                    CucsFabricCIoEpAdminState,
    cucsFabricFcoeSanPcConfigState                                   CucsFabricConfigState,
    cucsFabricFcoeSanPcEpDn                                          SnmpAdminString,
    cucsFabricFcoeSanPcFltAggr                                       Unsigned64,
    cucsFabricFcoeSanPcIfRole                                        CucsFabricSanPcIfRole,
    cucsFabricFcoeSanPcIfType                                        CucsFabricCIoEpIfType,
    cucsFabricFcoeSanPcLocale                                        CucsFabricExternalPcLocale,
    cucsFabricFcoeSanPcName                                          SnmpAdminString,
    cucsFabricFcoeSanPcOperState                                     CucsNetworkPortOperState,
    cucsFabricFcoeSanPcPeerDn                                        SnmpAdminString,
    cucsFabricFcoeSanPcPortId                                        Gauge32,
    cucsFabricFcoeSanPcStateQual                                     SnmpAdminString,
    cucsFabricFcoeSanPcSwitchId                                      CucsNetworkSwitchId,
    cucsFabricFcoeSanPcTransport                                     CucsFabricFcoeSanPcTransport,
    cucsFabricFcoeSanPcType                                          CucsFabricSanPcType,
    cucsFabricFcoeSanPcWarnings                                      CucsFabricWarnings,
    cucsFabricFcoeSanPcFcoeState                                     CucsNetworkPortOperState,
    cucsFabricFcoeSanPcFcoeStateReason                               SnmpAdminString,
    cucsFabricFcoeSanPcDescr                                         SnmpAdminString,
    cucsFabricFcoeSanPcLacpPolicyName                                SnmpAdminString,
    cucsFabricFcoeSanPcOperLacpPolicyName                            SnmpAdminString,
    cucsFabricFcoeSanPcSpeed                                         CucsPortEthAdminSpeed
}

cucsFabricFcoeSanPcInstanceId OBJECT-TYPE
    SYNTAX       CucsManagedObjectId
    MAX-ACCESS   not-accessible
    STATUS       current
    DESCRIPTION
        "Instance identifier of the managed object."
    ::= { cucsFabricFcoeSanPcEntry 1 }

cucsFabricFcoeSanPcDn OBJECT-TYPE
    SYNTAX       CucsManagedObjectDn
    MAX-ACCESS   read-only
    STATUS       current
    DESCRIPTION
        "Cisco UCS fabric:FcoeSanPc:dn managed object property"
    ::= { cucsFabricFcoeSanPcEntry 2 }

cucsFabricFcoeSanPcRn OBJECT-TYPE
    SYNTAX       SnmpAdminString
    MAX-ACCESS   read-only
    STATUS       current
    DESCRIPTION
        "Cisco UCS fabric:FcoeSanPc:rn managed object property"
    ::= { cucsFabricFcoeSanPcEntry 3 }

cucsFabricFcoeSanPcAdminState OBJECT-TYPE
    SYNTAX       CucsFabricCIoEpAdminState
    MAX-ACCESS   read-only
    STATUS       current
    DESCRIPTION
        "Cisco UCS fabric:FcoeSanPc:adminState managed object property"
    ::= { cucsFabricFcoeSanPcEntry 4 }

cucsFabricFcoeSanPcConfigState OBJECT-TYPE
    SYNTAX       CucsFabricConfigState
    MAX-ACCESS   read-only
    STATUS       current
    DESCRIPTION
        "Cisco UCS fabric:FcoeSanPc:configState managed object property"
    ::= { cucsFabricFcoeSanPcEntry 5 }

cucsFabricFcoeSanPcEpDn OBJECT-TYPE
    SYNTAX       SnmpAdminString
    MAX-ACCESS   read-only
    STATUS       current
    DESCRIPTION
        "Cisco UCS fabric:FcoeSanPc:epDn managed object property"
    ::= { cucsFabricFcoeSanPcEntry 6 }

cucsFabricFcoeSanPcFltAggr OBJECT-TYPE
    SYNTAX       Unsigned64
    MAX-ACCESS   read-only
    STATUS       current
    DESCRIPTION
        "Cisco UCS fabric:FcoeSanPc:fltAggr managed object property"
    ::= { cucsFabricFcoeSanPcEntry 7 }

cucsFabricFcoeSanPcIfRole OBJECT-TYPE
    SYNTAX       CucsFabricSanPcIfRole
    MAX-ACCESS   read-only
    STATUS       current
    DESCRIPTION
        "Cisco UCS fabric:FcoeSanPc:ifRole managed object property"
    ::= { cucsFabricFcoeSanPcEntry 8 }

cucsFabricFcoeSanPcIfType OBJECT-TYPE
    SYNTAX       CucsFabricCIoEpIfType
    MAX-ACCESS   read-only
    STATUS       current
    DESCRIPTION
        "Cisco UCS fabric:FcoeSanPc:ifType managed object property"
    ::= { cucsFabricFcoeSanPcEntry 9 }

cucsFabricFcoeSanPcLocale OBJECT-TYPE
    SYNTAX       CucsFabricExternalPcLocale
    MAX-ACCESS   read-only
    STATUS       current
    DESCRIPTION
        "Cisco UCS fabric:FcoeSanPc:locale managed object property"
    ::= { cucsFabricFcoeSanPcEntry 10 }

cucsFabricFcoeSanPcName OBJECT-TYPE
    SYNTAX       SnmpAdminString
    MAX-ACCESS   read-only
    STATUS       current
    DESCRIPTION
        "Cisco UCS fabric:FcoeSanPc:name managed object property"
    ::= { cucsFabricFcoeSanPcEntry 11 }

cucsFabricFcoeSanPcOperState OBJECT-TYPE
    SYNTAX       CucsNetworkPortOperState
    MAX-ACCESS   read-only
    STATUS       current
    DESCRIPTION
        "Cisco UCS fabric:FcoeSanPc:operState managed object property"
    ::= { cucsFabricFcoeSanPcEntry 12 }

cucsFabricFcoeSanPcPeerDn OBJECT-TYPE
    SYNTAX       SnmpAdminString
    MAX-ACCESS   read-only
    STATUS       current
    DESCRIPTION
        "Cisco UCS fabric:FcoeSanPc:peerDn managed object property"
    ::= { cucsFabricFcoeSanPcEntry 14 }

cucsFabricFcoeSanPcPortId OBJECT-TYPE
    SYNTAX       Gauge32
    MAX-ACCESS   read-only
    STATUS       current
    DESCRIPTION
        "Cisco UCS fabric:FcoeSanPc:portId managed object property"
    ::= { cucsFabricFcoeSanPcEntry 15 }

cucsFabricFcoeSanPcStateQual OBJECT-TYPE
    SYNTAX       SnmpAdminString
    MAX-ACCESS   read-only
    STATUS       current
    DESCRIPTION
        "Cisco UCS fabric:FcoeSanPc:stateQual managed object property"
    ::= { cucsFabricFcoeSanPcEntry 16 }

cucsFabricFcoeSanPcSwitchId OBJECT-TYPE
    SYNTAX       CucsNetworkSwitchId
    MAX-ACCESS   read-only
    STATUS       current
    DESCRIPTION
        "Cisco UCS fabric:FcoeSanPc:switchId managed object property"
    ::= { cucsFabricFcoeSanPcEntry 17 }

cucsFabricFcoeSanPcTransport OBJECT-TYPE
    SYNTAX       CucsFabricFcoeSanPcTransport
    MAX-ACCESS   read-only
    STATUS       current
    DESCRIPTION
        "Cisco UCS fabric:FcoeSanPc:transport managed object property"
    ::= { cucsFabricFcoeSanPcEntry 18 }

cucsFabricFcoeSanPcType OBJECT-TYPE
    SYNTAX       CucsFabricSanPcType
    MAX-ACCESS   read-only
    STATUS       current
    DESCRIPTION
        "Cisco UCS fabric:FcoeSanPc:type managed object property"
    ::= { cucsFabricFcoeSanPcEntry 19 }

cucsFabricFcoeSanPcWarnings OBJECT-TYPE
    SYNTAX       CucsFabricWarnings
    MAX-ACCESS   read-only
    STATUS       current
    DESCRIPTION
        "Cisco UCS fabric:FcoeSanPc:warnings managed object property"
    ::= { cucsFabricFcoeSanPcEntry 20 }

cucsFabricFcoeSanPcFcoeState OBJECT-TYPE
    SYNTAX       CucsNetworkPortOperState
    MAX-ACCESS   read-only
    STATUS       current
    DESCRIPTION
        "Cisco UCS fabric:FcoeSanPc:fcoeState managed object property"
    ::= { cucsFabricFcoeSanPcEntry 21 }

cucsFabricFcoeSanPcFcoeStateReason OBJECT-TYPE
    SYNTAX       SnmpAdminString
    MAX-ACCESS   read-only
    STATUS       current
    DESCRIPTION
        "Cisco UCS fabric:FcoeSanPc:fcoeStateReason managed
        object property"
    ::= { cucsFabricFcoeSanPcEntry 22 }

cucsFabricFcoeSanPcDescr OBJECT-TYPE
    SYNTAX       SnmpAdminString
    MAX-ACCESS   read-only
    STATUS       current
    DESCRIPTION
        "Cisco UCS fabric:FcoeSanPc:descr managed object property"
    ::= { cucsFabricFcoeSanPcEntry 23 }

cucsFabricFcoeSanPcLacpPolicyName OBJECT-TYPE
    SYNTAX       SnmpAdminString
    MAX-ACCESS   read-only
    STATUS       current
    DESCRIPTION
        "Cisco UCS fabric:FcoeSanPc:lacpPolicyName managed
        object property"
    ::= { cucsFabricFcoeSanPcEntry 24 }

cucsFabricFcoeSanPcOperLacpPolicyName OBJECT-TYPE
    SYNTAX       SnmpAdminString
    MAX-ACCESS   read-only
    STATUS       current
    DESCRIPTION
        "Cisco UCS fabric:FcoeSanPc:operLacpPolicyName
        managed object property"
    ::= { cucsFabricFcoeSanPcEntry 25 }

cucsFabricFcoeSanPcSpeed OBJECT-TYPE
    SYNTAX       CucsPortEthAdminSpeed
    MAX-ACCESS   read-only
    STATUS       current
    DESCRIPTION
        "Cisco UCS fabric:FcoeSanPc:speed managed object property"
    ::= { cucsFabricFcoeSanPcEntry 26 }

cucsFabricFcoeSanPcEpTable OBJECT-TYPE
    SYNTAX           SEQUENCE OF CucsFabricFcoeSanPcEpEntry
    MAX-ACCESS       not-accessible
    STATUS           current
    DESCRIPTION
        "Cisco UCS fabric:FcoeSanPcEp managed object table"
    ::= { cucsFabricObjects 80 }

cucsFabricFcoeSanPcEpEntry OBJECT-TYPE
    SYNTAX           CucsFabricFcoeSanPcEpEntry
    MAX-ACCESS       not-accessible
    STATUS           current
    DESCRIPTION
        "Entry for the cucsFabricFcoeSanPcEpTable table."
    INDEX { cucsFabricFcoeSanPcEpInstanceId }
    ::= { cucsFabricFcoeSanPcEpTable 1 }

CucsFabricFcoeSanPcEpEntry ::= SEQUENCE {
    cucsFabricFcoeSanPcEpInstanceId                                  CucsManagedObjectId,
    cucsFabricFcoeSanPcEpDnData                                      CucsManagedObjectDn,
    cucsFabricFcoeSanPcEpRn                                          SnmpAdminString,
    cucsFabricFcoeSanPcEpAdminState                                  CucsFabricExternalEpAdminState,
    cucsFabricFcoeSanPcEpChassisId                                   Gauge32,
    cucsFabricFcoeSanPcEpEpDn                                        SnmpAdminString,
    cucsFabricFcoeSanPcEpFltAggr                                     Unsigned64,
    cucsFabricFcoeSanPcEpIfRole                                      CucsFabricSanEpIfRole,
    cucsFabricFcoeSanPcEpIfType                                      CucsFabricPIoEpIfType,
    cucsFabricFcoeSanPcEpLicGP                                       Unsigned64,
    cucsFabricFcoeSanPcEpLicState                                    CucsLicenseState,
    cucsFabricFcoeSanPcEpLocale                                      CucsFabricExternalEpLocale,
    cucsFabricFcoeSanPcEpMembership                                  CucsFabricMembershipStatus,
    cucsFabricFcoeSanPcEpName                                        SnmpAdminString,
    cucsFabricFcoeSanPcEpOperState                                   CucsFabricPIoEpOperState,
    cucsFabricFcoeSanPcEpOperStateReason                             SnmpAdminString,
    cucsFabricFcoeSanPcEpPeerChassisId                               Gauge32,
    cucsFabricFcoeSanPcEpPeerDn                                      SnmpAdminString,
    cucsFabricFcoeSanPcEpPeerPortId                                  Gauge32,
    cucsFabricFcoeSanPcEpPeerSlotId                                  Gauge32,
    cucsFabricFcoeSanPcEpPortId                                      CucsFabricFcoeSanPcEpPortId,
    cucsFabricFcoeSanPcEpSlotId                                      CucsFabricFcoeSanPcEpSlotId,
    cucsFabricFcoeSanPcEpSwitchId                                    CucsNetworkSwitchId,
    cucsFabricFcoeSanPcEpTransport                                   CucsFabricAFcoeSanEpTransport,
    cucsFabricFcoeSanPcEpType                                        CucsFabricSanEpType,
    cucsFabricFcoeSanPcEpWarnings                                    CucsFabricWarnings,
    cucsFabricFcoeSanPcEpEthLinkProfileName                          SnmpAdminString,
    cucsFabricFcoeSanPcEpOperEthLinkProfileName                      SnmpAdminString,
    cucsFabricFcoeSanPcEpUdldOperState                               CucsFabricUdldOperState,
    cucsFabricFcoeSanPcEpAggrPortId                                  Gauge32,
    cucsFabricFcoeSanPcEpPeerAggrPortId                              Gauge32,
    cucsFabricFcoeSanPcEpAutoNegotiate                               TruthValue
}

cucsFabricFcoeSanPcEpInstanceId OBJECT-TYPE
    SYNTAX       CucsManagedObjectId
    MAX-ACCESS   not-accessible
    STATUS       current
    DESCRIPTION
        "Instance identifier of the managed object."
    ::= { cucsFabricFcoeSanPcEpEntry 1 }

cucsFabricFcoeSanPcEpDnData OBJECT-TYPE
    SYNTAX       CucsManagedObjectDn
    MAX-ACCESS   read-only
    STATUS       current
    DESCRIPTION
        "Cisco UCS fabric:FcoeSanPcEp:dn managed object property"
    ::= { cucsFabricFcoeSanPcEpEntry 2 }

cucsFabricFcoeSanPcEpRn OBJECT-TYPE
    SYNTAX       SnmpAdminString
    MAX-ACCESS   read-only
    STATUS       current
    DESCRIPTION
        "Cisco UCS fabric:FcoeSanPcEp:rn managed object property"
    ::= { cucsFabricFcoeSanPcEpEntry 3 }

cucsFabricFcoeSanPcEpAdminState OBJECT-TYPE
    SYNTAX       CucsFabricExternalEpAdminState
    MAX-ACCESS   read-only
    STATUS       current
    DESCRIPTION
        "Cisco UCS fabric:FcoeSanPcEp:adminState managed object property"
    ::= { cucsFabricFcoeSanPcEpEntry 4 }

cucsFabricFcoeSanPcEpChassisId OBJECT-TYPE
    SYNTAX       Gauge32
    MAX-ACCESS   read-only
    STATUS       current
    DESCRIPTION
        "Cisco UCS fabric:FcoeSanPcEp:chassisId managed object property"
    ::= { cucsFabricFcoeSanPcEpEntry 5 }

cucsFabricFcoeSanPcEpEpDn OBJECT-TYPE
    SYNTAX       SnmpAdminString
    MAX-ACCESS   read-only
    STATUS       current
    DESCRIPTION
        "Cisco UCS fabric:FcoeSanPcEp:epDn managed object property"
    ::= { cucsFabricFcoeSanPcEpEntry 6 }

cucsFabricFcoeSanPcEpFltAggr OBJECT-TYPE
    SYNTAX       Unsigned64
    MAX-ACCESS   read-only
    STATUS       current
    DESCRIPTION
        "Cisco UCS fabric:FcoeSanPcEp:fltAggr managed object property"
    ::= { cucsFabricFcoeSanPcEpEntry 7 }

cucsFabricFcoeSanPcEpIfRole OBJECT-TYPE
    SYNTAX       CucsFabricSanEpIfRole
    MAX-ACCESS   read-only
    STATUS       current
    DESCRIPTION
        "Cisco UCS fabric:FcoeSanPcEp:ifRole managed object property"
    ::= { cucsFabricFcoeSanPcEpEntry 8 }

cucsFabricFcoeSanPcEpIfType OBJECT-TYPE
    SYNTAX       CucsFabricPIoEpIfType
    MAX-ACCESS   read-only
    STATUS       current
    DESCRIPTION
        "Cisco UCS fabric:FcoeSanPcEp:ifType managed object property"
    ::= { cucsFabricFcoeSanPcEpEntry 9 }

cucsFabricFcoeSanPcEpLicGP OBJECT-TYPE
    SYNTAX       Unsigned64
    MAX-ACCESS   read-only
    STATUS       current
    DESCRIPTION
        "Cisco UCS fabric:FcoeSanPcEp:licGP managed object property"
    ::= { cucsFabricFcoeSanPcEpEntry 10 }

cucsFabricFcoeSanPcEpLicState OBJECT-TYPE
    SYNTAX       CucsLicenseState
    MAX-ACCESS   read-only
    STATUS       current
    DESCRIPTION
        "Cisco UCS fabric:FcoeSanPcEp:licState managed object property"
    ::= { cucsFabricFcoeSanPcEpEntry 11 }

cucsFabricFcoeSanPcEpLocale OBJECT-TYPE
    SYNTAX       CucsFabricExternalEpLocale
    MAX-ACCESS   read-only
    STATUS       current
    DESCRIPTION
        "Cisco UCS fabric:FcoeSanPcEp:locale managed object property"
    ::= { cucsFabricFcoeSanPcEpEntry 12 }

cucsFabricFcoeSanPcEpMembership OBJECT-TYPE
    SYNTAX       CucsFabricMembershipStatus
    MAX-ACCESS   read-only
    STATUS       current
    DESCRIPTION
        "Cisco UCS fabric:FcoeSanPcEp:membership managed object property"
    ::= { cucsFabricFcoeSanPcEpEntry 13 }

cucsFabricFcoeSanPcEpName OBJECT-TYPE
    SYNTAX       SnmpAdminString
    MAX-ACCESS   read-only
    STATUS       current
    DESCRIPTION
        "Cisco UCS fabric:FcoeSanPcEp:name managed object property"
    ::= { cucsFabricFcoeSanPcEpEntry 14 }

cucsFabricFcoeSanPcEpOperState OBJECT-TYPE
    SYNTAX       CucsFabricPIoEpOperState
    MAX-ACCESS   read-only
    STATUS       current
    DESCRIPTION
        "Cisco UCS fabric:FcoeSanPcEp:operState managed object property"
    ::= { cucsFabricFcoeSanPcEpEntry 15 }

cucsFabricFcoeSanPcEpOperStateReason OBJECT-TYPE
    SYNTAX       SnmpAdminString
    MAX-ACCESS   read-only
    STATUS       current
    DESCRIPTION
        "Cisco UCS fabric:FcoeSanPcEp:operStateReason managed
        object property"
    ::= { cucsFabricFcoeSanPcEpEntry 16 }

cucsFabricFcoeSanPcEpPeerChassisId OBJECT-TYPE
    SYNTAX       Gauge32
    MAX-ACCESS   read-only
    STATUS       current
    DESCRIPTION
        "Cisco UCS fabric:FcoeSanPcEp:peerChassisId managed
        object property"
    ::= { cucsFabricFcoeSanPcEpEntry 17 }

cucsFabricFcoeSanPcEpPeerDn OBJECT-TYPE
    SYNTAX       SnmpAdminString
    MAX-ACCESS   read-only
    STATUS       current
    DESCRIPTION
        "Cisco UCS fabric:FcoeSanPcEp:peerDn managed object property"
    ::= { cucsFabricFcoeSanPcEpEntry 18 }

cucsFabricFcoeSanPcEpPeerPortId OBJECT-TYPE
    SYNTAX       Gauge32
    MAX-ACCESS   read-only
    STATUS       current
    DESCRIPTION
        "Cisco UCS fabric:FcoeSanPcEp:peerPortId managed object property"
    ::= { cucsFabricFcoeSanPcEpEntry 19 }

cucsFabricFcoeSanPcEpPeerSlotId OBJECT-TYPE
    SYNTAX       Gauge32
    MAX-ACCESS   read-only
    STATUS       current
    DESCRIPTION
        "Cisco UCS fabric:FcoeSanPcEp:peerSlotId managed object property"
    ::= { cucsFabricFcoeSanPcEpEntry 20 }

cucsFabricFcoeSanPcEpPortId OBJECT-TYPE
    SYNTAX       CucsFabricFcoeSanPcEpPortId
    MAX-ACCESS   read-only
    STATUS       current
    DESCRIPTION
        "Cisco UCS fabric:FcoeSanPcEp:portId managed object property"
    ::= { cucsFabricFcoeSanPcEpEntry 21 }

cucsFabricFcoeSanPcEpSlotId OBJECT-TYPE
    SYNTAX       CucsFabricFcoeSanPcEpSlotId
    MAX-ACCESS   read-only
    STATUS       current
    DESCRIPTION
        "Cisco UCS fabric:FcoeSanPcEp:slotId managed object property"
    ::= { cucsFabricFcoeSanPcEpEntry 22 }

cucsFabricFcoeSanPcEpSwitchId OBJECT-TYPE
    SYNTAX       CucsNetworkSwitchId
    MAX-ACCESS   read-only
    STATUS       current
    DESCRIPTION
        "Cisco UCS fabric:FcoeSanPcEp:switchId managed object property"
    ::= { cucsFabricFcoeSanPcEpEntry 23 }

cucsFabricFcoeSanPcEpTransport OBJECT-TYPE
    SYNTAX       CucsFabricAFcoeSanEpTransport
    MAX-ACCESS   read-only
    STATUS       current
    DESCRIPTION
        "Cisco UCS fabric:FcoeSanPcEp:transport managed object property"
    ::= { cucsFabricFcoeSanPcEpEntry 24 }

cucsFabricFcoeSanPcEpType OBJECT-TYPE
    SYNTAX       CucsFabricSanEpType
    MAX-ACCESS   read-only
    STATUS       current
    DESCRIPTION
        "Cisco UCS fabric:FcoeSanPcEp:type managed object property"
    ::= { cucsFabricFcoeSanPcEpEntry 25 }

cucsFabricFcoeSanPcEpWarnings OBJECT-TYPE
    SYNTAX       CucsFabricWarnings
    MAX-ACCESS   read-only
    STATUS       current
    DESCRIPTION
        "Cisco UCS fabric:FcoeSanPcEp:warnings managed object property"
    ::= { cucsFabricFcoeSanPcEpEntry 26 }

cucsFabricFcoeSanPcEpEthLinkProfileName OBJECT-TYPE
    SYNTAX       SnmpAdminString
    MAX-ACCESS   read-only
    STATUS       current
    DESCRIPTION
        "Cisco UCS fabric:FcoeSanPcEp:ethLinkProfileName
        managed object property"
    ::= { cucsFabricFcoeSanPcEpEntry 27 }

cucsFabricFcoeSanPcEpOperEthLinkProfileName OBJECT-TYPE
    SYNTAX       SnmpAdminString
    MAX-ACCESS   read-only
    STATUS       current
    DESCRIPTION
        "Cisco UCS fabric:FcoeSanPcEp:operEthLinkProfileName
        managed object property"
    ::= { cucsFabricFcoeSanPcEpEntry 28 }

cucsFabricFcoeSanPcEpUdldOperState OBJECT-TYPE
    SYNTAX       CucsFabricUdldOperState
    MAX-ACCESS   read-only
    STATUS       current
    DESCRIPTION
        "Cisco UCS fabric:FcoeSanPcEp:udldOperState managed
        object property"
    ::= { cucsFabricFcoeSanPcEpEntry 29 }

cucsFabricFcoeSanPcEpAggrPortId OBJECT-TYPE
    SYNTAX       Gauge32
    MAX-ACCESS   read-only
    STATUS       current
    DESCRIPTION
        "Cisco UCS fabric:FcoeSanPcEp:aggrPortId managed object property"
    ::= { cucsFabricFcoeSanPcEpEntry 30 }

cucsFabricFcoeSanPcEpPeerAggrPortId OBJECT-TYPE
    SYNTAX       Gauge32
    MAX-ACCESS   read-only
    STATUS       current
    DESCRIPTION
        "Cisco UCS fabric:FcoeSanPcEp:peerAggrPortId managed
        object property"
    ::= { cucsFabricFcoeSanPcEpEntry 31 }

cucsFabricFcoeSanPcEpAutoNegotiate OBJECT-TYPE
    SYNTAX       TruthValue
    MAX-ACCESS   read-only
    STATUS       current
    DESCRIPTION
        "Cisco UCS fabric:FcoeSanPcEp:autoNegotiate managed
        object property"
    ::= { cucsFabricFcoeSanPcEpEntry 32 }

cucsFabricFcoeVsanPcTable OBJECT-TYPE
    SYNTAX           SEQUENCE OF CucsFabricFcoeVsanPcEntry
    MAX-ACCESS       not-accessible
    STATUS           current
    DESCRIPTION
        "Cisco UCS fabric:FcoeVsanPc managed object table"
    ::= { cucsFabricObjects 81 }

cucsFabricFcoeVsanPcEntry OBJECT-TYPE
    SYNTAX           CucsFabricFcoeVsanPcEntry
    MAX-ACCESS       not-accessible
    STATUS           current
    DESCRIPTION
        "Entry for the cucsFabricFcoeVsanPcTable table."
    INDEX { cucsFabricFcoeVsanPcInstanceId }
    ::= { cucsFabricFcoeVsanPcTable 1 }

CucsFabricFcoeVsanPcEntry ::= SEQUENCE {
    cucsFabricFcoeVsanPcInstanceId                                   CucsManagedObjectId,
    cucsFabricFcoeVsanPcDn                                           CucsManagedObjectDn,
    cucsFabricFcoeVsanPcRn                                           SnmpAdminString,
    cucsFabricFcoeVsanPcAdminState                                   CucsFabricCIoEpAdminState,
    cucsFabricFcoeVsanPcEpDn                                         SnmpAdminString,
    cucsFabricFcoeVsanPcFltAggr                                      Unsigned64,
    cucsFabricFcoeVsanPcIfRole                                       CucsFabricSanPcIfRole,
    cucsFabricFcoeVsanPcIfType                                       CucsFabricCIoEpIfType,
    cucsFabricFcoeVsanPcLocale                                       CucsFabricExternalPcLocale,
    cucsFabricFcoeVsanPcName                                         SnmpAdminString,
    cucsFabricFcoeVsanPcOperState                                    CucsNetworkPortOperState,
    cucsFabricFcoeVsanPcPeerDn                                       SnmpAdminString,
    cucsFabricFcoeVsanPcPortId                                       Gauge32,
    cucsFabricFcoeVsanPcStateQual                                    SnmpAdminString,
    cucsFabricFcoeVsanPcSwitchId                                     CucsNetworkSwitchId,
    cucsFabricFcoeVsanPcTransport                                    CucsFabricFcoeVsanPcTransport,
    cucsFabricFcoeVsanPcType                                         CucsFabricSanPcType,
    cucsFabricFcoeVsanPcWarnings                                     CucsFabricWarnings,
    cucsFabricFcoeVsanPcDescr                                        SnmpAdminString
}

cucsFabricFcoeVsanPcInstanceId OBJECT-TYPE
    SYNTAX       CucsManagedObjectId
    MAX-ACCESS   not-accessible
    STATUS       current
    DESCRIPTION
        "Instance identifier of the managed object."
    ::= { cucsFabricFcoeVsanPcEntry 1 }

cucsFabricFcoeVsanPcDn OBJECT-TYPE
    SYNTAX       CucsManagedObjectDn
    MAX-ACCESS   read-only
    STATUS       current
    DESCRIPTION
        "Cisco UCS fabric:FcoeVsanPc:dn managed object property"
    ::= { cucsFabricFcoeVsanPcEntry 2 }

cucsFabricFcoeVsanPcRn OBJECT-TYPE
    SYNTAX       SnmpAdminString
    MAX-ACCESS   read-only
    STATUS       current
    DESCRIPTION
        "Cisco UCS fabric:FcoeVsanPc:rn managed object property"
    ::= { cucsFabricFcoeVsanPcEntry 3 }

cucsFabricFcoeVsanPcAdminState OBJECT-TYPE
    SYNTAX       CucsFabricCIoEpAdminState
    MAX-ACCESS   read-only
    STATUS       current
    DESCRIPTION
        "Cisco UCS fabric:FcoeVsanPc:adminState managed object property"
    ::= { cucsFabricFcoeVsanPcEntry 4 }

cucsFabricFcoeVsanPcEpDn OBJECT-TYPE
    SYNTAX       SnmpAdminString
    MAX-ACCESS   read-only
    STATUS       current
    DESCRIPTION
        "Cisco UCS fabric:FcoeVsanPc:epDn managed object property"
    ::= { cucsFabricFcoeVsanPcEntry 5 }

cucsFabricFcoeVsanPcFltAggr OBJECT-TYPE
    SYNTAX       Unsigned64
    MAX-ACCESS   read-only
    STATUS       current
    DESCRIPTION
        "Cisco UCS fabric:FcoeVsanPc:fltAggr managed object property"
    ::= { cucsFabricFcoeVsanPcEntry 6 }

cucsFabricFcoeVsanPcIfRole OBJECT-TYPE
    SYNTAX       CucsFabricSanPcIfRole
    MAX-ACCESS   read-only
    STATUS       current
    DESCRIPTION
        "Cisco UCS fabric:FcoeVsanPc:ifRole managed object property"
    ::= { cucsFabricFcoeVsanPcEntry 7 }

cucsFabricFcoeVsanPcIfType OBJECT-TYPE
    SYNTAX       CucsFabricCIoEpIfType
    MAX-ACCESS   read-only
    STATUS       current
    DESCRIPTION
        "Cisco UCS fabric:FcoeVsanPc:ifType managed object property"
    ::= { cucsFabricFcoeVsanPcEntry 8 }

cucsFabricFcoeVsanPcLocale OBJECT-TYPE
    SYNTAX       CucsFabricExternalPcLocale
    MAX-ACCESS   read-only
    STATUS       current
    DESCRIPTION
        "Cisco UCS fabric:FcoeVsanPc:locale managed object property"
    ::= { cucsFabricFcoeVsanPcEntry 9 }

cucsFabricFcoeVsanPcName OBJECT-TYPE
    SYNTAX       SnmpAdminString
    MAX-ACCESS   read-only
    STATUS       current
    DESCRIPTION
        "Cisco UCS fabric:FcoeVsanPc:name managed object property"
    ::= { cucsFabricFcoeVsanPcEntry 10 }

cucsFabricFcoeVsanPcOperState OBJECT-TYPE
    SYNTAX       CucsNetworkPortOperState
    MAX-ACCESS   read-only
    STATUS       current
    DESCRIPTION
        "Cisco UCS fabric:FcoeVsanPc:operState managed object property"
    ::= { cucsFabricFcoeVsanPcEntry 11 }

cucsFabricFcoeVsanPcPeerDn OBJECT-TYPE
    SYNTAX       SnmpAdminString
    MAX-ACCESS   read-only
    STATUS       current
    DESCRIPTION
        "Cisco UCS fabric:FcoeVsanPc:peerDn managed object property"
    ::= { cucsFabricFcoeVsanPcEntry 12 }

cucsFabricFcoeVsanPcPortId OBJECT-TYPE
    SYNTAX       Gauge32
    MAX-ACCESS   read-only
    STATUS       current
    DESCRIPTION
        "Cisco UCS fabric:FcoeVsanPc:portId managed object property"
    ::= { cucsFabricFcoeVsanPcEntry 13 }

cucsFabricFcoeVsanPcStateQual OBJECT-TYPE
    SYNTAX       SnmpAdminString
    MAX-ACCESS   read-only
    STATUS       current
    DESCRIPTION
        "Cisco UCS fabric:FcoeVsanPc:stateQual managed object property"
    ::= { cucsFabricFcoeVsanPcEntry 14 }

cucsFabricFcoeVsanPcSwitchId OBJECT-TYPE
    SYNTAX       CucsNetworkSwitchId
    MAX-ACCESS   read-only
    STATUS       current
    DESCRIPTION
        "Cisco UCS fabric:FcoeVsanPc:switchId managed object property"
    ::= { cucsFabricFcoeVsanPcEntry 15 }

cucsFabricFcoeVsanPcTransport OBJECT-TYPE
    SYNTAX       CucsFabricFcoeVsanPcTransport
    MAX-ACCESS   read-only
    STATUS       current
    DESCRIPTION
        "Cisco UCS fabric:FcoeVsanPc:transport managed object property"
    ::= { cucsFabricFcoeVsanPcEntry 16 }

cucsFabricFcoeVsanPcType OBJECT-TYPE
    SYNTAX       CucsFabricSanPcType
    MAX-ACCESS   read-only
    STATUS       current
    DESCRIPTION
        "Cisco UCS fabric:FcoeVsanPc:type managed object property"
    ::= { cucsFabricFcoeVsanPcEntry 17 }

cucsFabricFcoeVsanPcWarnings OBJECT-TYPE
    SYNTAX       CucsFabricWarnings
    MAX-ACCESS   read-only
    STATUS       current
    DESCRIPTION
        "Cisco UCS fabric:FcoeVsanPc:warnings managed object property"
    ::= { cucsFabricFcoeVsanPcEntry 18 }

cucsFabricFcoeVsanPcDescr OBJECT-TYPE
    SYNTAX       SnmpAdminString
    MAX-ACCESS   read-only
    STATUS       current
    DESCRIPTION
        "Cisco UCS fabric:FcoeVsanPc:descr managed object property"
    ::= { cucsFabricFcoeVsanPcEntry 19 }

cucsFabricFcoeVsanPortEpTable OBJECT-TYPE
    SYNTAX           SEQUENCE OF CucsFabricFcoeVsanPortEpEntry
    MAX-ACCESS       not-accessible
    STATUS           current
    DESCRIPTION
        "Cisco UCS fabric:FcoeVsanPortEp managed object table"
    ::= { cucsFabricObjects 64 }

cucsFabricFcoeVsanPortEpEntry OBJECT-TYPE
    SYNTAX           CucsFabricFcoeVsanPortEpEntry
    MAX-ACCESS       not-accessible
    STATUS           current
    DESCRIPTION
        "Entry for the cucsFabricFcoeVsanPortEpTable table."
    INDEX { cucsFabricFcoeVsanPortEpInstanceId }
    ::= { cucsFabricFcoeVsanPortEpTable 1 }

CucsFabricFcoeVsanPortEpEntry ::= SEQUENCE {
    cucsFabricFcoeVsanPortEpInstanceId                               CucsManagedObjectId,
    cucsFabricFcoeVsanPortEpDn                                       CucsManagedObjectDn,
    cucsFabricFcoeVsanPortEpRn                                       SnmpAdminString,
    cucsFabricFcoeVsanPortEpAdminState                               CucsFabricExternalEpAdminState,
    cucsFabricFcoeVsanPortEpChassisId                                Gauge32,
    cucsFabricFcoeVsanPortEpEpDn                                     SnmpAdminString,
    cucsFabricFcoeVsanPortEpIfRole                                   CucsFabricSanEpIfRole,
    cucsFabricFcoeVsanPortEpIfType                                   CucsFabricPIoEpIfType,
    cucsFabricFcoeVsanPortEpLicGP                                    Unsigned64,
    cucsFabricFcoeVsanPortEpLicState                                 CucsLicenseState,
    cucsFabricFcoeVsanPortEpLocale                                   CucsFabricExternalEpLocale,
    cucsFabricFcoeVsanPortEpName                                     SnmpAdminString,
    cucsFabricFcoeVsanPortEpPeerChassisId                            Gauge32,
    cucsFabricFcoeVsanPortEpPeerDn                                   SnmpAdminString,
    cucsFabricFcoeVsanPortEpPeerPortId                               Gauge32,
    cucsFabricFcoeVsanPortEpPeerSlotId                               Gauge32,
    cucsFabricFcoeVsanPortEpPortId                                   CucsFabricFcoeVsanPortEpPortId,
    cucsFabricFcoeVsanPortEpSlotId                                   CucsFabricFcoeVsanPortEpSlotId,
    cucsFabricFcoeVsanPortEpSwitchId                                 CucsNetworkSwitchId,
    cucsFabricFcoeVsanPortEpTransport                                CucsFabricAFcSanEpTransport,
    cucsFabricFcoeVsanPortEpType                                     CucsFabricSanEpType,
    cucsFabricFcoeVsanPortEpFltAggr                                  Unsigned64,
    cucsFabricFcoeVsanPortEpOperState                                CucsFabricPIoEpOperState,
    cucsFabricFcoeVsanPortEpOperStateReason                          SnmpAdminString,
    cucsFabricFcoeVsanPortEpWarnings                                 CucsFabricWarnings,
    cucsFabricFcoeVsanPortEpAggrPortId                               Gauge32,
    cucsFabricFcoeVsanPortEpPeerAggrPortId                           Gauge32,
    cucsFabricFcoeVsanPortEpAutoNegotiate                            TruthValue
}

cucsFabricFcoeVsanPortEpInstanceId OBJECT-TYPE
    SYNTAX       CucsManagedObjectId
    MAX-ACCESS   not-accessible
    STATUS       current
    DESCRIPTION
        "Instance identifier of the managed object."
    ::= { cucsFabricFcoeVsanPortEpEntry 1 }

cucsFabricFcoeVsanPortEpDn OBJECT-TYPE
    SYNTAX       CucsManagedObjectDn
    MAX-ACCESS   read-only
    STATUS       current
    DESCRIPTION
        "Cisco UCS fabric:FcoeVsanPortEp:dn managed object property"
    ::= { cucsFabricFcoeVsanPortEpEntry 2 }

cucsFabricFcoeVsanPortEpRn OBJECT-TYPE
    SYNTAX       SnmpAdminString
    MAX-ACCESS   read-only
    STATUS       current
    DESCRIPTION
        "Cisco UCS fabric:FcoeVsanPortEp:rn managed object property"
    ::= { cucsFabricFcoeVsanPortEpEntry 3 }

cucsFabricFcoeVsanPortEpAdminState OBJECT-TYPE
    SYNTAX       CucsFabricExternalEpAdminState
    MAX-ACCESS   read-only
    STATUS       current
    DESCRIPTION
        "Cisco UCS fabric:FcoeVsanPortEp:adminState managed
        object property"
    ::= { cucsFabricFcoeVsanPortEpEntry 4 }

cucsFabricFcoeVsanPortEpChassisId OBJECT-TYPE
    SYNTAX       Gauge32
    MAX-ACCESS   read-only
    STATUS       current
    DESCRIPTION
        "Cisco UCS fabric:FcoeVsanPortEp:chassisId managed
        object property"
    ::= { cucsFabricFcoeVsanPortEpEntry 5 }

cucsFabricFcoeVsanPortEpEpDn OBJECT-TYPE
    SYNTAX       SnmpAdminString
    MAX-ACCESS   read-only
    STATUS       current
    DESCRIPTION
        "Cisco UCS fabric:FcoeVsanPortEp:epDn managed object property"
    ::= { cucsFabricFcoeVsanPortEpEntry 6 }

cucsFabricFcoeVsanPortEpIfRole OBJECT-TYPE
    SYNTAX       CucsFabricSanEpIfRole
    MAX-ACCESS   read-only
    STATUS       current
    DESCRIPTION
        "Cisco UCS fabric:FcoeVsanPortEp:ifRole managed object property"
    ::= { cucsFabricFcoeVsanPortEpEntry 7 }

cucsFabricFcoeVsanPortEpIfType OBJECT-TYPE
    SYNTAX       CucsFabricPIoEpIfType
    MAX-ACCESS   read-only
    STATUS       current
    DESCRIPTION
        "Cisco UCS fabric:FcoeVsanPortEp:ifType managed object property"
    ::= { cucsFabricFcoeVsanPortEpEntry 8 }

cucsFabricFcoeVsanPortEpLicGP OBJECT-TYPE
    SYNTAX       Unsigned64
    MAX-ACCESS   read-only
    STATUS       current
    DESCRIPTION
        "Cisco UCS fabric:FcoeVsanPortEp:licGP managed object property"
    ::= { cucsFabricFcoeVsanPortEpEntry 9 }

cucsFabricFcoeVsanPortEpLicState OBJECT-TYPE
    SYNTAX       CucsLicenseState
    MAX-ACCESS   read-only
    STATUS       current
    DESCRIPTION
        "Cisco UCS fabric:FcoeVsanPortEp:licState managed object property"
    ::= { cucsFabricFcoeVsanPortEpEntry 10 }

cucsFabricFcoeVsanPortEpLocale OBJECT-TYPE
    SYNTAX       CucsFabricExternalEpLocale
    MAX-ACCESS   read-only
    STATUS       current
    DESCRIPTION
        "Cisco UCS fabric:FcoeVsanPortEp:locale managed object property"
    ::= { cucsFabricFcoeVsanPortEpEntry 11 }

cucsFabricFcoeVsanPortEpName OBJECT-TYPE
    SYNTAX       SnmpAdminString
    MAX-ACCESS   read-only
    STATUS       current
    DESCRIPTION
        "Cisco UCS fabric:FcoeVsanPortEp:name managed object property"
    ::= { cucsFabricFcoeVsanPortEpEntry 12 }

cucsFabricFcoeVsanPortEpPeerChassisId OBJECT-TYPE
    SYNTAX       Gauge32
    MAX-ACCESS   read-only
    STATUS       current
    DESCRIPTION
        "Cisco UCS fabric:FcoeVsanPortEp:peerChassisId
        managed object property"
    ::= { cucsFabricFcoeVsanPortEpEntry 13 }

cucsFabricFcoeVsanPortEpPeerDn OBJECT-TYPE
    SYNTAX       SnmpAdminString
    MAX-ACCESS   read-only
    STATUS       current
    DESCRIPTION
        "Cisco UCS fabric:FcoeVsanPortEp:peerDn managed object property"
    ::= { cucsFabricFcoeVsanPortEpEntry 14 }

cucsFabricFcoeVsanPortEpPeerPortId OBJECT-TYPE
    SYNTAX       Gauge32
    MAX-ACCESS   read-only
    STATUS       current
    DESCRIPTION
        "Cisco UCS fabric:FcoeVsanPortEp:peerPortId managed
        object property"
    ::= { cucsFabricFcoeVsanPortEpEntry 15 }

cucsFabricFcoeVsanPortEpPeerSlotId OBJECT-TYPE
    SYNTAX       Gauge32
    MAX-ACCESS   read-only
    STATUS       current
    DESCRIPTION
        "Cisco UCS fabric:FcoeVsanPortEp:peerSlotId managed
        object property"
    ::= { cucsFabricFcoeVsanPortEpEntry 16 }

cucsFabricFcoeVsanPortEpPortId OBJECT-TYPE
    SYNTAX       CucsFabricFcoeVsanPortEpPortId
    MAX-ACCESS   read-only
    STATUS       current
    DESCRIPTION
        "Cisco UCS fabric:FcoeVsanPortEp:portId managed object property"
    ::= { cucsFabricFcoeVsanPortEpEntry 17 }

cucsFabricFcoeVsanPortEpSlotId OBJECT-TYPE
    SYNTAX       CucsFabricFcoeVsanPortEpSlotId
    MAX-ACCESS   read-only
    STATUS       current
    DESCRIPTION
        "Cisco UCS fabric:FcoeVsanPortEp:slotId managed object property"
    ::= { cucsFabricFcoeVsanPortEpEntry 18 }

cucsFabricFcoeVsanPortEpSwitchId OBJECT-TYPE
    SYNTAX       CucsNetworkSwitchId
    MAX-ACCESS   read-only
    STATUS       current
    DESCRIPTION
        "Cisco UCS fabric:FcoeVsanPortEp:switchId managed object property"
    ::= { cucsFabricFcoeVsanPortEpEntry 19 }

cucsFabricFcoeVsanPortEpTransport OBJECT-TYPE
    SYNTAX       CucsFabricAFcSanEpTransport
    MAX-ACCESS   read-only
    STATUS       current
    DESCRIPTION
        "Cisco UCS fabric:FcoeVsanPortEp:transport managed
        object property"
    ::= { cucsFabricFcoeVsanPortEpEntry 20 }

cucsFabricFcoeVsanPortEpType OBJECT-TYPE
    SYNTAX       CucsFabricSanEpType
    MAX-ACCESS   read-only
    STATUS       current
    DESCRIPTION
        "Cisco UCS fabric:FcoeVsanPortEp:type managed object property"
    ::= { cucsFabricFcoeVsanPortEpEntry 21 }

cucsFabricFcoeVsanPortEpFltAggr OBJECT-TYPE
    SYNTAX       Unsigned64
    MAX-ACCESS   read-only
    STATUS       current
    DESCRIPTION
        "Cisco UCS fabric:FcoeVsanPortEp:fltAggr managed object property"
    ::= { cucsFabricFcoeVsanPortEpEntry 22 }

cucsFabricFcoeVsanPortEpOperState OBJECT-TYPE
    SYNTAX       CucsFabricPIoEpOperState
    MAX-ACCESS   read-only
    STATUS       current
    DESCRIPTION
        "Cisco UCS fabric:FcoeVsanPortEp:operState managed
        object property"
    ::= { cucsFabricFcoeVsanPortEpEntry 23 }

cucsFabricFcoeVsanPortEpOperStateReason OBJECT-TYPE
    SYNTAX       SnmpAdminString
    MAX-ACCESS   read-only
    STATUS       current
    DESCRIPTION
        "Cisco UCS fabric:FcoeVsanPortEp:operStateReason
        managed object property"
    ::= { cucsFabricFcoeVsanPortEpEntry 24 }

cucsFabricFcoeVsanPortEpWarnings OBJECT-TYPE
    SYNTAX       CucsFabricWarnings
    MAX-ACCESS   read-only
    STATUS       current
    DESCRIPTION
        "Cisco UCS fabric:FcoeVsanPortEp:warnings managed object property"
    ::= { cucsFabricFcoeVsanPortEpEntry 25 }

cucsFabricFcoeVsanPortEpAggrPortId OBJECT-TYPE
    SYNTAX       Gauge32
    MAX-ACCESS   read-only
    STATUS       current
    DESCRIPTION
        "Cisco UCS fabric:FcoeVsanPortEp:aggrPortId managed
        object property"
    ::= { cucsFabricFcoeVsanPortEpEntry 26 }

cucsFabricFcoeVsanPortEpPeerAggrPortId OBJECT-TYPE
    SYNTAX       Gauge32
    MAX-ACCESS   read-only
    STATUS       current
    DESCRIPTION
        "Cisco UCS fabric:FcoeVsanPortEp:peerAggrPortId
        managed object property"
    ::= { cucsFabricFcoeVsanPortEpEntry 27 }

cucsFabricFcoeVsanPortEpAutoNegotiate OBJECT-TYPE
    SYNTAX       TruthValue
    MAX-ACCESS   read-only
    STATUS       current
    DESCRIPTION
        "Cisco UCS fabric:FcoeVsanPortEp:autoNegotiate
        managed object property"
    ::= { cucsFabricFcoeVsanPortEpEntry 28 }

cucsFabricFlowMonDefinitionTable OBJECT-TYPE
    SYNTAX           SEQUENCE OF CucsFabricFlowMonDefinitionEntry
    MAX-ACCESS       not-accessible
    STATUS           current
    DESCRIPTION
        "Cisco UCS fabric:FlowMonDefinition managed object table"
    ::= { cucsFabricObjects 107 }

cucsFabricFlowMonDefinitionEntry OBJECT-TYPE
    SYNTAX           CucsFabricFlowMonDefinitionEntry
    MAX-ACCESS       not-accessible
    STATUS           current
    DESCRIPTION
        "Entry for the cucsFabricFlowMonDefinitionTable table."
    INDEX { cucsFabricFlowMonDefinitionInstanceId }
    ::= { cucsFabricFlowMonDefinitionTable 1 }

CucsFabricFlowMonDefinitionEntry ::= SEQUENCE {
    cucsFabricFlowMonDefinitionInstanceId                            CucsManagedObjectId,
    cucsFabricFlowMonDefinitionDn                                    CucsManagedObjectDn,
    cucsFabricFlowMonDefinitionRn                                    SnmpAdminString,
    cucsFabricFlowMonDefinitionDescr                                 SnmpAdminString,
    cucsFabricFlowMonDefinitionIntId                                 SnmpAdminString,
    cucsFabricFlowMonDefinitionIpv4keys                              CucsFabricFlowMonIpv4Keys,
    cucsFabricFlowMonDefinitionIpv6keys                              CucsFabricFlowMonIpv6Keys,
    cucsFabricFlowMonDefinitionKeyType                               CucsFabricFlowMonKeyType,
    cucsFabricFlowMonDefinitionL2keys                                CucsFabricFlowMonL2Keys,
    cucsFabricFlowMonDefinitionName                                  SnmpAdminString,
    cucsFabricFlowMonDefinitionNonkeys                               CucsFabricFlowMonNonKeys,
    cucsFabricFlowMonDefinitionPolicyLevel                           Gauge32,
    cucsFabricFlowMonDefinitionPolicyOwner                           CucsPolicyPolicyOwner,
    cucsFabricFlowMonDefinitionRecordType                            CucsFabricFlowMonDefType
}

cucsFabricFlowMonDefinitionInstanceId OBJECT-TYPE
    SYNTAX       CucsManagedObjectId
    MAX-ACCESS   not-accessible
    STATUS       current
    DESCRIPTION
        "Instance identifier of the managed object."
    ::= { cucsFabricFlowMonDefinitionEntry 1 }

cucsFabricFlowMonDefinitionDn OBJECT-TYPE
    SYNTAX       CucsManagedObjectDn
    MAX-ACCESS   read-only
    STATUS       current
    DESCRIPTION
        "Cisco UCS fabric:FlowMonDefinition:dn managed object property"
    ::= { cucsFabricFlowMonDefinitionEntry 2 }

cucsFabricFlowMonDefinitionRn OBJECT-TYPE
    SYNTAX       SnmpAdminString
    MAX-ACCESS   read-only
    STATUS       current
    DESCRIPTION
        "Cisco UCS fabric:FlowMonDefinition:rn managed object property"
    ::= { cucsFabricFlowMonDefinitionEntry 3 }

cucsFabricFlowMonDefinitionDescr OBJECT-TYPE
    SYNTAX       SnmpAdminString
    MAX-ACCESS   read-only
    STATUS       current
    DESCRIPTION
        "Cisco UCS fabric:FlowMonDefinition:descr managed object property"
    ::= { cucsFabricFlowMonDefinitionEntry 4 }

cucsFabricFlowMonDefinitionIntId OBJECT-TYPE
    SYNTAX       SnmpAdminString
    MAX-ACCESS   read-only
    STATUS       current
    DESCRIPTION
        "Cisco UCS fabric:FlowMonDefinition:intId managed object property"
    ::= { cucsFabricFlowMonDefinitionEntry 5 }

cucsFabricFlowMonDefinitionIpv4keys OBJECT-TYPE
    SYNTAX       CucsFabricFlowMonIpv4Keys
    MAX-ACCESS   read-only
    STATUS       current
    DESCRIPTION
        "Cisco UCS fabric:FlowMonDefinition:ipv4keys managed
        object property"
    ::= { cucsFabricFlowMonDefinitionEntry 6 }

cucsFabricFlowMonDefinitionIpv6keys OBJECT-TYPE
    SYNTAX       CucsFabricFlowMonIpv6Keys
    MAX-ACCESS   read-only
    STATUS       current
    DESCRIPTION
        "Cisco UCS fabric:FlowMonDefinition:ipv6keys managed
        object property"
    ::= { cucsFabricFlowMonDefinitionEntry 7 }

cucsFabricFlowMonDefinitionKeyType OBJECT-TYPE
    SYNTAX       CucsFabricFlowMonKeyType
    MAX-ACCESS   read-only
    STATUS       current
    DESCRIPTION
        "Cisco UCS fabric:FlowMonDefinition:keyType managed
        object property"
    ::= { cucsFabricFlowMonDefinitionEntry 8 }

cucsFabricFlowMonDefinitionL2keys OBJECT-TYPE
    SYNTAX       CucsFabricFlowMonL2Keys
    MAX-ACCESS   read-only
    STATUS       current
    DESCRIPTION
        "Cisco UCS fabric:FlowMonDefinition:l2keys managed
        object property"
    ::= { cucsFabricFlowMonDefinitionEntry 9 }

cucsFabricFlowMonDefinitionName OBJECT-TYPE
    SYNTAX       SnmpAdminString
    MAX-ACCESS   read-only
    STATUS       current
    DESCRIPTION
        "Cisco UCS fabric:FlowMonDefinition:name managed object property"
    ::= { cucsFabricFlowMonDefinitionEntry 10 }

cucsFabricFlowMonDefinitionNonkeys OBJECT-TYPE
    SYNTAX       CucsFabricFlowMonNonKeys
    MAX-ACCESS   read-only
    STATUS       current
    DESCRIPTION
        "Cisco UCS fabric:FlowMonDefinition:nonkeys managed
        object property"
    ::= { cucsFabricFlowMonDefinitionEntry 11 }

cucsFabricFlowMonDefinitionPolicyLevel OBJECT-TYPE
    SYNTAX       Gauge32
    MAX-ACCESS   read-only
    STATUS       current
    DESCRIPTION
        "Cisco UCS fabric:FlowMonDefinition:policyLevel
        managed object property"
    ::= { cucsFabricFlowMonDefinitionEntry 12 }

cucsFabricFlowMonDefinitionPolicyOwner OBJECT-TYPE
    SYNTAX       CucsPolicyPolicyOwner
    MAX-ACCESS   read-only
    STATUS       current
    DESCRIPTION
        "Cisco UCS fabric:FlowMonDefinition:policyOwner
        managed object property"
    ::= { cucsFabricFlowMonDefinitionEntry 13 }

cucsFabricFlowMonDefinitionRecordType OBJECT-TYPE
    SYNTAX       CucsFabricFlowMonDefType
    MAX-ACCESS   read-only
    STATUS       current
    DESCRIPTION
        "Cisco UCS fabric:FlowMonDefinition:recordType
        managed object property"
    ::= { cucsFabricFlowMonDefinitionEntry 14 }

cucsFabricFlowMonExporterProfileTable OBJECT-TYPE
    SYNTAX           SEQUENCE OF CucsFabricFlowMonExporterProfileEntry
    MAX-ACCESS       not-accessible
    STATUS           current
    DESCRIPTION
        "Cisco UCS fabric:FlowMonExporterProfile managed object table"
    ::= { cucsFabricObjects 108 }

cucsFabricFlowMonExporterProfileEntry OBJECT-TYPE
    SYNTAX           CucsFabricFlowMonExporterProfileEntry
    MAX-ACCESS       not-accessible
    STATUS           current
    DESCRIPTION
        "Entry for the cucsFabricFlowMonExporterProfileTable table."
    INDEX { cucsFabricFlowMonExporterProfileInstanceId }
    ::= { cucsFabricFlowMonExporterProfileTable 1 }

CucsFabricFlowMonExporterProfileEntry ::= SEQUENCE {
    cucsFabricFlowMonExporterProfileInstanceId                       CucsManagedObjectId,
    cucsFabricFlowMonExporterProfileDn                               CucsManagedObjectDn,
    cucsFabricFlowMonExporterProfileRn                               SnmpAdminString,
    cucsFabricFlowMonExporterProfileDescr                            SnmpAdminString,
    cucsFabricFlowMonExporterProfileIntId                            SnmpAdminString,
    cucsFabricFlowMonExporterProfileName                             SnmpAdminString,
    cucsFabricFlowMonExporterProfilePolicyLevel                      Gauge32,
    cucsFabricFlowMonExporterProfilePolicyOwner                      CucsPolicyPolicyOwner
}

cucsFabricFlowMonExporterProfileInstanceId OBJECT-TYPE
    SYNTAX       CucsManagedObjectId
    MAX-ACCESS   not-accessible
    STATUS       current
    DESCRIPTION
        "Instance identifier of the managed object."
    ::= { cucsFabricFlowMonExporterProfileEntry 1 }

cucsFabricFlowMonExporterProfileDn OBJECT-TYPE
    SYNTAX       CucsManagedObjectDn
    MAX-ACCESS   read-only
    STATUS       current
    DESCRIPTION
        "Cisco UCS fabric:FlowMonExporterProfile:dn managed
        object property"
    ::= { cucsFabricFlowMonExporterProfileEntry 2 }

cucsFabricFlowMonExporterProfileRn OBJECT-TYPE
    SYNTAX       SnmpAdminString
    MAX-ACCESS   read-only
    STATUS       current
    DESCRIPTION
        "Cisco UCS fabric:FlowMonExporterProfile:rn managed
        object property"
    ::= { cucsFabricFlowMonExporterProfileEntry 3 }

cucsFabricFlowMonExporterProfileDescr OBJECT-TYPE
    SYNTAX       SnmpAdminString
    MAX-ACCESS   read-only
    STATUS       current
    DESCRIPTION
        "Cisco UCS fabric:FlowMonExporterProfile:descr
        managed object property"
    ::= { cucsFabricFlowMonExporterProfileEntry 4 }

cucsFabricFlowMonExporterProfileIntId OBJECT-TYPE
    SYNTAX       SnmpAdminString
    MAX-ACCESS   read-only
    STATUS       current
    DESCRIPTION
        "Cisco UCS fabric:FlowMonExporterProfile:intId
        managed object property"
    ::= { cucsFabricFlowMonExporterProfileEntry 5 }

cucsFabricFlowMonExporterProfileName OBJECT-TYPE
    SYNTAX       SnmpAdminString
    MAX-ACCESS   read-only
    STATUS       current
    DESCRIPTION
        "Cisco UCS fabric:FlowMonExporterProfile:name managed
        object property"
    ::= { cucsFabricFlowMonExporterProfileEntry 6 }

cucsFabricFlowMonExporterProfilePolicyLevel OBJECT-TYPE
    SYNTAX       Gauge32
    MAX-ACCESS   read-only
    STATUS       current
    DESCRIPTION
        "Cisco UCS fabric:FlowMonExporterProfile:policyLevel
        managed object property"
    ::= { cucsFabricFlowMonExporterProfileEntry 7 }

cucsFabricFlowMonExporterProfilePolicyOwner OBJECT-TYPE
    SYNTAX       CucsPolicyPolicyOwner
    MAX-ACCESS   read-only
    STATUS       current
    DESCRIPTION
        "Cisco UCS fabric:FlowMonExporterProfile:policyOwner
        managed object property"
    ::= { cucsFabricFlowMonExporterProfileEntry 8 }

cucsFabricIfTable OBJECT-TYPE
    SYNTAX           SEQUENCE OF CucsFabricIfEntry
    MAX-ACCESS       not-accessible
    STATUS           current
    DESCRIPTION
        "Cisco UCS fabric:If managed object table"
    ::= { cucsFabricObjects 41 }

cucsFabricIfEntry OBJECT-TYPE
    SYNTAX           CucsFabricIfEntry
    MAX-ACCESS       not-accessible
    STATUS           current
    DESCRIPTION
        "Entry for the cucsFabricIfTable table."
    INDEX { cucsFabricIfInstanceId }
    ::= { cucsFabricIfTable 1 }

CucsFabricIfEntry ::= SEQUENCE {
    cucsFabricIfInstanceId                                           CucsManagedObjectId,
    cucsFabricIfDn                                                   CucsManagedObjectDn,
    cucsFabricIfRn                                                   SnmpAdminString,
    cucsFabricIfAddr                                                 InetAddressIPv4,
    cucsFabricIfId                                                   CucsNetworkSwitchId
}

cucsFabricIfInstanceId OBJECT-TYPE
    SYNTAX       CucsManagedObjectId
    MAX-ACCESS   not-accessible
    STATUS       current
    DESCRIPTION
        "Instance identifier of the managed object."
    ::= { cucsFabricIfEntry 1 }

cucsFabricIfDn OBJECT-TYPE
    SYNTAX       CucsManagedObjectDn
    MAX-ACCESS   read-only
    STATUS       current
    DESCRIPTION
        "Cisco UCS fabric:If:dn managed object property"
    ::= { cucsFabricIfEntry 2 }

cucsFabricIfRn OBJECT-TYPE
    SYNTAX       SnmpAdminString
    MAX-ACCESS   read-only
    STATUS       current
    DESCRIPTION
        "Cisco UCS fabric:If:rn managed object property"
    ::= { cucsFabricIfEntry 3 }

cucsFabricIfAddr OBJECT-TYPE
    SYNTAX       InetAddressIPv4
    MAX-ACCESS   read-only
    STATUS       current
    DESCRIPTION
        "Cisco UCS fabric:If:addr managed object property"
    ::= { cucsFabricIfEntry 4 }

cucsFabricIfId OBJECT-TYPE
    SYNTAX       CucsNetworkSwitchId
    MAX-ACCESS   read-only
    STATUS       current
    DESCRIPTION
        "Cisco UCS fabric:If:id managed object property"
    ::= { cucsFabricIfEntry 5 }

cucsFabricLacpPolicyTable OBJECT-TYPE
    SYNTAX           SEQUENCE OF CucsFabricLacpPolicyEntry
    MAX-ACCESS       not-accessible
    STATUS           current
    DESCRIPTION
        "Cisco UCS fabric:LacpPolicy managed object table"
    ::= { cucsFabricObjects 121 }

cucsFabricLacpPolicyEntry OBJECT-TYPE
    SYNTAX           CucsFabricLacpPolicyEntry
    MAX-ACCESS       not-accessible
    STATUS           current
    DESCRIPTION
        "Entry for the cucsFabricLacpPolicyTable table."
    INDEX { cucsFabricLacpPolicyInstanceId }
    ::= { cucsFabricLacpPolicyTable 1 }

CucsFabricLacpPolicyEntry ::= SEQUENCE {
    cucsFabricLacpPolicyInstanceId                                   CucsManagedObjectId,
    cucsFabricLacpPolicyDn                                           CucsManagedObjectDn,
    cucsFabricLacpPolicyRn                                           SnmpAdminString,
    cucsFabricLacpPolicyDescr                                        SnmpAdminString,
    cucsFabricLacpPolicyFastTimer                                    CucsFabricLacpRate,
    cucsFabricLacpPolicyIntId                                        SnmpAdminString,
    cucsFabricLacpPolicyName                                         SnmpAdminString,
    cucsFabricLacpPolicyPolicyLevel                                  Gauge32,
    cucsFabricLacpPolicyPolicyOwner                                  CucsPolicyPolicyOwner,
    cucsFabricLacpPolicySuspendIndividual                            CucsFabricLacpSuspend
}

cucsFabricLacpPolicyInstanceId OBJECT-TYPE
    SYNTAX       CucsManagedObjectId
    MAX-ACCESS   not-accessible
    STATUS       current
    DESCRIPTION
        "Instance identifier of the managed object."
    ::= { cucsFabricLacpPolicyEntry 1 }

cucsFabricLacpPolicyDn OBJECT-TYPE
    SYNTAX       CucsManagedObjectDn
    MAX-ACCESS   read-only
    STATUS       current
    DESCRIPTION
        "Cisco UCS fabric:LacpPolicy:dn managed object property"
    ::= { cucsFabricLacpPolicyEntry 2 }

cucsFabricLacpPolicyRn OBJECT-TYPE
    SYNTAX       SnmpAdminString
    MAX-ACCESS   read-only
    STATUS       current
    DESCRIPTION
        "Cisco UCS fabric:LacpPolicy:rn managed object property"
    ::= { cucsFabricLacpPolicyEntry 3 }

cucsFabricLacpPolicyDescr OBJECT-TYPE
    SYNTAX       SnmpAdminString
    MAX-ACCESS   read-only
    STATUS       current
    DESCRIPTION
        "Cisco UCS fabric:LacpPolicy:descr managed object property"
    ::= { cucsFabricLacpPolicyEntry 4 }

cucsFabricLacpPolicyFastTimer OBJECT-TYPE
    SYNTAX       CucsFabricLacpRate
    MAX-ACCESS   read-only
    STATUS       current
    DESCRIPTION
        "Cisco UCS fabric:LacpPolicy:fastTimer managed object property"
    ::= { cucsFabricLacpPolicyEntry 5 }

cucsFabricLacpPolicyIntId OBJECT-TYPE
    SYNTAX       SnmpAdminString
    MAX-ACCESS   read-only
    STATUS       current
    DESCRIPTION
        "Cisco UCS fabric:LacpPolicy:intId managed object property"
    ::= { cucsFabricLacpPolicyEntry 6 }

cucsFabricLacpPolicyName OBJECT-TYPE
    SYNTAX       SnmpAdminString
    MAX-ACCESS   read-only
    STATUS       current
    DESCRIPTION
        "Cisco UCS fabric:LacpPolicy:name managed object property"
    ::= { cucsFabricLacpPolicyEntry 7 }

cucsFabricLacpPolicyPolicyLevel OBJECT-TYPE
    SYNTAX       Gauge32
    MAX-ACCESS   read-only
    STATUS       current
    DESCRIPTION
        "Cisco UCS fabric:LacpPolicy:policyLevel managed object property"
    ::= { cucsFabricLacpPolicyEntry 8 }

cucsFabricLacpPolicyPolicyOwner OBJECT-TYPE
    SYNTAX       CucsPolicyPolicyOwner
    MAX-ACCESS   read-only
    STATUS       current
    DESCRIPTION
        "Cisco UCS fabric:LacpPolicy:policyOwner managed object property"
    ::= { cucsFabricLacpPolicyEntry 9 }

cucsFabricLacpPolicySuspendIndividual OBJECT-TYPE
    SYNTAX       CucsFabricLacpSuspend
    MAX-ACCESS   read-only
    STATUS       current
    DESCRIPTION
        "Cisco UCS fabric:LacpPolicy:suspendIndividual
        managed object property"
    ::= { cucsFabricLacpPolicyEntry 10 }

cucsFabricLanAccessMgrTable OBJECT-TYPE
    SYNTAX           SEQUENCE OF CucsFabricLanAccessMgrEntry
    MAX-ACCESS       not-accessible
    STATUS           current
    DESCRIPTION
        "Cisco UCS fabric:LanAccessMgr managed object table"
    ::= { cucsFabricObjects 82 }

cucsFabricLanAccessMgrEntry OBJECT-TYPE
    SYNTAX           CucsFabricLanAccessMgrEntry
    MAX-ACCESS       not-accessible
    STATUS           current
    DESCRIPTION
        "Entry for the cucsFabricLanAccessMgrTable table."
    INDEX { cucsFabricLanAccessMgrInstanceId }
    ::= { cucsFabricLanAccessMgrTable 1 }

CucsFabricLanAccessMgrEntry ::= SEQUENCE {
    cucsFabricLanAccessMgrInstanceId                                 CucsManagedObjectId,
    cucsFabricLanAccessMgrDn                                         CucsManagedObjectDn,
    cucsFabricLanAccessMgrRn                                         SnmpAdminString
}

cucsFabricLanAccessMgrInstanceId OBJECT-TYPE
    SYNTAX       CucsManagedObjectId
    MAX-ACCESS   not-accessible
    STATUS       current
    DESCRIPTION
        "Instance identifier of the managed object."
    ::= { cucsFabricLanAccessMgrEntry 1 }

cucsFabricLanAccessMgrDn OBJECT-TYPE
    SYNTAX       CucsManagedObjectDn
    MAX-ACCESS   read-only
    STATUS       current
    DESCRIPTION
        "Cisco UCS fabric:LanAccessMgr:dn managed object property"
    ::= { cucsFabricLanAccessMgrEntry 2 }

cucsFabricLanAccessMgrRn OBJECT-TYPE
    SYNTAX       SnmpAdminString
    MAX-ACCESS   read-only
    STATUS       current
    DESCRIPTION
        "Cisco UCS fabric:LanAccessMgr:rn managed object property"
    ::= { cucsFabricLanAccessMgrEntry 3 }

cucsFabricLanCloudTable OBJECT-TYPE
    SYNTAX           SEQUENCE OF CucsFabricLanCloudEntry
    MAX-ACCESS       not-accessible
    STATUS           current
    DESCRIPTION
        "Cisco UCS fabric:LanCloud managed object table"
    ::= { cucsFabricObjects 42 }

cucsFabricLanCloudEntry OBJECT-TYPE
    SYNTAX           CucsFabricLanCloudEntry
    MAX-ACCESS       not-accessible
    STATUS           current
    DESCRIPTION
        "Entry for the cucsFabricLanCloudTable table."
    INDEX { cucsFabricLanCloudInstanceId }
    ::= { cucsFabricLanCloudTable 1 }

CucsFabricLanCloudEntry ::= SEQUENCE {
    cucsFabricLanCloudInstanceId                                     CucsManagedObjectId,
    cucsFabricLanCloudDn                                             CucsManagedObjectDn,
    cucsFabricLanCloudRn                                             SnmpAdminString,
    cucsFabricLanCloudFsmDescr                                       SnmpAdminString,
    cucsFabricLanCloudFsmPrev                                        SnmpAdminString,
    cucsFabricLanCloudFsmProgr                                       Gauge32,
    cucsFabricLanCloudFsmRmtInvErrCode                               Gauge32,
    cucsFabricLanCloudFsmRmtInvErrDescr                              SnmpAdminString,
    cucsFabricLanCloudFsmRmtInvRslt                                  CucsConditionRemoteInvRslt,
    cucsFabricLanCloudFsmStageDescr                                  SnmpAdminString,
    cucsFabricLanCloudFsmStamp                                       DateAndTime,
    cucsFabricLanCloudFsmStatus                                      SnmpAdminString,
    cucsFabricLanCloudFsmTry                                         Gauge32,
    cucsFabricLanCloudMacAging                                       TimeIntervalSec,
    cucsFabricLanCloudMode                                           CucsFabricSwitchingMode,
    cucsFabricLanCloudVlanCompression                                CucsFabricLanCloudVlanCompression
}

cucsFabricLanCloudInstanceId OBJECT-TYPE
    SYNTAX       CucsManagedObjectId
    MAX-ACCESS   not-accessible
    STATUS       current
    DESCRIPTION
        "Instance identifier of the managed object."
    ::= { cucsFabricLanCloudEntry 1 }

cucsFabricLanCloudDn OBJECT-TYPE
    SYNTAX       CucsManagedObjectDn
    MAX-ACCESS   read-only
    STATUS       current
    DESCRIPTION
        "Cisco UCS fabric:LanCloud:dn managed object property"
    ::= { cucsFabricLanCloudEntry 2 }

cucsFabricLanCloudRn OBJECT-TYPE
    SYNTAX       SnmpAdminString
    MAX-ACCESS   read-only
    STATUS       current
    DESCRIPTION
        "Cisco UCS fabric:LanCloud:rn managed object property"
    ::= { cucsFabricLanCloudEntry 3 }

cucsFabricLanCloudFsmDescr OBJECT-TYPE
    SYNTAX       SnmpAdminString
    MAX-ACCESS   read-only
    STATUS       current
    DESCRIPTION
        "Cisco UCS fabric:LanCloud:fsmDescr managed object property"
    ::= { cucsFabricLanCloudEntry 4 }

cucsFabricLanCloudFsmPrev OBJECT-TYPE
    SYNTAX       SnmpAdminString
    MAX-ACCESS   read-only
    STATUS       current
    DESCRIPTION
        "Cisco UCS fabric:LanCloud:fsmPrev managed object property"
    ::= { cucsFabricLanCloudEntry 5 }

cucsFabricLanCloudFsmProgr OBJECT-TYPE
    SYNTAX       Gauge32
    MAX-ACCESS   read-only
    STATUS       current
    DESCRIPTION
        "Cisco UCS fabric:LanCloud:fsmProgr managed object property"
    ::= { cucsFabricLanCloudEntry 6 }

cucsFabricLanCloudFsmRmtInvErrCode OBJECT-TYPE
    SYNTAX       Gauge32
    MAX-ACCESS   read-only
    STATUS       current
    DESCRIPTION
        "Cisco UCS fabric:LanCloud:fsmRmtInvErrCode managed
        object property"
    ::= { cucsFabricLanCloudEntry 7 }

cucsFabricLanCloudFsmRmtInvErrDescr OBJECT-TYPE
    SYNTAX       SnmpAdminString
    MAX-ACCESS   read-only
    STATUS       current
    DESCRIPTION
        "Cisco UCS fabric:LanCloud:fsmRmtInvErrDescr managed
        object property"
    ::= { cucsFabricLanCloudEntry 8 }

cucsFabricLanCloudFsmRmtInvRslt OBJECT-TYPE
    SYNTAX       CucsConditionRemoteInvRslt
    MAX-ACCESS   read-only
    STATUS       current
    DESCRIPTION
        "Cisco UCS fabric:LanCloud:fsmRmtInvRslt managed object property"
    ::= { cucsFabricLanCloudEntry 9 }

cucsFabricLanCloudFsmStageDescr OBJECT-TYPE
    SYNTAX       SnmpAdminString
    MAX-ACCESS   read-only
    STATUS       current
    DESCRIPTION
        "Cisco UCS fabric:LanCloud:fsmStageDescr managed object property"
    ::= { cucsFabricLanCloudEntry 10 }

cucsFabricLanCloudFsmStamp OBJECT-TYPE
    SYNTAX       DateAndTime
    MAX-ACCESS   read-only
    STATUS       current
    DESCRIPTION
        "Cisco UCS fabric:LanCloud:fsmStamp managed object property"
    ::= { cucsFabricLanCloudEntry 11 }

cucsFabricLanCloudFsmStatus OBJECT-TYPE
    SYNTAX       SnmpAdminString
    MAX-ACCESS   read-only
    STATUS       current
    DESCRIPTION
        "Cisco UCS fabric:LanCloud:fsmStatus managed object property"
    ::= { cucsFabricLanCloudEntry 12 }

cucsFabricLanCloudFsmTry OBJECT-TYPE
    SYNTAX       Gauge32
    MAX-ACCESS   read-only
    STATUS       current
    DESCRIPTION
        "Cisco UCS fabric:LanCloud:fsmTry managed object property"
    ::= { cucsFabricLanCloudEntry 13 }

cucsFabricLanCloudMacAging OBJECT-TYPE
    SYNTAX       TimeIntervalSec
    MAX-ACCESS   read-only
    STATUS       current
    DESCRIPTION
        "Cisco UCS fabric:LanCloud:macAging managed object property"
    ::= { cucsFabricLanCloudEntry 14 }

cucsFabricLanCloudMode OBJECT-TYPE
    SYNTAX       CucsFabricSwitchingMode
    MAX-ACCESS   read-only
    STATUS       current
    DESCRIPTION
        "Cisco UCS fabric:LanCloud:mode managed object property"
    ::= { cucsFabricLanCloudEntry 15 }

cucsFabricLanCloudVlanCompression OBJECT-TYPE
    SYNTAX       CucsFabricLanCloudVlanCompression
    MAX-ACCESS   read-only
    STATUS       current
    DESCRIPTION
        "Cisco UCS fabric:LanCloud:vlanCompression managed
        object property"
    ::= { cucsFabricLanCloudEntry 16 }

cucsFabricLanCloudFsmTable OBJECT-TYPE
    SYNTAX           SEQUENCE OF CucsFabricLanCloudFsmEntry
    MAX-ACCESS       not-accessible
    STATUS           current
    DESCRIPTION
        "Cisco UCS fabric:LanCloudFsm managed object table"
    ::= { cucsFabricObjects 83 }

cucsFabricLanCloudFsmEntry OBJECT-TYPE
    SYNTAX           CucsFabricLanCloudFsmEntry
    MAX-ACCESS       not-accessible
    STATUS           current
    DESCRIPTION
        "Entry for the cucsFabricLanCloudFsmTable table."
    INDEX { cucsFabricLanCloudFsmInstanceId }
    ::= { cucsFabricLanCloudFsmTable 1 }

CucsFabricLanCloudFsmEntry ::= SEQUENCE {
    cucsFabricLanCloudFsmInstanceId                                  CucsManagedObjectId,
    cucsFabricLanCloudFsmDn                                          CucsManagedObjectDn,
    cucsFabricLanCloudFsmRn                                          SnmpAdminString,
    cucsFabricLanCloudFsmCompletionTime                              DateAndTime,
    cucsFabricLanCloudFsmCurrentFsm                                  CucsFabricLanCloudFsmCurrentFsm,
    cucsFabricLanCloudFsmDescrData                                   SnmpAdminString,
    cucsFabricLanCloudFsmFsmStatus                                   CucsFsmFsmStageStatus,
    cucsFabricLanCloudFsmProgress                                    Gauge32,
    cucsFabricLanCloudFsmRmtErrCode                                  Gauge32,
    cucsFabricLanCloudFsmRmtErrDescr                                 SnmpAdminString,
    cucsFabricLanCloudFsmRmtRslt                                     CucsConditionRemoteInvRslt
}

cucsFabricLanCloudFsmInstanceId OBJECT-TYPE
    SYNTAX       CucsManagedObjectId
    MAX-ACCESS   not-accessible
    STATUS       current
    DESCRIPTION
        "Instance identifier of the managed object."
    ::= { cucsFabricLanCloudFsmEntry 1 }

cucsFabricLanCloudFsmDn OBJECT-TYPE
    SYNTAX       CucsManagedObjectDn
    MAX-ACCESS   read-only
    STATUS       current
    DESCRIPTION
        "Cisco UCS fabric:LanCloudFsm:dn managed object property"
    ::= { cucsFabricLanCloudFsmEntry 2 }

cucsFabricLanCloudFsmRn OBJECT-TYPE
    SYNTAX       SnmpAdminString
    MAX-ACCESS   read-only
    STATUS       current
    DESCRIPTION
        "Cisco UCS fabric:LanCloudFsm:rn managed object property"
    ::= { cucsFabricLanCloudFsmEntry 3 }

cucsFabricLanCloudFsmCompletionTime OBJECT-TYPE
    SYNTAX       DateAndTime
    MAX-ACCESS   read-only
    STATUS       current
    DESCRIPTION
        "Cisco UCS fabric:LanCloudFsm:completionTime managed
        object property"
    ::= { cucsFabricLanCloudFsmEntry 4 }

cucsFabricLanCloudFsmCurrentFsm OBJECT-TYPE
    SYNTAX       CucsFabricLanCloudFsmCurrentFsm
    MAX-ACCESS   read-only
    STATUS       current
    DESCRIPTION
        "Cisco UCS fabric:LanCloudFsm:currentFsm managed object property"
    ::= { cucsFabricLanCloudFsmEntry 5 }

cucsFabricLanCloudFsmDescrData OBJECT-TYPE
    SYNTAX       SnmpAdminString
    MAX-ACCESS   read-only
    STATUS       current
    DESCRIPTION
        "Cisco UCS fabric:LanCloudFsm:descr managed object property"
    ::= { cucsFabricLanCloudFsmEntry 6 }

cucsFabricLanCloudFsmFsmStatus OBJECT-TYPE
    SYNTAX       CucsFsmFsmStageStatus
    MAX-ACCESS   read-only
    STATUS       current
    DESCRIPTION
        "Cisco UCS fabric:LanCloudFsm:fsmStatus managed object property"
    ::= { cucsFabricLanCloudFsmEntry 7 }

cucsFabricLanCloudFsmProgress OBJECT-TYPE
    SYNTAX       Gauge32
    MAX-ACCESS   read-only
    STATUS       current
    DESCRIPTION
        "Cisco UCS fabric:LanCloudFsm:progress managed object property"
    ::= { cucsFabricLanCloudFsmEntry 8 }

cucsFabricLanCloudFsmRmtErrCode OBJECT-TYPE
    SYNTAX       Gauge32
    MAX-ACCESS   read-only
    STATUS       current
    DESCRIPTION
        "Cisco UCS fabric:LanCloudFsm:rmtErrCode managed object property"
    ::= { cucsFabricLanCloudFsmEntry 9 }

cucsFabricLanCloudFsmRmtErrDescr OBJECT-TYPE
    SYNTAX       SnmpAdminString
    MAX-ACCESS   read-only
    STATUS       current
    DESCRIPTION
        "Cisco UCS fabric:LanCloudFsm:rmtErrDescr managed object property"
    ::= { cucsFabricLanCloudFsmEntry 10 }

cucsFabricLanCloudFsmRmtRslt OBJECT-TYPE
    SYNTAX       CucsConditionRemoteInvRslt
    MAX-ACCESS   read-only
    STATUS       current
    DESCRIPTION
        "Cisco UCS fabric:LanCloudFsm:rmtRslt managed object property"
    ::= { cucsFabricLanCloudFsmEntry 11 }

cucsFabricLanCloudFsmStageTable OBJECT-TYPE
    SYNTAX           SEQUENCE OF CucsFabricLanCloudFsmStageEntry
    MAX-ACCESS       not-accessible
    STATUS           current
    DESCRIPTION
        "Cisco UCS fabric:LanCloudFsmStage managed object table"
    ::= { cucsFabricObjects 84 }

cucsFabricLanCloudFsmStageEntry OBJECT-TYPE
    SYNTAX           CucsFabricLanCloudFsmStageEntry
    MAX-ACCESS       not-accessible
    STATUS           current
    DESCRIPTION
        "Entry for the cucsFabricLanCloudFsmStageTable table."
    INDEX { cucsFabricLanCloudFsmStageInstanceId }
    ::= { cucsFabricLanCloudFsmStageTable 1 }

CucsFabricLanCloudFsmStageEntry ::= SEQUENCE {
    cucsFabricLanCloudFsmStageInstanceId                             CucsManagedObjectId,
    cucsFabricLanCloudFsmStageDn                                     CucsManagedObjectDn,
    cucsFabricLanCloudFsmStageRn                                     SnmpAdminString,
    cucsFabricLanCloudFsmStageDescrData                              SnmpAdminString,
    cucsFabricLanCloudFsmStageLastUpdateTime                         DateAndTime,
    cucsFabricLanCloudFsmStageName                                   CucsFabricLanCloudFsmStageName,
    cucsFabricLanCloudFsmStageOrder                                  Gauge32,
    cucsFabricLanCloudFsmStageRetry                                  Gauge32,
    cucsFabricLanCloudFsmStageStageStatus                            CucsFsmFsmStageStatus
}

cucsFabricLanCloudFsmStageInstanceId OBJECT-TYPE
    SYNTAX       CucsManagedObjectId
    MAX-ACCESS   not-accessible
    STATUS       current
    DESCRIPTION
        "Instance identifier of the managed object."
    ::= { cucsFabricLanCloudFsmStageEntry 1 }

cucsFabricLanCloudFsmStageDn OBJECT-TYPE
    SYNTAX       CucsManagedObjectDn
    MAX-ACCESS   read-only
    STATUS       current
    DESCRIPTION
        "Cisco UCS fabric:LanCloudFsmStage:dn managed object property"
    ::= { cucsFabricLanCloudFsmStageEntry 2 }

cucsFabricLanCloudFsmStageRn OBJECT-TYPE
    SYNTAX       SnmpAdminString
    MAX-ACCESS   read-only
    STATUS       current
    DESCRIPTION
        "Cisco UCS fabric:LanCloudFsmStage:rn managed object property"
    ::= { cucsFabricLanCloudFsmStageEntry 3 }

cucsFabricLanCloudFsmStageDescrData OBJECT-TYPE
    SYNTAX       SnmpAdminString
    MAX-ACCESS   read-only
    STATUS       current
    DESCRIPTION
        "Cisco UCS fabric:LanCloudFsmStage:descr managed object property"
    ::= { cucsFabricLanCloudFsmStageEntry 4 }

cucsFabricLanCloudFsmStageLastUpdateTime OBJECT-TYPE
    SYNTAX       DateAndTime
    MAX-ACCESS   read-only
    STATUS       current
    DESCRIPTION
        "Cisco UCS fabric:LanCloudFsmStage:lastUpdateTime
        managed object property"
    ::= { cucsFabricLanCloudFsmStageEntry 5 }

cucsFabricLanCloudFsmStageName OBJECT-TYPE
    SYNTAX       CucsFabricLanCloudFsmStageName
    MAX-ACCESS   read-only
    STATUS       current
    DESCRIPTION
        "Cisco UCS fabric:LanCloudFsmStage:name managed object property"
    ::= { cucsFabricLanCloudFsmStageEntry 6 }

cucsFabricLanCloudFsmStageOrder OBJECT-TYPE
    SYNTAX       Gauge32
    MAX-ACCESS   read-only
    STATUS       current
    DESCRIPTION
        "Cisco UCS fabric:LanCloudFsmStage:order managed object property"
    ::= { cucsFabricLanCloudFsmStageEntry 7 }

cucsFabricLanCloudFsmStageRetry OBJECT-TYPE
    SYNTAX       Gauge32
    MAX-ACCESS   read-only
    STATUS       current
    DESCRIPTION
        "Cisco UCS fabric:LanCloudFsmStage:retry managed object property"
    ::= { cucsFabricLanCloudFsmStageEntry 8 }

cucsFabricLanCloudFsmStageStageStatus OBJECT-TYPE
    SYNTAX       CucsFsmFsmStageStatus
    MAX-ACCESS   read-only
    STATUS       current
    DESCRIPTION
        "Cisco UCS fabric:LanCloudFsmStage:stageStatus
        managed object property"
    ::= { cucsFabricLanCloudFsmStageEntry 9 }

cucsFabricLanCloudFsmTaskTable OBJECT-TYPE
    SYNTAX           SEQUENCE OF CucsFabricLanCloudFsmTaskEntry
    MAX-ACCESS       not-accessible
    STATUS           current
    DESCRIPTION
        "Cisco UCS fabric:LanCloudFsmTask managed object table"
    ::= { cucsFabricObjects 43 }

cucsFabricLanCloudFsmTaskEntry OBJECT-TYPE
    SYNTAX           CucsFabricLanCloudFsmTaskEntry
    MAX-ACCESS       not-accessible
    STATUS           current
    DESCRIPTION
        "Entry for the cucsFabricLanCloudFsmTaskTable table."
    INDEX { cucsFabricLanCloudFsmTaskInstanceId }
    ::= { cucsFabricLanCloudFsmTaskTable 1 }

CucsFabricLanCloudFsmTaskEntry ::= SEQUENCE {
    cucsFabricLanCloudFsmTaskInstanceId                              CucsManagedObjectId,
    cucsFabricLanCloudFsmTaskDn                                      CucsManagedObjectDn,
    cucsFabricLanCloudFsmTaskRn                                      SnmpAdminString,
    cucsFabricLanCloudFsmTaskCompletion                              CucsFsmCompletion,
    cucsFabricLanCloudFsmTaskFlags                                   CucsFsmFlags,
    cucsFabricLanCloudFsmTaskItem                                    CucsFabricLanCloudFsmTaskItem,
    cucsFabricLanCloudFsmTaskSeqId                                   Gauge32
}

cucsFabricLanCloudFsmTaskInstanceId OBJECT-TYPE
    SYNTAX       CucsManagedObjectId
    MAX-ACCESS   not-accessible
    STATUS       current
    DESCRIPTION
        "Instance identifier of the managed object."
    ::= { cucsFabricLanCloudFsmTaskEntry 1 }

cucsFabricLanCloudFsmTaskDn OBJECT-TYPE
    SYNTAX       CucsManagedObjectDn
    MAX-ACCESS   read-only
    STATUS       current
    DESCRIPTION
        "Cisco UCS fabric:LanCloudFsmTask:dn managed object property"
    ::= { cucsFabricLanCloudFsmTaskEntry 2 }

cucsFabricLanCloudFsmTaskRn OBJECT-TYPE
    SYNTAX       SnmpAdminString
    MAX-ACCESS   read-only
    STATUS       current
    DESCRIPTION
        "Cisco UCS fabric:LanCloudFsmTask:rn managed object property"
    ::= { cucsFabricLanCloudFsmTaskEntry 3 }

cucsFabricLanCloudFsmTaskCompletion OBJECT-TYPE
    SYNTAX       CucsFsmCompletion
    MAX-ACCESS   read-only
    STATUS       current
    DESCRIPTION
        "Cisco UCS fabric:LanCloudFsmTask:completion managed
        object property"
    ::= { cucsFabricLanCloudFsmTaskEntry 4 }

cucsFabricLanCloudFsmTaskFlags OBJECT-TYPE
    SYNTAX       CucsFsmFlags
    MAX-ACCESS   read-only
    STATUS       current
    DESCRIPTION
        "Cisco UCS fabric:LanCloudFsmTask:flags managed object property"
    ::= { cucsFabricLanCloudFsmTaskEntry 5 }

cucsFabricLanCloudFsmTaskItem OBJECT-TYPE
    SYNTAX       CucsFabricLanCloudFsmTaskItem
    MAX-ACCESS   read-only
    STATUS       current
    DESCRIPTION
        "Cisco UCS fabric:LanCloudFsmTask:item managed object property"
    ::= { cucsFabricLanCloudFsmTaskEntry 6 }

cucsFabricLanCloudFsmTaskSeqId OBJECT-TYPE
    SYNTAX       Gauge32
    MAX-ACCESS   read-only
    STATUS       current
    DESCRIPTION
        "Cisco UCS fabric:LanCloudFsmTask:seqId managed object property"
    ::= { cucsFabricLanCloudFsmTaskEntry 7 }

cucsFabricLanCloudPolicyTable OBJECT-TYPE
    SYNTAX           SEQUENCE OF CucsFabricLanCloudPolicyEntry
    MAX-ACCESS       not-accessible
    STATUS           current
    DESCRIPTION
        "Cisco UCS fabric:LanCloudPolicy managed object table"
    ::= { cucsFabricObjects 191 }

cucsFabricLanCloudPolicyEntry OBJECT-TYPE
    SYNTAX           CucsFabricLanCloudPolicyEntry
    MAX-ACCESS       not-accessible
    STATUS           current
    DESCRIPTION
        "Entry for the cucsFabricLanCloudPolicyTable table."
    INDEX { cucsFabricLanCloudPolicyInstanceId }
    ::= { cucsFabricLanCloudPolicyTable 1 }

CucsFabricLanCloudPolicyEntry ::= SEQUENCE {
    cucsFabricLanCloudPolicyInstanceId                               CucsManagedObjectId,
    cucsFabricLanCloudPolicyDn                                       CucsManagedObjectDn,
    cucsFabricLanCloudPolicyRn                                       SnmpAdminString,
    cucsFabricLanCloudPolicyDescr                                    SnmpAdminString,
    cucsFabricLanCloudPolicyIntId                                    SnmpAdminString,
    cucsFabricLanCloudPolicyMacAging                                 TimeIntervalSec,
    cucsFabricLanCloudPolicyMode                                     CucsFabricSwitchingMode,
    cucsFabricLanCloudPolicyName                                     SnmpAdminString,
    cucsFabricLanCloudPolicyPolicyLevel                              Gauge32,
    cucsFabricLanCloudPolicyPolicyOwner                              CucsPolicyPolicyOwner,
    cucsFabricLanCloudPolicyVlanCompression                          CucsFabricLanCloudPolicyVlanCompression
}

cucsFabricLanCloudPolicyInstanceId OBJECT-TYPE
    SYNTAX       CucsManagedObjectId
    MAX-ACCESS   not-accessible
    STATUS       current
    DESCRIPTION
        "Instance identifier of the managed object."
    ::= { cucsFabricLanCloudPolicyEntry 1 }

cucsFabricLanCloudPolicyDn OBJECT-TYPE
    SYNTAX       CucsManagedObjectDn
    MAX-ACCESS   read-only
    STATUS       current
    DESCRIPTION
        "Cisco UCS fabric:LanCloudPolicy:dn managed object property"
    ::= { cucsFabricLanCloudPolicyEntry 2 }

cucsFabricLanCloudPolicyRn OBJECT-TYPE
    SYNTAX       SnmpAdminString
    MAX-ACCESS   read-only
    STATUS       current
    DESCRIPTION
        "Cisco UCS fabric:LanCloudPolicy:rn managed object property"
    ::= { cucsFabricLanCloudPolicyEntry 3 }

cucsFabricLanCloudPolicyDescr OBJECT-TYPE
    SYNTAX       SnmpAdminString
    MAX-ACCESS   read-only
    STATUS       current
    DESCRIPTION
        "Cisco UCS fabric:LanCloudPolicy:descr managed object property"
    ::= { cucsFabricLanCloudPolicyEntry 4 }

cucsFabricLanCloudPolicyIntId OBJECT-TYPE
    SYNTAX       SnmpAdminString
    MAX-ACCESS   read-only
    STATUS       current
    DESCRIPTION
        "Cisco UCS fabric:LanCloudPolicy:intId managed object property"
    ::= { cucsFabricLanCloudPolicyEntry 5 }

cucsFabricLanCloudPolicyMacAging OBJECT-TYPE
    SYNTAX       TimeIntervalSec
    MAX-ACCESS   read-only
    STATUS       current
    DESCRIPTION
        "Cisco UCS fabric:LanCloudPolicy:macAging managed object property"
    ::= { cucsFabricLanCloudPolicyEntry 6 }

cucsFabricLanCloudPolicyMode OBJECT-TYPE
    SYNTAX       CucsFabricSwitchingMode
    MAX-ACCESS   read-only
    STATUS       current
    DESCRIPTION
        "Cisco UCS fabric:LanCloudPolicy:mode managed object property"
    ::= { cucsFabricLanCloudPolicyEntry 7 }

cucsFabricLanCloudPolicyName OBJECT-TYPE
    SYNTAX       SnmpAdminString
    MAX-ACCESS   read-only
    STATUS       current
    DESCRIPTION
        "Cisco UCS fabric:LanCloudPolicy:name managed object property"
    ::= { cucsFabricLanCloudPolicyEntry 8 }

cucsFabricLanCloudPolicyPolicyLevel OBJECT-TYPE
    SYNTAX       Gauge32
    MAX-ACCESS   read-only
    STATUS       current
    DESCRIPTION
        "Cisco UCS fabric:LanCloudPolicy:policyLevel managed
        object property"
    ::= { cucsFabricLanCloudPolicyEntry 9 }

cucsFabricLanCloudPolicyPolicyOwner OBJECT-TYPE
    SYNTAX       CucsPolicyPolicyOwner
    MAX-ACCESS   read-only
    STATUS       current
    DESCRIPTION
        "Cisco UCS fabric:LanCloudPolicy:policyOwner managed
        object property"
    ::= { cucsFabricLanCloudPolicyEntry 10 }

cucsFabricLanCloudPolicyVlanCompression OBJECT-TYPE
    SYNTAX       CucsFabricLanCloudPolicyVlanCompression
    MAX-ACCESS   read-only
    STATUS       current
    DESCRIPTION
        "Cisco UCS fabric:LanCloudPolicy:vlanCompression
        managed object property"
    ::= { cucsFabricLanCloudPolicyEntry 11 }

cucsFabricLanMonCloudTable OBJECT-TYPE
    SYNTAX           SEQUENCE OF CucsFabricLanMonCloudEntry
    MAX-ACCESS       not-accessible
    STATUS           current
    DESCRIPTION
        "Cisco UCS fabric:LanMonCloud managed object table"
    ::= { cucsFabricObjects 44 }

cucsFabricLanMonCloudEntry OBJECT-TYPE
    SYNTAX           CucsFabricLanMonCloudEntry
    MAX-ACCESS       not-accessible
    STATUS           current
    DESCRIPTION
        "Entry for the cucsFabricLanMonCloudTable table."
    INDEX { cucsFabricLanMonCloudInstanceId }
    ::= { cucsFabricLanMonCloudTable 1 }

CucsFabricLanMonCloudEntry ::= SEQUENCE {
    cucsFabricLanMonCloudInstanceId                                  CucsManagedObjectId,
    cucsFabricLanMonCloudDn                                          CucsManagedObjectDn,
    cucsFabricLanMonCloudRn                                          SnmpAdminString,
    cucsFabricLanMonCloudMode                                        CucsFabricSwitchingMode
}

cucsFabricLanMonCloudInstanceId OBJECT-TYPE
    SYNTAX       CucsManagedObjectId
    MAX-ACCESS   not-accessible
    STATUS       current
    DESCRIPTION
        "Instance identifier of the managed object."
    ::= { cucsFabricLanMonCloudEntry 1 }

cucsFabricLanMonCloudDn OBJECT-TYPE
    SYNTAX       CucsManagedObjectDn
    MAX-ACCESS   read-only
    STATUS       current
    DESCRIPTION
        "Cisco UCS fabric:LanMonCloud:dn managed object property"
    ::= { cucsFabricLanMonCloudEntry 2 }

cucsFabricLanMonCloudRn OBJECT-TYPE
    SYNTAX       SnmpAdminString
    MAX-ACCESS   read-only
    STATUS       current
    DESCRIPTION
        "Cisco UCS fabric:LanMonCloud:rn managed object property"
    ::= { cucsFabricLanMonCloudEntry 3 }

cucsFabricLanMonCloudMode OBJECT-TYPE
    SYNTAX       CucsFabricSwitchingMode
    MAX-ACCESS   read-only
    STATUS       current
    DESCRIPTION
        "Cisco UCS fabric:LanMonCloud:mode managed object property"
    ::= { cucsFabricLanMonCloudEntry 4 }

cucsFabricLanPinGroupTable OBJECT-TYPE
    SYNTAX           SEQUENCE OF CucsFabricLanPinGroupEntry
    MAX-ACCESS       not-accessible
    STATUS           current
    DESCRIPTION
        "Cisco UCS fabric:LanPinGroup managed object table"
    ::= { cucsFabricObjects 45 }

cucsFabricLanPinGroupEntry OBJECT-TYPE
    SYNTAX           CucsFabricLanPinGroupEntry
    MAX-ACCESS       not-accessible
    STATUS           current
    DESCRIPTION
        "Entry for the cucsFabricLanPinGroupTable table."
    INDEX { cucsFabricLanPinGroupInstanceId }
    ::= { cucsFabricLanPinGroupTable 1 }

CucsFabricLanPinGroupEntry ::= SEQUENCE {
    cucsFabricLanPinGroupInstanceId                                  CucsManagedObjectId,
    cucsFabricLanPinGroupDn                                          CucsManagedObjectDn,
    cucsFabricLanPinGroupRn                                          SnmpAdminString,
    cucsFabricLanPinGroupDescr                                       SnmpAdminString,
    cucsFabricLanPinGroupIntId                                       SnmpAdminString,
    cucsFabricLanPinGroupName                                        SnmpAdminString,
    cucsFabricLanPinGroupSize                                        Gauge32,
    cucsFabricLanPinGroupPolicyLevel                                 Gauge32,
    cucsFabricLanPinGroupPolicyOwner                                 CucsPolicyPolicyOwner
}

cucsFabricLanPinGroupInstanceId OBJECT-TYPE
    SYNTAX       CucsManagedObjectId
    MAX-ACCESS   not-accessible
    STATUS       current
    DESCRIPTION
        "Instance identifier of the managed object."
    ::= { cucsFabricLanPinGroupEntry 1 }

cucsFabricLanPinGroupDn OBJECT-TYPE
    SYNTAX       CucsManagedObjectDn
    MAX-ACCESS   read-only
    STATUS       current
    DESCRIPTION
        "Cisco UCS fabric:LanPinGroup:dn managed object property"
    ::= { cucsFabricLanPinGroupEntry 2 }

cucsFabricLanPinGroupRn OBJECT-TYPE
    SYNTAX       SnmpAdminString
    MAX-ACCESS   read-only
    STATUS       current
    DESCRIPTION
        "Cisco UCS fabric:LanPinGroup:rn managed object property"
    ::= { cucsFabricLanPinGroupEntry 3 }

cucsFabricLanPinGroupDescr OBJECT-TYPE
    SYNTAX       SnmpAdminString
    MAX-ACCESS   read-only
    STATUS       current
    DESCRIPTION
        "Cisco UCS fabric:LanPinGroup:descr managed object property"
    ::= { cucsFabricLanPinGroupEntry 4 }

cucsFabricLanPinGroupIntId OBJECT-TYPE
    SYNTAX       SnmpAdminString
    MAX-ACCESS   read-only
    STATUS       current
    DESCRIPTION
        "Cisco UCS fabric:LanPinGroup:intId managed object property"
    ::= { cucsFabricLanPinGroupEntry 5 }

cucsFabricLanPinGroupName OBJECT-TYPE
    SYNTAX       SnmpAdminString
    MAX-ACCESS   read-only
    STATUS       current
    DESCRIPTION
        "Cisco UCS fabric:LanPinGroup:name managed object property"
    ::= { cucsFabricLanPinGroupEntry 6 }

cucsFabricLanPinGroupSize OBJECT-TYPE
    SYNTAX       Gauge32
    MAX-ACCESS   read-only
    STATUS       current
    DESCRIPTION
        "Cisco UCS fabric:LanPinGroup:size managed object property"
    ::= { cucsFabricLanPinGroupEntry 7 }

cucsFabricLanPinGroupPolicyLevel OBJECT-TYPE
    SYNTAX       Gauge32
    MAX-ACCESS   read-only
    STATUS       current
    DESCRIPTION
        "Cisco UCS fabric:LanPinGroup:policyLevel managed object property"
    ::= { cucsFabricLanPinGroupEntry 8 }

cucsFabricLanPinGroupPolicyOwner OBJECT-TYPE
    SYNTAX       CucsPolicyPolicyOwner
    MAX-ACCESS   read-only
    STATUS       current
    DESCRIPTION
        "Cisco UCS fabric:LanPinGroup:policyOwner managed object property"
    ::= { cucsFabricLanPinGroupEntry 9 }

cucsFabricLanPinTargetTable OBJECT-TYPE
    SYNTAX           SEQUENCE OF CucsFabricLanPinTargetEntry
    MAX-ACCESS       not-accessible
    STATUS           current
    DESCRIPTION
        "Cisco UCS fabric:LanPinTarget managed object table"
    ::= { cucsFabricObjects 46 }

cucsFabricLanPinTargetEntry OBJECT-TYPE
    SYNTAX           CucsFabricLanPinTargetEntry
    MAX-ACCESS       not-accessible
    STATUS           current
    DESCRIPTION
        "Entry for the cucsFabricLanPinTargetTable table."
    INDEX { cucsFabricLanPinTargetInstanceId }
    ::= { cucsFabricLanPinTargetTable 1 }

CucsFabricLanPinTargetEntry ::= SEQUENCE {
    cucsFabricLanPinTargetInstanceId                                 CucsManagedObjectId,
    cucsFabricLanPinTargetDn                                         CucsManagedObjectDn,
    cucsFabricLanPinTargetRn                                         SnmpAdminString,
    cucsFabricLanPinTargetEpDn                                       SnmpAdminString,
    cucsFabricLanPinTargetFabricId                                   SnmpAdminString,
    cucsFabricLanPinTargetTargetStatus                               CucsFabricTargetStatus,
    cucsFabricLanPinTargetAggrPortId                                 CucsFabricPinTargetAggrPortId,
    cucsFabricLanPinTargetPortId                                     CucsFabricPinTargetPortId,
    cucsFabricLanPinTargetSlotId                                     CucsFabricPinTargetSlotId
}

cucsFabricLanPinTargetInstanceId OBJECT-TYPE
    SYNTAX       CucsManagedObjectId
    MAX-ACCESS   not-accessible
    STATUS       current
    DESCRIPTION
        "Instance identifier of the managed object."
    ::= { cucsFabricLanPinTargetEntry 1 }

cucsFabricLanPinTargetDn OBJECT-TYPE
    SYNTAX       CucsManagedObjectDn
    MAX-ACCESS   read-only
    STATUS       current
    DESCRIPTION
        "Cisco UCS fabric:LanPinTarget:dn managed object property"
    ::= { cucsFabricLanPinTargetEntry 2 }

cucsFabricLanPinTargetRn OBJECT-TYPE
    SYNTAX       SnmpAdminString
    MAX-ACCESS   read-only
    STATUS       current
    DESCRIPTION
        "Cisco UCS fabric:LanPinTarget:rn managed object property"
    ::= { cucsFabricLanPinTargetEntry 3 }

cucsFabricLanPinTargetEpDn OBJECT-TYPE
    SYNTAX       SnmpAdminString
    MAX-ACCESS   read-only
    STATUS       current
    DESCRIPTION
        "Cisco UCS fabric:LanPinTarget:epDn managed object property"
    ::= { cucsFabricLanPinTargetEntry 4 }

cucsFabricLanPinTargetFabricId OBJECT-TYPE
    SYNTAX       SnmpAdminString
    MAX-ACCESS   read-only
    STATUS       current
    DESCRIPTION
        "Cisco UCS fabric:LanPinTarget:fabricId managed object property"
    ::= { cucsFabricLanPinTargetEntry 5 }

cucsFabricLanPinTargetTargetStatus OBJECT-TYPE
    SYNTAX       CucsFabricTargetStatus
    MAX-ACCESS   read-only
    STATUS       current
    DESCRIPTION
        "Cisco UCS fabric:LanPinTarget:targetStatus managed
        object property"
    ::= { cucsFabricLanPinTargetEntry 6 }

cucsFabricLanPinTargetAggrPortId OBJECT-TYPE
    SYNTAX       CucsFabricPinTargetAggrPortId
    MAX-ACCESS   read-only
    STATUS       current
    DESCRIPTION
        "Cisco UCS fabric:LanPinTarget:aggrPortId managed object property"
    ::= { cucsFabricLanPinTargetEntry 7 }

cucsFabricLanPinTargetPortId OBJECT-TYPE
    SYNTAX       CucsFabricPinTargetPortId
    MAX-ACCESS   read-only
    STATUS       current
    DESCRIPTION
        "Cisco UCS fabric:LanPinTarget:portId managed object property"
    ::= { cucsFabricLanPinTargetEntry 8 }

cucsFabricLanPinTargetSlotId OBJECT-TYPE
    SYNTAX       CucsFabricPinTargetSlotId
    MAX-ACCESS   read-only
    STATUS       current
    DESCRIPTION
        "Cisco UCS fabric:LanPinTarget:slotId managed object property"
    ::= { cucsFabricLanPinTargetEntry 9 }

cucsFabricLastAckedSlotTable OBJECT-TYPE
    SYNTAX           SEQUENCE OF CucsFabricLastAckedSlotEntry
    MAX-ACCESS       not-accessible
    STATUS           current
    DESCRIPTION
        "Cisco UCS fabric:LastAckedSlot managed object table"
    ::= { cucsFabricObjects 47 }

cucsFabricLastAckedSlotEntry OBJECT-TYPE
    SYNTAX           CucsFabricLastAckedSlotEntry
    MAX-ACCESS       not-accessible
    STATUS           current
    DESCRIPTION
        "Entry for the cucsFabricLastAckedSlotTable table."
    INDEX { cucsFabricLastAckedSlotInstanceId }
    ::= { cucsFabricLastAckedSlotTable 1 }

CucsFabricLastAckedSlotEntry ::= SEQUENCE {
    cucsFabricLastAckedSlotInstanceId                                CucsManagedObjectId,
    cucsFabricLastAckedSlotDn                                        CucsManagedObjectDn,
    cucsFabricLastAckedSlotRn                                        SnmpAdminString,
    cucsFabricLastAckedSlotChassisId                                 Gauge32,
    cucsFabricLastAckedSlotSlotId                                    Gauge32,
    cucsFabricLastAckedSlotSwitchId                                  CucsNetworkSwitchId,
    cucsFabricLastAckedSlotBoardAggregationRole                      CucsEquipmentBoardAggregationRole,
    cucsFabricLastAckedSlotServerInstanceId                          Gauge32
}

cucsFabricLastAckedSlotInstanceId OBJECT-TYPE
    SYNTAX       CucsManagedObjectId
    MAX-ACCESS   not-accessible
    STATUS       current
    DESCRIPTION
        "Instance identifier of the managed object."
    ::= { cucsFabricLastAckedSlotEntry 1 }

cucsFabricLastAckedSlotDn OBJECT-TYPE
    SYNTAX       CucsManagedObjectDn
    MAX-ACCESS   read-only
    STATUS       current
    DESCRIPTION
        "Cisco UCS fabric:LastAckedSlot:dn managed object property"
    ::= { cucsFabricLastAckedSlotEntry 2 }

cucsFabricLastAckedSlotRn OBJECT-TYPE
    SYNTAX       SnmpAdminString
    MAX-ACCESS   read-only
    STATUS       current
    DESCRIPTION
        "Cisco UCS fabric:LastAckedSlot:rn managed object property"
    ::= { cucsFabricLastAckedSlotEntry 3 }

cucsFabricLastAckedSlotChassisId OBJECT-TYPE
    SYNTAX       Gauge32
    MAX-ACCESS   read-only
    STATUS       current
    DESCRIPTION
        "Cisco UCS fabric:LastAckedSlot:chassisId managed object property"
    ::= { cucsFabricLastAckedSlotEntry 4 }

cucsFabricLastAckedSlotSlotId OBJECT-TYPE
    SYNTAX       Gauge32
    MAX-ACCESS   read-only
    STATUS       current
    DESCRIPTION
        "Cisco UCS fabric:LastAckedSlot:slotId managed object property"
    ::= { cucsFabricLastAckedSlotEntry 5 }

cucsFabricLastAckedSlotSwitchId OBJECT-TYPE
    SYNTAX       CucsNetworkSwitchId
    MAX-ACCESS   read-only
    STATUS       current
    DESCRIPTION
        "Cisco UCS fabric:LastAckedSlot:switchId managed object property"
    ::= { cucsFabricLastAckedSlotEntry 6 }

cucsFabricLastAckedSlotBoardAggregationRole OBJECT-TYPE
    SYNTAX       CucsEquipmentBoardAggregationRole
    MAX-ACCESS   read-only
    STATUS       current
    DESCRIPTION
        "Cisco UCS fabric:LastAckedSlot:boardAggregationRole
        managed object property"
    ::= { cucsFabricLastAckedSlotEntry 7 }

cucsFabricLastAckedSlotServerInstanceId OBJECT-TYPE
    SYNTAX       Gauge32
    MAX-ACCESS   read-only
    STATUS       current
    DESCRIPTION
        "Cisco UCS fabric:LastAckedSlot:serverInstanceId
        managed object property"
    ::= { cucsFabricLastAckedSlotEntry 8 }

cucsFabricLocaleTable OBJECT-TYPE
    SYNTAX           SEQUENCE OF CucsFabricLocaleEntry
    MAX-ACCESS       not-accessible
    STATUS           current
    DESCRIPTION
        "Cisco UCS fabric:Locale managed object table"
    ::= { cucsFabricObjects 48 }

cucsFabricLocaleEntry OBJECT-TYPE
    SYNTAX           CucsFabricLocaleEntry
    MAX-ACCESS       not-accessible
    STATUS           current
    DESCRIPTION
        "Entry for the cucsFabricLocaleTable table."
    INDEX { cucsFabricLocaleInstanceId }
    ::= { cucsFabricLocaleTable 1 }

CucsFabricLocaleEntry ::= SEQUENCE {
    cucsFabricLocaleInstanceId                                       CucsManagedObjectId,
    cucsFabricLocaleDn                                               CucsManagedObjectDn,
    cucsFabricLocaleRn                                               SnmpAdminString,
    cucsFabricLocaleCType                                            Gauge32,
    cucsFabricLocaleChassisId                                        Gauge32,
    cucsFabricLocaleLocale                                           CucsNetworkLocale,
    cucsFabricLocaleName                                             SnmpAdminString,
    cucsFabricLocaleSide                                             CucsNetworkSide,
    cucsFabricLocaleSlotId                                           Gauge32,
    cucsFabricLocaleSwitchId                                         CucsNetworkSwitchId,
    cucsFabricLocaleTransport                                        CucsNetworkTransport,
    cucsFabricLocaleType                                             CucsNetworkConnectionType,
    cucsFabricLocaleEvacState                                        CucsEquipmentEvacState
}

cucsFabricLocaleInstanceId OBJECT-TYPE
    SYNTAX       CucsManagedObjectId
    MAX-ACCESS   not-accessible
    STATUS       current
    DESCRIPTION
        "Instance identifier of the managed object."
    ::= { cucsFabricLocaleEntry 1 }

cucsFabricLocaleDn OBJECT-TYPE
    SYNTAX       CucsManagedObjectDn
    MAX-ACCESS   read-only
    STATUS       current
    DESCRIPTION
        "Cisco UCS fabric:Locale:dn managed object property"
    ::= { cucsFabricLocaleEntry 2 }

cucsFabricLocaleRn OBJECT-TYPE
    SYNTAX       SnmpAdminString
    MAX-ACCESS   read-only
    STATUS       current
    DESCRIPTION
        "Cisco UCS fabric:Locale:rn managed object property"
    ::= { cucsFabricLocaleEntry 3 }

cucsFabricLocaleCType OBJECT-TYPE
    SYNTAX       Gauge32
    MAX-ACCESS   read-only
    STATUS       current
    DESCRIPTION
        "Cisco UCS fabric:Locale:cType managed object property"
    ::= { cucsFabricLocaleEntry 4 }

cucsFabricLocaleChassisId OBJECT-TYPE
    SYNTAX       Gauge32
    MAX-ACCESS   read-only
    STATUS       current
    DESCRIPTION
        "Cisco UCS fabric:Locale:chassisId managed object property"
    ::= { cucsFabricLocaleEntry 5 }

cucsFabricLocaleLocale OBJECT-TYPE
    SYNTAX       CucsNetworkLocale
    MAX-ACCESS   read-only
    STATUS       current
    DESCRIPTION
        "Cisco UCS fabric:Locale:locale managed object property"
    ::= { cucsFabricLocaleEntry 6 }

cucsFabricLocaleName OBJECT-TYPE
    SYNTAX       SnmpAdminString
    MAX-ACCESS   read-only
    STATUS       current
    DESCRIPTION
        "Cisco UCS fabric:Locale:name managed object property"
    ::= { cucsFabricLocaleEntry 7 }

cucsFabricLocaleSide OBJECT-TYPE
    SYNTAX       CucsNetworkSide
    MAX-ACCESS   read-only
    STATUS       current
    DESCRIPTION
        "Cisco UCS fabric:Locale:side managed object property"
    ::= { cucsFabricLocaleEntry 8 }

cucsFabricLocaleSlotId OBJECT-TYPE
    SYNTAX       Gauge32
    MAX-ACCESS   read-only
    STATUS       current
    DESCRIPTION
        "Cisco UCS fabric:Locale:slotId managed object property"
    ::= { cucsFabricLocaleEntry 9 }

cucsFabricLocaleSwitchId OBJECT-TYPE
    SYNTAX       CucsNetworkSwitchId
    MAX-ACCESS   read-only
    STATUS       current
    DESCRIPTION
        "Cisco UCS fabric:Locale:switchId managed object property"
    ::= { cucsFabricLocaleEntry 10 }

cucsFabricLocaleTransport OBJECT-TYPE
    SYNTAX       CucsNetworkTransport
    MAX-ACCESS   read-only
    STATUS       current
    DESCRIPTION
        "Cisco UCS fabric:Locale:transport managed object property"
    ::= { cucsFabricLocaleEntry 11 }

cucsFabricLocaleType OBJECT-TYPE
    SYNTAX       CucsNetworkConnectionType
    MAX-ACCESS   read-only
    STATUS       current
    DESCRIPTION
        "Cisco UCS fabric:Locale:type managed object property"
    ::= { cucsFabricLocaleEntry 12 }

cucsFabricLocaleEvacState OBJECT-TYPE
    SYNTAX       CucsEquipmentEvacState
    MAX-ACCESS   read-only
    STATUS       current
    DESCRIPTION
        "Cisco UCS fabric:Locale:evacState managed object property"
    ::= { cucsFabricLocaleEntry 13 }

cucsFabricMulticastPolicyTable OBJECT-TYPE
    SYNTAX           SEQUENCE OF CucsFabricMulticastPolicyEntry
    MAX-ACCESS       not-accessible
    STATUS           current
    DESCRIPTION
        "Cisco UCS fabric:MulticastPolicy managed object table"
    ::= { cucsFabricObjects 85 }

cucsFabricMulticastPolicyEntry OBJECT-TYPE
    SYNTAX           CucsFabricMulticastPolicyEntry
    MAX-ACCESS       not-accessible
    STATUS           current
    DESCRIPTION
        "Entry for the cucsFabricMulticastPolicyTable table."
    INDEX { cucsFabricMulticastPolicyInstanceId }
    ::= { cucsFabricMulticastPolicyTable 1 }

CucsFabricMulticastPolicyEntry ::= SEQUENCE {
    cucsFabricMulticastPolicyInstanceId                              CucsManagedObjectId,
    cucsFabricMulticastPolicyDn                                      CucsManagedObjectDn,
    cucsFabricMulticastPolicyRn                                      SnmpAdminString,
    cucsFabricMulticastPolicyDescr                                   SnmpAdminString,
    cucsFabricMulticastPolicyIntId                                   SnmpAdminString,
    cucsFabricMulticastPolicyName                                    SnmpAdminString,
    cucsFabricMulticastPolicyPolicyLevel                             Gauge32,
    cucsFabricMulticastPolicyPolicyOwner                             CucsPolicyPolicyOwner,
    cucsFabricMulticastPolicyQuerierIpAddr                           InetAddressIPv4,
    cucsFabricMulticastPolicyQuerierState                            CucsFabricQuerierType,
    cucsFabricMulticastPolicySnoopingState                           CucsFabricSnoopingType,
    cucsFabricMulticastPolicyConfigQualifier                         CucsFabricPolicyConfigIssues,
    cucsFabricMulticastPolicyQuerierIpAddrPeer                       InetAddressIPv4
}

cucsFabricMulticastPolicyInstanceId OBJECT-TYPE
    SYNTAX       CucsManagedObjectId
    MAX-ACCESS   not-accessible
    STATUS       current
    DESCRIPTION
        "Instance identifier of the managed object."
    ::= { cucsFabricMulticastPolicyEntry 1 }

cucsFabricMulticastPolicyDn OBJECT-TYPE
    SYNTAX       CucsManagedObjectDn
    MAX-ACCESS   read-only
    STATUS       current
    DESCRIPTION
        "Cisco UCS fabric:MulticastPolicy:dn managed object property"
    ::= { cucsFabricMulticastPolicyEntry 2 }

cucsFabricMulticastPolicyRn OBJECT-TYPE
    SYNTAX       SnmpAdminString
    MAX-ACCESS   read-only
    STATUS       current
    DESCRIPTION
        "Cisco UCS fabric:MulticastPolicy:rn managed object property"
    ::= { cucsFabricMulticastPolicyEntry 3 }

cucsFabricMulticastPolicyDescr OBJECT-TYPE
    SYNTAX       SnmpAdminString
    MAX-ACCESS   read-only
    STATUS       current
    DESCRIPTION
        "Cisco UCS fabric:MulticastPolicy:descr managed object property"
    ::= { cucsFabricMulticastPolicyEntry 4 }

cucsFabricMulticastPolicyIntId OBJECT-TYPE
    SYNTAX       SnmpAdminString
    MAX-ACCESS   read-only
    STATUS       current
    DESCRIPTION
        "Cisco UCS fabric:MulticastPolicy:intId managed object property"
    ::= { cucsFabricMulticastPolicyEntry 5 }

cucsFabricMulticastPolicyName OBJECT-TYPE
    SYNTAX       SnmpAdminString
    MAX-ACCESS   read-only
    STATUS       current
    DESCRIPTION
        "Cisco UCS fabric:MulticastPolicy:name managed object property"
    ::= { cucsFabricMulticastPolicyEntry 6 }

cucsFabricMulticastPolicyPolicyLevel OBJECT-TYPE
    SYNTAX       Gauge32
    MAX-ACCESS   read-only
    STATUS       current
    DESCRIPTION
        "Cisco UCS fabric:MulticastPolicy:policyLevel managed
        object property"
    ::= { cucsFabricMulticastPolicyEntry 7 }

cucsFabricMulticastPolicyPolicyOwner OBJECT-TYPE
    SYNTAX       CucsPolicyPolicyOwner
    MAX-ACCESS   read-only
    STATUS       current
    DESCRIPTION
        "Cisco UCS fabric:MulticastPolicy:policyOwner managed
        object property"
    ::= { cucsFabricMulticastPolicyEntry 8 }

cucsFabricMulticastPolicyQuerierIpAddr OBJECT-TYPE
    SYNTAX       InetAddressIPv4
    MAX-ACCESS   read-only
    STATUS       current
    DESCRIPTION
        "Cisco UCS fabric:MulticastPolicy:querierIpAddr
        managed object property"
    ::= { cucsFabricMulticastPolicyEntry 9 }

cucsFabricMulticastPolicyQuerierState OBJECT-TYPE
    SYNTAX       CucsFabricQuerierType
    MAX-ACCESS   read-only
    STATUS       current
    DESCRIPTION
        "Cisco UCS fabric:MulticastPolicy:querierState
        managed object property"
    ::= { cucsFabricMulticastPolicyEntry 10 }

cucsFabricMulticastPolicySnoopingState OBJECT-TYPE
    SYNTAX       CucsFabricSnoopingType
    MAX-ACCESS   read-only
    STATUS       current
    DESCRIPTION
        "Cisco UCS fabric:MulticastPolicy:snoopingState
        managed object property"
    ::= { cucsFabricMulticastPolicyEntry 11 }

cucsFabricMulticastPolicyConfigQualifier OBJECT-TYPE
    SYNTAX       CucsFabricPolicyConfigIssues
    MAX-ACCESS   read-only
    STATUS       current
    DESCRIPTION
        "Cisco UCS fabric:MulticastPolicy:configQualifier
        managed object property"
    ::= { cucsFabricMulticastPolicyEntry 12 }

cucsFabricMulticastPolicyQuerierIpAddrPeer OBJECT-TYPE
    SYNTAX       InetAddressIPv4
    MAX-ACCESS   read-only
    STATUS       current
    DESCRIPTION
        "Cisco UCS fabric:MulticastPolicy:querierIpAddrPeer
        managed object property"
    ::= { cucsFabricMulticastPolicyEntry 13 }

cucsFabricNetGroupTable OBJECT-TYPE
    SYNTAX           SEQUENCE OF CucsFabricNetGroupEntry
    MAX-ACCESS       not-accessible
    STATUS           current
    DESCRIPTION
        "Cisco UCS fabric:NetGroup managed object table"
    ::= { cucsFabricObjects 86 }

cucsFabricNetGroupEntry OBJECT-TYPE
    SYNTAX           CucsFabricNetGroupEntry
    MAX-ACCESS       not-accessible
    STATUS           current
    DESCRIPTION
        "Entry for the cucsFabricNetGroupTable table."
    INDEX { cucsFabricNetGroupInstanceId }
    ::= { cucsFabricNetGroupTable 1 }

CucsFabricNetGroupEntry ::= SEQUENCE {
    cucsFabricNetGroupInstanceId                                     CucsManagedObjectId,
    cucsFabricNetGroupDn                                             CucsManagedObjectDn,
    cucsFabricNetGroupRn                                             SnmpAdminString,
    cucsFabricNetGroupAssigned                                       Gauge32,
    cucsFabricNetGroupAssignmentOrder                                CucsPoolPoolAssignmentOrder,
    cucsFabricNetGroupDescr                                          SnmpAdminString,
    cucsFabricNetGroupId                                             Gauge32,
    cucsFabricNetGroupIntId                                          SnmpAdminString,
    cucsFabricNetGroupName                                           SnmpAdminString,
    cucsFabricNetGroupNativeNet                                      SnmpAdminString,
    cucsFabricNetGroupNativeNetDn                                    SnmpAdminString,
    cucsFabricNetGroupOwner                                          CucsFabricOwner,
    cucsFabricNetGroupPeerDn                                         SnmpAdminString,
    cucsFabricNetGroupPolicyLevel                                    Gauge32,
    cucsFabricNetGroupPolicyOwner                                    CucsPolicyPolicyOwner,
    cucsFabricNetGroupSize                                           Gauge32,
    cucsFabricNetGroupSwitchId                                       CucsFabricNetGroupSwitchId,
    cucsFabricNetGroupType                                           CucsFabricNetGroupType,
    cucsFabricNetGroupConfigIssues                                   CucsFabricNetGroupConfigIssues
}

cucsFabricNetGroupInstanceId OBJECT-TYPE
    SYNTAX       CucsManagedObjectId
    MAX-ACCESS   not-accessible
    STATUS       current
    DESCRIPTION
        "Instance identifier of the managed object."
    ::= { cucsFabricNetGroupEntry 1 }

cucsFabricNetGroupDn OBJECT-TYPE
    SYNTAX       CucsManagedObjectDn
    MAX-ACCESS   read-only
    STATUS       current
    DESCRIPTION
        "Cisco UCS fabric:NetGroup:dn managed object property"
    ::= { cucsFabricNetGroupEntry 2 }

cucsFabricNetGroupRn OBJECT-TYPE
    SYNTAX       SnmpAdminString
    MAX-ACCESS   read-only
    STATUS       current
    DESCRIPTION
        "Cisco UCS fabric:NetGroup:rn managed object property"
    ::= { cucsFabricNetGroupEntry 3 }

cucsFabricNetGroupAssigned OBJECT-TYPE
    SYNTAX       Gauge32
    MAX-ACCESS   read-only
    STATUS       current
    DESCRIPTION
        "Cisco UCS fabric:NetGroup:assigned managed object property"
    ::= { cucsFabricNetGroupEntry 4 }

cucsFabricNetGroupAssignmentOrder OBJECT-TYPE
    SYNTAX       CucsPoolPoolAssignmentOrder
    MAX-ACCESS   read-only
    STATUS       current
    DESCRIPTION
        "Cisco UCS fabric:NetGroup:assignmentOrder managed
        object property"
    ::= { cucsFabricNetGroupEntry 5 }

cucsFabricNetGroupDescr OBJECT-TYPE
    SYNTAX       SnmpAdminString
    MAX-ACCESS   read-only
    STATUS       current
    DESCRIPTION
        "Cisco UCS fabric:NetGroup:descr managed object property"
    ::= { cucsFabricNetGroupEntry 6 }

cucsFabricNetGroupId OBJECT-TYPE
    SYNTAX       Gauge32
    MAX-ACCESS   read-only
    STATUS       current
    DESCRIPTION
        "Cisco UCS fabric:NetGroup:id managed object property"
    ::= { cucsFabricNetGroupEntry 7 }

cucsFabricNetGroupIntId OBJECT-TYPE
    SYNTAX       SnmpAdminString
    MAX-ACCESS   read-only
    STATUS       current
    DESCRIPTION
        "Cisco UCS fabric:NetGroup:intId managed object property"
    ::= { cucsFabricNetGroupEntry 8 }

cucsFabricNetGroupName OBJECT-TYPE
    SYNTAX       SnmpAdminString
    MAX-ACCESS   read-only
    STATUS       current
    DESCRIPTION
        "Cisco UCS fabric:NetGroup:name managed object property"
    ::= { cucsFabricNetGroupEntry 9 }

cucsFabricNetGroupNativeNet OBJECT-TYPE
    SYNTAX       SnmpAdminString
    MAX-ACCESS   read-only
    STATUS       current
    DESCRIPTION
        "Cisco UCS fabric:NetGroup:nativeNet managed object property"
    ::= { cucsFabricNetGroupEntry 10 }

cucsFabricNetGroupNativeNetDn OBJECT-TYPE
    SYNTAX       SnmpAdminString
    MAX-ACCESS   read-only
    STATUS       current
    DESCRIPTION
        "Cisco UCS fabric:NetGroup:nativeNetDn managed object property"
    ::= { cucsFabricNetGroupEntry 11 }

cucsFabricNetGroupOwner OBJECT-TYPE
    SYNTAX       CucsFabricOwner
    MAX-ACCESS   read-only
    STATUS       current
    DESCRIPTION
        "Cisco UCS fabric:NetGroup:owner managed object property"
    ::= { cucsFabricNetGroupEntry 12 }

cucsFabricNetGroupPeerDn OBJECT-TYPE
    SYNTAX       SnmpAdminString
    MAX-ACCESS   read-only
    STATUS       current
    DESCRIPTION
        "Cisco UCS fabric:NetGroup:peerDn managed object property"
    ::= { cucsFabricNetGroupEntry 13 }

cucsFabricNetGroupPolicyLevel OBJECT-TYPE
    SYNTAX       Gauge32
    MAX-ACCESS   read-only
    STATUS       current
    DESCRIPTION
        "Cisco UCS fabric:NetGroup:policyLevel managed object property"
    ::= { cucsFabricNetGroupEntry 14 }

cucsFabricNetGroupPolicyOwner OBJECT-TYPE
    SYNTAX       CucsPolicyPolicyOwner
    MAX-ACCESS   read-only
    STATUS       current
    DESCRIPTION
        "Cisco UCS fabric:NetGroup:policyOwner managed object property"
    ::= { cucsFabricNetGroupEntry 15 }

cucsFabricNetGroupSize OBJECT-TYPE
    SYNTAX       Gauge32
    MAX-ACCESS   read-only
    STATUS       current
    DESCRIPTION
        "Cisco UCS fabric:NetGroup:size managed object property"
    ::= { cucsFabricNetGroupEntry 16 }

cucsFabricNetGroupSwitchId OBJECT-TYPE
    SYNTAX       CucsFabricNetGroupSwitchId
    MAX-ACCESS   read-only
    STATUS       current
    DESCRIPTION
        "Cisco UCS fabric:NetGroup:switchId managed object property"
    ::= { cucsFabricNetGroupEntry 17 }

cucsFabricNetGroupType OBJECT-TYPE
    SYNTAX       CucsFabricNetGroupType
    MAX-ACCESS   read-only
    STATUS       current
    DESCRIPTION
        "Cisco UCS fabric:NetGroup:type managed object property"
    ::= { cucsFabricNetGroupEntry 18 }

cucsFabricNetGroupConfigIssues OBJECT-TYPE
    SYNTAX       CucsFabricNetGroupConfigIssues
    MAX-ACCESS   read-only
    STATUS       current
    DESCRIPTION
        "Cisco UCS fabric:NetGroup:configIssues managed object property"
    ::= { cucsFabricNetGroupEntry 21 }

cucsFabricNetflowCollectorTable OBJECT-TYPE
    SYNTAX           SEQUENCE OF CucsFabricNetflowCollectorEntry
    MAX-ACCESS       not-accessible
    STATUS           current
    DESCRIPTION
        "Cisco UCS fabric:NetflowCollector managed object table"
    ::= { cucsFabricObjects 109 }

cucsFabricNetflowCollectorEntry OBJECT-TYPE
    SYNTAX           CucsFabricNetflowCollectorEntry
    MAX-ACCESS       not-accessible
    STATUS           current
    DESCRIPTION
        "Entry for the cucsFabricNetflowCollectorTable table."
    INDEX { cucsFabricNetflowCollectorInstanceId }
    ::= { cucsFabricNetflowCollectorTable 1 }

CucsFabricNetflowCollectorEntry ::= SEQUENCE {
    cucsFabricNetflowCollectorInstanceId                             CucsManagedObjectId,
    cucsFabricNetflowCollectorDn                                     CucsManagedObjectDn,
    cucsFabricNetflowCollectorRn                                     SnmpAdminString,
    cucsFabricNetflowCollectorDescr                                  SnmpAdminString,
    cucsFabricNetflowCollectorFlowProtocol                           CucsFabricNetflowCollectorFlowProtocol,
    cucsFabricNetflowCollectorId                                     CucsNetworkSwitchId,
    cucsFabricNetflowCollectorLocale                                 CucsFabricFlowMonCollectorLocale,
    cucsFabricNetflowCollectorName                                   SnmpAdminString,
    cucsFabricNetflowCollectorPort                                   Gauge32,
    cucsFabricNetflowCollectorSourceVlan                             SnmpAdminString,
    cucsFabricNetflowCollectorSourceVlanDn                           SnmpAdminString,
    cucsFabricNetflowCollectorTransport                              CucsFabricEthLanFlowMonCollectorTransport,
    cucsFabricNetflowCollectorType                                   CucsFabricLanFlowMonCollectorType
}

cucsFabricNetflowCollectorInstanceId OBJECT-TYPE
    SYNTAX       CucsManagedObjectId
    MAX-ACCESS   not-accessible
    STATUS       current
    DESCRIPTION
        "Instance identifier of the managed object."
    ::= { cucsFabricNetflowCollectorEntry 1 }

cucsFabricNetflowCollectorDn OBJECT-TYPE
    SYNTAX       CucsManagedObjectDn
    MAX-ACCESS   read-only
    STATUS       current
    DESCRIPTION
        "Cisco UCS fabric:NetflowCollector:dn managed object property"
    ::= { cucsFabricNetflowCollectorEntry 2 }

cucsFabricNetflowCollectorRn OBJECT-TYPE
    SYNTAX       SnmpAdminString
    MAX-ACCESS   read-only
    STATUS       current
    DESCRIPTION
        "Cisco UCS fabric:NetflowCollector:rn managed object property"
    ::= { cucsFabricNetflowCollectorEntry 3 }

cucsFabricNetflowCollectorDescr OBJECT-TYPE
    SYNTAX       SnmpAdminString
    MAX-ACCESS   read-only
    STATUS       current
    DESCRIPTION
        "Cisco UCS fabric:NetflowCollector:descr managed object property"
    ::= { cucsFabricNetflowCollectorEntry 4 }

cucsFabricNetflowCollectorFlowProtocol OBJECT-TYPE
    SYNTAX       CucsFabricNetflowCollectorFlowProtocol
    MAX-ACCESS   read-only
    STATUS       current
    DESCRIPTION
        "Cisco UCS fabric:NetflowCollector:flowProtocol
        managed object property"
    ::= { cucsFabricNetflowCollectorEntry 5 }

cucsFabricNetflowCollectorId OBJECT-TYPE
    SYNTAX       CucsNetworkSwitchId
    MAX-ACCESS   read-only
    STATUS       current
    DESCRIPTION
        "Cisco UCS fabric:NetflowCollector:id managed object property"
    ::= { cucsFabricNetflowCollectorEntry 6 }

cucsFabricNetflowCollectorLocale OBJECT-TYPE
    SYNTAX       CucsFabricFlowMonCollectorLocale
    MAX-ACCESS   read-only
    STATUS       current
    DESCRIPTION
        "Cisco UCS fabric:NetflowCollector:locale managed object property"
    ::= { cucsFabricNetflowCollectorEntry 7 }

cucsFabricNetflowCollectorName OBJECT-TYPE
    SYNTAX       SnmpAdminString
    MAX-ACCESS   read-only
    STATUS       current
    DESCRIPTION
        "Cisco UCS fabric:NetflowCollector:name managed object property"
    ::= { cucsFabricNetflowCollectorEntry 8 }

cucsFabricNetflowCollectorPort OBJECT-TYPE
    SYNTAX       Gauge32
    MAX-ACCESS   read-only
    STATUS       current
    DESCRIPTION
        "Cisco UCS fabric:NetflowCollector:port managed object property"
    ::= { cucsFabricNetflowCollectorEntry 9 }

cucsFabricNetflowCollectorSourceVlan OBJECT-TYPE
    SYNTAX       SnmpAdminString
    MAX-ACCESS   read-only
    STATUS       current
    DESCRIPTION
        "Cisco UCS fabric:NetflowCollector:sourceVlan managed
        object property"
    ::= { cucsFabricNetflowCollectorEntry 10 }

cucsFabricNetflowCollectorSourceVlanDn OBJECT-TYPE
    SYNTAX       SnmpAdminString
    MAX-ACCESS   read-only
    STATUS       current
    DESCRIPTION
        "Cisco UCS fabric:NetflowCollector:sourceVlanDn
        managed object property"
    ::= { cucsFabricNetflowCollectorEntry 11 }

cucsFabricNetflowCollectorTransport OBJECT-TYPE
    SYNTAX       CucsFabricEthLanFlowMonCollectorTransport
    MAX-ACCESS   read-only
    STATUS       current
    DESCRIPTION
        "Cisco UCS fabric:NetflowCollector:transport managed
        object property"
    ::= { cucsFabricNetflowCollectorEntry 12 }

cucsFabricNetflowCollectorType OBJECT-TYPE
    SYNTAX       CucsFabricLanFlowMonCollectorType
    MAX-ACCESS   read-only
    STATUS       current
    DESCRIPTION
        "Cisco UCS fabric:NetflowCollector:type managed object property"
    ::= { cucsFabricNetflowCollectorEntry 13 }

cucsFabricNetflowIPv4AddrTable OBJECT-TYPE
    SYNTAX           SEQUENCE OF CucsFabricNetflowIPv4AddrEntry
    MAX-ACCESS       not-accessible
    STATUS           current
    DESCRIPTION
        "Cisco UCS fabric:NetflowIPv4Addr managed object table"
    ::= { cucsFabricObjects 110 }

cucsFabricNetflowIPv4AddrEntry OBJECT-TYPE
    SYNTAX           CucsFabricNetflowIPv4AddrEntry
    MAX-ACCESS       not-accessible
    STATUS           current
    DESCRIPTION
        "Entry for the cucsFabricNetflowIPv4AddrTable table."
    INDEX { cucsFabricNetflowIPv4AddrInstanceId }
    ::= { cucsFabricNetflowIPv4AddrTable 1 }

CucsFabricNetflowIPv4AddrEntry ::= SEQUENCE {
    cucsFabricNetflowIPv4AddrInstanceId                              CucsManagedObjectId,
    cucsFabricNetflowIPv4AddrDn                                      CucsManagedObjectDn,
    cucsFabricNetflowIPv4AddrRn                                      SnmpAdminString,
    cucsFabricNetflowIPv4AddrAddr                                    InetAddressIPv4,
    cucsFabricNetflowIPv4AddrDefGw                                   InetAddressIPv4,
    cucsFabricNetflowIPv4AddrFabricId                                CucsNetworkSwitchId,
    cucsFabricNetflowIPv4AddrSubnet                                  InetAddressIPv4
}

cucsFabricNetflowIPv4AddrInstanceId OBJECT-TYPE
    SYNTAX       CucsManagedObjectId
    MAX-ACCESS   not-accessible
    STATUS       current
    DESCRIPTION
        "Instance identifier of the managed object."
    ::= { cucsFabricNetflowIPv4AddrEntry 1 }

cucsFabricNetflowIPv4AddrDn OBJECT-TYPE
    SYNTAX       CucsManagedObjectDn
    MAX-ACCESS   read-only
    STATUS       current
    DESCRIPTION
        "Cisco UCS fabric:NetflowIPv4Addr:dn managed object property"
    ::= { cucsFabricNetflowIPv4AddrEntry 2 }

cucsFabricNetflowIPv4AddrRn OBJECT-TYPE
    SYNTAX       SnmpAdminString
    MAX-ACCESS   read-only
    STATUS       current
    DESCRIPTION
        "Cisco UCS fabric:NetflowIPv4Addr:rn managed object property"
    ::= { cucsFabricNetflowIPv4AddrEntry 3 }

cucsFabricNetflowIPv4AddrAddr OBJECT-TYPE
    SYNTAX       InetAddressIPv4
    MAX-ACCESS   read-only
    STATUS       current
    DESCRIPTION
        "Cisco UCS fabric:NetflowIPv4Addr:addr managed object property"
    ::= { cucsFabricNetflowIPv4AddrEntry 4 }

cucsFabricNetflowIPv4AddrDefGw OBJECT-TYPE
    SYNTAX       InetAddressIPv4
    MAX-ACCESS   read-only
    STATUS       current
    DESCRIPTION
        "Cisco UCS fabric:NetflowIPv4Addr:defGw managed object property"
    ::= { cucsFabricNetflowIPv4AddrEntry 5 }

cucsFabricNetflowIPv4AddrFabricId OBJECT-TYPE
    SYNTAX       CucsNetworkSwitchId
    MAX-ACCESS   read-only
    STATUS       current
    DESCRIPTION
        "Cisco UCS fabric:NetflowIPv4Addr:fabricId managed
        object property"
    ::= { cucsFabricNetflowIPv4AddrEntry 6 }

cucsFabricNetflowIPv4AddrSubnet OBJECT-TYPE
    SYNTAX       InetAddressIPv4
    MAX-ACCESS   read-only
    STATUS       current
    DESCRIPTION
        "Cisco UCS fabric:NetflowIPv4Addr:subnet managed object property"
    ::= { cucsFabricNetflowIPv4AddrEntry 7 }

cucsFabricNetflowMonExporterTable OBJECT-TYPE
    SYNTAX           SEQUENCE OF CucsFabricNetflowMonExporterEntry
    MAX-ACCESS       not-accessible
    STATUS           current
    DESCRIPTION
        "Cisco UCS fabric:NetflowMonExporter managed object table"
    ::= { cucsFabricObjects 111 }

cucsFabricNetflowMonExporterEntry OBJECT-TYPE
    SYNTAX           CucsFabricNetflowMonExporterEntry
    MAX-ACCESS       not-accessible
    STATUS           current
    DESCRIPTION
        "Entry for the cucsFabricNetflowMonExporterTable table."
    INDEX { cucsFabricNetflowMonExporterInstanceId }
    ::= { cucsFabricNetflowMonExporterTable 1 }

CucsFabricNetflowMonExporterEntry ::= SEQUENCE {
    cucsFabricNetflowMonExporterInstanceId                           CucsManagedObjectId,
    cucsFabricNetflowMonExporterDn                                   CucsManagedObjectDn,
    cucsFabricNetflowMonExporterRn                                   SnmpAdminString,
    cucsFabricNetflowMonExporterDescr                                SnmpAdminString,
    cucsFabricNetflowMonExporterDscp                                 Gauge32,
    cucsFabricNetflowMonExporterExportInternal                       Gauge32,
    cucsFabricNetflowMonExporterExporterStatsTimeout                 Gauge32,
    cucsFabricNetflowMonExporterFlowExpProfile                       SnmpAdminString,
    cucsFabricNetflowMonExporterFlowMonCollector                     SnmpAdminString,
    cucsFabricNetflowMonExporterIntId                                SnmpAdminString,
    cucsFabricNetflowMonExporterInterfaceTableTimeout                Gauge32,
    cucsFabricNetflowMonExporterName                                 SnmpAdminString,
    cucsFabricNetflowMonExporterOperFlowExpProfile                   SnmpAdminString,
    cucsFabricNetflowMonExporterPolicyLevel                          Gauge32,
    cucsFabricNetflowMonExporterPolicyOwner                          CucsPolicyPolicyOwner,
    cucsFabricNetflowMonExporterProtocol                             CucsFabricNetflowMonExporterProtocol,
    cucsFabricNetflowMonExporterTemplateDataTimeout                  Gauge32,
    cucsFabricNetflowMonExporterTransport                            CucsFabricEthLanFlowMonExporterTransport,
    cucsFabricNetflowMonExporterTransportProtocol                    CucsFabricNFTransport,
    cucsFabricNetflowMonExporterType                                 CucsFabricLanFlowMonExporterType,
    cucsFabricNetflowMonExporterVersion                              CucsFabricNFExporterVersion
}

cucsFabricNetflowMonExporterInstanceId OBJECT-TYPE
    SYNTAX       CucsManagedObjectId
    MAX-ACCESS   not-accessible
    STATUS       current
    DESCRIPTION
        "Instance identifier of the managed object."
    ::= { cucsFabricNetflowMonExporterEntry 1 }

cucsFabricNetflowMonExporterDn OBJECT-TYPE
    SYNTAX       CucsManagedObjectDn
    MAX-ACCESS   read-only
    STATUS       current
    DESCRIPTION
        "Cisco UCS fabric:NetflowMonExporter:dn managed object property"
    ::= { cucsFabricNetflowMonExporterEntry 2 }

cucsFabricNetflowMonExporterRn OBJECT-TYPE
    SYNTAX       SnmpAdminString
    MAX-ACCESS   read-only
    STATUS       current
    DESCRIPTION
        "Cisco UCS fabric:NetflowMonExporter:rn managed object property"
    ::= { cucsFabricNetflowMonExporterEntry 3 }

cucsFabricNetflowMonExporterDescr OBJECT-TYPE
    SYNTAX       SnmpAdminString
    MAX-ACCESS   read-only
    STATUS       current
    DESCRIPTION
        "Cisco UCS fabric:NetflowMonExporter:descr managed
        object property"
    ::= { cucsFabricNetflowMonExporterEntry 4 }

cucsFabricNetflowMonExporterDscp OBJECT-TYPE
    SYNTAX       Gauge32
    MAX-ACCESS   read-only
    STATUS       current
    DESCRIPTION
        "Cisco UCS fabric:NetflowMonExporter:dscp managed object property"
    ::= { cucsFabricNetflowMonExporterEntry 5 }

cucsFabricNetflowMonExporterExportInternal OBJECT-TYPE
    SYNTAX       Gauge32
    MAX-ACCESS   read-only
    STATUS       current
    DESCRIPTION
        "Cisco UCS fabric:NetflowMonExporter:exportInternal
        managed object property"
    ::= { cucsFabricNetflowMonExporterEntry 6 }

cucsFabricNetflowMonExporterExporterStatsTimeout OBJECT-TYPE
    SYNTAX       Gauge32
    MAX-ACCESS   read-only
    STATUS       current
    DESCRIPTION
        "Cisco UCS fabric:NetflowMonExporter:exporterStatsTimeout
        managed object property"
    ::= { cucsFabricNetflowMonExporterEntry 7 }

cucsFabricNetflowMonExporterFlowExpProfile OBJECT-TYPE
    SYNTAX       SnmpAdminString
    MAX-ACCESS   read-only
    STATUS       current
    DESCRIPTION
        "Cisco UCS fabric:NetflowMonExporter:flowExpProfile
        managed object property"
    ::= { cucsFabricNetflowMonExporterEntry 8 }

cucsFabricNetflowMonExporterFlowMonCollector OBJECT-TYPE
    SYNTAX       SnmpAdminString
    MAX-ACCESS   read-only
    STATUS       current
    DESCRIPTION
        "Cisco UCS fabric:NetflowMonExporter:flowMonCollector
        managed object property"
    ::= { cucsFabricNetflowMonExporterEntry 9 }

cucsFabricNetflowMonExporterIntId OBJECT-TYPE
    SYNTAX       SnmpAdminString
    MAX-ACCESS   read-only
    STATUS       current
    DESCRIPTION
        "Cisco UCS fabric:NetflowMonExporter:intId managed
        object property"
    ::= { cucsFabricNetflowMonExporterEntry 10 }

cucsFabricNetflowMonExporterInterfaceTableTimeout OBJECT-TYPE
    SYNTAX       Gauge32
    MAX-ACCESS   read-only
    STATUS       current
    DESCRIPTION
        "Cisco UCS fabric:NetflowMonExporter:interfaceTableTimeout
        managed object property"
    ::= { cucsFabricNetflowMonExporterEntry 11 }

cucsFabricNetflowMonExporterName OBJECT-TYPE
    SYNTAX       SnmpAdminString
    MAX-ACCESS   read-only
    STATUS       current
    DESCRIPTION
        "Cisco UCS fabric:NetflowMonExporter:name managed object property"
    ::= { cucsFabricNetflowMonExporterEntry 12 }

cucsFabricNetflowMonExporterOperFlowExpProfile OBJECT-TYPE
    SYNTAX       SnmpAdminString
    MAX-ACCESS   read-only
    STATUS       current
    DESCRIPTION
        "Cisco UCS fabric:NetflowMonExporter:operFlowExpProfile
        managed object property"
    ::= { cucsFabricNetflowMonExporterEntry 13 }

cucsFabricNetflowMonExporterPolicyLevel OBJECT-TYPE
    SYNTAX       Gauge32
    MAX-ACCESS   read-only
    STATUS       current
    DESCRIPTION
        "Cisco UCS fabric:NetflowMonExporter:policyLevel
        managed object property"
    ::= { cucsFabricNetflowMonExporterEntry 14 }

cucsFabricNetflowMonExporterPolicyOwner OBJECT-TYPE
    SYNTAX       CucsPolicyPolicyOwner
    MAX-ACCESS   read-only
    STATUS       current
    DESCRIPTION
        "Cisco UCS fabric:NetflowMonExporter:policyOwner
        managed object property"
    ::= { cucsFabricNetflowMonExporterEntry 15 }

cucsFabricNetflowMonExporterProtocol OBJECT-TYPE
    SYNTAX       CucsFabricNetflowMonExporterProtocol
    MAX-ACCESS   read-only
    STATUS       current
    DESCRIPTION
        "Cisco UCS fabric:NetflowMonExporter:protocol managed
        object property"
    ::= { cucsFabricNetflowMonExporterEntry 16 }

cucsFabricNetflowMonExporterTemplateDataTimeout OBJECT-TYPE
    SYNTAX       Gauge32
    MAX-ACCESS   read-only
    STATUS       current
    DESCRIPTION
        "Cisco UCS fabric:NetflowMonExporter:templateDataTimeout
        managed object property"
    ::= { cucsFabricNetflowMonExporterEntry 17 }

cucsFabricNetflowMonExporterTransport OBJECT-TYPE
    SYNTAX       CucsFabricEthLanFlowMonExporterTransport
    MAX-ACCESS   read-only
    STATUS       current
    DESCRIPTION
        "Cisco UCS fabric:NetflowMonExporter:transport
        managed object property"
    ::= { cucsFabricNetflowMonExporterEntry 18 }

cucsFabricNetflowMonExporterTransportProtocol OBJECT-TYPE
    SYNTAX       CucsFabricNFTransport
    MAX-ACCESS   read-only
    STATUS       current
    DESCRIPTION
        "Cisco UCS fabric:NetflowMonExporter:transportProtocol
        managed object property"
    ::= { cucsFabricNetflowMonExporterEntry 19 }

cucsFabricNetflowMonExporterType OBJECT-TYPE
    SYNTAX       CucsFabricLanFlowMonExporterType
    MAX-ACCESS   read-only
    STATUS       current
    DESCRIPTION
        "Cisco UCS fabric:NetflowMonExporter:type managed object property"
    ::= { cucsFabricNetflowMonExporterEntry 20 }

cucsFabricNetflowMonExporterVersion OBJECT-TYPE
    SYNTAX       CucsFabricNFExporterVersion
    MAX-ACCESS   read-only
    STATUS       current
    DESCRIPTION
        "Cisco UCS fabric:NetflowMonExporter:version managed
        object property"
    ::= { cucsFabricNetflowMonExporterEntry 21 }

cucsFabricNetflowMonExporterRefTable OBJECT-TYPE
    SYNTAX           SEQUENCE OF CucsFabricNetflowMonExporterRefEntry
    MAX-ACCESS       not-accessible
    STATUS           current
    DESCRIPTION
        "Cisco UCS fabric:NetflowMonExporterRef managed object table"
    ::= { cucsFabricObjects 112 }

cucsFabricNetflowMonExporterRefEntry OBJECT-TYPE
    SYNTAX           CucsFabricNetflowMonExporterRefEntry
    MAX-ACCESS       not-accessible
    STATUS           current
    DESCRIPTION
        "Entry for the cucsFabricNetflowMonExporterRefTable table."
    INDEX { cucsFabricNetflowMonExporterRefInstanceId }
    ::= { cucsFabricNetflowMonExporterRefTable 1 }

CucsFabricNetflowMonExporterRefEntry ::= SEQUENCE {
    cucsFabricNetflowMonExporterRefInstanceId                        CucsManagedObjectId,
    cucsFabricNetflowMonExporterRefDn                                CucsManagedObjectDn,
    cucsFabricNetflowMonExporterRefRn                                SnmpAdminString,
    cucsFabricNetflowMonExporterRefIndex                             Gauge32,
    cucsFabricNetflowMonExporterRefNfMonExporterName                 SnmpAdminString,
    cucsFabricNetflowMonExporterRefOperNfMonExporterName             SnmpAdminString,
    cucsFabricNetflowMonExporterRefSwitchId                          CucsNetworkSwitchId
}

cucsFabricNetflowMonExporterRefInstanceId OBJECT-TYPE
    SYNTAX       CucsManagedObjectId
    MAX-ACCESS   not-accessible
    STATUS       current
    DESCRIPTION
        "Instance identifier of the managed object."
    ::= { cucsFabricNetflowMonExporterRefEntry 1 }

cucsFabricNetflowMonExporterRefDn OBJECT-TYPE
    SYNTAX       CucsManagedObjectDn
    MAX-ACCESS   read-only
    STATUS       current
    DESCRIPTION
        "Cisco UCS fabric:NetflowMonExporterRef:dn managed
        object property"
    ::= { cucsFabricNetflowMonExporterRefEntry 2 }

cucsFabricNetflowMonExporterRefRn OBJECT-TYPE
    SYNTAX       SnmpAdminString
    MAX-ACCESS   read-only
    STATUS       current
    DESCRIPTION
        "Cisco UCS fabric:NetflowMonExporterRef:rn managed
        object property"
    ::= { cucsFabricNetflowMonExporterRefEntry 3 }

cucsFabricNetflowMonExporterRefIndex OBJECT-TYPE
    SYNTAX       Gauge32
    MAX-ACCESS   read-only
    STATUS       current
    DESCRIPTION
        "Cisco UCS fabric:NetflowMonExporterRef:index managed
        object property"
    ::= { cucsFabricNetflowMonExporterRefEntry 4 }

cucsFabricNetflowMonExporterRefNfMonExporterName OBJECT-TYPE
    SYNTAX       SnmpAdminString
    MAX-ACCESS   read-only
    STATUS       current
    DESCRIPTION
        "Cisco UCS fabric:NetflowMonExporterRef:nfMonExporterName
        managed object property"
    ::= { cucsFabricNetflowMonExporterRefEntry 5 }

cucsFabricNetflowMonExporterRefOperNfMonExporterName OBJECT-TYPE
    SYNTAX       SnmpAdminString
    MAX-ACCESS   read-only
    STATUS       current
    DESCRIPTION
        "Cisco UCS fabric:NetflowMonExporterRef:operNfMonExporterName
        managed object property"
    ::= { cucsFabricNetflowMonExporterRefEntry 6 }

cucsFabricNetflowMonExporterRefSwitchId OBJECT-TYPE
    SYNTAX       CucsNetworkSwitchId
    MAX-ACCESS   read-only
    STATUS       current
    DESCRIPTION
        "Cisco UCS fabric:NetflowMonExporterRef:switchId
        managed object property"
    ::= { cucsFabricNetflowMonExporterRefEntry 7 }

cucsFabricNetflowMonSessionTable OBJECT-TYPE
    SYNTAX           SEQUENCE OF CucsFabricNetflowMonSessionEntry
    MAX-ACCESS       not-accessible
    STATUS           current
    DESCRIPTION
        "Cisco UCS fabric:NetflowMonSession managed object table"
    ::= { cucsFabricObjects 113 }

cucsFabricNetflowMonSessionEntry OBJECT-TYPE
    SYNTAX           CucsFabricNetflowMonSessionEntry
    MAX-ACCESS       not-accessible
    STATUS           current
    DESCRIPTION
        "Entry for the cucsFabricNetflowMonSessionTable table."
    INDEX { cucsFabricNetflowMonSessionInstanceId }
    ::= { cucsFabricNetflowMonSessionTable 1 }

CucsFabricNetflowMonSessionEntry ::= SEQUENCE {
    cucsFabricNetflowMonSessionInstanceId                            CucsManagedObjectId,
    cucsFabricNetflowMonSessionDn                                    CucsManagedObjectDn,
    cucsFabricNetflowMonSessionRn                                    SnmpAdminString,
    cucsFabricNetflowMonSessionAdminState                            CucsFabricNetflowMonSessionAdminState,
    cucsFabricNetflowMonSessionConfigFailReason                      SnmpAdminString,
    cucsFabricNetflowMonSessionConfigQualifier                       CucsFabricNetflowConfigIssues,
    cucsFabricNetflowMonSessionDescr                                 SnmpAdminString,
    cucsFabricNetflowMonSessionId                                    CucsNetworkSwitchId,
    cucsFabricNetflowMonSessionIsConfigSuccess                       TruthValue,
    cucsFabricNetflowMonSessionLocale                                CucsFabricExternalLocale,
    cucsFabricNetflowMonSessionName                                  SnmpAdminString,
    cucsFabricNetflowMonSessionProtocol                              CucsFabricNetflowMonSessionProtocol,
    cucsFabricNetflowMonSessionSession                               Gauge32,
    cucsFabricNetflowMonSessionTransport                             CucsFabricEthLanFlowMonTransport,
    cucsFabricNetflowMonSessionType                                  CucsFabricLanFlowMonType
}

cucsFabricNetflowMonSessionInstanceId OBJECT-TYPE
    SYNTAX       CucsManagedObjectId
    MAX-ACCESS   not-accessible
    STATUS       current
    DESCRIPTION
        "Instance identifier of the managed object."
    ::= { cucsFabricNetflowMonSessionEntry 1 }

cucsFabricNetflowMonSessionDn OBJECT-TYPE
    SYNTAX       CucsManagedObjectDn
    MAX-ACCESS   read-only
    STATUS       current
    DESCRIPTION
        "Cisco UCS fabric:NetflowMonSession:dn managed object property"
    ::= { cucsFabricNetflowMonSessionEntry 2 }

cucsFabricNetflowMonSessionRn OBJECT-TYPE
    SYNTAX       SnmpAdminString
    MAX-ACCESS   read-only
    STATUS       current
    DESCRIPTION
        "Cisco UCS fabric:NetflowMonSession:rn managed object property"
    ::= { cucsFabricNetflowMonSessionEntry 3 }

cucsFabricNetflowMonSessionAdminState OBJECT-TYPE
    SYNTAX       CucsFabricNetflowMonSessionAdminState
    MAX-ACCESS   read-only
    STATUS       current
    DESCRIPTION
        "Cisco UCS fabric:NetflowMonSession:adminState
        managed object property"
    ::= { cucsFabricNetflowMonSessionEntry 4 }

cucsFabricNetflowMonSessionConfigFailReason OBJECT-TYPE
    SYNTAX       SnmpAdminString
    MAX-ACCESS   read-only
    STATUS       current
    DESCRIPTION
        "Cisco UCS fabric:NetflowMonSession:configFailReason
        managed object property"
    ::= { cucsFabricNetflowMonSessionEntry 5 }

cucsFabricNetflowMonSessionConfigQualifier OBJECT-TYPE
    SYNTAX       CucsFabricNetflowConfigIssues
    MAX-ACCESS   read-only
    STATUS       current
    DESCRIPTION
        "Cisco UCS fabric:NetflowMonSession:configQualifier
        managed object property"
    ::= { cucsFabricNetflowMonSessionEntry 6 }

cucsFabricNetflowMonSessionDescr OBJECT-TYPE
    SYNTAX       SnmpAdminString
    MAX-ACCESS   read-only
    STATUS       current
    DESCRIPTION
        "Cisco UCS fabric:NetflowMonSession:descr managed object property"
    ::= { cucsFabricNetflowMonSessionEntry 7 }

cucsFabricNetflowMonSessionId OBJECT-TYPE
    SYNTAX       CucsNetworkSwitchId
    MAX-ACCESS   read-only
    STATUS       current
    DESCRIPTION
        "Cisco UCS fabric:NetflowMonSession:id managed object property"
    ::= { cucsFabricNetflowMonSessionEntry 8 }

cucsFabricNetflowMonSessionIsConfigSuccess OBJECT-TYPE
    SYNTAX       TruthValue
    MAX-ACCESS   read-only
    STATUS       current
    DESCRIPTION
        "Cisco UCS fabric:NetflowMonSession:isConfigSuccess
        managed object property"
    ::= { cucsFabricNetflowMonSessionEntry 9 }

cucsFabricNetflowMonSessionLocale OBJECT-TYPE
    SYNTAX       CucsFabricExternalLocale
    MAX-ACCESS   read-only
    STATUS       current
    DESCRIPTION
        "Cisco UCS fabric:NetflowMonSession:locale managed
        object property"
    ::= { cucsFabricNetflowMonSessionEntry 10 }

cucsFabricNetflowMonSessionName OBJECT-TYPE
    SYNTAX       SnmpAdminString
    MAX-ACCESS   read-only
    STATUS       current
    DESCRIPTION
        "Cisco UCS fabric:NetflowMonSession:name managed object property"
    ::= { cucsFabricNetflowMonSessionEntry 11 }

cucsFabricNetflowMonSessionProtocol OBJECT-TYPE
    SYNTAX       CucsFabricNetflowMonSessionProtocol
    MAX-ACCESS   read-only
    STATUS       current
    DESCRIPTION
        "Cisco UCS fabric:NetflowMonSession:protocol managed
        object property"
    ::= { cucsFabricNetflowMonSessionEntry 12 }

cucsFabricNetflowMonSessionSession OBJECT-TYPE
    SYNTAX       Gauge32
    MAX-ACCESS   read-only
    STATUS       current
    DESCRIPTION
        "Cisco UCS fabric:NetflowMonSession:session managed
        object property"
    ::= { cucsFabricNetflowMonSessionEntry 13 }

cucsFabricNetflowMonSessionTransport OBJECT-TYPE
    SYNTAX       CucsFabricEthLanFlowMonTransport
    MAX-ACCESS   read-only
    STATUS       current
    DESCRIPTION
        "Cisco UCS fabric:NetflowMonSession:transport managed
        object property"
    ::= { cucsFabricNetflowMonSessionEntry 14 }

cucsFabricNetflowMonSessionType OBJECT-TYPE
    SYNTAX       CucsFabricLanFlowMonType
    MAX-ACCESS   read-only
    STATUS       current
    DESCRIPTION
        "Cisco UCS fabric:NetflowMonSession:type managed object property"
    ::= { cucsFabricNetflowMonSessionEntry 15 }

cucsFabricNetflowMonSrcEpTable OBJECT-TYPE
    SYNTAX           SEQUENCE OF CucsFabricNetflowMonSrcEpEntry
    MAX-ACCESS       not-accessible
    STATUS           current
    DESCRIPTION
        "Cisco UCS fabric:NetflowMonSrcEp managed object table"
    ::= { cucsFabricObjects 114 }

cucsFabricNetflowMonSrcEpEntry OBJECT-TYPE
    SYNTAX           CucsFabricNetflowMonSrcEpEntry
    MAX-ACCESS       not-accessible
    STATUS           current
    DESCRIPTION
        "Entry for the cucsFabricNetflowMonSrcEpTable table."
    INDEX { cucsFabricNetflowMonSrcEpInstanceId }
    ::= { cucsFabricNetflowMonSrcEpTable 1 }

CucsFabricNetflowMonSrcEpEntry ::= SEQUENCE {
    cucsFabricNetflowMonSrcEpInstanceId                              CucsManagedObjectId,
    cucsFabricNetflowMonSrcEpDn                                      CucsManagedObjectDn,
    cucsFabricNetflowMonSrcEpRn                                      SnmpAdminString,
    cucsFabricNetflowMonSrcEpName                                    SnmpAdminString,
    cucsFabricNetflowMonSrcEpProtocol                                CucsFabricNetflowMonSrcEpProtocol,
    cucsFabricNetflowMonSrcEpSession                                 Gauge32,
    cucsFabricNetflowMonSrcEpTransport                               CucsFabricEthLanFlowMonSrcEpTransport,
    cucsFabricNetflowMonSrcEpType                                    CucsFabricLanFlowMonSrcEpType
}

cucsFabricNetflowMonSrcEpInstanceId OBJECT-TYPE
    SYNTAX       CucsManagedObjectId
    MAX-ACCESS   not-accessible
    STATUS       current
    DESCRIPTION
        "Instance identifier of the managed object."
    ::= { cucsFabricNetflowMonSrcEpEntry 1 }

cucsFabricNetflowMonSrcEpDn OBJECT-TYPE
    SYNTAX       CucsManagedObjectDn
    MAX-ACCESS   read-only
    STATUS       current
    DESCRIPTION
        "Cisco UCS fabric:NetflowMonSrcEp:dn managed object property"
    ::= { cucsFabricNetflowMonSrcEpEntry 2 }

cucsFabricNetflowMonSrcEpRn OBJECT-TYPE
    SYNTAX       SnmpAdminString
    MAX-ACCESS   read-only
    STATUS       current
    DESCRIPTION
        "Cisco UCS fabric:NetflowMonSrcEp:rn managed object property"
    ::= { cucsFabricNetflowMonSrcEpEntry 3 }

cucsFabricNetflowMonSrcEpName OBJECT-TYPE
    SYNTAX       SnmpAdminString
    MAX-ACCESS   read-only
    STATUS       current
    DESCRIPTION
        "Cisco UCS fabric:NetflowMonSrcEp:name managed object property"
    ::= { cucsFabricNetflowMonSrcEpEntry 4 }

cucsFabricNetflowMonSrcEpProtocol OBJECT-TYPE
    SYNTAX       CucsFabricNetflowMonSrcEpProtocol
    MAX-ACCESS   read-only
    STATUS       current
    DESCRIPTION
        "Cisco UCS fabric:NetflowMonSrcEp:protocol managed
        object property"
    ::= { cucsFabricNetflowMonSrcEpEntry 5 }

cucsFabricNetflowMonSrcEpSession OBJECT-TYPE
    SYNTAX       Gauge32
    MAX-ACCESS   read-only
    STATUS       current
    DESCRIPTION
        "Cisco UCS fabric:NetflowMonSrcEp:session managed object property"
    ::= { cucsFabricNetflowMonSrcEpEntry 6 }

cucsFabricNetflowMonSrcEpTransport OBJECT-TYPE
    SYNTAX       CucsFabricEthLanFlowMonSrcEpTransport
    MAX-ACCESS   read-only
    STATUS       current
    DESCRIPTION
        "Cisco UCS fabric:NetflowMonSrcEp:transport managed
        object property"
    ::= { cucsFabricNetflowMonSrcEpEntry 7 }

cucsFabricNetflowMonSrcEpType OBJECT-TYPE
    SYNTAX       CucsFabricLanFlowMonSrcEpType
    MAX-ACCESS   read-only
    STATUS       current
    DESCRIPTION
        "Cisco UCS fabric:NetflowMonSrcEp:type managed object property"
    ::= { cucsFabricNetflowMonSrcEpEntry 8 }

cucsFabricNetflowMonSrcRefTable OBJECT-TYPE
    SYNTAX           SEQUENCE OF CucsFabricNetflowMonSrcRefEntry
    MAX-ACCESS       not-accessible
    STATUS           current
    DESCRIPTION
        "Cisco UCS fabric:NetflowMonSrcRef managed object table"
    ::= { cucsFabricObjects 115 }

cucsFabricNetflowMonSrcRefEntry OBJECT-TYPE
    SYNTAX           CucsFabricNetflowMonSrcRefEntry
    MAX-ACCESS       not-accessible
    STATUS           current
    DESCRIPTION
        "Entry for the cucsFabricNetflowMonSrcRefTable table."
    INDEX { cucsFabricNetflowMonSrcRefInstanceId }
    ::= { cucsFabricNetflowMonSrcRefTable 1 }

CucsFabricNetflowMonSrcRefEntry ::= SEQUENCE {
    cucsFabricNetflowMonSrcRefInstanceId                             CucsManagedObjectId,
    cucsFabricNetflowMonSrcRefDn                                     CucsManagedObjectDn,
    cucsFabricNetflowMonSrcRefRn                                     SnmpAdminString,
    cucsFabricNetflowMonSrcRefId                                     Unsigned64,
    cucsFabricNetflowMonSrcRefProtocol                               CucsFabricNetflowMonSrcRefProtocol,
    cucsFabricNetflowMonSrcRefSourceDn                               SnmpAdminString,
    cucsFabricNetflowMonSrcRefSourceType                             CucsFabricEthFlowMonSourceType,
    cucsFabricNetflowMonSrcRefType                                   CucsFabricEthFlowMonSrcRefType
}

cucsFabricNetflowMonSrcRefInstanceId OBJECT-TYPE
    SYNTAX       CucsManagedObjectId
    MAX-ACCESS   not-accessible
    STATUS       current
    DESCRIPTION
        "Instance identifier of the managed object."
    ::= { cucsFabricNetflowMonSrcRefEntry 1 }

cucsFabricNetflowMonSrcRefDn OBJECT-TYPE
    SYNTAX       CucsManagedObjectDn
    MAX-ACCESS   read-only
    STATUS       current
    DESCRIPTION
        "Cisco UCS fabric:NetflowMonSrcRef:dn managed object property"
    ::= { cucsFabricNetflowMonSrcRefEntry 2 }

cucsFabricNetflowMonSrcRefRn OBJECT-TYPE
    SYNTAX       SnmpAdminString
    MAX-ACCESS   read-only
    STATUS       current
    DESCRIPTION
        "Cisco UCS fabric:NetflowMonSrcRef:rn managed object property"
    ::= { cucsFabricNetflowMonSrcRefEntry 3 }

cucsFabricNetflowMonSrcRefId OBJECT-TYPE
    SYNTAX       Unsigned64
    MAX-ACCESS   read-only
    STATUS       current
    DESCRIPTION
        "Cisco UCS fabric:NetflowMonSrcRef:id managed object property"
    ::= { cucsFabricNetflowMonSrcRefEntry 4 }

cucsFabricNetflowMonSrcRefProtocol OBJECT-TYPE
    SYNTAX       CucsFabricNetflowMonSrcRefProtocol
    MAX-ACCESS   read-only
    STATUS       current
    DESCRIPTION
        "Cisco UCS fabric:NetflowMonSrcRef:protocol managed
        object property"
    ::= { cucsFabricNetflowMonSrcRefEntry 5 }

cucsFabricNetflowMonSrcRefSourceDn OBJECT-TYPE
    SYNTAX       SnmpAdminString
    MAX-ACCESS   read-only
    STATUS       current
    DESCRIPTION
        "Cisco UCS fabric:NetflowMonSrcRef:sourceDn managed
        object property"
    ::= { cucsFabricNetflowMonSrcRefEntry 6 }

cucsFabricNetflowMonSrcRefSourceType OBJECT-TYPE
    SYNTAX       CucsFabricEthFlowMonSourceType
    MAX-ACCESS   read-only
    STATUS       current
    DESCRIPTION
        "Cisco UCS fabric:NetflowMonSrcRef:sourceType managed
        object property"
    ::= { cucsFabricNetflowMonSrcRefEntry 7 }

cucsFabricNetflowMonSrcRefType OBJECT-TYPE
    SYNTAX       CucsFabricEthFlowMonSrcRefType
    MAX-ACCESS   read-only
    STATUS       current
    DESCRIPTION
        "Cisco UCS fabric:NetflowMonSrcRef:type managed object property"
    ::= { cucsFabricNetflowMonSrcRefEntry 8 }

cucsFabricNetflowMonitorTable OBJECT-TYPE
    SYNTAX           SEQUENCE OF CucsFabricNetflowMonitorEntry
    MAX-ACCESS       not-accessible
    STATUS           current
    DESCRIPTION
        "Cisco UCS fabric:NetflowMonitor managed object table"
    ::= { cucsFabricObjects 116 }

cucsFabricNetflowMonitorEntry OBJECT-TYPE
    SYNTAX           CucsFabricNetflowMonitorEntry
    MAX-ACCESS       not-accessible
    STATUS           current
    DESCRIPTION
        "Entry for the cucsFabricNetflowMonitorTable table."
    INDEX { cucsFabricNetflowMonitorInstanceId }
    ::= { cucsFabricNetflowMonitorTable 1 }

CucsFabricNetflowMonitorEntry ::= SEQUENCE {
    cucsFabricNetflowMonitorInstanceId                               CucsManagedObjectId,
    cucsFabricNetflowMonitorDn                                       CucsManagedObjectDn,
    cucsFabricNetflowMonitorRn                                       SnmpAdminString,
    cucsFabricNetflowMonitorDescr                                    SnmpAdminString,
    cucsFabricNetflowMonitorFlowMonProtocol                          CucsFabricNetflowMonitorFlowMonProtocol,
    cucsFabricNetflowMonitorFlowMonRecordDef                         SnmpAdminString,
    cucsFabricNetflowMonitorFlowTimeoutPolicy                        SnmpAdminString,
    cucsFabricNetflowMonitorIntId                                    SnmpAdminString,
    cucsFabricNetflowMonitorName                                     SnmpAdminString,
    cucsFabricNetflowMonitorOperFlowMonRecordDef                     SnmpAdminString,
    cucsFabricNetflowMonitorOperFlowTimeoutPolicy                    SnmpAdminString,
    cucsFabricNetflowMonitorPolicyLevel                              Gauge32,
    cucsFabricNetflowMonitorPolicyOwner                              CucsPolicyPolicyOwner,
    cucsFabricNetflowMonitorTransport                                CucsFabricEthLanFlowMonitorTransport,
    cucsFabricNetflowMonitorType                                     CucsFabricLanFlowMonitorType
}

cucsFabricNetflowMonitorInstanceId OBJECT-TYPE
    SYNTAX       CucsManagedObjectId
    MAX-ACCESS   not-accessible
    STATUS       current
    DESCRIPTION
        "Instance identifier of the managed object."
    ::= { cucsFabricNetflowMonitorEntry 1 }

cucsFabricNetflowMonitorDn OBJECT-TYPE
    SYNTAX       CucsManagedObjectDn
    MAX-ACCESS   read-only
    STATUS       current
    DESCRIPTION
        "Cisco UCS fabric:NetflowMonitor:dn managed object property"
    ::= { cucsFabricNetflowMonitorEntry 2 }

cucsFabricNetflowMonitorRn OBJECT-TYPE
    SYNTAX       SnmpAdminString
    MAX-ACCESS   read-only
    STATUS       current
    DESCRIPTION
        "Cisco UCS fabric:NetflowMonitor:rn managed object property"
    ::= { cucsFabricNetflowMonitorEntry 3 }

cucsFabricNetflowMonitorDescr OBJECT-TYPE
    SYNTAX       SnmpAdminString
    MAX-ACCESS   read-only
    STATUS       current
    DESCRIPTION
        "Cisco UCS fabric:NetflowMonitor:descr managed object property"
    ::= { cucsFabricNetflowMonitorEntry 4 }

cucsFabricNetflowMonitorFlowMonProtocol OBJECT-TYPE
    SYNTAX       CucsFabricNetflowMonitorFlowMonProtocol
    MAX-ACCESS   read-only
    STATUS       current
    DESCRIPTION
        "Cisco UCS fabric:NetflowMonitor:flowMonProtocol
        managed object property"
    ::= { cucsFabricNetflowMonitorEntry 5 }

cucsFabricNetflowMonitorFlowMonRecordDef OBJECT-TYPE
    SYNTAX       SnmpAdminString
    MAX-ACCESS   read-only
    STATUS       current
    DESCRIPTION
        "Cisco UCS fabric:NetflowMonitor:flowMonRecordDef
        managed object property"
    ::= { cucsFabricNetflowMonitorEntry 6 }

cucsFabricNetflowMonitorFlowTimeoutPolicy OBJECT-TYPE
    SYNTAX       SnmpAdminString
    MAX-ACCESS   read-only
    STATUS       current
    DESCRIPTION
        "Cisco UCS fabric:NetflowMonitor:flowTimeoutPolicy
        managed object property"
    ::= { cucsFabricNetflowMonitorEntry 7 }

cucsFabricNetflowMonitorIntId OBJECT-TYPE
    SYNTAX       SnmpAdminString
    MAX-ACCESS   read-only
    STATUS       current
    DESCRIPTION
        "Cisco UCS fabric:NetflowMonitor:intId managed object property"
    ::= { cucsFabricNetflowMonitorEntry 8 }

cucsFabricNetflowMonitorName OBJECT-TYPE
    SYNTAX       SnmpAdminString
    MAX-ACCESS   read-only
    STATUS       current
    DESCRIPTION
        "Cisco UCS fabric:NetflowMonitor:name managed object property"
    ::= { cucsFabricNetflowMonitorEntry 9 }

cucsFabricNetflowMonitorOperFlowMonRecordDef OBJECT-TYPE
    SYNTAX       SnmpAdminString
    MAX-ACCESS   read-only
    STATUS       current
    DESCRIPTION
        "Cisco UCS fabric:NetflowMonitor:operFlowMonRecordDef
        managed object property"
    ::= { cucsFabricNetflowMonitorEntry 10 }

cucsFabricNetflowMonitorOperFlowTimeoutPolicy OBJECT-TYPE
    SYNTAX       SnmpAdminString
    MAX-ACCESS   read-only
    STATUS       current
    DESCRIPTION
        "Cisco UCS fabric:NetflowMonitor:operFlowTimeoutPolicy
        managed object property"
    ::= { cucsFabricNetflowMonitorEntry 11 }

cucsFabricNetflowMonitorPolicyLevel OBJECT-TYPE
    SYNTAX       Gauge32
    MAX-ACCESS   read-only
    STATUS       current
    DESCRIPTION
        "Cisco UCS fabric:NetflowMonitor:policyLevel managed
        object property"
    ::= { cucsFabricNetflowMonitorEntry 12 }

cucsFabricNetflowMonitorPolicyOwner OBJECT-TYPE
    SYNTAX       CucsPolicyPolicyOwner
    MAX-ACCESS   read-only
    STATUS       current
    DESCRIPTION
        "Cisco UCS fabric:NetflowMonitor:policyOwner managed
        object property"
    ::= { cucsFabricNetflowMonitorEntry 13 }

cucsFabricNetflowMonitorTransport OBJECT-TYPE
    SYNTAX       CucsFabricEthLanFlowMonitorTransport
    MAX-ACCESS   read-only
    STATUS       current
    DESCRIPTION
        "Cisco UCS fabric:NetflowMonitor:transport managed
        object property"
    ::= { cucsFabricNetflowMonitorEntry 14 }

cucsFabricNetflowMonitorType OBJECT-TYPE
    SYNTAX       CucsFabricLanFlowMonitorType
    MAX-ACCESS   read-only
    STATUS       current
    DESCRIPTION
        "Cisco UCS fabric:NetflowMonitor:type managed object property"
    ::= { cucsFabricNetflowMonitorEntry 15 }

cucsFabricNetflowMonitorRefTable OBJECT-TYPE
    SYNTAX           SEQUENCE OF CucsFabricNetflowMonitorRefEntry
    MAX-ACCESS       not-accessible
    STATUS           current
    DESCRIPTION
        "Cisco UCS fabric:NetflowMonitorRef managed object table"
    ::= { cucsFabricObjects 117 }

cucsFabricNetflowMonitorRefEntry OBJECT-TYPE
    SYNTAX           CucsFabricNetflowMonitorRefEntry
    MAX-ACCESS       not-accessible
    STATUS           current
    DESCRIPTION
        "Entry for the cucsFabricNetflowMonitorRefTable table."
    INDEX { cucsFabricNetflowMonitorRefInstanceId }
    ::= { cucsFabricNetflowMonitorRefTable 1 }

CucsFabricNetflowMonitorRefEntry ::= SEQUENCE {
    cucsFabricNetflowMonitorRefInstanceId                            CucsManagedObjectId,
    cucsFabricNetflowMonitorRefDn                                    CucsManagedObjectDn,
    cucsFabricNetflowMonitorRefRn                                    SnmpAdminString,
    cucsFabricNetflowMonitorRefDirection                             CucsFabricDirection,
    cucsFabricNetflowMonitorRefIndex                                 Gauge32,
    cucsFabricNetflowMonitorRefNfMonitorName                         SnmpAdminString,
    cucsFabricNetflowMonitorRefOperNfMonitorName                     SnmpAdminString,
    cucsFabricNetflowMonitorRefSwitchId                              CucsNetworkSwitchId
}

cucsFabricNetflowMonitorRefInstanceId OBJECT-TYPE
    SYNTAX       CucsManagedObjectId
    MAX-ACCESS   not-accessible
    STATUS       current
    DESCRIPTION
        "Instance identifier of the managed object."
    ::= { cucsFabricNetflowMonitorRefEntry 1 }

cucsFabricNetflowMonitorRefDn OBJECT-TYPE
    SYNTAX       CucsManagedObjectDn
    MAX-ACCESS   read-only
    STATUS       current
    DESCRIPTION
        "Cisco UCS fabric:NetflowMonitorRef:dn managed object property"
    ::= { cucsFabricNetflowMonitorRefEntry 2 }

cucsFabricNetflowMonitorRefRn OBJECT-TYPE
    SYNTAX       SnmpAdminString
    MAX-ACCESS   read-only
    STATUS       current
    DESCRIPTION
        "Cisco UCS fabric:NetflowMonitorRef:rn managed object property"
    ::= { cucsFabricNetflowMonitorRefEntry 3 }

cucsFabricNetflowMonitorRefDirection OBJECT-TYPE
    SYNTAX       CucsFabricDirection
    MAX-ACCESS   read-only
    STATUS       current
    DESCRIPTION
        "Cisco UCS fabric:NetflowMonitorRef:direction managed
        object property"
    ::= { cucsFabricNetflowMonitorRefEntry 4 }

cucsFabricNetflowMonitorRefIndex OBJECT-TYPE
    SYNTAX       Gauge32
    MAX-ACCESS   read-only
    STATUS       current
    DESCRIPTION
        "Cisco UCS fabric:NetflowMonitorRef:index managed object property"
    ::= { cucsFabricNetflowMonitorRefEntry 5 }

cucsFabricNetflowMonitorRefNfMonitorName OBJECT-TYPE
    SYNTAX       SnmpAdminString
    MAX-ACCESS   read-only
    STATUS       current
    DESCRIPTION
        "Cisco UCS fabric:NetflowMonitorRef:nfMonitorName
        managed object property"
    ::= { cucsFabricNetflowMonitorRefEntry 6 }

cucsFabricNetflowMonitorRefOperNfMonitorName OBJECT-TYPE
    SYNTAX       SnmpAdminString
    MAX-ACCESS   read-only
    STATUS       current
    DESCRIPTION
        "Cisco UCS fabric:NetflowMonitorRef:operNfMonitorName
        managed object property"
    ::= { cucsFabricNetflowMonitorRefEntry 7 }

cucsFabricNetflowMonitorRefSwitchId OBJECT-TYPE
    SYNTAX       CucsNetworkSwitchId
    MAX-ACCESS   read-only
    STATUS       current
    DESCRIPTION
        "Cisco UCS fabric:NetflowMonitorRef:switchId managed
        object property"
    ::= { cucsFabricNetflowMonitorRefEntry 8 }

cucsFabricNetflowTimeoutPolicyTable OBJECT-TYPE
    SYNTAX           SEQUENCE OF CucsFabricNetflowTimeoutPolicyEntry
    MAX-ACCESS       not-accessible
    STATUS           current
    DESCRIPTION
        "Cisco UCS fabric:NetflowTimeoutPolicy managed object table"
    ::= { cucsFabricObjects 118 }

cucsFabricNetflowTimeoutPolicyEntry OBJECT-TYPE
    SYNTAX           CucsFabricNetflowTimeoutPolicyEntry
    MAX-ACCESS       not-accessible
    STATUS           current
    DESCRIPTION
        "Entry for the cucsFabricNetflowTimeoutPolicyTable table."
    INDEX { cucsFabricNetflowTimeoutPolicyInstanceId }
    ::= { cucsFabricNetflowTimeoutPolicyTable 1 }

CucsFabricNetflowTimeoutPolicyEntry ::= SEQUENCE {
    cucsFabricNetflowTimeoutPolicyInstanceId                         CucsManagedObjectId,
    cucsFabricNetflowTimeoutPolicyDn                                 CucsManagedObjectDn,
    cucsFabricNetflowTimeoutPolicyRn                                 SnmpAdminString,
    cucsFabricNetflowTimeoutPolicyActiveTimeout                      Gauge32,
    cucsFabricNetflowTimeoutPolicyDescr                              SnmpAdminString,
    cucsFabricNetflowTimeoutPolicyInactiveTimeout                    Gauge32,
    cucsFabricNetflowTimeoutPolicyIntId                              SnmpAdminString,
    cucsFabricNetflowTimeoutPolicyName                               SnmpAdminString,
    cucsFabricNetflowTimeoutPolicyPolicyLevel                        Gauge32,
    cucsFabricNetflowTimeoutPolicyPolicyOwner                        CucsPolicyPolicyOwner
}

cucsFabricNetflowTimeoutPolicyInstanceId OBJECT-TYPE
    SYNTAX       CucsManagedObjectId
    MAX-ACCESS   not-accessible
    STATUS       current
    DESCRIPTION
        "Instance identifier of the managed object."
    ::= { cucsFabricNetflowTimeoutPolicyEntry 1 }

cucsFabricNetflowTimeoutPolicyDn OBJECT-TYPE
    SYNTAX       CucsManagedObjectDn
    MAX-ACCESS   read-only
    STATUS       current
    DESCRIPTION
        "Cisco UCS fabric:NetflowTimeoutPolicy:dn managed object property"
    ::= { cucsFabricNetflowTimeoutPolicyEntry 2 }

cucsFabricNetflowTimeoutPolicyRn OBJECT-TYPE
    SYNTAX       SnmpAdminString
    MAX-ACCESS   read-only
    STATUS       current
    DESCRIPTION
        "Cisco UCS fabric:NetflowTimeoutPolicy:rn managed object property"
    ::= { cucsFabricNetflowTimeoutPolicyEntry 3 }

cucsFabricNetflowTimeoutPolicyActiveTimeout OBJECT-TYPE
    SYNTAX       Gauge32
    MAX-ACCESS   read-only
    STATUS       current
    DESCRIPTION
        "Cisco UCS fabric:NetflowTimeoutPolicy:activeTimeout
        managed object property"
    ::= { cucsFabricNetflowTimeoutPolicyEntry 4 }

cucsFabricNetflowTimeoutPolicyDescr OBJECT-TYPE
    SYNTAX       SnmpAdminString
    MAX-ACCESS   read-only
    STATUS       current
    DESCRIPTION
        "Cisco UCS fabric:NetflowTimeoutPolicy:descr managed
        object property"
    ::= { cucsFabricNetflowTimeoutPolicyEntry 5 }

cucsFabricNetflowTimeoutPolicyInactiveTimeout OBJECT-TYPE
    SYNTAX       Gauge32
    MAX-ACCESS   read-only
    STATUS       current
    DESCRIPTION
        "Cisco UCS fabric:NetflowTimeoutPolicy:inactiveTimeout
        managed object property"
    ::= { cucsFabricNetflowTimeoutPolicyEntry 6 }

cucsFabricNetflowTimeoutPolicyIntId OBJECT-TYPE
    SYNTAX       SnmpAdminString
    MAX-ACCESS   read-only
    STATUS       current
    DESCRIPTION
        "Cisco UCS fabric:NetflowTimeoutPolicy:intId managed
        object property"
    ::= { cucsFabricNetflowTimeoutPolicyEntry 7 }

cucsFabricNetflowTimeoutPolicyName OBJECT-TYPE
    SYNTAX       SnmpAdminString
    MAX-ACCESS   read-only
    STATUS       current
    DESCRIPTION
        "Cisco UCS fabric:NetflowTimeoutPolicy:name managed
        object property"
    ::= { cucsFabricNetflowTimeoutPolicyEntry 8 }

cucsFabricNetflowTimeoutPolicyPolicyLevel OBJECT-TYPE
    SYNTAX       Gauge32
    MAX-ACCESS   read-only
    STATUS       current
    DESCRIPTION
        "Cisco UCS fabric:NetflowTimeoutPolicy:policyLevel
        managed object property"
    ::= { cucsFabricNetflowTimeoutPolicyEntry 9 }

cucsFabricNetflowTimeoutPolicyPolicyOwner OBJECT-TYPE
    SYNTAX       CucsPolicyPolicyOwner
    MAX-ACCESS   read-only
    STATUS       current
    DESCRIPTION
        "Cisco UCS fabric:NetflowTimeoutPolicy:policyOwner
        managed object property"
    ::= { cucsFabricNetflowTimeoutPolicyEntry 10 }

cucsFabricOrgVlanPolicyTable OBJECT-TYPE
    SYNTAX           SEQUENCE OF CucsFabricOrgVlanPolicyEntry
    MAX-ACCESS       not-accessible
    STATUS           current
    DESCRIPTION
        "Cisco UCS fabric:OrgVlanPolicy managed object table"
    ::= { cucsFabricObjects 87 }

cucsFabricOrgVlanPolicyEntry OBJECT-TYPE
    SYNTAX           CucsFabricOrgVlanPolicyEntry
    MAX-ACCESS       not-accessible
    STATUS           current
    DESCRIPTION
        "Entry for the cucsFabricOrgVlanPolicyTable table."
    INDEX { cucsFabricOrgVlanPolicyInstanceId }
    ::= { cucsFabricOrgVlanPolicyTable 1 }

CucsFabricOrgVlanPolicyEntry ::= SEQUENCE {
    cucsFabricOrgVlanPolicyInstanceId                                CucsManagedObjectId,
    cucsFabricOrgVlanPolicyDn                                        CucsManagedObjectDn,
    cucsFabricOrgVlanPolicyRn                                        SnmpAdminString,
    cucsFabricOrgVlanPolicyAdminState                                CucsFabricAdminState,
    cucsFabricOrgVlanPolicyName                                      SnmpAdminString
}

cucsFabricOrgVlanPolicyInstanceId OBJECT-TYPE
    SYNTAX       CucsManagedObjectId
    MAX-ACCESS   not-accessible
    STATUS       current
    DESCRIPTION
        "Instance identifier of the managed object."
    ::= { cucsFabricOrgVlanPolicyEntry 1 }

cucsFabricOrgVlanPolicyDn OBJECT-TYPE
    SYNTAX       CucsManagedObjectDn
    MAX-ACCESS   read-only
    STATUS       current
    DESCRIPTION
        "Cisco UCS fabric:OrgVlanPolicy:dn managed object property"
    ::= { cucsFabricOrgVlanPolicyEntry 2 }

cucsFabricOrgVlanPolicyRn OBJECT-TYPE
    SYNTAX       SnmpAdminString
    MAX-ACCESS   read-only
    STATUS       current
    DESCRIPTION
        "Cisco UCS fabric:OrgVlanPolicy:rn managed object property"
    ::= { cucsFabricOrgVlanPolicyEntry 3 }

cucsFabricOrgVlanPolicyAdminState OBJECT-TYPE
    SYNTAX       CucsFabricAdminState
    MAX-ACCESS   read-only
    STATUS       current
    DESCRIPTION
        "Cisco UCS fabric:OrgVlanPolicy:adminState managed
        object property"
    ::= { cucsFabricOrgVlanPolicyEntry 4 }

cucsFabricOrgVlanPolicyName OBJECT-TYPE
    SYNTAX       SnmpAdminString
    MAX-ACCESS   read-only
    STATUS       current
    DESCRIPTION
        "Cisco UCS fabric:OrgVlanPolicy:name managed object property"
    ::= { cucsFabricOrgVlanPolicyEntry 5 }

cucsFabricPathTable OBJECT-TYPE
    SYNTAX           SEQUENCE OF CucsFabricPathEntry
    MAX-ACCESS       not-accessible
    STATUS           current
    DESCRIPTION
        "Cisco UCS fabric:Path managed object table"
    ::= { cucsFabricObjects 49 }

cucsFabricPathEntry OBJECT-TYPE
    SYNTAX           CucsFabricPathEntry
    MAX-ACCESS       not-accessible
    STATUS           current
    DESCRIPTION
        "Entry for the cucsFabricPathTable table."
    INDEX { cucsFabricPathInstanceId }
    ::= { cucsFabricPathTable 1 }

CucsFabricPathEntry ::= SEQUENCE {
    cucsFabricPathInstanceId                                         CucsManagedObjectId,
    cucsFabricPathDn                                                 CucsManagedObjectDn,
    cucsFabricPathRn                                                 SnmpAdminString,
    cucsFabricPathCType                                              Gauge32,
    cucsFabricPathChassisId                                          Gauge32,
    cucsFabricPathEnacp                                              Gauge32,
    cucsFabricPathId                                                 Gauge32,
    cucsFabricPathLocale                                             CucsNetworkLocale,
    cucsFabricPathName                                               SnmpAdminString,
    cucsFabricPathNsSize                                             Gauge32,
    cucsFabricPathSide                                               CucsNetworkSide,
    cucsFabricPathSwitchId                                           CucsNetworkSwitchId,
    cucsFabricPathTransport                                          CucsNetworkTransport,
    cucsFabricPathType                                               CucsNetworkConnectionType,
    cucsFabricPathRetimerHifPortList                                 SnmpAdminString
}

cucsFabricPathInstanceId OBJECT-TYPE
    SYNTAX       CucsManagedObjectId
    MAX-ACCESS   not-accessible
    STATUS       current
    DESCRIPTION
        "Instance identifier of the managed object."
    ::= { cucsFabricPathEntry 1 }

cucsFabricPathDn OBJECT-TYPE
    SYNTAX       CucsManagedObjectDn
    MAX-ACCESS   read-only
    STATUS       current
    DESCRIPTION
        "Cisco UCS fabric:Path:dn managed object property"
    ::= { cucsFabricPathEntry 2 }

cucsFabricPathRn OBJECT-TYPE
    SYNTAX       SnmpAdminString
    MAX-ACCESS   read-only
    STATUS       current
    DESCRIPTION
        "Cisco UCS fabric:Path:rn managed object property"
    ::= { cucsFabricPathEntry 3 }

cucsFabricPathCType OBJECT-TYPE
    SYNTAX       Gauge32
    MAX-ACCESS   read-only
    STATUS       current
    DESCRIPTION
        "Cisco UCS fabric:Path:cType managed object property"
    ::= { cucsFabricPathEntry 4 }

cucsFabricPathChassisId OBJECT-TYPE
    SYNTAX       Gauge32
    MAX-ACCESS   read-only
    STATUS       current
    DESCRIPTION
        "Cisco UCS fabric:Path:chassisId managed object property"
    ::= { cucsFabricPathEntry 5 }

cucsFabricPathEnacp OBJECT-TYPE
    SYNTAX       Gauge32
    MAX-ACCESS   read-only
    STATUS       current
    DESCRIPTION
        "Cisco UCS fabric:Path:enacp managed object property"
    ::= { cucsFabricPathEntry 6 }

cucsFabricPathId OBJECT-TYPE
    SYNTAX       Gauge32
    MAX-ACCESS   read-only
    STATUS       current
    DESCRIPTION
        "Cisco UCS fabric:Path:id managed object property"
    ::= { cucsFabricPathEntry 7 }

cucsFabricPathLocale OBJECT-TYPE
    SYNTAX       CucsNetworkLocale
    MAX-ACCESS   read-only
    STATUS       current
    DESCRIPTION
        "Cisco UCS fabric:Path:locale managed object property"
    ::= { cucsFabricPathEntry 8 }

cucsFabricPathName OBJECT-TYPE
    SYNTAX       SnmpAdminString
    MAX-ACCESS   read-only
    STATUS       current
    DESCRIPTION
        "Cisco UCS fabric:Path:name managed object property"
    ::= { cucsFabricPathEntry 9 }

cucsFabricPathNsSize OBJECT-TYPE
    SYNTAX       Gauge32
    MAX-ACCESS   read-only
    STATUS       current
    DESCRIPTION
        "Cisco UCS fabric:Path:nsSize managed object property"
    ::= { cucsFabricPathEntry 10 }

cucsFabricPathSide OBJECT-TYPE
    SYNTAX       CucsNetworkSide
    MAX-ACCESS   read-only
    STATUS       current
    DESCRIPTION
        "Cisco UCS fabric:Path:side managed object property"
    ::= { cucsFabricPathEntry 11 }

cucsFabricPathSwitchId OBJECT-TYPE
    SYNTAX       CucsNetworkSwitchId
    MAX-ACCESS   read-only
    STATUS       current
    DESCRIPTION
        "Cisco UCS fabric:Path:switchId managed object property"
    ::= { cucsFabricPathEntry 12 }

cucsFabricPathTransport OBJECT-TYPE
    SYNTAX       CucsNetworkTransport
    MAX-ACCESS   read-only
    STATUS       current
    DESCRIPTION
        "Cisco UCS fabric:Path:transport managed object property"
    ::= { cucsFabricPathEntry 13 }

cucsFabricPathType OBJECT-TYPE
    SYNTAX       CucsNetworkConnectionType
    MAX-ACCESS   read-only
    STATUS       current
    DESCRIPTION
        "Cisco UCS fabric:Path:type managed object property"
    ::= { cucsFabricPathEntry 14 }

cucsFabricPathRetimerHifPortList OBJECT-TYPE
    SYNTAX       SnmpAdminString
    MAX-ACCESS   read-only
    STATUS       current
    DESCRIPTION
        "Cisco UCS fabric:Path:retimerHifPortList managed object property"
    ::= { cucsFabricPathEntry 15 }

cucsFabricPathConnTable OBJECT-TYPE
    SYNTAX           SEQUENCE OF CucsFabricPathConnEntry
    MAX-ACCESS       not-accessible
    STATUS           current
    DESCRIPTION
        "Cisco UCS fabric:PathConn managed object table"
    ::= { cucsFabricObjects 50 }

cucsFabricPathConnEntry OBJECT-TYPE
    SYNTAX           CucsFabricPathConnEntry
    MAX-ACCESS       not-accessible
    STATUS           current
    DESCRIPTION
        "Entry for the cucsFabricPathConnTable table."
    INDEX { cucsFabricPathConnInstanceId }
    ::= { cucsFabricPathConnTable 1 }

CucsFabricPathConnEntry ::= SEQUENCE {
    cucsFabricPathConnInstanceId                                     CucsManagedObjectId,
    cucsFabricPathConnDn                                             CucsManagedObjectDn,
    cucsFabricPathConnRn                                             SnmpAdminString,
    cucsFabricPathConnCType                                          Gauge32,
    cucsFabricPathConnLocale                                         CucsNetworkLocale,
    cucsFabricPathConnName                                           SnmpAdminString,
    cucsFabricPathConnTransport                                      CucsNetworkTransport,
    cucsFabricPathConnType                                           CucsNetworkConnectionType
}

cucsFabricPathConnInstanceId OBJECT-TYPE
    SYNTAX       CucsManagedObjectId
    MAX-ACCESS   not-accessible
    STATUS       current
    DESCRIPTION
        "Instance identifier of the managed object."
    ::= { cucsFabricPathConnEntry 1 }

cucsFabricPathConnDn OBJECT-TYPE
    SYNTAX       CucsManagedObjectDn
    MAX-ACCESS   read-only
    STATUS       current
    DESCRIPTION
        "Cisco UCS fabric:PathConn:dn managed object property"
    ::= { cucsFabricPathConnEntry 2 }

cucsFabricPathConnRn OBJECT-TYPE
    SYNTAX       SnmpAdminString
    MAX-ACCESS   read-only
    STATUS       current
    DESCRIPTION
        "Cisco UCS fabric:PathConn:rn managed object property"
    ::= { cucsFabricPathConnEntry 3 }

cucsFabricPathConnCType OBJECT-TYPE
    SYNTAX       Gauge32
    MAX-ACCESS   read-only
    STATUS       current
    DESCRIPTION
        "Cisco UCS fabric:PathConn:cType managed object property"
    ::= { cucsFabricPathConnEntry 4 }

cucsFabricPathConnLocale OBJECT-TYPE
    SYNTAX       CucsNetworkLocale
    MAX-ACCESS   read-only
    STATUS       current
    DESCRIPTION
        "Cisco UCS fabric:PathConn:locale managed object property"
    ::= { cucsFabricPathConnEntry 5 }

cucsFabricPathConnName OBJECT-TYPE
    SYNTAX       SnmpAdminString
    MAX-ACCESS   read-only
    STATUS       current
    DESCRIPTION
        "Cisco UCS fabric:PathConn:name managed object property"
    ::= { cucsFabricPathConnEntry 6 }

cucsFabricPathConnTransport OBJECT-TYPE
    SYNTAX       CucsNetworkTransport
    MAX-ACCESS   read-only
    STATUS       current
    DESCRIPTION
        "Cisco UCS fabric:PathConn:transport managed object property"
    ::= { cucsFabricPathConnEntry 7 }

cucsFabricPathConnType OBJECT-TYPE
    SYNTAX       CucsNetworkConnectionType
    MAX-ACCESS   read-only
    STATUS       current
    DESCRIPTION
        "Cisco UCS fabric:PathConn:type managed object property"
    ::= { cucsFabricPathConnEntry 8 }

cucsFabricPathEpTable OBJECT-TYPE
    SYNTAX           SEQUENCE OF CucsFabricPathEpEntry
    MAX-ACCESS       not-accessible
    STATUS           current
    DESCRIPTION
        "Cisco UCS fabric:PathEp managed object table"
    ::= { cucsFabricObjects 51 }

cucsFabricPathEpEntry OBJECT-TYPE
    SYNTAX           CucsFabricPathEpEntry
    MAX-ACCESS       not-accessible
    STATUS           current
    DESCRIPTION
        "Entry for the cucsFabricPathEpTable table."
    INDEX { cucsFabricPathEpInstanceId }
    ::= { cucsFabricPathEpTable 1 }

CucsFabricPathEpEntry ::= SEQUENCE {
    cucsFabricPathEpInstanceId                                       CucsManagedObjectId,
    cucsFabricPathEpDn                                               CucsManagedObjectDn,
    cucsFabricPathEpRn                                               SnmpAdminString,
    cucsFabricPathEpCType                                            Gauge32,
    cucsFabricPathEpChassisId                                        Gauge32,
    cucsFabricPathEpEpDn                                             SnmpAdminString,
    cucsFabricPathEpIfRole                                           CucsNetworkPortRole,
    cucsFabricPathEpIfType                                           CucsFabricPathEpIfType,
    cucsFabricPathEpLocale                                           CucsFabricPathEpLocale,
    cucsFabricPathEpName                                             SnmpAdminString,
    cucsFabricPathEpPeerDn                                           SnmpAdminString,
    cucsFabricPathEpPeerPortId                                       Gauge32,
    cucsFabricPathEpPeerSlotId                                       Gauge32,
    cucsFabricPathEpPortId                                           Gauge32,
    cucsFabricPathEpSide                                             CucsNetworkSide,
    cucsFabricPathEpSlotId                                           Gauge32,
    cucsFabricPathEpSwitchId                                         CucsNetworkSwitchId,
    cucsFabricPathEpTransport                                        CucsNetworkTransport,
    cucsFabricPathEpType                                             CucsNetworkConnectionType,
    cucsFabricPathEpDiagLldpTransmit                                 TruthValue,
    cucsFabricPathEpPeerChassisId                                    Gauge32,
    cucsFabricPathEpPeerMac                                          MacAddress,
    cucsFabricPathEpAggrPortId                                       Gauge32,
    cucsFabricPathEpPeerAggrPortId                                   Gauge32,
    cucsFabricPathEpPortGroupRole                                    Gauge32
}

cucsFabricPathEpInstanceId OBJECT-TYPE
    SYNTAX       CucsManagedObjectId
    MAX-ACCESS   not-accessible
    STATUS       current
    DESCRIPTION
        "Instance identifier of the managed object."
    ::= { cucsFabricPathEpEntry 1 }

cucsFabricPathEpDn OBJECT-TYPE
    SYNTAX       CucsManagedObjectDn
    MAX-ACCESS   read-only
    STATUS       current
    DESCRIPTION
        "Cisco UCS fabric:PathEp:dn managed object property"
    ::= { cucsFabricPathEpEntry 2 }

cucsFabricPathEpRn OBJECT-TYPE
    SYNTAX       SnmpAdminString
    MAX-ACCESS   read-only
    STATUS       current
    DESCRIPTION
        "Cisco UCS fabric:PathEp:rn managed object property"
    ::= { cucsFabricPathEpEntry 3 }

cucsFabricPathEpCType OBJECT-TYPE
    SYNTAX       Gauge32
    MAX-ACCESS   read-only
    STATUS       current
    DESCRIPTION
        "Cisco UCS fabric:PathEp:cType managed object property"
    ::= { cucsFabricPathEpEntry 4 }

cucsFabricPathEpChassisId OBJECT-TYPE
    SYNTAX       Gauge32
    MAX-ACCESS   read-only
    STATUS       current
    DESCRIPTION
        "Cisco UCS fabric:PathEp:chassisId managed object property"
    ::= { cucsFabricPathEpEntry 5 }

cucsFabricPathEpEpDn OBJECT-TYPE
    SYNTAX       SnmpAdminString
    MAX-ACCESS   read-only
    STATUS       current
    DESCRIPTION
        "Cisco UCS fabric:PathEp:epDn managed object property"
    ::= { cucsFabricPathEpEntry 6 }

cucsFabricPathEpIfRole OBJECT-TYPE
    SYNTAX       CucsNetworkPortRole
    MAX-ACCESS   read-only
    STATUS       current
    DESCRIPTION
        "Cisco UCS fabric:PathEp:ifRole managed object property"
    ::= { cucsFabricPathEpEntry 7 }

cucsFabricPathEpIfType OBJECT-TYPE
    SYNTAX       CucsFabricPathEpIfType
    MAX-ACCESS   read-only
    STATUS       current
    DESCRIPTION
        "Cisco UCS fabric:PathEp:ifType managed object property"
    ::= { cucsFabricPathEpEntry 8 }

cucsFabricPathEpLocale OBJECT-TYPE
    SYNTAX       CucsFabricPathEpLocale
    MAX-ACCESS   read-only
    STATUS       current
    DESCRIPTION
        "Cisco UCS fabric:PathEp:locale managed object property"
    ::= { cucsFabricPathEpEntry 9 }

cucsFabricPathEpName OBJECT-TYPE
    SYNTAX       SnmpAdminString
    MAX-ACCESS   read-only
    STATUS       current
    DESCRIPTION
        "Cisco UCS fabric:PathEp:name managed object property"
    ::= { cucsFabricPathEpEntry 10 }

cucsFabricPathEpPeerDn OBJECT-TYPE
    SYNTAX       SnmpAdminString
    MAX-ACCESS   read-only
    STATUS       current
    DESCRIPTION
        "Cisco UCS fabric:PathEp:peerDn managed object property"
    ::= { cucsFabricPathEpEntry 11 }

cucsFabricPathEpPeerPortId OBJECT-TYPE
    SYNTAX       Gauge32
    MAX-ACCESS   read-only
    STATUS       current
    DESCRIPTION
        "Cisco UCS fabric:PathEp:peerPortId managed object property"
    ::= { cucsFabricPathEpEntry 12 }

cucsFabricPathEpPeerSlotId OBJECT-TYPE
    SYNTAX       Gauge32
    MAX-ACCESS   read-only
    STATUS       current
    DESCRIPTION
        "Cisco UCS fabric:PathEp:peerSlotId managed object property"
    ::= { cucsFabricPathEpEntry 13 }

cucsFabricPathEpPortId OBJECT-TYPE
    SYNTAX       Gauge32
    MAX-ACCESS   read-only
    STATUS       current
    DESCRIPTION
        "Cisco UCS fabric:PathEp:portId managed object property"
    ::= { cucsFabricPathEpEntry 14 }

cucsFabricPathEpSide OBJECT-TYPE
    SYNTAX       CucsNetworkSide
    MAX-ACCESS   read-only
    STATUS       current
    DESCRIPTION
        "Cisco UCS fabric:PathEp:side managed object property"
    ::= { cucsFabricPathEpEntry 15 }

cucsFabricPathEpSlotId OBJECT-TYPE
    SYNTAX       Gauge32
    MAX-ACCESS   read-only
    STATUS       current
    DESCRIPTION
        "Cisco UCS fabric:PathEp:slotId managed object property"
    ::= { cucsFabricPathEpEntry 16 }

cucsFabricPathEpSwitchId OBJECT-TYPE
    SYNTAX       CucsNetworkSwitchId
    MAX-ACCESS   read-only
    STATUS       current
    DESCRIPTION
        "Cisco UCS fabric:PathEp:switchId managed object property"
    ::= { cucsFabricPathEpEntry 17 }

cucsFabricPathEpTransport OBJECT-TYPE
    SYNTAX       CucsNetworkTransport
    MAX-ACCESS   read-only
    STATUS       current
    DESCRIPTION
        "Cisco UCS fabric:PathEp:transport managed object property"
    ::= { cucsFabricPathEpEntry 18 }

cucsFabricPathEpType OBJECT-TYPE
    SYNTAX       CucsNetworkConnectionType
    MAX-ACCESS   read-only
    STATUS       current
    DESCRIPTION
        "Cisco UCS fabric:PathEp:type managed object property"
    ::= { cucsFabricPathEpEntry 19 }

cucsFabricPathEpDiagLldpTransmit OBJECT-TYPE
    SYNTAX       TruthValue
    MAX-ACCESS   read-only
    STATUS       current
    DESCRIPTION
        "Cisco UCS fabric:PathEp:diagLldpTransmit managed object property"
    ::= { cucsFabricPathEpEntry 20 }

cucsFabricPathEpPeerChassisId OBJECT-TYPE
    SYNTAX       Gauge32
    MAX-ACCESS   read-only
    STATUS       current
    DESCRIPTION
        "Cisco UCS fabric:PathEp:peerChassisId managed object property"
    ::= { cucsFabricPathEpEntry 21 }

cucsFabricPathEpPeerMac OBJECT-TYPE
    SYNTAX       MacAddress
    MAX-ACCESS   read-only
    STATUS       current
    DESCRIPTION
        "Cisco UCS fabric:PathEp:peerMac managed object property"
    ::= { cucsFabricPathEpEntry 22 }

cucsFabricPathEpAggrPortId OBJECT-TYPE
    SYNTAX       Gauge32
    MAX-ACCESS   read-only
    STATUS       current
    DESCRIPTION
        "Cisco UCS fabric:PathEp:aggrPortId managed object property"
    ::= { cucsFabricPathEpEntry 23 }

cucsFabricPathEpPeerAggrPortId OBJECT-TYPE
    SYNTAX       Gauge32
    MAX-ACCESS   read-only
    STATUS       current
    DESCRIPTION
        "Cisco UCS fabric:PathEp:peerAggrPortId managed object property"
    ::= { cucsFabricPathEpEntry 24 }

cucsFabricPathEpPortGroupRole OBJECT-TYPE
    SYNTAX       Gauge32
    MAX-ACCESS   read-only
    STATUS       current
    DESCRIPTION
        "Cisco UCS fabric:PathEp:portGroupRole managed object property"
    ::= { cucsFabricPathEpEntry 25 }

cucsFabricPoolableVlanTable OBJECT-TYPE
    SYNTAX           SEQUENCE OF CucsFabricPoolableVlanEntry
    MAX-ACCESS       not-accessible
    STATUS           current
    DESCRIPTION
        "Cisco UCS fabric:PoolableVlan managed object table"
    ::= { cucsFabricObjects 88 }

cucsFabricPoolableVlanEntry OBJECT-TYPE
    SYNTAX           CucsFabricPoolableVlanEntry
    MAX-ACCESS       not-accessible
    STATUS           current
    DESCRIPTION
        "Entry for the cucsFabricPoolableVlanTable table."
    INDEX { cucsFabricPoolableVlanInstanceId }
    ::= { cucsFabricPoolableVlanTable 1 }

CucsFabricPoolableVlanEntry ::= SEQUENCE {
    cucsFabricPoolableVlanInstanceId                                 CucsManagedObjectId,
    cucsFabricPoolableVlanDn                                         CucsManagedObjectDn,
    cucsFabricPoolableVlanRn                                         SnmpAdminString,
    cucsFabricPoolableVlanId                                         Unsigned64,
    cucsFabricPoolableVlanPoolDn                                     SnmpAdminString
}

cucsFabricPoolableVlanInstanceId OBJECT-TYPE
    SYNTAX       CucsManagedObjectId
    MAX-ACCESS   not-accessible
    STATUS       current
    DESCRIPTION
        "Instance identifier of the managed object."
    ::= { cucsFabricPoolableVlanEntry 1 }

cucsFabricPoolableVlanDn OBJECT-TYPE
    SYNTAX       CucsManagedObjectDn
    MAX-ACCESS   read-only
    STATUS       current
    DESCRIPTION
        "Cisco UCS fabric:PoolableVlan:dn managed object property"
    ::= { cucsFabricPoolableVlanEntry 2 }

cucsFabricPoolableVlanRn OBJECT-TYPE
    SYNTAX       SnmpAdminString
    MAX-ACCESS   read-only
    STATUS       current
    DESCRIPTION
        "Cisco UCS fabric:PoolableVlan:rn managed object property"
    ::= { cucsFabricPoolableVlanEntry 3 }

cucsFabricPoolableVlanId OBJECT-TYPE
    SYNTAX       Unsigned64
    MAX-ACCESS   read-only
    STATUS       current
    DESCRIPTION
        "Cisco UCS fabric:PoolableVlan:id managed object property"
    ::= { cucsFabricPoolableVlanEntry 4 }

cucsFabricPoolableVlanPoolDn OBJECT-TYPE
    SYNTAX       SnmpAdminString
    MAX-ACCESS   read-only
    STATUS       current
    DESCRIPTION
        "Cisco UCS fabric:PoolableVlan:poolDn managed object property"
    ::= { cucsFabricPoolableVlanEntry 5 }

cucsFabricPooledVlanTable OBJECT-TYPE
    SYNTAX           SEQUENCE OF CucsFabricPooledVlanEntry
    MAX-ACCESS       not-accessible
    STATUS           current
    DESCRIPTION
        "Cisco UCS fabric:PooledVlan managed object table"
    ::= { cucsFabricObjects 89 }

cucsFabricPooledVlanEntry OBJECT-TYPE
    SYNTAX           CucsFabricPooledVlanEntry
    MAX-ACCESS       not-accessible
    STATUS           current
    DESCRIPTION
        "Entry for the cucsFabricPooledVlanTable table."
    INDEX { cucsFabricPooledVlanInstanceId }
    ::= { cucsFabricPooledVlanTable 1 }

CucsFabricPooledVlanEntry ::= SEQUENCE {
    cucsFabricPooledVlanInstanceId                                   CucsManagedObjectId,
    cucsFabricPooledVlanDn                                           CucsManagedObjectDn,
    cucsFabricPooledVlanRn                                           SnmpAdminString,
    cucsFabricPooledVlanAssigned                                     TruthValue,
    cucsFabricPooledVlanAssignedToDn                                 SnmpAdminString,
    cucsFabricPooledVlanName                                         SnmpAdminString,
    cucsFabricPooledVlanPeerDn                                       SnmpAdminString,
    cucsFabricPooledVlanPoolableDn                                   SnmpAdminString,
    cucsFabricPooledVlanPrevAssignedToDn                             SnmpAdminString,
    cucsFabricPooledVlanConfigIssues                                 CucsFabricPoolMemberConfigIssues
}

cucsFabricPooledVlanInstanceId OBJECT-TYPE
    SYNTAX       CucsManagedObjectId
    MAX-ACCESS   not-accessible
    STATUS       current
    DESCRIPTION
        "Instance identifier of the managed object."
    ::= { cucsFabricPooledVlanEntry 1 }

cucsFabricPooledVlanDn OBJECT-TYPE
    SYNTAX       CucsManagedObjectDn
    MAX-ACCESS   read-only
    STATUS       current
    DESCRIPTION
        "Cisco UCS fabric:PooledVlan:dn managed object property"
    ::= { cucsFabricPooledVlanEntry 2 }

cucsFabricPooledVlanRn OBJECT-TYPE
    SYNTAX       SnmpAdminString
    MAX-ACCESS   read-only
    STATUS       current
    DESCRIPTION
        "Cisco UCS fabric:PooledVlan:rn managed object property"
    ::= { cucsFabricPooledVlanEntry 3 }

cucsFabricPooledVlanAssigned OBJECT-TYPE
    SYNTAX       TruthValue
    MAX-ACCESS   read-only
    STATUS       current
    DESCRIPTION
        "Cisco UCS fabric:PooledVlan:assigned managed object property"
    ::= { cucsFabricPooledVlanEntry 4 }

cucsFabricPooledVlanAssignedToDn OBJECT-TYPE
    SYNTAX       SnmpAdminString
    MAX-ACCESS   read-only
    STATUS       current
    DESCRIPTION
        "Cisco UCS fabric:PooledVlan:assignedToDn managed object property"
    ::= { cucsFabricPooledVlanEntry 5 }

cucsFabricPooledVlanName OBJECT-TYPE
    SYNTAX       SnmpAdminString
    MAX-ACCESS   read-only
    STATUS       current
    DESCRIPTION
        "Cisco UCS fabric:PooledVlan:name managed object property"
    ::= { cucsFabricPooledVlanEntry 6 }

cucsFabricPooledVlanPeerDn OBJECT-TYPE
    SYNTAX       SnmpAdminString
    MAX-ACCESS   read-only
    STATUS       current
    DESCRIPTION
        "Cisco UCS fabric:PooledVlan:peerDn managed object property"
    ::= { cucsFabricPooledVlanEntry 7 }

cucsFabricPooledVlanPoolableDn OBJECT-TYPE
    SYNTAX       SnmpAdminString
    MAX-ACCESS   read-only
    STATUS       current
    DESCRIPTION
        "Cisco UCS fabric:PooledVlan:poolableDn managed object property"
    ::= { cucsFabricPooledVlanEntry 8 }

cucsFabricPooledVlanPrevAssignedToDn OBJECT-TYPE
    SYNTAX       SnmpAdminString
    MAX-ACCESS   read-only
    STATUS       current
    DESCRIPTION
        "Cisco UCS fabric:PooledVlan:prevAssignedToDn managed
        object property"
    ::= { cucsFabricPooledVlanEntry 9 }

cucsFabricPooledVlanConfigIssues OBJECT-TYPE
    SYNTAX       CucsFabricPoolMemberConfigIssues
    MAX-ACCESS   read-only
    STATUS       current
    DESCRIPTION
        "Cisco UCS fabric:PooledVlan:configIssues managed object property"
    ::= { cucsFabricPooledVlanEntry 10 }

cucsFabricSanCloudTable OBJECT-TYPE
    SYNTAX           SEQUENCE OF CucsFabricSanCloudEntry
    MAX-ACCESS       not-accessible
    STATUS           current
    DESCRIPTION
        "Cisco UCS fabric:SanCloud managed object table"
    ::= { cucsFabricObjects 52 }

cucsFabricSanCloudEntry OBJECT-TYPE
    SYNTAX           CucsFabricSanCloudEntry
    MAX-ACCESS       not-accessible
    STATUS           current
    DESCRIPTION
        "Entry for the cucsFabricSanCloudTable table."
    INDEX { cucsFabricSanCloudInstanceId }
    ::= { cucsFabricSanCloudTable 1 }

CucsFabricSanCloudEntry ::= SEQUENCE {
    cucsFabricSanCloudInstanceId                                     CucsManagedObjectId,
    cucsFabricSanCloudDn                                             CucsManagedObjectDn,
    cucsFabricSanCloudRn                                             SnmpAdminString,
    cucsFabricSanCloudFsmDescr                                       SnmpAdminString,
    cucsFabricSanCloudFsmPrev                                        SnmpAdminString,
    cucsFabricSanCloudFsmProgr                                       Gauge32,
    cucsFabricSanCloudFsmRmtInvErrCode                               Gauge32,
    cucsFabricSanCloudFsmRmtInvErrDescr                              SnmpAdminString,
    cucsFabricSanCloudFsmRmtInvRslt                                  CucsConditionRemoteInvRslt,
    cucsFabricSanCloudFsmStageDescr                                  SnmpAdminString,
    cucsFabricSanCloudFsmStamp                                       DateAndTime,
    cucsFabricSanCloudFsmStatus                                      SnmpAdminString,
    cucsFabricSanCloudFsmTry                                         Gauge32,
    cucsFabricSanCloudMode                                           CucsFabricSwitchingMode
}

cucsFabricSanCloudInstanceId OBJECT-TYPE
    SYNTAX       CucsManagedObjectId
    MAX-ACCESS   not-accessible
    STATUS       current
    DESCRIPTION
        "Instance identifier of the managed object."
    ::= { cucsFabricSanCloudEntry 1 }

cucsFabricSanCloudDn OBJECT-TYPE
    SYNTAX       CucsManagedObjectDn
    MAX-ACCESS   read-only
    STATUS       current
    DESCRIPTION
        "Cisco UCS fabric:SanCloud:dn managed object property"
    ::= { cucsFabricSanCloudEntry 2 }

cucsFabricSanCloudRn OBJECT-TYPE
    SYNTAX       SnmpAdminString
    MAX-ACCESS   read-only
    STATUS       current
    DESCRIPTION
        "Cisco UCS fabric:SanCloud:rn managed object property"
    ::= { cucsFabricSanCloudEntry 3 }

cucsFabricSanCloudFsmDescr OBJECT-TYPE
    SYNTAX       SnmpAdminString
    MAX-ACCESS   read-only
    STATUS       current
    DESCRIPTION
        "Cisco UCS fabric:SanCloud:fsmDescr managed object property"
    ::= { cucsFabricSanCloudEntry 4 }

cucsFabricSanCloudFsmPrev OBJECT-TYPE
    SYNTAX       SnmpAdminString
    MAX-ACCESS   read-only
    STATUS       current
    DESCRIPTION
        "Cisco UCS fabric:SanCloud:fsmPrev managed object property"
    ::= { cucsFabricSanCloudEntry 5 }

cucsFabricSanCloudFsmProgr OBJECT-TYPE
    SYNTAX       Gauge32
    MAX-ACCESS   read-only
    STATUS       current
    DESCRIPTION
        "Cisco UCS fabric:SanCloud:fsmProgr managed object property"
    ::= { cucsFabricSanCloudEntry 6 }

cucsFabricSanCloudFsmRmtInvErrCode OBJECT-TYPE
    SYNTAX       Gauge32
    MAX-ACCESS   read-only
    STATUS       current
    DESCRIPTION
        "Cisco UCS fabric:SanCloud:fsmRmtInvErrCode managed
        object property"
    ::= { cucsFabricSanCloudEntry 7 }

cucsFabricSanCloudFsmRmtInvErrDescr OBJECT-TYPE
    SYNTAX       SnmpAdminString
    MAX-ACCESS   read-only
    STATUS       current
    DESCRIPTION
        "Cisco UCS fabric:SanCloud:fsmRmtInvErrDescr managed
        object property"
    ::= { cucsFabricSanCloudEntry 8 }

cucsFabricSanCloudFsmRmtInvRslt OBJECT-TYPE
    SYNTAX       CucsConditionRemoteInvRslt
    MAX-ACCESS   read-only
    STATUS       current
    DESCRIPTION
        "Cisco UCS fabric:SanCloud:fsmRmtInvRslt managed object property"
    ::= { cucsFabricSanCloudEntry 9 }

cucsFabricSanCloudFsmStageDescr OBJECT-TYPE
    SYNTAX       SnmpAdminString
    MAX-ACCESS   read-only
    STATUS       current
    DESCRIPTION
        "Cisco UCS fabric:SanCloud:fsmStageDescr managed object property"
    ::= { cucsFabricSanCloudEntry 10 }

cucsFabricSanCloudFsmStamp OBJECT-TYPE
    SYNTAX       DateAndTime
    MAX-ACCESS   read-only
    STATUS       current
    DESCRIPTION
        "Cisco UCS fabric:SanCloud:fsmStamp managed object property"
    ::= { cucsFabricSanCloudEntry 11 }

cucsFabricSanCloudFsmStatus OBJECT-TYPE
    SYNTAX       SnmpAdminString
    MAX-ACCESS   read-only
    STATUS       current
    DESCRIPTION
        "Cisco UCS fabric:SanCloud:fsmStatus managed object property"
    ::= { cucsFabricSanCloudEntry 12 }

cucsFabricSanCloudFsmTry OBJECT-TYPE
    SYNTAX       Gauge32
    MAX-ACCESS   read-only
    STATUS       current
    DESCRIPTION
        "Cisco UCS fabric:SanCloud:fsmTry managed object property"
    ::= { cucsFabricSanCloudEntry 13 }

cucsFabricSanCloudMode OBJECT-TYPE
    SYNTAX       CucsFabricSwitchingMode
    MAX-ACCESS   read-only
    STATUS       current
    DESCRIPTION
        "Cisco UCS fabric:SanCloud:mode managed object property"
    ::= { cucsFabricSanCloudEntry 14 }

cucsFabricSanCloudFsmTable OBJECT-TYPE
    SYNTAX           SEQUENCE OF CucsFabricSanCloudFsmEntry
    MAX-ACCESS       not-accessible
    STATUS           current
    DESCRIPTION
        "Cisco UCS fabric:SanCloudFsm managed object table"
    ::= { cucsFabricObjects 90 }

cucsFabricSanCloudFsmEntry OBJECT-TYPE
    SYNTAX           CucsFabricSanCloudFsmEntry
    MAX-ACCESS       not-accessible
    STATUS           current
    DESCRIPTION
        "Entry for the cucsFabricSanCloudFsmTable table."
    INDEX { cucsFabricSanCloudFsmInstanceId }
    ::= { cucsFabricSanCloudFsmTable 1 }

CucsFabricSanCloudFsmEntry ::= SEQUENCE {
    cucsFabricSanCloudFsmInstanceId                                  CucsManagedObjectId,
    cucsFabricSanCloudFsmDn                                          CucsManagedObjectDn,
    cucsFabricSanCloudFsmRn                                          SnmpAdminString,
    cucsFabricSanCloudFsmCompletionTime                              DateAndTime,
    cucsFabricSanCloudFsmCurrentFsm                                  CucsFabricSanCloudFsmCurrentFsm,
    cucsFabricSanCloudFsmDescrData                                   SnmpAdminString,
    cucsFabricSanCloudFsmFsmStatus                                   CucsFsmFsmStageStatus,
    cucsFabricSanCloudFsmProgress                                    Gauge32,
    cucsFabricSanCloudFsmRmtErrCode                                  Gauge32,
    cucsFabricSanCloudFsmRmtErrDescr                                 SnmpAdminString,
    cucsFabricSanCloudFsmRmtRslt                                     CucsConditionRemoteInvRslt
}

cucsFabricSanCloudFsmInstanceId OBJECT-TYPE
    SYNTAX       CucsManagedObjectId
    MAX-ACCESS   not-accessible
    STATUS       current
    DESCRIPTION
        "Instance identifier of the managed object."
    ::= { cucsFabricSanCloudFsmEntry 1 }

cucsFabricSanCloudFsmDn OBJECT-TYPE
    SYNTAX       CucsManagedObjectDn
    MAX-ACCESS   read-only
    STATUS       current
    DESCRIPTION
        "Cisco UCS fabric:SanCloudFsm:dn managed object property"
    ::= { cucsFabricSanCloudFsmEntry 2 }

cucsFabricSanCloudFsmRn OBJECT-TYPE
    SYNTAX       SnmpAdminString
    MAX-ACCESS   read-only
    STATUS       current
    DESCRIPTION
        "Cisco UCS fabric:SanCloudFsm:rn managed object property"
    ::= { cucsFabricSanCloudFsmEntry 3 }

cucsFabricSanCloudFsmCompletionTime OBJECT-TYPE
    SYNTAX       DateAndTime
    MAX-ACCESS   read-only
    STATUS       current
    DESCRIPTION
        "Cisco UCS fabric:SanCloudFsm:completionTime managed
        object property"
    ::= { cucsFabricSanCloudFsmEntry 4 }

cucsFabricSanCloudFsmCurrentFsm OBJECT-TYPE
    SYNTAX       CucsFabricSanCloudFsmCurrentFsm
    MAX-ACCESS   read-only
    STATUS       current
    DESCRIPTION
        "Cisco UCS fabric:SanCloudFsm:currentFsm managed object property"
    ::= { cucsFabricSanCloudFsmEntry 5 }

cucsFabricSanCloudFsmDescrData OBJECT-TYPE
    SYNTAX       SnmpAdminString
    MAX-ACCESS   read-only
    STATUS       current
    DESCRIPTION
        "Cisco UCS fabric:SanCloudFsm:descr managed object property"
    ::= { cucsFabricSanCloudFsmEntry 6 }

cucsFabricSanCloudFsmFsmStatus OBJECT-TYPE
    SYNTAX       CucsFsmFsmStageStatus
    MAX-ACCESS   read-only
    STATUS       current
    DESCRIPTION
        "Cisco UCS fabric:SanCloudFsm:fsmStatus managed object property"
    ::= { cucsFabricSanCloudFsmEntry 7 }

cucsFabricSanCloudFsmProgress OBJECT-TYPE
    SYNTAX       Gauge32
    MAX-ACCESS   read-only
    STATUS       current
    DESCRIPTION
        "Cisco UCS fabric:SanCloudFsm:progress managed object property"
    ::= { cucsFabricSanCloudFsmEntry 8 }

cucsFabricSanCloudFsmRmtErrCode OBJECT-TYPE
    SYNTAX       Gauge32
    MAX-ACCESS   read-only
    STATUS       current
    DESCRIPTION
        "Cisco UCS fabric:SanCloudFsm:rmtErrCode managed object property"
    ::= { cucsFabricSanCloudFsmEntry 9 }

cucsFabricSanCloudFsmRmtErrDescr OBJECT-TYPE
    SYNTAX       SnmpAdminString
    MAX-ACCESS   read-only
    STATUS       current
    DESCRIPTION
        "Cisco UCS fabric:SanCloudFsm:rmtErrDescr managed object property"
    ::= { cucsFabricSanCloudFsmEntry 10 }

cucsFabricSanCloudFsmRmtRslt OBJECT-TYPE
    SYNTAX       CucsConditionRemoteInvRslt
    MAX-ACCESS   read-only
    STATUS       current
    DESCRIPTION
        "Cisco UCS fabric:SanCloudFsm:rmtRslt managed object property"
    ::= { cucsFabricSanCloudFsmEntry 11 }

cucsFabricSanCloudFsmStageTable OBJECT-TYPE
    SYNTAX           SEQUENCE OF CucsFabricSanCloudFsmStageEntry
    MAX-ACCESS       not-accessible
    STATUS           current
    DESCRIPTION
        "Cisco UCS fabric:SanCloudFsmStage managed object table"
    ::= { cucsFabricObjects 91 }

cucsFabricSanCloudFsmStageEntry OBJECT-TYPE
    SYNTAX           CucsFabricSanCloudFsmStageEntry
    MAX-ACCESS       not-accessible
    STATUS           current
    DESCRIPTION
        "Entry for the cucsFabricSanCloudFsmStageTable table."
    INDEX { cucsFabricSanCloudFsmStageInstanceId }
    ::= { cucsFabricSanCloudFsmStageTable 1 }

CucsFabricSanCloudFsmStageEntry ::= SEQUENCE {
    cucsFabricSanCloudFsmStageInstanceId                             CucsManagedObjectId,
    cucsFabricSanCloudFsmStageDn                                     CucsManagedObjectDn,
    cucsFabricSanCloudFsmStageRn                                     SnmpAdminString,
    cucsFabricSanCloudFsmStageDescrData                              SnmpAdminString,
    cucsFabricSanCloudFsmStageLastUpdateTime                         DateAndTime,
    cucsFabricSanCloudFsmStageName                                   CucsFabricSanCloudFsmStageName,
    cucsFabricSanCloudFsmStageOrder                                  Gauge32,
    cucsFabricSanCloudFsmStageRetry                                  Gauge32,
    cucsFabricSanCloudFsmStageStageStatus                            CucsFsmFsmStageStatus
}

cucsFabricSanCloudFsmStageInstanceId OBJECT-TYPE
    SYNTAX       CucsManagedObjectId
    MAX-ACCESS   not-accessible
    STATUS       current
    DESCRIPTION
        "Instance identifier of the managed object."
    ::= { cucsFabricSanCloudFsmStageEntry 1 }

cucsFabricSanCloudFsmStageDn OBJECT-TYPE
    SYNTAX       CucsManagedObjectDn
    MAX-ACCESS   read-only
    STATUS       current
    DESCRIPTION
        "Cisco UCS fabric:SanCloudFsmStage:dn managed object property"
    ::= { cucsFabricSanCloudFsmStageEntry 2 }

cucsFabricSanCloudFsmStageRn OBJECT-TYPE
    SYNTAX       SnmpAdminString
    MAX-ACCESS   read-only
    STATUS       current
    DESCRIPTION
        "Cisco UCS fabric:SanCloudFsmStage:rn managed object property"
    ::= { cucsFabricSanCloudFsmStageEntry 3 }

cucsFabricSanCloudFsmStageDescrData OBJECT-TYPE
    SYNTAX       SnmpAdminString
    MAX-ACCESS   read-only
    STATUS       current
    DESCRIPTION
        "Cisco UCS fabric:SanCloudFsmStage:descr managed object property"
    ::= { cucsFabricSanCloudFsmStageEntry 4 }

cucsFabricSanCloudFsmStageLastUpdateTime OBJECT-TYPE
    SYNTAX       DateAndTime
    MAX-ACCESS   read-only
    STATUS       current
    DESCRIPTION
        "Cisco UCS fabric:SanCloudFsmStage:lastUpdateTime
        managed object property"
    ::= { cucsFabricSanCloudFsmStageEntry 5 }

cucsFabricSanCloudFsmStageName OBJECT-TYPE
    SYNTAX       CucsFabricSanCloudFsmStageName
    MAX-ACCESS   read-only
    STATUS       current
    DESCRIPTION
        "Cisco UCS fabric:SanCloudFsmStage:name managed object property"
    ::= { cucsFabricSanCloudFsmStageEntry 6 }

cucsFabricSanCloudFsmStageOrder OBJECT-TYPE
    SYNTAX       Gauge32
    MAX-ACCESS   read-only
    STATUS       current
    DESCRIPTION
        "Cisco UCS fabric:SanCloudFsmStage:order managed object property"
    ::= { cucsFabricSanCloudFsmStageEntry 7 }

cucsFabricSanCloudFsmStageRetry OBJECT-TYPE
    SYNTAX       Gauge32
    MAX-ACCESS   read-only
    STATUS       current
    DESCRIPTION
        "Cisco UCS fabric:SanCloudFsmStage:retry managed object property"
    ::= { cucsFabricSanCloudFsmStageEntry 8 }

cucsFabricSanCloudFsmStageStageStatus OBJECT-TYPE
    SYNTAX       CucsFsmFsmStageStatus
    MAX-ACCESS   read-only
    STATUS       current
    DESCRIPTION
        "Cisco UCS fabric:SanCloudFsmStage:stageStatus
        managed object property"
    ::= { cucsFabricSanCloudFsmStageEntry 9 }

cucsFabricSanCloudFsmTaskTable OBJECT-TYPE
    SYNTAX           SEQUENCE OF CucsFabricSanCloudFsmTaskEntry
    MAX-ACCESS       not-accessible
    STATUS           current
    DESCRIPTION
        "Cisco UCS fabric:SanCloudFsmTask managed object table"
    ::= { cucsFabricObjects 53 }

cucsFabricSanCloudFsmTaskEntry OBJECT-TYPE
    SYNTAX           CucsFabricSanCloudFsmTaskEntry
    MAX-ACCESS       not-accessible
    STATUS           current
    DESCRIPTION
        "Entry for the cucsFabricSanCloudFsmTaskTable table."
    INDEX { cucsFabricSanCloudFsmTaskInstanceId }
    ::= { cucsFabricSanCloudFsmTaskTable 1 }

CucsFabricSanCloudFsmTaskEntry ::= SEQUENCE {
    cucsFabricSanCloudFsmTaskInstanceId                              CucsManagedObjectId,
    cucsFabricSanCloudFsmTaskDn                                      CucsManagedObjectDn,
    cucsFabricSanCloudFsmTaskRn                                      SnmpAdminString,
    cucsFabricSanCloudFsmTaskCompletion                              CucsFsmCompletion,
    cucsFabricSanCloudFsmTaskFlags                                   CucsFsmFlags,
    cucsFabricSanCloudFsmTaskItem                                    CucsFabricSanCloudFsmTaskItem,
    cucsFabricSanCloudFsmTaskSeqId                                   Gauge32
}

cucsFabricSanCloudFsmTaskInstanceId OBJECT-TYPE
    SYNTAX       CucsManagedObjectId
    MAX-ACCESS   not-accessible
    STATUS       current
    DESCRIPTION
        "Instance identifier of the managed object."
    ::= { cucsFabricSanCloudFsmTaskEntry 1 }

cucsFabricSanCloudFsmTaskDn OBJECT-TYPE
    SYNTAX       CucsManagedObjectDn
    MAX-ACCESS   read-only
    STATUS       current
    DESCRIPTION
        "Cisco UCS fabric:SanCloudFsmTask:dn managed object property"
    ::= { cucsFabricSanCloudFsmTaskEntry 2 }

cucsFabricSanCloudFsmTaskRn OBJECT-TYPE
    SYNTAX       SnmpAdminString
    MAX-ACCESS   read-only
    STATUS       current
    DESCRIPTION
        "Cisco UCS fabric:SanCloudFsmTask:rn managed object property"
    ::= { cucsFabricSanCloudFsmTaskEntry 3 }

cucsFabricSanCloudFsmTaskCompletion OBJECT-TYPE
    SYNTAX       CucsFsmCompletion
    MAX-ACCESS   read-only
    STATUS       current
    DESCRIPTION
        "Cisco UCS fabric:SanCloudFsmTask:completion managed
        object property"
    ::= { cucsFabricSanCloudFsmTaskEntry 4 }

cucsFabricSanCloudFsmTaskFlags OBJECT-TYPE
    SYNTAX       CucsFsmFlags
    MAX-ACCESS   read-only
    STATUS       current
    DESCRIPTION
        "Cisco UCS fabric:SanCloudFsmTask:flags managed object property"
    ::= { cucsFabricSanCloudFsmTaskEntry 5 }

cucsFabricSanCloudFsmTaskItem OBJECT-TYPE
    SYNTAX       CucsFabricSanCloudFsmTaskItem
    MAX-ACCESS   read-only
    STATUS       current
    DESCRIPTION
        "Cisco UCS fabric:SanCloudFsmTask:item managed object property"
    ::= { cucsFabricSanCloudFsmTaskEntry 6 }

cucsFabricSanCloudFsmTaskSeqId OBJECT-TYPE
    SYNTAX       Gauge32
    MAX-ACCESS   read-only
    STATUS       current
    DESCRIPTION
        "Cisco UCS fabric:SanCloudFsmTask:seqId managed object property"
    ::= { cucsFabricSanCloudFsmTaskEntry 7 }

cucsFabricSanMonCloudTable OBJECT-TYPE
    SYNTAX           SEQUENCE OF CucsFabricSanMonCloudEntry
    MAX-ACCESS       not-accessible
    STATUS           current
    DESCRIPTION
        "Cisco UCS fabric:SanMonCloud managed object table"
    ::= { cucsFabricObjects 54 }

cucsFabricSanMonCloudEntry OBJECT-TYPE
    SYNTAX           CucsFabricSanMonCloudEntry
    MAX-ACCESS       not-accessible
    STATUS           current
    DESCRIPTION
        "Entry for the cucsFabricSanMonCloudTable table."
    INDEX { cucsFabricSanMonCloudInstanceId }
    ::= { cucsFabricSanMonCloudTable 1 }

CucsFabricSanMonCloudEntry ::= SEQUENCE {
    cucsFabricSanMonCloudInstanceId                                  CucsManagedObjectId,
    cucsFabricSanMonCloudDn                                          CucsManagedObjectDn,
    cucsFabricSanMonCloudRn                                          SnmpAdminString,
    cucsFabricSanMonCloudMode                                        CucsFabricSwitchingMode
}

cucsFabricSanMonCloudInstanceId OBJECT-TYPE
    SYNTAX       CucsManagedObjectId
    MAX-ACCESS   not-accessible
    STATUS       current
    DESCRIPTION
        "Instance identifier of the managed object."
    ::= { cucsFabricSanMonCloudEntry 1 }

cucsFabricSanMonCloudDn OBJECT-TYPE
    SYNTAX       CucsManagedObjectDn
    MAX-ACCESS   read-only
    STATUS       current
    DESCRIPTION
        "Cisco UCS fabric:SanMonCloud:dn managed object property"
    ::= { cucsFabricSanMonCloudEntry 2 }

cucsFabricSanMonCloudRn OBJECT-TYPE
    SYNTAX       SnmpAdminString
    MAX-ACCESS   read-only
    STATUS       current
    DESCRIPTION
        "Cisco UCS fabric:SanMonCloud:rn managed object property"
    ::= { cucsFabricSanMonCloudEntry 3 }

cucsFabricSanMonCloudMode OBJECT-TYPE
    SYNTAX       CucsFabricSwitchingMode
    MAX-ACCESS   read-only
    STATUS       current
    DESCRIPTION
        "Cisco UCS fabric:SanMonCloud:mode managed object property"
    ::= { cucsFabricSanMonCloudEntry 4 }

cucsFabricSanPinGroupTable OBJECT-TYPE
    SYNTAX           SEQUENCE OF CucsFabricSanPinGroupEntry
    MAX-ACCESS       not-accessible
    STATUS           current
    DESCRIPTION
        "Cisco UCS fabric:SanPinGroup managed object table"
    ::= { cucsFabricObjects 55 }

cucsFabricSanPinGroupEntry OBJECT-TYPE
    SYNTAX           CucsFabricSanPinGroupEntry
    MAX-ACCESS       not-accessible
    STATUS           current
    DESCRIPTION
        "Entry for the cucsFabricSanPinGroupTable table."
    INDEX { cucsFabricSanPinGroupInstanceId }
    ::= { cucsFabricSanPinGroupTable 1 }

CucsFabricSanPinGroupEntry ::= SEQUENCE {
    cucsFabricSanPinGroupInstanceId                                  CucsManagedObjectId,
    cucsFabricSanPinGroupDn                                          CucsManagedObjectDn,
    cucsFabricSanPinGroupRn                                          SnmpAdminString,
    cucsFabricSanPinGroupDescr                                       SnmpAdminString,
    cucsFabricSanPinGroupIntId                                       SnmpAdminString,
    cucsFabricSanPinGroupName                                        SnmpAdminString,
    cucsFabricSanPinGroupSize                                        Gauge32,
    cucsFabricSanPinGroupPolicyLevel                                 Gauge32,
    cucsFabricSanPinGroupPolicyOwner                                 CucsPolicyPolicyOwner
}

cucsFabricSanPinGroupInstanceId OBJECT-TYPE
    SYNTAX       CucsManagedObjectId
    MAX-ACCESS   not-accessible
    STATUS       current
    DESCRIPTION
        "Instance identifier of the managed object."
    ::= { cucsFabricSanPinGroupEntry 1 }

cucsFabricSanPinGroupDn OBJECT-TYPE
    SYNTAX       CucsManagedObjectDn
    MAX-ACCESS   read-only
    STATUS       current
    DESCRIPTION
        "Cisco UCS fabric:SanPinGroup:dn managed object property"
    ::= { cucsFabricSanPinGroupEntry 2 }

cucsFabricSanPinGroupRn OBJECT-TYPE
    SYNTAX       SnmpAdminString
    MAX-ACCESS   read-only
    STATUS       current
    DESCRIPTION
        "Cisco UCS fabric:SanPinGroup:rn managed object property"
    ::= { cucsFabricSanPinGroupEntry 3 }

cucsFabricSanPinGroupDescr OBJECT-TYPE
    SYNTAX       SnmpAdminString
    MAX-ACCESS   read-only
    STATUS       current
    DESCRIPTION
        "Cisco UCS fabric:SanPinGroup:descr managed object property"
    ::= { cucsFabricSanPinGroupEntry 4 }

cucsFabricSanPinGroupIntId OBJECT-TYPE
    SYNTAX       SnmpAdminString
    MAX-ACCESS   read-only
    STATUS       current
    DESCRIPTION
        "Cisco UCS fabric:SanPinGroup:intId managed object property"
    ::= { cucsFabricSanPinGroupEntry 5 }

cucsFabricSanPinGroupName OBJECT-TYPE
    SYNTAX       SnmpAdminString
    MAX-ACCESS   read-only
    STATUS       current
    DESCRIPTION
        "Cisco UCS fabric:SanPinGroup:name managed object property"
    ::= { cucsFabricSanPinGroupEntry 6 }

cucsFabricSanPinGroupSize OBJECT-TYPE
    SYNTAX       Gauge32
    MAX-ACCESS   read-only
    STATUS       current
    DESCRIPTION
        "Cisco UCS fabric:SanPinGroup:size managed object property"
    ::= { cucsFabricSanPinGroupEntry 7 }

cucsFabricSanPinGroupPolicyLevel OBJECT-TYPE
    SYNTAX       Gauge32
    MAX-ACCESS   read-only
    STATUS       current
    DESCRIPTION
        "Cisco UCS fabric:SanPinGroup:policyLevel managed object property"
    ::= { cucsFabricSanPinGroupEntry 8 }

cucsFabricSanPinGroupPolicyOwner OBJECT-TYPE
    SYNTAX       CucsPolicyPolicyOwner
    MAX-ACCESS   read-only
    STATUS       current
    DESCRIPTION
        "Cisco UCS fabric:SanPinGroup:policyOwner managed object property"
    ::= { cucsFabricSanPinGroupEntry 9 }

cucsFabricSanPinTargetTable OBJECT-TYPE
    SYNTAX           SEQUENCE OF CucsFabricSanPinTargetEntry
    MAX-ACCESS       not-accessible
    STATUS           current
    DESCRIPTION
        "Cisco UCS fabric:SanPinTarget managed object table"
    ::= { cucsFabricObjects 56 }

cucsFabricSanPinTargetEntry OBJECT-TYPE
    SYNTAX           CucsFabricSanPinTargetEntry
    MAX-ACCESS       not-accessible
    STATUS           current
    DESCRIPTION
        "Entry for the cucsFabricSanPinTargetTable table."
    INDEX { cucsFabricSanPinTargetInstanceId }
    ::= { cucsFabricSanPinTargetTable 1 }

CucsFabricSanPinTargetEntry ::= SEQUENCE {
    cucsFabricSanPinTargetInstanceId                                 CucsManagedObjectId,
    cucsFabricSanPinTargetDn                                         CucsManagedObjectDn,
    cucsFabricSanPinTargetRn                                         SnmpAdminString,
    cucsFabricSanPinTargetEpDn                                       SnmpAdminString,
    cucsFabricSanPinTargetFabricId                                   SnmpAdminString,
    cucsFabricSanPinTargetTargetStatus                               CucsFabricTargetStatus,
    cucsFabricSanPinTargetAggrPortId                                 CucsFabricPinTargetAggrPortId,
    cucsFabricSanPinTargetPortId                                     CucsFabricPinTargetPortId,
    cucsFabricSanPinTargetSlotId                                     CucsFabricPinTargetSlotId
}

cucsFabricSanPinTargetInstanceId OBJECT-TYPE
    SYNTAX       CucsManagedObjectId
    MAX-ACCESS   not-accessible
    STATUS       current
    DESCRIPTION
        "Instance identifier of the managed object."
    ::= { cucsFabricSanPinTargetEntry 1 }

cucsFabricSanPinTargetDn OBJECT-TYPE
    SYNTAX       CucsManagedObjectDn
    MAX-ACCESS   read-only
    STATUS       current
    DESCRIPTION
        "Cisco UCS fabric:SanPinTarget:dn managed object property"
    ::= { cucsFabricSanPinTargetEntry 2 }

cucsFabricSanPinTargetRn OBJECT-TYPE
    SYNTAX       SnmpAdminString
    MAX-ACCESS   read-only
    STATUS       current
    DESCRIPTION
        "Cisco UCS fabric:SanPinTarget:rn managed object property"
    ::= { cucsFabricSanPinTargetEntry 3 }

cucsFabricSanPinTargetEpDn OBJECT-TYPE
    SYNTAX       SnmpAdminString
    MAX-ACCESS   read-only
    STATUS       current
    DESCRIPTION
        "Cisco UCS fabric:SanPinTarget:epDn managed object property"
    ::= { cucsFabricSanPinTargetEntry 4 }

cucsFabricSanPinTargetFabricId OBJECT-TYPE
    SYNTAX       SnmpAdminString
    MAX-ACCESS   read-only
    STATUS       current
    DESCRIPTION
        "Cisco UCS fabric:SanPinTarget:fabricId managed object property"
    ::= { cucsFabricSanPinTargetEntry 5 }

cucsFabricSanPinTargetTargetStatus OBJECT-TYPE
    SYNTAX       CucsFabricTargetStatus
    MAX-ACCESS   read-only
    STATUS       current
    DESCRIPTION
        "Cisco UCS fabric:SanPinTarget:targetStatus managed
        object property"
    ::= { cucsFabricSanPinTargetEntry 6 }

cucsFabricSanPinTargetAggrPortId OBJECT-TYPE
    SYNTAX       CucsFabricPinTargetAggrPortId
    MAX-ACCESS   read-only
    STATUS       current
    DESCRIPTION
        "Cisco UCS fabric:SanPinTarget:aggrPortId managed object property"
    ::= { cucsFabricSanPinTargetEntry 7 }

cucsFabricSanPinTargetPortId OBJECT-TYPE
    SYNTAX       CucsFabricPinTargetPortId
    MAX-ACCESS   read-only
    STATUS       current
    DESCRIPTION
        "Cisco UCS fabric:SanPinTarget:portId managed object property"
    ::= { cucsFabricSanPinTargetEntry 8 }

cucsFabricSanPinTargetSlotId OBJECT-TYPE
    SYNTAX       CucsFabricPinTargetSlotId
    MAX-ACCESS   read-only
    STATUS       current
    DESCRIPTION
        "Cisco UCS fabric:SanPinTarget:slotId managed object property"
    ::= { cucsFabricSanPinTargetEntry 9 }

cucsFabricSubGroupTable OBJECT-TYPE
    SYNTAX           SEQUENCE OF CucsFabricSubGroupEntry
    MAX-ACCESS       not-accessible
    STATUS           current
    DESCRIPTION
        "Cisco UCS fabric:SubGroup managed object table"
    ::= { cucsFabricObjects 122 }

cucsFabricSubGroupEntry OBJECT-TYPE
    SYNTAX           CucsFabricSubGroupEntry
    MAX-ACCESS       not-accessible
    STATUS           current
    DESCRIPTION
        "Entry for the cucsFabricSubGroupTable table."
    INDEX { cucsFabricSubGroupInstanceId }
    ::= { cucsFabricSubGroupTable 1 }

CucsFabricSubGroupEntry ::= SEQUENCE {
    cucsFabricSubGroupInstanceId                                     CucsManagedObjectId,
    cucsFabricSubGroupDn                                             CucsManagedObjectDn,
    cucsFabricSubGroupRn                                             SnmpAdminString,
    cucsFabricSubGroupAggrPortId                                     CucsFabricSubGroupAggrPortId,
    cucsFabricSubGroupConfigState                                    CucsFabricSubGroupConfigState,
    cucsFabricSubGroupLicGP                                          Unsigned64,
    cucsFabricSubGroupLicState                                       CucsLicenseState,
    cucsFabricSubGroupLocale                                         CucsNetworkLocale,
    cucsFabricSubGroupName                                           SnmpAdminString,
    cucsFabricSubGroupSlotId                                         CucsFabricSubGroupSlotId,
    cucsFabricSubGroupSwitchId                                       CucsNetworkSwitchId,
    cucsFabricSubGroupTransport                                      CucsNetworkTransport,
    cucsFabricSubGroupType                                           CucsNetworkConnectionType
}

cucsFabricSubGroupInstanceId OBJECT-TYPE
    SYNTAX       CucsManagedObjectId
    MAX-ACCESS   not-accessible
    STATUS       current
    DESCRIPTION
        "Instance identifier of the managed object."
    ::= { cucsFabricSubGroupEntry 1 }

cucsFabricSubGroupDn OBJECT-TYPE
    SYNTAX       CucsManagedObjectDn
    MAX-ACCESS   read-only
    STATUS       current
    DESCRIPTION
        "Cisco UCS fabric:SubGroup:dn managed object property"
    ::= { cucsFabricSubGroupEntry 2 }

cucsFabricSubGroupRn OBJECT-TYPE
    SYNTAX       SnmpAdminString
    MAX-ACCESS   read-only
    STATUS       current
    DESCRIPTION
        "Cisco UCS fabric:SubGroup:rn managed object property"
    ::= { cucsFabricSubGroupEntry 3 }

cucsFabricSubGroupAggrPortId OBJECT-TYPE
    SYNTAX       CucsFabricSubGroupAggrPortId
    MAX-ACCESS   read-only
    STATUS       current
    DESCRIPTION
        "Cisco UCS fabric:SubGroup:aggrPortId managed object property"
    ::= { cucsFabricSubGroupEntry 4 }

cucsFabricSubGroupConfigState OBJECT-TYPE
    SYNTAX       CucsFabricSubGroupConfigState
    MAX-ACCESS   read-only
    STATUS       current
    DESCRIPTION
        "Cisco UCS fabric:SubGroup:configState managed object property"
    ::= { cucsFabricSubGroupEntry 5 }

cucsFabricSubGroupLicGP OBJECT-TYPE
    SYNTAX       Unsigned64
    MAX-ACCESS   read-only
    STATUS       current
    DESCRIPTION
        "Cisco UCS fabric:SubGroup:licGP managed object property"
    ::= { cucsFabricSubGroupEntry 6 }

cucsFabricSubGroupLicState OBJECT-TYPE
    SYNTAX       CucsLicenseState
    MAX-ACCESS   read-only
    STATUS       current
    DESCRIPTION
        "Cisco UCS fabric:SubGroup:licState managed object property"
    ::= { cucsFabricSubGroupEntry 7 }

cucsFabricSubGroupLocale OBJECT-TYPE
    SYNTAX       CucsNetworkLocale
    MAX-ACCESS   read-only
    STATUS       current
    DESCRIPTION
        "Cisco UCS fabric:SubGroup:locale managed object property"
    ::= { cucsFabricSubGroupEntry 8 }

cucsFabricSubGroupName OBJECT-TYPE
    SYNTAX       SnmpAdminString
    MAX-ACCESS   read-only
    STATUS       current
    DESCRIPTION
        "Cisco UCS fabric:SubGroup:name managed object property"
    ::= { cucsFabricSubGroupEntry 9 }

cucsFabricSubGroupSlotId OBJECT-TYPE
    SYNTAX       CucsFabricSubGroupSlotId
    MAX-ACCESS   read-only
    STATUS       current
    DESCRIPTION
        "Cisco UCS fabric:SubGroup:slotId managed object property"
    ::= { cucsFabricSubGroupEntry 10 }

cucsFabricSubGroupSwitchId OBJECT-TYPE
    SYNTAX       CucsNetworkSwitchId
    MAX-ACCESS   read-only
    STATUS       current
    DESCRIPTION
        "Cisco UCS fabric:SubGroup:switchId managed object property"
    ::= { cucsFabricSubGroupEntry 11 }

cucsFabricSubGroupTransport OBJECT-TYPE
    SYNTAX       CucsNetworkTransport
    MAX-ACCESS   read-only
    STATUS       current
    DESCRIPTION
        "Cisco UCS fabric:SubGroup:transport managed object property"
    ::= { cucsFabricSubGroupEntry 12 }

cucsFabricSubGroupType OBJECT-TYPE
    SYNTAX       CucsNetworkConnectionType
    MAX-ACCESS   read-only
    STATUS       current
    DESCRIPTION
        "Cisco UCS fabric:SubGroup:type managed object property"
    ::= { cucsFabricSubGroupEntry 13 }

cucsFabricSwChPhEpTable OBJECT-TYPE
    SYNTAX           SEQUENCE OF CucsFabricSwChPhEpEntry
    MAX-ACCESS       not-accessible
    STATUS           current
    DESCRIPTION
        "Cisco UCS fabric:SwChPhEp managed object table"
    ::= { cucsFabricObjects 57 }

cucsFabricSwChPhEpEntry OBJECT-TYPE
    SYNTAX           CucsFabricSwChPhEpEntry
    MAX-ACCESS       not-accessible
    STATUS           current
    DESCRIPTION
        "Entry for the cucsFabricSwChPhEpTable table."
    INDEX { cucsFabricSwChPhEpInstanceId }
    ::= { cucsFabricSwChPhEpTable 1 }

CucsFabricSwChPhEpEntry ::= SEQUENCE {
    cucsFabricSwChPhEpInstanceId                                     CucsManagedObjectId,
    cucsFabricSwChPhEpDn                                             CucsManagedObjectDn,
    cucsFabricSwChPhEpRn                                             SnmpAdminString,
    cucsFabricSwChPhEpAdminState                                     CucsFabricSwChPhEpAdminState,
    cucsFabricSwChPhEpChassisId                                      Gauge32,
    cucsFabricSwChPhEpEpDn                                           SnmpAdminString,
    cucsFabricSwChPhEpEqType                                         CucsEquipmentFabricEpType,
    cucsFabricSwChPhEpIfRole                                         CucsFabricSwChEpIfRole,
    cucsFabricSwChPhEpIfType                                         CucsFabricPIoEpIfType,
    cucsFabricSwChPhEpLc                                             CucsFabricLifeCycle,
    cucsFabricSwChPhEpLicGP                                          Unsigned64,
    cucsFabricSwChPhEpLicState                                       CucsLicenseState,
    cucsFabricSwChPhEpLocale                                         CucsFabricInternalEpLocale,
    cucsFabricSwChPhEpModel                                          SnmpAdminString,
    cucsFabricSwChPhEpName                                           SnmpAdminString,
    cucsFabricSwChPhEpPeerDn                                         SnmpAdminString,
    cucsFabricSwChPhEpPeerPortId                                     Gauge32,
    cucsFabricSwChPhEpPeerSlotId                                     Gauge32,
    cucsFabricSwChPhEpPortId                                         CucsFabricPIoEpPortId,
    cucsFabricSwChPhEpRevision                                       SnmpAdminString,
    cucsFabricSwChPhEpSerial                                         SnmpAdminString,
    cucsFabricSwChPhEpSlotId                                         CucsFabricPIoEpSlotId,
    cucsFabricSwChPhEpSwitchId                                       CucsNetworkSwitchId,
    cucsFabricSwChPhEpTransport                                      CucsNetworkTransport,
    cucsFabricSwChPhEpType                                           CucsFabricSwChEpType,
    cucsFabricSwChPhEpVendor                                         SnmpAdminString,
    cucsFabricSwChPhEpPeerChassisId                                  Gauge32,
    cucsFabricSwChPhEpFltAggr                                        Unsigned64,
    cucsFabricSwChPhEpOperState                                      CucsFabricPIoEpOperState,
    cucsFabricSwChPhEpOperStateReason                                SnmpAdminString,
    cucsFabricSwChPhEpAggrPortId                                     Gauge32,
    cucsFabricSwChPhEpPeerAggrPortId                                 Gauge32,
    cucsFabricSwChPhEpAutoNegotiate                                  TruthValue,
    cucsFabricSwChPhEpConfigQualifier                                CucsEquipmentConfigIssues
}

cucsFabricSwChPhEpInstanceId OBJECT-TYPE
    SYNTAX       CucsManagedObjectId
    MAX-ACCESS   not-accessible
    STATUS       current
    DESCRIPTION
        "Instance identifier of the managed object."
    ::= { cucsFabricSwChPhEpEntry 1 }

cucsFabricSwChPhEpDn OBJECT-TYPE
    SYNTAX       CucsManagedObjectDn
    MAX-ACCESS   read-only
    STATUS       current
    DESCRIPTION
        "Cisco UCS fabric:SwChPhEp:dn managed object property"
    ::= { cucsFabricSwChPhEpEntry 2 }

cucsFabricSwChPhEpRn OBJECT-TYPE
    SYNTAX       SnmpAdminString
    MAX-ACCESS   read-only
    STATUS       current
    DESCRIPTION
        "Cisco UCS fabric:SwChPhEp:rn managed object property"
    ::= { cucsFabricSwChPhEpEntry 3 }

cucsFabricSwChPhEpAdminState OBJECT-TYPE
    SYNTAX       CucsFabricSwChPhEpAdminState
    MAX-ACCESS   read-only
    STATUS       current
    DESCRIPTION
        "Cisco UCS fabric:SwChPhEp:adminState managed object property"
    ::= { cucsFabricSwChPhEpEntry 4 }

cucsFabricSwChPhEpChassisId OBJECT-TYPE
    SYNTAX       Gauge32
    MAX-ACCESS   read-only
    STATUS       current
    DESCRIPTION
        "Cisco UCS fabric:SwChPhEp:chassisId managed object property"
    ::= { cucsFabricSwChPhEpEntry 5 }

cucsFabricSwChPhEpEpDn OBJECT-TYPE
    SYNTAX       SnmpAdminString
    MAX-ACCESS   read-only
    STATUS       current
    DESCRIPTION
        "Cisco UCS fabric:SwChPhEp:epDn managed object property"
    ::= { cucsFabricSwChPhEpEntry 6 }

cucsFabricSwChPhEpEqType OBJECT-TYPE
    SYNTAX       CucsEquipmentFabricEpType
    MAX-ACCESS   read-only
    STATUS       current
    DESCRIPTION
        "Cisco UCS fabric:SwChPhEp:eqType managed object property"
    ::= { cucsFabricSwChPhEpEntry 7 }

cucsFabricSwChPhEpIfRole OBJECT-TYPE
    SYNTAX       CucsFabricSwChEpIfRole
    MAX-ACCESS   read-only
    STATUS       current
    DESCRIPTION
        "Cisco UCS fabric:SwChPhEp:ifRole managed object property"
    ::= { cucsFabricSwChPhEpEntry 8 }

cucsFabricSwChPhEpIfType OBJECT-TYPE
    SYNTAX       CucsFabricPIoEpIfType
    MAX-ACCESS   read-only
    STATUS       current
    DESCRIPTION
        "Cisco UCS fabric:SwChPhEp:ifType managed object property"
    ::= { cucsFabricSwChPhEpEntry 9 }

cucsFabricSwChPhEpLc OBJECT-TYPE
    SYNTAX       CucsFabricLifeCycle
    MAX-ACCESS   read-only
    STATUS       current
    DESCRIPTION
        "Cisco UCS fabric:SwChPhEp:lc managed object property"
    ::= { cucsFabricSwChPhEpEntry 10 }

cucsFabricSwChPhEpLicGP OBJECT-TYPE
    SYNTAX       Unsigned64
    MAX-ACCESS   read-only
    STATUS       current
    DESCRIPTION
        "Cisco UCS fabric:SwChPhEp:licGP managed object property"
    ::= { cucsFabricSwChPhEpEntry 11 }

cucsFabricSwChPhEpLicState OBJECT-TYPE
    SYNTAX       CucsLicenseState
    MAX-ACCESS   read-only
    STATUS       current
    DESCRIPTION
        "Cisco UCS fabric:SwChPhEp:licState managed object property"
    ::= { cucsFabricSwChPhEpEntry 12 }

cucsFabricSwChPhEpLocale OBJECT-TYPE
    SYNTAX       CucsFabricInternalEpLocale
    MAX-ACCESS   read-only
    STATUS       current
    DESCRIPTION
        "Cisco UCS fabric:SwChPhEp:locale managed object property"
    ::= { cucsFabricSwChPhEpEntry 13 }

cucsFabricSwChPhEpModel OBJECT-TYPE
    SYNTAX       SnmpAdminString
    MAX-ACCESS   read-only
    STATUS       current
    DESCRIPTION
        "Cisco UCS fabric:SwChPhEp:model managed object property"
    ::= { cucsFabricSwChPhEpEntry 14 }

cucsFabricSwChPhEpName OBJECT-TYPE
    SYNTAX       SnmpAdminString
    MAX-ACCESS   read-only
    STATUS       current
    DESCRIPTION
        "Cisco UCS fabric:SwChPhEp:name managed object property"
    ::= { cucsFabricSwChPhEpEntry 15 }

cucsFabricSwChPhEpPeerDn OBJECT-TYPE
    SYNTAX       SnmpAdminString
    MAX-ACCESS   read-only
    STATUS       current
    DESCRIPTION
        "Cisco UCS fabric:SwChPhEp:peerDn managed object property"
    ::= { cucsFabricSwChPhEpEntry 16 }

cucsFabricSwChPhEpPeerPortId OBJECT-TYPE
    SYNTAX       Gauge32
    MAX-ACCESS   read-only
    STATUS       current
    DESCRIPTION
        "Cisco UCS fabric:SwChPhEp:peerPortId managed object property"
    ::= { cucsFabricSwChPhEpEntry 17 }

cucsFabricSwChPhEpPeerSlotId OBJECT-TYPE
    SYNTAX       Gauge32
    MAX-ACCESS   read-only
    STATUS       current
    DESCRIPTION
        "Cisco UCS fabric:SwChPhEp:peerSlotId managed object property"
    ::= { cucsFabricSwChPhEpEntry 18 }

cucsFabricSwChPhEpPortId OBJECT-TYPE
    SYNTAX       CucsFabricPIoEpPortId
    MAX-ACCESS   read-only
    STATUS       current
    DESCRIPTION
        "Cisco UCS fabric:SwChPhEp:portId managed object property"
    ::= { cucsFabricSwChPhEpEntry 19 }

cucsFabricSwChPhEpRevision OBJECT-TYPE
    SYNTAX       SnmpAdminString
    MAX-ACCESS   read-only
    STATUS       current
    DESCRIPTION
        "Cisco UCS fabric:SwChPhEp:revision managed object property"
    ::= { cucsFabricSwChPhEpEntry 20 }

cucsFabricSwChPhEpSerial OBJECT-TYPE
    SYNTAX       SnmpAdminString
    MAX-ACCESS   read-only
    STATUS       current
    DESCRIPTION
        "Cisco UCS fabric:SwChPhEp:serial managed object property"
    ::= { cucsFabricSwChPhEpEntry 21 }

cucsFabricSwChPhEpSlotId OBJECT-TYPE
    SYNTAX       CucsFabricPIoEpSlotId
    MAX-ACCESS   read-only
    STATUS       current
    DESCRIPTION
        "Cisco UCS fabric:SwChPhEp:slotId managed object property"
    ::= { cucsFabricSwChPhEpEntry 22 }

cucsFabricSwChPhEpSwitchId OBJECT-TYPE
    SYNTAX       CucsNetworkSwitchId
    MAX-ACCESS   read-only
    STATUS       current
    DESCRIPTION
        "Cisco UCS fabric:SwChPhEp:switchId managed object property"
    ::= { cucsFabricSwChPhEpEntry 23 }

cucsFabricSwChPhEpTransport OBJECT-TYPE
    SYNTAX       CucsNetworkTransport
    MAX-ACCESS   read-only
    STATUS       current
    DESCRIPTION
        "Cisco UCS fabric:SwChPhEp:transport managed object property"
    ::= { cucsFabricSwChPhEpEntry 24 }

cucsFabricSwChPhEpType OBJECT-TYPE
    SYNTAX       CucsFabricSwChEpType
    MAX-ACCESS   read-only
    STATUS       current
    DESCRIPTION
        "Cisco UCS fabric:SwChPhEp:type managed object property"
    ::= { cucsFabricSwChPhEpEntry 25 }

cucsFabricSwChPhEpVendor OBJECT-TYPE
    SYNTAX       SnmpAdminString
    MAX-ACCESS   read-only
    STATUS       current
    DESCRIPTION
        "Cisco UCS fabric:SwChPhEp:vendor managed object property"
    ::= { cucsFabricSwChPhEpEntry 26 }

cucsFabricSwChPhEpPeerChassisId OBJECT-TYPE
    SYNTAX       Gauge32
    MAX-ACCESS   read-only
    STATUS       current
    DESCRIPTION
        "Cisco UCS fabric:SwChPhEp:peerChassisId managed object property"
    ::= { cucsFabricSwChPhEpEntry 27 }

cucsFabricSwChPhEpFltAggr OBJECT-TYPE
    SYNTAX       Unsigned64
    MAX-ACCESS   read-only
    STATUS       current
    DESCRIPTION
        "Cisco UCS fabric:SwChPhEp:fltAggr managed object property"
    ::= { cucsFabricSwChPhEpEntry 28 }

cucsFabricSwChPhEpOperState OBJECT-TYPE
    SYNTAX       CucsFabricPIoEpOperState
    MAX-ACCESS   read-only
    STATUS       current
    DESCRIPTION
        "Cisco UCS fabric:SwChPhEp:operState managed object property"
    ::= { cucsFabricSwChPhEpEntry 29 }

cucsFabricSwChPhEpOperStateReason OBJECT-TYPE
    SYNTAX       SnmpAdminString
    MAX-ACCESS   read-only
    STATUS       current
    DESCRIPTION
        "Cisco UCS fabric:SwChPhEp:operStateReason managed
        object property"
    ::= { cucsFabricSwChPhEpEntry 30 }

cucsFabricSwChPhEpAggrPortId OBJECT-TYPE
    SYNTAX       Gauge32
    MAX-ACCESS   read-only
    STATUS       current
    DESCRIPTION
        "Cisco UCS fabric:SwChPhEp:aggrPortId managed object property"
    ::= { cucsFabricSwChPhEpEntry 31 }

cucsFabricSwChPhEpPeerAggrPortId OBJECT-TYPE
    SYNTAX       Gauge32
    MAX-ACCESS   read-only
    STATUS       current
    DESCRIPTION
        "Cisco UCS fabric:SwChPhEp:peerAggrPortId managed object property"
    ::= { cucsFabricSwChPhEpEntry 32 }

cucsFabricSwChPhEpAutoNegotiate OBJECT-TYPE
    SYNTAX       TruthValue
    MAX-ACCESS   read-only
    STATUS       current
    DESCRIPTION
        "Cisco UCS fabric:SwChPhEp:autoNegotiate managed object property"
    ::= { cucsFabricSwChPhEpEntry 34 }

cucsFabricSwChPhEpConfigQualifier OBJECT-TYPE
    SYNTAX       CucsEquipmentConfigIssues
    MAX-ACCESS   read-only
    STATUS       current
    DESCRIPTION
        "Cisco UCS fabric:SwChPhEp:configQualifier managed
        object property"
    ::= { cucsFabricSwChPhEpEntry 35 }

cucsFabricSwSubGroupTable OBJECT-TYPE
    SYNTAX           SEQUENCE OF CucsFabricSwSubGroupEntry
    MAX-ACCESS       not-accessible
    STATUS           current
    DESCRIPTION
        "Cisco UCS fabric:SwSubGroup managed object table"
    ::= { cucsFabricObjects 123 }

cucsFabricSwSubGroupEntry OBJECT-TYPE
    SYNTAX           CucsFabricSwSubGroupEntry
    MAX-ACCESS       not-accessible
    STATUS           current
    DESCRIPTION
        "Entry for the cucsFabricSwSubGroupTable table."
    INDEX { cucsFabricSwSubGroupInstanceId }
    ::= { cucsFabricSwSubGroupTable 1 }

CucsFabricSwSubGroupEntry ::= SEQUENCE {
    cucsFabricSwSubGroupInstanceId                                   CucsManagedObjectId,
    cucsFabricSwSubGroupDn                                           CucsManagedObjectDn,
    cucsFabricSwSubGroupRn                                           SnmpAdminString,
    cucsFabricSwSubGroupAggrPortId                                   CucsFabricSwSubGroupAggrPortId,
    cucsFabricSwSubGroupConfigState                                  CucsFabricSwSubGroupConfigState,
    cucsFabricSwSubGroupLicGP                                        Unsigned64,
    cucsFabricSwSubGroupLicState                                     CucsLicenseState,
    cucsFabricSwSubGroupLocale                                       CucsNetworkLocale,
    cucsFabricSwSubGroupName                                         SnmpAdminString,
    cucsFabricSwSubGroupSlotId                                       CucsFabricSwSubGroupSlotId,
    cucsFabricSwSubGroupSwitchId                                     CucsNetworkSwitchId,
    cucsFabricSwSubGroupTransport                                    CucsNetworkTransport,
    cucsFabricSwSubGroupType                                         CucsNetworkConnectionType
}

cucsFabricSwSubGroupInstanceId OBJECT-TYPE
    SYNTAX       CucsManagedObjectId
    MAX-ACCESS   not-accessible
    STATUS       current
    DESCRIPTION
        "Instance identifier of the managed object."
    ::= { cucsFabricSwSubGroupEntry 1 }

cucsFabricSwSubGroupDn OBJECT-TYPE
    SYNTAX       CucsManagedObjectDn
    MAX-ACCESS   read-only
    STATUS       current
    DESCRIPTION
        "Cisco UCS fabric:SwSubGroup:dn managed object property"
    ::= { cucsFabricSwSubGroupEntry 2 }

cucsFabricSwSubGroupRn OBJECT-TYPE
    SYNTAX       SnmpAdminString
    MAX-ACCESS   read-only
    STATUS       current
    DESCRIPTION
        "Cisco UCS fabric:SwSubGroup:rn managed object property"
    ::= { cucsFabricSwSubGroupEntry 3 }

cucsFabricSwSubGroupAggrPortId OBJECT-TYPE
    SYNTAX       CucsFabricSwSubGroupAggrPortId
    MAX-ACCESS   read-only
    STATUS       current
    DESCRIPTION
        "Cisco UCS fabric:SwSubGroup:aggrPortId managed object property"
    ::= { cucsFabricSwSubGroupEntry 4 }

cucsFabricSwSubGroupConfigState OBJECT-TYPE
    SYNTAX       CucsFabricSwSubGroupConfigState
    MAX-ACCESS   read-only
    STATUS       current
    DESCRIPTION
        "Cisco UCS fabric:SwSubGroup:configState managed object property"
    ::= { cucsFabricSwSubGroupEntry 5 }

cucsFabricSwSubGroupLicGP OBJECT-TYPE
    SYNTAX       Unsigned64
    MAX-ACCESS   read-only
    STATUS       current
    DESCRIPTION
        "Cisco UCS fabric:SwSubGroup:licGP managed object property"
    ::= { cucsFabricSwSubGroupEntry 6 }

cucsFabricSwSubGroupLicState OBJECT-TYPE
    SYNTAX       CucsLicenseState
    MAX-ACCESS   read-only
    STATUS       current
    DESCRIPTION
        "Cisco UCS fabric:SwSubGroup:licState managed object property"
    ::= { cucsFabricSwSubGroupEntry 7 }

cucsFabricSwSubGroupLocale OBJECT-TYPE
    SYNTAX       CucsNetworkLocale
    MAX-ACCESS   read-only
    STATUS       current
    DESCRIPTION
        "Cisco UCS fabric:SwSubGroup:locale managed object property"
    ::= { cucsFabricSwSubGroupEntry 8 }

cucsFabricSwSubGroupName OBJECT-TYPE
    SYNTAX       SnmpAdminString
    MAX-ACCESS   read-only
    STATUS       current
    DESCRIPTION
        "Cisco UCS fabric:SwSubGroup:name managed object property"
    ::= { cucsFabricSwSubGroupEntry 9 }

cucsFabricSwSubGroupSlotId OBJECT-TYPE
    SYNTAX       CucsFabricSwSubGroupSlotId
    MAX-ACCESS   read-only
    STATUS       current
    DESCRIPTION
        "Cisco UCS fabric:SwSubGroup:slotId managed object property"
    ::= { cucsFabricSwSubGroupEntry 10 }

cucsFabricSwSubGroupSwitchId OBJECT-TYPE
    SYNTAX       CucsNetworkSwitchId
    MAX-ACCESS   read-only
    STATUS       current
    DESCRIPTION
        "Cisco UCS fabric:SwSubGroup:switchId managed object property"
    ::= { cucsFabricSwSubGroupEntry 11 }

cucsFabricSwSubGroupTransport OBJECT-TYPE
    SYNTAX       CucsNetworkTransport
    MAX-ACCESS   read-only
    STATUS       current
    DESCRIPTION
        "Cisco UCS fabric:SwSubGroup:transport managed object property"
    ::= { cucsFabricSwSubGroupEntry 12 }

cucsFabricSwSubGroupType OBJECT-TYPE
    SYNTAX       CucsNetworkConnectionType
    MAX-ACCESS   read-only
    STATUS       current
    DESCRIPTION
        "Cisco UCS fabric:SwSubGroup:type managed object property"
    ::= { cucsFabricSwSubGroupEntry 13 }

cucsFabricUdldLinkPolicyTable OBJECT-TYPE
    SYNTAX           SEQUENCE OF CucsFabricUdldLinkPolicyEntry
    MAX-ACCESS       not-accessible
    STATUS           current
    DESCRIPTION
        "Cisco UCS fabric:UdldLinkPolicy managed object table"
    ::= { cucsFabricObjects 119 }

cucsFabricUdldLinkPolicyEntry OBJECT-TYPE
    SYNTAX           CucsFabricUdldLinkPolicyEntry
    MAX-ACCESS       not-accessible
    STATUS           current
    DESCRIPTION
        "Entry for the cucsFabricUdldLinkPolicyTable table."
    INDEX { cucsFabricUdldLinkPolicyInstanceId }
    ::= { cucsFabricUdldLinkPolicyTable 1 }

CucsFabricUdldLinkPolicyEntry ::= SEQUENCE {
    cucsFabricUdldLinkPolicyInstanceId                               CucsManagedObjectId,
    cucsFabricUdldLinkPolicyDn                                       CucsManagedObjectDn,
    cucsFabricUdldLinkPolicyRn                                       SnmpAdminString,
    cucsFabricUdldLinkPolicyAdminState                               CucsFabricUdldLinkPolicyAdminState,
    cucsFabricUdldLinkPolicyDescr                                    SnmpAdminString,
    cucsFabricUdldLinkPolicyIntId                                    SnmpAdminString,
    cucsFabricUdldLinkPolicyMode                                     CucsFabricUdldLinkPolicyMode,
    cucsFabricUdldLinkPolicyName                                     SnmpAdminString,
    cucsFabricUdldLinkPolicyPolicyLevel                              Gauge32,
    cucsFabricUdldLinkPolicyPolicyOwner                              CucsPolicyPolicyOwner,
    cucsFabricUdldLinkPolicyProtocol                                 CucsFabricEthUdldPolicyProtocol,
    cucsFabricUdldLinkPolicyType                                     CucsFabricEthLinkPolicyType
}

cucsFabricUdldLinkPolicyInstanceId OBJECT-TYPE
    SYNTAX       CucsManagedObjectId
    MAX-ACCESS   not-accessible
    STATUS       current
    DESCRIPTION
        "Instance identifier of the managed object."
    ::= { cucsFabricUdldLinkPolicyEntry 1 }

cucsFabricUdldLinkPolicyDn OBJECT-TYPE
    SYNTAX       CucsManagedObjectDn
    MAX-ACCESS   read-only
    STATUS       current
    DESCRIPTION
        "Cisco UCS fabric:UdldLinkPolicy:dn managed object property"
    ::= { cucsFabricUdldLinkPolicyEntry 2 }

cucsFabricUdldLinkPolicyRn OBJECT-TYPE
    SYNTAX       SnmpAdminString
    MAX-ACCESS   read-only
    STATUS       current
    DESCRIPTION
        "Cisco UCS fabric:UdldLinkPolicy:rn managed object property"
    ::= { cucsFabricUdldLinkPolicyEntry 3 }

cucsFabricUdldLinkPolicyAdminState OBJECT-TYPE
    SYNTAX       CucsFabricUdldLinkPolicyAdminState
    MAX-ACCESS   read-only
    STATUS       current
    DESCRIPTION
        "Cisco UCS fabric:UdldLinkPolicy:adminState managed
        object property"
    ::= { cucsFabricUdldLinkPolicyEntry 4 }

cucsFabricUdldLinkPolicyDescr OBJECT-TYPE
    SYNTAX       SnmpAdminString
    MAX-ACCESS   read-only
    STATUS       current
    DESCRIPTION
        "Cisco UCS fabric:UdldLinkPolicy:descr managed object property"
    ::= { cucsFabricUdldLinkPolicyEntry 5 }

cucsFabricUdldLinkPolicyIntId OBJECT-TYPE
    SYNTAX       SnmpAdminString
    MAX-ACCESS   read-only
    STATUS       current
    DESCRIPTION
        "Cisco UCS fabric:UdldLinkPolicy:intId managed object property"
    ::= { cucsFabricUdldLinkPolicyEntry 6 }

cucsFabricUdldLinkPolicyMode OBJECT-TYPE
    SYNTAX       CucsFabricUdldLinkPolicyMode
    MAX-ACCESS   read-only
    STATUS       current
    DESCRIPTION
        "Cisco UCS fabric:UdldLinkPolicy:mode managed object property"
    ::= { cucsFabricUdldLinkPolicyEntry 7 }

cucsFabricUdldLinkPolicyName OBJECT-TYPE
    SYNTAX       SnmpAdminString
    MAX-ACCESS   read-only
    STATUS       current
    DESCRIPTION
        "Cisco UCS fabric:UdldLinkPolicy:name managed object property"
    ::= { cucsFabricUdldLinkPolicyEntry 8 }

cucsFabricUdldLinkPolicyPolicyLevel OBJECT-TYPE
    SYNTAX       Gauge32
    MAX-ACCESS   read-only
    STATUS       current
    DESCRIPTION
        "Cisco UCS fabric:UdldLinkPolicy:policyLevel managed
        object property"
    ::= { cucsFabricUdldLinkPolicyEntry 9 }

cucsFabricUdldLinkPolicyPolicyOwner OBJECT-TYPE
    SYNTAX       CucsPolicyPolicyOwner
    MAX-ACCESS   read-only
    STATUS       current
    DESCRIPTION
        "Cisco UCS fabric:UdldLinkPolicy:policyOwner managed
        object property"
    ::= { cucsFabricUdldLinkPolicyEntry 10 }

cucsFabricUdldLinkPolicyProtocol OBJECT-TYPE
    SYNTAX       CucsFabricEthUdldPolicyProtocol
    MAX-ACCESS   read-only
    STATUS       current
    DESCRIPTION
        "Cisco UCS fabric:UdldLinkPolicy:protocol managed object property"
    ::= { cucsFabricUdldLinkPolicyEntry 11 }

cucsFabricUdldLinkPolicyType OBJECT-TYPE
    SYNTAX       CucsFabricEthLinkPolicyType
    MAX-ACCESS   read-only
    STATUS       current
    DESCRIPTION
        "Cisco UCS fabric:UdldLinkPolicy:type managed object property"
    ::= { cucsFabricUdldLinkPolicyEntry 12 }

cucsFabricUdldPolicyTable OBJECT-TYPE
    SYNTAX           SEQUENCE OF CucsFabricUdldPolicyEntry
    MAX-ACCESS       not-accessible
    STATUS           current
    DESCRIPTION
        "Cisco UCS fabric:UdldPolicy managed object table"
    ::= { cucsFabricObjects 120 }

cucsFabricUdldPolicyEntry OBJECT-TYPE
    SYNTAX           CucsFabricUdldPolicyEntry
    MAX-ACCESS       not-accessible
    STATUS           current
    DESCRIPTION
        "Entry for the cucsFabricUdldPolicyTable table."
    INDEX { cucsFabricUdldPolicyInstanceId }
    ::= { cucsFabricUdldPolicyTable 1 }

CucsFabricUdldPolicyEntry ::= SEQUENCE {
    cucsFabricUdldPolicyInstanceId                                   CucsManagedObjectId,
    cucsFabricUdldPolicyDn                                           CucsManagedObjectDn,
    cucsFabricUdldPolicyRn                                           SnmpAdminString,
    cucsFabricUdldPolicyDescr                                        SnmpAdminString,
    cucsFabricUdldPolicyIntId                                        SnmpAdminString,
    cucsFabricUdldPolicyMsgInterval                                  Gauge32,
    cucsFabricUdldPolicyName                                         SnmpAdminString,
    cucsFabricUdldPolicyPolicyLevel                                  Gauge32,
    cucsFabricUdldPolicyPolicyOwner                                  CucsPolicyPolicyOwner,
    cucsFabricUdldPolicyRecoveryAction                               CucsFabricRecoveryAction
}

cucsFabricUdldPolicyInstanceId OBJECT-TYPE
    SYNTAX       CucsManagedObjectId
    MAX-ACCESS   not-accessible
    STATUS       current
    DESCRIPTION
        "Instance identifier of the managed object."
    ::= { cucsFabricUdldPolicyEntry 1 }

cucsFabricUdldPolicyDn OBJECT-TYPE
    SYNTAX       CucsManagedObjectDn
    MAX-ACCESS   read-only
    STATUS       current
    DESCRIPTION
        "Cisco UCS fabric:UdldPolicy:dn managed object property"
    ::= { cucsFabricUdldPolicyEntry 2 }

cucsFabricUdldPolicyRn OBJECT-TYPE
    SYNTAX       SnmpAdminString
    MAX-ACCESS   read-only
    STATUS       current
    DESCRIPTION
        "Cisco UCS fabric:UdldPolicy:rn managed object property"
    ::= { cucsFabricUdldPolicyEntry 3 }

cucsFabricUdldPolicyDescr OBJECT-TYPE
    SYNTAX       SnmpAdminString
    MAX-ACCESS   read-only
    STATUS       current
    DESCRIPTION
        "Cisco UCS fabric:UdldPolicy:descr managed object property"
    ::= { cucsFabricUdldPolicyEntry 4 }

cucsFabricUdldPolicyIntId OBJECT-TYPE
    SYNTAX       SnmpAdminString
    MAX-ACCESS   read-only
    STATUS       current
    DESCRIPTION
        "Cisco UCS fabric:UdldPolicy:intId managed object property"
    ::= { cucsFabricUdldPolicyEntry 5 }

cucsFabricUdldPolicyMsgInterval OBJECT-TYPE
    SYNTAX       Gauge32
    MAX-ACCESS   read-only
    STATUS       current
    DESCRIPTION
        "Cisco UCS fabric:UdldPolicy:msgInterval managed object property"
    ::= { cucsFabricUdldPolicyEntry 6 }

cucsFabricUdldPolicyName OBJECT-TYPE
    SYNTAX       SnmpAdminString
    MAX-ACCESS   read-only
    STATUS       current
    DESCRIPTION
        "Cisco UCS fabric:UdldPolicy:name managed object property"
    ::= { cucsFabricUdldPolicyEntry 7 }

cucsFabricUdldPolicyPolicyLevel OBJECT-TYPE
    SYNTAX       Gauge32
    MAX-ACCESS   read-only
    STATUS       current
    DESCRIPTION
        "Cisco UCS fabric:UdldPolicy:policyLevel managed object property"
    ::= { cucsFabricUdldPolicyEntry 8 }

cucsFabricUdldPolicyPolicyOwner OBJECT-TYPE
    SYNTAX       CucsPolicyPolicyOwner
    MAX-ACCESS   read-only
    STATUS       current
    DESCRIPTION
        "Cisco UCS fabric:UdldPolicy:policyOwner managed object property"
    ::= { cucsFabricUdldPolicyEntry 9 }

cucsFabricUdldPolicyRecoveryAction OBJECT-TYPE
    SYNTAX       CucsFabricRecoveryAction
    MAX-ACCESS   read-only
    STATUS       current
    DESCRIPTION
        "Cisco UCS fabric:UdldPolicy:recoveryAction managed
        object property"
    ::= { cucsFabricUdldPolicyEntry 10 }

cucsFabricVConTable OBJECT-TYPE
    SYNTAX           SEQUENCE OF CucsFabricVConEntry
    MAX-ACCESS       not-accessible
    STATUS           current
    DESCRIPTION
        "Cisco UCS fabric:VCon managed object table"
    ::= { cucsFabricObjects 58 }

cucsFabricVConEntry OBJECT-TYPE
    SYNTAX           CucsFabricVConEntry
    MAX-ACCESS       not-accessible
    STATUS           current
    DESCRIPTION
        "Entry for the cucsFabricVConTable table."
    INDEX { cucsFabricVConInstanceId }
    ::= { cucsFabricVConTable 1 }

CucsFabricVConEntry ::= SEQUENCE {
    cucsFabricVConInstanceId                                         CucsManagedObjectId,
    cucsFabricVConDn                                                 CucsManagedObjectDn,
    cucsFabricVConRn                                                 SnmpAdminString,
    cucsFabricVConFabric                                             SnmpAdminString,
    cucsFabricVConId                                                 SnmpAdminString,
    cucsFabricVConPlacement                                          CucsFabricVConPlacementPref,
    cucsFabricVConSelect                                             CucsFabricVConSelectPref,
    cucsFabricVConShare                                              CucsFabricVConSharePref,
    cucsFabricVConTransport                                          CucsFabricVConTransportPref,
    cucsFabricVConEquipmentDn                                        SnmpAdminString,
    cucsFabricVConInstType                                           CucsFabricVConInstType,
    cucsFabricVConPropAcl                                            Unsigned64
}

cucsFabricVConInstanceId OBJECT-TYPE
    SYNTAX       CucsManagedObjectId
    MAX-ACCESS   not-accessible
    STATUS       current
    DESCRIPTION
        "Instance identifier of the managed object."
    ::= { cucsFabricVConEntry 1 }

cucsFabricVConDn OBJECT-TYPE
    SYNTAX       CucsManagedObjectDn
    MAX-ACCESS   read-only
    STATUS       current
    DESCRIPTION
        "Cisco UCS fabric:VCon:dn managed object property"
    ::= { cucsFabricVConEntry 2 }

cucsFabricVConRn OBJECT-TYPE
    SYNTAX       SnmpAdminString
    MAX-ACCESS   read-only
    STATUS       current
    DESCRIPTION
        "Cisco UCS fabric:VCon:rn managed object property"
    ::= { cucsFabricVConEntry 3 }

cucsFabricVConFabric OBJECT-TYPE
    SYNTAX       SnmpAdminString
    MAX-ACCESS   read-only
    STATUS       current
    DESCRIPTION
        "Cisco UCS fabric:VCon:fabric managed object property"
    ::= { cucsFabricVConEntry 4 }

cucsFabricVConId OBJECT-TYPE
    SYNTAX       SnmpAdminString
    MAX-ACCESS   read-only
    STATUS       current
    DESCRIPTION
        "Cisco UCS fabric:VCon:id managed object property"
    ::= { cucsFabricVConEntry 5 }

cucsFabricVConPlacement OBJECT-TYPE
    SYNTAX       CucsFabricVConPlacementPref
    MAX-ACCESS   read-only
    STATUS       current
    DESCRIPTION
        "Cisco UCS fabric:VCon:placement managed object property"
    ::= { cucsFabricVConEntry 6 }

cucsFabricVConSelect OBJECT-TYPE
    SYNTAX       CucsFabricVConSelectPref
    MAX-ACCESS   read-only
    STATUS       current
    DESCRIPTION
        "Cisco UCS fabric:VCon:select managed object property"
    ::= { cucsFabricVConEntry 7 }

cucsFabricVConShare OBJECT-TYPE
    SYNTAX       CucsFabricVConSharePref
    MAX-ACCESS   read-only
    STATUS       current
    DESCRIPTION
        "Cisco UCS fabric:VCon:share managed object property"
    ::= { cucsFabricVConEntry 8 }

cucsFabricVConTransport OBJECT-TYPE
    SYNTAX       CucsFabricVConTransportPref
    MAX-ACCESS   read-only
    STATUS       current
    DESCRIPTION
        "Cisco UCS fabric:VCon:transport managed object property"
    ::= { cucsFabricVConEntry 9 }

cucsFabricVConEquipmentDn OBJECT-TYPE
    SYNTAX       SnmpAdminString
    MAX-ACCESS   read-only
    STATUS       current
    DESCRIPTION
        "Cisco UCS fabric:VCon:equipmentDn managed object property"
    ::= { cucsFabricVConEntry 10 }

cucsFabricVConInstType OBJECT-TYPE
    SYNTAX       CucsFabricVConInstType
    MAX-ACCESS   read-only
    STATUS       current
    DESCRIPTION
        "Cisco UCS fabric:VCon:instType managed object property"
    ::= { cucsFabricVConEntry 11 }

cucsFabricVConPropAcl OBJECT-TYPE
    SYNTAX       Unsigned64
    MAX-ACCESS   read-only
    STATUS       current
    DESCRIPTION
        "Cisco UCS fabric:VCon:propAcl managed object property"
    ::= { cucsFabricVConEntry 12 }

cucsFabricVConProfileTable OBJECT-TYPE
    SYNTAX           SEQUENCE OF CucsFabricVConProfileEntry
    MAX-ACCESS       not-accessible
    STATUS           current
    DESCRIPTION
        "Cisco UCS fabric:VConProfile managed object table"
    ::= { cucsFabricObjects 59 }

cucsFabricVConProfileEntry OBJECT-TYPE
    SYNTAX           CucsFabricVConProfileEntry
    MAX-ACCESS       not-accessible
    STATUS           current
    DESCRIPTION
        "Entry for the cucsFabricVConProfileTable table."
    INDEX { cucsFabricVConProfileInstanceId }
    ::= { cucsFabricVConProfileTable 1 }

CucsFabricVConProfileEntry ::= SEQUENCE {
    cucsFabricVConProfileInstanceId                                  CucsManagedObjectId,
    cucsFabricVConProfileDn                                          CucsManagedObjectDn,
    cucsFabricVConProfileRn                                          SnmpAdminString,
    cucsFabricVConProfileDescr                                       SnmpAdminString,
    cucsFabricVConProfileIntId                                       SnmpAdminString,
    cucsFabricVConProfileName                                        SnmpAdminString,
    cucsFabricVConProfileMezzMapping                                 CucsFabricVConMappingScheme,
    cucsFabricVConProfilePolicyLevel                                 Gauge32,
    cucsFabricVConProfilePolicyOwner                                 CucsPolicyPolicyOwner
}

cucsFabricVConProfileInstanceId OBJECT-TYPE
    SYNTAX       CucsManagedObjectId
    MAX-ACCESS   not-accessible
    STATUS       current
    DESCRIPTION
        "Instance identifier of the managed object."
    ::= { cucsFabricVConProfileEntry 1 }

cucsFabricVConProfileDn OBJECT-TYPE
    SYNTAX       CucsManagedObjectDn
    MAX-ACCESS   read-only
    STATUS       current
    DESCRIPTION
        "Cisco UCS fabric:VConProfile:dn managed object property"
    ::= { cucsFabricVConProfileEntry 2 }

cucsFabricVConProfileRn OBJECT-TYPE
    SYNTAX       SnmpAdminString
    MAX-ACCESS   read-only
    STATUS       current
    DESCRIPTION
        "Cisco UCS fabric:VConProfile:rn managed object property"
    ::= { cucsFabricVConProfileEntry 3 }

cucsFabricVConProfileDescr OBJECT-TYPE
    SYNTAX       SnmpAdminString
    MAX-ACCESS   read-only
    STATUS       current
    DESCRIPTION
        "Cisco UCS fabric:VConProfile:descr managed object property"
    ::= { cucsFabricVConProfileEntry 4 }

cucsFabricVConProfileIntId OBJECT-TYPE
    SYNTAX       SnmpAdminString
    MAX-ACCESS   read-only
    STATUS       current
    DESCRIPTION
        "Cisco UCS fabric:VConProfile:intId managed object property"
    ::= { cucsFabricVConProfileEntry 5 }

cucsFabricVConProfileName OBJECT-TYPE
    SYNTAX       SnmpAdminString
    MAX-ACCESS   read-only
    STATUS       current
    DESCRIPTION
        "Cisco UCS fabric:VConProfile:name managed object property"
    ::= { cucsFabricVConProfileEntry 6 }

cucsFabricVConProfileMezzMapping OBJECT-TYPE
    SYNTAX       CucsFabricVConMappingScheme
    MAX-ACCESS   read-only
    STATUS       current
    DESCRIPTION
        "Cisco UCS fabric:VConProfile:mezzMapping managed object property"
    ::= { cucsFabricVConProfileEntry 7 }

cucsFabricVConProfilePolicyLevel OBJECT-TYPE
    SYNTAX       Gauge32
    MAX-ACCESS   read-only
    STATUS       current
    DESCRIPTION
        "Cisco UCS fabric:VConProfile:policyLevel managed object property"
    ::= { cucsFabricVConProfileEntry 8 }

cucsFabricVConProfilePolicyOwner OBJECT-TYPE
    SYNTAX       CucsPolicyPolicyOwner
    MAX-ACCESS   read-only
    STATUS       current
    DESCRIPTION
        "Cisco UCS fabric:VConProfile:policyOwner managed object property"
    ::= { cucsFabricVConProfileEntry 9 }

cucsFabricVlanTable OBJECT-TYPE
    SYNTAX           SEQUENCE OF CucsFabricVlanEntry
    MAX-ACCESS       not-accessible
    STATUS           current
    DESCRIPTION
        "Cisco UCS fabric:Vlan managed object table"
    ::= { cucsFabricObjects 60 }

cucsFabricVlanEntry OBJECT-TYPE
    SYNTAX           CucsFabricVlanEntry
    MAX-ACCESS       not-accessible
    STATUS           current
    DESCRIPTION
        "Entry for the cucsFabricVlanTable table."
    INDEX { cucsFabricVlanInstanceId }
    ::= { cucsFabricVlanTable 1 }

CucsFabricVlanEntry ::= SEQUENCE {
    cucsFabricVlanInstanceId                                         CucsManagedObjectId,
    cucsFabricVlanDn                                                 CucsManagedObjectDn,
    cucsFabricVlanRn                                                 SnmpAdminString,
    cucsFabricVlanDefaultNet                                         TruthValue,
    cucsFabricVlanEndPtDn                                            SnmpAdminString,
    cucsFabricVlanId                                                 Gauge32,
    cucsFabricVlanIfRole                                             CucsFabricVnetEpIfRole,
    cucsFabricVlanIfType                                             CucsNetworkVnetEpIfType,
    cucsFabricVlanLocale                                             CucsFabricVnetEpLocale,
    cucsFabricVlanName                                               SnmpAdminString,
    cucsFabricVlanPeerDn                                             SnmpAdminString,
    cucsFabricVlanPubNwDn                                            SnmpAdminString,
    cucsFabricVlanPubNwId                                            Gauge32,
    cucsFabricVlanPubNwName                                          SnmpAdminString,
    cucsFabricVlanSharing                                            CucsFabricAVlanSharing,
    cucsFabricVlanSwitchId                                           CucsFabricVlanSwitchId,
    cucsFabricVlanTransport                                          CucsFabricAVlanTransport,
    cucsFabricVlanType                                               CucsFabricAVlanType,
    cucsFabricVlanOperState                                          CucsFabricVlanOperState,
    cucsFabricVlanCloud                                              CucsFabricCloudType,
    cucsFabricVlanCompressionType                                    CucsFabricVlanCompType,
    cucsFabricVlanConfigIssues                                       CucsFabricVlanConfigIssues,
    cucsFabricVlanFltAggr                                            Unsigned64,
    cucsFabricVlanMcastPolicyName                                    SnmpAdminString,
    cucsFabricVlanOperMcastPolicyName                                SnmpAdminString,
    cucsFabricVlanGlobal                                             Unsigned64,
    cucsFabricVlanLocal                                              Unsigned64,
    cucsFabricVlanPolicyOwner                                        CucsFabricVnetEpPolicyOwner,
    cucsFabricVlanAssocPrimaryVlanState                              CucsFabricVlanAssocPrimaryVlanState,
    cucsFabricVlanAssocPrimaryVlanSwitchId                           CucsFabricAVlanAssocPrimaryVlanSwitchId,
    cucsFabricVlanOverlapStateForA                                   CucsFabricVlanOverlapState,
    cucsFabricVlanOverlapStateForB                                   CucsFabricVlanOverlapState
}

cucsFabricVlanInstanceId OBJECT-TYPE
    SYNTAX       CucsManagedObjectId
    MAX-ACCESS   not-accessible
    STATUS       current
    DESCRIPTION
        "Instance identifier of the managed object."
    ::= { cucsFabricVlanEntry 1 }

cucsFabricVlanDn OBJECT-TYPE
    SYNTAX       CucsManagedObjectDn
    MAX-ACCESS   read-only
    STATUS       current
    DESCRIPTION
        "Cisco UCS fabric:Vlan:dn managed object property"
    ::= { cucsFabricVlanEntry 2 }

cucsFabricVlanRn OBJECT-TYPE
    SYNTAX       SnmpAdminString
    MAX-ACCESS   read-only
    STATUS       current
    DESCRIPTION
        "Cisco UCS fabric:Vlan:rn managed object property"
    ::= { cucsFabricVlanEntry 3 }

cucsFabricVlanDefaultNet OBJECT-TYPE
    SYNTAX       TruthValue
    MAX-ACCESS   read-only
    STATUS       current
    DESCRIPTION
        "Cisco UCS fabric:Vlan:defaultNet managed object property"
    ::= { cucsFabricVlanEntry 4 }

cucsFabricVlanEndPtDn OBJECT-TYPE
    SYNTAX       SnmpAdminString
    MAX-ACCESS   read-only
    STATUS       current
    DESCRIPTION
        "Cisco UCS fabric:Vlan:epDn managed object property"
    ::= { cucsFabricVlanEntry 5 }

cucsFabricVlanId OBJECT-TYPE
    SYNTAX       Gauge32
    MAX-ACCESS   read-only
    STATUS       current
    DESCRIPTION
        "Cisco UCS fabric:Vlan:id managed object property"
    ::= { cucsFabricVlanEntry 6 }

cucsFabricVlanIfRole OBJECT-TYPE
    SYNTAX       CucsFabricVnetEpIfRole
    MAX-ACCESS   read-only
    STATUS       current
    DESCRIPTION
        "Cisco UCS fabric:Vlan:ifRole managed object property"
    ::= { cucsFabricVlanEntry 7 }

cucsFabricVlanIfType OBJECT-TYPE
    SYNTAX       CucsNetworkVnetEpIfType
    MAX-ACCESS   read-only
    STATUS       current
    DESCRIPTION
        "Cisco UCS fabric:Vlan:ifType managed object property"
    ::= { cucsFabricVlanEntry 8 }

cucsFabricVlanLocale OBJECT-TYPE
    SYNTAX       CucsFabricVnetEpLocale
    MAX-ACCESS   read-only
    STATUS       current
    DESCRIPTION
        "Cisco UCS fabric:Vlan:locale managed object property"
    ::= { cucsFabricVlanEntry 9 }

cucsFabricVlanName OBJECT-TYPE
    SYNTAX       SnmpAdminString
    MAX-ACCESS   read-only
    STATUS       current
    DESCRIPTION
        "Cisco UCS fabric:Vlan:name managed object property"
    ::= { cucsFabricVlanEntry 10 }

cucsFabricVlanPeerDn OBJECT-TYPE
    SYNTAX       SnmpAdminString
    MAX-ACCESS   read-only
    STATUS       current
    DESCRIPTION
        "Cisco UCS fabric:Vlan:peerDn managed object property"
    ::= { cucsFabricVlanEntry 11 }

cucsFabricVlanPubNwDn OBJECT-TYPE
    SYNTAX       SnmpAdminString
    MAX-ACCESS   read-only
    STATUS       current
    DESCRIPTION
        "Cisco UCS fabric:Vlan:pubNwDn managed object property"
    ::= { cucsFabricVlanEntry 12 }

cucsFabricVlanPubNwId OBJECT-TYPE
    SYNTAX       Gauge32
    MAX-ACCESS   read-only
    STATUS       current
    DESCRIPTION
        "Cisco UCS fabric:Vlan:pubNwId managed object property"
    ::= { cucsFabricVlanEntry 13 }

cucsFabricVlanPubNwName OBJECT-TYPE
    SYNTAX       SnmpAdminString
    MAX-ACCESS   read-only
    STATUS       current
    DESCRIPTION
        "Cisco UCS fabric:Vlan:pubNwName managed object property"
    ::= { cucsFabricVlanEntry 14 }

cucsFabricVlanSharing OBJECT-TYPE
    SYNTAX       CucsFabricAVlanSharing
    MAX-ACCESS   read-only
    STATUS       current
    DESCRIPTION
        "Cisco UCS fabric:Vlan:sharing managed object property"
    ::= { cucsFabricVlanEntry 15 }

cucsFabricVlanSwitchId OBJECT-TYPE
    SYNTAX       CucsFabricVlanSwitchId
    MAX-ACCESS   read-only
    STATUS       current
    DESCRIPTION
        "Cisco UCS fabric:Vlan:switchId managed object property"
    ::= { cucsFabricVlanEntry 16 }

cucsFabricVlanTransport OBJECT-TYPE
    SYNTAX       CucsFabricAVlanTransport
    MAX-ACCESS   read-only
    STATUS       current
    DESCRIPTION
        "Cisco UCS fabric:Vlan:transport managed object property"
    ::= { cucsFabricVlanEntry 17 }

cucsFabricVlanType OBJECT-TYPE
    SYNTAX       CucsFabricAVlanType
    MAX-ACCESS   read-only
    STATUS       current
    DESCRIPTION
        "Cisco UCS fabric:Vlan:type managed object property"
    ::= { cucsFabricVlanEntry 18 }

cucsFabricVlanOperState OBJECT-TYPE
    SYNTAX       CucsFabricVlanOperState
    MAX-ACCESS   read-only
    STATUS       current
    DESCRIPTION
        "Cisco UCS fabric:Vlan:operState managed object property"
    ::= { cucsFabricVlanEntry 19 }

cucsFabricVlanCloud OBJECT-TYPE
    SYNTAX       CucsFabricCloudType
    MAX-ACCESS   read-only
    STATUS       current
    DESCRIPTION
        "Cisco UCS fabric:Vlan:cloud managed object property"
    ::= { cucsFabricVlanEntry 20 }

cucsFabricVlanCompressionType OBJECT-TYPE
    SYNTAX       CucsFabricVlanCompType
    MAX-ACCESS   read-only
    STATUS       current
    DESCRIPTION
        "Cisco UCS fabric:Vlan:compressionType managed object property"
    ::= { cucsFabricVlanEntry 21 }

cucsFabricVlanConfigIssues OBJECT-TYPE
    SYNTAX       CucsFabricVlanConfigIssues
    MAX-ACCESS   read-only
    STATUS       current
    DESCRIPTION
        "Cisco UCS fabric:Vlan:configIssues managed object property"
    ::= { cucsFabricVlanEntry 22 }

cucsFabricVlanFltAggr OBJECT-TYPE
    SYNTAX       Unsigned64
    MAX-ACCESS   read-only
    STATUS       current
    DESCRIPTION
        "Cisco UCS fabric:Vlan:fltAggr managed object property"
    ::= { cucsFabricVlanEntry 23 }

cucsFabricVlanMcastPolicyName OBJECT-TYPE
    SYNTAX       SnmpAdminString
    MAX-ACCESS   read-only
    STATUS       current
    DESCRIPTION
        "Cisco UCS fabric:Vlan:mcastPolicyName managed object property"
    ::= { cucsFabricVlanEntry 24 }

cucsFabricVlanOperMcastPolicyName OBJECT-TYPE
    SYNTAX       SnmpAdminString
    MAX-ACCESS   read-only
    STATUS       current
    DESCRIPTION
        "Cisco UCS fabric:Vlan:operMcastPolicyName managed
        object property"
    ::= { cucsFabricVlanEntry 25 }

cucsFabricVlanGlobal OBJECT-TYPE
    SYNTAX       Unsigned64
    MAX-ACCESS   read-only
    STATUS       current
    DESCRIPTION
        "Cisco UCS fabric:Vlan:global managed object property"
    ::= { cucsFabricVlanEntry 26 }

cucsFabricVlanLocal OBJECT-TYPE
    SYNTAX       Unsigned64
    MAX-ACCESS   read-only
    STATUS       current
    DESCRIPTION
        "Cisco UCS fabric:Vlan:local managed object property"
    ::= { cucsFabricVlanEntry 28 }

cucsFabricVlanPolicyOwner OBJECT-TYPE
    SYNTAX       CucsFabricVnetEpPolicyOwner
    MAX-ACCESS   read-only
    STATUS       current
    DESCRIPTION
        "Cisco UCS fabric:Vlan:policyOwner managed object property"
    ::= { cucsFabricVlanEntry 29 }

cucsFabricVlanAssocPrimaryVlanState OBJECT-TYPE
    SYNTAX       CucsFabricVlanAssocPrimaryVlanState
    MAX-ACCESS   read-only
    STATUS       current
    DESCRIPTION
        "Cisco UCS fabric:Vlan:assocPrimaryVlanState managed
        object property"
    ::= { cucsFabricVlanEntry 30 }

cucsFabricVlanAssocPrimaryVlanSwitchId OBJECT-TYPE
    SYNTAX       CucsFabricAVlanAssocPrimaryVlanSwitchId
    MAX-ACCESS   read-only
    STATUS       current
    DESCRIPTION
        "Cisco UCS fabric:Vlan:assocPrimaryVlanSwitchId
        managed object property"
    ::= { cucsFabricVlanEntry 31 }

cucsFabricVlanOverlapStateForA OBJECT-TYPE
    SYNTAX       CucsFabricVlanOverlapState
    MAX-ACCESS   read-only
    STATUS       current
    DESCRIPTION
        "Cisco UCS fabric:Vlan:overlapStateForA managed object property"
    ::= { cucsFabricVlanEntry 32 }

cucsFabricVlanOverlapStateForB OBJECT-TYPE
    SYNTAX       CucsFabricVlanOverlapState
    MAX-ACCESS   read-only
    STATUS       current
    DESCRIPTION
        "Cisco UCS fabric:Vlan:overlapStateForB managed object property"
    ::= { cucsFabricVlanEntry 33 }

cucsFabricVlanEpTable OBJECT-TYPE
    SYNTAX           SEQUENCE OF CucsFabricVlanEpEntry
    MAX-ACCESS       not-accessible
    STATUS           current
    DESCRIPTION
        "Cisco UCS fabric:VlanEp managed object table"
    ::= { cucsFabricObjects 61 }

cucsFabricVlanEpEntry OBJECT-TYPE
    SYNTAX           CucsFabricVlanEpEntry
    MAX-ACCESS       not-accessible
    STATUS           current
    DESCRIPTION
        "Entry for the cucsFabricVlanEpTable table."
    INDEX { cucsFabricVlanEpInstanceId }
    ::= { cucsFabricVlanEpTable 1 }

CucsFabricVlanEpEntry ::= SEQUENCE {
    cucsFabricVlanEpInstanceId                                       CucsManagedObjectId,
    cucsFabricVlanEpDn                                               CucsManagedObjectDn,
    cucsFabricVlanEpRn                                               SnmpAdminString,
    cucsFabricVlanEpEpDn                                             SnmpAdminString,
    cucsFabricVlanEpId                                               Gauge32,
    cucsFabricVlanEpIfRole                                           CucsFabricVnetEpIfRole,
    cucsFabricVlanEpIfType                                           CucsNetworkVnetEpIfType,
    cucsFabricVlanEpIsNative                                         TruthValue,
    cucsFabricVlanEpLocale                                           CucsFabricVnetEpLocale,
    cucsFabricVlanEpName                                             SnmpAdminString,
    cucsFabricVlanEpPeerDn                                           SnmpAdminString,
    cucsFabricVlanEpPubNwDn                                          SnmpAdminString,
    cucsFabricVlanEpPubNwId                                          Gauge32,
    cucsFabricVlanEpPubNwName                                        SnmpAdminString,
    cucsFabricVlanEpSharing                                          CucsFabricAVlanSharing,
    cucsFabricVlanEpSwitchId                                         CucsNetworkSwitchId,
    cucsFabricVlanEpTransport                                        CucsFabricAVlanTransport,
    cucsFabricVlanEpType                                             CucsFabricAVlanType,
    cucsFabricVlanEpOperState                                        CucsFabricVlanOperState,
    cucsFabricVlanEpPolicyOwner                                      CucsFabricVnetEpPolicyOwner,
    cucsFabricVlanEpAssocPrimaryVlanState                            CucsFabricVlanAssocPrimaryVlanState,
    cucsFabricVlanEpAssocPrimaryVlanSwitchId                         CucsFabricAVlanAssocPrimaryVlanSwitchId,
    cucsFabricVlanEpOverlapStateForA                                 CucsFabricVlanOverlapState,
    cucsFabricVlanEpOverlapStateForB                                 CucsFabricVlanOverlapState
}

cucsFabricVlanEpInstanceId OBJECT-TYPE
    SYNTAX       CucsManagedObjectId
    MAX-ACCESS   not-accessible
    STATUS       current
    DESCRIPTION
        "Instance identifier of the managed object."
    ::= { cucsFabricVlanEpEntry 1 }

cucsFabricVlanEpDn OBJECT-TYPE
    SYNTAX       CucsManagedObjectDn
    MAX-ACCESS   read-only
    STATUS       current
    DESCRIPTION
        "Cisco UCS fabric:VlanEp:dn managed object property"
    ::= { cucsFabricVlanEpEntry 2 }

cucsFabricVlanEpRn OBJECT-TYPE
    SYNTAX       SnmpAdminString
    MAX-ACCESS   read-only
    STATUS       current
    DESCRIPTION
        "Cisco UCS fabric:VlanEp:rn managed object property"
    ::= { cucsFabricVlanEpEntry 3 }

cucsFabricVlanEpEpDn OBJECT-TYPE
    SYNTAX       SnmpAdminString
    MAX-ACCESS   read-only
    STATUS       current
    DESCRIPTION
        "Cisco UCS fabric:VlanEp:epDn managed object property"
    ::= { cucsFabricVlanEpEntry 4 }

cucsFabricVlanEpId OBJECT-TYPE
    SYNTAX       Gauge32
    MAX-ACCESS   read-only
    STATUS       current
    DESCRIPTION
        "Cisco UCS fabric:VlanEp:id managed object property"
    ::= { cucsFabricVlanEpEntry 5 }

cucsFabricVlanEpIfRole OBJECT-TYPE
    SYNTAX       CucsFabricVnetEpIfRole
    MAX-ACCESS   read-only
    STATUS       current
    DESCRIPTION
        "Cisco UCS fabric:VlanEp:ifRole managed object property"
    ::= { cucsFabricVlanEpEntry 6 }

cucsFabricVlanEpIfType OBJECT-TYPE
    SYNTAX       CucsNetworkVnetEpIfType
    MAX-ACCESS   read-only
    STATUS       current
    DESCRIPTION
        "Cisco UCS fabric:VlanEp:ifType managed object property"
    ::= { cucsFabricVlanEpEntry 7 }

cucsFabricVlanEpIsNative OBJECT-TYPE
    SYNTAX       TruthValue
    MAX-ACCESS   read-only
    STATUS       current
    DESCRIPTION
        "Cisco UCS fabric:VlanEp:isNative managed object property"
    ::= { cucsFabricVlanEpEntry 8 }

cucsFabricVlanEpLocale OBJECT-TYPE
    SYNTAX       CucsFabricVnetEpLocale
    MAX-ACCESS   read-only
    STATUS       current
    DESCRIPTION
        "Cisco UCS fabric:VlanEp:locale managed object property"
    ::= { cucsFabricVlanEpEntry 9 }

cucsFabricVlanEpName OBJECT-TYPE
    SYNTAX       SnmpAdminString
    MAX-ACCESS   read-only
    STATUS       current
    DESCRIPTION
        "Cisco UCS fabric:VlanEp:name managed object property"
    ::= { cucsFabricVlanEpEntry 10 }

cucsFabricVlanEpPeerDn OBJECT-TYPE
    SYNTAX       SnmpAdminString
    MAX-ACCESS   read-only
    STATUS       current
    DESCRIPTION
        "Cisco UCS fabric:VlanEp:peerDn managed object property"
    ::= { cucsFabricVlanEpEntry 11 }

cucsFabricVlanEpPubNwDn OBJECT-TYPE
    SYNTAX       SnmpAdminString
    MAX-ACCESS   read-only
    STATUS       current
    DESCRIPTION
        "Cisco UCS fabric:VlanEp:pubNwDn managed object property"
    ::= { cucsFabricVlanEpEntry 12 }

cucsFabricVlanEpPubNwId OBJECT-TYPE
    SYNTAX       Gauge32
    MAX-ACCESS   read-only
    STATUS       current
    DESCRIPTION
        "Cisco UCS fabric:VlanEp:pubNwId managed object property"
    ::= { cucsFabricVlanEpEntry 13 }

cucsFabricVlanEpPubNwName OBJECT-TYPE
    SYNTAX       SnmpAdminString
    MAX-ACCESS   read-only
    STATUS       current
    DESCRIPTION
        "Cisco UCS fabric:VlanEp:pubNwName managed object property"
    ::= { cucsFabricVlanEpEntry 14 }

cucsFabricVlanEpSharing OBJECT-TYPE
    SYNTAX       CucsFabricAVlanSharing
    MAX-ACCESS   read-only
    STATUS       current
    DESCRIPTION
        "Cisco UCS fabric:VlanEp:sharing managed object property"
    ::= { cucsFabricVlanEpEntry 15 }

cucsFabricVlanEpSwitchId OBJECT-TYPE
    SYNTAX       CucsNetworkSwitchId
    MAX-ACCESS   read-only
    STATUS       current
    DESCRIPTION
        "Cisco UCS fabric:VlanEp:switchId managed object property"
    ::= { cucsFabricVlanEpEntry 16 }

cucsFabricVlanEpTransport OBJECT-TYPE
    SYNTAX       CucsFabricAVlanTransport
    MAX-ACCESS   read-only
    STATUS       current
    DESCRIPTION
        "Cisco UCS fabric:VlanEp:transport managed object property"
    ::= { cucsFabricVlanEpEntry 17 }

cucsFabricVlanEpType OBJECT-TYPE
    SYNTAX       CucsFabricAVlanType
    MAX-ACCESS   read-only
    STATUS       current
    DESCRIPTION
        "Cisco UCS fabric:VlanEp:type managed object property"
    ::= { cucsFabricVlanEpEntry 18 }

cucsFabricVlanEpOperState OBJECT-TYPE
    SYNTAX       CucsFabricVlanOperState
    MAX-ACCESS   read-only
    STATUS       current
    DESCRIPTION
        "Cisco UCS fabric:VlanEp:operState managed object property"
    ::= { cucsFabricVlanEpEntry 19 }

cucsFabricVlanEpPolicyOwner OBJECT-TYPE
    SYNTAX       CucsFabricVnetEpPolicyOwner
    MAX-ACCESS   read-only
    STATUS       current
    DESCRIPTION
        "Cisco UCS fabric:VlanEp:policyOwner managed object property"
    ::= { cucsFabricVlanEpEntry 21 }

cucsFabricVlanEpAssocPrimaryVlanState OBJECT-TYPE
    SYNTAX       CucsFabricVlanAssocPrimaryVlanState
    MAX-ACCESS   read-only
    STATUS       current
    DESCRIPTION
        "Cisco UCS fabric:VlanEp:assocPrimaryVlanState
        managed object property"
    ::= { cucsFabricVlanEpEntry 22 }

cucsFabricVlanEpAssocPrimaryVlanSwitchId OBJECT-TYPE
    SYNTAX       CucsFabricAVlanAssocPrimaryVlanSwitchId
    MAX-ACCESS   read-only
    STATUS       current
    DESCRIPTION
        "Cisco UCS fabric:VlanEp:assocPrimaryVlanSwitchId
        managed object property"
    ::= { cucsFabricVlanEpEntry 23 }

cucsFabricVlanEpOverlapStateForA OBJECT-TYPE
    SYNTAX       CucsFabricVlanOverlapState
    MAX-ACCESS   read-only
    STATUS       current
    DESCRIPTION
        "Cisco UCS fabric:VlanEp:overlapStateForA managed object property"
    ::= { cucsFabricVlanEpEntry 24 }

cucsFabricVlanEpOverlapStateForB OBJECT-TYPE
    SYNTAX       CucsFabricVlanOverlapState
    MAX-ACCESS   read-only
    STATUS       current
    DESCRIPTION
        "Cisco UCS fabric:VlanEp:overlapStateForB managed object property"
    ::= { cucsFabricVlanEpEntry 25 }

cucsFabricVlanGroupReqTable OBJECT-TYPE
    SYNTAX           SEQUENCE OF CucsFabricVlanGroupReqEntry
    MAX-ACCESS       not-accessible
    STATUS           current
    DESCRIPTION
        "Cisco UCS fabric:VlanGroupReq managed object table"
    ::= { cucsFabricObjects 92 }

cucsFabricVlanGroupReqEntry OBJECT-TYPE
    SYNTAX           CucsFabricVlanGroupReqEntry
    MAX-ACCESS       not-accessible
    STATUS           current
    DESCRIPTION
        "Entry for the cucsFabricVlanGroupReqTable table."
    INDEX { cucsFabricVlanGroupReqInstanceId }
    ::= { cucsFabricVlanGroupReqTable 1 }

CucsFabricVlanGroupReqEntry ::= SEQUENCE {
    cucsFabricVlanGroupReqInstanceId                                 CucsManagedObjectId,
    cucsFabricVlanGroupReqDn                                         CucsManagedObjectDn,
    cucsFabricVlanGroupReqRn                                         SnmpAdminString,
    cucsFabricVlanGroupReqConfigIssues                               CucsFabricReqIssues,
    cucsFabricVlanGroupReqName                                       SnmpAdminString,
    cucsFabricVlanGroupReqType                                       CucsFabricAccessType
}

cucsFabricVlanGroupReqInstanceId OBJECT-TYPE
    SYNTAX       CucsManagedObjectId
    MAX-ACCESS   not-accessible
    STATUS       current
    DESCRIPTION
        "Instance identifier of the managed object."
    ::= { cucsFabricVlanGroupReqEntry 1 }

cucsFabricVlanGroupReqDn OBJECT-TYPE
    SYNTAX       CucsManagedObjectDn
    MAX-ACCESS   read-only
    STATUS       current
    DESCRIPTION
        "Cisco UCS fabric:VlanGroupReq:dn managed object property"
    ::= { cucsFabricVlanGroupReqEntry 2 }

cucsFabricVlanGroupReqRn OBJECT-TYPE
    SYNTAX       SnmpAdminString
    MAX-ACCESS   read-only
    STATUS       current
    DESCRIPTION
        "Cisco UCS fabric:VlanGroupReq:rn managed object property"
    ::= { cucsFabricVlanGroupReqEntry 3 }

cucsFabricVlanGroupReqConfigIssues OBJECT-TYPE
    SYNTAX       CucsFabricReqIssues
    MAX-ACCESS   read-only
    STATUS       current
    DESCRIPTION
        "Cisco UCS fabric:VlanGroupReq:configIssues managed
        object property"
    ::= { cucsFabricVlanGroupReqEntry 4 }

cucsFabricVlanGroupReqName OBJECT-TYPE
    SYNTAX       SnmpAdminString
    MAX-ACCESS   read-only
    STATUS       current
    DESCRIPTION
        "Cisco UCS fabric:VlanGroupReq:name managed object property"
    ::= { cucsFabricVlanGroupReqEntry 5 }

cucsFabricVlanGroupReqType OBJECT-TYPE
    SYNTAX       CucsFabricAccessType
    MAX-ACCESS   read-only
    STATUS       current
    DESCRIPTION
        "Cisco UCS fabric:VlanGroupReq:type managed object property"
    ::= { cucsFabricVlanGroupReqEntry 6 }

cucsFabricVlanPermitTable OBJECT-TYPE
    SYNTAX           SEQUENCE OF CucsFabricVlanPermitEntry
    MAX-ACCESS       not-accessible
    STATUS           current
    DESCRIPTION
        "Cisco UCS fabric:VlanPermit managed object table"
    ::= { cucsFabricObjects 93 }

cucsFabricVlanPermitEntry OBJECT-TYPE
    SYNTAX           CucsFabricVlanPermitEntry
    MAX-ACCESS       not-accessible
    STATUS           current
    DESCRIPTION
        "Entry for the cucsFabricVlanPermitTable table."
    INDEX { cucsFabricVlanPermitInstanceId }
    ::= { cucsFabricVlanPermitTable 1 }

CucsFabricVlanPermitEntry ::= SEQUENCE {
    cucsFabricVlanPermitInstanceId                                   CucsManagedObjectId,
    cucsFabricVlanPermitDn                                           CucsManagedObjectDn,
    cucsFabricVlanPermitRn                                           SnmpAdminString,
    cucsFabricVlanPermitCloud                                        CucsFabricCloudType,
    cucsFabricVlanPermitName                                         SnmpAdminString,
    cucsFabricVlanPermitSwitchId                                     SnmpAdminString
}

cucsFabricVlanPermitInstanceId OBJECT-TYPE
    SYNTAX       CucsManagedObjectId
    MAX-ACCESS   not-accessible
    STATUS       current
    DESCRIPTION
        "Instance identifier of the managed object."
    ::= { cucsFabricVlanPermitEntry 1 }

cucsFabricVlanPermitDn OBJECT-TYPE
    SYNTAX       CucsManagedObjectDn
    MAX-ACCESS   read-only
    STATUS       current
    DESCRIPTION
        "Cisco UCS fabric:VlanPermit:dn managed object property"
    ::= { cucsFabricVlanPermitEntry 2 }

cucsFabricVlanPermitRn OBJECT-TYPE
    SYNTAX       SnmpAdminString
    MAX-ACCESS   read-only
    STATUS       current
    DESCRIPTION
        "Cisco UCS fabric:VlanPermit:rn managed object property"
    ::= { cucsFabricVlanPermitEntry 3 }

cucsFabricVlanPermitCloud OBJECT-TYPE
    SYNTAX       CucsFabricCloudType
    MAX-ACCESS   read-only
    STATUS       current
    DESCRIPTION
        "Cisco UCS fabric:VlanPermit:cloud managed object property"
    ::= { cucsFabricVlanPermitEntry 4 }

cucsFabricVlanPermitName OBJECT-TYPE
    SYNTAX       SnmpAdminString
    MAX-ACCESS   read-only
    STATUS       current
    DESCRIPTION
        "Cisco UCS fabric:VlanPermit:name managed object property"
    ::= { cucsFabricVlanPermitEntry 5 }

cucsFabricVlanPermitSwitchId OBJECT-TYPE
    SYNTAX       SnmpAdminString
    MAX-ACCESS   read-only
    STATUS       current
    DESCRIPTION
        "Cisco UCS fabric:VlanPermit:switchId managed object property"
    ::= { cucsFabricVlanPermitEntry 6 }

cucsFabricVlanReqTable OBJECT-TYPE
    SYNTAX           SEQUENCE OF CucsFabricVlanReqEntry
    MAX-ACCESS       not-accessible
    STATUS           current
    DESCRIPTION
        "Cisco UCS fabric:VlanReq managed object table"
    ::= { cucsFabricObjects 94 }

cucsFabricVlanReqEntry OBJECT-TYPE
    SYNTAX           CucsFabricVlanReqEntry
    MAX-ACCESS       not-accessible
    STATUS           current
    DESCRIPTION
        "Entry for the cucsFabricVlanReqTable table."
    INDEX { cucsFabricVlanReqInstanceId }
    ::= { cucsFabricVlanReqTable 1 }

CucsFabricVlanReqEntry ::= SEQUENCE {
    cucsFabricVlanReqInstanceId                                      CucsManagedObjectId,
    cucsFabricVlanReqDn                                              CucsManagedObjectDn,
    cucsFabricVlanReqRn                                              SnmpAdminString,
    cucsFabricVlanReqConfigIssues                                    CucsFabricReqIssues,
    cucsFabricVlanReqName                                            SnmpAdminString,
    cucsFabricVlanReqType                                            CucsFabricAccessType
}

cucsFabricVlanReqInstanceId OBJECT-TYPE
    SYNTAX       CucsManagedObjectId
    MAX-ACCESS   not-accessible
    STATUS       current
    DESCRIPTION
        "Instance identifier of the managed object."
    ::= { cucsFabricVlanReqEntry 1 }

cucsFabricVlanReqDn OBJECT-TYPE
    SYNTAX       CucsManagedObjectDn
    MAX-ACCESS   read-only
    STATUS       current
    DESCRIPTION
        "Cisco UCS fabric:VlanReq:dn managed object property"
    ::= { cucsFabricVlanReqEntry 2 }

cucsFabricVlanReqRn OBJECT-TYPE
    SYNTAX       SnmpAdminString
    MAX-ACCESS   read-only
    STATUS       current
    DESCRIPTION
        "Cisco UCS fabric:VlanReq:rn managed object property"
    ::= { cucsFabricVlanReqEntry 3 }

cucsFabricVlanReqConfigIssues OBJECT-TYPE
    SYNTAX       CucsFabricReqIssues
    MAX-ACCESS   read-only
    STATUS       current
    DESCRIPTION
        "Cisco UCS fabric:VlanReq:configIssues managed object property"
    ::= { cucsFabricVlanReqEntry 4 }

cucsFabricVlanReqName OBJECT-TYPE
    SYNTAX       SnmpAdminString
    MAX-ACCESS   read-only
    STATUS       current
    DESCRIPTION
        "Cisco UCS fabric:VlanReq:name managed object property"
    ::= { cucsFabricVlanReqEntry 5 }

cucsFabricVlanReqType OBJECT-TYPE
    SYNTAX       CucsFabricAccessType
    MAX-ACCESS   read-only
    STATUS       current
    DESCRIPTION
        "Cisco UCS fabric:VlanReq:type managed object property"
    ::= { cucsFabricVlanReqEntry 6 }

cucsFabricVnetEpSyncEpTable OBJECT-TYPE
    SYNTAX           SEQUENCE OF CucsFabricVnetEpSyncEpEntry
    MAX-ACCESS       not-accessible
    STATUS           current
    DESCRIPTION
        "Cisco UCS fabric:VnetEpSyncEp managed object table"
    ::= { cucsFabricObjects 98 }

cucsFabricVnetEpSyncEpEntry OBJECT-TYPE
    SYNTAX           CucsFabricVnetEpSyncEpEntry
    MAX-ACCESS       not-accessible
    STATUS           current
    DESCRIPTION
        "Entry for the cucsFabricVnetEpSyncEpTable table."
    INDEX { cucsFabricVnetEpSyncEpInstanceId }
    ::= { cucsFabricVnetEpSyncEpTable 1 }

CucsFabricVnetEpSyncEpEntry ::= SEQUENCE {
    cucsFabricVnetEpSyncEpInstanceId                                 CucsManagedObjectId,
    cucsFabricVnetEpSyncEpDn                                         CucsManagedObjectDn,
    cucsFabricVnetEpSyncEpRn                                         SnmpAdminString,
    cucsFabricVnetEpSyncEpFsmDescr                                   SnmpAdminString,
    cucsFabricVnetEpSyncEpFsmPrev                                    SnmpAdminString,
    cucsFabricVnetEpSyncEpFsmProgr                                   Gauge32,
    cucsFabricVnetEpSyncEpFsmRmtInvErrCode                           Gauge32,
    cucsFabricVnetEpSyncEpFsmRmtInvErrDescr                          SnmpAdminString,
    cucsFabricVnetEpSyncEpFsmRmtInvRslt                              CucsConditionRemoteInvRslt,
    cucsFabricVnetEpSyncEpFsmStageDescr                              SnmpAdminString,
    cucsFabricVnetEpSyncEpFsmStamp                                   DateAndTime,
    cucsFabricVnetEpSyncEpFsmStatus                                  SnmpAdminString,
    cucsFabricVnetEpSyncEpFsmTry                                     Gauge32,
    cucsFabricVnetEpSyncEpGenNumSync                                 Gauge32,
    cucsFabricVnetEpSyncEpId                                         Gauge32,
    cucsFabricVnetEpSyncEpIsChangedObjectUpdate                      TruthValue
}

cucsFabricVnetEpSyncEpInstanceId OBJECT-TYPE
    SYNTAX       CucsManagedObjectId
    MAX-ACCESS   not-accessible
    STATUS       current
    DESCRIPTION
        "Instance identifier of the managed object."
    ::= { cucsFabricVnetEpSyncEpEntry 1 }

cucsFabricVnetEpSyncEpDn OBJECT-TYPE
    SYNTAX       CucsManagedObjectDn
    MAX-ACCESS   read-only
    STATUS       current
    DESCRIPTION
        "Cisco UCS fabric:VnetEpSyncEp:dn managed object property"
    ::= { cucsFabricVnetEpSyncEpEntry 2 }

cucsFabricVnetEpSyncEpRn OBJECT-TYPE
    SYNTAX       SnmpAdminString
    MAX-ACCESS   read-only
    STATUS       current
    DESCRIPTION
        "Cisco UCS fabric:VnetEpSyncEp:rn managed object property"
    ::= { cucsFabricVnetEpSyncEpEntry 3 }

cucsFabricVnetEpSyncEpFsmDescr OBJECT-TYPE
    SYNTAX       SnmpAdminString
    MAX-ACCESS   read-only
    STATUS       current
    DESCRIPTION
        "Cisco UCS fabric:VnetEpSyncEp:fsmDescr managed object property"
    ::= { cucsFabricVnetEpSyncEpEntry 4 }

cucsFabricVnetEpSyncEpFsmPrev OBJECT-TYPE
    SYNTAX       SnmpAdminString
    MAX-ACCESS   read-only
    STATUS       current
    DESCRIPTION
        "Cisco UCS fabric:VnetEpSyncEp:fsmPrev managed object property"
    ::= { cucsFabricVnetEpSyncEpEntry 5 }

cucsFabricVnetEpSyncEpFsmProgr OBJECT-TYPE
    SYNTAX       Gauge32
    MAX-ACCESS   read-only
    STATUS       current
    DESCRIPTION
        "Cisco UCS fabric:VnetEpSyncEp:fsmProgr managed object property"
    ::= { cucsFabricVnetEpSyncEpEntry 6 }

cucsFabricVnetEpSyncEpFsmRmtInvErrCode OBJECT-TYPE
    SYNTAX       Gauge32
    MAX-ACCESS   read-only
    STATUS       current
    DESCRIPTION
        "Cisco UCS fabric:VnetEpSyncEp:fsmRmtInvErrCode
        managed object property"
    ::= { cucsFabricVnetEpSyncEpEntry 7 }

cucsFabricVnetEpSyncEpFsmRmtInvErrDescr OBJECT-TYPE
    SYNTAX       SnmpAdminString
    MAX-ACCESS   read-only
    STATUS       current
    DESCRIPTION
        "Cisco UCS fabric:VnetEpSyncEp:fsmRmtInvErrDescr
        managed object property"
    ::= { cucsFabricVnetEpSyncEpEntry 8 }

cucsFabricVnetEpSyncEpFsmRmtInvRslt OBJECT-TYPE
    SYNTAX       CucsConditionRemoteInvRslt
    MAX-ACCESS   read-only
    STATUS       current
    DESCRIPTION
        "Cisco UCS fabric:VnetEpSyncEp:fsmRmtInvRslt managed
        object property"
    ::= { cucsFabricVnetEpSyncEpEntry 9 }

cucsFabricVnetEpSyncEpFsmStageDescr OBJECT-TYPE
    SYNTAX       SnmpAdminString
    MAX-ACCESS   read-only
    STATUS       current
    DESCRIPTION
        "Cisco UCS fabric:VnetEpSyncEp:fsmStageDescr managed
        object property"
    ::= { cucsFabricVnetEpSyncEpEntry 10 }

cucsFabricVnetEpSyncEpFsmStamp OBJECT-TYPE
    SYNTAX       DateAndTime
    MAX-ACCESS   read-only
    STATUS       current
    DESCRIPTION
        "Cisco UCS fabric:VnetEpSyncEp:fsmStamp managed object property"
    ::= { cucsFabricVnetEpSyncEpEntry 11 }

cucsFabricVnetEpSyncEpFsmStatus OBJECT-TYPE
    SYNTAX       SnmpAdminString
    MAX-ACCESS   read-only
    STATUS       current
    DESCRIPTION
        "Cisco UCS fabric:VnetEpSyncEp:fsmStatus managed object property"
    ::= { cucsFabricVnetEpSyncEpEntry 12 }

cucsFabricVnetEpSyncEpFsmTry OBJECT-TYPE
    SYNTAX       Gauge32
    MAX-ACCESS   read-only
    STATUS       current
    DESCRIPTION
        "Cisco UCS fabric:VnetEpSyncEp:fsmTry managed object property"
    ::= { cucsFabricVnetEpSyncEpEntry 13 }

cucsFabricVnetEpSyncEpGenNumSync OBJECT-TYPE
    SYNTAX       Gauge32
    MAX-ACCESS   read-only
    STATUS       current
    DESCRIPTION
        "Cisco UCS fabric:VnetEpSyncEp:genNumSync managed object property"
    ::= { cucsFabricVnetEpSyncEpEntry 14 }

cucsFabricVnetEpSyncEpId OBJECT-TYPE
    SYNTAX       Gauge32
    MAX-ACCESS   read-only
    STATUS       current
    DESCRIPTION
        "Cisco UCS fabric:VnetEpSyncEp:id managed object property"
    ::= { cucsFabricVnetEpSyncEpEntry 15 }

cucsFabricVnetEpSyncEpIsChangedObjectUpdate OBJECT-TYPE
    SYNTAX       TruthValue
    MAX-ACCESS   read-only
    STATUS       current
    DESCRIPTION
        "Cisco UCS fabric:VnetEpSyncEp:isChangedObjectUpdate
        managed object property"
    ::= { cucsFabricVnetEpSyncEpEntry 16 }

cucsFabricVnetEpSyncEpFsmTable OBJECT-TYPE
    SYNTAX           SEQUENCE OF CucsFabricVnetEpSyncEpFsmEntry
    MAX-ACCESS       not-accessible
    STATUS           current
    DESCRIPTION
        "Cisco UCS fabric:VnetEpSyncEpFsm managed object table"
    ::= { cucsFabricObjects 99 }

cucsFabricVnetEpSyncEpFsmEntry OBJECT-TYPE
    SYNTAX           CucsFabricVnetEpSyncEpFsmEntry
    MAX-ACCESS       not-accessible
    STATUS           current
    DESCRIPTION
        "Entry for the cucsFabricVnetEpSyncEpFsmTable table."
    INDEX { cucsFabricVnetEpSyncEpFsmInstanceId }
    ::= { cucsFabricVnetEpSyncEpFsmTable 1 }

CucsFabricVnetEpSyncEpFsmEntry ::= SEQUENCE {
    cucsFabricVnetEpSyncEpFsmInstanceId                              CucsManagedObjectId,
    cucsFabricVnetEpSyncEpFsmDn                                      CucsManagedObjectDn,
    cucsFabricVnetEpSyncEpFsmRn                                      SnmpAdminString,
    cucsFabricVnetEpSyncEpFsmCompletionTime                          DateAndTime,
    cucsFabricVnetEpSyncEpFsmCurrentFsm                              CucsFabricVnetEpSyncEpFsmCurrentFsm,
    cucsFabricVnetEpSyncEpFsmDescrData                               SnmpAdminString,
    cucsFabricVnetEpSyncEpFsmFsmStatus                               CucsFsmFsmStageStatus,
    cucsFabricVnetEpSyncEpFsmProgress                                Gauge32,
    cucsFabricVnetEpSyncEpFsmRmtErrCode                              Gauge32,
    cucsFabricVnetEpSyncEpFsmRmtErrDescr                             SnmpAdminString,
    cucsFabricVnetEpSyncEpFsmRmtRslt                                 CucsConditionRemoteInvRslt
}

cucsFabricVnetEpSyncEpFsmInstanceId OBJECT-TYPE
    SYNTAX       CucsManagedObjectId
    MAX-ACCESS   not-accessible
    STATUS       current
    DESCRIPTION
        "Instance identifier of the managed object."
    ::= { cucsFabricVnetEpSyncEpFsmEntry 1 }

cucsFabricVnetEpSyncEpFsmDn OBJECT-TYPE
    SYNTAX       CucsManagedObjectDn
    MAX-ACCESS   read-only
    STATUS       current
    DESCRIPTION
        "Cisco UCS fabric:VnetEpSyncEpFsm:dn managed object property"
    ::= { cucsFabricVnetEpSyncEpFsmEntry 2 }

cucsFabricVnetEpSyncEpFsmRn OBJECT-TYPE
    SYNTAX       SnmpAdminString
    MAX-ACCESS   read-only
    STATUS       current
    DESCRIPTION
        "Cisco UCS fabric:VnetEpSyncEpFsm:rn managed object property"
    ::= { cucsFabricVnetEpSyncEpFsmEntry 3 }

cucsFabricVnetEpSyncEpFsmCompletionTime OBJECT-TYPE
    SYNTAX       DateAndTime
    MAX-ACCESS   read-only
    STATUS       current
    DESCRIPTION
        "Cisco UCS fabric:VnetEpSyncEpFsm:completionTime
        managed object property"
    ::= { cucsFabricVnetEpSyncEpFsmEntry 4 }

cucsFabricVnetEpSyncEpFsmCurrentFsm OBJECT-TYPE
    SYNTAX       CucsFabricVnetEpSyncEpFsmCurrentFsm
    MAX-ACCESS   read-only
    STATUS       current
    DESCRIPTION
        "Cisco UCS fabric:VnetEpSyncEpFsm:currentFsm managed
        object property"
    ::= { cucsFabricVnetEpSyncEpFsmEntry 5 }

cucsFabricVnetEpSyncEpFsmDescrData OBJECT-TYPE
    SYNTAX       SnmpAdminString
    MAX-ACCESS   read-only
    STATUS       current
    DESCRIPTION
        "Cisco UCS fabric:VnetEpSyncEpFsm:descr managed object property"
    ::= { cucsFabricVnetEpSyncEpFsmEntry 6 }

cucsFabricVnetEpSyncEpFsmFsmStatus OBJECT-TYPE
    SYNTAX       CucsFsmFsmStageStatus
    MAX-ACCESS   read-only
    STATUS       current
    DESCRIPTION
        "Cisco UCS fabric:VnetEpSyncEpFsm:fsmStatus managed
        object property"
    ::= { cucsFabricVnetEpSyncEpFsmEntry 7 }

cucsFabricVnetEpSyncEpFsmProgress OBJECT-TYPE
    SYNTAX       Gauge32
    MAX-ACCESS   read-only
    STATUS       current
    DESCRIPTION
        "Cisco UCS fabric:VnetEpSyncEpFsm:progress managed
        object property"
    ::= { cucsFabricVnetEpSyncEpFsmEntry 8 }

cucsFabricVnetEpSyncEpFsmRmtErrCode OBJECT-TYPE
    SYNTAX       Gauge32
    MAX-ACCESS   read-only
    STATUS       current
    DESCRIPTION
        "Cisco UCS fabric:VnetEpSyncEpFsm:rmtErrCode managed
        object property"
    ::= { cucsFabricVnetEpSyncEpFsmEntry 9 }

cucsFabricVnetEpSyncEpFsmRmtErrDescr OBJECT-TYPE
    SYNTAX       SnmpAdminString
    MAX-ACCESS   read-only
    STATUS       current
    DESCRIPTION
        "Cisco UCS fabric:VnetEpSyncEpFsm:rmtErrDescr managed
        object property"
    ::= { cucsFabricVnetEpSyncEpFsmEntry 10 }

cucsFabricVnetEpSyncEpFsmRmtRslt OBJECT-TYPE
    SYNTAX       CucsConditionRemoteInvRslt
    MAX-ACCESS   read-only
    STATUS       current
    DESCRIPTION
        "Cisco UCS fabric:VnetEpSyncEpFsm:rmtRslt managed object property"
    ::= { cucsFabricVnetEpSyncEpFsmEntry 11 }

cucsFabricVnetEpSyncEpFsmStageTable OBJECT-TYPE
    SYNTAX           SEQUENCE OF CucsFabricVnetEpSyncEpFsmStageEntry
    MAX-ACCESS       not-accessible
    STATUS           current
    DESCRIPTION
        "Cisco UCS fabric:VnetEpSyncEpFsmStage managed object table"
    ::= { cucsFabricObjects 100 }

cucsFabricVnetEpSyncEpFsmStageEntry OBJECT-TYPE
    SYNTAX           CucsFabricVnetEpSyncEpFsmStageEntry
    MAX-ACCESS       not-accessible
    STATUS           current
    DESCRIPTION
        "Entry for the cucsFabricVnetEpSyncEpFsmStageTable table."
    INDEX { cucsFabricVnetEpSyncEpFsmStageInstanceId }
    ::= { cucsFabricVnetEpSyncEpFsmStageTable 1 }

CucsFabricVnetEpSyncEpFsmStageEntry ::= SEQUENCE {
    cucsFabricVnetEpSyncEpFsmStageInstanceId                         CucsManagedObjectId,
    cucsFabricVnetEpSyncEpFsmStageDn                                 CucsManagedObjectDn,
    cucsFabricVnetEpSyncEpFsmStageRn                                 SnmpAdminString,
    cucsFabricVnetEpSyncEpFsmStageDescrData                          SnmpAdminString,
    cucsFabricVnetEpSyncEpFsmStageLastUpdateTime                     DateAndTime,
    cucsFabricVnetEpSyncEpFsmStageName                               CucsFabricVnetEpSyncEpFsmStageName,
    cucsFabricVnetEpSyncEpFsmStageOrder                              Gauge32,
    cucsFabricVnetEpSyncEpFsmStageRetry                              Gauge32,
    cucsFabricVnetEpSyncEpFsmStageStageStatus                        CucsFsmFsmStageStatus
}

cucsFabricVnetEpSyncEpFsmStageInstanceId OBJECT-TYPE
    SYNTAX       CucsManagedObjectId
    MAX-ACCESS   not-accessible
    STATUS       current
    DESCRIPTION
        "Instance identifier of the managed object."
    ::= { cucsFabricVnetEpSyncEpFsmStageEntry 1 }

cucsFabricVnetEpSyncEpFsmStageDn OBJECT-TYPE
    SYNTAX       CucsManagedObjectDn
    MAX-ACCESS   read-only
    STATUS       current
    DESCRIPTION
        "Cisco UCS fabric:VnetEpSyncEpFsmStage:dn managed object property"
    ::= { cucsFabricVnetEpSyncEpFsmStageEntry 2 }

cucsFabricVnetEpSyncEpFsmStageRn OBJECT-TYPE
    SYNTAX       SnmpAdminString
    MAX-ACCESS   read-only
    STATUS       current
    DESCRIPTION
        "Cisco UCS fabric:VnetEpSyncEpFsmStage:rn managed object property"
    ::= { cucsFabricVnetEpSyncEpFsmStageEntry 3 }

cucsFabricVnetEpSyncEpFsmStageDescrData OBJECT-TYPE
    SYNTAX       SnmpAdminString
    MAX-ACCESS   read-only
    STATUS       current
    DESCRIPTION
        "Cisco UCS fabric:VnetEpSyncEpFsmStage:descr managed
        object property"
    ::= { cucsFabricVnetEpSyncEpFsmStageEntry 4 }

cucsFabricVnetEpSyncEpFsmStageLastUpdateTime OBJECT-TYPE
    SYNTAX       DateAndTime
    MAX-ACCESS   read-only
    STATUS       current
    DESCRIPTION
        "Cisco UCS fabric:VnetEpSyncEpFsmStage:lastUpdateTime
        managed object property"
    ::= { cucsFabricVnetEpSyncEpFsmStageEntry 5 }

cucsFabricVnetEpSyncEpFsmStageName OBJECT-TYPE
    SYNTAX       CucsFabricVnetEpSyncEpFsmStageName
    MAX-ACCESS   read-only
    STATUS       current
    DESCRIPTION
        "Cisco UCS fabric:VnetEpSyncEpFsmStage:name managed
        object property"
    ::= { cucsFabricVnetEpSyncEpFsmStageEntry 6 }

cucsFabricVnetEpSyncEpFsmStageOrder OBJECT-TYPE
    SYNTAX       Gauge32
    MAX-ACCESS   read-only
    STATUS       current
    DESCRIPTION
        "Cisco UCS fabric:VnetEpSyncEpFsmStage:order managed
        object property"
    ::= { cucsFabricVnetEpSyncEpFsmStageEntry 7 }

cucsFabricVnetEpSyncEpFsmStageRetry OBJECT-TYPE
    SYNTAX       Gauge32
    MAX-ACCESS   read-only
    STATUS       current
    DESCRIPTION
        "Cisco UCS fabric:VnetEpSyncEpFsmStage:retry managed
        object property"
    ::= { cucsFabricVnetEpSyncEpFsmStageEntry 8 }

cucsFabricVnetEpSyncEpFsmStageStageStatus OBJECT-TYPE
    SYNTAX       CucsFsmFsmStageStatus
    MAX-ACCESS   read-only
    STATUS       current
    DESCRIPTION
        "Cisco UCS fabric:VnetEpSyncEpFsmStage:stageStatus
        managed object property"
    ::= { cucsFabricVnetEpSyncEpFsmStageEntry 9 }

cucsFabricVnetEpSyncEpFsmTaskTable OBJECT-TYPE
    SYNTAX           SEQUENCE OF CucsFabricVnetEpSyncEpFsmTaskEntry
    MAX-ACCESS       not-accessible
    STATUS           current
    DESCRIPTION
        "Cisco UCS fabric:VnetEpSyncEpFsmTask managed object table"
    ::= { cucsFabricObjects 101 }

cucsFabricVnetEpSyncEpFsmTaskEntry OBJECT-TYPE
    SYNTAX           CucsFabricVnetEpSyncEpFsmTaskEntry
    MAX-ACCESS       not-accessible
    STATUS           current
    DESCRIPTION
        "Entry for the cucsFabricVnetEpSyncEpFsmTaskTable table."
    INDEX { cucsFabricVnetEpSyncEpFsmTaskInstanceId }
    ::= { cucsFabricVnetEpSyncEpFsmTaskTable 1 }

CucsFabricVnetEpSyncEpFsmTaskEntry ::= SEQUENCE {
    cucsFabricVnetEpSyncEpFsmTaskInstanceId                          CucsManagedObjectId,
    cucsFabricVnetEpSyncEpFsmTaskDn                                  CucsManagedObjectDn,
    cucsFabricVnetEpSyncEpFsmTaskRn                                  SnmpAdminString,
    cucsFabricVnetEpSyncEpFsmTaskCompletion                          CucsFsmCompletion,
    cucsFabricVnetEpSyncEpFsmTaskFlags                               CucsFsmFlags,
    cucsFabricVnetEpSyncEpFsmTaskItem                                CucsFabricVnetEpSyncEpFsmTaskItem,
    cucsFabricVnetEpSyncEpFsmTaskSeqId                               Gauge32
}

cucsFabricVnetEpSyncEpFsmTaskInstanceId OBJECT-TYPE
    SYNTAX       CucsManagedObjectId
    MAX-ACCESS   not-accessible
    STATUS       current
    DESCRIPTION
        "Instance identifier of the managed object."
    ::= { cucsFabricVnetEpSyncEpFsmTaskEntry 1 }

cucsFabricVnetEpSyncEpFsmTaskDn OBJECT-TYPE
    SYNTAX       CucsManagedObjectDn
    MAX-ACCESS   read-only
    STATUS       current
    DESCRIPTION
        "Cisco UCS fabric:VnetEpSyncEpFsmTask:dn managed object property"
    ::= { cucsFabricVnetEpSyncEpFsmTaskEntry 2 }

cucsFabricVnetEpSyncEpFsmTaskRn OBJECT-TYPE
    SYNTAX       SnmpAdminString
    MAX-ACCESS   read-only
    STATUS       current
    DESCRIPTION
        "Cisco UCS fabric:VnetEpSyncEpFsmTask:rn managed object property"
    ::= { cucsFabricVnetEpSyncEpFsmTaskEntry 3 }

cucsFabricVnetEpSyncEpFsmTaskCompletion OBJECT-TYPE
    SYNTAX       CucsFsmCompletion
    MAX-ACCESS   read-only
    STATUS       current
    DESCRIPTION
        "Cisco UCS fabric:VnetEpSyncEpFsmTask:completion
        managed object property"
    ::= { cucsFabricVnetEpSyncEpFsmTaskEntry 4 }

cucsFabricVnetEpSyncEpFsmTaskFlags OBJECT-TYPE
    SYNTAX       CucsFsmFlags
    MAX-ACCESS   read-only
    STATUS       current
    DESCRIPTION
        "Cisco UCS fabric:VnetEpSyncEpFsmTask:flags managed
        object property"
    ::= { cucsFabricVnetEpSyncEpFsmTaskEntry 5 }

cucsFabricVnetEpSyncEpFsmTaskItem OBJECT-TYPE
    SYNTAX       CucsFabricVnetEpSyncEpFsmTaskItem
    MAX-ACCESS   read-only
    STATUS       current
    DESCRIPTION
        "Cisco UCS fabric:VnetEpSyncEpFsmTask:item managed
        object property"
    ::= { cucsFabricVnetEpSyncEpFsmTaskEntry 6 }

cucsFabricVnetEpSyncEpFsmTaskSeqId OBJECT-TYPE
    SYNTAX       Gauge32
    MAX-ACCESS   read-only
    STATUS       current
    DESCRIPTION
        "Cisco UCS fabric:VnetEpSyncEpFsmTask:seqId managed
        object property"
    ::= { cucsFabricVnetEpSyncEpFsmTaskEntry 7 }

cucsFabricVsanTable OBJECT-TYPE
    SYNTAX           SEQUENCE OF CucsFabricVsanEntry
    MAX-ACCESS       not-accessible
    STATUS           current
    DESCRIPTION
        "Cisco UCS fabric:Vsan managed object table"
    ::= { cucsFabricObjects 62 }

cucsFabricVsanEntry OBJECT-TYPE
    SYNTAX           CucsFabricVsanEntry
    MAX-ACCESS       not-accessible
    STATUS           current
    DESCRIPTION
        "Entry for the cucsFabricVsanTable table."
    INDEX { cucsFabricVsanInstanceId }
    ::= { cucsFabricVsanTable 1 }

CucsFabricVsanEntry ::= SEQUENCE {
    cucsFabricVsanInstanceId                                         CucsManagedObjectId,
    cucsFabricVsanDn                                                 CucsManagedObjectDn,
    cucsFabricVsanRn                                                 SnmpAdminString,
    cucsFabricVsanEndPtDn                                            SnmpAdminString,
    cucsFabricVsanFcoeVlan                                           Gauge32,
    cucsFabricVsanId                                                 Gauge32,
    cucsFabricVsanIfRole                                             CucsFabricVnetEpIfRole,
    cucsFabricVsanIfType                                             CucsNetworkVnetEpIfType,
    cucsFabricVsanLocale                                             CucsFabricVnetEpLocale,
    cucsFabricVsanName                                               SnmpAdminString,
    cucsFabricVsanPeerDn                                             SnmpAdminString,
    cucsFabricVsanSwitchId                                           CucsFabricVsanSwitchId,
    cucsFabricVsanTransport                                          CucsFabricAVsanTransport,
    cucsFabricVsanType                                               CucsFabricAVsanType,
    cucsFabricVsanDefaultZoning                                      CucsFabricDefaultZoningState,
    cucsFabricVsanFltAggr                                            Unsigned64,
    cucsFabricVsanOperState                                          CucsFabricVsanOperState,
    cucsFabricVsanFcZoneSharingMode                                  CucsFabricFcZoneSharingMode,
    cucsFabricVsanZoningState                                        CucsFabricZoningState,
    cucsFabricVsanGlobal                                             Unsigned64,
    cucsFabricVsanLocal                                              Unsigned64,
    cucsFabricVsanPolicyOwner                                        CucsFabricVnetEpPolicyOwner
}

cucsFabricVsanInstanceId OBJECT-TYPE
    SYNTAX       CucsManagedObjectId
    MAX-ACCESS   not-accessible
    STATUS       current
    DESCRIPTION
        "Instance identifier of the managed object."
    ::= { cucsFabricVsanEntry 1 }

cucsFabricVsanDn OBJECT-TYPE
    SYNTAX       CucsManagedObjectDn
    MAX-ACCESS   read-only
    STATUS       current
    DESCRIPTION
        "Cisco UCS fabric:Vsan:dn managed object property"
    ::= { cucsFabricVsanEntry 2 }

cucsFabricVsanRn OBJECT-TYPE
    SYNTAX       SnmpAdminString
    MAX-ACCESS   read-only
    STATUS       current
    DESCRIPTION
        "Cisco UCS fabric:Vsan:rn managed object property"
    ::= { cucsFabricVsanEntry 3 }

cucsFabricVsanEndPtDn OBJECT-TYPE
    SYNTAX       SnmpAdminString
    MAX-ACCESS   read-only
    STATUS       current
    DESCRIPTION
        "Cisco UCS fabric:Vsan:epDn managed object property"
    ::= { cucsFabricVsanEntry 4 }

cucsFabricVsanFcoeVlan OBJECT-TYPE
    SYNTAX       Gauge32
    MAX-ACCESS   read-only
    STATUS       current
    DESCRIPTION
        "Cisco UCS fabric:Vsan:fcoeVlan managed object property"
    ::= { cucsFabricVsanEntry 5 }

cucsFabricVsanId OBJECT-TYPE
    SYNTAX       Gauge32
    MAX-ACCESS   read-only
    STATUS       current
    DESCRIPTION
        "Cisco UCS fabric:Vsan:id managed object property"
    ::= { cucsFabricVsanEntry 6 }

cucsFabricVsanIfRole OBJECT-TYPE
    SYNTAX       CucsFabricVnetEpIfRole
    MAX-ACCESS   read-only
    STATUS       current
    DESCRIPTION
        "Cisco UCS fabric:Vsan:ifRole managed object property"
    ::= { cucsFabricVsanEntry 7 }

cucsFabricVsanIfType OBJECT-TYPE
    SYNTAX       CucsNetworkVnetEpIfType
    MAX-ACCESS   read-only
    STATUS       current
    DESCRIPTION
        "Cisco UCS fabric:Vsan:ifType managed object property"
    ::= { cucsFabricVsanEntry 8 }

cucsFabricVsanLocale OBJECT-TYPE
    SYNTAX       CucsFabricVnetEpLocale
    MAX-ACCESS   read-only
    STATUS       current
    DESCRIPTION
        "Cisco UCS fabric:Vsan:locale managed object property"
    ::= { cucsFabricVsanEntry 9 }

cucsFabricVsanName OBJECT-TYPE
    SYNTAX       SnmpAdminString
    MAX-ACCESS   read-only
    STATUS       current
    DESCRIPTION
        "Cisco UCS fabric:Vsan:name managed object property"
    ::= { cucsFabricVsanEntry 10 }

cucsFabricVsanPeerDn OBJECT-TYPE
    SYNTAX       SnmpAdminString
    MAX-ACCESS   read-only
    STATUS       current
    DESCRIPTION
        "Cisco UCS fabric:Vsan:peerDn managed object property"
    ::= { cucsFabricVsanEntry 11 }

cucsFabricVsanSwitchId OBJECT-TYPE
    SYNTAX       CucsFabricVsanSwitchId
    MAX-ACCESS   read-only
    STATUS       current
    DESCRIPTION
        "Cisco UCS fabric:Vsan:switchId managed object property"
    ::= { cucsFabricVsanEntry 12 }

cucsFabricVsanTransport OBJECT-TYPE
    SYNTAX       CucsFabricAVsanTransport
    MAX-ACCESS   read-only
    STATUS       current
    DESCRIPTION
        "Cisco UCS fabric:Vsan:transport managed object property"
    ::= { cucsFabricVsanEntry 13 }

cucsFabricVsanType OBJECT-TYPE
    SYNTAX       CucsFabricAVsanType
    MAX-ACCESS   read-only
    STATUS       current
    DESCRIPTION
        "Cisco UCS fabric:Vsan:type managed object property"
    ::= { cucsFabricVsanEntry 14 }

cucsFabricVsanDefaultZoning OBJECT-TYPE
    SYNTAX       CucsFabricDefaultZoningState
    MAX-ACCESS   read-only
    STATUS       current
    DESCRIPTION
        "Cisco UCS fabric:Vsan:defaultZoning managed object property"
    ::= { cucsFabricVsanEntry 15 }

cucsFabricVsanFltAggr OBJECT-TYPE
    SYNTAX       Unsigned64
    MAX-ACCESS   read-only
    STATUS       current
    DESCRIPTION
        "Cisco UCS fabric:Vsan:fltAggr managed object property"
    ::= { cucsFabricVsanEntry 16 }

cucsFabricVsanOperState OBJECT-TYPE
    SYNTAX       CucsFabricVsanOperState
    MAX-ACCESS   read-only
    STATUS       current
    DESCRIPTION
        "Cisco UCS fabric:Vsan:operState managed object property"
    ::= { cucsFabricVsanEntry 17 }

cucsFabricVsanFcZoneSharingMode OBJECT-TYPE
    SYNTAX       CucsFabricFcZoneSharingMode
    MAX-ACCESS   read-only
    STATUS       current
    DESCRIPTION
        "Cisco UCS fabric:Vsan:fcZoneSharingMode managed object property"
    ::= { cucsFabricVsanEntry 18 }

cucsFabricVsanZoningState OBJECT-TYPE
    SYNTAX       CucsFabricZoningState
    MAX-ACCESS   read-only
    STATUS       current
    DESCRIPTION
        "Cisco UCS fabric:Vsan:zoningState managed object property"
    ::= { cucsFabricVsanEntry 19 }

cucsFabricVsanGlobal OBJECT-TYPE
    SYNTAX       Unsigned64
    MAX-ACCESS   read-only
    STATUS       current
    DESCRIPTION
        "Cisco UCS fabric:Vsan:global managed object property"
    ::= { cucsFabricVsanEntry 20 }

cucsFabricVsanLocal OBJECT-TYPE
    SYNTAX       Unsigned64
    MAX-ACCESS   read-only
    STATUS       current
    DESCRIPTION
        "Cisco UCS fabric:Vsan:local managed object property"
    ::= { cucsFabricVsanEntry 22 }

cucsFabricVsanPolicyOwner OBJECT-TYPE
    SYNTAX       CucsFabricVnetEpPolicyOwner
    MAX-ACCESS   read-only
    STATUS       current
    DESCRIPTION
        "Cisco UCS fabric:Vsan:policyOwner managed object property"
    ::= { cucsFabricVsanEntry 23 }

cucsFabricVsanEpTable OBJECT-TYPE
    SYNTAX           SEQUENCE OF CucsFabricVsanEpEntry
    MAX-ACCESS       not-accessible
    STATUS           current
    DESCRIPTION
        "Cisco UCS fabric:VsanEp managed object table"
    ::= { cucsFabricObjects 63 }

cucsFabricVsanEpEntry OBJECT-TYPE
    SYNTAX           CucsFabricVsanEpEntry
    MAX-ACCESS       not-accessible
    STATUS           current
    DESCRIPTION
        "Entry for the cucsFabricVsanEpTable table."
    INDEX { cucsFabricVsanEpInstanceId }
    ::= { cucsFabricVsanEpTable 1 }

CucsFabricVsanEpEntry ::= SEQUENCE {
    cucsFabricVsanEpInstanceId                                       CucsManagedObjectId,
    cucsFabricVsanEpDn                                               CucsManagedObjectDn,
    cucsFabricVsanEpRn                                               SnmpAdminString,
    cucsFabricVsanEpEpDn                                             SnmpAdminString,
    cucsFabricVsanEpFcoeVlan                                         Gauge32,
    cucsFabricVsanEpId                                               Gauge32,
    cucsFabricVsanEpIfRole                                           CucsFabricVnetEpIfRole,
    cucsFabricVsanEpIfType                                           CucsNetworkVnetEpIfType,
    cucsFabricVsanEpLocale                                           CucsFabricVnetEpLocale,
    cucsFabricVsanEpName                                             SnmpAdminString,
    cucsFabricVsanEpPeerDn                                           SnmpAdminString,
    cucsFabricVsanEpSwitchId                                         CucsNetworkSwitchId,
    cucsFabricVsanEpTransport                                        CucsFabricAVsanTransport,
    cucsFabricVsanEpType                                             CucsFabricAVsanType,
    cucsFabricVsanEpOperState                                        CucsFabricVsanOperState,
    cucsFabricVsanEpZoningState                                      CucsFabricZoningState,
    cucsFabricVsanEpPolicyOwner                                      CucsFabricVnetEpPolicyOwner
}

cucsFabricVsanEpInstanceId OBJECT-TYPE
    SYNTAX       CucsManagedObjectId
    MAX-ACCESS   not-accessible
    STATUS       current
    DESCRIPTION
        "Instance identifier of the managed object."
    ::= { cucsFabricVsanEpEntry 1 }

cucsFabricVsanEpDn OBJECT-TYPE
    SYNTAX       CucsManagedObjectDn
    MAX-ACCESS   read-only
    STATUS       current
    DESCRIPTION
        "Cisco UCS fabric:VsanEp:dn managed object property"
    ::= { cucsFabricVsanEpEntry 2 }

cucsFabricVsanEpRn OBJECT-TYPE
    SYNTAX       SnmpAdminString
    MAX-ACCESS   read-only
    STATUS       current
    DESCRIPTION
        "Cisco UCS fabric:VsanEp:rn managed object property"
    ::= { cucsFabricVsanEpEntry 3 }

cucsFabricVsanEpEpDn OBJECT-TYPE
    SYNTAX       SnmpAdminString
    MAX-ACCESS   read-only
    STATUS       current
    DESCRIPTION
        "Cisco UCS fabric:VsanEp:epDn managed object property"
    ::= { cucsFabricVsanEpEntry 4 }

cucsFabricVsanEpFcoeVlan OBJECT-TYPE
    SYNTAX       Gauge32
    MAX-ACCESS   read-only
    STATUS       current
    DESCRIPTION
        "Cisco UCS fabric:VsanEp:fcoeVlan managed object property"
    ::= { cucsFabricVsanEpEntry 5 }

cucsFabricVsanEpId OBJECT-TYPE
    SYNTAX       Gauge32
    MAX-ACCESS   read-only
    STATUS       current
    DESCRIPTION
        "Cisco UCS fabric:VsanEp:id managed object property"
    ::= { cucsFabricVsanEpEntry 6 }

cucsFabricVsanEpIfRole OBJECT-TYPE
    SYNTAX       CucsFabricVnetEpIfRole
    MAX-ACCESS   read-only
    STATUS       current
    DESCRIPTION
        "Cisco UCS fabric:VsanEp:ifRole managed object property"
    ::= { cucsFabricVsanEpEntry 7 }

cucsFabricVsanEpIfType OBJECT-TYPE
    SYNTAX       CucsNetworkVnetEpIfType
    MAX-ACCESS   read-only
    STATUS       current
    DESCRIPTION
        "Cisco UCS fabric:VsanEp:ifType managed object property"
    ::= { cucsFabricVsanEpEntry 8 }

cucsFabricVsanEpLocale OBJECT-TYPE
    SYNTAX       CucsFabricVnetEpLocale
    MAX-ACCESS   read-only
    STATUS       current
    DESCRIPTION
        "Cisco UCS fabric:VsanEp:locale managed object property"
    ::= { cucsFabricVsanEpEntry 9 }

cucsFabricVsanEpName OBJECT-TYPE
    SYNTAX       SnmpAdminString
    MAX-ACCESS   read-only
    STATUS       current
    DESCRIPTION
        "Cisco UCS fabric:VsanEp:name managed object property"
    ::= { cucsFabricVsanEpEntry 10 }

cucsFabricVsanEpPeerDn OBJECT-TYPE
    SYNTAX       SnmpAdminString
    MAX-ACCESS   read-only
    STATUS       current
    DESCRIPTION
        "Cisco UCS fabric:VsanEp:peerDn managed object property"
    ::= { cucsFabricVsanEpEntry 11 }

cucsFabricVsanEpSwitchId OBJECT-TYPE
    SYNTAX       CucsNetworkSwitchId
    MAX-ACCESS   read-only
    STATUS       current
    DESCRIPTION
        "Cisco UCS fabric:VsanEp:switchId managed object property"
    ::= { cucsFabricVsanEpEntry 12 }

cucsFabricVsanEpTransport OBJECT-TYPE
    SYNTAX       CucsFabricAVsanTransport
    MAX-ACCESS   read-only
    STATUS       current
    DESCRIPTION
        "Cisco UCS fabric:VsanEp:transport managed object property"
    ::= { cucsFabricVsanEpEntry 13 }

cucsFabricVsanEpType OBJECT-TYPE
    SYNTAX       CucsFabricAVsanType
    MAX-ACCESS   read-only
    STATUS       current
    DESCRIPTION
        "Cisco UCS fabric:VsanEp:type managed object property"
    ::= { cucsFabricVsanEpEntry 14 }

cucsFabricVsanEpOperState OBJECT-TYPE
    SYNTAX       CucsFabricVsanOperState
    MAX-ACCESS   read-only
    STATUS       current
    DESCRIPTION
        "Cisco UCS fabric:VsanEp:operState managed object property"
    ::= { cucsFabricVsanEpEntry 15 }

cucsFabricVsanEpZoningState OBJECT-TYPE
    SYNTAX       CucsFabricZoningState
    MAX-ACCESS   read-only
    STATUS       current
    DESCRIPTION
        "Cisco UCS fabric:VsanEp:zoningState managed object property"
    ::= { cucsFabricVsanEpEntry 16 }

cucsFabricVsanEpPolicyOwner OBJECT-TYPE
    SYNTAX       CucsFabricVnetEpPolicyOwner
    MAX-ACCESS   read-only
    STATUS       current
    DESCRIPTION
        "Cisco UCS fabric:VsanEp:policyOwner managed object property"
    ::= { cucsFabricVsanEpEntry 18 }

cucsFabricVsanMembershipTable OBJECT-TYPE
    SYNTAX           SEQUENCE OF CucsFabricVsanMembershipEntry
    MAX-ACCESS       not-accessible
    STATUS           current
    DESCRIPTION
        "Cisco UCS fabric:VsanMembership managed object table"
    ::= { cucsFabricObjects 95 }

cucsFabricVsanMembershipEntry OBJECT-TYPE
    SYNTAX           CucsFabricVsanMembershipEntry
    MAX-ACCESS       not-accessible
    STATUS           current
    DESCRIPTION
        "Entry for the cucsFabricVsanMembershipTable table."
    INDEX { cucsFabricVsanMembershipInstanceId }
    ::= { cucsFabricVsanMembershipTable 1 }

CucsFabricVsanMembershipEntry ::= SEQUENCE {
    cucsFabricVsanMembershipInstanceId                               CucsManagedObjectId,
    cucsFabricVsanMembershipDn                                       CucsManagedObjectDn,
    cucsFabricVsanMembershipRn                                       SnmpAdminString,
    cucsFabricVsanMembershipMemberStatus                             CucsFabricMemberStatus,
    cucsFabricVsanMembershipStateQual                                SnmpAdminString,
    cucsFabricVsanMembershipVsanId                                   Gauge32,
    cucsFabricVsanMembershipParentAdminState                         CucsFabricAdminState
}

cucsFabricVsanMembershipInstanceId OBJECT-TYPE
    SYNTAX       CucsManagedObjectId
    MAX-ACCESS   not-accessible
    STATUS       current
    DESCRIPTION
        "Instance identifier of the managed object."
    ::= { cucsFabricVsanMembershipEntry 1 }

cucsFabricVsanMembershipDn OBJECT-TYPE
    SYNTAX       CucsManagedObjectDn
    MAX-ACCESS   read-only
    STATUS       current
    DESCRIPTION
        "Cisco UCS fabric:VsanMembership:dn managed object property"
    ::= { cucsFabricVsanMembershipEntry 2 }

cucsFabricVsanMembershipRn OBJECT-TYPE
    SYNTAX       SnmpAdminString
    MAX-ACCESS   read-only
    STATUS       current
    DESCRIPTION
        "Cisco UCS fabric:VsanMembership:rn managed object property"
    ::= { cucsFabricVsanMembershipEntry 3 }

cucsFabricVsanMembershipMemberStatus OBJECT-TYPE
    SYNTAX       CucsFabricMemberStatus
    MAX-ACCESS   read-only
    STATUS       current
    DESCRIPTION
        "Cisco UCS fabric:VsanMembership:memberStatus managed
        object property"
    ::= { cucsFabricVsanMembershipEntry 4 }

cucsFabricVsanMembershipStateQual OBJECT-TYPE
    SYNTAX       SnmpAdminString
    MAX-ACCESS   read-only
    STATUS       current
    DESCRIPTION
        "Cisco UCS fabric:VsanMembership:stateQual managed
        object property"
    ::= { cucsFabricVsanMembershipEntry 5 }

cucsFabricVsanMembershipVsanId OBJECT-TYPE
    SYNTAX       Gauge32
    MAX-ACCESS   read-only
    STATUS       current
    DESCRIPTION
        "Cisco UCS fabric:VsanMembership:vsanId managed object property"
    ::= { cucsFabricVsanMembershipEntry 6 }

cucsFabricVsanMembershipParentAdminState OBJECT-TYPE
    SYNTAX       CucsFabricAdminState
    MAX-ACCESS   read-only
    STATUS       current
    DESCRIPTION
        "Cisco UCS fabric:VsanMembership:parentAdminState
        managed object property"
    ::= { cucsFabricVsanMembershipEntry 7 }

cucsFabricZoneIdUniverseTable OBJECT-TYPE
    SYNTAX           SEQUENCE OF CucsFabricZoneIdUniverseEntry
    MAX-ACCESS       not-accessible
    STATUS           current
    DESCRIPTION
        "Cisco UCS fabric:ZoneIdUniverse managed object table"
    ::= { cucsFabricObjects 96 }

cucsFabricZoneIdUniverseEntry OBJECT-TYPE
    SYNTAX           CucsFabricZoneIdUniverseEntry
    MAX-ACCESS       not-accessible
    STATUS           current
    DESCRIPTION
        "Entry for the cucsFabricZoneIdUniverseTable table."
    INDEX { cucsFabricZoneIdUniverseInstanceId }
    ::= { cucsFabricZoneIdUniverseTable 1 }

CucsFabricZoneIdUniverseEntry ::= SEQUENCE {
    cucsFabricZoneIdUniverseInstanceId                               CucsManagedObjectId,
    cucsFabricZoneIdUniverseDn                                       CucsManagedObjectDn,
    cucsFabricZoneIdUniverseRn                                       SnmpAdminString
}

cucsFabricZoneIdUniverseInstanceId OBJECT-TYPE
    SYNTAX       CucsManagedObjectId
    MAX-ACCESS   not-accessible
    STATUS       current
    DESCRIPTION
        "Instance identifier of the managed object."
    ::= { cucsFabricZoneIdUniverseEntry 1 }

cucsFabricZoneIdUniverseDn OBJECT-TYPE
    SYNTAX       CucsManagedObjectDn
    MAX-ACCESS   read-only
    STATUS       current
    DESCRIPTION
        "Cisco UCS fabric:ZoneIdUniverse:dn managed object property"
    ::= { cucsFabricZoneIdUniverseEntry 2 }

cucsFabricZoneIdUniverseRn OBJECT-TYPE
    SYNTAX       SnmpAdminString
    MAX-ACCESS   read-only
    STATUS       current
    DESCRIPTION
        "Cisco UCS fabric:ZoneIdUniverse:rn managed object property"
    ::= { cucsFabricZoneIdUniverseEntry 3 }

END
