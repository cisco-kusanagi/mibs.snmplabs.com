Wellfleet-OSI-MIB DEFINITIONS ::= BEGIN

-- Created by mdl2asn version 3.1
-- Creation date: Wed Aug 30 16:46:01 EDT 1995


    IMPORTS

      IpAddress, Counter, Opaque
        FROM RFC1155-SMI
      OBJECT-TYPE
        FROM RFC-1212
      DisplayString
        FROM RFC1213-MIB
      wfOsiGroup
        FROM Wellfleet-COMMON-MIB;


    wfOsi		OBJECT IDENTIFIER ::= { wfOsiGroup 1 }

    wfOsiDelete OBJECT-TYPE
        SYNTAX	INTEGER {
    		    created(1),
    		    deleted(2)
    		}
        ACCESS	read-write
        STATUS	mandatory
        DESCRIPTION
                "This value determines whether OSI is configured on this slot."
        DEFVAL	{ created }
        ::= { wfOsi 1 }

    wfOsiDisable OBJECT-TYPE
        SYNTAX	INTEGER {
    		    enabled(1),
    		    disabled(2)
    		}
        ACCESS	read-write
        STATUS	mandatory
        DESCRIPTION
                "This value determines whether OSI is to startup."
        DEFVAL	{ enabled }
        ::= { wfOsi 2 }

    wfOsiState OBJECT-TYPE
        SYNTAX	INTEGER {
    		    up(1),
    		    down(2),
    		    init(3),
    		    notpresent(4)
    		}
        ACCESS	read-only
        STATUS	mandatory
        DESCRIPTION
                "This value determines whether OSI is to startup."
        DEFVAL	{ notpresent }
        ::= { wfOsi 3 }

    wfOsiIsisVersion OBJECT-TYPE
        SYNTAX	DisplayString
        ACCESS	read-only
        STATUS	mandatory
        DESCRIPTION
                "This read-only parameter identifies the version number of the
                IS-IS protocol to which this node conforms to.          "
        ::= { wfOsi 4 }

    wfOsiRouterType OBJECT-TYPE
        SYNTAX	INTEGER {
    		    l1only(1),
    		    l1l2(3)
    		}
        ACCESS	read-write
        STATUS	mandatory
        DESCRIPTION
                "This value determines whether this system is an L1-only router or
                L1-L2  IS."
        DEFVAL	{ l1l2 }
        ::= { wfOsi 5 }

    wfOsiRouterId OBJECT-TYPE
        SYNTAX	OCTET STRING
        ACCESS	read-write
        STATUS	mandatory
        DESCRIPTION
                "This value contains the system ID of this Intermediate System.
                If no value is entered by the user, Site Manager should
                supply a 6-byte value that will be unique (a MAC address
                would work).
                 "
        ::= { wfOsi 6 }

    wfOsiLoadBal OBJECT-TYPE
        SYNTAX	INTEGER {
    		    enabled(1),
    		    disabled(2)
    		}
        ACCESS	read-write
        STATUS	mandatory
        DESCRIPTION
                "This Boolean defines whether or not we are doing load balancing
                over multiple paths."
        DEFVAL	{ disabled }
        ::= { wfOsi 7 }

    wfOsiMaxAreas OBJECT-TYPE
        SYNTAX	INTEGER(1..1000)
        ACCESS	read-write
        STATUS	mandatory
        DESCRIPTION
                "This value defines the maximum allowable number of areas addresses
                for the domain that this router exists in."
        DEFVAL	{ 63 }
        ::= { wfOsi 8 }

    wfOsiMaxEs OBJECT-TYPE
        SYNTAX	INTEGER(1..4000)
        ACCESS	read-write
        STATUS	mandatory
        DESCRIPTION
                "This value defines the maximum allowable number of End Systems
                for the area that this router exists in."
        DEFVAL	{ 512 }
        ::= { wfOsi 9 }

    wfOsiMaxL1Is OBJECT-TYPE
        SYNTAX	INTEGER(1..1000)
        ACCESS	read-write
        STATUS	mandatory
        DESCRIPTION
                "This value defines the maximum allowable number of L1 Intermediate
                Systems for the area that this router exists in."
        DEFVAL	{ 15 }
        ::= { wfOsi 10 }

    wfOsiMaxL2Is OBJECT-TYPE
        SYNTAX	INTEGER(1..1000)
        ACCESS	read-write
        STATUS	mandatory
        DESCRIPTION
                "This value defines the maximum allowable number of L2 Intermediate
                Systems for the domain that this router exists in."
        DEFVAL	{ 63 }
        ::= { wfOsi 11 }

    wfOsiMaxExtAddr OBJECT-TYPE
        SYNTAX	INTEGER(1..500)
        ACCESS	read-write
        STATUS	mandatory
        DESCRIPTION
                "This value defines the maximum allowable number of External Addresses
                for the domain that this router exists in.
                 The default value of this field is 0."
        DEFVAL	{ 1 }
        ::= { wfOsi 12 }

    wfOsiCksumIsPdus OBJECT-TYPE
        SYNTAX	INTEGER {
    		    enabled(1),
    		    disabled(2)
    		}
        ACCESS	read-write
        STATUS	mandatory
        DESCRIPTION
                "This value indicates whether ISIS PDUs will carry a checksum."
        DEFVAL	{ enabled }
        ::= { wfOsi 13 }

    wfOsiL1LspPassword OBJECT-TYPE
        SYNTAX	DisplayString
        ACCESS	read-write
        STATUS	mandatory
        DESCRIPTION
                "This assigns a password such that only L1 Lsps with the matching
                password will be accepted.  All L1 Lsps generated
                 by this system will contain this string in the password option."
        ::= { wfOsi 14 }

    wfOsiL2LspPassword OBJECT-TYPE
        SYNTAX	DisplayString
        ACCESS	read-write
        STATUS	mandatory
        DESCRIPTION
                "This assigns a password such that only L2 Lsps with the matching
                password will be accepted.  All L2 Lsps generated
                 by this system will contain this string in the password option."
        ::= { wfOsi 15 }

    wfOsiAreaAddr OBJECT-TYPE
        SYNTAX	OCTET STRING
        ACCESS	read-write
        STATUS	mandatory
        DESCRIPTION
                "This Assigns the area address for this router.
                This field must be filled in.
                       If the user doesn't enter a value, then assign 490040.
                       Site Manager must force the user to enter at least a 3-byte
                value for this field.
                "
        ::= { wfOsi 16 }

    wfOsiAreaAddrAlias1 OBJECT-TYPE
        SYNTAX	OCTET STRING
        ACCESS	read-write
        STATUS	mandatory
        DESCRIPTION
                "This Assigns the first area address alias for this router.
                This field does no have to be filled in, but if the user
                tries to enter a value, Site Manager must make sure that
                it is at least 3-bytes in length."
        ::= { wfOsi 17 }

    wfOsiAreaAddrAlias2 OBJECT-TYPE
        SYNTAX	OCTET STRING
        ACCESS	read-write
        STATUS	obsolete
        DESCRIPTION
                "This Assigns the second area address alias for this router.
                This field does no have to be filled in, but if the user
                tries to enter a value, Site Manager must make sure that
                it is at least 3-bytes in length."
        ::= { wfOsi 18 }

    wfOsiCorruptedLsps OBJECT-TYPE
        SYNTAX	Counter
        ACCESS	read-only
        STATUS	mandatory
        DESCRIPTION
                "Number of Corrupted Lsps Detected."
        ::= { wfOsi 19 }

    wfOsiL1LspDbOverloads OBJECT-TYPE
        SYNTAX	Counter
        ACCESS	read-only
        STATUS	mandatory
        DESCRIPTION
                "Number of times the L1 Lsp Database Overload event has
                been generated. "
        ::= { wfOsi 20 }

    wfOsiL2LspDbOverloads OBJECT-TYPE
        SYNTAX	Counter
        ACCESS	read-only
        STATUS	mandatory
        DESCRIPTION
                "Number of times the L2 Lsp Database Overload event has
                been generated. "
        ::= { wfOsi 21 }

    wfOsiManAddrDroppedAreas OBJECT-TYPE
        SYNTAX	Counter
        ACCESS	read-only
        STATUS	mandatory
        DESCRIPTION
                "Number of times the Manual Address Dropped from Area event
                has been generated. "
        ::= { wfOsi 22 }

    wfOsiSeqNumberSkips OBJECT-TYPE
        SYNTAX	Counter
        ACCESS	read-only
        STATUS	mandatory
        DESCRIPTION
                "Number of times the Sequence Number Skipped event has
                been generated. "
        ::= { wfOsi 23 }

    wfOsiOwnLspPurges OBJECT-TYPE
        SYNTAX	Counter
        ACCESS	read-only
        STATUS	mandatory
        DESCRIPTION
                "Number of times the Own Lsp Purged event has
                been generated. "
        ::= { wfOsi 24 }

    wfOsiOthLspPurges OBJECT-TYPE
        SYNTAX	Counter
        ACCESS	read-only
        STATUS	mandatory
        DESCRIPTION
                "Number of times the Other Lsp Purged event has
                been generated. "
        ::= { wfOsi 25 }

    wfOsiExceedMaxSeqNums OBJECT-TYPE
        SYNTAX	Counter
        ACCESS	read-only
        STATUS	mandatory
        DESCRIPTION
                "Number of times the Attempt tp Exceed Maximum Sequence Number
                event has been generated. "
        ::= { wfOsi 26 }

    wfOsiNearestL2Is OBJECT-TYPE
        SYNTAX	OCTET STRING
        ACCESS	read-only
        STATUS	mandatory
        DESCRIPTION
                "This is the ID of the Nearest L2 system in this area."
        ::= { wfOsi 27 }

    wfOsiMaxDynEs OBJECT-TYPE
        SYNTAX	INTEGER(1..4000)
        ACCESS	read-write
        STATUS	mandatory
        DESCRIPTION
                "This is the maximum number of dynamically learned (via Hello)
                End Systems allowed per slot."
        DEFVAL	{ 1024 }
        ::= { wfOsi 28 }

    wfOsiMaxDynL1Is OBJECT-TYPE
        SYNTAX	INTEGER(1..1000)
        ACCESS	read-write
        STATUS	mandatory
        DESCRIPTION
                "This is the maximum number of dynamically learned (via Hello)
                Level 1 Intermediate Systems allowed per slot."
        DEFVAL	{ 64 }
        ::= { wfOsi 29 }

    wfOsiMaxDynL2Is OBJECT-TYPE
        SYNTAX	INTEGER(1..1000)
        ACCESS	read-write
        STATUS	mandatory
        DESCRIPTION
                "This is the maximum number of dynamically learned (via Hello)
                Level 2 Intermediate Systems allowed per slot."
        DEFVAL	{ 64 }
        ::= { wfOsi 30 }

    wfOsiNumDynEsAdjs OBJECT-TYPE
        SYNTAX	Counter
        ACCESS	read-only
        STATUS	mandatory
        DESCRIPTION
                "Number of Dynamic ES adjs the osi master gate
                receives from the cct gate. "
        ::= { wfOsi 31 }

    wfOsiNumDynL1Adjs OBJECT-TYPE
        SYNTAX	Counter
        ACCESS	read-only
        STATUS	mandatory
        DESCRIPTION
                "Number of Dynamic L1 adjs the osi master gate
                receives from the cct gate. "
        ::= { wfOsi 32 }

    wfOsiNumDynL2Adjs OBJECT-TYPE
        SYNTAX	Counter
        ACCESS	read-only
        STATUS	mandatory
        DESCRIPTION
                "Number of Dynamic L2 adjs the osi master gate
                receives from the cct gate. "
        ::= { wfOsi 33 }

    wfOsiNumL1Routes OBJECT-TYPE
        SYNTAX	Counter
        ACCESS	read-only
        STATUS	mandatory
        DESCRIPTION
                "Number of L1 Routes. WL 2.27.93"
        ::= { wfOsi 34 }

    wfOsiNumL2Routes OBJECT-TYPE
        SYNTAX	Counter
        ACCESS	read-only
        STATUS	mandatory
        DESCRIPTION
                "Number of L2 Routes. WL 2.27.93"
        ::= { wfOsi 35 }

    wfOsiNumDynPtpEsAdjs OBJECT-TYPE
        SYNTAX	Counter
        ACCESS	read-only
        STATUS	mandatory
        DESCRIPTION
                "Number of Dynamic Point-to-Point ES adjs the osi master gate
                receives on."
        ::= { wfOsi 36 }

    wfOsiNumDynPtpIsAdjs OBJECT-TYPE
        SYNTAX	Counter
        ACCESS	read-only
        STATUS	mandatory
        DESCRIPTION
                "Number of Dynamic Point-to-Point IS adjs the osi master gate
                receives on ."
        ::= { wfOsi 37 }

    wfOsiClnpSrcRtOptionDisable OBJECT-TYPE
        SYNTAX	INTEGER {
    		    enabled(1),
    		    disabled(2)
    		}
        ACCESS	read-write
        STATUS	mandatory
        DESCRIPTION
                "Enable/Disable processing of Source Route options in CLNP PDUs.
                This is required for GOSIP v2 support. GOSIP prohibits processing
                Source Routing options. "
        DEFVAL	{ enabled }
        ::= { wfOsi 38 }

    wfOsiNumL1Lsps OBJECT-TYPE
        SYNTAX	Counter
        ACCESS	read-only
        STATUS	mandatory
        DESCRIPTION
                "Number of L1 LSPs stored in database."
        ::= { wfOsi 39 }

    wfOsiNumL2Lsps OBJECT-TYPE
        SYNTAX	Counter
        ACCESS	read-only
        STATUS	mandatory
        DESCRIPTION
                "Number of L2 LSPs stored in database."
        ::= { wfOsi 40 }

    wfOsiFletchRelaxedEnable OBJECT-TYPE
        SYNTAX  INTEGER {
                    enabled(1),
                    disabled(2)
                }
        ACCESS  read-write
        STATUS  mandatory
        DESCRIPTION
                "Enable/Disable whether non-standard Fletcher Checksums are
                allowed in LSP's. If enabled, a log message will be generated,
                otherwise the LSP will be rejected."
        DEFVAL  { disabled }
        ::= { wfOsi 41 }

    wfOsiStaticRouteTable OBJECT-TYPE
        SYNTAX	SEQUENCE OF WfOsiStaticRouteEntry
        ACCESS	not-accessible
        STATUS	mandatory
        DESCRIPTION
                "This table contains all the static routes for this system."
        ::= { wfOsiGroup 2 }

    wfOsiStaticRouteEntry OBJECT-TYPE
        SYNTAX	WfOsiStaticRouteEntry
        ACCESS	not-accessible
        STATUS	mandatory
        DESCRIPTION
                "This is the Static Route Entry for the Static Route Table."
        INDEX	{ wfOsiStaticRouteAddr }
        ::= { wfOsiStaticRouteTable 1 }

    WfOsiStaticRouteEntry ::= SEQUENCE {
    	    wfOsiStaticRouteDelete
    		INTEGER,
    	    wfOsiStaticRouteDisable
    		INTEGER,
    	    wfOsiStaticRouteAddr
    		OCTET STRING,
    	    wfOsiStaticRouteNibbleLength
    		INTEGER,
    	    wfOsiStaticRouteNextHopIs
    		OCTET STRING,
    	    wfOsiStaticRouteType
    		INTEGER,
    	    wfOsiStaticRouteCost
    		INTEGER
        }

    wfOsiStaticRouteDelete OBJECT-TYPE
        SYNTAX	INTEGER {
    		    created(1),
    		    deleted(2)
    		}
        ACCESS	read-write
        STATUS	mandatory
        DESCRIPTION
                "Create/Delete parameter for Osi Static Route Record."
        DEFVAL	{ created }
        ::= { wfOsiStaticRouteEntry 1 }

    wfOsiStaticRouteDisable OBJECT-TYPE
        SYNTAX	INTEGER {
    		    enabled(1),
    		    disabled(2)
    		}
        ACCESS	read-write
        STATUS	mandatory
        DESCRIPTION
                "Enable/Disable parameter for this Static Route."
        DEFVAL	{ enabled }
        ::= { wfOsiStaticRouteEntry 2 }

    wfOsiStaticRouteAddr OBJECT-TYPE
        SYNTAX	OCTET STRING (SIZE (20))
        ACCESS	read-only
        STATUS	mandatory
        DESCRIPTION
                "This specifies the address of the static route. It is also
                the inst_id."
        ::= { wfOsiStaticRouteEntry 3 }

    wfOsiStaticRouteNibbleLength OBJECT-TYPE
        SYNTAX	INTEGER
        ACCESS	read-write
        STATUS	mandatory
        DESCRIPTION
                "This is the length in nibbles of the static route address.
                It is necessary to specify it in nibbles since the static route
                may be an external address which can be specified in nibbles."
        ::= { wfOsiStaticRouteEntry 4 }

    wfOsiStaticRouteNextHopIs OBJECT-TYPE
        SYNTAX	OCTET STRING
        ACCESS	read-write
        STATUS	mandatory
        DESCRIPTION
                "This is the 6-octet ID of the next Hop IS that all
                data destined to wfOsiStaticRouteAddr will be forwarded to."
        ::= { wfOsiStaticRouteEntry 5 }

    wfOsiStaticRouteType OBJECT-TYPE
        SYNTAX	INTEGER {
    		    es(9),
    		    areaaddr(11),
    		    extaddr(13)
    		}
        ACCESS	read-write
        STATUS	mandatory
        DESCRIPTION
                "This specifies whether the destination is an End System,
                an area, or an external Domain."
        DEFVAL	{ es }
        ::= { wfOsiStaticRouteEntry 6 }

    wfOsiStaticRouteCost OBJECT-TYPE
        SYNTAX	INTEGER(1..1023)
        ACCESS	read-write
        STATUS	mandatory
        DESCRIPTION
                "This value is the cost to get to this address."
        DEFVAL	{ 20 }
        ::= { wfOsiStaticRouteEntry 7 }

    wfOsiCircuitTable OBJECT-TYPE
        SYNTAX	SEQUENCE OF WfOsiCircuitEntry
        ACCESS	not-accessible
        STATUS	mandatory
        DESCRIPTION
                "This Table contains all circuit configuration info
                counters available on a per circuit basis."
        ::= { wfOsiGroup 3 }

    wfOsiCircuitEntry OBJECT-TYPE
        SYNTAX	WfOsiCircuitEntry
        ACCESS	not-accessible
        STATUS	mandatory
        DESCRIPTION
                "This is the circuit entry record that appears in the
                Circuit Table."
        INDEX	{ wfOsiCircuitId }
        ::= { wfOsiCircuitTable 1 }

    WfOsiCircuitEntry ::= SEQUENCE {
    	    wfOsiCircuitDelete
    		INTEGER,
    	    wfOsiCircuitDisable
    		INTEGER,
    	    wfOsiCircuitState
    		INTEGER,
    	    wfOsiCircuitId
    		INTEGER,
    	    wfOsiCircuitRouterLevel
    		INTEGER,
    	    wfOsiCircuitL1DefaultMetric
    		INTEGER,
    	    wfOsiCircuitL2DefaultMetric
    		INTEGER,
    	    wfOsiCircuitL1DrPriority
    		INTEGER,
    	    wfOsiCircuitL2DrPriority
    		INTEGER,
    	    wfOsiCircuitIsisHelloTimer
    		INTEGER,
    	    wfOsiCircuitEsisHelloTimer
    		INTEGER,
    	    wfOsiCircuitEshConfigTime
    		INTEGER,
    	    wfOsiCircuitPassword
    		DisplayString,
    	    wfOsiCircuitReceivedPkts
    		Counter,
    	    wfOsiCircuitSentPkts
    		Counter,
    	    wfOsiCircuitDroppedPkts
    		Counter,
    	    wfOsiCircuitFragmentedPdus
    		Counter,
    	    wfOsiCircuitCongestionDiscards
    		Counter,
    	    wfOsiCircuitAddrUnreachDiscards
    		Counter,
    	    wfOsiCircuitAgedPduDiscards
    		Counter,
    	    wfOsiCircuitPduFormatErrDiscards
    		Counter,
    	    wfOsiCircuitUnsuppOptsDiscards
    		Counter,
    	    wfOsiCircuitSentErrorReports
    		Counter,
    	    wfOsiCircuitReceivedControlPdus
    		Counter,
    	    wfOsiCircuitSentControlPdus
    		Counter,
    	    wfOsiCircuitStateChanges
    		Counter,
    	    wfOsiCircuitAdjStateChanges
    		Counter,
    	    wfOsiCircuitInitFailures
    		Counter,
    	    wfOsiCircuitRejectedAdjs
    		Counter,
    	    wfOsiCircuitReceivedBadLsps
    		Counter,
    	    wfOsiCircuitReceivedBadSnps
    		Counter,
    	    wfOsiCircuitReceivedBadEshs
    		Counter,
    	    wfOsiCircuitReceivedBadL1Iihs
    		Counter,
    	    wfOsiCircuitReceivedBadL2Iihs
    		Counter,
    	    wfOsiCircuitL1DrChanges
    		Counter,
    	    wfOsiCircuitL2DrChanges
    		Counter,
    	    wfOsiCircuitClnpForwarding
    		Counter,
    	    wfOsiCircuitClnpDefaultLifeTime
    		Counter,
    	    wfOsiCircuitClnpInReceives
    		Counter,
    	    wfOsiCircuitClnpInAddrErrors
    		Counter,
    	    wfOsiCircuitClnpForwPdus
    		Counter,
    	    wfOsiCircuitClnpInUnknownNlps
    		Counter,
    	    wfOsiCircuitClnpInDelivers
    		Counter,
    	    wfOsiCircuitClnpInUnknownUlps
    		Counter,
    	    wfOsiCircuitClnpSegCreates
    		Counter,
    	    wfOsiCircuitClnpInOpts
    		Counter,
    	    wfOsiCircuitClnpOutOpts
    		Counter,
    	    wfOsiCircuitEsisEshIns
    		Counter,
    	    wfOsiCircuitEsisIshOuts
    		Counter,
    	    wfOsiCircuitEsisRduOuts
    		Counter,
    	    wfOsiCircuitL1DesignatedRouter
    		OCTET STRING,
    	    wfOsiCircuitL2DesignatedRouter
    		OCTET STRING,
    	    wfOsiCircuitClnpOutEchoReplies
    		Counter,
    	    wfOsiCircuitClnpOutEchoRequests
    		Counter,
    	    wfOsiCircuitClnpInEchoReplies
    		Counter,
    	    wfOsiCircuitClnpInEchoRequests
    		Counter,
    	    wfOsiCircuitNumDynEsAdjs
    		Counter,
    	    wfOsiCircuitNumDynL1Adjs
    		Counter,
    	    wfOsiCircuitNumDynL2Adjs
    		Counter,
    	    wfOsiCircuitNumDynPtpIsAdjs
    		Counter,
    	    wfOsiCircuitNumDynPtpEsAdjs
    		Counter,
    	    wfOsiCircuitBadIshReceived
    		Counter,
    	    wfOsiCircuitEsisIshIns
    		Counter,
    	    wfOsiCircuitIihHoldMultiplier
    		INTEGER,
    	    wfOsiCircuitIshHoldMultiplier
    		INTEGER,
    	    wfOsiCircuitDisableRedirect
    		INTEGER
        }

    wfOsiCircuitDelete OBJECT-TYPE
        SYNTAX	INTEGER {
    		    created(1),
    		    deleted(2)
    		}
        ACCESS	read-write
        STATUS	mandatory
        DESCRIPTION
                "This value determines whether this circuit is configured."
        DEFVAL	{ created }
        ::= { wfOsiCircuitEntry 1 }

    wfOsiCircuitDisable OBJECT-TYPE
        SYNTAX	INTEGER {
    		    enabled(1),
    		    disabled(2)
    		}
        ACCESS	read-write
        STATUS	mandatory
        DESCRIPTION
                "Enable/Disable parameter for this circuit."
        DEFVAL	{ enabled }
        ::= { wfOsiCircuitEntry 2 }

    wfOsiCircuitState OBJECT-TYPE
        SYNTAX	INTEGER {
    		    up(1),
    		    down(2)
    		}
        ACCESS	read-only
        STATUS	mandatory
        DESCRIPTION
                "This indicates whether the circuit state is up or down."
        DEFVAL	{ down }
        ::= { wfOsiCircuitEntry 3 }

    wfOsiCircuitId OBJECT-TYPE
        SYNTAX	INTEGER
        ACCESS	read-only
        STATUS	mandatory
        DESCRIPTION
                "A unique value for each known circuit."
        ::= { wfOsiCircuitEntry 4 }

    wfOsiCircuitRouterLevel OBJECT-TYPE
        SYNTAX	INTEGER {
    		    l1(1),
    		    l2(2),
    		    l1l2(3),
    		    ext(4),
    		    l2ext(6),
    		    l1l2ext(7),
    		    esisonly(8)
    		}
        ACCESS	read-write
        STATUS	mandatory
        DESCRIPTION
                "This is the level protocol that the circuit runs.
                Its a bit mask to allow for some combination of
                L1, L2, External, ES-IS-only."
        DEFVAL	{ l1l2 }
        ::= { wfOsiCircuitEntry 5 }

    wfOsiCircuitL1DefaultMetric OBJECT-TYPE
        SYNTAX	INTEGER(1..63)
        ACCESS	read-write
        STATUS	mandatory
        DESCRIPTION
                "This is the default cost of using this circuit for L1 traffic."
        DEFVAL	{ 20 }
        ::= { wfOsiCircuitEntry 6 }

    wfOsiCircuitL2DefaultMetric OBJECT-TYPE
        SYNTAX	INTEGER(1..63)
        ACCESS	read-write
        STATUS	mandatory
        DESCRIPTION
                "This is the default cost of using this circuit for L2 traffic."
        DEFVAL	{ 20 }
        ::= { wfOsiCircuitEntry 7 }

    wfOsiCircuitL1DrPriority OBJECT-TYPE
        SYNTAX	INTEGER(1..127)
        ACCESS	read-write
        STATUS	mandatory
        DESCRIPTION
                "This is the priority for this system to become L1 designated
                router on this LAN circuit."
        DEFVAL	{ 64 }
        ::= { wfOsiCircuitEntry 8 }

    wfOsiCircuitL2DrPriority OBJECT-TYPE
        SYNTAX	INTEGER(1..127)
        ACCESS	read-write
        STATUS	mandatory
        DESCRIPTION
                "This is the priority for this system to become L2 designated
                router on this LAN circuit."
        DEFVAL	{ 64 }
        ::= { wfOsiCircuitEntry 9 }

    wfOsiCircuitIsisHelloTimer OBJECT-TYPE
        SYNTAX	INTEGER(1..3600)
        ACCESS	read-write
        STATUS	mandatory
        DESCRIPTION
                "This is the period (secs) between IIH hello transmissions."
        DEFVAL	{ 8 }
        ::= { wfOsiCircuitEntry 10 }

    wfOsiCircuitEsisHelloTimer OBJECT-TYPE
        SYNTAX	INTEGER(1..3600)
        ACCESS	read-write
        STATUS	mandatory
        DESCRIPTION
                "This is the period (secs) between ISH hello transmissions."
        DEFVAL	{ 30 }
        ::= { wfOsiCircuitEntry 11 }

    wfOsiCircuitEshConfigTime OBJECT-TYPE
        SYNTAX	INTEGER(1..3600)
        ACCESS	read-write
        STATUS	mandatory
        DESCRIPTION
                "This is the suggested time between ESH transmissions from an
                ES went in ISHs (ESCT)."
        DEFVAL	{ 600 }
        ::= { wfOsiCircuitEntry 12 }

    wfOsiCircuitPassword OBJECT-TYPE
        SYNTAX	DisplayString
        ACCESS	read-write
        STATUS	mandatory
        DESCRIPTION
                "This is Circuit Password for this circuit. Used to filter
                out Hellos from systems without the correct password."
        ::= { wfOsiCircuitEntry 13 }

    wfOsiCircuitReceivedPkts OBJECT-TYPE
        SYNTAX	Counter
        ACCESS	read-only
        STATUS	mandatory
        DESCRIPTION
                "This is the number of pkts that have been received on this
                circuit."
        ::= { wfOsiCircuitEntry 14 }

    wfOsiCircuitSentPkts OBJECT-TYPE
        SYNTAX	Counter
        ACCESS	read-only
        STATUS	mandatory
        DESCRIPTION
                "This is the number of pkts sent out this circuit."
        ::= { wfOsiCircuitEntry 15 }

    wfOsiCircuitDroppedPkts OBJECT-TYPE
        SYNTAX	Counter
        ACCESS	read-only
        STATUS	mandatory
        DESCRIPTION
                "This is the number of pkts dropped on this circuit."
        ::= { wfOsiCircuitEntry 16 }

    wfOsiCircuitFragmentedPdus OBJECT-TYPE
        SYNTAX	Counter
        ACCESS	read-only
        STATUS	mandatory
        DESCRIPTION
                "This is the number of pdus that had to be fragmented
                when forwarded out this circuit."
        ::= { wfOsiCircuitEntry 17 }

    wfOsiCircuitCongestionDiscards OBJECT-TYPE
        SYNTAX	Counter
        ACCESS	read-only
        STATUS	mandatory
        DESCRIPTION
                "This is the number of PDUs dropped because of congestion."
        ::= { wfOsiCircuitEntry 18 }

    wfOsiCircuitAddrUnreachDiscards OBJECT-TYPE
        SYNTAX	Counter
        ACCESS	read-only
        STATUS	mandatory
        DESCRIPTION
                "This is the number of PDUs dropped because the destination
                is unreachable."
        ::= { wfOsiCircuitEntry 19 }

    wfOsiCircuitAgedPduDiscards OBJECT-TYPE
        SYNTAX	Counter
        ACCESS	read-only
        STATUS	mandatory
        DESCRIPTION
                "This is the number of PDUs dropped because of aging."
        ::= { wfOsiCircuitEntry 20 }

    wfOsiCircuitPduFormatErrDiscards OBJECT-TYPE
        SYNTAX	Counter
        ACCESS	read-only
        STATUS	mandatory
        DESCRIPTION
                "This is the number of PDUs dropped because of Format Error."
        ::= { wfOsiCircuitEntry 21 }

    wfOsiCircuitUnsuppOptsDiscards OBJECT-TYPE
        SYNTAX	Counter
        ACCESS	read-only
        STATUS	mandatory
        DESCRIPTION
                "This is the number of PDUs dropped because they contain
                unsupported options."
        ::= { wfOsiCircuitEntry 22 }

    wfOsiCircuitSentErrorReports OBJECT-TYPE
        SYNTAX	Counter
        ACCESS	read-only
        STATUS	mandatory
        DESCRIPTION
                "This is the number of error reports sent out this circuit."
        ::= { wfOsiCircuitEntry 23 }

    wfOsiCircuitReceivedControlPdus OBJECT-TYPE
        SYNTAX	Counter
        ACCESS	read-only
        STATUS	mandatory
        DESCRIPTION
                "This is the number of ESIS or ISIS PDUs received on this circuit."
        ::= { wfOsiCircuitEntry 24 }

    wfOsiCircuitSentControlPdus OBJECT-TYPE
        SYNTAX	Counter
        ACCESS	read-only
        STATUS	mandatory
        DESCRIPTION
                "This is the number of ESIS or ISIS PDUs sent out this circuit."
        ::= { wfOsiCircuitEntry 25 }

    wfOsiCircuitStateChanges OBJECT-TYPE
        SYNTAX	Counter
        ACCESS	read-only
        STATUS	mandatory
        DESCRIPTION
                "This is the number of times the circuit goes from down to up
                or from up to down."
        ::= { wfOsiCircuitEntry 26 }

    wfOsiCircuitAdjStateChanges OBJECT-TYPE
        SYNTAX	Counter
        ACCESS	read-only
        STATUS	mandatory
        DESCRIPTION
                "This is the number of times an adjacency off of this circuit
                goes from down to up or from up to down state."
        ::= { wfOsiCircuitEntry 27 }

    wfOsiCircuitInitFailures OBJECT-TYPE
        SYNTAX	Counter
        ACCESS	read-only
        STATUS	mandatory
        DESCRIPTION
                "This is the number of times this circuit fails to initialize."
        ::= { wfOsiCircuitEntry 28 }

    wfOsiCircuitRejectedAdjs OBJECT-TYPE
        SYNTAX	Counter
        ACCESS	read-only
        STATUS	mandatory
        DESCRIPTION
                "This is the number of Adjacencies that were rejected on
                this circuit."
        ::= { wfOsiCircuitEntry 29 }

    wfOsiCircuitReceivedBadLsps OBJECT-TYPE
        SYNTAX	Counter
        ACCESS	read-only
        STATUS	mandatory
        DESCRIPTION
                "This is the number of bad Lsps received on this circuit."
        ::= { wfOsiCircuitEntry 30 }

    wfOsiCircuitReceivedBadSnps OBJECT-TYPE
        SYNTAX	Counter
        ACCESS	read-only
        STATUS	mandatory
        DESCRIPTION
                "This is the number of BAD Sequence Number Pdus received on
                this circuit."
        ::= { wfOsiCircuitEntry 31 }

    wfOsiCircuitReceivedBadEshs OBJECT-TYPE
        SYNTAX	Counter
        ACCESS	read-only
        STATUS	mandatory
        DESCRIPTION
                "This is the number of bad ESHs received on this circuit."
        ::= { wfOsiCircuitEntry 32 }

    wfOsiCircuitReceivedBadL1Iihs OBJECT-TYPE
        SYNTAX	Counter
        ACCESS	read-only
        STATUS	mandatory
        DESCRIPTION
                "This is the number of bad L1 IIHs received on this circuit."
        ::= { wfOsiCircuitEntry 33 }

    wfOsiCircuitReceivedBadL2Iihs OBJECT-TYPE
        SYNTAX	Counter
        ACCESS	read-only
        STATUS	mandatory
        DESCRIPTION
                "This is the number of bad L2 IIHs received on this circuit."
        ::= { wfOsiCircuitEntry 34 }

    wfOsiCircuitL1DrChanges OBJECT-TYPE
        SYNTAX	Counter
        ACCESS	read-only
        STATUS	mandatory
        DESCRIPTION
                "This is the number of times the L1 Designated Router has been
                elected on this circuit."
        ::= { wfOsiCircuitEntry 35 }

    wfOsiCircuitL2DrChanges OBJECT-TYPE
        SYNTAX	Counter
        ACCESS	read-only
        STATUS	mandatory
        DESCRIPTION
                "This is the number of times the L2 Designated Router has been
                elected on this circuit."
        ::= { wfOsiCircuitEntry 36 }

    wfOsiCircuitClnpForwarding OBJECT-TYPE
        SYNTAX	Counter
        ACCESS	read-only
        STATUS	mandatory
        DESCRIPTION
                "This shows whether forwarding is enabled over this circuit."
        ::= { wfOsiCircuitEntry 37 }

    wfOsiCircuitClnpDefaultLifeTime OBJECT-TYPE
        SYNTAX	Counter
        ACCESS	read-only
        STATUS	mandatory
        DESCRIPTION
                "This is the lifetime included in clnp pdus generated by this
                router (i.e. echo and echo reply pdus, error report pdus)."
        ::= { wfOsiCircuitEntry 38 }

    wfOsiCircuitClnpInReceives OBJECT-TYPE
        SYNTAX	Counter
        ACCESS	read-only
        STATUS	mandatory
        DESCRIPTION
                "This is the number of CLNP pdus received from this circuit."
        ::= { wfOsiCircuitEntry 39 }

    wfOsiCircuitClnpInAddrErrors OBJECT-TYPE
        SYNTAX	Counter
        ACCESS	read-only
        STATUS	mandatory
        DESCRIPTION
                "This is the number of CLNP pdus recived from this circuit
                with Address format errors."
        ::= { wfOsiCircuitEntry 40 }

    wfOsiCircuitClnpForwPdus OBJECT-TYPE
        SYNTAX	Counter
        ACCESS	read-only
        STATUS	mandatory
        DESCRIPTION
                "This is the number of Clnp PDUs received on this circuit
                that are forwarded."
        ::= { wfOsiCircuitEntry 41 }

    wfOsiCircuitClnpInUnknownNlps OBJECT-TYPE
        SYNTAX	Counter
        ACCESS	read-only
        STATUS	mandatory
        DESCRIPTION
                "This is the number of Clnp PDUs received on this circuit
                where the network layer addressed is unknown (Bad NLPID)."
        ::= { wfOsiCircuitEntry 42 }

    wfOsiCircuitClnpInDelivers OBJECT-TYPE
        SYNTAX	Counter
        ACCESS	read-only
        STATUS	mandatory
        DESCRIPTION
                "This is the number of Clnp PDUs received on this circuit
                whose destination is this router."
        ::= { wfOsiCircuitEntry 43 }

    wfOsiCircuitClnpInUnknownUlps OBJECT-TYPE
        SYNTAX	Counter
        ACCESS	read-only
        STATUS	mandatory
        DESCRIPTION
                "This is number of Clnp PDUs received on this circuit addressed
                to this router where the upper layer is unknown."
        ::= { wfOsiCircuitEntry 44 }

    wfOsiCircuitClnpSegCreates OBJECT-TYPE
        SYNTAX	Counter
        ACCESS	read-only
        STATUS	mandatory
        DESCRIPTION
                "This is the number of CLNP segments created from
                pdus received on this circuit."
        ::= { wfOsiCircuitEntry 45 }

    wfOsiCircuitClnpInOpts OBJECT-TYPE
        SYNTAX	Counter
        ACCESS	read-only
        STATUS	mandatory
        DESCRIPTION
                "This is the number of CLNP pdus received with an options
                portion."
        ::= { wfOsiCircuitEntry 46 }

    wfOsiCircuitClnpOutOpts OBJECT-TYPE
        SYNTAX	Counter
        ACCESS	read-only
        STATUS	mandatory
        DESCRIPTION
                "This is the number of CLNP pdus sent with an options
                portion."
        ::= { wfOsiCircuitEntry 47 }

    wfOsiCircuitEsisEshIns OBJECT-TYPE
        SYNTAX	Counter
        ACCESS	read-only
        STATUS	mandatory
        DESCRIPTION
                "This is the number of ESHs received from this circuit."
        ::= { wfOsiCircuitEntry 48 }

    wfOsiCircuitEsisIshOuts OBJECT-TYPE
        SYNTAX	Counter
        ACCESS	read-only
        STATUS	mandatory
        DESCRIPTION
                "This is the number of ISHs sent out this circuit."
        ::= { wfOsiCircuitEntry 49 }

    wfOsiCircuitEsisRduOuts OBJECT-TYPE
        SYNTAX	Counter
        ACCESS	read-only
        STATUS	mandatory
        DESCRIPTION
                "This is the number of Redirects sent out this circuit."
        ::= { wfOsiCircuitEntry 50 }

    wfOsiCircuitL1DesignatedRouter OBJECT-TYPE
        SYNTAX	OCTET STRING
        ACCESS	read-only
        STATUS	mandatory
        DESCRIPTION
                "This is the ID of the L1 Designated Router on this
                circuit."
        ::= { wfOsiCircuitEntry 51 }

    wfOsiCircuitL2DesignatedRouter OBJECT-TYPE
        SYNTAX	OCTET STRING
        ACCESS	read-only
        STATUS	mandatory
        DESCRIPTION
                "This is the ID of the L2 Designated Router on this
                circuit."
        ::= { wfOsiCircuitEntry 52 }

    wfOsiCircuitClnpOutEchoReplies OBJECT-TYPE
        SYNTAX	Counter
        ACCESS	read-only
        STATUS	mandatory
        DESCRIPTION
                "This is the number of CLNP Echo Replies sent out this circuit."
        ::= { wfOsiCircuitEntry 53 }

    wfOsiCircuitClnpOutEchoRequests OBJECT-TYPE
        SYNTAX	Counter
        ACCESS	read-only
        STATUS	mandatory
        DESCRIPTION
                "This is the number of Clnp Echo Requests sent out this circuit."
        ::= { wfOsiCircuitEntry 54 }

    wfOsiCircuitClnpInEchoReplies OBJECT-TYPE
        SYNTAX	Counter
        ACCESS	read-only
        STATUS	mandatory
        DESCRIPTION
                "This is the number of CLNP Echo Replies received on this circuit."
        ::= { wfOsiCircuitEntry 55 }

    wfOsiCircuitClnpInEchoRequests OBJECT-TYPE
        SYNTAX	Counter
        ACCESS	read-only
        STATUS	mandatory
        DESCRIPTION
                "This is the number of CLNP Echo Requests recived on this circuit."
        ::= { wfOsiCircuitEntry 56 }

    wfOsiCircuitNumDynEsAdjs OBJECT-TYPE
        SYNTAX	Counter
        ACCESS	read-only
        STATUS	mandatory
        DESCRIPTION
                "This is the number of Dynamic End System Adjacencies formed on
                this circuit."
        ::= { wfOsiCircuitEntry 57 }

    wfOsiCircuitNumDynL1Adjs OBJECT-TYPE
        SYNTAX	Counter
        ACCESS	read-only
        STATUS	mandatory
        DESCRIPTION
                "This is the number of Dynamic Level 1 Intermediate System
                Adjacencies formed on this circuit. "
        ::= { wfOsiCircuitEntry 58 }

    wfOsiCircuitNumDynL2Adjs OBJECT-TYPE
        SYNTAX	Counter
        ACCESS	read-only
        STATUS	mandatory
        DESCRIPTION
                "This is the number of Dynamic Level 2 Intermediate System
                Adjacencies formed on this circuit."
        ::= { wfOsiCircuitEntry 59 }

    wfOsiCircuitNumDynPtpIsAdjs OBJECT-TYPE
        SYNTAX	Counter
        ACCESS	read-only
        STATUS	mandatory
        DESCRIPTION
                "This is the number of Dynamic Intermediate System Point-to-Point
                Adjacencies formed on this circuit."
        ::= { wfOsiCircuitEntry 60 }

    wfOsiCircuitNumDynPtpEsAdjs OBJECT-TYPE
        SYNTAX	Counter
        ACCESS	read-only
        STATUS	mandatory
        DESCRIPTION
                "This is the number of Dynamic End System Point-to-Point
                Adjaciences formed on this circuit."
        ::= { wfOsiCircuitEntry 61 }

    wfOsiCircuitBadIshReceived OBJECT-TYPE
        SYNTAX	Counter
        ACCESS	read-only
        STATUS	mandatory
        DESCRIPTION
                "This is the number of bad Intermediate System Hellos
                received on this circuit. These will only be received on
                Point-to-Point circuits."
        ::= { wfOsiCircuitEntry 62 }

    wfOsiCircuitEsisIshIns OBJECT-TYPE
        SYNTAX	Counter
        ACCESS	read-only
        STATUS	mandatory
        DESCRIPTION
                "This is the number of good Intermediate System Hellos
                received on this circuit. These will only be received on
                Point-to-Point circuits."
        ::= { wfOsiCircuitEntry 63 }

    wfOsiCircuitIihHoldMultiplier OBJECT-TYPE
        SYNTAX	INTEGER(1..5)
        ACCESS	read-write
        STATUS	mandatory
        DESCRIPTION
                "This is the multiplier value used to compute the hold time
                set in the IIH PDUs transmitted from this router. Hold time
                equals IIH Timer times IIH Hold Multiplier."
        DEFVAL	{ 3 }
        ::= { wfOsiCircuitEntry 64 }

    wfOsiCircuitIshHoldMultiplier OBJECT-TYPE
        SYNTAX	INTEGER(1..5)
        ACCESS	read-write
        STATUS	mandatory
        DESCRIPTION
                "This is the multiplier value used to compute the hold time
                set in the ISH PDUs transmitted from this router. Hold time
                equals IIH Timer times IIH Hold Multiplier."
        DEFVAL	{ 3 }
        ::= { wfOsiCircuitEntry 65 }

    wfOsiCircuitDisableRedirect OBJECT-TYPE
        SYNTAX	INTEGER {
    		    enabled(1),
    		    disabled(2)
    		}
        ACCESS	read-write
        STATUS	mandatory
        DESCRIPTION
                "Allow Redirects to be disabled. This is required
                when operating over Frame Relay in group mode in a
                partial mesh topology."
        DEFVAL	{ enabled }
        ::= { wfOsiCircuitEntry 66 }

    wfOsiExternalAddressTable OBJECT-TYPE
        SYNTAX	SEQUENCE OF WfOsiExternalAddressEntry
        ACCESS	not-accessible
        STATUS	mandatory
        DESCRIPTION
                "This is the table of External Addresses for this Router."
        ::= { wfOsiGroup 4 }

    wfOsiExternalAddressEntry OBJECT-TYPE
        SYNTAX	WfOsiExternalAddressEntry
        ACCESS	not-accessible
        STATUS	mandatory
        DESCRIPTION
                "This is the External Address Record for this Router."
        INDEX	{ wfOsiExtAddrCircuit,
    		  wfOsiExtAddr }
        ::= { wfOsiExternalAddressTable 1 }

    WfOsiExternalAddressEntry ::= SEQUENCE {
    	    wfOsiExtAddrDelete
    		INTEGER,
    	    wfOsiExtAddrDisable
    		INTEGER,
    	    wfOsiExtAddr
    		OCTET STRING,
    	    wfOsiExtAddrCircuit
    		INTEGER,
    	    wfOsiExtAddrNibbleLength
    		INTEGER,
    	    wfOsiExtAddrSnpa
    		OCTET STRING,
    	    wfOsiExtAddrCost
    		INTEGER
        }

    wfOsiExtAddrDelete OBJECT-TYPE
        SYNTAX	INTEGER {
    		    created(1),
    		    deleted(2)
    		}
        ACCESS	read-write
        STATUS	mandatory
        DESCRIPTION
                "This is the Create/Delete parameter for this ExtAddr entry."
        DEFVAL	{ created }
        ::= { wfOsiExternalAddressEntry 1 }

    wfOsiExtAddrDisable OBJECT-TYPE
        SYNTAX	INTEGER {
    		    enabled(1),
    		    disabled(2)
    		}
        ACCESS	read-write
        STATUS	mandatory
        DESCRIPTION
                "Enable/Disable parameter for this ExtAddr."
        DEFVAL	{ enabled }
        ::= { wfOsiExternalAddressEntry 2 }

    wfOsiExtAddr OBJECT-TYPE
        SYNTAX	OCTET STRING (SIZE (20))
        ACCESS	read-only
        STATUS	mandatory
        DESCRIPTION
                "This is the prefix external address. It is also the inst_id."
        ::= { wfOsiExternalAddressEntry 3 }

    wfOsiExtAddrCircuit OBJECT-TYPE
        SYNTAX	INTEGER
        ACCESS	read-only
        STATUS	mandatory
        DESCRIPTION
                "This is the circuit to go out for this adj."
        ::= { wfOsiExternalAddressEntry 4 }

    wfOsiExtAddrNibbleLength OBJECT-TYPE
        SYNTAX	INTEGER
        ACCESS	read-write
        STATUS	mandatory
        DESCRIPTION
                "This is the length in nibbles of the external address."
        ::= { wfOsiExternalAddressEntry 5 }

    wfOsiExtAddrSnpa OBJECT-TYPE
        SYNTAX	OCTET STRING
        ACCESS	read-write
        STATUS	mandatory
        DESCRIPTION
                "This is the SNPA of the neighbor on this circuit."
        ::= { wfOsiExternalAddressEntry 6 }

    wfOsiExtAddrCost OBJECT-TYPE
        SYNTAX	INTEGER(1..63)
        ACCESS	read-write
        STATUS	mandatory
        DESCRIPTION
                "This is the external metric cost to this address."
        DEFVAL	{ 20 }
        ::= { wfOsiExternalAddressEntry 7 }

    wfOsiStaticEsTable OBJECT-TYPE
        SYNTAX	SEQUENCE OF WfOsiStaticEsEntry
        ACCESS	not-accessible
        STATUS	mandatory
        DESCRIPTION
                "This is the Static ES Table for this router."
        ::= { wfOsiGroup 5 }

    wfOsiStaticEsEntry OBJECT-TYPE
        SYNTAX	WfOsiStaticEsEntry
        ACCESS	not-accessible
        STATUS	mandatory
        DESCRIPTION
                "This is the Static ES entry for the Static ES Table."
        INDEX	{ wfOsiStaticEsCircuit,
    		  wfOsiStaticEsId }
        ::= { wfOsiStaticEsTable 1 }

    WfOsiStaticEsEntry ::= SEQUENCE {
    	    wfOsiStaticEsDelete
    		INTEGER,
    	    wfOsiStaticEsDisable
    		INTEGER,
    	    wfOsiStaticEsId
    		OCTET STRING,
    	    wfOsiStaticEsCircuit
    		INTEGER,
    	    wfOsiStaticEsSnpa
    		OCTET STRING
        }

    wfOsiStaticEsDelete OBJECT-TYPE
        SYNTAX	INTEGER {
    		    created(1),
    		    deleted(2)
    		}
        ACCESS	read-write
        STATUS	mandatory
        DESCRIPTION
                "This is the Create/Delete parameter for this Static ES entry."
        DEFVAL	{ created }
        ::= { wfOsiStaticEsEntry 1 }

    wfOsiStaticEsDisable OBJECT-TYPE
        SYNTAX	INTEGER {
    		    enabled(1),
    		    disabled(2)
    		}
        ACCESS	read-write
        STATUS	mandatory
        DESCRIPTION
                "Enable/Disable parameter for this Static ES."
        DEFVAL	{ enabled }
        ::= { wfOsiStaticEsEntry 2 }

    wfOsiStaticEsId OBJECT-TYPE
        SYNTAX	OCTET STRING (SIZE (6))
        ACCESS	read-only
        STATUS	mandatory
        DESCRIPTION
                "This is the ESID of the neighbor."
        ::= { wfOsiStaticEsEntry 3 }

    wfOsiStaticEsCircuit OBJECT-TYPE
        SYNTAX	INTEGER
        ACCESS	read-only
        STATUS	mandatory
        DESCRIPTION
                "This is the circuit to go out for this adj."
        ::= { wfOsiStaticEsEntry 4 }

    wfOsiStaticEsSnpa OBJECT-TYPE
        SYNTAX	OCTET STRING
        ACCESS	read-write
        STATUS	mandatory
        DESCRIPTION
                "This is the SNPA of the neighbor on this circuit."
        ::= { wfOsiStaticEsEntry 5 }

    wfOsiTrafficFilterTable OBJECT-TYPE
        SYNTAX	SEQUENCE OF WfOsiTrafficFilterEntry
        ACCESS	not-accessible
        STATUS	mandatory
        DESCRIPTION
                "OSI Traffic Filters"
        ::= { wfOsiGroup 6 }

    wfOsiTrafficFilterEntry OBJECT-TYPE
        SYNTAX	WfOsiTrafficFilterEntry
        ACCESS	not-accessible
        STATUS	mandatory
        DESCRIPTION
                "A traffic filter definition"
        INDEX	{ wfOsiTrafficFilterCircuit,
    		  wfOsiTrafficFilterRuleNumber,
    		  wfOsiTrafficFilterFragment }
        ::= { wfOsiTrafficFilterTable 1 }

    WfOsiTrafficFilterEntry ::= SEQUENCE {
    	    wfOsiTrafficFilterDelete
    		INTEGER,
    	    wfOsiTrafficFilterDisable
    		INTEGER,
    	    wfOsiTrafficFilterStatus
    		INTEGER,
    	    wfOsiTrafficFilterCounter
    		Counter,
    	    wfOsiTrafficFilterDefinition
    		Opaque,
    	    wfOsiTrafficFilterReserved
    		INTEGER,
    	    wfOsiTrafficFilterCircuit
    		INTEGER,
    	    wfOsiTrafficFilterRuleNumber
    		INTEGER,
    	    wfOsiTrafficFilterFragment
    		INTEGER,
    	    wfOsiTrafficFilterName
    		DisplayString
        }

    wfOsiTrafficFilterDelete OBJECT-TYPE
        SYNTAX	INTEGER {
    		    created(1),
    		    deleted(2)
    		}
        ACCESS	read-write
        STATUS	mandatory
        DESCRIPTION
                "Defines the existence of the traffic filter rule:
                created - traffic filter exists
                delete - traffic filter does not exist and can be deleted."
        DEFVAL	{ created }
        ::= { wfOsiTrafficFilterEntry 1 }

    wfOsiTrafficFilterDisable OBJECT-TYPE
        SYNTAX	INTEGER {
    		    enabled(1),
    		    disabled(2)
    		}
        ACCESS	read-write
        STATUS	mandatory
        DESCRIPTION
                "Defines whether or not the traffic filter rule should be used:
                enabled - activate the rule.
                disabled - inactivate the rule."
        DEFVAL	{ enabled }
        ::= { wfOsiTrafficFilterEntry 2 }

    wfOsiTrafficFilterStatus OBJECT-TYPE
        SYNTAX	INTEGER {
    		    active(1),
    		    error(2),
    		    inactive(3)
    		}
        ACCESS	read-only
        STATUS	mandatory
        DESCRIPTION
                "Defines the current status of the traffic filter:
                inactive - the rule is not in use.
                active - the rule is being used.
                error - the application detected an error in the rule."
        DEFVAL	{ inactive }
        ::= { wfOsiTrafficFilterEntry 3 }

    wfOsiTrafficFilterCounter OBJECT-TYPE
        SYNTAX	Counter
        ACCESS	read-only
        STATUS	mandatory
        DESCRIPTION
                "The number of received packets that have
                matched this rule."
        ::= { wfOsiTrafficFilterEntry 4 }

    wfOsiTrafficFilterDefinition OBJECT-TYPE
        SYNTAX	Opaque
        ACCESS	read-write
        STATUS	mandatory
        DESCRIPTION
                "The filter rule definition."
        ::= { wfOsiTrafficFilterEntry 5 }

    wfOsiTrafficFilterReserved OBJECT-TYPE
        SYNTAX	INTEGER
        ACCESS	read-only
        STATUS	mandatory
        DESCRIPTION
                "Reserved field."
        ::= { wfOsiTrafficFilterEntry 6 }

    wfOsiTrafficFilterCircuit OBJECT-TYPE
        SYNTAX	INTEGER
        ACCESS	read-only
        STATUS	mandatory
        DESCRIPTION
                "The ID of the Circuit to which the
                filter is applied."
        ::= { wfOsiTrafficFilterEntry 7 }

    wfOsiTrafficFilterRuleNumber OBJECT-TYPE
        SYNTAX	INTEGER
        ACCESS	read-only
        STATUS	mandatory
        DESCRIPTION
                "ID for the rule."
        ::= { wfOsiTrafficFilterEntry 8 }

    wfOsiTrafficFilterFragment OBJECT-TYPE
        SYNTAX	INTEGER
        ACCESS	read-only
        STATUS	mandatory
        DESCRIPTION
                "Fragment number - for large rules."
        ::= { wfOsiTrafficFilterEntry 9 }

    wfOsiTrafficFilterName OBJECT-TYPE
        SYNTAX	DisplayString
        ACCESS	read-write
        STATUS	mandatory
        DESCRIPTION
                "name of the rule number"
        ::= { wfOsiTrafficFilterEntry 10 }

    wfOsiL1LspHdrTable OBJECT-TYPE
        SYNTAX	SEQUENCE OF WfOsiL1LspHdrEntry
        ACCESS	not-accessible
        STATUS	mandatory
        DESCRIPTION
                "2 u_int32's so the inst_id len is 2."
        ::= { wfOsiGroup 7 }

    wfOsiL1LspHdrEntry OBJECT-TYPE
        SYNTAX	WfOsiL1LspHdrEntry
        ACCESS	not-accessible
        STATUS	mandatory
        DESCRIPTION
                "A Record in the Level 1 Lsp Header Table"
        INDEX	{ wfOsiL1LspHdrLspId }
        ::= { wfOsiL1LspHdrTable 1 }

    WfOsiL1LspHdrEntry ::= SEQUENCE {
    	    wfOsiL1LspHdrLspId
    		OCTET STRING,
    	    wfOsiL1LspHdrLifetime
    		INTEGER,
    	    wfOsiL1LspHdrSeqnum
    		INTEGER,
    	    wfOsiL1LspHdrFlags
    		OCTET STRING,
    	    wfOsiL1LspHdrCksum
    		OCTET STRING
        }

    wfOsiL1LspHdrLspId OBJECT-TYPE
        SYNTAX	OCTET STRING (SIZE (8))
        ACCESS	read-only
        STATUS	mandatory
        DESCRIPTION
                "LSPID = Source ID + Pseudo-node ID + LSP number"
        ::= { wfOsiL1LspHdrEntry 1 }

    wfOsiL1LspHdrLifetime OBJECT-TYPE
        SYNTAX	INTEGER
        ACCESS	read-only
        STATUS	mandatory
        DESCRIPTION
                "Lsp Lifetime"
        ::= { wfOsiL1LspHdrEntry 2 }

    wfOsiL1LspHdrSeqnum OBJECT-TYPE
        SYNTAX	INTEGER
        ACCESS	read-only
        STATUS	mandatory
        DESCRIPTION
                "Lsp sequence number"
        ::= { wfOsiL1LspHdrEntry 3 }

    wfOsiL1LspHdrFlags OBJECT-TYPE
        SYNTAX	OCTET STRING
        ACCESS	read-only
        STATUS	mandatory
        DESCRIPTION
                "Flags: P/ATT/LSPDBOL/IS type"
        ::= { wfOsiL1LspHdrEntry 4 }

    wfOsiL1LspHdrCksum OBJECT-TYPE
        SYNTAX	OCTET STRING
        ACCESS	read-only
        STATUS	mandatory
        DESCRIPTION
                "Checksum"
        ::= { wfOsiL1LspHdrEntry 5 }

    wfOsiL2LspHdrTable OBJECT-TYPE
        SYNTAX	SEQUENCE OF WfOsiL2LspHdrEntry
        ACCESS	not-accessible
        STATUS	mandatory
        DESCRIPTION
                "2 u_int32's so the inst_id len is 2."
        ::= { wfOsiGroup 8 }

    wfOsiL2LspHdrEntry OBJECT-TYPE
        SYNTAX	WfOsiL2LspHdrEntry
        ACCESS	not-accessible
        STATUS	mandatory
        DESCRIPTION
                "A Record in the Lsp Header Table"
        INDEX	{ wfOsiL2LspHdrLspId }
        ::= { wfOsiL2LspHdrTable 1 }

    WfOsiL2LspHdrEntry ::= SEQUENCE {
    	    wfOsiL2LspHdrLspId
    		OCTET STRING,
    	    wfOsiL2LspHdrLifetime
    		INTEGER,
    	    wfOsiL2LspHdrSeqnum
    		INTEGER,
    	    wfOsiL2LspHdrFlags
    		OCTET STRING,
    	    wfOsiL2LspHdrCksum
    		OCTET STRING
        }

    wfOsiL2LspHdrLspId OBJECT-TYPE
        SYNTAX	OCTET STRING (SIZE (8))
        ACCESS	read-only
        STATUS	mandatory
        DESCRIPTION
                "LSPID = Source ID + Pseudo-node ID + LSP number"
        ::= { wfOsiL2LspHdrEntry 1 }

    wfOsiL2LspHdrLifetime OBJECT-TYPE
        SYNTAX	INTEGER
        ACCESS	read-only
        STATUS	mandatory
        DESCRIPTION
                "Lsp Lifetime"
        ::= { wfOsiL2LspHdrEntry 2 }

    wfOsiL2LspHdrSeqnum OBJECT-TYPE
        SYNTAX	INTEGER
        ACCESS	read-only
        STATUS	mandatory
        DESCRIPTION
                "Lsp sequence number"
        ::= { wfOsiL2LspHdrEntry 3 }

    wfOsiL2LspHdrFlags OBJECT-TYPE
        SYNTAX	OCTET STRING
        ACCESS	read-only
        STATUS	mandatory
        DESCRIPTION
                "Flags: P/ATT/LSPDBOL/IS type"
        ::= { wfOsiL2LspHdrEntry 4 }

    wfOsiL2LspHdrCksum OBJECT-TYPE
        SYNTAX	OCTET STRING
        ACCESS	read-only
        STATUS	mandatory
        DESCRIPTION
                "Checksum"
        ::= { wfOsiL2LspHdrEntry 5 }

    wfOsiDynAdjTable OBJECT-TYPE
        SYNTAX	SEQUENCE OF WfOsiDynAdjEntry
        ACCESS	not-accessible
        STATUS	mandatory
        DESCRIPTION
                "Dynamic Adjacency Table"
        ::= { wfOsiGroup 9 }

    wfOsiDynAdjEntry OBJECT-TYPE
        SYNTAX	WfOsiDynAdjEntry
        ACCESS	not-accessible
        STATUS	mandatory
        DESCRIPTION
                "Adjacency Table - the real index is the adjacency id"
        INDEX	{ wfOsiDynAdjId }
        ::= { wfOsiDynAdjTable 1 }

    WfOsiDynAdjEntry ::= SEQUENCE {
    	    wfOsiDynAdjId
    		INTEGER,
    	    wfOsiDynAdjDatabase
    		INTEGER,
    	    wfOsiDynAdjType
    		INTEGER,
    	    wfOsiDynAdjState
    		INTEGER,
    	    wfOsiDynAdjCircuitId
    		INTEGER,
    	    wfOsiDynAdjHoldTime
    		INTEGER,
    	    wfOsiDynAdjPriority
    		INTEGER,
    	    wfOsiDynAdjSnpaAddr
    		OCTET STRING,
    	    wfOsiDynAdjNsapAddr
    		OCTET STRING,
    	    wfOsiDynAdjLanId
    		OCTET STRING
        }

    wfOsiDynAdjId OBJECT-TYPE
        SYNTAX	INTEGER
        ACCESS	read-only
        STATUS	mandatory
        DESCRIPTION
                "Index in the Adjacency Table"
        ::= { wfOsiDynAdjEntry 1 }

    wfOsiDynAdjDatabase OBJECT-TYPE
        SYNTAX	INTEGER
        ACCESS	read-only
        STATUS	mandatory
        DESCRIPTION
                "Database into which the Adjacency is stored,
                1=ES, 2=Level 1 IS, 3=Level 2 IS."
        ::= { wfOsiDynAdjEntry 2 }

    wfOsiDynAdjType OBJECT-TYPE
        SYNTAX	INTEGER
        ACCESS	read-only
        STATUS	mandatory
        DESCRIPTION
                "The type of adjacency. (see Osi_const.h)"
        ::= { wfOsiDynAdjEntry 3 }

    wfOsiDynAdjState OBJECT-TYPE
        SYNTAX	INTEGER
        ACCESS	read-only
        STATUS	mandatory
        DESCRIPTION
                "The state of the adjacency. INITIALIZING, UP or FAILED"
        ::= { wfOsiDynAdjEntry 4 }

    wfOsiDynAdjCircuitId OBJECT-TYPE
        SYNTAX	INTEGER
        ACCESS	read-only
        STATUS	mandatory
        DESCRIPTION
                "A unique value for each known circuit."
        ::= { wfOsiDynAdjEntry 5 }

    wfOsiDynAdjHoldTime OBJECT-TYPE
        SYNTAX	INTEGER
        ACCESS	read-only
        STATUS	mandatory
        DESCRIPTION
                "Hold Time received from neighbor."
        ::= { wfOsiDynAdjEntry 6 }

    wfOsiDynAdjPriority OBJECT-TYPE
        SYNTAX	INTEGER
        ACCESS	read-only
        STATUS	mandatory
        DESCRIPTION
                "Priority to become designated router. IS only."
        ::= { wfOsiDynAdjEntry 7 }

    wfOsiDynAdjSnpaAddr OBJECT-TYPE
        SYNTAX	OCTET STRING
        ACCESS	read-only
        STATUS	mandatory
        DESCRIPTION
                "SNAP address for neighbor."
        ::= { wfOsiDynAdjEntry 8 }

    wfOsiDynAdjNsapAddr OBJECT-TYPE
        SYNTAX	OCTET STRING
        ACCESS	read-only
        STATUS	mandatory
        DESCRIPTION
                "Neighbor address (NSAP)."
        ::= { wfOsiDynAdjEntry 9 }

    wfOsiDynAdjLanId OBJECT-TYPE
        SYNTAX	OCTET STRING
        ACCESS	read-only
        STATUS	mandatory
        DESCRIPTION
                "LAN ID from Designated Router. IS only."
        ::= { wfOsiDynAdjEntry 10 }

    wfOsiL1RoutesTable OBJECT-TYPE
        SYNTAX	SEQUENCE OF WfOsiL1RouteEntry
        ACCESS	not-accessible
        STATUS	mandatory
        DESCRIPTION
                "This is the L1 Routes Table for this router."
        ::= { wfOsiGroup 10 }

    wfOsiL1RouteEntry OBJECT-TYPE
        SYNTAX	WfOsiL1RouteEntry
        ACCESS	not-accessible
        STATUS	mandatory
        DESCRIPTION
                "This is the L1 Route entry for the Routes Table."
        INDEX	{ wfOsiL1RouteType,
    		  wfOsiL1RoutePathSplit,
    		  wfOsiL1RouteId }
        ::= { wfOsiL1RoutesTable 1 }

    WfOsiL1RouteEntry ::= SEQUENCE {
    	    wfOsiL1RouteId
    		OCTET STRING,
    	    wfOsiL1RoutePathSplit
    		INTEGER,
    	    wfOsiL1RouteType
    		INTEGER,
    	    wfOsiL1RouteNextHopSnpa
    		OCTET STRING,
    	    wfOsiL1RouteNextHopId
    		OCTET STRING,
    	    wfOsiL1RouteNextHopType
    		INTEGER,
    	    wfOsiL1RouteNextHopCircuit
    		INTEGER,
    	    wfOsiL1RouteDefaultMetricCost
    		INTEGER
        }

    wfOsiL1RouteId OBJECT-TYPE
        SYNTAX	OCTET STRING (SIZE (6))
        ACCESS	read-only
        STATUS	mandatory
        DESCRIPTION
                "This is the SysID of the L1 Destination."
        ::= { wfOsiL1RouteEntry 1 }

    wfOsiL1RoutePathSplit OBJECT-TYPE
        SYNTAX	INTEGER
        ACCESS	read-only
        STATUS	mandatory
        DESCRIPTION
                "This assigns a number to each equal cost path to the
                destination.  There can be up to 2 equal cost paths
                to a destination."
        ::= { wfOsiL1RouteEntry 2 }

    wfOsiL1RouteType OBJECT-TYPE
        SYNTAX	INTEGER
        ACCESS	read-only
        STATUS	mandatory
        DESCRIPTION
                "This tells what kind of a route this entry is."
        ::= { wfOsiL1RouteEntry 3 }

    wfOsiL1RouteNextHopSnpa OBJECT-TYPE
        SYNTAX	OCTET STRING
        ACCESS	read-only
        STATUS	mandatory
        DESCRIPTION
                "This is the SNPA of the next hop adj for this route."
        ::= { wfOsiL1RouteEntry 4 }

    wfOsiL1RouteNextHopId OBJECT-TYPE
        SYNTAX	OCTET STRING
        ACCESS	read-only
        STATUS	mandatory
        DESCRIPTION
                "This is the ID of the next hop adjacency to this route.
                If its just an ES then it is the 6byte System ID.
                If the next HOP is an IS then it is the NET. "
        ::= { wfOsiL1RouteEntry 5 }

    wfOsiL1RouteNextHopType OBJECT-TYPE
        SYNTAX	INTEGER
        ACCESS	read-only
        STATUS	mandatory
        DESCRIPTION
                "This is the adj type of the next hop for this route."
        ::= { wfOsiL1RouteEntry 6 }

    wfOsiL1RouteNextHopCircuit OBJECT-TYPE
        SYNTAX	INTEGER
        ACCESS	read-only
        STATUS	mandatory
        DESCRIPTION
                "This is the circuit to forward out for this route."
        ::= { wfOsiL1RouteEntry 7 }

    wfOsiL1RouteDefaultMetricCost OBJECT-TYPE
        SYNTAX	INTEGER
        ACCESS	read-only
        STATUS	mandatory
        DESCRIPTION
                "This is the cost to from this system to this destination."
        ::= { wfOsiL1RouteEntry 8 }

    wfOsiL2RoutesTable OBJECT-TYPE
        SYNTAX	SEQUENCE OF WfOsiL2RouteEntry
        ACCESS	not-accessible
        STATUS	mandatory
        DESCRIPTION
                "This is the L2 Routes Table for this router."
        ::= { wfOsiGroup 11 }

    wfOsiL2RouteEntry OBJECT-TYPE
        SYNTAX	WfOsiL2RouteEntry
        ACCESS	not-accessible
        STATUS	mandatory
        DESCRIPTION
                "This is the L2 Route entry for the Routes Table."
        INDEX	{ wfOsiL2RouteType,
    		  wfOsiL2RoutePathSplit,
    		  wfOsiL2RouteId }
        ::= { wfOsiL2RoutesTable 1 }

    WfOsiL2RouteEntry ::= SEQUENCE {
    	    wfOsiL2RouteId
    		OCTET STRING,
    	    wfOsiL2RoutePathSplit
    		INTEGER,
    	    wfOsiL2RouteType
    		INTEGER,
    	    wfOsiL2RouteNextHopSnpa
    		OCTET STRING,
    	    wfOsiL2RouteNextHopId
    		OCTET STRING,
    	    wfOsiL2RouteNextHopType
    		INTEGER,
    	    wfOsiL2RouteNextHopCircuit
    		INTEGER,
    	    wfOsiL2RouteDefaultMetricCost
    		INTEGER
        }

    wfOsiL2RouteId OBJECT-TYPE
        SYNTAX	OCTET STRING (SIZE (13))
        ACCESS	read-only
        STATUS	mandatory
        DESCRIPTION
                "This is the SysID of the L2 Destination."
        ::= { wfOsiL2RouteEntry 1 }

    wfOsiL2RoutePathSplit OBJECT-TYPE
        SYNTAX	INTEGER
        ACCESS	read-only
        STATUS	mandatory
        DESCRIPTION
                "This assigns a number to each equal cost path to the
                destination.  There can be up to 2 equal cost paths
                to a destination."
        ::= { wfOsiL2RouteEntry 2 }

    wfOsiL2RouteType OBJECT-TYPE
        SYNTAX	INTEGER
        ACCESS	read-only
        STATUS	mandatory
        DESCRIPTION
                "This tells what kind of a route this entry is."
        ::= { wfOsiL2RouteEntry 3 }

    wfOsiL2RouteNextHopSnpa OBJECT-TYPE
        SYNTAX	OCTET STRING
        ACCESS	read-only
        STATUS	mandatory
        DESCRIPTION
                "This is the SNPA of the neighbor on this circuit."
        ::= { wfOsiL2RouteEntry 4 }

    wfOsiL2RouteNextHopId OBJECT-TYPE
        SYNTAX	OCTET STRING
        ACCESS	read-only
        STATUS	mandatory
        DESCRIPTION
                "This is the ID of the next hop adjacency to this route.
                If its just an ES then it is the 6byte System ID.
                If the next HOP is an IS then it is the NET. "
        ::= { wfOsiL2RouteEntry 5 }

    wfOsiL2RouteNextHopType OBJECT-TYPE
        SYNTAX	INTEGER
        ACCESS	read-only
        STATUS	mandatory
        DESCRIPTION
                "This is the adj type of the next hop for this route."
        ::= { wfOsiL2RouteEntry 6 }

    wfOsiL2RouteNextHopCircuit OBJECT-TYPE
        SYNTAX	INTEGER
        ACCESS	read-only
        STATUS	mandatory
        DESCRIPTION
                "This is the circuit to go out for this adj."
        ::= { wfOsiL2RouteEntry 7 }

    wfOsiL2RouteDefaultMetricCost OBJECT-TYPE
        SYNTAX	INTEGER
        ACCESS	read-only
        STATUS	mandatory
        DESCRIPTION
                "This is the cost to from this system to this destination."
        ::= { wfOsiL2RouteEntry 8 }

    wfOsiDecnetTrans	OBJECT IDENTIFIER ::= { wfOsiGroup 12 }

    wfOsiDecnetTransDelete OBJECT-TYPE
        SYNTAX	INTEGER {
    		    created(1),
    		    deleted(2)
    		}
        ACCESS	read-write
        STATUS	mandatory
        DESCRIPTION
                "This value determines whether DECnet Phase 4 to Phase 5
                Transition functions are configured."
        DEFVAL	{ created }
        ::= { wfOsiDecnetTrans 1 }

    wfOsiDecnetTransDisable OBJECT-TYPE
        SYNTAX	INTEGER {
    		    enabled(1),
    		    disabled(2)
    		}
        ACCESS	read-write
        STATUS	mandatory
        DESCRIPTION
                "This value determines whether DECnet Phase 4 to Phase 5
                Transition functions are enabled."
        DEFVAL	{ enabled }
        ::= { wfOsiDecnetTrans 2 }

    wfOsiDecnetTransState OBJECT-TYPE
        SYNTAX	INTEGER {
    		    up(1),
    		    down(2),
    		    init(3),
    		    notpresent(4)
    		}
        ACCESS	read-only
        STATUS	mandatory
        DESCRIPTION
                "This value displays the state of the DECnet Phase 4 to Phase 5
                Transition function."
        DEFVAL	{ notpresent }
        ::= { wfOsiDecnetTrans 3 }

    wfOsiDecnetTransPhase4Pkts OBJECT-TYPE
        SYNTAX	Counter
        ACCESS	read-only
        STATUS	mandatory
        DESCRIPTION
                "Number of successfully translated Phase 4 packets"
        ::= { wfOsiDecnetTrans 4 }

    wfOsiDecnetTransSegFail OBJECT-TYPE
        SYNTAX	Counter
        ACCESS	read-only
        STATUS	mandatory
        DESCRIPTION
                "Number of times Phase 5 translation failed because the packet
                was segmented."
        ::= { wfOsiDecnetTrans 5 }

    wfOsiDecnetTransNselFail OBJECT-TYPE
        SYNTAX	Counter
        ACCESS	read-only
        STATUS	mandatory
        DESCRIPTION
                "Number of times Phase 5 translation failed because the NSELs
                were not the same."
        ::= { wfOsiDecnetTrans 6 }

    wfOsiDecnetTransUnrFail OBJECT-TYPE
        SYNTAX	Counter
        ACCESS	read-only
        STATUS	mandatory
        DESCRIPTION
                "Number of times Phase 5 failed to find a route to the
                destination."
        ::= { wfOsiDecnetTrans 7 }

    wfOsiDecnetTransNumPhase4Es OBJECT-TYPE
        SYNTAX	Counter
        ACCESS	read-only
        STATUS	mandatory
        DESCRIPTION
                "Number of Phase 4 ES Adjacencies announced by the Phase 4
                (DECnet IV) router."
        ::= { wfOsiDecnetTrans 8 }

    wfOsiAreaAddressTable OBJECT-TYPE
        SYNTAX	SEQUENCE OF WfOsiAreaAddressEntry
        ACCESS	not-accessible
        STATUS	mandatory
        DESCRIPTION
                "This is the table of Area Addresses for this Router."
        ::= { wfOsiGroup 13 }

    wfOsiAreaAddressEntry OBJECT-TYPE
        SYNTAX	WfOsiAreaAddressEntry
        ACCESS	not-accessible
        STATUS	mandatory
        DESCRIPTION
                "This is the Area Address Record for this Router."
        INDEX	{ wfOsiAreaAddress }
        ::= { wfOsiAreaAddressTable 1 }

    WfOsiAreaAddressEntry ::= SEQUENCE {
    	    wfOsiAreaAddrDelete
    		INTEGER,
    	    wfOsiAreaAddrDisable
    		INTEGER,
    	    wfOsiAreaAddress
    		OCTET STRING
        }

    wfOsiAreaAddrDelete OBJECT-TYPE
        SYNTAX	INTEGER {
    		    created(1),
    		    deleted(2)
    		}
        ACCESS	read-write
        STATUS	mandatory
        DESCRIPTION
                "This is the Create/Delete parameter for this AreaAddr entry."
        DEFVAL	{ created }
        ::= { wfOsiAreaAddressEntry 1 }

    wfOsiAreaAddrDisable OBJECT-TYPE
        SYNTAX	INTEGER {
    		    enabled(1),
    		    disabled(2)
    		}
        ACCESS	read-write
        STATUS	mandatory
        DESCRIPTION
                "Enable/Disable parameter for this AreaAddr."
        DEFVAL	{ enabled }
        ::= { wfOsiAreaAddressEntry 2 }

    wfOsiAreaAddress OBJECT-TYPE
        SYNTAX	OCTET STRING (SIZE (3..13))
        ACCESS	read-only
        STATUS	mandatory
        DESCRIPTION
                "This is the prefix area address. It is also the inst_id."
        ::= { wfOsiAreaAddressEntry 3 }


    wfOsiTarpEntry   OBJECT IDENTIFIER ::= { wfOsiGroup 14 }

    wfOsiTarpCreate OBJECT-TYPE
        SYNTAX  INTEGER {
                    created(1),
                    deleted(2)
                }
        ACCESS  read-write
        STATUS  mandatory
        DESCRIPTION
                "This value determines whether OSI Tarp is configured on this slot."
        DEFVAL  { created }
        ::= { wfOsiTarpEntry 1 }

    wfOsiTarpEnable OBJECT-TYPE
        SYNTAX  INTEGER {
                    enabled(1),
                    disabled(2)
                }
        ACCESS  read-write
        STATUS  mandatory
        DESCRIPTION
                "This value dtermines if OSI Tarp is to startup."
        DEFVAL  { enabled }
        ::= { wfOsiTarpEntry 2 }

    wfOsiTarpState OBJECT-TYPE
        SYNTAX  INTEGER {
                    up(1),
                    down(2),
                    init(3),
                    notpresent(4)
                }
        ACCESS  read-only
        STATUS  mandatory
        DESCRIPTION
                "This value describes the state of OSI Tarp."
        DEFVAL  { notpresent }
        ::= { wfOsiTarpEntry 3 }

    wfOsiTarpTID OBJECT-TYPE
        SYNTAX  DisplayString
        ACCESS  read-write
        STATUS  mandatory
        DESCRIPTION
                "This value contains the Target Identifier
                 assigned to the router (Network Entity)."
        ::= { wfOsiTarpEntry 4 }

    wfOsiTarpOriginate OBJECT-TYPE
        SYNTAX INTEGER {
                   enabled(1),
                   disabled(2)
               }
        ACCESS  read-write
        STATUS  mandatory
        DESCRIPTION
                "This value determines if TARP is allowed
                 to originate any tarp requests."
        DEFVAL  { enabled }
        ::= { wfOsiTarpEntry 5 }

    wfOsiTarpLifetime OBJECT-TYPE
        SYNTAX  INTEGER(1..65535)
        ACCESS  read-write
        STATUS  mandatory
        DESCRIPTION
                "This value determines what the lifetime of
                 of TARP packets originated by this router
                 will be."
        DEFVAL  { 25 }
        ::= { wfOsiTarpEntry 6 }

    wfOsiTarpStartSeq OBJECT-TYPE
        SYNTAX  INTEGER(1..65535)
        ACCESS  read-write
        STATUS  mandatory
        DESCRIPTION
                "This value determines what the starting
                 sequence number of TARP packets originated
                 by this router will be."
        DEFVAL  { 1 }
        ::= { wfOsiTarpEntry 7 }

    wfOsiTarpNextSeq OBJECT-TYPE
        SYNTAX  INTEGER(0..65535)
        ACCESS  read-only
        STATUS  mandatory
        DESCRIPTION
                "This value determines what the next sequence
                 number of TARP packets originated by this
                 router will be."
        ::= { wfOsiTarpEntry 8 }

    wfOsiTarpTarPro OBJECT-TYPE
        SYNTAX  INTEGER (1..255)
        ACCESS  read-write
        STATUS  mandatory
        DESCRIPTION
                "This value describes what the Protocol Address
                 Type field within the TARP packet must be.
                 A value of 'FE' describes a CLNP address type."
        ::= { wfOsiTarpEntry 9 }

    wfOsiTarpTDC OBJECT-TYPE
        SYNTAX  INTEGER {
                    enabled(1),
                    disabled(2)
                }
        ACCESS  read-write
        STATUS  mandatory
        DESCRIPTION
                "This value determines whether or not TARP
                 uses and maintains a Tarp Data Cache."
        DEFVAL  { enabled }
        ::= { wfOsiTarpEntry 10 }

    wfOsiTarpL2TDC OBJECT-TYPE
        SYNTAX  INTEGER {
                    enabled(1),
                    disabled(2)
                }
        ACCESS  read-write
        STATUS  mandatory
        DESCRIPTION
                "This value determines whether or not TARP
                 uses and maintains a Level 2 Tarp Data Cache."
        DEFVAL  { enabled }
        ::= { wfOsiTarpEntry 11 }

    wfOsiTarpT1 OBJECT-TYPE
        SYNTAX  INTEGER(1..3600)
        ACCESS  read-write
        STATUS  mandatory
        DESCRIPTION
                "This value configures the Tarp T1 Timer - how
                 many seconds to wait for a response to a Type1
                 Request PDU."
        DEFVAL  { 15 }
        ::= { wfOsiTarpEntry 12 }

    wfOsiTarpT2 OBJECT-TYPE
        SYNTAX  INTEGER(1..3600)
        ACCESS  read-write
        STATUS  mandatory
        DESCRIPTION
                "This value configures the Tarp T2 Timer - how
                 many seconds to wait for a response to a Type2
                 Request PDU."
        DEFVAL  { 25 }
        ::= { wfOsiTarpEntry 13 }

    wfOsiTarpT3 OBJECT-TYPE
        SYNTAX  INTEGER(1..3600)
        ACCESS  read-write
        STATUS  mandatory
        DESCRIPTION
                "This value configures the Tarp T3 Timer - how
                 many seconds to wait for a response to a Type5
                 Request PDU."
        DEFVAL  { 40 }
        ::= { wfOsiTarpEntry 14 }

    wfOsiTarpT4 OBJECT-TYPE
        SYNTAX  INTEGER(1..3600)
        ACCESS  read-write
        STATUS  mandatory
        DESCRIPTION
                "This value configures the Tarp T4 Timer, which
                 is used during the Error Recovery process after
                 T2 expires."
        DEFVAL  { 20 }
        ::= { wfOsiTarpEntry 15 }

    wfOsiTarpLDBTimer OBJECT-TYPE
        SYNTAX  INTEGER(1..600)
        ACCESS  read-write
        STATUS  mandatory
        DESCRIPTION
                "This value configures the Loop Detection Buffer's
                 Entry Timer."
        DEFVAL  { 300 }
        ::= { wfOsiTarpEntry 16 }

    wfOsiTarpLDBFlush OBJECT-TYPE
        SYNTAX  INTEGER(1..86400)
        ACCESS  read-write
        STATUS  mandatory
        DESCRIPTION
                "This value configures the timer that signals the
                 flushing of the Loop Detection Buffer."
        DEFVAL  { 300 }
        ::= { wfOsiTarpEntry 17 }

    wfOsiTarpLDBSize OBJECT-TYPE
        SYNTAX  INTEGER(1..5000)
        ACCESS  read-write
        STATUS  mandatory
        DESCRIPTION
                "This value specifies the maximum number of entries
                 the the Loop Detection Buffer can hold."
        DEFVAL  { 50 }
        ::= { wfOsiTarpEntry 18 }

    wfOsiTarpType1Rcv OBJECT-TYPE
        SYNTAX  Counter
        ACCESS  read-only
        STATUS  mandatory
        DESCRIPTION
                "This value counts the number of Type 1 Tarp packets
                 received by this interface."
        ::= { wfOsiTarpEntry 19 }

    wfOsiTarpType1Xmt OBJECT-TYPE
        SYNTAX  Counter
        ACCESS  read-only
        STATUS  mandatory
        DESCRIPTION
                "This value counts the number of Type 1 Tarp packets
                 transmitted by this interface."
        ::= { wfOsiTarpEntry 20 }

    wfOsiTarpType2Rcv OBJECT-TYPE
        SYNTAX  Counter
        ACCESS  read-only
        STATUS  mandatory
        DESCRIPTION
                "This value counts the number of Type 2 Tarp packets
                 received by this interface."
        ::= { wfOsiTarpEntry 21 }

    wfOsiTarpType2Xmt OBJECT-TYPE
        SYNTAX  Counter
        ACCESS  read-only
        STATUS  mandatory
        DESCRIPTION
                "This value counts the number of Type 2 Tarp packets
                 transmitted by this interface."
        ::= { wfOsiTarpEntry 22 }

    wfOsiTarpType3Rcv OBJECT-TYPE
        SYNTAX  Counter
        ACCESS  read-only
        STATUS  mandatory
        DESCRIPTION
                "This value counts the number of Type 3 Tarp packets
                 received by this interface."
        ::= { wfOsiTarpEntry 23 }

    wfOsiTarpType3Xmt OBJECT-TYPE
        SYNTAX  Counter
        ACCESS  read-only
        STATUS  mandatory
        DESCRIPTION
                "This value counts the number of Type 3 Tarp packets
                 transmitted by this interface."
        ::= { wfOsiTarpEntry 24 }

    wfOsiTarpType4Rcv OBJECT-TYPE
        SYNTAX  Counter
        ACCESS  read-only
        STATUS  mandatory
        DESCRIPTION
                "This value counts the number of Type 4 Tarp packets
                 received by this interface."
        ::= { wfOsiTarpEntry 25 }

    wfOsiTarpType4Xmt OBJECT-TYPE
        SYNTAX  Counter
        ACCESS  read-only
        STATUS  mandatory
        DESCRIPTION
                "This value counts the number of Type 4 Tarp packets
                 transmitted by this interface."
        ::= { wfOsiTarpEntry 26 }

    wfOsiTarpType5Rcv OBJECT-TYPE
        SYNTAX  Counter
        ACCESS  read-only
        STATUS  mandatory
        DESCRIPTION
                "This value counts the number of Type 5 Tarp packets
                 received by this interface."
        ::= { wfOsiTarpEntry 27 }

    wfOsiTarpType5Xmt OBJECT-TYPE
        SYNTAX  Counter
        ACCESS  read-only
        STATUS  mandatory
        DESCRIPTION
                "This value counts the number of Type 5 Tarp packets
                 transmitted by this interface."
        ::= { wfOsiTarpEntry 28 }


    wfOsiTarpCircuitTable  OBJECT-TYPE
        SYNTAX  SEQUENCE OF WfOsiTarpCircuitEntry
        ACCESS  not-accessible
        STATUS  mandatory
        DESCRIPTION
                "This table contains all of the Tarp interfaces for
                 this system."
        ::= { wfOsiGroup 15 }

    wfOsiTarpCircuitEntry OBJECT-TYPE
        SYNTAX  WfOsiTarpCircuitEntry
        ACCESS  not-accessible
        STATUS  mandatory
        DESCRIPTION
                "This is the Tarp Interface Entry for the Tarp Interface
                 Table."
        INDEX   { wfOsiTarpCircuitCct }
        ::= { wfOsiTarpCircuitTable 1 }

    WfOsiTarpCircuitEntry ::= SEQUENCE {
        wfOsiTarpCircuitCreate
            INTEGER,
        wfOsiTarpCircuitEnable
            INTEGER,
        wfOsiTarpCircuitState
            INTEGER,
        wfOsiTarpCircuitCct
            INTEGER,
        wfOsiTarpCircuitPropagate
            INTEGER,
        wfOsiTarpCircuitOriginate
            INTEGER,
        wfOsiTarpCircuitType1Rcv
            Counter,
        wfOsiTarpCircuitType1Xmt
            Counter,
        wfOsiTarpCircuitType2Rcv
            Counter,
        wfOsiTarpCircuitType2Xmt
            Counter,
        wfOsiTarpCircuitType3Rcv
            Counter,
        wfOsiTarpCircuitType3Xmt
            Counter,
        wfOsiTarpCircuitType4Rcv
            Counter,
        wfOsiTarpCircuitType4Xmt
            Counter,
        wfOsiTarpCircuitType5Rcv
            Counter,
        wfOsiTarpCircuitType5Xmt
            Counter,
        wfOsiTarpCircuitNoBufs
            Counter
    }

    wfOsiTarpCircuitCreate OBJECT-TYPE
        SYNTAX  INTEGER {
                    created(1),
                    deleted(2)
                }
        ACCESS  read-write
        STATUS  mandatory
        DESCRIPTION
                "This value determines if the Tarp Interface is to be created
                 for this OSI interface."
        DEFVAL  { created }
        ::= { wfOsiTarpCircuitEntry 1 }

    wfOsiTarpCircuitEnable OBJECT-TYPE
        SYNTAX  INTEGER {
                    enabled(1),
                    disabled(2)
                }
        ACCESS  read-write
        STATUS  mandatory
        DESCRIPTION
                "This value determines if the Tarp Interface is to be
                 enabled for this OSI interface."
        DEFVAL  { enabled }
        ::= { wfOsiTarpCircuitEntry 2 }

    wfOsiTarpCircuitState OBJECT-TYPE
        SYNTAX  INTEGER {
                    up(1),
                    down(2),
                    init(3),
                    notpresent(4)
                }
        ACCESS  read-only
        STATUS  mandatory
        DESCRIPTION
                "This value reflects the state of the Tarp interface."
        DEFVAL { notpresent }
        ::= { wfOsiTarpCircuitEntry 3 }

    wfOsiTarpCircuitCct  OBJECT-TYPE
        SYNTAX  INTEGER
        ACCESS  read-only
        STATUS  mandatory
        DESCRIPTION
                "Circuit number for this Tarp Interface."
        ::= { wfOsiTarpCircuitEntry 4 }

    wfOsiTarpCircuitPropagate OBJECT-TYPE
        SYNTAX  INTEGER {
                    enabled(1),
                    disabled(2)
                }
        ACCESS  read-write
        STATUS  mandatory
        DESCRIPTION
                "This value determines if this interface will propagate
                 transit Tarp packets out this interface."
        DEFVAL  { enabled }
        ::= { wfOsiTarpCircuitEntry 5 }

    wfOsiTarpCircuitOriginate OBJECT-TYPE
        SYNTAX  INTEGER {
                    enabled(1),
                    disabled(2)
                }
        ACCESS  read-write
        STATUS  mandatory
        DESCRIPTION
                "This value determines if this interface will send out
                 Tarp packets originated by the router."
        DEFVAL  { enabled }
        ::= { wfOsiTarpCircuitEntry 6 }

    wfOsiTarpCircuitType1Rcv OBJECT-TYPE
        SYNTAX  Counter
        ACCESS  read-only
        STATUS  mandatory
        DESCRIPTION
                "This value counts the number of Type 1 Tarp packets
                 received by this interface."
        ::= { wfOsiTarpCircuitEntry 7 }

    wfOsiTarpCircuitType1Xmt OBJECT-TYPE
        SYNTAX  Counter
        ACCESS  read-only
        STATUS  mandatory
        DESCRIPTION
                "This value counts the number of Type 1 Tarp packets
                 transmitted by this interface."
        ::= { wfOsiTarpCircuitEntry 8 }

    wfOsiTarpCircuitType2Rcv OBJECT-TYPE
        SYNTAX  Counter
        ACCESS  read-only
        STATUS  mandatory
        DESCRIPTION
                "This value counts the number of Type 2 Tarp packets
                 received by this interface."
        ::= { wfOsiTarpCircuitEntry 9 }

    wfOsiTarpCircuitType2Xmt OBJECT-TYPE
        SYNTAX  Counter
        ACCESS  read-only
        STATUS  mandatory
        DESCRIPTION
                "This value counts the number of Type 2 Tarp packets
                 transmitted by this interface."
        ::= { wfOsiTarpCircuitEntry 10 }

    wfOsiTarpCircuitType3Rcv OBJECT-TYPE
        SYNTAX  Counter
        ACCESS  read-only
        STATUS  mandatory
        DESCRIPTION
                "This value counts the number of Type 3 Tarp packets
                 received by this interface."
        ::= { wfOsiTarpCircuitEntry 11 }

    wfOsiTarpCircuitType3Xmt OBJECT-TYPE
        SYNTAX  Counter
        ACCESS  read-only
        STATUS  mandatory
        DESCRIPTION
                "This value counts the number of Type 3 Tarp packets
                 transmitted by this interface."
        ::= { wfOsiTarpCircuitEntry 12 }

    wfOsiTarpCircuitType4Rcv OBJECT-TYPE
        SYNTAX  Counter
        ACCESS  read-only
        STATUS  mandatory
        DESCRIPTION
                "This value counts the number of Type 4 Tarp packets
                 received by this interface."
        ::= { wfOsiTarpCircuitEntry 13 }

    wfOsiTarpCircuitType4Xmt OBJECT-TYPE
        SYNTAX  Counter
        ACCESS  read-only
        STATUS  mandatory
        DESCRIPTION
                "This value counts the number of Type 4 Tarp packets
                 transmitted by this interface."
        ::= { wfOsiTarpCircuitEntry 14 }

    wfOsiTarpCircuitType5Rcv OBJECT-TYPE
        SYNTAX  Counter
        ACCESS  read-only
        STATUS  mandatory
        DESCRIPTION
                "This value counts the number of Type 5 Tarp packets
                 received by this interface."
        ::= { wfOsiTarpCircuitEntry 15 }

    wfOsiTarpCircuitType5Xmt OBJECT-TYPE
        SYNTAX  Counter
        ACCESS  read-only
        STATUS  mandatory
        DESCRIPTION
                "This value counts the number of Type 5 Tarp packets
                 transmitted by this interface."
        ::= { wfOsiTarpCircuitEntry 16 }

    wfOsiTarpCircuitNoBufs OBJECT-TYPE
        SYNTAX  Counter
        ACCESS  read-only
        STATUS  mandatory
        DESCRIPTION
                "This value represents the number of times Tarp tried
                 to allocate a buffer but was unable."
        ::= { wfOsiTarpCircuitEntry 17 }


    wfOsiTarpLDBTable  OBJECT-TYPE
        SYNTAX  SEQUENCE OF WfOsiTarpLDBEntry
        ACCESS  not-accessible
        STATUS  mandatory
        DESCRIPTION
                "Table of wfOsiTarpLDBEntry's."
        ::= { wfOsiGroup 16 }

    wfOsiTarpLDBEntry  OBJECT-TYPE
        SYNTAX  WfOsiTarpLDBEntry
        ACCESS  not-accessible
        STATUS  mandatory
        DESCRIPTION
                "Each entry in the Loop Detection Buffer."
        INDEX   { wfOsiTarpLDBNSAP }
        ::= { wfOsiTarpLDBTable 1 }

    WfOsiTarpLDBEntry ::= SEQUENCE {
        wfOsiTarpLDBCreate
            INTEGER,
        wfOsiTarpLDBNSAP
            OCTET STRING,
        wfOsiTarpLDBSequence
            INTEGER,
        wfOsiTarpLDBCurrentTimer
            INTEGER
    }

        wfOsiTarpLDBCreate OBJECT-TYPE
        SYNTAX  INTEGER {
                    created(1),
                    deleted(2)
                }
        ACCESS  read-write
        STATUS  mandatory
        DESCRIPTION
                "Specifies the creation or deletion of the instance."
        ::= { wfOsiTarpLDBEntry 1 }

        wfOsiTarpLDBNSAP OBJECT-TYPE
        SYNTAX  OCTET STRING
        ACCESS  read-only
        STATUS  mandatory
        DESCRIPTION
                "The NSAP address for this entry."
        ::= { wfOsiTarpLDBEntry 2 }

    wfOsiTarpLDBSequence OBJECT-TYPE
        SYNTAX  INTEGER(0..65535)
        ACCESS  read-only
        STATUS  mandatory
        DESCRIPTION
                "The sequence number for this LDB entry."
        ::= { wfOsiTarpLDBEntry 3 }

    wfOsiTarpLDBCurrentTimer OBJECT-TYPE
        SYNTAX  INTEGER(1..600)
        ACCESS  read-write
        STATUS  mandatory
        DESCRIPTION
                "Current timer for this LDB Entry."
        DEFVAL  { 300 }
        ::= { wfOsiTarpLDBEntry 4 }


    wfOsiTarpStaticAdjTable  OBJECT-TYPE
        SYNTAX  SEQUENCE OF WfOsiTarpStaticAdjEntry
        ACCESS  not-accessible
        STATUS  mandatory
        DESCRIPTION
                "Table of wfOsiTarpStaticAdjEntry's."
        ::= { wfOsiGroup 17 }

    wfOsiTarpStaticAdjEntry OBJECT-TYPE
        SYNTAX  WfOsiTarpStaticAdjEntry
        ACCESS  not-accessible
        STATUS  mandatory
        DESCRIPTION
                "This is the static adjacency record that appears
                 in the adjacency table."
        INDEX   { wfOsiTarpStaticAdjNSAP }
        ::= { wfOsiTarpStaticAdjTable 1 }

    WfOsiTarpStaticAdjEntry ::= SEQUENCE {
        wfOsiTarpStaticAdjCreate
            INTEGER,
        wfOsiTarpStaticAdjEnable
            INTEGER,
        wfOsiTarpStaticAdjNSAP
            OCTET STRING,
        wfOsiTarpStaticNibbleLength
            INTEGER
    }

    wfOsiTarpStaticAdjCreate OBJECT-TYPE
        SYNTAX  INTEGER {
                    created(1),
                    deleted(2)
                }
        ACCESS  read-write
        STATUS  mandatory
        DESCRIPTION
                "This value determines if this instance should be
                 created or deleted."
        DEFVAL  { created }
        ::= { wfOsiTarpStaticAdjEntry 1 }

    wfOsiTarpStaticAdjEnable OBJECT-TYPE
        SYNTAX  INTEGER {
                    enabled(1),
                    disabled(2)
                }
        ACCESS  read-write
        STATUS  mandatory
        DESCRIPTION
                "This value determines if the Static Adjacency should
                 be enabled."
        DEFVAL  { enabled }
        ::= { wfOsiTarpStaticAdjEntry 2 }

    wfOsiTarpStaticAdjNSAP OBJECT-TYPE
        SYNTAX  OCTET STRING (SIZE (20))
        ACCESS  read-only
        STATUS  mandatory
        DESCRIPTION
                "This specifies the address of the Static Adjacency. It
                 is also the instance ID."
        ::= { wfOsiTarpStaticAdjEntry 3 }

    wfOsiTarpStaticNibbleLength OBJECT-TYPE
        SYNTAX  INTEGER
        ACCESS  read-write
        STATUS  mandatory
        DESCRIPTION
                "Describes the number of nibbles in the Static NSAP
                 Address."
        ::= { wfOsiTarpStaticAdjEntry 4 }


    wfOsiTarpIgnoreAdjTable  OBJECT-TYPE
        SYNTAX  SEQUENCE OF WfOsiTarpIgnoreAdjEntry
        ACCESS  not-accessible
        STATUS  mandatory
        DESCRIPTION
                "This table contains all the adjacency entries that
                 should be ignored."
        ::= { wfOsiGroup 18 }

    wfOsiTarpIgnoreAdjEntry OBJECT-TYPE
        SYNTAX  WfOsiTarpIgnoreAdjEntry
        ACCESS  not-accessible
        STATUS  mandatory
        DESCRIPTION
                "This is the ignore static route entry for the
                 wfOsiTarpIgnoreAdj table."
        INDEX   { wfOsiTarpIgnoreAdjNSAP }
        ::= { wfOsiTarpIgnoreAdjTable 1 }

    WfOsiTarpIgnoreAdjEntry ::= SEQUENCE {
        wfOsiTarpIgnoreAdjCreate
            INTEGER,
        wfOsiTarpIgnoreAdjEnable
            INTEGER,
        wfOsiTarpIgnoreAdjNSAP
            OCTET STRING,
        wfOsiTarpIgnoreNibbleLength
            INTEGER
    }

    wfOsiTarpIgnoreAdjCreate OBJECT-TYPE
        SYNTAX  INTEGER {
                    created(1),
                    deleted(2)
                }
        ACCESS  read-write
        STATUS  mandatory
        DESCRIPTION
                "Signifies this instance should be created."
        DEFVAL  { created }
        ::= { wfOsiTarpIgnoreAdjEntry 1 }

    wfOsiTarpIgnoreAdjEnable OBJECT-TYPE
        SYNTAX  INTEGER {
                    enabled(1),
                    disabled(2)
                }
        ACCESS  read-write
        STATUS  mandatory
        DESCRIPTION
                "This value determines if this instance should be enabled
                 or disabled."
        DEFVAL  { enabled }
        ::= { wfOsiTarpIgnoreAdjEntry 2 }

    wfOsiTarpIgnoreAdjNSAP OBJECT-TYPE
        SYNTAX  OCTET STRING (SIZE (20))
        ACCESS  read-only
        STATUS  mandatory
        DESCRIPTION
                "Identifies the OSI Adjacency that should be ignored."
        ::= { wfOsiTarpIgnoreAdjEntry 3 }

    wfOsiTarpIgnoreNibbleLength OBJECT-TYPE
        SYNTAX  INTEGER
        ACCESS  read-write
        STATUS  mandatory
        DESCRIPTION
                "Describes the number of nibbles in the Static NSAP
                 Address for the Ignore Static Route."
        ::= { wfOsiTarpIgnoreAdjEntry 4 }

    wfOsiGreAdjTable OBJECT-TYPE
        SYNTAX  SEQUENCE OF WfOsiGreAdjEntry
        ACCESS  not-accessible
        STATUS  mandatory
        DESCRIPTION
                "Gre Adjacency Table"
        ::= { wfOsiGroup 19 }

    wfOsiGreAdjEntry OBJECT-TYPE
        SYNTAX  WfOsiGreAdjEntry
        ACCESS  not-accessible
        STATUS  mandatory
        DESCRIPTION
                "GRE Adjacency Entry"
        INDEX   { wfOsiGreAdjTnlNum, wfOsiGreAdjConnNum }
        ::= { wfOsiGreAdjTable 1 }

    WfOsiGreAdjEntry ::= SEQUENCE {
            wfOsiGreAdjDelete
                INTEGER,
            wfOsiGreAdjDisable
                INTEGER,
            wfOsiGreAdjTnlNum
                INTEGER,
            wfOsiGreAdjConnNum
                INTEGER,
            wfOsiGreAdjRemoteISId
                IpAddress,
            wfOsiGreAdjCircuitId
                INTEGER
        }
 
   wfOsiGreAdjDelete OBJECT-TYPE
       SYNTAX  INTEGER {
                   created(1),
                   deleted(2)
               }
       ACCESS  read-write
       STATUS  mandatory
       DESCRIPTION
               "Delete/Create parameter."
       DEFVAL  { created }
       ::= { wfOsiGreAdjEntry 1 }

   wfOsiGreAdjDisable OBJECT-TYPE
       SYNTAX  INTEGER {
                   enabled(1),
                   disabled(2)
               }
       ACCESS  read-write
       STATUS  mandatory
       DESCRIPTION
               "Enable/Disable parameter"
       DEFVAL  { enabled }
       ::= { wfOsiGreAdjEntry 2 }

   wfOsiGreAdjTnlNum OBJECT-TYPE
       SYNTAX INTEGER
       ACCESS read-only
       STATUS mandatory
       DESCRIPTION
               "GRE tunnel number from GRE MIB"
       ::= { wfOsiGreAdjEntry 3 }

   wfOsiGreAdjConnNum OBJECT-TYPE
       SYNTAX INTEGER
       ACCESS read-only
       STATUS mandatory
       DESCRIPTION
               "GRE remote tunnel connection number from GRE MIB."
       ::= { wfOsiGreAdjEntry 4 }

   wfOsiGreAdjRemoteISId OBJECT-TYPE
       SYNTAX  IpAddress
       ACCESS  read-write
       STATUS  mandatory
       DESCRIPTION
               "This is the Physical IP address of the Destination."
       ::= { wfOsiGreAdjEntry 5 }

   wfOsiGreAdjCircuitId OBJECT-TYPE
       SYNTAX  INTEGER
       ACCESS  read-write
       STATUS  mandatory
       DESCRIPTION
               "Circuit number on which this link in configured."
       ::= { wfOsiGreAdjEntry 6 } 


    END  -- Wellfleet-OSI-MIB
