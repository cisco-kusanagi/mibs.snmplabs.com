-- extracted from draft-ietf-ipcdn-cable-gateway-device-mib-00.txt
-- at Wed Jun 25 06:13:38 2003

   CABH-IETF-PS-DEV-MIB DEFINITIONS ::= BEGIN 
    
   IMPORTS 
      MODULE-IDENTITY, 
      OBJECT-TYPE, 
      Integer32, 
      NOTIFICATION-TYPE, 
      mib-2                FROM SNMPv2-SMI 
    
      TruthValue, 
      PhysAddress, 
      DateAndTime, 
      TimeStamp            FROM SNMPv2-TC 
    
      SnmpAdminString      FROM SNMP-FRAMEWORK-MIB 
    
      OBJECT-GROUP, 
      MODULE-COMPLIANCE, 
      NOTIFICATION-GROUP   FROM SNMPv2-CONF 
        
      InetAddressType, 
      InetAddress          FROM INET-ADDRESS-MIB 
    
      IANAifType           FROM IANAifType-MIB 
       
      docsDevSwCurrentVers, 
      docsDevEvLevel,  
      docsDevEvId,  
      docsDevEvText,  
      docsDevSwFilename,  
      docsDevSwServer              FROM DOCS-CABLE-DEVICE-MIB -- RFC2669 
                                  
      cabhCdpServerDhcpAddress, 
      cabhCdpWanDataAddrClientId, 
      cabhCdpLanTransThreshold, 
      cabhCdpLanTransCurCount      FROM CABH-IETF-CDP-MIB 
    
      ZeroBasedCounter32           FROM RMON2-MIB; 
    
    
   cabhPsDevMib MODULE-IDENTITY 
       LAST-UPDATED    "200306210000Z" -- Jun 21, 2003 
       ORGANIZATION    "IETF IPCDN Working Group" 
       CONTACT-INFO 
               "Kevin Luehrs 
               Postal: Cable Television Laboratories, Inc. 
               400 Centennial Parkway 
               Louisville, Colorado 80027-1266 
               U.S.A. 
               Phone:  +1 303-661-9100 
               Fax:    +1 303-661-9199 
               E-mail: k.luehrs@cablelabs.com; mibs@cablelabs.com 
    
               IETF IPCDN Working Group 
               General Discussion: ipcdn@ietf.org 
               Subscribe: http://www.ietf.org/mailman/listinfo/ipcdn 
               Archive: ftp://ftp.ietf.org/ietf-mail-archive/ipcdn 
               Co-chairs: Richard Woundy, 
                          Richard_Woundy@cable.comcast.com 
                          Jean-Francois Mule, jf.mule@cablelabs.com" 
       DESCRIPTION 
                "This MIB module supplies the basic management objects 
                for the Portal Services logical element of a CableHome  
                compliant Residential Gateway device. The PS device  
                parameters describe general PS Device attributes and  
                behavior characteristics. 
                Most of the PS Device MIB is needed for configuration  
                download. 
    
                Copyright (C) The Internet Society (2003). This version 
                of this MIB module is part of RFC xxxx; see the RFC 
                itself for full legal notices." 
       REVISION         "200306210000Z" -- Jun 21, 2003 
       DESCRIPTION 
               "Initial version, published as RFC xxxx." 
               -- RFC editor to assign xxxx 
       ::= { mib-2 xx }    
       -- xx to be assigned by IANA 
    
   -- Textual Conventions 
    
   cabhPsDevMibObjects  OBJECT IDENTIFIER ::= { cabhPsDevMib 1 } 
   cabhPsDevBase        OBJECT IDENTIFIER ::= { cabhPsDevMibObjects 1 } 
   cabhPsDevProv        OBJECT IDENTIFIER ::= { cabhPsDevMibObjects 2 } 
   cabhPsDevAttrib      OBJECT IDENTIFIER ::= { cabhPsDevMibObjects 3 } 
   cabhPsDevPsAttrib    OBJECT IDENTIFIER ::= { cabhPsDevAttrib 1 } 
   cabhPsDevBpAttrib    OBJECT IDENTIFIER ::= { cabhPsDevAttrib 2 } 
   cabhPsDevPsStats     OBJECT IDENTIFIER ::= { cabhPsDevMibObjects 4 } 
    
    
   -- 
   -- The following group describes the base objects in the PS. 
   -- These are device based parameters.  
   -- 
    
   cabhPsDevDateTime     OBJECT-TYPE 
    SYNTAX       DateAndTime 
    MAX-ACCESS   read-write 
    STATUS       current 
    DESCRIPTION 
            "The date and time, with optional timezone information." 
       ::= { cabhPsDevBase 1 } 
    
   cabhPsDevResetNow    OBJECT-TYPE 
       SYNTAX     TruthValue 
       MAX-ACCESS read-write 
       STATUS     current 
       DESCRIPTION 
               "Setting this object to true(1) causes the stand-alone or  
               embedded PS device to reboot. Device code initializes as 
               if starting from a power-on reset. The CMP ensures that 
               MIB  object values persist as specified in Appendix I of 
               the CableHome 1.0 specification. Reading this object 
               always returns false(2)." 
       ::= { cabhPsDevBase 2 } 
    
   cabhPsDevSerialNumber OBJECT-TYPE 
       SYNTAX       SnmpAdminString (SIZE (0..128)) 
       MAX-ACCESS   read-only 
       STATUS       current 
       DESCRIPTION 
               "The manufacturer's serial number for this PS. This  
               parameter is manufacturer provided and is stored in  
               non-volatile memory." 
       ::= { cabhPsDevBase 3 } 
    
   cabhPsDevHardwareVersion OBJECT-TYPE 
       SYNTAX       SnmpAdminString (SIZE (0..48)) 
       MAX-ACCESS   read-only 
       STATUS       current 
       DESCRIPTION 
               "The manufacturer's hardware version for this PS. This  
               parameter is manufacturer provided and is stored in  
               non-volatile memory." 
       ::= { cabhPsDevBase 4 } 
    
   cabhPsDevWanManMacAddress  OBJECT-TYPE 
       SYNTAX       PhysAddress (SIZE (0..16)) 
       MAX-ACCESS   read-only 
       STATUS       current 
       DESCRIPTION 
               "The PS WAN-Man MAC address. This is the PS hardware 
               address to be used by the CDC to uniquely identify the PS 
               to the cable data network DHCP server for the acquisition 
               of an IP address to be used for management messaging 
               between the cable network NMS and the CMP." 
       ::= { cabhPsDevBase 5 } 
    
   cabhPsDevWanDataMacAddress  OBJECT-TYPE 
       SYNTAX       PhysAddress (SIZE (0..16)) 
       MAX-ACCESS   read-only 
       STATUS       current 
       DESCRIPTION 
               "The PS WAN-Data MAC address. The PS could have multiple  
               WAN-Data Interfaces, which share the same hardware 
               address. The client identifiers will be unique so that 
               each may be assigned a different, unique IP address." 
    ::= { cabhPsDevBase 6 } 
    
   cabhPsDevTypeIdentifier    OBJECT-TYPE 
       SYNTAX       SnmpAdminString  
       MAX-ACCESS   read-only 
       STATUS       current 
       DESCRIPTION 
               "This is a copy of the device type identifier used in 
               the DHCP option 60 exchanged between the PS and the DHCP 
               server." 
       REFERENCE 
               "CableHome 1.0 Specification, CH-SP-I04-030411, 
               7.2.3.3 CDC Requirements 
               CableHome 1.1 Specification, CH 1.1-SP-I01-030418, 
               7.3.3.2.3 CDC Function System Description"  
       ::= { cabhPsDevBase 7 } 
    
   cabhPsDevSetToFactory    OBJECT-TYPE 
       SYNTAX       TruthValue 
       MAX-ACCESS   read-write 
       STATUS       current 
       DESCRIPTION 
               "Setting this object to true(1) sets all PsDev MIB 
               objects to the factory default values. Reading this 
               object always returns false(2)." 
       ::= { cabhPsDevBase 8 } 
    
   cabhPsDevTodSyncStatus     OBJECT-TYPE 
       SYNTAX       TruthValue 
       MAX-ACCESS   read-only 
       STATUS       current 
       DESCRIPTION 
               "This object indicates whether the PS was able to  
               successfully synchronize with the Time of Day (ToD)Server  
               in the cable network. The PS sets this object to true(1) 
               if the PS successfully synchronizes its time with the ToD  
               server. The PS sets this object to false(2) if the PS 
               does not successfully synchronize with the ToD server" 
      DEFVAL { false }   
       ::= { cabhPsDevBase 10 } 
    
   cabhPsDevProvMode    OBJECT-TYPE 
       SYNTAX     INTEGER 
       { 
          dhcpmode(1), 
          snmpmode(2), 
          dormantCHmode(3) 
       } 
       MAX-ACCESS read-only 
       STATUS     current 
       DESCRIPTION 
               "This object indicates the provisioning mode in which the 
               PS is operating. If the PS is operating in DHCP 
               Provisioning Mode as described in the CableHome 1.1 
               specification, the PS sets this object to dhcpmode(1). 
               If the PS is operating in SNMP Provisioning Mode, the PS  
               sets this object to snmpmode(2).If the PS is not 
               configured to operate in either dhcpmode or snmpmode it 
               will fall back to Dormant CableHome Mode and set the 
               value of cabhPsDevProvMode to dormantCHmode(3)." 
       ::={ cabhPsDevBase 11 } 
    
   cabhPsDevLastSetToFactory    OBJECT-TYPE 
    SYNTAX       TimeStamp 
    MAX-ACCESS   read-only 
    STATUS       current 
    DESCRIPTION 
            "The value of sysUpTime when cabhPsDevSetToFactory was last 
            set to true. Zero if never reset." 
       ::= { cabhPsDevBase 12 } 
       
   -- 
   --    The following group defines Provisioning Specific parameters 
   -- 
    
   cabhPsDevProvisioningTimer OBJECT-TYPE 
       SYNTAX       INTEGER (0..16383) 
       UNITS     "minutes" 
       MAX-ACCESS   read-write 
       STATUS       current 
       DESCRIPTION 
               "This object enables the user to set the duration of the  
               provisioning timeout timer. The value is in minutes. 
               Setting the timer to 0 disables it. The default value for 
               the timer is 5." 
       DEFVAL {5} 
       ::=  {cabhPsDevProv 1} 
    
   cabhPsDevProvConfigFile OBJECT-TYPE 
    SYNTAX       SnmpAdminString (SIZE(1..128)) 
    MAX-ACCESS   read-write 
    STATUS       current 
    DESCRIPTION 
            "The URL of the TFTP host for downloading provisioning and  
            configuration parameters to this device. Returns NULL if the  
            server address is unknown." 
    ::= { cabhPsDevProv 2 } 
        
   cabhPsDevProvConfigHash OBJECT-TYPE 
       SYNTAX      OCTET STRING (SIZE(0|20)) 
       MAX-ACCESS  read-write 
       STATUS      current 
       DESCRIPTION 
               "Hash of the contents of the config file, which is  
               calculated and sent by the NMS to the PS. For the SHA-1  
               authentication algorithm the hash length is 160 bits. 
               This hash value is encoded in the binary format." 
    DEFVAL {''h} 
       ::= { cabhPsDevProv 3 } 
    
   cabhPsDevProvConfigFileSize OBJECT-TYPE 
       SYNTAX      Integer32 
       UNITS     "bytes" 
       MAX-ACCESS read-only 
       STATUS      current 
       DESCRIPTION     
               "Size of the configuration file." 
       ::={ cabhPsDevProv 4 } 
        
   cabhPsDevProvConfigFileStatus OBJECT-TYPE 
       SYNTAX     INTEGER  
       { 
           idle(1), 
           busy(2) 
       } 
       MAX-ACCESS read-only 
       STATUS     current 
       DESCRIPTION 
               "This object indicates the current status of the  
               configuration file download process. It is provided to  
               indicate to the management entity that the PS will 
               reject PS Configuration File triggers (set request to  
               cabhPsDevProvConfigFile) when busy." 
       ::={ cabhPsDevProv 5 } 
    
   cabhPsDevProvConfigTLVProcessed OBJECT-TYPE 
       SYNTAX     INTEGER (0..16383) 
       MAX-ACCESS read-only 
       STATUS     current 
       DESCRIPTION 
               "Number of TLVs processed in config file." 
       ::={ cabhPsDevProv 6 } 
        
   cabhPsDevProvConfigTLVRejected OBJECT-TYPE 
       SYNTAX     INTEGER (0..16383) 
       MAX-ACCESS read-only 
       STATUS     current 
       DESCRIPTION 
               "Number of TLVs rejected in config file." 
       ::={ cabhPsDevProv 7 } 
    
   cabhPsDevProvSolicitedKeyTimeout OBJECT-TYPE 
          SYNTAX       Integer32 (15..600) 
          UNITS     "seconds" 
          MAX-ACCESS   read-write 
          STATUS       current 
       DESCRIPTION 
               "This timeout applies only when the Provisioning Server 
               initiated key management (with a Wake Up message) for  
               SNMPv3.  It is the period during which the PS will save  
               a number (inside the sequence number field) from the sent  
               out AP Request and wait for the matching AP Reply from 
               the Provisioning Server." 
       DEFVAL { 120 } 
       ::= { cabhPsDevProv 8 } 
    
   cabhPsDevProvState    OBJECT-TYPE 
       SYNTAX       INTEGER 
       { 
           pass(1), 
           inProgress(2), 
           fail(3) 
       } 
       MAX-ACCESS   read-only 
       STATUS       current 
       DESCRIPTION 
               "This object indicates the completion state of the  
               initialization process. Pass or Fail states occur after  
               completion of the initialization flow. InProgress occurs  
               from PS initialization start to PS initialization end." 
       ::= { cabhPsDevProv 9 } 
    
   cabhPsDevProvAuthState    OBJECT-TYPE 
       SYNTAX       INTEGER 
       { 
           accepted(1), 
           rejected(2)     
       } 
       MAX-ACCESS  read-only 
       STATUS      current 
       DESCRIPTION 
               "This object indicates the authentication state of the  
               configuration file." 
       ::= { cabhPsDevProv 10 } 
    
        
   cabhPsDevTimeServerAddrType OBJECT-TYPE 
       SYNTAX       InetAddressType 
       MAX-ACCESS   read-only 
       STATUS       current 
       DESCRIPTION 
               "The IP address type of the Time server (RFC-868).  
               IP version 4 is typically used." 
    ::= { cabhPsDevProv 12 } 
    
   cabhPsDevTimeServerAddr OBJECT-TYPE 
       SYNTAX       InetAddress 
       MAX-ACCESS   read-only 
       STATUS       current 
       DESCRIPTION 
               "The IP address of the Time server (RFC-868). Returns  
               0.0.0.0 if the time server IP address is unknown." 
       ::= { cabhPsDevProv 13 } 
    
    
   --============================================================== 
   -- 
   --   PS Device Profile Group 
   -- 
   --  The cabhPsDevPsProfile contains the Residential Gateway's 
   --  device attributes. This set of attributes is analogous to  
   --  some attributes of the BP Device profile. 
   -- 
   --============================================================== 
    
   cabhPsDevPsDeviceType       OBJECT-TYPE 
       SYNTAX    SnmpAdminString (SIZE(1..32)) 
       MAX-ACCESS       read-only 
       STATUS    current 
       DESCRIPTION       
               "The type of device, as defined in the CableHome  
               specifications (Residential Gateway Device or CableHome 
               Host Device), that implements this OID." 
       DEFVAL { "CableHome Residential Gateway" } 
       ::= { cabhPsDevPsAttrib 1 } 
    
   cabhPsDevPsManufacturerUrl  OBJECT-TYPE 
       SYNTAX      SnmpAdminString (SIZE(0..32)) 
       MAX-ACCESS  read-only 
       STATUS      current 
       DESCRIPTION       
               "Universal Resource Locator to the Residential Gateway  
               device manufacturer's web site." 
       REFERENCE 
               "CableHome 1.1 Specification, CH1.1-SP-I01-030418, 
               6.5.3.1.3 Device Profile Description" 
       DEFVAL { "" } 
       ::= { cabhPsDevPsAttrib 3 } 
    
    
   cabhPsDevPsModelUrl  OBJECT-TYPE 
       SYNTAX      SnmpAdminString (SIZE(0..32)) 
       MAX-ACCESS  read-only 
       STATUS      current 
       DESCRIPTION       
               "Universal Resource Locator to the web site describing 
               this CableHome compliant residential gateway device." 
       REFERENCE 
               "CableHome 1.1 Specification, CH1.1-SP-I01-030418, 
               6.5.3.1.3 Device Profile Description" 
       DEFVAL { "" } 
       ::= { cabhPsDevPsAttrib 7 } 
    
    
   cabhPsDevPsModelUpc  OBJECT-TYPE 
       SYNTAX      SnmpAdminString (SIZE(0..32)) 
       MAX-ACCESS  read-only 
       STATUS      current 
       DESCRIPTION       
               "Universal Product Code of the CableHome compliant 
               residential gateway device." 
       REFERENCE 
               "CableHome 1.1 Specification, CH1.1-SP-I01-030418, 
               6.5.3.1.3 Device Profile Description.  
               See also: Uniform Code Council  www.uc-council.org" 
       DEFVAL { "" } 
       ::= { cabhPsDevPsAttrib 8 } 
    
   --=================================================================== 
   -- 
   --   CableHome Host/BP Device Profile Table 
   -- 
   --  The cabhPsDevBpProfile contains the list of the CableHome Host  
   --  device attributes provided to the PS by BPs passing their Device  
   --  Profile XML schema via SOAP/HTTP.  
   -- 
   --=================================================================== 
    
   cabhPsDevBpProfileTable OBJECT-TYPE 
       SYNTAX SEQUENCE OF CabhPsDevBpProfileEntry 
       MAX-ACCESS  not-accessible 
       STATUS      current 
       DESCRIPTION 
               "This table contains the information for the CableHome 
               Host Device Profiles. Attributes of a device make up a 
               Device Profile." 
       ::= { cabhPsDevBpAttrib 1 } 
    
    
   cabhPsDevBpProfileEntry  OBJECT-TYPE 
       SYNTAX   CabhPsDevBpProfileEntry 
       MAX-ACCESS      not-accessible 
       STATUS  current 
       DESCRIPTION       
               "The table that describes the CableHome Host Device  
               Profile." 
       INDEX { cabhPsDevBpIndex }  
       ::= { cabhPsDevBpProfileTable 1 } 
    
   CabhPsDevBpProfileEntry ::= SEQUENCE { 
           cabhPsDevBpIndex       INTEGER, 
           cabhPsDevBpDeviceType  SnmpAdminString, 
           cabhPsDevBpManufacturer           SnmpAdminString, 
           cabhPsDevBpManufacturerUrl        SnmpAdminString, 
           cabhPsDevBpSerialNumber           SnmpAdminString, 
           cabhPsDevBpHardwareVersion        SnmpAdminString, 
           cabhPsDevBpHardwareOptions        SnmpAdminString, 
           cabhPsDevBpModelName              SnmpAdminString, 
           cabhPsDevBpModelNumber            SnmpAdminString, 
           cabhPsDevBpModelUrl               SnmpAdminString, 
           cabhPsDevBpModelUpc               SnmpAdminString, 
           cabhPsDevBpModelSoftwareOs        SnmpAdminString, 
           cabhPsDevBpModelSoftwareVersion   SnmpAdminString, 
           cabhPsDevBpLanInterfaceType       IANAifType, 
           cabhPsDevBpNumberInterfacePriorities INTEGER, 
           cabhPsDevBpPhysicalLocation       SnmpAdminString, 
           cabhPsDevBpPhysicalAddress        PhysAddress 
           } 
    
   cabhPsDevBpIndex     OBJECT-TYPE 
       SYNTAX        INTEGER (1..65535) 
       MAX-ACCESS   not-accessible 
       STATUS       current 
       DESCRIPTION       
               "Integer index into the CableHome Host Device Profile 
               Table" 
       ::= { cabhPsDevBpProfileEntry 1 } 
    
   cabhPsDevBpDeviceType      OBJECT-TYPE 
       SYNTAX    SnmpAdminString (SIZE(0..32)) 
       MAX-ACCESS    read-only 
       STATUS current 
       DESCRIPTION       
               "The type of device, as defined by the CableHome  
               specifications (CableHome Residential Gateway or 
   CableHome  
               Host Device), that passed the Device Profile whose  
               information is made available through this table row." 
       REFERENCE 
               "CableHome 1.1 Specification, CH 1.1-SP-I01-030418,  
               6.5.3.1.3 Device Profile Description" 
       DEFVAL     { "CableHome Host" } 
       ::= { cabhPsDevBpProfileEntry 2 } 
    
   cabhPsDevBpManufacturer    OBJECT-TYPE 
       SYNTAX    SnmpAdminString (SIZE(0..32)) 
       MAX-ACCESS    read-only 
       STATUS    current 
       DESCRIPTION       
               "The name of the CableHome Host Device's manufacturer." 
       REFERENCE 
               "CableHome 1.1 Specification, CH 1.1-SP-I01-030418, 
               6.5.3.1.3 Device Profile Description" 
       DEFVAL  { "" } 
       ::= { cabhPsDevBpProfileEntry 3 } 
    
    
   cabhPsDevBpManufacturerUrl  OBJECT-TYPE 
       SYNTAX    SnmpAdminString (SIZE(0..32)) 
       MAX-ACCESS  read-only 
       STATUS      current 
       DESCRIPTION       
               "Universal Resource Locator to the CableHome Host device  
               manufacturer's web site." 
       REFERENCE 
               "CableHome 1.1 Specification, CH 1.1-SP-I01-030418,  
               6.5.3.1.3 Device Profile Description" 
       DEFVAL   { "" } 
       ::= { cabhPsDevBpProfileEntry 4 } 
    
    
   cabhPsDevBpSerialNumber     OBJECT-TYPE 
       SYNTAX      SnmpAdminString (SIZE(0..32)) 
       MAX-ACCESS  read-only 
       STATUS      current 
       DESCRIPTION       
               "The serial number assigned by the manufacturer for this  
               CableHome Host Device." 
       DEFVAL { "" } 
       ::= { cabhPsDevBpProfileEntry 5 } 
        
   cabhPsDevBpHardwareVersion  OBJECT-TYPE 
       SYNTAX      SnmpAdminString (SIZE(0..32)) 
       MAX-ACCESS  read-only 
       STATUS      current 
       DESCRIPTION       
               "The hardware version number assigned by the manufacturer  
               for this CableHome Host Device." 
       REFERENCE 
               "CableHome 1.1 Specification, CH 1.1-SP-I01-030418,  
               6.5.3.1.3 Device Profile Description" 
       DEFVAL { '00'h } 
    ::= { cabhPsDevBpProfileEntry 6 } 
        
   cabhPsDevBpHardwareOptions  OBJECT-TYPE 
       SYNTAX      SnmpAdminString (SIZE(0..32)) 
       MAX-ACCESS  read-only 
       STATUS      current 
       DESCRIPTION       
               "The hardware options implemented on this CableHome Host  
               Device." 
       REFERENCE 
               "CableHome 1.1 Specification, CH 1.1-SP-I01-030418, 
                6.5.3.1.3 Device Profile Description" 
       DEFVAL { "" } 
       ::= { cabhPsDevBpProfileEntry 7 } 
        
   cabhPsDevBpModelName OBJECT-TYPE 
       SYNTAX      SnmpAdminString (SIZE(0..32)) 
       MAX-ACCESS  read-only 
       STATUS      current 
       DESCRIPTION       
               "The model name assigned by the manufacturer for this 
               CableHome Host Device." 
       REFERENCE 
               "CableHome 1.1 Specification, CH 1.1-SP-I01-030418,  
               6.5.3.1.3 Device Profile Description" 
       DEFVAL  { "" } 
       ::= { cabhPsDevBpProfileEntry 8 } 
    
    
   cabhPsDevBpModelNumber      OBJECT-TYPE 
       SYNTAX      SnmpAdminString (SIZE(0..32)) 
       MAX-ACCESS  read-only 
       STATUS      current 
       DESCRIPTION       
               "The model number assigned by the manufacturer for this  
               CableHome Host Device." 
       REFERENCE 
               "CableHome 1.1 Specification, CH 1.1-SP-I01-030418, 
               6.5.3.1.3 Device Profile Description" 
       DEFVAL  { "" } 
       ::= { cabhPsDevBpProfileEntry 9 } 
    
   cabhPsDevBpModelUrl  OBJECT-TYPE 
       SYNTAX      SnmpAdminString (SIZE(0..32)) 
       MAX-ACCESS  read-only 
       STATUS      current 
       DESCRIPTION       
               "The Universal Resource Locator to the web site 
               describing this CableHome Host Device model." 
       REFERENCE 
               "CableHome 1.1 Specification, CH 1.1-SP-I01-030418,  
               6.5.3.1.3 Device Profile Description" 
    DEFVAL { "" } 
    ::= { cabhPsDevBpProfileEntry 10 } 
    
   cabhPsDevBpModelUpc  OBJECT-TYPE 
       SYNTAX      SnmpAdminString (SIZE(0..32)) 
       MAX-ACCESS  read-only 
       STATUS      current 
       DESCRIPTION       
               "Universal Product Code of the CableHome Host Device." 
       REFERENCE 
               "CableHome 1.1 Specification, CH 1.1-SP-I01-030418,  
               6.5.3.1.3 Device Profile Description" 
       DEFVAL  { "" } 
       ::= { cabhPsDevBpProfileEntry 11 } 
    
   cabhPsDevBpModelSoftwareOs       OBJECT-TYPE 
       SYNTAX      SnmpAdminString (SIZE(0..32)) 
       MAX-ACCESS  read-only 
       STATUS      current 
       DESCRIPTION     
               "Software operating system implemented on the CableHome 
               Host Device." 
       REFERENCE 
               "CableHome 1.1 Specification, CH 1.1-SP-I01-030418,  
               6.5.3.1.3 Device Profile Description" 
       DEFVAL { "" } 
       ::= { cabhPsDevBpProfileEntry 12 } 
    
   cabhPsDevBpModelSoftwareVersion   OBJECT-TYPE 
       SYNTAX      SnmpAdminString (SIZE(0..32)) 
       MAX-ACCESS  read-only 
       STATUS      current 
       DESCRIPTION          
               "Version of the operating system implemented on the  
               CableHome Host Device." 

       REFERENCE 
               "CableHome 1.1 Specification, CH 1.1-SP-I01-030418,  
               6.5.3.1.3 Device Profile Description" 
       DEFVAL { "" } 
       ::= { cabhPsDevBpProfileEntry 13 } 
    
   cabhPsDevBpLanInterfaceType     OBJECT-TYPE 
       SYNTAX     IANAifType 
       MAX-ACCESS read-only 
       STATUS     current 
       DESCRIPTION 
               "The ifType for the LAN Interface implemented on the  
               CableHome Host Device." 
       REFERENCE 
               "http://www.iana.org/assignments/ianaiftype-mib 
               See also: CableHome 1.1 Specification, 
               CH1.1-SP-I01-030418, 6.5.3.1.3 Device Profile 
               Description." 
       DEFVAL { other } 
       ::= { cabhPsDevBpProfileEntry 14 } 
    
   cabhPsDevBpNumberInterfacePriorities  OBJECT-TYPE 
       SYNTAX      INTEGER (1..8) 
       MAX-ACCESS    read-only 
       STATUS     current 
       DESCRIPTION          
               "Number of QoS priorities supported by the LAN 
               technology (Data Link Layer) implemented in the 
               CableHome Host Device." 
       DEFVAL { 1 } 
       ::= { cabhPsDevBpProfileEntry 15 } 
    
   cabhPsDevBpPhysicalLocation       OBJECT-TYPE 
       SYNTAX      SnmpAdminString (SIZE(0..32)) 
       MAX-ACCESS  read-only 
       STATUS      current 
       DESCRIPTION          
               "Physical location of the CableHome Host Device." 
       REFERENCE 
               "CableHome 1.1 Specification, CH 1.1-SP-I01-030418,  
               6.5.3.1.3 Device Profile Description" 
       DEFVAL { "" } 
       ::= { cabhPsDevBpProfileEntry 16 } 
    
   cabhPsDevBpPhysicalAddress  OBJECT-TYPE 
       SYNTAX      PhysAddress (SIZE (0..16)) 
       MAX-ACCESS  read-only 
       STATUS      current 
       DESCRIPTION          
               "The CableHome Host Device's hardware address." 

       REFERENCE 
               "CableHome 1.1 Specification, CH 1.1-SP-I01-030418,  
               6.5.3.1.3 Device Profile Description" 
       DEFVAL { ''h } 
       ::= { cabhPsDevBpProfileEntry 17 } 
    
         
    
   --================================================================= 
   -- 
   --   LAN IP Traffic Statistics Table 
   -- 
   --  The cabhPsDevLanIpTrafficTable contains the Traffic Statistics 
   --  for all LAN IP Devices connected to the PS. When the PS learns 
   --  a new LAN IP address an entry is added to this table. 
   -- 
   --================================================================= 
    
   cabhPsDevLanIpTrafficCountersReset    OBJECT-TYPE 
       SYNTAX       INTEGER 
       { 
           clearCounters(1), 
           clearTable(2) 
       } 
       MAX-ACCESS   read-write 
       STATUS       current 
       DESCRIPTION 
               "Setting this object to clearCounters(1) resets all the  
               traffic statistic counter entries to zero in the  
               cabhPsDevLanIpTrafficTable. Setting this object to  
               clearTable(2) removes all entries in the  
               cabhPsDevLanIpTrafficTable. Reading this object always  
               returns clearCounters(1)." 
       DEFVAL   { clearCounters }   
       ::= { cabhPsDevPsStats 1 } 
    
   cabhPsDevLanIpTrafficCountersLastReset    OBJECT-TYPE 
       SYNTAX   TimeStamp 
       MAX-ACCESS      read-only 
       STATUS   current 
       DESCRIPTION 
               "The value of sysUpTime when  
               cabhPsDevLanIpTrafficCountersReset was last written to.  
               Zero if never written to." 
    ::= { cabhPsDevPsStats 2 } 
    
   cabhPsDevLanIpTrafficEnabled OBJECT-TYPE 
       SYNTAX       TruthValue 
       MAX-ACCESS   read-write 
       STATUS       current 
       DESCRIPTION 
               "Setting this object to true(1) turns on the IP traffic  
               counters. Setting this object false(2) turns off the IP  
               traffic counters." 
       DEFVAL   { false }  -- IP traffic counters are off by default 
       ::= { cabhPsDevPsStats 3 } 
    
   cabhPsDevLanIpTrafficTable OBJECT-TYPE 
       SYNTAX      SEQUENCE OF CabhPsDevLanIpTrafficEntry 
       MAX-ACCESS   not-accessible 
       STATUS       current 
       DESCRIPTION 
               "This table contains IP-layer Traffic Statistics for all 
               LAN IP Devices connected to the PS."  
       ::= { cabhPsDevPsStats 4 } 
    
   cabhPsDevLanIpTrafficEntry  OBJECT-TYPE 
       SYNTAX       CabhPsDevLanIpTrafficEntry 
       MAX-ACCESS   not-accessible 
       STATUS       current 
       DESCRIPTION 
               "List of Traffic Statistics for LAN IP Devices." 
       INDEX { cabhPsDevLanIpTrafficIndex } 
       ::= { cabhPsDevLanIpTrafficTable 1 } 
    
   CabhPsDevLanIpTrafficEntry ::= SEQUENCE { 
       cabhPsDevLanIpTrafficIndex      INTEGER, 
       cabhPsDevLanIpTrafficInetAddressType   InetAddressType, 
       cabhPsDevLanIpTrafficInetAddress       InetAddress, 
       cabhPsDevLanIpTrafficInOctets   ZeroBasedCounter32, 
       cabhPsDevLanIpTrafficOutOctets  ZeroBasedCounter32 
       } 
    
   cabhPsDevLanIpTrafficIndex    OBJECT-TYPE 
       SYNTAX       INTEGER   (1..65535) 
       MAX-ACCESS   not-accessible 
       STATUS       current 
       DESCRIPTION 
               "The Index into the LAN IP Traffic Statistics Table." 
       ::= { cabhPsDevLanIpTrafficEntry 1 } 
    
    
   cabhPsDevLanIpTrafficInetAddressType OBJECT-TYPE 
       SYNTAX       InetAddressType 
       MAX-ACCESS  read-only 
       STATUS       current 
       DESCRIPTION 
               "The type of IP address assigned to the LAN IP device 
               to which the statistics in this table row apply.  IP 
               version 4 is typically used." 

       DEFVAL { ipv4 } 
       ::= { cabhPsDevLanIpTrafficEntry 2 } 
    
   cabhPsDevLanIpTrafficInetAddress OBJECT-TYPE 
       SYNTAX       InetAddress 
       MAX-ACCESS   read-only 
       STATUS       current 
       DESCRIPTION 
               "The IP address of the LAN IP device to which the 
               statistics in this table row apply.  An IPv4 IP address 
               is typically used." 
    ::= { cabhPsDevLanIpTrafficEntry 3 } 
    
   cabhPsDevLanIpTrafficInOctets    OBJECT-TYPE 
       SYNTAX     ZeroBasedCounter32 
       MAX-ACCESS read-only 
       STATUS     current 
       DESCRIPTION 
               "The total number of octets received from the LAN IP  
               address." 
    ::= { cabhPsDevLanIpTrafficEntry 4 } 
      
   cabhPsDevLanIpTrafficOutOctets    OBJECT-TYPE 
       SYNTAX     ZeroBasedCounter32 
       MAX-ACCESS read-only 
       STATUS     current 
       DESCRIPTION 
               "The total number of octets transmitted to the LAN IP  
               address." 
       ::= { cabhPsDevLanIpTrafficEntry 5 } 
    
    
   --  
    
   cabhPsNotification     OBJECT IDENTIFIER ::= { cabhPsDevMib 2 } 
   cabhPsDevNotifications OBJECT IDENTIFIER ::= { cabhPsNotification 2 } 
   cabhPsConformance      OBJECT IDENTIFIER ::= { cabhPsDevMib 3 } 
   cabhPsCompliances      OBJECT IDENTIFIER ::= { cabhPsConformance 1 } 
   cabhPsGroups    OBJECT IDENTIFIER ::= { cabhPsConformance 2 } 
    
   -- 
   --    Notification Group 
   -- 
    
   cabhPsDevInitTLVUnknownTrap     NOTIFICATION-TYPE  
       OBJECTS   {  
           docsDevEvLevel,  
           docsDevEvId,  
           docsDevEvText,  
           cabhPsDevWanManMacAddress  

       }  
       STATUS  current  
       DESCRIPTION  
               "Event due to detection of unknown TLV during the TLV  
               parsing process. The values of docsDevEvLevel, docsDevId,  
               and docsDevEvText are from the entry which logs this 
               event in the docsDevEventTable.  The value of  
               cabhPsDevWanManMacAddress indicates the WAN-Man MAC 
               address of the PS. This part of the information is 
               uniform across all PS Traps."  
       ::= { cabhPsDevNotifications 1 } 
    
    
   cabhPsDevInitTrap  NOTIFICATION-TYPE 
       OBJECTS {   
           docsDevEvLevel, 
           docsDevEvId, 
           docsDevEvText, 
           cabhPsDevWanManMacAddress, 
           cabhPsDevProvConfigFile, 
           cabhPsDevProvConfigTLVProcessed, 
           cabhPsDevProvConfigTLVRejected 
       } 
       STATUS      current 
       DESCRIPTION 
               "This inform is issued to confirm the successful 
               completion of the CableHome provisioning process." 
       ::= { cabhPsDevNotifications 2 } 
    
   cabhPsDevInitRetryTrap  NOTIFICATION-TYPE 
       OBJECTS  { 
           docsDevEvLevel, 
           docsDevEvId, 
           docsDevEvText, 
           cabhPsDevWanManMacAddress 
       } 
       STATUS      current 
       DESCRIPTION 
               "An event to report a failure happened during the  
               initialization process and was detected in the PS." 
       ::= { cabhPsDevNotifications 3 } 
    
   cabhPsDevDHCPFailTrap NOTIFICATION-TYPE  
       OBJECTS {    
           docsDevEvLevel,  
           docsDevEvId,  
           docsDevEvText,  
           cabhPsDevWanManMacAddress,  
           cabhCdpServerDhcpAddress 
       }  
       STATUS  current  
       DESCRIPTION  
               "An event to report the failure of a DHCP server. The 
               value of cabhCdpServerDhcpAddressis the IP address of 
               the DHCP server."  
       ::= { cabhPsDevNotifications 4 } 
    
    
   cabhPsDevSwUpgradeInitTrap NOTIFICATION-TYPE  
       OBJECTS {    
           docsDevEvLevel,  
           docsDevEvId,  
           docsDevEvText,  
           cabhPsDevWanManMacAddress,  
           docsDevSwFilename,  
           docsDevSwServer  
       }  
       STATUS  current  
       DESCRIPTION  
               "An event to report a software upgrade initiated event.  
               The values of docsDevSwFilename, and docsDevSwServer  
               indicate the software image name and the IP address of 
               the server from which the image was downloaded."  
       ::= { cabhPsDevNotifications 5 } 
    
    
   cabhPsDevSwUpgradeFailTrap NOTIFICATION-TYPE  
       OBJECTS {    
           docsDevEvLevel,  
           docsDevEvId,  
           docsDevEvText,  
           cabhPsDevWanManMacAddress,  
           docsDevSwFilename,  
           docsDevSwServer  
       }  
       STATUS  current  
       DESCRIPTION  
               "An event to report the failure of a software upgrade  
               attempt. The values of docsDevSwFilename, and  
               docsDevSwServer indicate the software image name and the 
               IP address of the server from which the image was 
               downloaded."  
          ::= { cabhPsDevNotifications 6 } 
    
    
   cabhPsDevSwUpgradeSuccessTrap NOTIFICATION-TYPE  
       OBJECTS {    
           docsDevEvLevel,  
           docsDevEvId, 
           docsDevEvText, 
           cabhPsDevWanManMacAddress, 
           docsDevSwFilename,  
           docsDevSwServer  
       }  
       STATUS  current  
       DESCRIPTION  
               "An event to report the Software upgrade success event. 
               The values of docsDevSwFilename, and docsDevSwServer  
               indicate the software image name and the IP address of 
               the server from which the image was downloaded."  
       ::= { cabhPsDevNotifications 7 } 
    
    
   cabhPsDevSwUpgradeCVCFailTrap NOTIFICATION-TYPE  
       OBJECTS {    
           docsDevEvLevel,  
           docsDevEvId,  
           docsDevEvText, 
           cabhPsDevWanManMacAddress  
       }  
       STATUS  current  
       DESCRIPTION  
               "An event to report the failure of the verification of 
               code file happened during a secure software upgrade 
               attempt."  
       ::= { cabhPsDevNotifications 8 } 
    
    
   cabhPsDevTODFailTrap NOTIFICATION-TYPE  
       OBJECTS {    
          docsDevEvLevel,  
          docsDevEvId,  
          docsDevEvText,  
          cabhPsDevTimeServerAddr,  
          cabhPsDevWanManMacAddress 
       }  
       STATUS  current  
       DESCRIPTION  
               "An event to report the failure of a time of day server.  
               The value of cabhPsDevTimeServerAddr indicates the server  
                IP address."   
       ::= { cabhPsDevNotifications 9 } 
    
   cabhPsDevCdpWanDataIpTrap  NOTIFICATION-TYPE 
       OBJECTS {  
           docsDevEvLevel,  
           docsDevEvId,  
           docsDevEvText, 
           cabhCdpWanDataAddrClientId,  
           cabhPsDevWanManMacAddress 

       } 
       STATUS      current 
       DESCRIPTION 
               "An event to report the failure of PS to obtain all 
               needed WAN-Data Ip Addresses. 
               cabhCdpWanDataAddrClientId indicates the ClientId for 
               which the failure occured."  
       ::= { cabhPsDevNotifications 10 } 
       
    
   cabhPsDevCdpThresholdTrap  NOTIFICATION-TYPE 
       OBJECTS {  
           docsDevEvLevel,  
           docsDevEvId,  
           docsDevEvText, 
           cabhPsDevWanManMacAddress, 
           cabhCdpLanTransThreshold 
       } 
       STATUS      current 
       DESCRIPTION 
               "An event to report that the LAN-Trans address assignment  
               threshold has been exceeded." 
       ::= { cabhPsDevNotifications 11 } 
    
   cabhPsDevCspTrap  NOTIFICATION-TYPE 
       OBJECTS {  
           docsDevEvLevel,  
           docsDevEvId,  
           docsDevEvText, 
           cabhPsDevWanManMacAddress 
       } 
       STATUS      current 
       DESCRIPTION 
               "To report an event with the CableHome Security Portal." 
       ::= { cabhPsDevNotifications 12 } 
    
   cabhPsDevCapTrap  NOTIFICATION-TYPE 
       OBJECTS {  
           docsDevEvLevel,  
           docsDevEvId,  
           docsDevEvText, 
           cabhPsDevWanManMacAddress 
       } 
       STATUS      current 
       DESCRIPTION 
               "To report an event with the CableHome Address Portal." 
       ::= { cabhPsDevNotifications 13 } 
    
   cabhPsDevCtpTrap  NOTIFICATION-TYPE 
       OBJECTS {  
           docsDevEvLevel,  
           docsDevEvId,  
           docsDevEvText, 
           cabhPsDevWanManMacAddress 
       } 
       STATUS      current 
       DESCRIPTION 
               "To report an event with the CableHome Test Portal." 
       ::= { cabhPsDevNotifications 14 } 
    
   cabhPsDevProvEnrollTrap  NOTIFICATION-TYPE 
       OBJECTS {  
           cabhPsDevHardwareVersion, 
           docsDevSwCurrentVers, 
           cabhPsDevTypeIdentifier, 
           cabhPsDevWanManMacAddress 
       }          
       STATUS    current 
       DESCRIPTION 
               "This inform is issued to initiate the CableHome  
               provisioning process for SNMP Provisioning Mode." 
       ::= { cabhPsDevNotifications 15 } 
    
    
   cabhPsDevCdpLanIpPoolTrap NOTIFICATION-TYPE 
       OBJECTS { 
           docsDevEvLevel,  
           docsDevEvId,  
           docsDevEvText,  
           cabhPsDevWanManMacAddress, 
           cabhCdpLanTransCurCount 
       }  
       STATUS current 
       DESCRIPTION 
               "An event to report that the pool of IP addresses for LAN  
               clients, as defined by cabh CdpLanPoolStart and  
               cabhCdpLanPoolEnd, is exhausted." 
       ::= { cabhPsDevNotifications 16} 
       
   -- compliance statements 
    
   cabhPsBasicCompliance MODULE-COMPLIANCE 
       STATUS     current 
       DESCRIPTION 
               "The compliance statement for devices that implement the  
               CableHome Portal Services logical element." 
       MODULE   -- cabhPsMib 
    
    
   -- unconditionally mandatory groups 
   MANDATORY-GROUPS { 
           cabhPsDevBaseGroup, 
           cabhPsDevProvGroup, 
           cabhPsNotificationGroup 
       }        
        
   -- conditionally mandatory group 
   GROUP cabhPsDevAttribGroup 
       DESCRIPTION 
               "This group is implemented only in CableHome 1.1 PS  
               elements, not CableHome 1.0 PS elements." 
         
   -- conditionally mandatory group 
   GROUP cabhPsDevPsStatsGroup 
       DESCRIPTION 
               "This group is implemented only in CableHome 1.1 PS 
               elements, not CableHome 1.0 PS elements." 
    
   OBJECT cabhPsDevTimeServerAddrType 
          SYNTAX InetAddressType { ipv4(1) } 
          DESCRIPTION 
              "An implementation is only required to support IPv4 
               addresses." 
    
   OBJECT cabhPsDevTimeServerAddr 
          SYNTAX  InetAddress (SIZE(4)) 
          DESCRIPTION 
              "An implementation is only required to support IPv4 
               addresses." 
    
   OBJECT cabhPsDevLanIpTrafficInetAddressType 
          SYNTAX InetAddressType { ipv4(1) } 
          DESCRIPTION 
              "An implementation is only required to support IPv4 
               addresses." 
    
   OBJECT cabhPsDevLanIpTrafficInetAddress 
          SYNTAX  InetAddress (SIZE(4)) 
          DESCRIPTION 
              "An implementation is only required to support IPv4 
               addresses." 
    
   ::= { cabhPsCompliances 1} 
    
    
   cabhPsDevBaseGroup OBJECT-GROUP 
       OBJECTS { 
           cabhPsDevDateTime, 
           cabhPsDevResetNow, 
           cabhPsDevSerialNumber, 
           cabhPsDevHardwareVersion, 
           cabhPsDevWanManMacAddress, 
           cabhPsDevWanDataMacAddress, 
           cabhPsDevTypeIdentifier, 
           cabhPsDevSetToFactory, 
           cabhPsDevTodSyncStatus,  
           cabhPsDevProvMode,  -- added dormant mode   
           cabhPsDevLastSetToFactory 
       } 
       STATUS     current 
       DESCRIPTION 
               "A collection of objects for providing device status and  
               control." 
       ::= { cabhPsGroups 1 }    
     
   cabhPsDevProvGroup OBJECT-GROUP 
       OBJECTS { 
           cabhPsDevProvisioningTimer, 
           cabhPsDevProvConfigFile, 
           cabhPsDevProvConfigHash, 
           cabhPsDevProvConfigFileSize, 
           cabhPsDevProvConfigFileStatus, 
           cabhPsDevProvConfigTLVProcessed, 
           cabhPsDevProvConfigTLVRejected, 
           cabhPsDevProvSolicitedKeyTimeout, 
           cabhPsDevProvState, 
           cabhPsDevProvAuthState, 
           cabhPsDevTimeServerAddrType, 
           cabhPsDevTimeServerAddr 
       }      
       STATUS     current 
       DESCRIPTION 
               "A collection of objects for controlling and providing 
               status on provisioning." 
       ::= { cabhPsGroups 2 }    
     
      
   cabhPsDevAttribGroup OBJECT-GROUP 
       OBJECTS { 
           cabhPsDevPsDeviceType, 
           cabhPsDevPsManufacturerUrl, 
           cabhPsDevPsModelUrl, 
           cabhPsDevPsModelUpc, 
           cabhPsDevBpDeviceType, 
           cabhPsDevBpManufacturer, 
           cabhPsDevBpManufacturerUrl, 
           cabhPsDevBpSerialNumber, 
           cabhPsDevBpHardwareVersion, 
           cabhPsDevBpHardwareOptions, 
           cabhPsDevBpModelName, 
           cabhPsDevBpModelNumber, 
           cabhPsDevBpModelUrl, 
           cabhPsDevBpModelUpc, 
           cabhPsDevBpModelSoftwareOs, 
           cabhPsDevBpModelSoftwareVersion, 
           cabhPsDevBpLanInterfaceType, 
           cabhPsDevBpNumberInterfacePriorities, 
           cabhPsDevBpPhysicalLocation, 
           cabhPsDevBpPhysicalAddress 
       }     
       STATUS     current 
       DESCRIPTION 
               "A collection of objects for providing information on 
               LAN IP devices known to the PS." 
       ::= { cabhPsGroups 3 }    
     
         
   cabhPsDevPsStatsGroup OBJECT-GROUP 
       OBJECTS {        
           cabhPsDevLanIpTrafficCountersReset, 
           cabhPsDevLanIpTrafficCountersLastReset, 
           cabhPsDevLanIpTrafficEnabled,  
           cabhPsDevLanIpTrafficInetAddressType, 
           cabhPsDevLanIpTrafficInetAddress, 
           cabhPsDevLanIpTrafficInOctets, 
           cabhPsDevLanIpTrafficOutOctets 
       } 
       STATUS     current 
       DESCRIPTION 
               "A collection of objects for providing information on LAN 
   IP 
               traffic." 
       ::= { cabhPsGroups 4 }    
     
   cabhPsNotificationGroup NOTIFICATION-GROUP 
       NOTIFICATIONS {  
           cabhPsDevInitTLVUnknownTrap,  
           cabhPsDevInitTrap, 
           cabhPsDevInitRetryTrap, 
           cabhPsDevDHCPFailTrap,  
           cabhPsDevSwUpgradeInitTrap,  
           cabhPsDevSwUpgradeFailTrap, 
           cabhPsDevSwUpgradeSuccessTrap,  
           cabhPsDevSwUpgradeCVCFailTrap,  
           cabhPsDevTODFailTrap, 
           cabhPsDevCdpWanDataIpTrap,  
           cabhPsDevCdpThresholdTrap,  
           cabhPsDevCspTrap,  
           cabhPsDevCapTrap,  
           cabhPsDevCtpTrap,  
           cabhPsDevProvEnrollTrap,  
           cabhPsDevCdpLanIpPoolTrap  
        } 
       STATUS    current 
       DESCRIPTION 
               "These notifications indicate change in status of the 
               Portal Services set of functions in a device complying 
               with CableLabs CableHome(tm) specifications." 
       ::= { cabhPsGroups 6 } 
    
   END 

--  
--    Copyright (C) The Internet Society (2003). All Rights Reserved. 
--     
--    This document and translations of it may be copied and furnished to 
--    others, and derivative works that comment on or otherwise explain it 
--    or assist in its implementation may be prepared, copied, published 
--    and distributed, in whole or in part, without restriction of any 
--    kind, provided that the above copyright notice and this paragraph are 
--    included on all such copies and derivative works.  However, this 
--    document itself may not be modified in any way, such as by removing 
--    the copyright notice or references to the Internet Society or other 
--    Internet organizations, except as needed for the purpose of 
--    developing Internet standards in which case the procedures for 
--    copyrights defined in the Internet Standards process must be 
--    followed, or as required to translate it into languages other than 
--    English. 
--     
--    The limited permissions granted above are perpetual and will not be 
--    revoked by the Internet Society or its successors or assigns. 
--     
--    This document and the information contained herein is provided on an 
--    "AS IS" basis and THE INTERNET SOCIETY AND THE INTERNET ENGINEERING 
--    TASK FORCE DISCLAIMS ALL WARRANTIES, EXPRESS OR IMPLIED, INCLUDING 
--    BUT NOT LIMITED TO ANY WARRANTY THAT THE USE OF THE INFORMATION 
--    HEREIN WILL NOT INFRINGE ANY RIGHTS OR ANY IMPLIED WARRANTIES OF 
--    MERCHANTABILITY OR FITNESS FOR A PARTICULAR PURPOSE."
