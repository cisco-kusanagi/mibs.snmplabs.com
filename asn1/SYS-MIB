SYS-MIB DEFINITIONS ::= BEGIN

	IMPORTS
		TruthValue										FROM SNMPv2-TC
		OBJECT-TYPE										FROM RFC-1212
		Gauge, IpAddress, TimeTicks, Counter,
		enterprises										FROM RFC1155-SMI
		DisplayString									FROM RFC1213-MIB
		rs232PortIndex									FROM RS232-MIB
		TRAP-TYPE										FROM RFC-1215
		Gauge32 FROM SNMPv2-SMI;

--	sysMIB MODULE-IDENTITY
--		LAST-UPDATED "9812230000Z"
--		ORGANIZATION "Northrop Grumman-Canada, Ltd."
--		CONTACT-INFO
--			"		Fulko K. Hew
--
--			Postal:	Northrop Grumman-Canada, Ltd.
--					777 Walkers Line
--					Burlington, Ontario
--					Canada
--					L7N 2G1
--
--			Tel:	+1 905 333 6000
--			Fax:	+1 905 333 6050
--
--			E-mail: fulko@ngcan.com"
--	DESCRIPTION
--		"The MIB module to describe generic MIB II like objects.
--		Although this is derived from the original MIB II definition
--		as per RFC 1213, it has been updated to make it more useful
--		especially with respect to TIGER operation."

	ngcan			OBJECT IDENTIFIER ::= { enterprises 1978 }	-- Northrop Grumman-Canada, Ltd.
	tiger			OBJECT IDENTIFIER ::= { ngcan 2 }			-- Tiger (Network Access Device)

	sysMIB			OBJECT IDENTIFIER ::= { tiger 18 }

	system			OBJECT IDENTIFIER ::= { sysMIB 1 }
	interfaces		OBJECT IDENTIFIER ::= { sysMIB 2 }
	ip				OBJECT IDENTIFIER ::= { sysMIB 3 }
	icmp			OBJECT IDENTIFIER ::= { sysMIB 4 }
	tcp				OBJECT IDENTIFIER ::= { sysMIB 5 }
	udp				OBJECT IDENTIFIER ::= { sysMIB 6 }
	snmp			OBJECT IDENTIFIER ::= { sysMIB 7 }
	sysTraps		OBJECT IDENTIFIER ::= { sysMIB 8 }
	partyMIB		OBJECT IDENTIFIER ::= { sysMIB 9 }

	-- textual conventions

	--
	-- !! NOTE !!
	--
	--  When trying to compile this MIB under HP Openview or a derivative,
	--  you may find that it complains about the following two lines.
	--  You may safely comment these out by placing a two dashes in front of them.
	--

	--Gauge32			::= INTEGER (0..2147483647)
	--defaultOID		OBJECT IDENTIFIER ::= { 0 0 }

	PhysAddress ::= OCTET STRING
		-- This data type is used to model media addresses.  For many
		-- types of media, this will be in a binary representation.
		-- For example, an ethernet address would be represented as
		-- a string of 6 octets.

	-- the System group

	-- Implementation of the System group is current for all
	-- systems.  If an agent is not configured to have a value
	-- for any of these variables, a string of length 0 is
	-- returned.

	sysDescr OBJECT-TYPE
		SYNTAX		DisplayString (SIZE (0..255))
		ACCESS		read-write
		STATUS		mandatory
		DESCRIPTION
			"A textual description of the Tiger.  This value
			corresponds to the description of the unit obtained from the
			configuration tool.  This object should only contain
			printable ASCII characters."
		::= { system 1 }

	sysObjectID OBJECT-TYPE
		SYNTAX		OBJECT IDENTIFIER
		ACCESS		read-only
		STATUS		mandatory
		DESCRIPTION
			"The vendor's authoritative identification of the
			network management subsystem contained in the
			entity.  This value is allocated within the SMI
			enterprises subtree (1.3.6.1.4.1) and provides an
			easy and unambiguous means for determining `what
			kind of box' is being managed.  Tiger is identified
			by the subtree (1.3.6.1.4.1.1978.2.18.1.2.0)"
		::= { system 2 }

	sysUpTime OBJECT-TYPE
		SYNTAX		TimeTicks
		ACCESS		read-only
		STATUS		mandatory
		DESCRIPTION
			"The time (in hundredths of a second) since the
			system was last re-initialized."
		::= { system 3 }

	sysContact OBJECT-TYPE
		SYNTAX		DisplayString (SIZE (0..255))
		ACCESS		read-write
		STATUS		mandatory
		DESCRIPTION
			"The textual identification of the contact person
			for this managed node, together with information
			on how to contact this person.  This will normally
			be filled in via the .cfg file as generated by the
			configuration tool."
		::= { system 4 }

	sysName OBJECT-TYPE
		SYNTAX		DisplayString (SIZE (0..255))
		ACCESS		read-write
		STATUS		mandatory
		DESCRIPTION
			"An administratively-assigned name for this managed node
			as identified from the .cfg file that was filled in by
			the configuration tool.

			By convention, this is the node's fully-qualified domain name.

			This parameter is also used as the prompt for TELNET sessions
			to help identify the Tiger."
		::= { system 5 }

	sysLocation OBJECT-TYPE
		SYNTAX		DisplayString (SIZE (0..255))
		ACCESS		read-write
		STATUS		mandatory
		DESCRIPTION
			"The physical location of this node
			as identified from the .cfg file that was filled in by
			the configuration tool.  (e.g., `telephone closet, 3rd floor')."
		::= { system 6 }

	sysServices OBJECT-TYPE
		SYNTAX		INTEGER (0..127)
		ACCESS		read-only
		STATUS		mandatory
		DESCRIPTION
			"A value which indicates the set of services that this entity primarily offers.

			The value is a sum.  This sum initially takes the value zero, Then, for each
			layer, L, in the range 1 through 7, that this node performs transactions
			for, 2 raised to (L - 1) is added to the sum.  For example, a node which
			performs primarily routing functions would have a value of 4 (2^(3-1)).
			In contrast, a node which is a host offering application services would
			have a value of 72 (2^(4-1) + 2^(7-1)).  Note that in the context of the
			Internet suite of protocols, values should be calculated accordingly:

			layer	functionality
			  1		physical (e.g., repeaters)
			  2		datalink/subnetwork (e.g., bridges)
			  3		internet (e.g., IP gateways)
			  4		end-to-end  (e.g., IP hosts)
			  7		applications (e.g., mail relays)

			For systems including OSI protocols, layers 5 and 6 may also be counted."
		::= { system 7 }

	-- the Interfaces group

	-- Implementation of the Interfaces group is current for
	-- all systems.

	ifNumber OBJECT-TYPE
		SYNTAX		INTEGER (1..1000)
		ACCESS		read-only
		STATUS		mandatory
		DESCRIPTION
			"The number of network interfaces (regardless of
			their current state) present on this system."
		::= { interfaces 1 }


	-- the Interfaces table

	-- The Interfaces table contains information on the entity's
	-- interfaces.  Each interface is thought of as being
	-- attached to a `subnetwork'.  Note that this term should
	-- not be confused with `subnet' which refers to an
	-- addressing partitioning scheme used in the Internet suite
	-- of protocols.

	ifTable OBJECT-TYPE
		SYNTAX		SEQUENCE OF IfEntry
		ACCESS		not-accessible
		STATUS		mandatory
		DESCRIPTION
			"A list of interface entries.  The number of
			entries is given by the value of ifNumber."
		::= { interfaces 2 }

	ifEntry OBJECT-TYPE
		SYNTAX		IfEntry
		ACCESS		not-accessible
		STATUS		mandatory
		DESCRIPTION
			"An interface entry containing objects at the
			subnetwork layer and below for a particular
			interface."
		INDEX		{ ifIndex }
		::= { ifTable 1 }

	IfEntry ::= SEQUENCE {
		ifIndex					INTEGER,
		ifDescr					DisplayString,
		ifType					INTEGER,
		ifMtu					INTEGER,
		ifSpeed					Gauge32,
		ifPhysAddress			PhysAddress,
		ifAdminStatus			INTEGER,
		ifOperStatus			INTEGER,
		ifLastChange			TimeTicks,
		ifInOctets				Counter,
		ifInUcastPkts			Counter,
		ifInNUcastPkts			Counter,
		ifInDiscards			Counter,
		ifInErrors				Counter,
		ifInUnknownProtos		Counter,
		ifOutOctets				Counter,
		ifOutUcastPkts			Counter,
		ifOutNUcastPkts			Counter,
		ifOutDiscards			Counter,
		ifOutErrors				Counter,
		ifOutQLen				Gauge32,
		ifSpecific				OBJECT IDENTIFIER,
		ifInMulticastPkts		Counter,
		ifInBroadcastPkts		Counter,
		ifOutMulticastPkts		Counter,
		ifOutBroadcastPkts		Counter,
		ifStateChangeTrapEnable	INTEGER,
		ifConnectorPresent		TruthValue,

		ifClearStats			INTEGER,
		ifClearStatsTime		TimeTicks,
		ifErrorRateTrapEnable	INTEGER,
		ifErrorRateInterval		INTEGER,
		ifErrorInLowThreshold	INTEGER,
		ifErrorInHighThreshold	INTEGER,
		ifErrorOutLowThreshold	INTEGER,
		ifErrorOutHighThreshold	INTEGER,
		ifErrType				INTEGER
		}

	ifIndex OBJECT-TYPE
		SYNTAX		INTEGER (1..1000)
		ACCESS		read-write
		STATUS		mandatory
		DESCRIPTION
			"A unique value for each interface.  Its value
			ranges between 1 and the value of ifNumber.  The
			value for each interface must remain constant at
			least from one re-initialization of the entity's
			network management system to the next re-initialization."
		::= { ifEntry 1 }

	ifDescr OBJECT-TYPE
		SYNTAX		DisplayString (SIZE (0..255))
		ACCESS		read-write
		STATUS		mandatory
		DESCRIPTION
			"A textual string containing information about the
			interface.  This string should include the name of
			the manufacturer, the product name and the version
			of the hardware interface."
		::= { ifEntry 2 }

	ifType OBJECT-TYPE
		SYNTAX		INTEGER {
			other					(1),	-- none of the following
			regular1822				(2),
			hdh1822					(3),
			ddn-x25					(4),
			rfc877-x25				(5),
			ethernet-csmacd			(6),
			iso88023-csmacd			(7),
			iso88024-tokenBus		(8),
			iso88025-tokenRing		(9),
			iso88026-man			(10),
			starLan					(11),
			proteon-10Mbit			(12),
			proteon-80Mbit			(13),
			hyperchannel			(14),
			fddi					(15),
			lapb					(16),
			sdlc					(17),
			ds1						(18),	-- T-1
			e1						(19),	-- european equiv. of T-1
			basicISDN				(20),
			primaryISDN				(21),	-- proprietary serial
			propPointToPointSerial	(22),
			ppp						(23),
			softwareLoopback		(24),
			eon						(25),	-- CLNP over IP [11]
			ethernet-3Mbit			(26),
			nsip					(27),	-- XNS over IP
			slip					(28),	-- generic SLIP
			ultra					(29),	-- ULTRA technologies
			ds3						(30),	-- T-3
			sip						(31),	-- SMDS
			frame-relay				(32),
			rs232					(33),
			para					(34),	-- parallel-port
			arcnet					(35),	-- arcnet
			arcnetPlus				(36),	-- arcnet plus
			atm						(37),	-- ATM cells
			miox25					(38),
			sonet					(39),	-- SONET or SDH
			x25ple					(40),
			iso88022llc				(41),
			localTalk				(42),
			smdsDxi					(43),
			frameRelayService		(44),	-- Frame relay DCE
			v35						(45),
			hssi					(46),
			hippi					(47),
			modem					(48),	-- Generic modem
			aal5					(49),	-- AAL5 over ATM
			sonetPath				(50),
			sonetVT					(51),
			smdsIcip				(52),	-- SMDS InterCarrier Interface
			propVirtual				(53),	-- proprietary virtual/internal
			propMultiplexor			(54),	-- proprietary multiplexing
			alc						(55),	-- the ALC protocol
			cap						(56),	-- Simple CAP application
			frip					(57),	-- Frame Relay to IP glue logic
			autif					(58),	-- ALC to TCP/UDP glue logic
			u100					(59),	-- the U100 protocol
			console					(60),	-- TIGER console application
			x2x						(61),	-- X.25 to X.25 transparent application
			mux						(62),	-- Tiger internal multiplexors
			apath					(63),	-- Type A path module
			pad						(64),	-- X.25 PAD (IATA, QLLC, IP)
			dlswCircuit				(65),	-- DLSw (circuit side)
			dlswSession				(66),	-- DLSw (session side)
			matipUser				(67),	-- MATIP (user side)
			matipSession			(68),	-- MATIP (session side)
			pcNic					(69)	-- PCI Tiger to PC IP-DPM channel
			}
		ACCESS		read-write
		STATUS		mandatory
		DESCRIPTION
			"The type of interface, distinguished according to the physical/link
			protocol(s) immediately `below' the network layer in the protocol stack."
		::= { ifEntry 3 }

	ifMtu OBJECT-TYPE
		SYNTAX		INTEGER
		ACCESS		read-write
		STATUS		mandatory
		DESCRIPTION
			"The size of the largest datagram which can be sent/received on the interface,
			specified in octets.  For interfaces that are used for transmitting network datagrams,
			this is the size of the largest network datagram that can be sent on the interface."
		::= { ifEntry 4 }

	ifSpeed OBJECT-TYPE
		SYNTAX		Gauge32
		ACCESS		read-only
		STATUS		mandatory
		DESCRIPTION
			"An estimate of the interface's current bandwidth in bits per second.
			For interfaces which do not vary in bandwidth or for those where no accurate
			estimation can be made, this object should contain the nominal bandwidth."
		::= { ifEntry 5 }

	ifPhysAddress OBJECT-TYPE
		SYNTAX		PhysAddress
		ACCESS		read-write
		STATUS		mandatory
		DESCRIPTION
			"This information is required for configuration only when BOOTP support is enabled
			in the TIGER configuration tool in order to properly create a bootptab record.

			The interface's address at the protocol layer immediately `below' the network
			layer in the protocol stack.  For interfaces which do not have such an address
			(e.g., a serial line), this object should contain an octet string of zero length.
			Although it is defined as a writable variable, TIGER may silently discard that
			information.  If the physical address given does not match the actual address,
			an error message may be shown.

			For Ethernet interfaces on TIGER, the leading 3 bytes should be: 004003.
			For Token Ring Interfaces, the leading 3 bytes should be: 0000F6.

			If you enter only the last 3 bytes of the MAC address, the configuration tool
			will automatically add the leading 3 bytes."
		::= { ifEntry 6 }

	ifAdminStatus OBJECT-TYPE
		SYNTAX		INTEGER {
			up		(1),	-- ready to pass packets
			down	(2),
			testing	(3)		-- in some test mode
			}
		ACCESS		read-write
		STATUS		mandatory
		DESCRIPTION
			"The desired state of the interface.
			The testing(3) state indicates that no operational packets can be passed."
		::= { ifEntry 7 }

	ifOperStatus OBJECT-TYPE
		SYNTAX		INTEGER {
			testing				(1),
			up					(2),
			down-L2				(3),
			down-modem			(4),
			down-other			(5),
			up-blocktx			(6),
			up-preventrx		(7),
			up-bothflow			(8),
			cts-failure			(9),
			dcd-failure			(10),
			hardware-failure	(11),
			up-isolated			(12)
			}
		ACCESS		read-only
		STATUS		mandatory
		DESCRIPTION
			"The current operational state of the interface.
			testing				- indicates that no operational packets can be passed.
			up					- normal operation
			down-L2				- down due to a level 2 failure
			dowm-modem			- down due to modem control signals
								- (Token Ring - transmitting beacon frames or rx beaconing, signal loss)
			down-other			- down for some other reason
								- (Token Ring - no status yet received, i.e. unknown status)
			up-blocktx			- normal; but Tiger received a flow control signal preventing it from sending data
			up-preventrx		- normal; but Tiger sent a flow control signal to stop the other end from sending data
			up-bothflow			- normal; but Tiger	received a flow control signal preventing it from sending data AND
													sent a flow control signal to stop the other end from sending data
			cts-failure			- RTS was requested, but CTS never came (probably detected via poll timeout)
			dcd-failure			- DCD dropped while receiving data, OR
								- unable to poll because other ends is still transmitting (polled protocols only).
			hardware-failure	- missing FPGA
								  (Token Ring: PCMCIA card missing)
			up-isolated			- (Token Ring: Single station on the ring)"
		::= { ifEntry 8 }

	ifLastChange OBJECT-TYPE
		SYNTAX		TimeTicks
		ACCESS		read-only
		STATUS		mandatory
		DESCRIPTION
			"The value of sysUpTime at the time the interface entered its current
			operational state.  If the current state was entered prior to the last
			re-initialization of the local network management subsystem, then this
			object contains a zero value."
		::= { ifEntry 9 }

	ifInOctets OBJECT-TYPE
		SYNTAX		Counter
		ACCESS		read-only
		STATUS		mandatory
		DESCRIPTION
			"The total number of octets received on the interface, including framing characters."
		::= { ifEntry 10 }

	ifInUcastPkts OBJECT-TYPE
		SYNTAX		Counter
		ACCESS		read-only
		STATUS		mandatory
		DESCRIPTION
			"The number of subnetwork-unicast packets delivered to a higher-layer protocol."
		::= { ifEntry 11 }

	ifInNUcastPkts OBJECT-TYPE
		SYNTAX		Counter
		ACCESS		read-only
		STATUS		mandatory
		DESCRIPTION
			"The number of non-unicast (i.e., subnetwork-broadcast or subnetwork-multicast)
			packets delivered to a higher-layer protocol."
		::= { ifEntry 12 }

	ifInDiscards OBJECT-TYPE
		SYNTAX		Counter
		ACCESS		read-only
		STATUS		mandatory
		DESCRIPTION
			"The number of inbound packets which were chosen to be discarded even though no
			errors had been detected to prevent their being deliverable to a higher-layer protocol.
			One possible reason for discarding such a packet could be to free up buffer space."
		::= { ifEntry 13 }

	ifInErrors OBJECT-TYPE
		SYNTAX		Counter
		ACCESS		read-only
		STATUS		mandatory
		DESCRIPTION
			"The number of inbound packets that contained errors preventing them from being
			deliverable to a higher-layer protocol."
		::= { ifEntry 14 }

	ifInUnknownProtos OBJECT-TYPE
		SYNTAX		Counter
		ACCESS		read-only
		STATUS		mandatory
		DESCRIPTION
			"The number of packets received via the interface which were discarded because
			of an unknown or unsupported protocol."
		::= { ifEntry 15 }

	ifOutOctets OBJECT-TYPE
		SYNTAX		Counter
		ACCESS		read-only
		STATUS		mandatory
		DESCRIPTION
			"The total number of octets transmitted out of the interface, including framing characters."
		::= { ifEntry 16 }

	ifOutUcastPkts OBJECT-TYPE
		SYNTAX		Counter
		ACCESS		read-only
		STATUS		mandatory
		DESCRIPTION
			"The total number of packets that higher-level protocols requested be transmitted
			to a subnetwork-unicast address, including those that were discarded or not sent."
		::= { ifEntry 17 }

	ifOutNUcastPkts OBJECT-TYPE
		SYNTAX		Counter
		ACCESS		read-only
		STATUS		mandatory
		DESCRIPTION
			"The total number of packets that higher-level protocols requested be transmitted
			to a non-unicast (i.e., a subnetwork-broadcast or subnetwork-multicast) address,
			including those that were discarded or not sent."
		::= { ifEntry 18 }

	ifOutDiscards OBJECT-TYPE
		SYNTAX		Counter
		ACCESS		read-only
		STATUS		mandatory
		DESCRIPTION
			"The number of outbound packets which were chosen to be discarded even though no
			errors had been detected to prevent their being transmitted.  One possible reason
			for discarding such a packet could be to free up buffer space."
		::= { ifEntry 19 }

	ifOutErrors OBJECT-TYPE
		SYNTAX		Counter
		ACCESS		read-only
		STATUS		mandatory
		DESCRIPTION
			"The number of outbound packets that could not be transmitted because of errors."
		::= { ifEntry 20 }

	ifOutQLen OBJECT-TYPE
		SYNTAX		Gauge32
		ACCESS		read-only
		STATUS		mandatory
		DESCRIPTION
			"The length of the output packet queue (in packets)."
		::= { ifEntry 21 }

	ifSpecific OBJECT-TYPE
		SYNTAX		OBJECT IDENTIFIER
		ACCESS		read-only
		STATUS		mandatory
		DESCRIPTION
			"A reference to MIB definitions specific to the particular media being used to
			realize the interface.  For example, if the interface is realized by an ethernet,
			then the value of this object refers to a document defining objects specific to
			ethernet.  If this information is not present, its value should be set to the OBJECT
			IDENTIFIER { 0 0 }, which is a syntatically valid object identifier, and any conformant
			implementation of ASN.1 and BER must be able to generate and recognize this value."
		DEFVAL		{ defaultOID }
		::= { ifEntry 22 }

	ifInMulticastPkts OBJECT-TYPE
		SYNTAX		Counter
		ACCESS		read-only
		STATUS		mandatory
		DESCRIPTION
			"The number of packets, delivered by this sub-layer to a higher (sub-)layer,
			which were addressed to a multicast address at this sub-layer.
			For a MAC layer protocol, this includes both Group and Functional addresses."
		::= { ifEntry 23 }

	ifInBroadcastPkts OBJECT-TYPE
		SYNTAX		Counter
		ACCESS		read-only
		STATUS		mandatory
		DESCRIPTION
			"The number of packets, delivered by this sub-layer to a higher (sub-)layer,
			which were addressed to a broadcast address at this sub-layer."
		::= { ifEntry 24 }

	ifOutMulticastPkts OBJECT-TYPE
		SYNTAX		Counter
		ACCESS		read-only
		STATUS		mandatory
		DESCRIPTION
			"The total number of packets that higher-level protocols requested be transmitted,
			and which were addressed to a multicast address at this sub-layer, including those
			that were discarded or not sent.  For a MAC layer protocol, this includes both
			Group and Functional addresses."
		::= { ifEntry 25 }

	ifOutBroadcastPkts OBJECT-TYPE
		SYNTAX		Counter
		ACCESS		read-only
		STATUS		mandatory
		DESCRIPTION
			"The total number of packets that higher-level protocols requested be transmitted,
			and which were addressed to a broadcast address at this sub-layer, including those
			that were discarded or not sent."
		::= { ifEntry 26 }

	ifStateChangeTrapEnable  OBJECT-TYPE
		SYNTAX		INTEGER {
			disabled	(1),
			enabled		(2)
			}
		ACCESS		read-write
		STATUS		mandatory
		DESCRIPTION
			"Indicates whether ifStateChange traps should be generated for this interface.

			By default, this object should have the value enabled for interfaces which do
			not operate on 'top' of any other interface (as defined in the ifStackTable),
			and disabled otherwise."
		DEFVAL		{ enabled }
		::= { ifEntry 27 }

	ifConnectorPresent	OBJECT-TYPE
		SYNTAX		TruthValue
		ACCESS		read-only
		STATUS		mandatory
		DESCRIPTION
			"This object has the value 'true(1)' if the interface sublayer has a physical
			connector and the value 'false(2)' otherwise."
		::= { ifEntry 28 }

	ifClearStats OBJECT-TYPE
		SYNTAX		INTEGER {
			clear				(1),
			cleared				(2),
			cleared-confirmed	(3)
			}
		ACCESS		read-write
		STATUS		mandatory
		DESCRIPTION
			"When set to 'clear' all of the interface statistics are cleared to zero.
			It will also force a clearing of all protocol, and 'user' statistics that
			are related to this interface.

			Normally, this object will be adjusted if it is associated with physical ports (i.e. 1 - 8)

			When read, this object should always return 'cleared' indicating that
			the clear operation took place.  Should the operation be defered, the
			value will remain as 'clear' until such time as:

				1/ all of the statistics have actually been zeroed, and
				2/ ifClearStatsTime has been updated with the correct time.

			Should an NMS read the object and receive a 'cleared' indication, the SNMP agent
			will set this object to 'cleared-confirmed'.  This aids the NMS in determining
			whether or not the agent successfully received subsequent clear request.

			Normal operation would be:

			NMS								Agent

			set 'clear'			-->			set to 'clear,' perform clearing
													.
			read				-->					.
			'clear'				<--					.
											clearing complete, set to 'cleared'
													.
			read				-->					.
			'cleared'			<--			set to 'cleared-confirmed'
													.
			read				-->					.
			'cleared-confirmed'	<--					.


			Rules:
				1/ NMS must read 'cleared-confirmed' BEFORE attempting
				   to set 'clear'.
				2/ After setting 'clear' the NMS must read 'cleared'.
				   then the NMS must read 'cleared-confirmed'.
			In this manner, if a 'clear' command was missed by the agent,
			the variable will still be set to either 'cleared' or 'cleared-confirmed'."
		DEFVAL	{ cleared }
		::= { ifEntry 29 }

	ifClearStatsTime OBJECT-TYPE
		SYNTAX		TimeTicks
		ACCESS		read-only
		STATUS		mandatory
		DESCRIPTION
			"The number of ticks when the Tiger last received a ifClearStats command."
		::= { ifEntry 30 }

	ifErrorRateTrapEnable	OBJECT-TYPE
		SYNTAX		INTEGER {
			disabled	(1),
			enabled		(2)
			}
		ACCESS		read-write
		STATUS		mandatory
		DESCRIPTION
			"Indicates whether ifErrorRate traps should be generated for this interface.
			In addition to enabling the trap via this object, thresholds must also be set."
		DEFVAL		{ enabled }
		::= { ifEntry 31 }

	ifErrorRateInterval OBJECT-TYPE
		SYNTAX		INTEGER
		ACCESS		read-write
		STATUS		mandatory
		DESCRIPTION
			"The amount of time over which any error rate is calculated."
		DEFVAL		{ 10 }
		::= { ifEntry 32 }

	ifErrorInLowThreshold OBJECT-TYPE
		SYNTAX		INTEGER
		ACCESS		read-write
		STATUS		mandatory
		DESCRIPTION
			"If the number of input errors drops below the low water mark (threshold)
			over the interval defined by 'ifErrorRateInterval' then a trap may be
			generated if enabled by 'ifErrorRateTrapEnable'.

			What errors constitute as input errors is dependant on the interface being monitored."
		DEFVAL		{ 0 }
		::= { ifEntry 33 }

	ifErrorInHighThreshold OBJECT-TYPE
		SYNTAX		INTEGER
		ACCESS		read-write
		STATUS		mandatory
		DESCRIPTION
			"If the Low water mark (threshold) has been reached, this defines the other
			end of the hysterisis curve, when more than 'ifErrorInHighThreshold' number
			of errors have occured over the measurement interval of 'ifErrorRateInterval'
			If this value is reached, then a trap may be generated if enabled by 
			'ifErrorRateTrapEnable'.

			ifErrorInLowThreshold <= ifErrorInHighThreshold
			What errors constitute as input errors is dependant on the interface being monitored."
		DEFVAL		{ 20 }
		::= { ifEntry 34 }

	ifErrorOutLowThreshold OBJECT-TYPE
		SYNTAX		INTEGER
		ACCESS		read-write
		STATUS		mandatory
		DESCRIPTION
			"If the number of output errors drops below the low water mark (threshold)
			over the interval defined by 'ifErrorRateInterval' then a trap may be
			generated if enabled by 'ifErrorRateTrapEnable'.

			ifErrorOutLowThreshold <= ifErrorOutHighThreshold
			What errors constitute as output errors is dependant on the interface being monitored."
		DEFVAL		{ 0 }
		::= { ifEntry 35 }

	ifErrorOutHighThreshold OBJECT-TYPE
		SYNTAX		INTEGER
		ACCESS		read-write
		STATUS		mandatory
		DESCRIPTION
			"If the Low water mark (threshold) has been reached, this defines the other
			end of the hysterisis curve, when more than 'ifErrorOutHighThreshold' number
			of errors have occured over the measurement interval of 'ifErrorRateInterval'
			If this value is reached, then a trap may be generated if enabled by
			'ifErrorRateTrapEnable'.

			ifErrorOutLowThreshold <= ifErrorOutHighThreshold
			What errors constitute as output errors is dependant on the interface being monitored."
		DEFVAL		{ 20 }
		::= { ifEntry 36 }

	ifErrType OBJECT-TYPE
		SYNTAX		INTEGER {
		in-alarm		(1),
		in-recovery		(2),
		out-alarm		(3),
		out-recovery	(4)
		}
	ACCESS		read-only
	STATUS		mandatory
	DESCRIPTION
		"Informs the NMS of the reason for the ifErrorRate trap that was received.
		When read asynchronously, it also indicates the last known state of this interface entry."
	::= { ifEntry 37 }

	-- the IP group

	-- Implementation of the IP group is current for all
	-- systems.

	ipForwarding OBJECT-TYPE
		SYNTAX		INTEGER {
			forwarding		(1),	-- acting as a gateway
			not-forwarding	(2)		-- NOT acting as a gateway
			}
		ACCESS		read-write
		STATUS		mandatory
		DESCRIPTION
			"The indication of whether this entity is acting
			as an IP gateway in respect to the forwarding of
			datagrams received by, but not addressed to, this
			entity.  IP gateways forward datagrams.  IP hosts
			do not (except those source-routed via the host).

			Note that for some managed nodes, this object may
			take on only a subset of the values possible.
			Accordingly, it is appropriate for an agent to
			return a `badValue' response if a management
			station attempts to change this object to an
			inappropriate value."
		::= { ip 1 }

	ipDefaultTTL OBJECT-TYPE
		SYNTAX		INTEGER (0..1000)
		ACCESS		read-write
		STATUS		mandatory
		DESCRIPTION
			"The default value inserted into the Time-To-Live
			field of the IP header of datagrams originated at
			this entity, whenever a TTL value is not supplied
			by the transport layer protocol."
		::= { ip 2 }

	ipInReceives OBJECT-TYPE
		SYNTAX		Counter
		ACCESS		read-only
		STATUS		mandatory
		DESCRIPTION
			"The total number of input datagrams received from
			interfaces, including those received in error."
		::= { ip 3 }

	ipInHdrErrors OBJECT-TYPE
		SYNTAX		Counter
		ACCESS		read-only
		STATUS		mandatory
		DESCRIPTION
			"The number of input datagrams discarded due to
			errors in their IP headers, including bad
			checksums, version number mismatch, other format
			errors, time-to-live exceeded, errors discovered
			in processing their IP options, etc."
		::= { ip 4 }

	ipInAddrErrors OBJECT-TYPE
		SYNTAX		Counter
		ACCESS		read-only
		STATUS		mandatory
		DESCRIPTION
			"The number of input datagrams discarded because
			the IP address in their IP header's destination
			field was not a valid address to be received at
			this entity.  This count includes invalid
			addresses (e.g., 0.0.0.0) and addresses of
			unsupported Classes (e.g., Class E).  For entities
			which are not IP Gateways and therefore do not
			forward datagrams, this counter includes datagrams
			discarded because the destination address was not
			a local address."
		::= { ip 5 }

	ipForwDatagrams OBJECT-TYPE
		SYNTAX		Counter
		ACCESS		read-only
		STATUS		mandatory
		DESCRIPTION
			"The number of input datagrams for which this
			entity was not their final IP destination, as a
			result of which an attempt was made to find a
			route to forward them to that final destination.
			In entities which do not act as IP Gateways, this
			counter will include only those packets which were
			Source-Routed via this entity, and the Source-
			Route option processing was successful."
		::= { ip 6 }

	ipInUnknownProtos OBJECT-TYPE
		SYNTAX		Counter
		ACCESS		read-only
		STATUS		mandatory
		DESCRIPTION
			"The number of locally-addressed datagrams
			received successfully but discarded because of an
			unknown or unsupported protocol."
		::= { ip 7 }

	ipInDiscards OBJECT-TYPE
		SYNTAX		Counter
		ACCESS		read-only
		STATUS		mandatory
		DESCRIPTION
			"The number of input IP datagrams for which no
			problems were encountered to prevent their
			continued processing, but which were discarded
			(e.g., for lack of buffer space).  Note that this
			counter does not include any datagrams discarded
			while awaiting re-assembly."
		::= { ip 8 }

	ipInDelivers OBJECT-TYPE
		SYNTAX		Counter
		ACCESS		read-only
		STATUS		mandatory
		DESCRIPTION
			"The total number of input datagrams successfully
			delivered to IP user-protocols (including ICMP)."
		::= { ip 9 }

	ipOutRequests OBJECT-TYPE
		SYNTAX		Counter
		ACCESS		read-only
		STATUS		mandatory
		DESCRIPTION
			"The total number of IP datagrams which local IP
			user-protocols (including ICMP) supplied to IP in
			requests for transmission.  Note that this counter
			does not include any datagrams counted in
			ipForwDatagrams."
		::= { ip 10 }

	ipOutDiscards OBJECT-TYPE
		SYNTAX		Counter
		ACCESS		read-only
		STATUS		mandatory
		DESCRIPTION
			"The number of output IP datagrams for which no
			problem was encountered to prevent their
			transmission to their destination, but which were
			discarded (e.g., for lack of buffer space).  Note
			that this counter would include datagrams counted
			in ipForwDatagrams if any such packets met this
			(discretionary) discard criterion."
		::= { ip 11 }

	ipOutNoRoutes OBJECT-TYPE
		SYNTAX		Counter
		ACCESS		read-only
		STATUS		mandatory
		DESCRIPTION
			"The number of IP datagrams discarded because no
			route could be found to transmit them to their
			destination.  Note that this counter includes any
			packets counted in ipForwDatagrams which meet this
			`no-route' criterion.  Note that this includes any
			datagarms which a host cannot route because all of
			its default gateways are down."
		::= { ip 12 }

	ipReasmTimeout OBJECT-TYPE
		SYNTAX		INTEGER (0..3600)
		ACCESS		read-write
		STATUS		mandatory
		DESCRIPTION
			"The maximum number of seconds which received
			fragments are held while they are awaiting
			reassembly at this entity."
		::= { ip 13 }

	ipReasmReqds OBJECT-TYPE
		SYNTAX		Counter
		ACCESS		read-only
		STATUS		mandatory
		DESCRIPTION
			"The number of IP fragments received which needed
			to be reassembled at this entity."
		::= { ip 14 }

	ipReasmOKs OBJECT-TYPE
		SYNTAX		Counter
		ACCESS		read-only
		STATUS		mandatory
		DESCRIPTION
			"The number of IP datagrams successfully re-assembled."
		::= { ip 15 }

	ipReasmFails OBJECT-TYPE
		SYNTAX		Counter
		ACCESS		read-only
		STATUS		mandatory
		DESCRIPTION
			"The number of failures detected by the IP re-
			assembly algorithm (for whatever reason: timed
			out, errors, etc).  Note that this is not
			necessarily a count of discarded IP fragments
			since some algorithms (notably the algorithm in
			RFC 815) can lose track of the number of fragments
			by combining them as they are received."
		::= { ip 16 }

	ipFragOKs OBJECT-TYPE
		SYNTAX		Counter
		ACCESS		read-only
		STATUS		mandatory
		DESCRIPTION
			"The number of IP datagrams that have been
			successfully fragmented at this entity."
		::= { ip 17 }

	ipFragFails OBJECT-TYPE
		SYNTAX		Counter
		ACCESS		read-only
		STATUS		mandatory
		DESCRIPTION
			"The number of IP datagrams that have been
			discarded because they needed to be fragmented at
			this entity but could not be, e.g., because their
			Don't Fragment flag was set."
		::= { ip 18 }

	ipFragCreates OBJECT-TYPE
		SYNTAX		Counter
		ACCESS		read-only
		STATUS		mandatory
		DESCRIPTION
			"The number of IP datagram fragments that have
			been generated as a result of fragmentation at
			this entity."
		::= { ip 19 }

	-- the IP address table

	-- The IP address table contains this entity's IP addressing
	-- information.

	ipAddrTable OBJECT-TYPE
		SYNTAX		SEQUENCE OF IpAddrEntry
		ACCESS		not-accessible
		STATUS		mandatory
		DESCRIPTION
			"The table of addressing information relevant to
			this entity's IP addresses."
		::= { ip 20 }

	ipAddrEntry OBJECT-TYPE
		SYNTAX		IpAddrEntry
		ACCESS		not-accessible
		STATUS		mandatory
		DESCRIPTION
			"The addressing information for one of this
			entity's IP addresses."
		INDEX		{ ipAdEntAddr }
		::= { ipAddrTable 1 }

	IpAddrEntry ::= SEQUENCE {
		ipAdEntAddr				IpAddress,
		ipAdEntIfIndex			INTEGER,
		ipAdEntNetMask			IpAddress,
		ipAdEntBcastAddr		INTEGER,
		ipAdEntReasmMaxSize		INTEGER
		}

	ipAdEntAddr OBJECT-TYPE
		SYNTAX		IpAddress
		ACCESS		read-write
		STATUS		mandatory
		DESCRIPTION
			"The IP address to which this entry's addressing information pertains.
			If this is a PPP port, an IP address of 0.0.0.0 signifies that
			IP address negotiation will occur on this link. If negotiation is enabled,
			the net mask will be forced to a correct value that is appropriate for that
			class of address."
		::= { ipAddrEntry 1 }

	ipAdEntIfIndex OBJECT-TYPE
		SYNTAX		INTEGER (1..1000)
		ACCESS		read-write
		STATUS		mandatory
		DESCRIPTION
			"The index value which uniquely identifies the
			interface to which this entry is applicable.  The
			interface identified by a particular value of this
			index is the same interface as identified by the
			same value of ifIndex."
		::= { ipAddrEntry 2 }

	ipAdEntNetMask OBJECT-TYPE
		SYNTAX		IpAddress
		ACCESS		read-write
		STATUS		mandatory
		DESCRIPTION
			"The subnet mask associated with the IP address of
			this entry.  The value of the mask is an IP
			address with all the network bits set to 1 and all
			the hosts bits set to 0."
		::= { ipAddrEntry 3 }

	ipAdEntBcastAddr OBJECT-TYPE
		SYNTAX		INTEGER (0..1)
		ACCESS		read-write
		STATUS		mandatory
		DESCRIPTION
			"The value of the least-significant bit in the IP
			broadcast address used for sending datagrams on
			the (logical) interface associated with the IP
			address of this entry.  For example, when the
			Internet standard all-ones broadcast address is
			used, the value will be 1.  This value applies to
			both the subnet and network broadcasts addresses
			used by the entity on this (logical) interface."
		::= { ipAddrEntry 4 }

	ipAdEntReasmMaxSize OBJECT-TYPE
		SYNTAX		INTEGER (0..65535)
		ACCESS		read-write
		STATUS		mandatory
		DESCRIPTION
			"The size of the largest IP datagram which this
			entity can re-assemble from incoming IP fragmented
			datagrams received on this interface."
		::= { ipAddrEntry 5 }

	-- the IP Address Translation table

	-- The IP address translation table contain the IpAddress to
	-- `physical' address equivalences.  Some interfaces do not
	-- use translation tables for determining address
	-- equivalences (e.g., DDN-X.25 has an algorithmic method);
	-- if all interfaces are of this type, then the Address
	-- Translation table is empty, i.e., has zero entries.

	ipNetToMediaTable OBJECT-TYPE
		SYNTAX		SEQUENCE OF IpNetToMediaEntry
		ACCESS		not-accessible
		STATUS		mandatory
		DESCRIPTION
			"The IP Address Translation table used for mapping
			from IP addresses to physical addresses."
		::= { ip 22 }

	ipNetToMediaEntry OBJECT-TYPE
		SYNTAX		IpNetToMediaEntry
		ACCESS		not-accessible
		STATUS		mandatory
		DESCRIPTION
			"Each entry contains one IpAddress to `physical' address equivalence."
		INDEX		{ ipNetToMediaIfIndex, ipNetToMediaNetAddress }
		::= { ipNetToMediaTable 1 }

	IpNetToMediaEntry ::= SEQUENCE {
		ipNetToMediaIfIndex		INTEGER,
		ipNetToMediaPhysAddress	PhysAddress,
		ipNetToMediaNetAddress	IpAddress,
		ipNetToMediaType		INTEGER
		}

	ipNetToMediaIfIndex OBJECT-TYPE
		SYNTAX		INTEGER (1..1000)
		ACCESS		read-write
		STATUS		mandatory
		DESCRIPTION
			"The interface on which this entry's equivalence
			is effective.  The interface identified by a
			particular value of this index is the same
			interface as identified by the same value of ifIndex."
		::= { ipNetToMediaEntry 1 }

	ipNetToMediaPhysAddress OBJECT-TYPE
		SYNTAX		PhysAddress
		ACCESS		read-write
		STATUS		mandatory
		DESCRIPTION
			"The media-dependent `physical' address."
		::= { ipNetToMediaEntry 2 }

	ipNetToMediaNetAddress OBJECT-TYPE
		SYNTAX		IpAddress
		ACCESS		read-write
		STATUS		mandatory
		DESCRIPTION
			"The IpAddress corresponding to the media-dependent `physical' address."
		::= { ipNetToMediaEntry 3 }

	ipNetToMediaType OBJECT-TYPE
		SYNTAX		INTEGER {
			other	(1),	-- none of the following
			invalid	(2),	-- an invalidated mapping
			dynamic	(3),
			static	(4)
			}
		ACCESS		read-write
		STATUS		mandatory
		DESCRIPTION
			"The type of mapping.

			Setting this object to the value invalid(2) has
			the effect of invalidating the corresponding entry
			in the ipNetToMediaTable.  That is, it effectively
			dissasociates the interface identified with said
			entry from the mapping identified with said entry.
			It is an implementation-specific matter as to
			whether the agent removes an invalidated entry
			from the table.  Accordingly, management stations
			must be prepared to receive tabular information
			from agents that corresponds to entries not
			currently in use.  Proper interpretation of such
			entries requires examination of the relevant
			ipNetToMediaType object."
		::= { ipNetToMediaEntry 4 }


	-- additional IP objects

	ipRoutingDiscards OBJECT-TYPE
		SYNTAX		Counter
		ACCESS		read-only
		STATUS		mandatory
		DESCRIPTION
			"The number of routing entries which were chosen
			to be discarded even though they are valid.  One
			possible reason for discarding such an entry could
			be to free-up buffer space for other routing
			entries."
		::= { ip 23 }

	ipClearStats OBJECT-TYPE
		SYNTAX		INTEGER {
			clear				(1),
			cleared				(2),
			cleared-confirmed	(3)
			}
		ACCESS		read-write
		STATUS		mandatory
		DESCRIPTION
			"When set to 'clear' all of the ip/icmp/tcp/udp/ppp/snmp statistics
			are cleared to zero.
			When read, this object should always return 'cleared' indicating that
			the clear operation took place.  Should the operation be defered, the
			value will remain as 'clear' until such time as:

				1/ all of the statistics have actually been zeroed, and
				2/ ipClearStatsTime has been updated with the correct time.

			Should an NMS read the object and receive a 'cleared' indication, the SNMP agent
			will set this object to 'cleared-confirmed'.  This aids the NMS in determining
			whether or not the agent successfully received subsequent clear request.

			Normal operation would be:

			NMS								Agent

			set 'clear'			-->			set to 'clear,' perform clearing
													.
			read				-->					.
			'clear'				<--					.
											clearing complete, set to 'cleared'
													.
			read				-->					.
			'cleared'			<--			set to 'cleared-confirmed'
													.
			read				-->					.
			'cleared-confirmed'	<--					.


			Rules:
				1/ NMS must read 'cleared-confirmed' BEFORE attempting
				   to set 'clear'.
				2/ After setting 'clear' the NMS must read 'cleared'.
				   then the NMS must read 'cleared-confirmed'.
			In this manner, if a 'clear' command was missed by the agent,
			the variable will still be set to either 'cleared' or 'cleared-confirmed'."
		DEFVAL	{ cleared }
		::= { ip 24 }

	ipClearStatsTime OBJECT-TYPE
		SYNTAX		TimeTicks
		ACCESS		read-only
		STATUS		mandatory
		DESCRIPTION
			"The number of ticks when the Tiger last received a ipClearStats command."
		::= { ip 25 }

	ipForward		OBJECT IDENTIFIER ::= { ip 26 }

	ipForwardNumber OBJECT-TYPE
		SYNTAX		Gauge
		ACCESS		read-only
		STATUS		mandatory
		DESCRIPTION
			"The number of current ipForwardTable entries that are not invalid."
		::= { ipForward 1 }

	 --  IP Forwarding Table

	 --  The IP Forwarding Table obsoletes and replaces the ipRoute
	 --  Table current in MIB-I and MIB-II.  It adds knowledge of
	 --  the autonomous system of the next hop, multiple next hop
	 --  support, and policy routing support.

	ipForwardTable OBJECT-TYPE
		SYNTAX		SEQUENCE OF IpForwardEntry
		ACCESS		not-accessible
		STATUS		mandatory
		DESCRIPTION
			"This entity's IP Routing table."
		REFERENCE
			"RFC 1213 Section 6.6, The IP Group"
		::= { ipForward 2 }

	ipForwardEntry OBJECT-TYPE
		SYNTAX		IpForwardEntry
		ACCESS		not-accessible
		STATUS		mandatory
		DESCRIPTION
			"A particular route to a particular destination, under a particular policy."
		INDEX {
			ipForwardDest,
--			ipForwardProto,
--			ipForwardPolicy,
			ipForwardNextHop
			}
		::= { ipForwardTable 1 }

	IpForwardEntry ::= SEQUENCE {
		ipForwardDest		IpAddress,
		ipForwardMask		IpAddress,
--		ipForwardPolicy		INTEGER,
		ipForwardNextHop	IpAddress,
		ipForwardIfIndex	INTEGER,
--		ipForwardType		INTEGER,
--		ipForwardProto		INTEGER,
--		ipForwardAge		INTEGER,
--		ipForwardInfo		OBJECT IDENTIFIER,
--		ipForwardNextHopAS	INTEGER,
		ipForwardMetric1	INTEGER,
		ipForwardMetric2	INTEGER,
		ipForwardMetric3	INTEGER,
		ipForwardMetric4	INTEGER,
		ipForwardMetric5	INTEGER
		}

	ipForwardDest OBJECT-TYPE
		SYNTAX		IpAddress
		ACCESS		read-write
		STATUS		mandatory
		DESCRIPTION
			"The destination IP address of this route.	An entry
			with a value of 0.0.0.0 is considered a default route.

			This object may not take a Multicast (Class D) address value.

			Any assignment (implicit or otherwise) of an instance of this
			object to a value x must be rejected if the bitwise logical-AND
			of x with the value of the corresponding instance of the
			ipForwardMask object is not equal to x."
		::= { ipForwardEntry 1 }

	ipForwardMask OBJECT-TYPE
		SYNTAX		IpAddress
		ACCESS		read-write
		STATUS		mandatory
		DESCRIPTION
			"Indicate the mask to be logical-ANDed with the destination
			address before being compared to the value in the ipForwardDest
			field.	For those systems that do not support arbitrary subnet
			masks, an agent constructs the value of the ipForwardMask by
			reference to the IP Address Class.

			Any assignment (implicit or otherwise) of an instance of this
			object to a value x must be rejected if the bitwise logical-AND
			of x with the value of the corresponding instance of the
			ipForwardDest object is not equal to ipForwardDest."
		DEFVAL		{ '00000000'h }		-- 0.0.0.0
		::= { ipForwardEntry 2 }

	 -- The following convention is included for specification
	 -- of TOS Field contents. At this time, the Host Requirements
	 -- and the Router Requirements documents disagree on the width
	 -- of the TOS field.  This mapping describes the Router
	 -- Requirements mapping, and leaves room to widen the TOS field
	 -- without impact to fielded systems.

--	ipForwardPolicy OBJECT-TYPE
--		SYNTAX		INTEGER
--		ACCESS		read-only
--		STATUS		mandatory
--		DESCRIPTION
--			"The general set of conditions that would cause the selection of
--			one multipath route (set of next hops for a given destination)
--			is referred to as 'policy'.
--
--			Unless the mechanism indicated by ipForwardProto specifies
--			otherwise, the policy specifier is the IP TOS Field.  The
--			encoding of IP TOS is as specified by the following convention.
--			Zero indicates the default path if no more specific policy applies.
--
--		+-----+-----+-----+-----+-----+-----+-----+-----+
--		|				  |					|	  |
--		|	PRECEDENCE	  |	TYPE OF SERVICE	|  0  |
--		|				  |					|	  |
--		+-----+-----+-----+-----+-----+-----+-----+-----+
--
--				 IP TOS				IP TOS
--			Field	  Policy	Field	  Policy
--			Contents	Code	Contents	Code
--			0 0 0 0  ==>   0	0 0 0 1  ==>   2
--			0 0 1 0  ==>   4	0 0 1 1  ==>   6
--			0 1 0 0  ==>   8	0 1 0 1  ==>  10
--			0 1 1 0  ==>  12	0 1 1 1  ==>  14
--			1 0 0 0  ==>  16	1 0 0 1  ==>  18
--			1 0 1 0  ==>  20	1 0 1 1  ==>  22
--			1 1 0 0  ==>  24	1 1 0 1  ==>  26
--			1 1 1 0  ==>  28	1 1 1 1  ==>  30
--
--			Protocols defining 'policy' otherwise must either define a set of
--			values which are valid for this object or must implement an integer-
--			instanced policy table for which this object's value acts as an index."
--		::= { ipForwardEntry 3 }
--
	ipForwardNextHop OBJECT-TYPE
		SYNTAX		IpAddress
		ACCESS		read-write
		STATUS		mandatory
		DESCRIPTION
			"On remote routes, the address of the next system
			en route; Otherwise, 0.0.0.0."
		::= { ipForwardEntry 4 }

	ipForwardIfIndex OBJECT-TYPE
		SYNTAX		INTEGER
		ACCESS		read-write
		STATUS		mandatory
		DESCRIPTION
			"The ifIndex value which identifies the local interface through
			which the next hop of this route should be reached."
		DEFVAL		{ 0 }
		::= { ipForwardEntry 5 }

--	ipForwardType OBJECT-TYPE
--		SYNTAX		INTEGER {
--			other	(1),	;; not specified by this MIB
--			invalid	(2),	;; logically deleted
--			local	(3),	;; local interface
--			remote	(4)		;; remote destination
--			}
--		ACCESS		read-write
--		STATUS		mandatory
--		DESCRIPTION
--			"The type of route.  Note that local(3) refers to a route
--			for which the next hop is the final destination; remote(4)
--			refers to a route for which the next hop is not the final
--			destination.
--
--			Setting this object to the value invalid(2) has the effect
--			of invalidating the corresponding entry in the ipForwardTable
--			object.	That is, it effectively disassociates the destination
--			identified with said entry from the route identified with said
--			entry.	It is an implementation-specific matter as to whether
--			the agent removes an invalidated entry from the table.
--			Accordingly, management stations must be prepared to receive
--			tabular information from agents that corresponds to entries
--			not currently in use.  Proper interpretation of such entries
--			requires examination of the relevant ipForwardType object."
--		DEFVAL		{ invalid }
--		::= { ipForwardEntry 6 }
--
--	ipForwardProto OBJECT-TYPE
--		SYNTAX		INTEGER {
--			other		(1),	;; not specified
--			local		(2),	;; local interface
--			netmgmt		(3),	;; static route
--			icmp		(4),	;; result of ICMP Redirect
--
--			;; the following are all dynamic routing protocols
--
--			egp			(5),	;; Exterior Gateway Protocol
--			ggp			(6),	;; Gateway-Gateway Protocol
--			hello		(7),	;; FuzzBall HelloSpeak
--			rip			(8),	;; Berkeley RIP or RIP-II
--			is-is		(9),	;; Dual IS-IS
--			es-is		(10),	;; ISO 9542
--			ciscoIgrp	(11),	;; Cisco IGRP
--			bbnSpfIgp	(12),	;; BBN SPF IGP
--			ospf		(13),	;; Open Shortest Path First
--			bgp			(14),	;; Border Gateway Protocol
--			idpr		(15)	;; InterDomain Policy Routing
--			}
--		ACCESS		read-only
--		STATUS		mandatory
--		DESCRIPTION
--			"The routing mechanism via which this route was learned.
--			Inclusion of values for gateway routing protocols is not
--			intended to imply that hosts should support those protocols."
--		::= { ipForwardEntry 7 }
--
--	ipForwardAge OBJECT-TYPE
--		SYNTAX		INTEGER
--		ACCESS		read-only
--		STATUS		mandatory
--		DESCRIPTION
--			"The number of seconds since this route was last updated or
--			otherwise determined to be correct.  Note that no semantics
--			of `too old' can be implied except through knowledge of the
--			routing protocol by which the route was learned."
--		DEFVAL		{ 0 }
--		::= { ipForwardEntry 8 }
--
--	ipForwardInfo OBJECT-TYPE
--		SYNTAX		OBJECT IDENTIFIER
--		ACCESS		read-write
--		STATUS		mandatory
--		DESCRIPTION
--			"A reference to MIB definitions specific to the particular routing
--			protocol which is responsible for this route, as determined by the
--			value specified in the route's ipForwardProto value.  If this
--			information is not present, its value should be set to the OBJECT
--			IDENTIFIER { 0 0 }, which is a syntactically valid object identifier,
--			and any implementation conforming to ASN.1 and the Basic Encoding
--			Rules must be able to generate and recognize this value."
--		DEFVAL		{ { 0 0 } }		;; 0.0
--		::= { ipForwardEntry 9 }
--
--	ipForwardNextHopAS OBJECT-TYPE
--		SYNTAX		INTEGER
--		ACCESS		read-write
--		STATUS		mandatory
--		DESCRIPTION
--			"The Autonomous System Number of the Next Hop.  When this is unknown
--			or not relevant to the protocol indicated by ipForwardProto, zero."
--		DEFVAL		{ 0 }
--		::= { ipForwardEntry 10 }

	ipForwardMetric1 OBJECT-TYPE
		SYNTAX		INTEGER
		ACCESS		read-write
		STATUS		mandatory
		DESCRIPTION
			"The primary routing metric for this route.

			The semantics of this metric are determined by the routing-protocol specified
			in the route's ipForwardProto value.  For static routing tables, Metric1 is
			the default 'cost' (1-15) of the route when it is in the up condition.  This
			is compared to other possible routes for the same destination, to state the
			preferred path.  If this metric is not used, its value should be set to -1."
		DEFVAL		{ -1 }
		::= { ipForwardEntry 11 }

	ipForwardMetric2 OBJECT-TYPE
		SYNTAX		INTEGER
		ACCESS		read-write
		STATUS		mandatory
		DESCRIPTION
			"An alternate routing metric for this route.

			The semantics of this metric are determined by the routing-protocol specified
			in the route's ipForwardProto value.  For static routing tables, Metric1 is
			the default 'cost' (1-15) of the route when it is in the up condition.  This
			is compared to other possible routes for the same destination, to state the
			preferred path.  If this metric is not used, its value should be set to -1."
		DEFVAL		{ -1 }
		::= { ipForwardEntry 12 }

	ipForwardMetric3 OBJECT-TYPE
		SYNTAX		INTEGER
		ACCESS		read-write
		STATUS		mandatory
		DESCRIPTION
			"An alternate routing metric for this route.

			The semantics of this metric are determined by the routing-protocol specified
			in the route's ipForwardProto value.  For static routing tables, Metric1 is
			the default 'cost' (1-15) of the route when it is in the up condition.  This
			is compared to other possible routes for the same destination, to state the
			preferred path.  If this metric is not used, its value should be set to -1."
		DEFVAL		{ -1 }
		::= { ipForwardEntry 13 }

	ipForwardMetric4 OBJECT-TYPE
		SYNTAX		INTEGER
		ACCESS		read-write
		STATUS		mandatory
		DESCRIPTION
			"An alternate routing metric for this route.

			The semantics of this metric are determined by the routing-protocol specified
			in the route's ipForwardProto value.  For static routing tables, Metric1 is
			the default 'cost' (1-15) of the route when it is in the up condition.  This
			is compared to other possible routes for the same destination, to state the
			preferred path.  If this metric is not used, its value should be set to -1."
		DEFVAL		{ -1 }
		::= { ipForwardEntry 14 }

	ipForwardMetric5 OBJECT-TYPE
		SYNTAX		INTEGER
		ACCESS		read-write
		STATUS		mandatory
		DESCRIPTION
			"An alternate routing metric for this route.

			The semantics of this metric are determined by the routing-protocol specified
			in the route's ipForwardProto value.  For static routing tables, Metric1 is
			the default 'cost' (1-15) of the route when it is in the up condition.  This
			is compared to other possible routes for the same destination, to state the
			preferred path.  If this metric is not used, its value should be set to -1."
		DEFVAL		{ -1 }
		::= { ipForwardEntry 15 }

    ipForwardTrapControl OBJECT-TYPE
        SYNTAX      INTEGER {
            disabled    (1),
            enabled     (2)
            }
        ACCESS      read-write
        STATUS      mandatory
        DESCRIPTION
            "If enabled, it allows the system to generate ipForward traps,
            when the routing table changes."
        DEFVAL      { enabled }
        ::= { ipForward 3 }

	ipForwardTrapReason OBJECT-TYPE
		SYNTAX		INTEGER {
			none	(1),
			add		(2),
			delete	(3),
			modify	(4)
			}
		ACCESS		read-only
		STATUS		mandatory
		DESCRIPTION
			"The reason that the ipRouteChange trap was generated.

					add			- the entry was added.
					delete		- the entry was removed.
					modified	- the entry was modified.  The metric probably changed value
									due to a link going up or down)."
		DEFVAL		{ none }
		::= { ipForward 4 }

	-- the ICMP group

	-- Implementation of the ICMP group is current for all
	-- systems.

	icmpInMsgs OBJECT-TYPE
		SYNTAX		Counter
		ACCESS		read-only
		STATUS		mandatory
		DESCRIPTION
			"The total number of ICMP messages which the
			entity received.  Note that this counter includes
			all those counted by icmpInErrors."
		::= { icmp 1 }

	icmpInErrors OBJECT-TYPE
		SYNTAX		Counter
		ACCESS		read-only
		STATUS		mandatory
		DESCRIPTION
			"The number of ICMP messages which the entity
			received but determined as having ICMP-specific
			errors (bad ICMP checksums, bad length, etc.)."
		::= { icmp 2 }

	icmpInDestUnreachs OBJECT-TYPE
		SYNTAX		Counter
		ACCESS		read-only
		STATUS		mandatory
		DESCRIPTION
			"The number of ICMP Destination Unreachable messages received."
		::= { icmp 3 }

	icmpInTimeExcds OBJECT-TYPE
		SYNTAX		Counter
		ACCESS		read-only
		STATUS		mandatory
		DESCRIPTION
			"The number of ICMP Time Exceeded messages received."
		::= { icmp 4 }

	icmpInParmProbs OBJECT-TYPE
		SYNTAX		Counter
		ACCESS		read-only
		STATUS		mandatory
		DESCRIPTION
			"The number of ICMP Parameter Problem messages received."
		::= { icmp 5 }

	icmpInSrcQuenchs OBJECT-TYPE
		SYNTAX		Counter
		ACCESS		read-only
		STATUS		mandatory
		DESCRIPTION
			"The number of ICMP Source Quench messages received."
		::= { icmp 6 }

	icmpInRedirects OBJECT-TYPE
		SYNTAX		Counter
		ACCESS		read-only
		STATUS		mandatory
		DESCRIPTION
			"The number of ICMP Redirect messages received."
		::= { icmp 7 }

	icmpInEchos OBJECT-TYPE
		SYNTAX		Counter
		ACCESS		read-only
		STATUS		mandatory
		DESCRIPTION
			"The number of ICMP Echo (request) messages received."
		::= { icmp 8 }

	icmpInEchoReps OBJECT-TYPE
		SYNTAX		Counter
		ACCESS		read-only
		STATUS		mandatory
		DESCRIPTION
			"The number of ICMP Echo Reply messages received."
		::= { icmp 9 }

	icmpInTimestamps OBJECT-TYPE
		SYNTAX		Counter
		ACCESS		read-only
		STATUS		mandatory
		DESCRIPTION
			"The number of ICMP Timestamp (request) messages received."
		::= { icmp 10 }

	icmpInTimestampReps OBJECT-TYPE
		SYNTAX		Counter
		ACCESS		read-only
		STATUS		mandatory
		DESCRIPTION
			"The number of ICMP Timestamp Reply messages received."
		::= { icmp 11 }

	icmpInAddrMasks OBJECT-TYPE
		SYNTAX		Counter
		ACCESS		read-only
		STATUS		mandatory
		DESCRIPTION
			"The number of ICMP Address Mask Request messages received."
		::= { icmp 12 }

	icmpInAddrMaskReps OBJECT-TYPE
		SYNTAX		Counter
		ACCESS		read-only
		STATUS		mandatory
		DESCRIPTION
			"The number of ICMP Address Mask Reply messages received."
		::= { icmp 13 }

	icmpOutMsgs OBJECT-TYPE
		SYNTAX		Counter
		ACCESS		read-only
		STATUS		mandatory
		DESCRIPTION
			"The total number of ICMP messages which this
			entity attempted to send.  Note that this counter
			includes all those counted by icmpOutErrors."
		::= { icmp 14 }

	icmpOutErrors OBJECT-TYPE
		SYNTAX		Counter
		ACCESS		read-only
		STATUS		mandatory
		DESCRIPTION
			"The number of ICMP messages which this entity did
			not send due to problems discovered within ICMP
			such as a lack of buffers.  This value should not
			include errors discovered outside the ICMP layer
			such as the inability of IP to route the resultant
			datagram.  In some implementations there may be no
			types of error which contribute to this counter's value."
		::= { icmp 15 }

	icmpOutDestUnreachs OBJECT-TYPE
		SYNTAX		Counter
		ACCESS		read-only
		STATUS		mandatory
		DESCRIPTION
			"The number of ICMP Destination Unreachable messages sent."
		::= { icmp 16 }

	icmpOutTimeExcds OBJECT-TYPE
		SYNTAX		Counter
		ACCESS		read-only
		STATUS		mandatory
		DESCRIPTION
			"The number of ICMP Time Exceeded messages sent."
		::= { icmp 17 }

	icmpOutParmProbs OBJECT-TYPE
		SYNTAX		Counter
		ACCESS		read-only
		STATUS		mandatory
		DESCRIPTION
			"The number of ICMP Parameter Problem messages sent."
		::= { icmp 18 }

	icmpOutSrcQuenchs OBJECT-TYPE
		SYNTAX		Counter
		ACCESS		read-only
		STATUS		mandatory
		DESCRIPTION
			"The number of ICMP Source Quench messages sent."
		::= { icmp 19 }

	icmpOutRedirects OBJECT-TYPE
		SYNTAX		Counter
		ACCESS		read-only
		STATUS		mandatory
		DESCRIPTION
			"The number of ICMP Redirect messages sent.  For a
			host, this object will always be zero, since hosts
			do not send redirects."
		::= { icmp 20 }

	icmpOutEchos OBJECT-TYPE
		SYNTAX		Counter
		ACCESS		read-only
		STATUS		mandatory
		DESCRIPTION
			"The number of ICMP Echo (request) messages sent."
		::= { icmp 21 }

	icmpOutEchoReps OBJECT-TYPE
		SYNTAX		Counter
		ACCESS		read-only
		STATUS		mandatory
		DESCRIPTION
			"The number of ICMP Echo Reply messages sent."
		::= { icmp 22 }

	icmpOutTimestamps OBJECT-TYPE
		SYNTAX		Counter
		ACCESS		read-only
		STATUS		mandatory
		DESCRIPTION
			"The number of ICMP Timestamp (request) messages sent."
		::= { icmp 23 }

	icmpOutTimestampReps OBJECT-TYPE
		SYNTAX		Counter
		ACCESS		read-only
		STATUS		mandatory
		DESCRIPTION
			"The number of ICMP Timestamp Reply messages sent."
		::= { icmp 24 }

	icmpOutAddrMasks OBJECT-TYPE
		SYNTAX		Counter
		ACCESS		read-only
		STATUS		mandatory
		DESCRIPTION
			"The number of ICMP Address Mask Request messages sent."
		::= { icmp 25 }

	icmpOutAddrMaskReps OBJECT-TYPE
		SYNTAX		Counter
		ACCESS		read-only
		STATUS		mandatory
		DESCRIPTION
			"The number of ICMP Address Mask Reply messages sent."
		::= { icmp 26 }


	-- the TCP group

	-- Implementation of the TCP group is current for all
	-- systems that implement the TCP.

	-- Note that instances of object types that represent
	-- information about a particular TCP connection are
	-- transient; they persist only as long as the connection
	-- in question.

	tcpRtoAlgorithm OBJECT-TYPE
		SYNTAX		INTEGER {
			other		(1),	-- none of the following
			constant	(2),	-- a constant rto
			rsre		(3),	-- MIL-STD-1778, Appendix B
			vanj		(4)		-- Van Jacobson's algorithm [10]
			}
		ACCESS		read-only
		STATUS		mandatory
		DESCRIPTION
			"The algorithm used to determine the timeout value
			used for retransmitting unacknowledged octets."
		::= { tcp 1 }

	tcpRtoMin OBJECT-TYPE
		SYNTAX		INTEGER (0..360000)
		ACCESS		read-only
		STATUS		mandatory
		DESCRIPTION
			"The minimum value permitted by a TCP
			implementation for the retransmission timeout,
			measured in milliseconds.  More refined semantics
			for objects of this type depend upon the algorithm
			used to determine the retransmission timeout.  In
			particular, when the timeout algorithm is rsre(3),
			an object of this type has the semantics of the
			LBOUND quantity described in RFC 793.
			UNITS: milliseconds"
		::= { tcp 2 }

	tcpRtoMax OBJECT-TYPE
		SYNTAX		INTEGER (0..360000)
		ACCESS		read-only
		STATUS		mandatory
		DESCRIPTION
			"The maximum value permitted by a TCP
			implementation for the retransmission timeout,
			measured in milliseconds.  More refined semantics
			for objects of this type depend upon the algorithm
			used to determine the retransmission timeout.  In
			particular, when the timeout algorithm is rsre(3),
			an object of this type has the semantics of the
			UBOUND quantity described in RFC 793.
			UNITS: milliseconds"
		::= { tcp 3 }

	tcpMaxConn OBJECT-TYPE
		SYNTAX		INTEGER
		ACCESS		read-only
		STATUS		mandatory
		DESCRIPTION
			"The limit on the total number of TCP connections
			the entity can support.  In entities where the
			maximum number of connections is dynamic, this
			object should contain the value -1."
		::= { tcp 4 }

	tcpActiveOpens OBJECT-TYPE
		SYNTAX		Counter
		ACCESS		read-only
		STATUS		mandatory
		DESCRIPTION
			"The number of times TCP connections have made a
			direct transition to the SYN-SENT state from the
			CLOSED state."
		::= { tcp 5 }

	tcpPassiveOpens OBJECT-TYPE
		SYNTAX		Counter
		ACCESS		read-only
		STATUS		mandatory
		DESCRIPTION
			"The number of times TCP connections have made a
			direct transition to the SYN-RCVD state from the
			LISTEN state."
		::= { tcp 6 }

	tcpAttemptFails OBJECT-TYPE
		SYNTAX		Counter
		ACCESS		read-only
		STATUS		mandatory
		DESCRIPTION
			"The number of times TCP connections have made a
			direct transition to the CLOSED state from either
			the SYN-SENT state or the SYN-RCVD state, plus the
			number of times TCP connections have made a direct
			transition to the LISTEN state from the SYN-RCVD
			state."
		::= { tcp 7 }

	tcpEstabResets OBJECT-TYPE
		SYNTAX		Counter
		ACCESS		read-only
		STATUS		mandatory
		DESCRIPTION
			"The number of times TCP connections have made a
			direct transition to the CLOSED state from either
			the ESTABLISHED state or the CLOSE-WAIT state."
		::= { tcp 8 }

	tcpCurrEstab OBJECT-TYPE
		SYNTAX		Gauge32
		ACCESS		read-only
		STATUS		mandatory
		DESCRIPTION
			"The number of TCP connections for which the
			current state is either ESTABLISHED or CLOSE-WAIT."
		::= { tcp 9 }

	tcpInSegs OBJECT-TYPE
		SYNTAX		Counter
		ACCESS		read-only
		STATUS		mandatory
		DESCRIPTION
			"The total number of segments received, including
			those received in error.  This count includes
			segments received on currently established
			connections."
		::= { tcp 10 }

	tcpOutSegs OBJECT-TYPE
		SYNTAX		Counter
		ACCESS		read-only
		STATUS		mandatory
		DESCRIPTION
			"The total number of segments sent, including
			those on current connections but excluding those
			containing only retransmitted octets."
		::= { tcp 11 }

	tcpRetransSegs OBJECT-TYPE
		SYNTAX		Counter
		ACCESS		read-only
		STATUS		mandatory
		DESCRIPTION
			"The total number of segments retransmitted - that
			is, the number of TCP segments transmitted
			containing one or more previously transmitted
			octets."
		::= { tcp 12 }


	-- the TCP Connection table

	-- The TCP connection table contains information about this
	-- entity's existing TCP connections.

	tcpConnTable OBJECT-TYPE
		SYNTAX		SEQUENCE OF TcpConnEntry
		ACCESS		not-accessible
		STATUS		mandatory
		DESCRIPTION
			"A table containing TCP connection-specific information."
		::= { tcp 13 }

	tcpConnEntry OBJECT-TYPE
		SYNTAX		TcpConnEntry
		ACCESS		not-accessible
		STATUS		mandatory
		DESCRIPTION
			"Information about a particular current TCP
			connection.  An object of this type is transient,
			in that it ceases to exist when (or soon after)
			the connection makes the transition to the CLOSED
			state."
		INDEX		{ tcpConnLocalAddress, tcpConnLocalPort, tcpConnRemAddress, tcpConnRemPort }
		::= { tcpConnTable 1 }

	TcpConnEntry ::= SEQUENCE {
		tcpConnState			INTEGER,
		tcpConnLocalAddress		IpAddress,
		tcpConnLocalPort		INTEGER,
		tcpConnRemAddress		IpAddress,
		tcpConnRemPort			INTEGER
		}

	tcpConnState OBJECT-TYPE
		SYNTAX		INTEGER {
			closed		(1),
			listen		(2),
			synSent		(3),
			synReceived	(4),
			established	(5),
			finWait1	(6),
			finWait2	(7),
			closeWait	(8),
			lastAck		(9),
			closing		(10),
			timeWait	(11),
			deleteTCB	(12)
			}
		ACCESS		read-write
		STATUS		mandatory
		DESCRIPTION
			"The state of this TCP connection.

			NOTE:	The following paragraphs are from rfc1213
					and Tiger does not currently support this.

			The only value which may be set by a management
			station is deleteTCB(12).  Accordingly, it is
			appropriate for an agent to return a `badValue'
			response if a management station attempts to set
			this object to any other value.

			If a management station sets this object to the
			value deleteTCB(12), then this has the effect of
			deleting the TCB (as defined in RFC 793) of the
			corresponding connection on the managed node,
			resulting in immediate termination of the
			connection.

			As an implementation-specific option, a RST
			segment may be sent from the managed node to the
			other TCP endpoint (note however that RST segments
			are not sent reliably)."
		::= { tcpConnEntry 1 }

	tcpConnLocalAddress OBJECT-TYPE
		SYNTAX		IpAddress
		ACCESS		read-only
		STATUS		mandatory
		DESCRIPTION
			"The local IP address for this TCP connection.  In
			the case of a connection in the listen state which
			is willing to accept connections for any IP
			interface associated with the node, the value
			0.0.0.0 is used."
		::= { tcpConnEntry 2 }

	tcpConnLocalPort OBJECT-TYPE
		SYNTAX		INTEGER (0..65535)
		ACCESS		read-only
		STATUS		mandatory
		DESCRIPTION
			"The local port number for this TCP connection."
		::= { tcpConnEntry 3 }

	tcpConnRemAddress OBJECT-TYPE
		SYNTAX		IpAddress
		ACCESS		read-only
		STATUS		mandatory
		DESCRIPTION
			"The remote IP address for this TCP connection."
		::= { tcpConnEntry 4 }

	tcpConnRemPort OBJECT-TYPE
		SYNTAX		INTEGER (0..65535)
		ACCESS		read-only
		STATUS		mandatory
		DESCRIPTION
			"The remote port number for this TCP connection."
		::= { tcpConnEntry 5 }


	-- additional TCP objects

	tcpInErrs OBJECT-TYPE
		SYNTAX		Counter
		ACCESS		read-only
		STATUS		mandatory
		DESCRIPTION
			"The total number of segments received in error (e.g., bad TCP checksums)."
		::= { tcp 14 }

	tcpOutRsts OBJECT-TYPE
		SYNTAX		Counter
		ACCESS		read-only
		STATUS		mandatory
		DESCRIPTION
			"The number of TCP segments sent containing the RST flag."
		::= { tcp 15 }

	tcpRetransAttempts OBJECT-TYPE
		SYNTAX		INTEGER (0..600)
		ACCESS		read-write
		STATUS		mandatory
		DESCRIPTION
			"The number of TCP retransmision attempts before the socket connection is
			declared down. The interval between attempts is fixed at approximately
			7 seconds. This parameter is global for all TCP applications.
			(default=6)"
		::= { tcp 16 }

	tcpKAInterval OBJECT-TYPE
		SYNTAX		INTEGER (1..600)
		ACCESS		read-write
		STATUS		mandatory
		DESCRIPTION
			"The interval of time, expressed in seconds between keepalive packets.
			Keepalive packets are generated when there is no other socket traffic.
			Although the operation of keepalive is defined on a per socket basis
			(see autif.mib), this parameter is global for all TCP applications.
			(default=30)"
		::= { tcp 17 }

	tcpKAAttempts OBJECT-TYPE
		SYNTAX		INTEGER (0..600)
		ACCESS		read-write
		STATUS		mandatory
		DESCRIPTION
			"The number of successive TCP keepalive packets sent with no reply at
			tcpKAIntervals before the socket connection is declared down.
			Although the operation of keepalive is defined on a per socket basis
			(see autif.mib), this parameter is global for all TCP applications.
			(default=3)"
		::= { tcp 18 }

	-- the UDP group

	-- Implementation of the UDP group is current for all
	-- systems which implement the UDP.

	udpInDatagrams OBJECT-TYPE
		SYNTAX		Counter
		ACCESS		read-only
		STATUS		mandatory
		DESCRIPTION
			"The total number of UDP datagrams delivered to UDP users."
		::= { udp 1 }

	udpNoPorts OBJECT-TYPE
		SYNTAX		Counter
		ACCESS		read-only
		STATUS		mandatory
		DESCRIPTION
			"The total number of received UDP datagrams for
			which there was no application at the destination port."
		::= { udp 2 }

	udpInErrors OBJECT-TYPE
		SYNTAX		Counter
		ACCESS		read-only
		STATUS		mandatory
		DESCRIPTION
			"The number of received UDP datagrams that could
			not be delivered for reasons other than the lack
			of an application at the destination port."
		::= { udp 3 }

	udpOutDatagrams OBJECT-TYPE
		SYNTAX		Counter
		ACCESS		read-only
		STATUS		mandatory
		DESCRIPTION
			"The total number of UDP datagrams sent from this entity."
		::= { udp 4 }

	-- the UDP Listener table

	-- The UDP listener table contains information about this
	-- entity's UDP end-points on which a local application is
	-- currently accepting datagrams.

	udpTable OBJECT-TYPE
		SYNTAX		SEQUENCE OF UdpEntry
		ACCESS		not-accessible
		STATUS		mandatory
		DESCRIPTION
			"A table containing UDP listener information."
		::= { udp 5 }

	udpEntry OBJECT-TYPE
		SYNTAX		UdpEntry
		ACCESS		not-accessible
		STATUS		mandatory
		DESCRIPTION
			"Information about a particular current UDP listener."
		INDEX	{ udpLocalAddress, udpLocalPort }
		::= { udpTable 1 }

	UdpEntry ::= SEQUENCE {
		udpLocalAddress		IpAddress,
		udpLocalPort		INTEGER
		}

	udpLocalAddress OBJECT-TYPE
		SYNTAX		IpAddress
		ACCESS		read-only
		STATUS		mandatory
		DESCRIPTION
			"The local IP address for this UDP listener.  In
			the case of a UDP listener which is willing to
			accept datagrams for any IP interface associated
			with the node, the value 0.0.0.0 is used."
		::= { udpEntry 1 }

	udpLocalPort OBJECT-TYPE
		SYNTAX		INTEGER (0..65535)
		ACCESS		read-only
		STATUS		mandatory
		DESCRIPTION
			"The local port number for this UDP listener."
		::= { udpEntry 2 }


	-- the SNMP group

	-- Implementation of the SNMP group is current for all
	-- systems which support an SNMP protocol entity.  Some of
	-- the objects defined below will be zero-valued in those
	-- SNMP implementations that are optimized to support only
	-- those functions specific to either a management agent or
	-- a management station.  In particular, it should be
	-- observed that the objects below refer to an SNMP entity,
	-- and there may be several SNMP entities residing on a
	-- managed node (e.g., if the node is hosting acting as
	-- a management station).

	snmpInPkts OBJECT-TYPE
		SYNTAX		Counter
		ACCESS		read-only
		STATUS		mandatory
		DESCRIPTION
			"The total number of Messages delivered to the
			SNMP entity from the transport service."
		::= { snmp 1 }

	snmpOutPkts OBJECT-TYPE
		SYNTAX		Counter
		ACCESS		read-only
		STATUS		mandatory
		DESCRIPTION
			"The total number of SNMP Messages which were
			passed from the SNMP protocol entity to the
			transport service."
		::= { snmp 2 }

	snmpInBadVersions OBJECT-TYPE
		SYNTAX		Counter
		ACCESS		read-only
		STATUS		mandatory
		DESCRIPTION
			"The total number of SNMP Messages which were
			delivered to the SNMP protocol entity and were for
			an unsupported SNMP version."
		::= { snmp 3 }

	snmpInBadCommunityNames OBJECT-TYPE
		SYNTAX		Counter
		ACCESS		read-only
		STATUS		mandatory
		DESCRIPTION
			"The total number of SNMP Messages delivered to
			the SNMP protocol entity which used a SNMP
			community name not known to said entity."
		::= { snmp 4 }

	snmpInBadCommunityUses OBJECT-TYPE
		SYNTAX		Counter
		ACCESS		read-only
		STATUS		mandatory
		DESCRIPTION
			"The total number of SNMP Messages delivered to
			the SNMP protocol entity which represented an SNMP
			operation which was not allowed by the SNMP
			community named in the Message."
		::= { snmp 5 }

	snmpInASNParseErrs OBJECT-TYPE
		SYNTAX		Counter
		ACCESS		read-only
		STATUS		mandatory
		DESCRIPTION
			"The total number of ASN.1 or BER errors
			encountered by the SNMP protocol entity when
			decoding received SNMP Messages."
		::= { snmp 6 }

	-- { snmp 7 } is not used

	snmpInTooBigs OBJECT-TYPE
		SYNTAX		Counter
		ACCESS		read-only
		STATUS		mandatory
		DESCRIPTION
			"The total number of SNMP PDUs which were
			delivered to the SNMP protocol entity and for
			which the value of the error-status field is
			`tooBig'."
		::= { snmp 8 }

	snmpInNoSuchNames OBJECT-TYPE
		SYNTAX		Counter
		ACCESS		read-only
		STATUS		mandatory
		DESCRIPTION
			"The total number of SNMP PDUs which were
			delivered to the SNMP protocol entity and for
			which the value of the error-status field is
			`noSuchName'."
		::= { snmp 9 }

	snmpInBadValues OBJECT-TYPE
		SYNTAX		Counter
		ACCESS		read-only
		STATUS		mandatory
		DESCRIPTION
			"The total number of SNMP PDUs which were
			delivered to the SNMP protocol entity and for
			which the value of the error-status field is
			`badValue'."
		::= { snmp 10 }

	snmpInReadOnlys OBJECT-TYPE
		SYNTAX		Counter
		ACCESS		read-only
		STATUS		mandatory
		DESCRIPTION
			"The total number valid SNMP PDUs which were
			delivered to the SNMP protocol entity and for
			which the value of the error-status field is
			`readOnly'.  It should be noted that it is a
			protocol error to generate an SNMP PDU which
			contains the value `readOnly' in the error-status
			field, as such this object is provided as a means
			of detecting incorrect implementations of the
			SNMP."
		::= { snmp 11 }

	snmpInGenErrs OBJECT-TYPE
		SYNTAX		Counter
		ACCESS		read-only
		STATUS		mandatory
		DESCRIPTION
			"The total number of SNMP PDUs which were
			delivered to the SNMP protocol entity and for
			which the value of the error-status field is
			`genErr'."
		::= { snmp 12 }

	snmpInTotalReqVars OBJECT-TYPE
		SYNTAX		Counter
		ACCESS		read-only
		STATUS		mandatory
		DESCRIPTION
			"The total number of MIB objects which have been
			retrieved successfully by the SNMP protocol entity
			as the result of receiving valid SNMP Get-Request
			and Get-Next PDUs."
		::= { snmp 13 }

	snmpInTotalSetVars OBJECT-TYPE
		SYNTAX		Counter
		ACCESS		read-only
		STATUS		mandatory
		DESCRIPTION
			"The total number of MIB objects which have been
			altered successfully by the SNMP protocol entity
			as the result of receiving valid SNMP Set-Request
			PDUs."
		::= { snmp 14 }

	snmpInGetRequests OBJECT-TYPE
		SYNTAX		Counter
		ACCESS		read-only
		STATUS		mandatory
		DESCRIPTION
			"The total number of SNMP Get-Request PDUs which
			have been accepted and processed by the SNMP
			protocol entity."
		::= { snmp 15 }

	snmpInGetNexts OBJECT-TYPE
		SYNTAX		Counter
		ACCESS		read-only
		STATUS		mandatory
		DESCRIPTION
			"The total number of SNMP Get-Next PDUs which have
			been accepted and processed by the SNMP protocol entity."
		::= { snmp 16 }

	snmpInSetRequests OBJECT-TYPE
		SYNTAX		Counter
		ACCESS		read-only
		STATUS		mandatory
		DESCRIPTION
			"The total number of SNMP Set-Request PDUs which
			have been accepted and processed by the SNMP
			protocol entity."
		::= { snmp 17 }

	snmpInGetResponses OBJECT-TYPE
		SYNTAX		Counter
		ACCESS		read-only
		STATUS		mandatory
		DESCRIPTION
			"The total number of SNMP Get-Response PDUs which
			have been accepted and processed by the SNMP
			protocol entity."
		::= { snmp 18 }

	snmpInTraps OBJECT-TYPE
		SYNTAX		Counter
		ACCESS		read-only
		STATUS		mandatory
		DESCRIPTION
			"The total number of SNMP Trap PDUs which have
			been accepted and processed by the SNMP protocol entity."
		::= { snmp 19 }

	snmpOutTooBigs OBJECT-TYPE
		SYNTAX		Counter
		ACCESS		read-only
		STATUS		mandatory
		DESCRIPTION
			"The total number of SNMP PDUs which were
			generated by the SNMP protocol entity and for
			which the value of the error-status field is `tooBig.'"
		::= { snmp 20 }

	snmpOutNoSuchNames OBJECT-TYPE
		SYNTAX		Counter
		ACCESS		read-only
		STATUS		mandatory
		DESCRIPTION
			"The total number of SNMP PDUs which were
			generated by the SNMP protocol entity and for
			which the value of the error-status is `noSuchName'."
		::= { snmp 21 }

	snmpOutBadValues OBJECT-TYPE
		SYNTAX		Counter
		ACCESS		read-only
		STATUS		mandatory
		DESCRIPTION
			"The total number of SNMP PDUs which were
			generated by the SNMP protocol entity and for
			which the value of the error-status field is `badValue'."
		::= { snmp 22 }

	-- { snmp 23 } is not used

	snmpOutGenErrs OBJECT-TYPE
		SYNTAX		Counter
		ACCESS		read-only
		STATUS		mandatory
		DESCRIPTION
			"The total number of SNMP PDUs which were
			generated by the SNMP protocol entity and for
			which the value of the error-status field is `genErr'."
		::= { snmp 24 }

	snmpOutGetRequests OBJECT-TYPE
		SYNTAX		Counter
		ACCESS		read-only
		STATUS		mandatory
		DESCRIPTION
			"The total number of SNMP Get-Request PDUs which
			have been generated by the SNMP protocol entity."
		::= { snmp 25 }

	snmpOutGetNexts OBJECT-TYPE
		SYNTAX		Counter
		ACCESS		read-only
		STATUS		mandatory
		DESCRIPTION
			"The total number of SNMP Get-Next PDUs which have
			been generated by the SNMP protocol entity."
		::= { snmp 26 }

	snmpOutSetRequests OBJECT-TYPE
		SYNTAX		Counter
		ACCESS		read-only
		STATUS		mandatory
		DESCRIPTION
			"The total number of SNMP Set-Request PDUs which
			have been generated by the SNMP protocol entity."
		::= { snmp 27 }

	snmpOutGetResponses OBJECT-TYPE
		SYNTAX		Counter
		ACCESS		read-only
		STATUS		mandatory
		DESCRIPTION
			"The total number of SNMP Get-Response PDUs which
			have been generated by the SNMP protocol entity."
		::= { snmp 28 }

	snmpOutTraps OBJECT-TYPE
		SYNTAX		Counter
		ACCESS		read-only
		STATUS		mandatory
		DESCRIPTION
			"The total number of SNMP Trap PDUs which have
			been generated by the SNMP protocol entity."
		::= { snmp 29 }

	snmpEnableAuthenTraps OBJECT-TYPE
		SYNTAX		INTEGER {
			enabled(1),
			disabled(2)
			}
		ACCESS		read-write
		STATUS		mandatory
		DESCRIPTION
			"Indicates whether the SNMP agent process is
			permitted to generate authentication-failure
			traps.  The value of this object overrides any
			configuration information; as such, it provides a
			means whereby all authentication-failure traps may
			be disabled.

			Note that it is strongly recommended that this
			object be stored in non-volatile memory so that it
			remains constant between re-initializations of the
			network management system."
		::= { snmp 30 }

	-- Note that full access to the partyTable, contextTable,
	-- aclTable, and viewTable gives a manager the ability to
	-- configure any parties with any/all capabilities (the
	-- equivalent of "root" access).  A lesser manager can be
	-- given access only to the partyTable so that it can
	-- maintain its own parties, but not increase/decrease
	-- their capabilities.  Such a lesser manager can also
	-- create new parties but they are of no use to it.

	partyCommTable OBJECT-TYPE
		SYNTAX		SEQUENCE OF PartyCommEntry
		ACCESS		not-accessible
		STATUS		mandatory
		DESCRIPTION
			"The SNMP community database."
		::= { partyMIB 1 }

	partyCommEntry OBJECT-TYPE
		SYNTAX		PartyCommEntry
		ACCESS		not-accessible
		STATUS		mandatory
		DESCRIPTION
			"Locally held information about a particular SNMP community."
		INDEX		{ partyCommIndex }
		::= { partyCommTable 1 }

	PartyCommEntry ::= SEQUENCE {
		partyCommIndex		INTEGER,
		partyCommunity		DisplayString,
		partyAccess			INTEGER
		}

	partyCommIndex OBJECT-TYPE
		SYNTAX		INTEGER (1..65535)
		ACCESS		read-write
		STATUS		mandatory
		DESCRIPTION
			"A unique value for each SNMPv2 party.  The value
			for each SNMPv2 party must remain constant at
			least from one re-initialization of the entity's
			network management system to the next re-initialization."
		::= { partyCommEntry 1 }

	partyCommunity OBJECT-TYPE
		SYNTAX		DisplayString (SIZE (0..255))
		ACCESS		read-write
		STATUS		mandatory
		DESCRIPTION
			"The SNMP community associated with this entry."
		::= { partyCommEntry 2 }

	partyAccess OBJECT-TYPE
		SYNTAX		INTEGER {
			read-only	(1),
			write-only	(2),
			read-write	(3),
			no-access	(4)
			}
		ACCESS		read-write
		STATUS		mandatory
		DESCRIPTION
			"Indicates the access rights of this community."
		DEFVAL		{ read-write }
		::= { partyCommEntry 3 }

--

	partyTrapTable OBJECT-TYPE
		SYNTAX		SEQUENCE OF PartyTrapEntry
		ACCESS		not-accessible
		STATUS		mandatory
		DESCRIPTION
			"The SNMP trap destination database."
		::= { partyMIB 2 }

	partyTrapEntry OBJECT-TYPE
		SYNTAX		PartyTrapEntry
		ACCESS		not-accessible
		STATUS		mandatory
		DESCRIPTION
			"Locally held information about a particular SNMP trap destination."
		INDEX		{ partyTrapIndex }
		::= { partyTrapTable 1 }

	PartyTrapEntry ::= SEQUENCE {
		partyTrapIndex		INTEGER,
		partyTAddress		IpAddress,
		partyTPort			INTEGER,
		partyTDomain		INTEGER,
		partyTCommunity		DisplayString
		}

	partyTrapIndex OBJECT-TYPE
		SYNTAX		INTEGER (1..65535)
		ACCESS		read-write
		STATUS		mandatory
		DESCRIPTION
			"A unique value for each SNMP trap destination entry."
		::= { partyTrapEntry 1 }

	partyTAddress OBJECT-TYPE
		SYNTAX		IpAddress
		ACCESS		read-write
		STATUS		mandatory
		DESCRIPTION
			"The IP address by which the party receives network management traffic."
		::= { partyTrapEntry 2 }

	partyTPort OBJECT-TYPE
		SYNTAX		INTEGER
		ACCESS		read-write
		STATUS		mandatory
		DESCRIPTION
			"The port address by which the party receives network management 
traffic."
		::= { partyTrapEntry 3 }

	partyTDomain OBJECT-TYPE
		SYNTAX		INTEGER {
			udp	(1),
			tcp	(2)
			}
		ACCESS		read-write
		STATUS		mandatory
		DESCRIPTION
			"Indicates the kind of transport service by which
			the party receives network management traffic."
		DEFVAL		{ udp }
		::= { partyTrapEntry 4 }

	partyTCommunity OBJECT-TYPE
		SYNTAX		DisplayString (SIZE (0..255))
		ACCESS		read-write
		STATUS		mandatory
		DESCRIPTION
			"The SNMP community used in the trap response to this entries address."
		::= { partyTrapEntry 5 }


	--
	-- Traps
	--
	-- This section defines the well-known notifications sent by Tiger agents.
	-- These are sent when the corresponding threshold is exceeded

	ifStateChange TRAP-TYPE
		ENTERPRISE		sysTraps
		VARIABLES		{ ifIndex, ifType, ifOperStatus, rs232PortIndex }
		DESCRIPTION
			"A linkStateChange trap signifies that the sending protocol entity recognizes a change
			in one of the communication links represented in the agent's configuration.
			Currently this trap is only applicable to:
				lapb		frame_relay
				sdlc		token ring
				u100		ethernet
				alc
				ppp
			Other interfaces that may be supported in the future are:
				apath	pad		x2x		cap
				mux		frip	autif"
		::= 1

	ifErrorRate TRAP-TYPE
		ENTERPRISE		sysTraps
		VARIABLES		{ ifIndex, ifType, ifErrType, rs232PortIndex }
		DESCRIPTION
			"A linkErrorRate trap signifies that the sending protocol entity discovered an
			error rate that
			in one of the communication links represented in the agent's configuration.
			Currently this trap is only applicable to:
				lapb		frame_relay
				sdlc		token ring
				u100		ethernet
				alc
				ppp
			Other interfaces that may be supported in the future are:
				apath	pad		x2x		cap
				mux		frip	autif"
		::= 2

	ipRouteChange TRAP-TYPE
		ENTERPRISE		sysTraps
		VARIABLES		{ ipForwardDest, ipForwardNextHop, ipForwardMetric1, ipForwardTrapReason }
		DESCRIPTION
			"An ipRouteChange trap signifies that the IP Forwarding table has been changed.
			An entry was added, deleted or modified."
		::= 3

	END
