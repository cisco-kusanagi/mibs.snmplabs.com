-- INTEL CONFIDENTIAL
-- Copyright 2006, 2007
-- Intel Corporation All Rights Reserved.
--
-- The source code contained or described herein and all documents related to
-- the source code ("Material") are owned by Intel Corporation or its
-- suppliers and licensors. Title to the Material remains with Intel
-- Corporation or its suppliers and licensors. The Material contains trade
-- secrets and proprietary and confidential information of Intel or its
-- suppliers and licensors. The Material is protected by worldwide copyright
-- and trade secret laws and treaty provisions. No part of the Material may be
-- used, copied, reproduced, modified, published, uploaded, posted,
-- transmitted, distributed, or disclosed in any way without Intel's prior
-- express written permission.
--
-- Unless otherwise expressly permitted by Intel in a separate license
-- agreement, use of the Material is subject to the copyright notices,
-- trademarks, warranty, use, and disclosure restrictions reflected on the
-- outside of the media, in the documents themselves, and in the "About" or
-- "Read Me" or similar file contained within this source code. Unless
-- otherwise expressly agreed by Intel in writing, you may not remove
-- or alter such notices in any way.
--

    INTELCORPORATION-MULTI-FLEX-SERVER-SCM-MIB DEFINITIONS ::= BEGIN

        IMPORTS
            MODULE-IDENTITY, OBJECT-TYPE, OBJECT-IDENTITY, Integer32, Counter64,
            Unsigned32
                FROM SNMPv2-SMI

            OBJECT-GROUP
                FROM SNMPv2-CONF

            DisplayString, PhysAddress
                FROM SNMPv2-TC

            regModule, groups
                FROM INTELCORPORATION-MULTI-FLEX-SERVER-REG

            Index, Presence, Power, INT32withException, IdromBinary16,
            PowerLedStates, FaultLedStates
                FROM INTELCORPORATION-MULTI-FLEX-SERVER-TC

            chassis
                FROM INTELCORPORATION-MULTI-FLEX-SERVER-MIB;


            multiFlexServerScmMibModule MODULE-IDENTITY
                LAST-UPDATED "200709290000Z"        -- August 29, 2007 at 00:00 GMT
                ORGANIZATION
                    "Intel Corporation"
                CONTACT-INFO
                    "Brian Kurle
                    Intel Corporation
                    JF5-2-C3
                    Tel: 503-712-5032
                    E-Mail: brianx.j.kurle@intel.com"
                DESCRIPTION
                    "Controller Module of the Multi-Flex Server"
                REVISION "200709290000Z"        -- August 29, 2007 at 00:00 GMT
                DESCRIPTION
                    "OEM added support to Battery table, added columns
                    scmBatteryCellType & scmBatteryHoldTime"
                REVISION "200708161300Z"        -- August 16, 2007 at 13:00 GMT
                DESCRIPTION
                    "Corrected a few entries that were marked as read-write
                    when they should have been read-only

                    Reordered Revision to reverse chronological as some
                    browsers choke, cleaned up some other simple nit-picky
                    errors"
                REVISION "200708101530Z"        -- August 10, 2007 at 15:30 GMT
                DESCRIPTION
                    "Removed scmBootLoaderVersion as it is no longer being
                    reported via the SCM (for version 2 of the SCM software)."
                REVISION "200708061300Z"        -- August 08, 2007 at 13:00 GMT
                DESCRIPTION
                    "Removed Presence LED (mistook dirty cache LED for
                    presence LED)"
                REVISION "200707161330Z"        -- July 16, 2007 at 13:30 GMT
                DESCRIPTION
                    "Added Power, Presence and Fault LED support"
                REVISION "200706181330Z"        -- June 18, 2007 at 13:30 GMT
                DESCRIPTION
                    "Finalized the Version information for the MIB based on
                    information available/used by the rest of the system
                    (e.g., the GUI/fwupdate)

                    Dropped scmBmcFirmwareVersion, scmDriverVersion,
                    scmSoftwareVersion, & scmBIOSVersion."
                REVISION "200706072030Z"        -- June 07, 2007 at 20:30 GMT
                DESCRIPTION
                    "Added the IdromBinary16 to represent the asset tag,
                    part number, and serial number fields within the IDROM
                    fields."
                REVISION "200706071330Z"        -- June 07, 2007 at 13:30 GMT
                DESCRIPTION
                    "Corrected maximum/nominal IDROM parameters and comments"
                REVISION "200705231100Z"        -- May 23, 2007 at 11:00 GMT
                DESCRIPTION
                    "Moved Presence to column 1 to be consistent across all
                    tables."
                REVISION "200705171130Z"        -- May 17, 2007 at 11:30 GMT
                DESCRIPTION
                    "Added/reworked IDROM data to the scmBatteryTable.  To
                    be consistent, IDROM data is placed first, thus
                    renumbered."
                REVISION "200704181905Z"        -- April 18, 2007 at 19:00 GMT
                DESCRIPTION
                    "Moved the trees and chassis nodes around to accomodate
                    the unique power supply characteristics.  Added the
                    missing numOfPwrUnknowns & pwrSupplyUnknownPresenceMask"
                REVISION "200704091030Z"        -- April 09, 2007 at 10:30 GMT
                DESCRIPTION
                    "Added scmBcmFirmwareVersion to be consistent with rest
                    of the subsystems.
                    Renamed *Rev to *Version to be consistent in naming
                    convention of other subsystems"
                REVISION "200703121800Z"        -- March 12, 2007 at 18:00 GMT
                DESCRIPTION
                    "scmTable data now complies with IDROM (DID/DSD)
                    information.

                    Renumbered / reorganized accordingly"
                REVISION "200703101830Z"        -- March 10, 2007 at 18:30 GMT
                DESCRIPTION
                    "Renamed MIB from *-CTL-* to *-SCM-*
                    All 'Manufac' references have been changed to
                    'Manufacture'
                    All 'Controller' references have been changed to 'Scm'
                    All 'Ctl' references have been changed to 'Scm'
                    All 'Logical' references have been changed to 'Virtual'
                    All 'Array' references have been changed to 'Pool'
                    All 'Disk' references have been changed to 'Drive'
                    All 'Phy' references have been changed to 'Physical'
                    All 'Drv' references have been changed to 'Drive' (or
                    'Drives' as appropriate) "
                REVISION "200703061030Z"        -- March 06, 2007 at 10:30 GMT
                DESCRIPTION
                    "Changed Mask representation from an Opaque to a
                    DisplayString at the request of the architects such
                    that it now is an ASCII representation of bit string
                    reflecting the presence with the left most 'bit' being
                    bit 1 and max* bits being represented."
                REVISION "200702221700Z"        -- February 22, 2007 at 17:00 GMT
                DESCRIPTION
                    "Renamed MIB file and updated internal relevance to
                    formal product name Multi-Flex Server"
                REVISION "200701151700Z"        -- January 15, 2007 at 17:00 GMT
                DESCRIPTION
                    "Corrected descriptions of ctlNumOfPhyDrvWithPFA,
                    ctlNumOfPhyDrvRebuilding, & ctlNumOfPhyDrvMissing"
                REVISION "200701051020Z"        -- January 05, 2007 at 10:20 GMT
                DESCRIPTION
                    "Added ctlBatteryPresence to Battery table to help
                    identify whether a battery exists or not."
                REVISION "200612281530Z"        -- December 28, 2006 at 15:30 GMT
                DESCRIPTION
                    "Corrected ctlStatsTable INDEX to AUGMENTS."
                REVISION "200612081330Z"        -- December 08, 2006 at 13:30 GMT
                DESCRIPTION
                    "Associated Battery table with Controller table.  Thus,
                    Battery table is now indexed by ctlIndex and the
                    columns have been renumbered accordingly."
                REVISION "200612051030Z"        -- December 05, 2006 at 10:30 GMT
                DESCRIPTION
                    "Renamed all of the *Transfered to *Transferred"
                REVISION "200612041600Z"        -- December 04, 2006 at 16:00 GMT
                DESCRIPTION
                    "Updated several object types to reflect changes in the
                    OEM objects.

                    Added ctlBIOSRev to ctlTable."
                REVISION "200611281530Z"        -- November 28, 2006 at 15:30 GMT
                DESCRIPTION
                    "Updated several object types to reflect changes in the
                    OEM objects.

                    ctlBatteryCycleCount        Unsigned32      -> Integer32
                    ctlBatteryRemainCapacity    Unsigned32      -> Integer32
                    ctlBatteryVoltage           Unsigned32      -> Integer32
                    ctlBatteryCurrent           Unsigned32      -> Integer32
                    ctlSCSIProtocol             DisplayString   -> INTEGER

                    Removed ctlStatsIndex from ctlStatsTable (reindexed
                    with ctlIndex and renumbered objects accordingly).

                    OEM changed the controller information, updated
                    ctlTable accordingly.  Removed ctlVoltage,
                    ctlPartnerStatus, ctlMasterMode, ctlActiveMode,
                    ctlPartnerActiveMode objects. Added ctlDriverRev,
                    ctlReadinessStatus, & ctlRole objects.

                    Removed scsiTargetTable and scsiChannelTable.
                    Renumbered ctlStatsTable to { controllers 2 } to be
                    closer associated with ctlTable and ctlBatteryTable to
                    { controllers 3 } to accomodate the deletion of the
                    aforementioned tables.

                    Cleaned up some illegal character usage to make it
                    SMIv2 compliant."
                REVISION "200611070701Z"        -- November 07, 2006 at 07:01 GMT
                DESCRIPTION
                    "Consolodated use of Presence datatype and changed
                    'chassis' to 'chassis'"
                REVISION "200610020629Z"        -- October 02, 2006 at 06:29 GMT
                DESCRIPTION
                    "Partitioned off and created as it's own module"
                ::= { regModule 14 }



-- ----------------------------------------------------------------------------
--
-- Controller group.
--
-- This group contains information about Controller.
--
-- ----------------------------------------------------------------------------

        maxScms OBJECT-TYPE
            SYNTAX Unsigned32
            MAX-ACCESS read-only
            STATUS current
            DESCRIPTION
                "Maximum number of Storage Controllers possible in this chassis."
            ::= { chassis 14 }

        numOfScms OBJECT-TYPE
            SYNTAX Integer32
            MAX-ACCESS read-only
            STATUS current
            DESCRIPTION
                "The number of Storage Controllers in the system."
            ::= { chassis 24 }

        scmPresenceMask OBJECT-TYPE
            SYNTAX DisplayString
            MAX-ACCESS read-only
            STATUS current
            DESCRIPTION
                "ASCII representation of bit string reflecting the presence
                of the blades with the left most 'bit' being bit 1 and
                maxScms bits being represented.

                Thus, '10' would express that SCM 1 (of two
                SCMs) are present"
            ::= { chassis 34 }

--
-- Storage Controller tree
--

        scms OBJECT-IDENTITY
            STATUS current
            DESCRIPTION
                "Container for Storage Controller Module specific
                information as well as all components logically contained
                within."
            ::= { chassis 204 }


        scmTable OBJECT-TYPE
            SYNTAX SEQUENCE OF ScmEntry
            MAX-ACCESS not-accessible
            STATUS current
            DESCRIPTION
                "Each row describes a SCM in the chassis that is supplying
                environmental data or supporting management via the SNMP
                agent.

                There may be only one row in this table, but there must be
                at least one row."
            ::= { scms 1 }


        scmEntry OBJECT-TYPE
            SYNTAX ScmEntry
            MAX-ACCESS not-accessible
            STATUS current
            DESCRIPTION
                "Parameters for the Storage Controller Table"
            INDEX { scmIndex }
            ::= { scmTable 1 }


        ScmEntry ::=
            SEQUENCE {

                scmIndex                            Index,
                scmPresence                         Presence,
                scmVendor                           DisplayString,
                scmMfgDate                          DisplayString,
                scmDeviceName                       DisplayString,
                scmPart                             IdromBinary16,
                scmSerialNo                         IdromBinary16,
                scmMaximumPower                     Power,
                scmNominalPower                     Power,
                scmAssetTag                         IdromBinary16,
                scmManagementMac                    PhysAddress,
                scmWWN                              DisplayString,
                scmSCSIProtocol                     INTEGER,
                scmPowerLed                         PowerLedStates,
                scmFaultLed                         FaultLedStates,
                scmFirmwareVersion                  DisplayString,
                scmOpStatus                         DisplayString,
                scmRole                             INTEGER,
                scmReadinessStatus                  DisplayString,
                scmNumOfPoolsPresent                INT32withException,
                scmNumOfPhysicalDrivesPresent       INT32withException,
                scmNumOfPhysicalDrivesOnline        INT32withException,
                scmNumOfPhysicalDrivesOffline       INT32withException,
                scmNumOfPhysicalDrivesWithPFA       INT32withException,
                scmNumOfPhysicalDrivesRebuilding    INT32withException,
                scmNumOfPhysicalDrivesMissing       INT32withException,
                scmNumOfPhysicalDrivesUnconfigured  INT32withException,
                scmNumOfVirtualDrivesPresent        INT32withException,
                scmNumOfVirtualDrivesOnline         INT32withException,
                scmNumOfVirtualDrivesOffline        INT32withException,
                scmNumOfVirtualDrivesCritical       INT32withException,
                scmNumOfGlobalSparesPresent         INT32withException,
                scmNumOfDedicatedSparesPresent              INT32withException,
                scmNumOfRevertibleGlobalSparesPresent       INT32withException,
                scmNumOfRevertibleGlobalSparesUsed          INT32withException,
                scmNumOfRevertibleDedicatedSparesPresent    INT32withException,
                scmNumOfRevertibleDedicatedSparesUsed       INT32withException,
                scmNumOfBGAs                                INT32withException,
                scmPowerOnHours                     INT32withException,
                scmDirtyCachePercentage             INT32withException,
                scmCacheUsagePercentage             INT32withException

             }

        scmIndex OBJECT-TYPE
            SYNTAX Index
            MAX-ACCESS read-only
            STATUS current
            DESCRIPTION
                "Slot to identify a particular SCM."
            ::= { scmEntry 1 }

        scmPresence OBJECT-TYPE
            SYNTAX Presence
            MAX-ACCESS read-only
            STATUS current
            DESCRIPTION
                "Whether a particular SCM is present."
            ::= { scmEntry 2 }

--
-- Storage Controller IDROM
--

        scmVendor OBJECT-TYPE
            SYNTAX DisplayString
            MAX-ACCESS read-only
            STATUS current
            DESCRIPTION
                "Device manufacturer"
            ::= { scmEntry 3 }

        scmMfgDate OBJECT-TYPE
            SYNTAX DisplayString
            MAX-ACCESS read-only
            STATUS current
            DESCRIPTION
                "Manufacture date/time"
            ::= { scmEntry 4 }

        scmDeviceName OBJECT-TYPE
            SYNTAX DisplayString
            MAX-ACCESS read-only
            STATUS current
            DESCRIPTION
                "Device Name"
            ::= { scmEntry 5 }

        scmPart OBJECT-TYPE
            SYNTAX IdromBinary16
            MAX-ACCESS read-only
            STATUS current
            DESCRIPTION
                "Device Part Number"
            ::= { scmEntry 6 }

        scmSerialNo OBJECT-TYPE
            SYNTAX IdromBinary16
            MAX-ACCESS read-only
            STATUS current
            DESCRIPTION
                "Device Serial Number"
            ::= { scmEntry 7 }

        scmMaximumPower OBJECT-TYPE
            SYNTAX Power
            MAX-ACCESS read-only
            STATUS current
            DESCRIPTION
                "Static maximum power generation / consumption (in watts):

                <0      - Negative numbers indicate device consumes power (in watts)
                >0      - Positive numbers indicate device generates power (in watts)
                0       - Device is passive (does not not consume or generate power)
                -1      - Maximum power generation/consumption not known or specified"
            ::= { scmEntry 8 }

        scmNominalPower OBJECT-TYPE
            SYNTAX Power
            MAX-ACCESS read-only
            STATUS current
            DESCRIPTION
                "Static Nominal power generation / consumption (in watts):

                <0      - Negative numbers indicate device consumes power (in watts)
                >0      - Positive numbers indicate device generates power (in watts)
                0       - Device is passive (does not not consume or generate power)
                -1      - Nominal power generation/consumption not known or specified"
            ::= { scmEntry 9 }

        scmAssetTag OBJECT-TYPE
            SYNTAX IdromBinary16
            MAX-ACCESS read-only
            STATUS current
            DESCRIPTION
                "Asset Tag # of device"
            ::= { scmEntry 10 }

        scmManagementMac OBJECT-TYPE
            SYNTAX PhysAddress
            MAX-ACCESS read-only
            STATUS current
            DESCRIPTION
                "MAC Address of switch management Ethernet port"
            ::= { scmEntry 11 }

        scmWWN OBJECT-TYPE
            SYNTAX DisplayString
            MAX-ACCESS read-only
            STATUS current
            DESCRIPTION
                "World-wide-name of this SCM."
            ::= { scmEntry 12 }

        scmSCSIProtocol OBJECT-TYPE
            SYNTAX INTEGER {
                    notApplicable(-32),
                    unknown(-16),
                    other(1),
                    scsi2(2),
                    scsi3(3)
                }
            MAX-ACCESS read-only
            STATUS current
            DESCRIPTION
                "The SCSI Protocol Supported by the SCM."
            ::= { scmEntry 13 }

        scmPowerLed OBJECT-TYPE
            SYNTAX PowerLedStates
            MAX-ACCESS read-only
            STATUS current
            DESCRIPTION
                "State of the Power LED on the SCM"
            ::= { scmEntry 14 }

        scmFaultLed OBJECT-TYPE
            SYNTAX FaultLedStates
            MAX-ACCESS read-only
            STATUS current
            DESCRIPTION
                "State of the Fault LED on the SCM"
            ::= { scmEntry 15 }

        scmFirmwareVersion OBJECT-TYPE
            SYNTAX DisplayString
            MAX-ACCESS read-only
            STATUS current
            DESCRIPTION
                "The Firmware Version of the SCM."
            ::= { scmEntry 16 }

        scmOpStatus OBJECT-TYPE
            SYNTAX DisplayString
            MAX-ACCESS read-only
            STATUS current
            DESCRIPTION
                "The Operational Status of the SCM."
            ::= { scmEntry 17 }

        scmRole OBJECT-TYPE
            SYNTAX INTEGER {
                    notApplicable(-32),
                    unknown(-16),
                    unavailable(-1),
                    primary(1),
                    secondary(0)
                }
            MAX-ACCESS read-only
            STATUS current
            DESCRIPTION
                "The role of the storage controller in the device instance.
                For the products that do not support High Availability,
                this attribute shall be always reported as primary."
            ::= { scmEntry 18 }

        scmReadinessStatus OBJECT-TYPE
            SYNTAX DisplayString
            MAX-ACCESS read-only
            STATUS current
            DESCRIPTION
                "The readiness of the storage controller in the instance.
                For the products that do not support High Availability,
                this attribute shall be always reported as 'Active'"
            ::= { scmEntry 19 }

        scmNumOfPoolsPresent OBJECT-TYPE
            SYNTAX INT32withException
            MAX-ACCESS read-only
            STATUS current
            DESCRIPTION
                "The Number of Storage Pools present in the SCM."
            ::= { scmEntry 20 }

        scmNumOfPhysicalDrivesPresent OBJECT-TYPE
            SYNTAX INT32withException
            MAX-ACCESS read-only
            STATUS current
            DESCRIPTION
                "The Number of Physical Drives present in the SCM."
            ::= { scmEntry 21 }

        scmNumOfPhysicalDrivesOnline OBJECT-TYPE
            SYNTAX INT32withException
            MAX-ACCESS read-only
            STATUS current
            DESCRIPTION
                "The Number of Physical Drives online in the SCM."
            ::= { scmEntry 22 }

        scmNumOfPhysicalDrivesOffline OBJECT-TYPE
            SYNTAX INT32withException
            MAX-ACCESS read-only
            STATUS current
            DESCRIPTION
                "The Number of Physical Drives offline in the SCM."
            ::= { scmEntry 23 }

        scmNumOfPhysicalDrivesWithPFA OBJECT-TYPE
            SYNTAX INT32withException
            MAX-ACCESS read-only
            STATUS current
            DESCRIPTION
                "The Number of Physical Drives with PFA in the SCM."
            ::= { scmEntry 24 }

        scmNumOfPhysicalDrivesRebuilding OBJECT-TYPE
            SYNTAX INT32withException
            MAX-ACCESS read-only
            STATUS current
            DESCRIPTION
                "The number of Physical Drives rebuilding in the
                storage controller."
            ::= { scmEntry 25 }

        scmNumOfPhysicalDrivesMissing OBJECT-TYPE
            SYNTAX INT32withException
            MAX-ACCESS read-only
            STATUS current
            DESCRIPTION
                "The number of missing Physical Drives (from existing
                configured storage pools) in the SCM."
            ::= { scmEntry 26 }

        scmNumOfPhysicalDrivesUnconfigured OBJECT-TYPE
            SYNTAX INT32withException
            MAX-ACCESS read-only
            STATUS current
            DESCRIPTION
                "The number of unconfigured Physical Drives in the SCM."
            ::= { scmEntry 27 }

        scmNumOfVirtualDrivesPresent OBJECT-TYPE
            SYNTAX INT32withException
            MAX-ACCESS read-only
            STATUS current
            DESCRIPTION
                "The Number of Virtual Drives present in the SCM."
            ::= { scmEntry 28 }

        scmNumOfVirtualDrivesOnline OBJECT-TYPE
            SYNTAX INT32withException
            MAX-ACCESS read-only
            STATUS current
            DESCRIPTION
                "The Number of Virtual Drives online in the SCM."
            ::= { scmEntry 29 }

        scmNumOfVirtualDrivesOffline OBJECT-TYPE
            SYNTAX INT32withException
            MAX-ACCESS read-only
            STATUS current
            DESCRIPTION
                "The Number of Virtual Drives offline in the SCM."
            ::= { scmEntry 30 }

        scmNumOfVirtualDrivesCritical OBJECT-TYPE
            SYNTAX INT32withException
            MAX-ACCESS read-only
            STATUS current
            DESCRIPTION
                "The Number of Virtual Drives critical in the SCM."
            ::= { scmEntry 31 }

        scmNumOfGlobalSparesPresent OBJECT-TYPE
            SYNTAX INT32withException
            MAX-ACCESS read-only
            STATUS current
            DESCRIPTION
                "The Number of Global Spares present in the SCM."
            ::= { scmEntry 32 }

        scmNumOfDedicatedSparesPresent OBJECT-TYPE
            SYNTAX INT32withException
            MAX-ACCESS read-only
            STATUS current
            DESCRIPTION
                "The Number of Dedicated Spares present in the SCM."
            ::= { scmEntry 33 }

        scmNumOfRevertibleGlobalSparesPresent OBJECT-TYPE
            SYNTAX INT32withException
            MAX-ACCESS read-only
            STATUS current
            DESCRIPTION
                "The Number of Revertive Global Spares present in the SCM."
            ::= { scmEntry 34 }

        scmNumOfRevertibleGlobalSparesUsed OBJECT-TYPE
            SYNTAX INT32withException
            MAX-ACCESS read-only
            STATUS current
            DESCRIPTION
                "The Number of Revertive Global Spares used in the SCM."
            ::= { scmEntry 35 }

        scmNumOfRevertibleDedicatedSparesPresent OBJECT-TYPE
            SYNTAX INT32withException
            MAX-ACCESS read-only
            STATUS current
            DESCRIPTION
                "The Number of Revertive Dedicated Spares present in the
                SCM."
            ::= { scmEntry 36 }

        scmNumOfRevertibleDedicatedSparesUsed OBJECT-TYPE
            SYNTAX INT32withException
            MAX-ACCESS read-only
            STATUS current
            DESCRIPTION
                "The Number of Revertive Dedicated Spares used in the SCM."
            ::= { scmEntry 37 }

        scmNumOfBGAs OBJECT-TYPE
            SYNTAX INT32withException
            MAX-ACCESS read-only
            STATUS current
            DESCRIPTION
                "The Number of Background Activities cocurrently running on
                the SCM."
            ::= { scmEntry 38 }

        scmPowerOnHours OBJECT-TYPE
            SYNTAX INT32withException
            MAX-ACCESS read-only
            STATUS current
            DESCRIPTION
                "The number of hours since last power on of the SCM."
            ::= { scmEntry 39 }

        scmDirtyCachePercentage OBJECT-TYPE
            SYNTAX INT32withException
            MAX-ACCESS read-only
            STATUS current
            DESCRIPTION
                "It Indicates percentage of the dirty cache on the SCM"
            ::= { scmEntry 40 }

        scmCacheUsagePercentage OBJECT-TYPE
            SYNTAX INT32withException
            MAX-ACCESS read-only
            STATUS current
            DESCRIPTION
                "It Indicates percentage of the used cache on the SCM"
            ::= { scmEntry 41 }


--
-- Controller Statistics Information
--

        scmStatsTable OBJECT-TYPE
            SYNTAX SEQUENCE OF ScmStatsEntry
            MAX-ACCESS not-accessible
            STATUS current
            DESCRIPTION
                "A table of SCM Statistics."
            ::= { scms 2 }

        scmStatsEntry OBJECT-TYPE
            SYNTAX ScmStatsEntry
            MAX-ACCESS not-accessible
            STATUS current
            DESCRIPTION
                "The statistics of a SCM since its last reset or statistics
                rest."
            AUGMENTS { scmEntry }
            ::= { scmStatsTable 1 }

        ScmStatsEntry ::=
            SEQUENCE {

                scmStatsDataTransferred             Counter64,
                scmStatsReadDataTransferred         Counter64,
                scmStatsWriteDataTransferred        Counter64,
                scmStatsNumOfErrors                 Integer32,
                scmStatsNumOfNonRWErrors            Integer32,
                scmStatsNumOfReadErrors             Integer32,
                scmStatsNumOfWriteErrors            Integer32,
                scmStatsNumOfIORequests             Counter64,
                scmStatsNumOfNonRWRequests          Counter64,
                scmStatsNumOfReadRequests           Counter64,
                scmStatsNumOfWriteRequests          Counter64,
                scmStatsStartTime                   Counter64,
                scmStatsCollectionTime              Counter64

             }

        scmStatsDataTransferred OBJECT-TYPE
            SYNTAX Counter64
            MAX-ACCESS read-only
            STATUS current
            DESCRIPTION
                "The total number of bytes of data transferred to and from
                the SCM."
            ::= { scmStatsEntry 1 }

        scmStatsReadDataTransferred OBJECT-TYPE
            SYNTAX Counter64
            MAX-ACCESS read-only
            STATUS current
            DESCRIPTION
                "The total number of bytes of data transferred from the
                SCM."
            ::= { scmStatsEntry 2 }

        scmStatsWriteDataTransferred OBJECT-TYPE
            SYNTAX Counter64
            MAX-ACCESS read-only
            STATUS current
            DESCRIPTION
                "The total number of bytes of data transferred to the SCM."
            ::= { scmStatsEntry 3 }

        scmStatsNumOfErrors OBJECT-TYPE
            SYNTAX Integer32
            MAX-ACCESS read-only
            STATUS current
            DESCRIPTION
                "The total number of errors."
            ::= { scmStatsEntry 4 }

        scmStatsNumOfNonRWErrors OBJECT-TYPE
            SYNTAX Integer32
            MAX-ACCESS read-only
            STATUS current
            DESCRIPTION
                "The total number of non-RW errors."
            ::= { scmStatsEntry 5 }

        scmStatsNumOfReadErrors OBJECT-TYPE
            SYNTAX Integer32
            MAX-ACCESS read-only
            STATUS current
            DESCRIPTION
                "The total number of Read errors."
            ::= { scmStatsEntry 6 }

        scmStatsNumOfWriteErrors OBJECT-TYPE
            SYNTAX Integer32
            MAX-ACCESS read-only
            STATUS current
            DESCRIPTION
                "The total number of Write errors."
            ::= { scmStatsEntry 7 }

        scmStatsNumOfIORequests OBJECT-TYPE
            SYNTAX Counter64
            MAX-ACCESS read-only
            STATUS current
            DESCRIPTION
                "The total number of IO requests."
            ::= { scmStatsEntry 8 }

        scmStatsNumOfNonRWRequests OBJECT-TYPE
            SYNTAX Counter64
            MAX-ACCESS read-only
            STATUS current
            DESCRIPTION
                "The total number of non-RW requests."
            ::= { scmStatsEntry 9 }

        scmStatsNumOfReadRequests OBJECT-TYPE
            SYNTAX Counter64
            MAX-ACCESS read-only
            STATUS current
            DESCRIPTION
                "The total number of read requests."
            ::= { scmStatsEntry 10 }

        scmStatsNumOfWriteRequests OBJECT-TYPE
            SYNTAX Counter64
            MAX-ACCESS read-only
            STATUS current
            DESCRIPTION
                "The total number of write requests."
            ::= { scmStatsEntry 11 }

        scmStatsStartTime OBJECT-TYPE
            SYNTAX Counter64
            MAX-ACCESS read-only
            STATUS current
            DESCRIPTION
                "The time when the statistics date starts to accumulate
                since last statistics reset."
            ::= { scmStatsEntry 12 }

        scmStatsCollectionTime OBJECT-TYPE
            SYNTAX Counter64
            MAX-ACCESS read-only
            STATUS current
            DESCRIPTION
                "The time when the statistics data was collected or updated
                last time."
            ::= { scmStatsEntry 13 }


--
-- Battery information for the Controllers.
--

        scmBatteryTable OBJECT-TYPE
            SYNTAX SEQUENCE OF ScmBatteryEntry
            MAX-ACCESS not-accessible
            STATUS current
            DESCRIPTION
                "The Battery table contains general information on
                Battery on each SCM."
            ::= { scms 3 }

        scmBatteryEntry OBJECT-TYPE
            SYNTAX ScmBatteryEntry
            MAX-ACCESS not-accessible
            STATUS current
            DESCRIPTION
                "A Battery entry containing objects for a particular
                Battery on each SCM."
            AUGMENTS { scmEntry }
            ::= { scmBatteryTable 1 }

        ScmBatteryEntry ::=
            SEQUENCE {

                scmBatteryPresence                  Presence,
                scmBatteryVendor                    DisplayString,
                scmBatteryMfgDate                   DisplayString,
                scmBatteryDeviceName                DisplayString,
                scmBatteryPart                      IdromBinary16,
                scmBatterySerialNo                  IdromBinary16,
                scmBatteryMaximumPower              Power,
                scmBatteryNominalPower              Power,
                scmBatteryAssetTag                  IdromBinary16,
                scmBatteryDeviceChemistry           DisplayString,
                scmBatteryTemperature               INT32withException,
                scmBatteryTempChargeThreshold       INT32withException,
                scmBatteryTempDisChargeThreshold    INT32withException,
                scmBatteryCycleCount                INT32withException,
                scmBatteryRemainCapacity            INT32withException,
                scmBatteryVoltage                   INT32withException,
                scmBatteryCurrent                   INT32withException,
                scmBatteryStatus                    DisplayString,
                scmBatteryCellType                  INTEGER,
                scmBatteryHoldTime                  INT32withException

             }

        scmBatteryPresence OBJECT-TYPE
            SYNTAX Presence
            MAX-ACCESS read-only
            STATUS current
            DESCRIPTION
                "Whether a particular battery is present."
            ::= { scmBatteryEntry 1 }

--
-- Storage Controller IDROM
--

        scmBatteryVendor OBJECT-TYPE
            SYNTAX DisplayString
            MAX-ACCESS read-only
            STATUS current
            DESCRIPTION
                "Device manufacturer"
            ::= { scmBatteryEntry 2 }

        scmBatteryMfgDate OBJECT-TYPE
            SYNTAX DisplayString
            MAX-ACCESS read-only
            STATUS current
            DESCRIPTION
                "Manufacture date/time"
            ::= { scmBatteryEntry 3 }

        scmBatteryDeviceName OBJECT-TYPE
            SYNTAX DisplayString
            MAX-ACCESS read-only
            STATUS current
            DESCRIPTION
                "Device Name of this battery."
            ::= { scmBatteryEntry 4 }

        scmBatteryPart OBJECT-TYPE
            SYNTAX IdromBinary16
            MAX-ACCESS read-only
            STATUS current
            DESCRIPTION
                "Device Part Number"
            ::= { scmBatteryEntry 5 }

        scmBatterySerialNo OBJECT-TYPE
            SYNTAX IdromBinary16
            MAX-ACCESS read-only
            STATUS current
            DESCRIPTION
                "Device Serial Number"
            ::= { scmBatteryEntry 6 }

        scmBatteryMaximumPower OBJECT-TYPE
            SYNTAX Power
            MAX-ACCESS read-only
            STATUS current
            DESCRIPTION
                "Static maximum power generation / consumption (in watts):

                <0      - Negative numbers indicate device consumes power (in watts)
                >0      - Positive numbers indicate device generates power (in watts)
                0       - Device is passive (does not not consume or generate power)
                -1      - Nominal power generation/consumption not known or specified"
            ::= { scmBatteryEntry 7 }

        scmBatteryNominalPower OBJECT-TYPE
            SYNTAX Power
            MAX-ACCESS read-only
            STATUS current
            DESCRIPTION
                "Static Nominal power generation / consumption (in watts):

                <0      - Negative numbers indicate device consumes power (in watts)
                >0      - Positive numbers indicate device generates power (in watts)
                0       - Device is passive (does not not consume or generate power)
                -1      - Nominal power generation/consumption not known or specified"
            ::= { scmBatteryEntry 8 }

        scmBatteryAssetTag OBJECT-TYPE
            SYNTAX IdromBinary16
            MAX-ACCESS read-only
            STATUS current
            DESCRIPTION
                "Asset Tag # of device"
            ::= { scmBatteryEntry 9 }

        scmBatteryDeviceChemistry OBJECT-TYPE
            SYNTAX DisplayString
            MAX-ACCESS read-only
            STATUS current
            DESCRIPTION
                "Device Chemistry of this battery."
            ::= { scmBatteryEntry 10 }

        scmBatteryTemperature OBJECT-TYPE
            SYNTAX INT32withException
            MAX-ACCESS read-only
            STATUS current
            DESCRIPTION
                "Temperature of this battery in celsius."
            ::= { scmBatteryEntry 11 }

        scmBatteryTempChargeThreshold OBJECT-TYPE
            SYNTAX INT32withException
            MAX-ACCESS read-only
            STATUS current
            DESCRIPTION
                "Temperature in celsius threshold for charging of this battery."
            ::= { scmBatteryEntry 12 }

        scmBatteryTempDisChargeThreshold OBJECT-TYPE
            SYNTAX INT32withException
            MAX-ACCESS read-only
            STATUS current
            DESCRIPTION
                "Temperature in celsius threshold for discharging of this
                battery."
            ::= { scmBatteryEntry 13 }

        scmBatteryCycleCount OBJECT-TYPE
            SYNTAX INT32withException
            MAX-ACCESS read-only
            STATUS current
            DESCRIPTION
                "Cycle Count of this battery."
            ::= { scmBatteryEntry 14 }

        scmBatteryRemainCapacity OBJECT-TYPE
            SYNTAX INT32withException
            MAX-ACCESS read-only
            STATUS current
            DESCRIPTION
                "Remaining capacity in percentage of this battery."
            ::= { scmBatteryEntry 15 }

        scmBatteryVoltage OBJECT-TYPE
            SYNTAX INT32withException
            MAX-ACCESS read-only
            STATUS current
            DESCRIPTION
                "Voltage in mV of this battery."
            ::= { scmBatteryEntry 16 }

        scmBatteryCurrent OBJECT-TYPE
            SYNTAX INT32withException
            MAX-ACCESS read-only
            STATUS current
            DESCRIPTION
                "Current in mA of this battery."
            ::= { scmBatteryEntry 17 }

        scmBatteryStatus OBJECT-TYPE
            SYNTAX DisplayString
            MAX-ACCESS read-only
            STATUS current
            DESCRIPTION
                "Status of this battery."
            ::= { scmBatteryEntry 18 }

        scmBatteryCellType    OBJECT-TYPE    
            SYNTAX INTEGER  { 
                    notApplicable(-32),
                    unknown(-16),
                    twoCell(2), 
                    fourCell(4)
            } 
            MAX-ACCESS        read-only
            STATUS            current
            DESCRIPTION        
                "The type of the battery cell."
            ::=  {  scmBatteryEntry  19  }


        scmBatteryHoldTime    OBJECT-TYPE    
            SYNTAX INT32withException
            MAX-ACCESS        read-only
            STATUS            current
            DESCRIPTION        
                "The hold time of battery in hour."
            ::=  {  scmBatteryEntry  20  }


--
-- (Controller) Actions
--

--
-- (Controller) Group information
--

        ctlGroup OBJECT-GROUP
            OBJECTS {

                maxScms,
                numOfScms,
                scmPresenceMask,

                scmIndex,
                scmPresence,
                scmVendor,
                scmMfgDate,
                scmDeviceName,
                scmPart,
                scmSerialNo,
                scmMaximumPower,
                scmNominalPower,
                scmAssetTag,
                scmManagementMac,
                scmWWN,
                scmSCSIProtocol,
                scmPowerLed,
                scmFaultLed,
                scmFirmwareVersion,
                scmOpStatus,
                scmRole,
                scmReadinessStatus,
                scmNumOfPoolsPresent,
                scmNumOfPhysicalDrivesPresent,
                scmNumOfPhysicalDrivesOnline,
                scmNumOfPhysicalDrivesOffline,
                scmNumOfPhysicalDrivesWithPFA,
                scmNumOfPhysicalDrivesRebuilding,
                scmNumOfPhysicalDrivesMissing,
                scmNumOfPhysicalDrivesUnconfigured,
                scmNumOfVirtualDrivesPresent,
                scmNumOfVirtualDrivesOnline,
                scmNumOfVirtualDrivesOffline,
                scmNumOfVirtualDrivesCritical,
                scmNumOfGlobalSparesPresent,
                scmNumOfDedicatedSparesPresent,
                scmNumOfRevertibleGlobalSparesPresent,
                scmNumOfRevertibleGlobalSparesUsed,
                scmNumOfRevertibleDedicatedSparesPresent,
                scmNumOfRevertibleDedicatedSparesUsed,
                scmNumOfBGAs,
                scmPowerOnHours,
                scmDirtyCachePercentage,
                scmCacheUsagePercentage,

                scmStatsDataTransferred,
                scmStatsReadDataTransferred,
                scmStatsWriteDataTransferred,
                scmStatsNumOfErrors,
                scmStatsNumOfNonRWErrors,
                scmStatsNumOfReadErrors,
                scmStatsNumOfWriteErrors,
                scmStatsNumOfIORequests,
                scmStatsNumOfNonRWRequests,
                scmStatsNumOfReadRequests,
                scmStatsNumOfWriteRequests,
                scmStatsStartTime,
                scmStatsCollectionTime,

                scmBatteryPresence,
                scmBatteryVendor,
                scmBatteryMfgDate,
                scmBatteryDeviceName,
                scmBatteryPart,
                scmBatterySerialNo,
                scmBatteryMaximumPower,
                scmBatteryNominalPower,
                scmBatteryAssetTag,
                scmBatteryDeviceChemistry,
                scmBatteryTemperature,
                scmBatteryTempChargeThreshold,
                scmBatteryTempDisChargeThreshold,
                scmBatteryCycleCount,
                scmBatteryRemainCapacity,
                scmBatteryVoltage,
                scmBatteryCurrent,
                scmBatteryStatus,
                scmBatteryCellType,
                scmBatteryHoldTime

            }
            STATUS current
            DESCRIPTION
                "Description."
            ::= { groups 14 }

    END

--  vim:ts=4:ai:nohls:nowrap:expandtab
