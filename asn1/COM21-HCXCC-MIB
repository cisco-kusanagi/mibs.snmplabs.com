-- 
--  Copyright 1996, Com21 Inc.  All Rights Reserved.
--
 
COM21-HCXCC-MIB DEFINITIONS ::= BEGIN
  IMPORTS 
        MODULE-IDENTITY, OBJECT-TYPE, NOTIFICATION-TYPE, Integer32,
        IpAddress, Gauge32
            FROM SNMPv2-SMI
        DisplayString
            FROM SNMPv2-TC
	      com21, com21Hcx
	          FROM COM21-HCX-MIB
			com21Traps FROM COM21-HCX-MIB
        hcxAlmSeverity, hcxEventLogTime
            FROM COM21-HCXALM-MIB;


        com21HcxCc MODULE-IDENTITY
                LAST-UPDATED "9701080000Z"
                ORGANIZATION "Com21, Inc."
                CONTACT-INFO
                "       Network Management
                                Postal: Paul Gordon
                                Com21, Inc.
                                750 Tasman Drive
                                Milpitas, California 95035
                                USA
                                Tel: +1 408 953 9100
                                Fax: +1 408 953 9299
                                E-mail: pgordon@com21.com"

                DESCRIPTION
                        "This is the Com21 ComController Common Control 
			   Unit MIB module. COM21 Part# 005-0025-00"
                ::= { com21Hcx 60 }


        com21HcxCcUnitGroup         OBJECT IDENTIFIER ::= {com21Hcx 61 }
        com21HcxCcNtpGroup          OBJECT IDENTIFIER ::= {com21Hcx 62 }

        PrimServiceState ::= INTEGER { is(1), oos(2) }
        Com21RowStatus   ::= INTEGER { active(1), create(2), destroy(3),
                                       deactive(4) }


        -- -- -- -- -- -- -- -- -- -- -- -- -- -- -- -- -- -- -- -- -- -- -- --
        -- -- -- -- -- -- -- -- -- -- -- -- -- -- -- -- -- -- -- -- -- -- -- --
        --
        -- COM21 ComController Enterprise MIB
        --
        -- This MIB contains SNMP Groups and Attributes definitions for COM21
        -- specific management.
        -- Also supported by the ComController shall be the MIB II for the 
	-- SNMP interface and the MIB II Interfaces Group for both the 
	-- ComController and ComPort Ethernet interfaces.
        -- This Enterprise MIB contains many elements of the ATM UNI 2.1 ILMI
        -- MIB. This full MIB is not presently supported by the COM21 equipment
        -- as there are no external UNI interfaces. When this changes then the
        -- full MIB should be supported and the related Enterprise MIB entries
        -- removed.
        --
        --   com21HcxCcUnitGroup        - this group provides for monitor and
        --                                control of a single CC card.
        --
	--   com21HcxCcNtpGroup		- this group provides for the
	--				  configuration time servers.
	--
        -- -- -- -- -- -- -- -- -- -- -- -- -- -- -- -- -- -- -- -- -- -- -- --
        -- -- -- -- -- -- -- -- -- -- -- -- -- -- -- -- -- -- -- -- -- -- -- --



	-- -- -- -- -- -- -- -- -- -- -- -- -- -- -- -- -- -- -- -- -- -- -- --
	-- -- -- -- -- -- -- -- -- -- -- -- -- -- -- -- -- -- -- -- -- -- -- --
	--
	-- com21HcxCcUnitGroup
	--
	-- defines the attributes related to the management of the 
	-- ComController CC Unit.
	--
	-- -- -- -- -- -- -- -- -- -- -- -- -- -- -- -- -- -- -- -- -- -- -- --
	-- -- -- -- -- -- -- -- -- -- -- -- -- -- -- -- -- -- -- -- -- -- -- --

        hcxCcShelfId OBJECT-TYPE
                SYNTAX INTEGER (1..2)
                MAX-ACCESS read-only
                STATUS current
                DESCRIPTION "
                        contains the associated shelf id."
                ::= { com21HcxCcUnitGroup 1 }

        hcxCcSlotId OBJECT-TYPE
                SYNTAX Integer32
                MAX-ACCESS read-only
                STATUS current
                DESCRIPTION "
                        contains the Common Controller slot id."
                ::= { com21HcxCcUnitGroup 2 }

        hcxCcHardwareVersion OBJECT-TYPE
                SYNTAX DisplayString (SIZE (16))
                MAX-ACCESS read-only   
                STATUS current
                DESCRIPTION "  
                        contains the hardware version of the CC card."
                ::= { com21HcxCcUnitGroup 3 }
 
        hcxCcBootVersion OBJECT-TYPE
                SYNTAX DisplayString (SIZE (16))
                MAX-ACCESS read-only
                STATUS current
                DESCRIPTION "
                        contains the version of the CC card boot ROM."
                ::= { com21HcxCcUnitGroup 4 }

        hcxSoftwareRevision OBJECT-TYPE
                SYNTAX DisplayString (SIZE(32))
                MAX-ACCESS read-only
                STATUS current
                DESCRIPTION "
                        The Common Controller Software Revision is a
                        display string value which contains the software
                        revision of the currently loaded COM21 Common
                        Controller software downloaded from the software
                        server device."
                ::= { com21HcxCcUnitGroup 6 }

        hcxControlPrimServState OBJECT-TYPE
                SYNTAX PrimServiceState
                MAX-ACCESS read-only
                STATUS current
                DESCRIPTION "
                        contains primary service state of the Common
                        Controller. This attribute indicates the overall
                        service state of the Controller. OOS indicates that
                        complete service cannot be provided. IS indicates
                        that the Controller is operating as normal, though
                        a non-service effecting error or test condition may
                        exist."   
                ::= { com21HcxCcUnitGroup 7 }

        hcxControlPrimServStateChange NOTIFICATION-TYPE
                OBJECTS { hcxAlmSeverity, hcxEventLogTime,
                            hcxCcShelfId, hcxCcSlotId,
                            hcxControlPrimServState }
                STATUS current
                DESCRIPTION "
                        generated whenever hcxControlPrimaryServiceState
                        changes value. This an event with no clear condition.
                        Only severity is WARNING."
                ::= { com21Traps 10 }

        hcxControlSecServState OBJECT-TYPE
                SYNTAX DisplayString (SIZE (16))
                MAX-ACCESS read-only  
                STATUS current
                DESCRIPTION "  
                        contains a string defining the secondary service states
                        of the Common Controller. The states supported by the
                        com21HcxControlGroup are: FAN - indicates Fan Failure,
                        HIGH - indicates high temp condition, PWR - indicates
                        power problem."
                ::= { com21HcxCcUnitGroup 8 }
 
        hcxControlSecServStateChange NOTIFICATION-TYPE
                OBJECTS { hcxAlmSeverity, hcxEventLogTime,
                            hcxCcShelfId, hcxCcSlotId,
                            hcxControlSecServState }
                STATUS current
                DESCRIPTION "
                        generated whenever hcxControlSecondaryServiceState
                        changes value. This an event with no clear condition.
                        Only severity is WARNING."
                ::= { com21Traps 11 }
  
        hcxCcDiagTestAction OBJECT-TYPE
                SYNTAX INTEGER { nil(1), execute(2) }
                MAX-ACCESS read-write
                STATUS current
                DESCRIPTION "
                        This attribute is used to invoke the internal
                        Common Controller diagnostic test. In order to 
			activate this test, the card must be placed in 
			the test state."
                ::= { com21HcxCcUnitGroup 9 }
 
        hcxCcDiagTestComplete NOTIFICATION-TYPE
                OBJECTS { hcxAlmSeverity, hcxEventLogTime,
                            hcxCcShelfId, hcxCcSlotId,
                            hcxCcDiagTestResult }
                STATUS current
                DESCRIPTION "
                        This notification is generated whenever the CC
                        card internal diagnostic tests are completed. Event
                        only, no clear. Only severity allowed is WARNING."
                ::= { com21Traps 12 }
         
        hcxCcDiagTestResult OBJECT-TYPE
                SYNTAX INTEGER { 
				inprogress(1),
				success(2), 
				failure(3),
				invalidState(4) }
                MAX-ACCESS read-only
                STATUS current
                DESCRIPTION "
                        This attribute contains the result of the last CC
                        card diagnostic test."
                ::= { com21HcxCcUnitGroup 10 }
 
        hcxCcTestStatusLed OBJECT-TYPE
                SYNTAX INTEGER { on (1), off (2) }
                MAX-ACCESS read-only
                STATUS current
                DESCRIPTION "
                        The CC Test Status LED is a read-only attribute 
			which describes the condition of the CC Test
                        Status light emitting diode located on the CC.
			This indicates that a service effecting test is
			in progress and that the LED is illuminated."
                ::= { com21HcxCcUnitGroup 11 }
 
        hcxCcTestStatusLedChange NOTIFICATION-TYPE
                OBJECTS { hcxAlmSeverity, hcxEventLogTime,
                            hcxCcShelfId, hcxCcSlotId,
                            hcxCcTestStatusLed }
                STATUS current
                DESCRIPTION "
                        generated whenever there is a change in test LED
                        status. This an event with no clear condition.
                        Only severity is WARNING."
                ::= { com21Traps 13 }
 
        hcxCcFaultStatusLed OBJECT-TYPE
                SYNTAX INTEGER { on (1), off (2) }
                MAX-ACCESS read-only
                STATUS current
                DESCRIPTION "
                        The Ethernet Fault Status LED is a read-only
                        attribute which describes the condition of the
                        ComController Ethernet Fault Status light emitting 
			diode located on the Ethernet board. A value of on(1)
                        indicates that an fault condition has been detected
                        (for which a trap will have been issued) and the
                        LED is illuminated."
                ::= { com21HcxCcUnitGroup 12 }
 
        hcxCcFaultStatusLedChange NOTIFICATION-TYPE
                OBJECTS { hcxAlmSeverity, hcxEventLogTime,
                            hcxCcShelfId, hcxCcSlotId,
                            hcxCcFaultStatusLed }
                STATUS current
                DESCRIPTION "
                        generated whenever there is a change in the Fault
                        LED status. This an event with no clear condition.
                        Only severity is WARNING."
                ::= { com21Traps 14 }

        hcxCcEtherLinkStatusLed OBJECT-TYPE
                SYNTAX INTEGER { on (1), off (2) }
                MAX-ACCESS read-only
                STATUS current
                DESCRIPTION "
                        The Ethernet Link Status LED is a read-only
                        attribute which describes the condition of the
                        CC Ethernet Link Status light emitting diode
                        located on the CC board. A value of on(1)
                        indicates that the link is up and active, and
                        that the LED is illuminated. Will be off if no
                        card present."
                ::= { com21HcxCcUnitGroup 13 }

        hcxCcEtherLinkStatusLedChange NOTIFICATION-TYPE
                OBJECTS { hcxAlmSeverity, hcxEventLogTime,
                            hcxCcShelfId, hcxCcSlotId,
                            hcxCcEtherLinkStatusLed }
                STATUS current
                DESCRIPTION "
                        generated whenever there is a change in link LED
                        status. This an event with no clear condition.
                        Only severity is WARNING."
                ::= { com21Traps 15 }

        hcxCcFlashBackupPeriod OBJECT-TYPE
                SYNTAX INTEGER (5..900)
                MAX-ACCESS read-write
                STATUS current
                DESCRIPTION "
                        The period (in seconds) at which the CC shall 
			automatically backup any configuration data to 
			flash. This must be a multiple of 5 seconds upto 
			15 minutes. Default is 60 seconds."
                ::= { com21HcxCcUnitGroup 14 }

        hcxCcFlashBackupAction OBJECT-TYPE
                SYNTAX INTEGER { nil(1), execute(2) }
                MAX-ACCESS read-write
                STATUS current
                DESCRIPTION "
                        This attribute is used to invoke the Common
                        Controller to save all configuration data to
                        flash."
                ::= { com21HcxCcUnitGroup 15 }

        hcxCcFlashBackupComplete NOTIFICATION-TYPE
                OBJECTS { hcxAlmSeverity, hcxEventLogTime,
                            hcxCcShelfId, hcxCcSlotId,
                            hcxCcFlashBackupResult }
                STATUS current
                DESCRIPTION "
                        This notification is generated whenever the CC
                        card completes a user directed flash backup of
                        configuration. Only severity allowed is WARNING."
                ::= { com21Traps 16 }
         
        hcxCcFlashBackupResult OBJECT-TYPE
                SYNTAX INTEGER {
                                inprogress(1),
                                success(2),
                                failure(3) }
                MAX-ACCESS read-only
                STATUS current
                DESCRIPTION "
                        This attribute contains the result of the last CC
                        user directed flash backup."
                ::= { com21HcxCcUnitGroup 16 }

        hcxSwitchSoftwareRevision OBJECT-TYPE
                SYNTAX DisplayString (SIZE(32))
                MAX-ACCESS read-only
                STATUS current
                DESCRIPTION "
                        software revision of the image loaded on the
			embedded ATM switch. In the case of the compact
			ComController this attribute refers to the boot
			software version."
                ::= { com21HcxCcUnitGroup 17 }

        hcxSwitchHardwareRevision OBJECT-TYPE
                SYNTAX DisplayString (SIZE(32))
                MAX-ACCESS read-only
                STATUS current
                DESCRIPTION "
                        hardware revision of the embedded ATM switch. This
			attribute is only applicable for the compact 
			ComController."
                ::= { com21HcxCcUnitGroup 18 }

        hcxSwitchSerialNumber OBJECT-TYPE 
                SYNTAX DisplayString (SIZE(32)) 
                MAX-ACCESS read-only 
                STATUS current 
                DESCRIPTION " 
                        serial number of the embedded ATM switch. This
                        attribute is only applicable for the compact 
                        ComController."
                ::= { com21HcxCcUnitGroup 19 }

        hcxNtpv3Control OBJECT-TYPE
                SYNTAX INTEGER { disable(1), enable(2) }
                MAX-ACCESS read-write
                STATUS current
                DESCRIPTION "
                        this attribute controls the NTPv3 feature.
			This features should NOT be enabled if NMAPS
			is in use. The timer servers are specified via
			com21HcxCcNtpGroup. Default diasble."
                ::= { com21HcxCcUnitGroup 20 }

        hcxDiskFaultState OBJECT-TYPE
                SYNTAX INTEGER { 
				noFault(1), 
				notInstalled(2),
				notMounted(3),
				failed(4) }
                MAX-ACCESS read-only
                STATUS current
                DESCRIPTION "
                        this attribute describes the fault state of the
			PCMCIA disk."
                ::= { com21HcxCcUnitGroup 21 }

        hcxDiskIdentifier OBJECT-TYPE
                SYNTAX DisplayString (SIZE(40))
                MAX-ACCESS read-only
                STATUS current
                DESCRIPTION "
                        this attribute indentifies the type of PCMCIA
                        device."
                ::= { com21HcxCcUnitGroup 22 }

        hcxDiskAccessFailure NOTIFICATION-TYPE
                OBJECTS { hcxAlmSeverity, hcxEventLogTime,
                            hcxCcShelfId, hcxCcSlotId,
                            hcxDiskFaultState }
                STATUS current
                DESCRIPTION "
                        generated whenever there is a failure to access
			the PCMCIA disk. Default severity is MAJOR."
                ::= { com21Traps 17 }

	hcxDiskAccessFailClear NOTIFICATION-TYPE
                OBJECTS { hcxAlmSeverity, hcxEventLogTime,
                            hcxCcShelfId, hcxCcSlotId }
                STATUS current
                DESCRIPTION "
                        generated whenever a previously reported disk
			failure is cleared. Severity is CLEARED."
                ::= { com21Traps 18 }

        hcxMibVersion OBJECT-TYPE
                SYNTAX Integer32
                MAX-ACCESS read-only
                STATUS current
                DESCRIPTION "
                        this attribute specifies the MIB version
                        used by CC."
                ::= { com21HcxCcUnitGroup 23 }



        -- -- -- -- -- -- -- -- -- -- -- -- -- -- -- -- -- -- -- -- -- -- -- --
        -- -- -- -- -- -- -- -- -- -- -- -- -- -- -- -- -- -- -- -- -- -- -- --
        --
        -- com21HcxCcNtpGroup
        --
        -- defines any NTPv3 time servers. This group shall only be accessed
	-- if the hcxNtpv3Control attribute is set to enable.
        --
        -- -- -- -- -- -- -- -- -- -- -- -- -- -- -- -- -- -- -- -- -- -- -- --
        -- -- -- -- -- -- -- -- -- -- -- -- -- -- -- -- -- -- -- -- -- -- -- --

        com21HcxCcNtpTable OBJECT-TYPE
                SYNTAX  SEQUENCE OF HcxCcNtpEntry
                MAX-ACCESS  not-accessible
                STATUS  current
                DESCRIPTION "."
                ::= { com21HcxCcNtpGroup 1 }
 
        com21HcxCcNtpEntry OBJECT-TYPE
                SYNTAX  HcxCcNtpEntry
                MAX-ACCESS  not-accessible
                STATUS  current
                DESCRIPTION "."
                INDEX { hcxCcNtpServerIndex }
                ::= { com21HcxCcNtpTable 1 }
 
        HcxCcNtpEntry ::= SEQUENCE {
                hcxCcNtpServerIndex       INTEGER,
                hcxCcNtpServerAddress     IpAddress,
		hcxCcNtpServerAddrStatus  Com21RowStatus }
 
        hcxCcNtpServerIndex OBJECT-TYPE
                SYNTAX INTEGER (1..6)
                MAX-ACCESS read-only
                STATUS current
                DESCRIPTION "
                        this attribute defines both the index of the address
			entry. The CC shall attempt to access each in order 
			starting with index 1."
                ::= { com21HcxCcNtpEntry 1 }

        hcxCcNtpServerAddress OBJECT-TYPE
                SYNTAX IpAddress
                MAX-ACCESS read-write
                STATUS current
                DESCRIPTION "
                        this attribute defines both the IP address of 
			a time server."
                ::= { com21HcxCcNtpEntry 2 }

        hcxCcNtpServerAddrStatus OBJECT-TYPE
                SYNTAX Com21RowStatus
                MAX-ACCESS read-create
                STATUS current
                DESCRIPTION "
			Used to delete or create an entry."
                ::= { com21HcxCcNtpEntry 3 }

   
END
