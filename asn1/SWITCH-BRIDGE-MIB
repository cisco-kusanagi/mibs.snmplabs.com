SWITCH-BRIDGE-MIB 
DEFINITIONS ::= BEGIN
    IMPORTS
    MODULE-IDENTITY, OBJECT-TYPE, NOTIFICATION-TYPE,
    TimeTicks, Counter32, Integer32     FROM SNMPv2-SMI
    TEXTUAL-CONVENTION, MacAddress      FROM SNMPv2-TC
    InterfaceIndex                      FROM IF-MIB
    bridgeModule                        FROM TELESYN-ATI-TC
    vLanNumber                          FROM SWITCH-VLAN-MIB
;
 
switchBridgeMib MODULE-IDENTITY
    LAST-UPDATED "9605312200Z"
	ORGANIZATION ""
	CONTACT-INFO ""
	DESCRIPTION  
			"The MIB module for bridge and spanning tree protocol.  This
			mib  is based on RFC 1493 with modifications to support
			multiple  bridges, one for each virtual LAN (VLAN), in one
			physical chassis.  The bridge protocol attributes are now in
			a table indexed by the  vLanNumber.  The port number used to
			index various tables is now a  virtual port number
			corresponding to the virtual port defined in the
			SWITCH-VLAN-MIB."
    REVISION "9704182200Z"
    DESCRIPTION
			"Corrected names to switchBridge because of possible identifier.
			
			Corrected the MAX-ACCESS clause for writable objects in the
			switchBridgeStaticEntry from read-write to read-create. Modified
			description of switchBridgeStaticAllowedToGoTo.  This object is
			also read-only because it maps to the set of ports in a VLAN.
			
			Removed the mib compiler specific extensions into a separate
			file."
	REVISION "9605312200Z"
	DESCRIPTION "Initial version"
	::= { bridgeModule	5 }
    BridgeId ::= TEXTUAL-CONVENTION
        DISPLAY-HINT       "1x"
        STATUS             current
        DESCRIPTION
             "Protocol to uniquely identify a bridge.  Its first two
             octets (in network byte order) contain a priority
             value and its last 6 octets contain the MAC address
             used to refer to a bridge in a unique fashion
             (typically, the numerically smallest MAC address
             of all ports on the bridge)."
        SYNTAX  OCTET STRING (SIZE (8)) 
      
      
      
      
      
      
      
      
      
      
      
    Timeout ::= TEXTUAL-CONVENTION
        DISPLAY-HINT       "d"
        STATUS             current
        DESCRIPTION
            "a STP timer in units of 1/100 seconds"
        SYNTAX    Integer32
          
          switchBridgeBase     OBJECT IDENTIFIER ::= { switchBridgeMib 1 }
          switchBridgeStp      OBJECT IDENTIFIER ::= { switchBridgeMib 2 }
          switchBridgeSr       OBJECT IDENTIFIER ::= { switchBridgeMib 3 }
          switchBridgeTp       OBJECT IDENTIFIER ::= { switchBridgeMib 4 }
          switchBridgeStatic   OBJECT IDENTIFIER ::= { switchBridgeMib 5 }
          switchBridgeTrapsGroup    OBJECT IDENTIFIER ::= { switchBridgeMib 6 }
          switchBridgeTraps    OBJECT IDENTIFIER ::= { switchBridgeTrapsGroup 0 }
          
          
          
      switchBridgeBaseTable OBJECT-TYPE
	      SYNTAX  SEQUENCE OF SwitchBridgeBaseEntry
	      MAX-ACCESS  not-accessible
	      STATUS      current
	      DESCRIPTION
		      "A table that contains generic information about
		      every bridge."
	      ::= { switchBridgeBase 1 }
      switchBridgeBaseEntry OBJECT-TYPE
	      SYNTAX  SwitchBridgeBaseEntry
	      MAX-ACCESS  not-accessible
	      STATUS      current
	      DESCRIPTION
		      "A list of information for each bridge supported by the VLAN."
	      INDEX  { vLanNumber }
	      ::= { switchBridgeBaseTable 1 }
		SwitchBridgeBaseEntry ::= SEQUENCE {
		   switchBridgeBaseAddress	MacAddress,
		   switchBridgeBaseNumPorts	Integer32,
		   switchBridgeBaseType		INTEGER
		}
          switchBridgeBaseAddress OBJECT-TYPE
              SYNTAX  MacAddress
              MAX-ACCESS  read-only
              STATUS      current
              DESCRIPTION
                      "The MAC address used by this bridge when it must
                      be referred to in a unique fashion.   It is
                      recommended that this be the numerically smallest
                      MAC address of all ports that belong to this
                      bridge.  However it is only required to be unique.
                      When concatenated with switchBridgeStpPriority a unique
                      BridgeIdentifier is formed which is used in the
                      Spanning Tree Protocol."
              REFERENCE
                      "IEEE 802.1D-1990: Sections 6.4.1.1.3 and 3.12.5"
              ::= { switchBridgeBaseEntry 1 }
          switchBridgeBaseNumPorts OBJECT-TYPE
              SYNTAX  Integer32
              MAX-ACCESS  read-only
              STATUS        current
              DESCRIPTION
                      "The number of ports controlled by this bridging
                      entity."
              REFERENCE
                      "IEEE 802.1D-1990: Section 6.4.1.1.3"
              ::= { switchBridgeBaseEntry 2 }
          switchBridgeBaseType OBJECT-TYPE
              SYNTAX  INTEGER {
                          unknown(1),
                          transparentOnly(2),
                          sourceRouteOnly(3),
                          srt(4)
                      }
              MAX-ACCESS  read-only
              STATUS      current
              DESCRIPTION
                      "Indicates what type of bridging this bridge can
                      perform.  If a bridge is actually performing a
                      certain type of bridging this will be indicated by
                      entries in the port table for the given type."
              ::= { switchBridgeBaseEntry 3 }
    
      switchBridgeBasePortTable OBJECT-TYPE
	      SYNTAX  SEQUENCE OF SwitchBridgeBasePortEntry
	      MAX-ACCESS  not-accessible
	      STATUS      current
	      DESCRIPTION
		      "A table that contains generic information about
		      every port that is associated with this bridge.
		      Transparent, source-route, and srt ports are
		      included."
	      ::= { switchBridgeBase 2 }
      switchBridgeBasePortEntry OBJECT-TYPE
	      SYNTAX  SwitchBridgeBasePortEntry
	      MAX-ACCESS  not-accessible
	      STATUS      current
	      DESCRIPTION
		      "A list of information for each port of the
		      bridge."
	      REFERENCE
		      "IEEE 802.1D-1990: Section 6.4.2, 6.6.1"
	      INDEX  { vLanNumber, switchBridgeBasePort }
	      ::= { switchBridgeBasePortTable 1 }
      SwitchBridgeBasePortEntry ::= SEQUENCE {
	      switchBridgeBasePort            INTEGER,
	      switchBridgeBasePortIfIndex     InterfaceIndex,
	      switchBridgeBasePortCircuit     OBJECT IDENTIFIER,
	      switchBridgeBasePortDelayExceededDiscards  Counter32,
	      switchBridgeBasePortMtuExceededDiscards    Counter32
	  }
      switchBridgeBasePort OBJECT-TYPE
	      SYNTAX  INTEGER (1..256)
	      MAX-ACCESS  not-accessible
	      STATUS      current
	      DESCRIPTION
		      "The virtual port number of the port for which this entry
		      contains bridge management information."
	      ::= { switchBridgeBasePortEntry 1 }
      switchBridgeBasePortIfIndex OBJECT-TYPE
	      SYNTAX  InterfaceIndex
	      MAX-ACCESS  read-only
	      STATUS      current
	      DESCRIPTION
		      "The value of the instance of the ifIndex object,
		      defined in MIB-II, for the interface corresponding
		      to this port."
	      ::= { switchBridgeBasePortEntry 2 }
      switchBridgeBasePortCircuit OBJECT-TYPE
	      SYNTAX  OBJECT IDENTIFIER
	      MAX-ACCESS  read-only
	      STATUS      current
	      DESCRIPTION
		      "For a port which (potentially) has the same value
		      of switchBridgeBasePortIfIndex as another port on the
		      same bridge, this object contains the name of an
		      object instance unique to this port.  For example,
		      in the case where multiple ports correspond one-
		      to-one with multiple X.25 virtual circuits, this
		      value might identify an (e.g., the first) object
		      instance associated with the X.25 virtual circuit
		      corresponding to this port.
    
		      For a port which has a unique value of
		      switchBridgeBasePortIfIndex, this object can have the
		      value { 0 0 }."
	      ::= { switchBridgeBasePortEntry 3 }
      switchBridgeBasePortDelayExceededDiscards OBJECT-TYPE
	      SYNTAX  Counter32
	      MAX-ACCESS  read-only
	      STATUS      current
	      DESCRIPTION
		      "The number of frames discarded by this port due
		      to excessive transit delay through the bridge.  It
		      is incremented by both transparent and source
		      route bridges."
	      REFERENCE
		       "IEEE 802.1D-1990: Section 6.6.1.1.3"
	      ::= { switchBridgeBasePortEntry 4 }
    
      switchBridgeBasePortMtuExceededDiscards OBJECT-TYPE
	      SYNTAX  Counter32
	      MAX-ACCESS  read-only
	      STATUS      current
	      DESCRIPTION
		      "The number of frames discarded by this port due
		      to an excessive size.  It is incremented by both
		      transparent and source route bridges."
	      REFERENCE
		      "IEEE 802.1D-1990: Section 6.6.1.1.3"
	      ::= { switchBridgeBasePortEntry 5 }
    
      
      
      
      
      switchBridgeStpTable OBJECT-TYPE
	      SYNTAX  SEQUENCE OF SwitchBridgeStpEntry
	      MAX-ACCESS  not-accessible
	      STATUS      current
	      DESCRIPTION
		      "A table that parameters of the spanning tree protocol."
	     ::= { switchBridgeStp 1 }
      switchBridgeStpEntry OBJECT-TYPE
	      SYNTAX  SwitchBridgeStpEntry
	      MAX-ACCESS  not-accessible
	      STATUS      current
	      DESCRIPTION
		      "A list of protocol parameters for each instance of the
		      spanning tree protocol."
	      INDEX  { vLanNumber }
	      ::= { switchBridgeStpTable 1 }
      SwitchBridgeStpEntry ::= SEQUENCE {
	      switchBridgeStpProtocolSpecification    INTEGER,
	      switchBridgeStpPriority                 INTEGER,
	      switchBridgeStpTimeSinceTopologyChange  TimeTicks,
	      switchBridgeStpTopChanges               Counter32,
	      switchBridgeStpDesignatedRoot           BridgeId,
	      switchBridgeStpRootCost                 Integer32,
	      switchBridgeStpRootPort                 Integer32,
	      switchBridgeStpMaxAge                   Timeout,
	      switchBridgeStpHelloTime                Timeout,
	      switchBridgeStpHoldTime                 Integer32,
	      switchBridgeStpForwardDelay             Timeout,
	      switchBridgeStpBridgeMaxAge             Timeout,
	      switchBridgeStpBridgeHelloTime          Timeout,
	      switchBridgeStpBridgeForwardDelay       Timeout
      }
      switchBridgeStpProtocolSpecification OBJECT-TYPE
	      SYNTAX  INTEGER {
			  unknown(1),
			  decLb100(2),
			  ieee8021d(3)
		      }
	      MAX-ACCESS  read-only
	      STATUS      current
	      DESCRIPTION
		      "An indication of what version of the Spanning
		      Tree Protocol is being run.  The value
		      'decLb100(2)' indicates the DEC LANbridge 100
		      Spanning Tree protocol.  IEEE 802.1d
		      implementations will return 'ieee8021d(3)'.  If
		      future versions of the IEEE Spanning Tree Protocol
		      are released that are incompatible with the
		      current version a new value will be defined."
	      ::= { switchBridgeStpEntry 1 }
      switchBridgeStpPriority OBJECT-TYPE
	      SYNTAX  INTEGER (0..65535)
	      MAX-ACCESS  read-write
	      STATUS      current
	      DESCRIPTION
		      "The value of the write-able portion of the Bridge
		      ID, i.e., the first two octets of the (8 octet
		      long) Bridge ID.  The other (last) 6 octets of the
		      Bridge ID are given by the value of
		      switchBridgeBaseAddress."
	      REFERENCE
		      "IEEE 802.1D-1990: Section 4.5.3.7"
	      ::= { switchBridgeStpEntry 2 }
      switchBridgeStpTimeSinceTopologyChange OBJECT-TYPE
	      SYNTAX  TimeTicks
	      MAX-ACCESS  read-only
	      STATUS      current
	      DESCRIPTION
		      "The time (in hundredths of a second) since the
		      last time a topology change was detected by the
		      bridge entity."
	      REFERENCE
		      "IEEE 802.1D-1990: Section 6.8.1.1.3"
	      ::= { switchBridgeStpEntry 3 }
      switchBridgeStpTopChanges OBJECT-TYPE
	      SYNTAX  Counter32
	      MAX-ACCESS  read-only
	      STATUS      current
	      DESCRIPTION
		      "The total number of topology changes detected by
		      this bridge since the management entity was last
		      reset or initialized."
	      REFERENCE
		      "IEEE 802.1D-1990: Section 6.8.1.1.3"
	      ::= { switchBridgeStpEntry 4 }
      switchBridgeStpDesignatedRoot OBJECT-TYPE
	      SYNTAX  BridgeId
	      MAX-ACCESS  read-only
	      STATUS      current
	      DESCRIPTION
		      "The bridge identifier of the root of the spanning
		      tree as determined by the Spanning Tree Protocol
		      as executed by this node.  This value is used as
		      the Root Identifier parameter in all Configuration
		      Bridge PDUs originated by this node."
	      REFERENCE
		      "IEEE 802.1D-1990: Section 4.5.3.1"
	      ::= { switchBridgeStpEntry 5 }
      switchBridgeStpRootCost OBJECT-TYPE
	      SYNTAX  Integer32
	      MAX-ACCESS  read-only
	      STATUS      current
	      DESCRIPTION
		      "The cost of the path to the root as seen from
		      this bridge."
	      REFERENCE
		      "IEEE 802.1D-1990: Section 4.5.3.2"
	      ::= { switchBridgeStpEntry 6 }
      switchBridgeStpRootPort OBJECT-TYPE
	      SYNTAX  Integer32
	      MAX-ACCESS  read-only
	      STATUS      current
	      DESCRIPTION
		      "The port number of the port which offers the
		      lowest cost path from this bridge to the root
		      bridge."
	      REFERENCE
		      "IEEE 802.1D-1990: Section 4.5.3.3"
	     ::= { switchBridgeStpEntry 7 }
    
      switchBridgeStpMaxAge OBJECT-TYPE
	      SYNTAX  Timeout
	      MAX-ACCESS  read-only
	      STATUS      current
	      DESCRIPTION
		      "The maximum age of Spanning Tree Protocol
		      information learned from the network on any port
		      before it is discarded, in units of hundredths of
		      a second.  This is the actual value that this
		      bridge is currently using."
	      REFERENCE
		      "IEEE 802.1D-1990: Section 4.5.3.4"
	     ::= { switchBridgeStpEntry 8 }
      switchBridgeStpHelloTime OBJECT-TYPE
	      SYNTAX  Timeout
	      MAX-ACCESS  read-only
	      STATUS      current
	      DESCRIPTION
		      "The amount of time between the transmission of
		      Configuration bridge PDUs by this node on any port
		      when it is the root of the spanning tree or trying
		      to become so, in units of hundredths of a second.
		      This is the actual value that this bridge is
		      currently using."
	      REFERENCE
		      "IEEE 802.1D-1990: Section 4.5.3.5"
	      ::= { switchBridgeStpEntry 9 }
      switchBridgeStpHoldTime OBJECT-TYPE
	      SYNTAX  Integer32
	      MAX-ACCESS  read-only
	      STATUS      current
	      DESCRIPTION
		      "This time value determines the interval length
		      during which no more than two Configuration bridge
		      PDUs shall be transmitted by this node, in units
		      of hundredths of a second."
	      REFERENCE
		      "IEEE 802.1D-1990: Section 4.5.3.14"
	      ::= { switchBridgeStpEntry 10 }
      switchBridgeStpForwardDelay OBJECT-TYPE
	      SYNTAX  Timeout
	      MAX-ACCESS  read-only
	      STATUS      current
	      DESCRIPTION
		      "This time value, measured in units of hundredths
		      of a second, controls how fast a port changes its
		      spanning state when moving towards the Forwarding
		      state.  The value determines how long the port
		      stays in each of the Listening and Learning
		      states, which precede the Forwarding state.  This
		      value is also used, when a topology change has
		      been detected and is underway, to age all dynamic
		      entries in the Forwarding Database.  [Note that
		      this value is the one that this bridge is
		      currently using, in contrast to
		      switchBridgeStpBridgeForwardDelay which is the value that
		      this bridge and all others would start using
		      if/when this bridge were to become the root.]"
	      REFERENCE
		      "IEEE 802.1D-1990: Section 4.5.3.6"
	      ::= { switchBridgeStpEntry 11 }
      switchBridgeStpBridgeMaxAge OBJECT-TYPE
	      SYNTAX  Timeout (600..4000)
	      MAX-ACCESS  read-write
	      STATUS      current
	      DESCRIPTION
		      "The value that all bridges use for MaxAge when
		      this bridge is acting as the root.  Note that
		      802.1D-1990 specifies that the range for this
		      parameter is related to the value of
		      switchBridgeStpBridgeHelloTime. The granularity of this
		      timer is specified by 802.1D-1990 to be 1 second.
		      An agent may return a badValue error if a set is
		      attempted to a value which is not a whole number
		      of seconds."
	      REFERENCE
		      "IEEE 802.1D-1990: Section 4.5.3.8"
	      ::= { switchBridgeStpEntry 12 }
      switchBridgeStpBridgeHelloTime OBJECT-TYPE
	      SYNTAX  Timeout (100..1000)
	      MAX-ACCESS  read-write
	      STATUS      current
	      DESCRIPTION
		      "The value that all bridges use for HelloTime when
		      this bridge is acting as the root.  The
		      granularity of this timer is specified by 802.1D-
		      1990 to be 1 second.  An agent may return a
		      badValue error if a set is attempted to a value
		      which is not a whole number of seconds."
	      REFERENCE
		      "IEEE 802.1D-1990: Section 4.5.3.9"
	     ::= { switchBridgeStpEntry 13 }
      switchBridgeStpBridgeForwardDelay OBJECT-TYPE
	      SYNTAX  Timeout (400..3000)
	      MAX-ACCESS  read-write
	      STATUS      current
	      DESCRIPTION
		      "The value that all bridges use for ForwardDelay
		      when this bridge is acting as the root.  Note that
		      802.1D-1990 specifies that the range for this
		      parameter is related to the value of
		      switchBridgeStpBridgeMaxAge.  The granularity of this
		      timer is specified by 802.1D-1990 to be 1 second.
		      An agent may return a badValue error if a set is
		      attempted to a value which is not a whole number
		      of seconds."
	      REFERENCE
		      "IEEE 802.1D-1990: Section 4.5.3.10"
	      ::= { switchBridgeStpEntry 14 }
      
      switchBridgeStpPortTable OBJECT-TYPE
	      SYNTAX  SEQUENCE OF SwitchBridgeStpPortEntry
	      MAX-ACCESS  not-accessible
	      STATUS      current
	      DESCRIPTION
		      "A table that contains port-specific information
		      for the Spanning Tree Protocol."
	      ::= { switchBridgeStp 15 }
      switchBridgeStpPortEntry OBJECT-TYPE
	      SYNTAX  SwitchBridgeStpPortEntry
	      MAX-ACCESS  not-accessible
	      STATUS      current
	      DESCRIPTION
		      "A list of information maintained by every port
		      about the Spanning Tree Protocol state for that
		      port."
	      INDEX   { vLanNumber, switchBridgeStpPort }
	      ::= { switchBridgeStpPortTable 1 }
      SwitchBridgeStpPortEntry ::=
	  SEQUENCE {
	      switchBridgeStpPort                      INTEGER,
	      switchBridgeStpPortPriority              INTEGER,
	      switchBridgeStpPortState                 INTEGER,
	      switchBridgeStpPortEnable                INTEGER,
	      switchBridgeStpPortPathCost              INTEGER,
	      switchBridgeStpPortDesignatedRoot        BridgeId,
	      switchBridgeStpPortDesignatedCost        Integer32,
	      switchBridgeStpPortDesignatedBridge      BridgeId,
	      switchBridgeStpPortDesignatedPort        OCTET STRING,
	      switchBridgeStpPortForwardTransitions    Counter32
	  }
      switchBridgeStpPort OBJECT-TYPE
	      SYNTAX  INTEGER (1..256)
	      MAX-ACCESS  not-accessible
	      STATUS      current
	      DESCRIPTION
		      "The virtual port number of the port for which this entry
		      contains Spanning Tree Protocol management
		      information.
		      This number corresponds to the vPortNumber defined in
		      the SWITCH-VLAN-MIB"
	      ::= { switchBridgeStpPortEntry 1 }
      switchBridgeStpPortPriority OBJECT-TYPE
	      SYNTAX  INTEGER (0..255)
	      MAX-ACCESS  read-write
	      STATUS      current
	      DESCRIPTION
		      "The value of the priority field which is
		      contained in the first (in network byte order)
		      octet of the (2 octet long) Port ID.  The other
		      octet of the Port ID is given by the value of
		      switchBridgeStpPort."
	      REFERENCE
		      "IEEE 802.1D-1990: Section 4.5.5.1"
	      ::= { switchBridgeStpPortEntry 2 }
      switchBridgeStpPortState OBJECT-TYPE
	      SYNTAX  INTEGER {
				      disabled(1),
				      blocking(2),
				      listening(3),
				      learning(4),
				      forwarding(5),
				      broken(6)
			      }
	      MAX-ACCESS  read-only
	      STATUS      current
	      DESCRIPTION
		      "The port's current state as defined by
		      application of the Spanning Tree Protocol.  This
		      state controls what action a port takes on
		      reception of a frame.  If the bridge has detected
		      a port that is malfunctioning it will place that
		      port into the broken(6) state.  For ports which
		      are disabled (see switchBridgeStpPortEnable), this object
		      will have a value of disabled(1)."
	      REFERENCE
		      "IEEE 802.1D-1990: Section 4.5.5.2"
	      ::= { switchBridgeStpPortEntry 3 }
      switchBridgeStpPortEnable OBJECT-TYPE
	      SYNTAX  INTEGER {
                      enabled(1),
                      disabled(2)
                  }
	      MAX-ACCESS  read-write
	      STATUS      current
	      DESCRIPTION
		      "The enabled/disabled status of the port."
	      REFERENCE
		      "IEEE 802.1D-1990: Section 4.5.5.2"
	      ::= { switchBridgeStpPortEntry 4 }
      switchBridgeStpPortPathCost OBJECT-TYPE
	      SYNTAX  INTEGER (1..65535)
	      MAX-ACCESS  read-write
	      STATUS      current
	      DESCRIPTION
		      "The contribution of this port to the path cost of
		      paths towards the spanning tree root which include
		      this port.  802.1D-1990 recommends that the
		      default value of this parameter be in inverse
		      proportion to the speed of the attached LAN."
	      REFERENCE
		      "IEEE 802.1D-1990: Section 4.5.5.3"
	      ::= { switchBridgeStpPortEntry 5 }
      switchBridgeStpPortDesignatedRoot OBJECT-TYPE
	      SYNTAX  BridgeId
	      MAX-ACCESS  read-only
	      STATUS      current
	      DESCRIPTION
		      "The unique Bridge Identifier of the Bridge
		      recorded as the Root in the Configuration BPDUs
		      transmitted by the Designated Bridge for the
		      segment to which the port is attached."
	      REFERENCE
		      "IEEE 802.1D-1990: Section 4.5.5.4"
	      ::= { switchBridgeStpPortEntry 6 }
      switchBridgeStpPortDesignatedCost OBJECT-TYPE
	      SYNTAX  Integer32
	      MAX-ACCESS  read-only
	      STATUS      current
	      DESCRIPTION
		      "The path cost of the Designated Port of the
		      segment connected to this port.  This value is
		      compared to the Root Path Cost field in received
		      bridge PDUs."
	      REFERENCE
		      "IEEE 802.1D-1990: Section 4.5.5.5"
	      ::= { switchBridgeStpPortEntry 7 }
      switchBridgeStpPortDesignatedBridge OBJECT-TYPE
	      SYNTAX  BridgeId
	      MAX-ACCESS  read-only
	      STATUS      current
	      DESCRIPTION
		      "The Bridge Identifier of the bridge which this
		      port considers to be the Designated Bridge for
		      this port's segment."
	      REFERENCE
		      "IEEE 802.1D-1990: Section 4.5.5.6"
	      ::= { switchBridgeStpPortEntry 8 }
      switchBridgeStpPortDesignatedPort OBJECT-TYPE
	      SYNTAX  OCTET STRING (SIZE (2))
	      MAX-ACCESS  read-only
	      STATUS      current
	      DESCRIPTION
		      "The Port Identifier of the port on the Designated
		      Bridge for this port's segment."
	      REFERENCE
		      "IEEE 802.1D-1990: Section 4.5.5.7"
	      ::= { switchBridgeStpPortEntry 9 }
      switchBridgeStpPortForwardTransitions OBJECT-TYPE
	      SYNTAX  Counter32
	      MAX-ACCESS  read-only
	      STATUS      current
	      DESCRIPTION
		      "The number of times this port has transitioned
		      from the Learning state to the Forwarding state."
	      ::= { switchBridgeStpPortEntry 10 }
      
      
      
      
      
      switchBridgeTpLearnedEntryDiscards OBJECT-TYPE
	      SYNTAX  Counter32
	      MAX-ACCESS  read-only
	      STATUS      current
	      DESCRIPTION
		      "The total number of Forwarding Database entries,
		      which have been or would have been learned, but
		      have been discarded due to a lack of space to
		      store them in the Forwarding Database.  If this
		      counter is increasing, it indicates that the
		      Forwarding Database is regularly becoming full (a
		      condition which has unpleasant performance effects
		      on the subnetwork).  If this counter has a
		      significant value but is not presently increasing,
		      it indicates that the problem has been occurring
		      but is not persistent."
	      REFERENCE
		      "IEEE 802.1D-1990: Section 6.7.1.1.3"
	      ::= { switchBridgeTp 1 }
      switchBridgeTpBaseTable OBJECT-TYPE
	      SYNTAX  SEQUENCE OF SwitchBridgeTpBaseEntry
	      MAX-ACCESS  not-accessible
	      STATUS      current
	      DESCRIPTION
		      "A table that contains generic information about
		      every bridge."
	      ::= { switchBridgeTp 2 }
      switchBridgeTpBaseEntry OBJECT-TYPE
	      SYNTAX  SwitchBridgeTpBaseEntry
	      MAX-ACCESS  not-accessible
	      STATUS      current
	      DESCRIPTION
		      "A list of information for each bridge supported by the VLAN."
	      INDEX  { vLanNumber }
	      ::= { switchBridgeTpBaseTable 1 }
      SwitchBridgeTpBaseEntry ::= SEQUENCE {
          switchBridgeTpAgingTime             INTEGER
      }
      switchBridgeTpAgingTime OBJECT-TYPE
	      SYNTAX   INTEGER (10..1000000)
	      MAX-ACCESS   read-write
	      STATUS       current
	      DESCRIPTION
		      "The timeout period in seconds for aging out
		      dynamically learned forwarding information.
		      802.1D-1990 recommends a default of 300 seconds."
	      REFERENCE
		      "IEEE 802.1D-1990: Section 6.7.1.1.3"
	      ::= { switchBridgeTpBaseEntry 2 }
      
      switchBridgeTpFdbTable OBJECT-TYPE
	      SYNTAX  SEQUENCE OF SwitchBridgeTpFdbEntry
	      MAX-ACCESS  not-accessible
	      STATUS      current
	      DESCRIPTION
		      "A table that contains information about unicast
		      entries for which the bridge has forwarding and/or
		      filtering information.  This information is used
		      by the transparent bridging function-async in
		      determining how to propagate a received frame."
	      ::= { switchBridgeTp 3 }
      switchBridgeTpFdbEntry OBJECT-TYPE
	      SYNTAX  SwitchBridgeTpFdbEntry
	      MAX-ACCESS  not-accessible
	      STATUS      current
	      DESCRIPTION
		      "Information about a specific unicast MAC address
		      for which the bridge has some forwarding and/or
		      filtering information."
	      INDEX   { switchBridgeStpPort, switchBridgeTpFdbAddress }
	      ::= { switchBridgeTpFdbTable 1 }
      SwitchBridgeTpFdbEntry ::= SEQUENCE {
	      switchBridgeTpFdbAddress     MacAddress,
	      switchBridgeTpFdbPort        INTEGER, 
	      switchBridgeTpFdbStatus      INTEGER
	  }
      switchBridgeTpFdbAddress OBJECT-TYPE
	      SYNTAX  MacAddress
	      MAX-ACCESS  not-accessible
	      STATUS      current
	      DESCRIPTION
		      "A unicast MAC address for which the bridge has
		      forwarding and/or filtering information."
	      REFERENCE
		      "IEEE 802.1D-1990: Section 3.9.1, 3.9.2"
	      ::= { switchBridgeTpFdbEntry 1 }
      switchBridgeTpFdbPort OBJECT-TYPE
	      SYNTAX  INTEGER (0..256)
	      MAX-ACCESS  not-accessible
	      STATUS      obsolete
	      DESCRIPTION
		      "Either the value '0', or the virtual port number of the
		      port on which a frame having a source address
		      equal to the value of the corresponding instance
		      of switchBridgeTpFdbAddress has been seen.  A value of
		      '0' indicates that the port number has not been
		      learned but that the bridge does have some
		      forwarding/filtering information about this
		      address (e.g. in the switchBridgeStaticTable).
		      Implementors are encouraged to assign the port
		      value to this object whenever it is learned even
		      for addresses for which the corresponding value of
		      switchBridgeTpFdbStatus is not learned(3)."
	      ::= { switchBridgeTpFdbEntry 2 }
      switchBridgeTpFdbStatus OBJECT-TYPE
	      SYNTAX  INTEGER {
                      other(1),
                      invalid(2),
                      learned(3),
                      self(4),
                      mgmt(5)
                  }
	      MAX-ACCESS  read-only
	      STATUS      current
	      DESCRIPTION
		      "The status of this entry.  The meanings of the
		      values are:
    
			other(1)   : none of the following.  This would
				     include the case where some other
				     MIB object (not the corresponding
				     instance of switchBridgeTpFdbPort, nor an
				     entry in the switchBridgeStaticTable) is
				     being used to determine if and how
				     frames addressed to the value of
				     the corresponding instance of
				     switchBridgeTpFdbAddress are being
				     forwarded.
    
			invalid(2) : this entry is not longer valid
				     (e.g., it was learned but has since
				     aged-out), but has not yet been
				     flushed from the table.
    
			learned(3) : the value of the corresponding
				     instance of switchBridgeTpFdbPort was
				     learned, and is being used.
    
			self(4)    : the value of the corresponding
				     instance of switchBridgeTpFdbAddress
				     represents one of the bridge's
				     addresses.  The corresponding
				     instance of switchBridgeTpFdbPort
				     indicates which of the bridge's
				     ports has this address.
    
			mgmt(5)    : the value of the corresponding
				     instance of switchBridgeTpFdbAddress is
				     also the value of an existing
				     instance of switchBridgeStaticAddress."
	      ::= { switchBridgeTpFdbEntry 3 }
      
      switchBridgeTpPortTable OBJECT-TYPE
	      SYNTAX  SEQUENCE OF SwitchBridgeTpPortEntry
	      MAX-ACCESS  not-accessible
	      STATUS      current
	      DESCRIPTION
		      "A table that contains information about every
		      port that is associated with this transparent
		      bridge."
	      ::= { switchBridgeTp 4 }
      switchBridgeTpPortEntry OBJECT-TYPE
	      SYNTAX  SwitchBridgeTpPortEntry
	      MAX-ACCESS  not-accessible
	      STATUS      current
	      DESCRIPTION
		      "A list of information for each port of a
		      transparent bridge."
	      INDEX   { vLanNumber, switchBridgeTpPort }
	  ::= { switchBridgeTpPortTable 1 }
      SwitchBridgeTpPortEntry ::= SEQUENCE {
	      switchBridgeTpPort              INTEGER,
	      switchBridgeTpPortMaxInfo       INTEGER,
	      switchBridgeTpPortInFrames      Counter32,
	      switchBridgeTpPortOutFrames     Counter32,
	      switchBridgeTpPortInDiscards    Counter32
	  }
      switchBridgeTpPort OBJECT-TYPE
	      SYNTAX  INTEGER (1..256)
	      MAX-ACCESS  not-accessible
	      STATUS      current
	      DESCRIPTION
		      "The virtual port number of the port for which this entry
		      contains Transparent bridging management
		      information."
	      ::= { switchBridgeTpPortEntry 1 }
      
      
      
      
      
      switchBridgeTpPortMaxInfo OBJECT-TYPE
	      SYNTAX  INTEGER (0..65535)
	      MAX-ACCESS  read-only
	      STATUS      current
	      DESCRIPTION
		      "The maximum size of the INFO (non-MAC) field that
		      this port will receive or transmit."
	      ::= { switchBridgeTpPortEntry 2 }
    
	  switchBridgeTpPortInFrames OBJECT-TYPE
	      SYNTAX  Counter32
	      MAX-ACCESS  read-only
	      STATUS      current
	      DESCRIPTION
		      "The number of frames that have been received by
		      this port from its segment. Note that a frame
		      received on the interface corresponding to this
		      port is only counted by this object if and only if
		      it is for a protocol being processed by the local
		      bridging function, including bridge management
		      frames."
	      REFERENCE
		      "IEEE 802.1D-1990: Section 6.6.1.1.3"
	      ::= { switchBridgeTpPortEntry 3 }
      switchBridgeTpPortOutFrames OBJECT-TYPE
	      SYNTAX  Counter32
	      MAX-ACCESS  read-only
	      STATUS      current
	      DESCRIPTION
		      "The number of frames that have been transmitted
		      by this port to its segment.  Note that a frame
		      transmitted on the interface corresponding to this
		      port is only counted by this object if and only if
		      it is for a protocol being processed by the local
		      bridging function, including bridge management
		      frames."
	      REFERENCE
		      "IEEE 802.1D-1990: Section 6.6.1.1.3"
	      ::= { switchBridgeTpPortEntry 4 }
      switchBridgeTpPortInDiscards OBJECT-TYPE
	      SYNTAX   Counter32
	      MAX-ACCESS   read-only
	      STATUS       current
	      DESCRIPTION
		      "Count of valid frames received which were
		      discarded (i.e., filtered) by the Forwarding
		      Process."
	      REFERENCE
		      "IEEE 802.1D-1990: Section 6.6.1.1.3"
	      ::= { switchBridgeTpPortEntry 5 }
      
      
      switchBridgeStaticTable OBJECT-TYPE
	      SYNTAX  SEQUENCE OF SwitchBridgeStaticEntry
	      MAX-ACCESS  not-accessible
	      STATUS      current
	      DESCRIPTION
		      "A table containing filtering information
		      configured into the bridge by (local or network)
		      management specifying the set of ports to which
		      frames received from specific ports and containing
		      specific destination addresses are allowed to be
		      forwarded.  The value of zero in this table as the
		      port number from which frames with a specific
		      destination address are received, is used to
		      specify all ports for which there is no specific
		      entry in this table for that particular
		      destination address.  Entries are valid for
		      unicast and for group/broadcast addresses."
	      REFERENCE
		      "IEEE 802.1D-1990: Section 6.7.2"
	      ::= { switchBridgeStatic 1 }
      switchBridgeStaticEntry OBJECT-TYPE
	      SYNTAX  SwitchBridgeStaticEntry
	      MAX-ACCESS  not-accessible
	      STATUS      current
	      DESCRIPTION
		      "Filtering information configured into the bridge
		      by (local or network) management specifying the
		      set of ports to which frames received from a
		      specific port and containing a specific
		      destination address are allowed to be forwarded."
	      REFERENCE
		      "IEEE 802.1D-1990: Section 6.7.2"
	      INDEX   { switchBridgeStpPort, switchBridgeStaticAddress }
	      ::= { switchBridgeStaticTable 1 }
      SwitchBridgeStaticEntry ::= SEQUENCE {
	      switchBridgeStaticAddress           MacAddress,
	      switchBridgeStaticReceivePort       INTEGER, 
	      switchBridgeStaticAllowedToGoTo     OCTET STRING,
	      switchBridgeStaticStatus            INTEGER
	  }
      switchBridgeStaticAddress OBJECT-TYPE
	      SYNTAX  MacAddress
	      MAX-ACCESS  not-accessible
	      STATUS      current
	      DESCRIPTION
			  "The MAC address in a frame to which this entry's filtering
			  information applies.  This object can take the value of a
			  unicast address, a group address."
	      REFERENCE
		      "IEEE 802.1D-1990: Section 3.9.1, 3.9.2"
	      ::= { switchBridgeStaticEntry 1 }
    
       switchBridgeStaticReceivePort OBJECT-TYPE
             SYNTAX  INTEGER (0..256)
             MAX-ACCESS  read-create
             STATUS      obsolete
             DESCRIPTION
                     "Either the value '0', or the port number of the
                     port from which a frame must be received in order
                     for this entry's filtering information to apply.
                     A value of zero indicates that this entry applies
                     on all ports of the bridge for which there is no
                     other applicable entry.
                     
                     The value of this object is the same as the
                     vPortNumber of the corresponding vPortEntry."
             ::= { switchBridgeStaticEntry 2 }
 
      switchBridgeStaticAllowedToGoTo OBJECT-TYPE
	      SYNTAX  OCTET STRING (SIZE(1..32))
	      MAX-ACCESS  read-only
	      STATUS      current
	      DESCRIPTION
		      "The set of ports to which frames received from a
		      specific port and destined for a specific MAC
		      address, are allowed to be forwarded.  Each octet
		      within the value of this object specifies a set of
		      eight ports, with the first octet specifying ports
		      1 through 8, the second octet specifying ports 9
		      through 16, etc.  Within each octet, the most
		      significant bit represents the lowest numbered
		      port, and the least significant bit represents the
		      highest numbered port.  Thus, each port of the
		      bridge is represented by a single bit within the
		      value of this object.  If that bit has a value of
		      '1' then that port is included in the set of
		      ports; the port is not included if its bit has a
		      value of '0'."
	      ::= { switchBridgeStaticEntry 3 }
      switchBridgeStaticStatus OBJECT-TYPE
	      SYNTAX  INTEGER {
			  other(1),
			  invalid(2),
			  permanent(3),
			  deleteOnReset(4),
			  deleteOnTimeout(5)
		      }
	      MAX-ACCESS  read-create
	      STATUS      current
	      DESCRIPTION
		      "This object indicates the status of this entry.
		      The default value is permanent(3).
    
			   other(1) - this entry is currently in use but
				the conditions under which it will
				remain so are different from each of the
				following values.
			   invalid(2) - writing this value to the object
				removes the corresponding entry.
			   permanent(3) - this entry is currently in use
				and will remain so after the next reset
				of the bridge.
			   deleteOnReset(4) - this entry is currently in
				use and will remain so until the next
				reset of the bridge.
			   deleteOnTimeout(5) - this entry is currently
				in use and will remain so until it is
				aged out."
	      ::= { switchBridgeStaticEntry 4 }
	     
      
      
      switchNewRoot NOTIFICATION-TYPE
	  OBJECTS   { switchBridgeStpDesignatedRoot }
      STATUS    current
	  DESCRIPTION
		  "The newRoot trap indicates that the sending agent
		  has become the new root of the Spanning Tree; the
		  trap is sent by a bridge soon after its election
		  as the new root, e.g., upon expiration of the
		  Topology Change Timer immediately subsequent to
		  its election.  Implementation of this trap is
		  optional."
	  ::= { switchBridgeTraps 1 }
      switchTopologyChange NOTIFICATION-TYPE
	  OBJECTS   { switchBridgeStpPortState }
      STATUS    current
	  DESCRIPTION
		  "A topologyChange trap is sent by a bridge when
		  any of its configured ports transitions from the
		  Learning state to the Forwarding state, or from
		  the Forwarding state to the Blocking state.  The
		  trap is not sent if a newRoot trap is sent for the
		  same transition.  Implementation of this trap is
		  optional."
	  ::= { switchBridgeTraps 2 }
END
