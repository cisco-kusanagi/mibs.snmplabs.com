--			Ascend mibatmp MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBATMP-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibatmpProfile  OBJECT IDENTIFIER ::= { configuration 42}

	-- The mibatmpProfile table
	--
	-- This table contains parameters for the mibatmpProfile profile
	--

    mibatmpProfileTable	OBJECT-TYPE
	SYNTAX		SEQUENCE OF MibatmpProfileEntry
	ACCESS		not-accessible
	STATUS		mandatory
	DESCRIPTION	"A list of mibatmpProfile profile entries."
	::= { mibatmpProfile 1 }

    mibatmpProfileEntry	OBJECT-TYPE
	SYNTAX		MibatmpProfileEntry
	ACCESS		not-accessible
	STATUS		mandatory
	DESCRIPTION	"A mibatmpProfile entry containing objects that
			 maps to the parameters of mibatmpProfile profile."
	INDEX		{ atmpProfile-Index-o }
	::= { mibatmpProfileTable 1 }

    MibatmpProfileEntry ::=
	SEQUENCE {
	    atmpProfile-Index-o
		INTEGER,
	    atmpProfile-AgentMode
		INTEGER,
	    atmpProfile-AgentType
		INTEGER,
	    atmpProfile-UdpPort
		INTEGER,
	    atmpProfile-HomeAgentPassword
		DisplayString,
	    atmpProfile-AtmpSapReply
		INTEGER,
	    atmpProfile-RetryTimeout
		INTEGER,
	    atmpProfile-RetryLimit
		INTEGER,
	    atmpProfile-IdleTimer
		INTEGER,
	    atmpProfile-MtuLimit
		INTEGER,
	    atmpProfile-ForceFragmentation
		INTEGER,
	    atmpProfile-AtmpSnmpTrap
		INTEGER,
	    atmpProfile-Action-o
		INTEGER
	}

    atmpProfile-Index-o	OBJECT-TYPE
	SYNTAX	INTEGER
	ACCESS	read-only
	STATUS	mandatory
	DESCRIPTION	""
	::= { mibatmpProfileEntry 1 }

    atmpProfile-AgentMode	OBJECT-TYPE
	SYNTAX	INTEGER {
		    tunnelDisabled (1),
		    homeAgent (2),
		    foreignAgent (3),
		    homeAndForeignAgent (4)
		}
	ACCESS	read-write
	STATUS	mandatory
	DESCRIPTION	"The valid modes for this ATMP agent."
	::= { mibatmpProfileEntry 2 }

    atmpProfile-AgentType	OBJECT-TYPE
	SYNTAX	INTEGER {
		    routerHomeAgent (1),
		    gatewayHomeAgent (2)
		}
	ACCESS	read-write
	STATUS	mandatory
	DESCRIPTION	"The type of Home Agent."
	::= { mibatmpProfileEntry 3 }

    atmpProfile-UdpPort	OBJECT-TYPE
	SYNTAX	INTEGER
	ACCESS	read-write
	STATUS	mandatory
	DESCRIPTION	"UDP port number to use locally."
	::= { mibatmpProfileEntry 4 }

    atmpProfile-HomeAgentPassword	OBJECT-TYPE
	SYNTAX	DisplayString
	ACCESS	read-write
	STATUS	mandatory
	DESCRIPTION	"The password required to access this home agent."
	::= { mibatmpProfileEntry 5 }

    atmpProfile-AtmpSapReply	OBJECT-TYPE
	SYNTAX	INTEGER {
		    no (1),
		    yes (2)
		}
	ACCESS	read-write
	STATUS	mandatory
	DESCRIPTION	"Whether an ATMP Home Agent should reply to IPX SAP Nearest Server queries from the Mobile Client."
	::= { mibatmpProfileEntry 6 }

    atmpProfile-RetryTimeout	OBJECT-TYPE
	SYNTAX	INTEGER
	ACCESS	read-write
	STATUS	mandatory
	DESCRIPTION	"The number of seconds between retries to establish a tunnel."
	::= { mibatmpProfileEntry 7 }

    atmpProfile-RetryLimit	OBJECT-TYPE
	SYNTAX	INTEGER
	ACCESS	read-write
	STATUS	mandatory
	DESCRIPTION	"The maximum number of failed attempts to establish a tunnel before switching to the alternate home agent."
	::= { mibatmpProfileEntry 8 }

    atmpProfile-IdleTimer	OBJECT-TYPE
	SYNTAX	INTEGER
	ACCESS	read-write
	STATUS	mandatory
	DESCRIPTION	"The number of minutes of no activity before an ATMP Home Agent will drop a tunnel. The value 0 disables the idle timer."
	::= { mibatmpProfileEntry 9 }

    atmpProfile-MtuLimit	OBJECT-TYPE
	SYNTAX	INTEGER
	ACCESS	read-write
	STATUS	mandatory
	DESCRIPTION	"The maximum IP packet size that can be transmitted to a remote agent without performing pre-fragmentation. The value 0 disables this feature. If enabled, the smallest size the system will use is 68, even if a smaller size is specified. This is to comply with the minimum IP packet size requirement per RFC 791."
	::= { mibatmpProfileEntry 10 }

    atmpProfile-ForceFragmentation	OBJECT-TYPE
	SYNTAX	INTEGER {
		    no (1),
		    yes (2)
		}
	ACCESS	read-write
	STATUS	mandatory
	DESCRIPTION	"When set to NO, an ICMP message will be sent if a frame needs fragmentation and the DF bit is set. This is the standard behavior. When set to YES, it forces pre-fragmentation of large IP frames before they are sent to the remote agent, even if the frame has the DF bit set. This behavior is not standard and prevents MTU discovery mechanisms."
	::= { mibatmpProfileEntry 11 }

    atmpProfile-AtmpSnmpTrap	OBJECT-TYPE
	SYNTAX	INTEGER {
		    no (1),
		    yes (2)
		}
	ACCESS	read-write
	STATUS	mandatory
	DESCRIPTION	"When set to No, do not send ATMP SNMP traps. If Yes, send traps. The default is No."
	::= { mibatmpProfileEntry 12 }

    atmpProfile-Action-o	OBJECT-TYPE
	SYNTAX	INTEGER {
		    noAction (1),
		    createProfile (2),
		    deleteProfile (3)
		}
	ACCESS	read-write
	STATUS	mandatory
	DESCRIPTION	""
	::= { mibatmpProfileEntry 13 }

END
