-- MCC16-MIB, TRANSITION NETWORKS, INC.
-- (Formerly a portion of TNI-MIB)
--
-- SUSPEND OEM EDITING
-- MIB Release 3.00.65 02/22/05 - Added cmefg100 Table and entries
-- MIB Release 3.00.64 02/05/04 - Changed crs2f100RmtDCE to read-only and
--                                crs4f100Table with entries
-- MIB Release 3.00.63 01/05/04 - Changed ccscf100LineBuildout to read-write
-- MIB Release 3.00.62 10/06/03 - Added crmfe100MbTxFxBwa and crmfe100MbFxTxBwa
-- MIB Release 3.00.61 08/19/03 - Added crs2f100Table and entries
-- MIB Release 3.00.60 07/18/03 - Added cpsConnector types 34 and 35
-- MIB Release 3.00.60 06/10/03 - Edited crmfe100Table and descriptions
-- MIB Release 3.00.59 05/28/03 - Added crmfe100Table and entries
-- MIB Release 3.00.58 05/14/03 - Added captf100Emulates
-- MIB Release 3.00.57 04/18/03 - Added cgetf100PauseType, cgetf100FiberAutoNegot,
--                                smacf100AgingTimer
-- MIB Release 3.00.56 04/15/03 - Added cgfeb100Table and entries, cbftf100RedundantPath
-- MIB Release 3.00.55 03/24/03 - Added two more entries under CpsConnector
-- MIB Release 3.00.54 03/13/03 - Added cbftf150Table and related entries
-- MIB Release 3.00.53 03/12/03 - Added cfetf205Table and related entries
-- MIB Release 3.00.52 01/30/03 - Updated descriptions in cpsmp110Table, 
--                                cbftf100Table, and smacf100PTable 
-- MIB Release 3.00.51 01/10/03 - Added cpsmc0800 Table and entries
-- MIB Release 3.00.50 11/27/02 - Updated smacf100 variable descriptions
-- MIB Release 3.00.49 11/26/02 - Added software read-write for cfetf100FarEndFault
-- MIB Release 3.00.48 11/07/02 - Added notSupported(3) to csdtf100CopperLoopback
-- MIB Release 3.00.47 10/02/02 - Added CacheClean variable to all Point
--                                system slide-in devices.  Updated description
--                                field for cpsvt100, cemtf100, and captf100.
--                                Updated enumerations for cpsvt100TermTiming.
-- MIB Release 3.00.46 08/01/02 - Added enumerations to variables in
--                                the cpsvt100Table
-- MIB Release 3.00.45 07/26/02 - Added smacf100SNMPModuleInstalled
-- MIB Release 3.00.44 07/11/02 - Added captf100Table
-- MIB Release 3.00.43 07/08/02 - Added cpsvt100 and cemtf100Table
-- MIB Release 3.00.42 06/24/02 - Added smacf100PAdvPause
-- MIB Release 3.00.41 06/05/02 - Added several Smacf100P and Smacf100 entries
-- MIB Release 3.00.40 05/22/02 - Documented Smacf100PTable entries
-- MIB Release 3.00.39 05/15/02 - Added many Smacf100 Port variables
-- MIB Release 3.00.38 05/09/02 - Added pSCabinetAdded/Removed traps
-- MIB Release 3.00.37 04/30/02 - Added CDFTF100Table and its entries
-- MIB Release 3.00.36 04/19/02 - Document smacf100PTx/RxOctets, WrapOctets
-- MIB Release 3.00.35 04/16/02 - Documented descriptions of cpsld100,
--                                added smaf100PSACCfg
-- MIB Release 3.00.34 03/20/02 - Added cpsld100ID and cpsld100Table
-- MIB Release 3.00.33 03/19/02 - Updated smacf100PTable entries
-- MIB Release 3.00.32 03/13/02 - Updated description of cfetf100FarEndFault
-- MIB Release 3.00.31 03/08/02 - Added smacf100PSubDeviceIndex 
--                                and smacf100PSTPState
-- MIB Release 3.00.30 01/24/02 - Added SMACF100Table, SMACF100PFullDuplex,
--                                SMACF100PSACStat, SMACF100PAutoNegot, and
--                                advertised speeds
-- MIB Release 3.00.29 01/22/02 - Added SMACF100P100Mbps variable
-- MIB Release 3.00.28 01/17/02 - Added SMACF100PTable, SMACF100 cabinet Id's
-- MIB Release 3.00.27 12/28/01 - Added remote management (Rmt) variables
--                                to csdtf100Table
-- MIB Release 3.00.26 12/03/01 - Added chassisCpsColonyLCId and 
--                                chassisCpsCpsmc1900Id
-- MIB Release 3.00.25 11/30/01 - Added cpsConnector scsimplex(29)
-- MIB Release 3.00.24 11/06/01 - Doc cleanup, add csdtf100FiberLoopback,
--                                cbftf100FormFactor values.
-- MIB Release 3.00.23 09/25/01 - Added cfetf105Table and cfetf105Id
-- MIB Release 3.00.22 09/19/01 - Added ccscf100Table and ccscf100Id
-- MIB Release 3.00.21 09/13/01 - Added connectorType 27 and 28, scsmsh 
--                                (SC Singlemode Short Haul) and stmmlh 
--                                (ST Multimode Long Haul), respectively
-- MIB Release 3.00.20 08/22/01 - Added notSupported(3) to cfetf100TPActivity and
--                                cfetf100FiberActivity
-- MIB Release 3.00.19 08/17/01 - Obsoleted cpsmm100TNTRIP and cpsmm100TNTRIPMask
-- MIB Release 3.00.18 08/15/01 - Added cpsConnector types for MTRJ-SM and
--                                Universal 26-pin Serial Interface Connector.
-- MIB Release 3.00.17 07/27/01 - Added cpsmm100SNMPTrpMgr entries "2" through "4"
-- MIB Release 3.00.16 04/30/01 - Added cbftf100LinkPassThrough
-- MIB Release 3.00.15 04/27/01 - Added cbftf100 and cetct100
-- MIB Release 3.00.14 04/14/01 - Added Point System specific traps
-- MIB Release 3.00.13 04/02/01 - Added last gasp feature to CPSMM100,
--                                and add the CPSMC0200
-- MIB Release 3.00.12 03/01/01 - Added CPSMP110CurrentSensorCount, 
--                                CPSMP110FanCount, CPSMP110TempSensorCount
-- MIB Release 3.00.11 03/01/01 - Added CPSMP110 Table
-- MIB Release 3.00.10 02/14/01 - Added CSDTF100 Table
-- MIB Release 3.00.09 01/15/01 - Added Cpsmc1300 13 slot chassis table type
-- MIB Release 3.00.08 12/15/00 - Change comment on cpsmm100SNMPTrapInterval
-- MIB Release 3.00.07 11/03/00 - Removed cgetf100RcvErrCnt
-- MIB Release 3.00.06 11/01/00 - Add cpsmp100SupplyType
-- MIB Release 3.00.05 10/31/00 - Add csetf100, cgetf100
-- MIB Release 3.00.04 09/15/00 - Change slotcps to slotCps, Add documentation,
--                                Remove cpsPSTable, Change FanICC to FanFault
--                                in cpsmp100, Make syntax for 'Enabled' vars
--                                more consistent. Make syntax for 'Signal'
--                                vars more consistent with 'Link' vars.
--                                Change CfgMatch value from inactive(3) to
--                                notApplicable(3). Change active(1) inactive(2)
--                                to yes(1) no(2) to improve consistency.
-- MIB Release 3.00.03 08/14/00 - Removed cfetf100FarEndFault and added 
--                              - cfetf100AutoCross entries
-- MIB Release 3.00.02 07/27/00 - Added cpsIsPrimary
-- MIB Release 3.00.01 07/17/00 - Added MRevision entries for cpsMc1800,
--                                cpsMc0800, cpsmm200, and cpsmm100
-- MIB Release 3.00 06/12/00 - CPSMC1800, CPSMM100, CFETF100, CFMFF100, 
--                             CETTF100, CPSMP100, CPSMM200 added.
-- MIB Release 2.07.1 11/10/99 - Remove extra comma from C/RS232-CF-01
-- MIB Release 2.07 09/22/99 - Add C/RS232-CF-01
-- MIB Release 2.06.6 09/10/99 - Remove extra comma from ceTbtFrl04
-- MIB Release 2.06.5 07/15/99 - Add ceTbtFrl04
-- MIB Release 2.06.4 06/26/99 - Add ceTxSx02
-- MIB Release 2.06.3 06/08/99 - Add mcc16ComNotes
-- MIB Release 2.06.2 05/14/99 - Add chstrCf01
-- MIB Release 2.06.1 05/10/99 - Add ceRTxFx01
-- MIB Release 2.06 04/20/99 - Add ct1e1Cf01, mc20pDblWide
-- MIB Release 2.05.1 01/26/99 - Add caCf02, cpsCf01, cbCf01, carCf01, carCf02
-- MIB Release 2.05 01/22/99 - Add cePswSx01
-- MIB Release 2.04.1 11/03/98 - OEM changes
-- MIB Release 2.04 10/16/98 - cfSmMm06, cpsCf01, cePswFx03
-- MIB Release 2.03 09/18/98 - ce100BtxFx04, cePswFx03, ce100BtxSx01,
--                             ce100BtxFx04Mt, ERROR trap, ERROR CLEAR trap
--                             POWER SUPPLY STATUS CHANGE trap.
--                             Split MCC16 definitions from TNI.MIB. 2.03
--                             is the initial release of MCC16-MIB.
-- 
--                             All of the above release description comments
--                             list items ADDED unless otherwise noted.
-- 
-- Copyright (c) 1996-2000 Transition Networks, Inc.  All Rights Reserved.
-- 
-- Reproduction of this document is authorized on condition that
-- this copyright notice is included.  This Transition Networks, Inc.
-- SNMP Management Information Base Specification (MCC-16-MIB) embodies
-- T.N.I.'s confidential and proprietary intellectual property.
-- T.N.I. retains all title and ownership in the MCC16-MIB Specification,
-- including any revisions.
-- 
-- It is T.N.I.'s intent to encourage the widespread use of this
-- specification in connection with the management of Transition
-- Networks, Inc.'s products.  T.N.I. grants vendor, end-users,
-- and other interested parties a non-exclusive license to use this
-- specification in connection with the management of Transition
-- Networks, Inc.'s products.
-- 
-- This MCC16-MIB Specification is supplied "AS IS," and T.N.I. makes
-- no warranty, either express or implied, as to the use,
-- operation, condition, or performance of the MCC16-MIB Specification.
-- 
-- T.N.I. retains the right to change this MCC16-MIB without notification.
--get=cgfeb100entry

-- RESUME OEM EDITING

MCC16-MIB DEFINITIONS ::= BEGIN

--
-- SECTION 1: Top Level Definitions
--

--
-- Imports
--
IMPORTS
	enterprises, Gauge,
	TimeTicks, IpAddress		FROM RFC1155-SMI
	DisplayString, PhysAddress	FROM RFC1213-MIB
	OBJECT-TYPE				FROM RFC-1212
	TRAP-TYPE				FROM RFC-1215;

MacAddress ::= OCTET STRING (SIZE (6))
		-- a 6 octet address in the "canonical" order defined by IEEE 
		-- 802.1a, i.e., as if it were transmitted least significant bit 
		-- first, even though 802.5 (in contrast to other 802.x protocols) 
		-- requires MAC addresses to be transmitted most significant bit 
		-- first.  16-bit addresses, if needed, are represented by setting
		-- their upper 4 octets to all 0's, i.e., AAFF would be
		-- represented as 00000000AAFF.


-- The types of connectors that can be built into a Point System converter.
-- No type of converter uses all of these connector types.
-- Some converters return 16 bit connector style values that contain additional
-- information on the connector in the upper byte. In these cases, the lower 
-- byte is one of the values below. 
CpsConnector ::= INTEGER { rj-45(10),     -- RJ-45, unshielded twisted pair
                           stmm(11),      -- ST fiber, multimode
                           stsm(12),      -- ST fiber, singlemode
                           scmm(13),      -- SC fiber, multimode
                           scsm(14),      -- SC fiber, singlemode
                           scsmlh(15),    -- SC fiber, singlemode, long haul
                           scsmelh(16),   -- SC fiber, singlemode, extra long haul
                           scsmlhlw(17),  -- SC fiber, long haul, long wavelength
                           mtrjmm(18),    -- MT-RJ multimode fiber
                           lc(19),        -- LC fiber, singlemode
                           bnc(20),       -- BNC coax
                           stsmlh(21),    -- ST Singlemode Long Haul
                           stsmelh(22),   -- ST Singlemode Extra Long Haul
                           scmm1300(23),  -- SC Multimode 1300nm
                           stmm1300(24),  -- ST Multimode 1300nm
                           mtrjsm(25),    -- MTRJ singlemode fiber
                           serial26(26),  -- Universal 26-pin Serial Interface Connector
                           stmmlh(27),    -- ST Multimode Long Haul
                           scsmsh(28),    -- SC Singlemode Short Haul
                           scsimplex(29), -- SC Simplex
                           bncdual(30),   -- Dual BNC coax connectors
                           db9rsxxx(31),  -- DB9 for RS232 and RS485
                           termblock(32), -- Terminal Block for RS485
                           rj11(33),      -- RJ-11, unshielded twisted pair
                           sc40km(34),    -- SC fiber, 1550nm 40km 
                           sc125km(35)    -- SC fiber, 1 x 9, 125km Gigiabit
                           }

--
-- Categories
--
transition       OBJECT IDENTIFIER ::=   { enterprises 868 }
productId        OBJECT IDENTIFIER ::=   { transition  1 }
  -- {productId 1 through 3} are reserved
chassisProdsId   OBJECT IDENTIFIER ::=   { productId 4 } 
chassisSlotTypes OBJECT IDENTIFIER ::=   { chassisProdsId 1 } 
chSlMc20p        OBJECT IDENTIFIER ::=   { chassisSlotTypes 1 } 
chSlcps          OBJECT IDENTIFIER ::=   { chassisSlotTypes 2 }
chassisMcc16Id   OBJECT IDENTIFIER ::=   { chassisProdsId 2 } 
products         OBJECT IDENTIFIER ::=   { transition 2 }

--  These are identifying OIDs for devices that can be inserted into 
--  a 20 pin media converter chassis slot, i.e. an MCC 16:
ceTbtFrl03Id      OBJECT IDENTIFIER ::=   { chSlMc20p 1 } 
ceCxTbt04Id       OBJECT IDENTIFIER ::=   { chSlMc20p 2 } 
ceCxFrl04Id       OBJECT IDENTIFIER ::=   { chSlMc20p 3 } 
cfSmMm02Id        OBJECT IDENTIFIER ::=   { chSlMc20p 4 } 
cfSmMm05Id        OBJECT IDENTIFIER ::=   { chSlMc20p 5 } 
caCf02Id          OBJECT IDENTIFIER ::=   { chSlMc20p 6 } 
cfSmMm06Id        OBJECT IDENTIFIER ::=   { chSlMc20p 7 } 
ct1e1Cf01Id       OBJECT IDENTIFIER ::=   { chSlMc20p 8 } 
ceRTxFx01Id       OBJECT IDENTIFIER ::=   { chSlMc20p 9 } 
ce100BtxFx04Id    OBJECT IDENTIFIER ::=   { chSlMc20p 10 } 
cpsCf01Id         OBJECT IDENTIFIER ::=   { chSlMc20p 12 } 
cbCf01Id          OBJECT IDENTIFIER ::=   { chSlMc20p 13 } 
carCf01Id         OBJECT IDENTIFIER ::=   { chSlMc20p 14 } 
carCf02Id         OBJECT IDENTIFIER ::=   { chSlMc20p 15 } 
cePswFx03Id       OBJECT IDENTIFIER ::=   { chSlMc20p 16 } 
cePswSx01Id       OBJECT IDENTIFIER ::=   { chSlMc20p 17 } 
cRs232Cf01Id      OBJECT IDENTIFIER ::=   { chSlMc20p 18 } 
cfSmMm04Id        OBJECT IDENTIFIER ::=   { chSlMc20p 24 } 
ce100BtxSx01Id    OBJECT IDENTIFIER ::=   { chSlMc20p 26 } 
ce100BtxFx04MtId  OBJECT IDENTIFIER ::=   { chSlMc20p 27 } 
cfdCd01Id         OBJECT IDENTIFIER ::=   { chSlMc20p 28 } 
ctrCf01Id         OBJECT IDENTIFIER ::=   { chSlMc20p 29 } 
ce100BtxFrl03Id   OBJECT IDENTIFIER ::=   { chSlMc20p 30 } 
mc20pEmptyId      OBJECT IDENTIFIER ::=   { chSlMc20p 31 }
-- this means that the ID bits that were seen were invalid.
mc20pErrorId      OBJECT IDENTIFIER ::=   { chSlMc20p 32 } 
mc20pDblWideId    OBJECT IDENTIFIER ::=   { chSlMc20p 33 } 
chstrCf01Id       OBJECT IDENTIFIER ::=   { chSlMc20p 34 } 
ceTxSx02Id        OBJECT IDENTIFIER ::=   { chSlMc20p 35 } 
ceTbtFrl04Id      OBJECT IDENTIFIER ::=   { chSlMc20p 36 } 
-- These are identifying OIDs for devices that can be inserted
-- into a chassis 2 i2c slot:
cpsmM100Id              OBJECT IDENTIFIER ::=   { chSlcps 1 }
cpsmM200Id              OBJECT IDENTIFIER ::=   { chSlcps 2 }
cettf100Id              OBJECT IDENTIFIER ::=   { chSlcps 3 }
cfetf100Id              OBJECT IDENTIFIER ::=   { chSlcps 4 }
cfmff100Id              OBJECT IDENTIFIER ::=   { chSlcps 5 }
cpsmp100Id              OBJECT IDENTIFIER ::=   { chSlcps 6 }
csetf100Id              OBJECT IDENTIFIER ::=   { chSlcps 7 }
cgetf100Id              OBJECT IDENTIFIER ::=   { chSlcps 8 }
csdtf100Id              OBJECT IDENTIFIER ::=   { chSlcps 9 }
cpsmp110Id              OBJECT IDENTIFIER ::=   { chSlcps 10 }
cbftf100Id              OBJECT IDENTIFIER ::=   { chSlcps 11 }
cetct100Id              OBJECT IDENTIFIER ::=   { chSlcps 12 }
ccscf100Id              OBJECT IDENTIFIER ::=   { chSlcps 13 }
cfetf105Id              OBJECT IDENTIFIER ::=   { chSlcps 14 }
smacf100PId             OBJECT IDENTIFIER ::=   { chSlcps 15 }
cpsld100Id              OBJECT IDENTIFIER ::=   { chSlcps 16 }
cdftf100Id              OBJECT IDENTIFIER ::=   { chSlcps 17 }
cpsvt100Id              OBJECT IDENTIFIER ::=   { chSlcps 18 }
cemtf100Id              OBJECT IDENTIFIER ::=   { chSlcps 19 }
captf100Id              OBJECT IDENTIFIER ::=   { chSlcps 20 }
cfetf205Id              OBJECT IDENTIFIER ::=   { chSlcps 21 }
cbftf150Id              OBJECT IDENTIFIER ::=   { chSlcps 22 }
cgfeb100Id              OBJECT IDENTIFIER ::=   { chSlcps 23 }
crmfe100Id              OBJECT IDENTIFIER ::=   { chSlcps 24 }
crs2f100Id              OBJECT IDENTIFIER ::=   { chSlcps 25 }
crs4f100Id              OBJECT IDENTIFIER ::=   { chSlcps 26 }
cmefg100Id              OBJECT IDENTIFIER ::=   { chSlcps 27 }

cpsEmptyId              OBJECT IDENTIFIER ::=   { chSlcps 1001 }
cpsDblWideId            OBJECT IDENTIFIER ::=   { chSlcps 1002 }
cpsUnknownDeviceId      OBJECT IDENTIFIER ::=   { chSlcps 1003 }

  -- {products 1 through 3} are reserved

--  chassis: chassis products
chassis         OBJECT IDENTIFIER ::= { products 4 }                
--  card: devices that plug in to a device listed under backplane(2)
card            OBJECT IDENTIFIER ::= { chassis 1 }         
--  slotMc20p: devices that plug into 20 pin media converter slot
slotMc20p       OBJECT IDENTIFIER ::= { card 1 }      
-- slotCps: devices that plug into Point System i2c slots
slotCps         OBJECT IDENTIFIER ::= { card 2 }
--  backplane: devices that have slots to accept devices listed under card(1),
--             or are the functional equivalent of such a device.
backplane       OBJECT IDENTIFIER ::= { chassis 2 }         
mcc16           OBJECT IDENTIFIER ::= { backplane 1 } 
mcc16Common     OBJECT IDENTIFIER ::= { mcc16 1 } 
mcc16Ver1       OBJECT IDENTIFIER ::= { mcc16 2 } 
cps             OBJECT IDENTIFIER ::= { backplane 2 }
cpsSlotSummary     OBJECT IDENTIFIER ::= { slotCps 1 }
-- cpsSlotDetail: the details of a Point System media converter, 
--                management module or power supply
cpsSlotDetail    OBJECT IDENTIFIER ::= { slotCps 2 }

chassisCpsmc1800Id      OBJECT IDENTIFIER ::=  { chassisProdsId 3 }
chassisCpsmc1850Id      OBJECT IDENTIFIER ::=  { chassisProdsId 4 }
chassisCpsmc0800Id      OBJECT IDENTIFIER ::=  { chassisProdsId 5 }
chassisCpsmc1300Id      OBJECT IDENTIFIER ::=  { chassisProdsId 6 }
chassisCpsmc0200Id      OBJECT IDENTIFIER ::=  { chassisProdsId 7 }
chassisSmacf100LCId     OBJECT IDENTIFIER ::=  { chassisProdsId 8 }
chassisCpsmc1900Id      OBJECT IDENTIFIER ::=  { chassisProdsId 9 }
chassisSmacf100Id       OBJECT IDENTIFIER ::=  { chassisProdsId 10 }

cpsCabSummary           OBJECT IDENTIFIER ::=  { cps 1 }
cpsCabDetail            OBJECT IDENTIFIER ::=  { cps 2 }
cpsAgent                OBJECT IDENTIFIER ::=  { cps 3 }
 

-- ==================================================================
--
-- SECTION 2:
--
--  Definitions for chassis based products.
--  First, the plug-in devices, then the chassis.
-- ==================================================================

-- ==================================================================
--  Table for C/E-TBT-FRL-03 media converters in a media converter chassis.
ceTbtFrl03Table OBJECT-TYPE 
        SYNTAX SEQUENCE OF CeTbtFrl03Entry
        ACCESS not-accessible
        STATUS mandatory
        DESCRIPTION "One table entry per slot in the media converter chassis.
             If physical slot 'n' contains a working C/E-TBT-FRL-03 media 
             converter, then entry 'n' in this table exists and describes
             the state of the converter's LEDs  If slot 'n' is empty, does
             not exist, or contains a different type of device, then table
             entry 'n' does not exist."
        ::= { slotMc20p 1 }

ceTbtFrl03Entry OBJECT-TYPE 
        SYNTAX CeTbtFrl03Entry
        ACCESS not-accessible
        STATUS mandatory
        DESCRIPTION "State of LEDs on a single C/E-TBT-FRL-03"
        INDEX { ceTbtFrl03Index }
        ::= { ceTbtFrl03Table 1 }

CeTbtFrl03Entry ::= 
        SEQUENCE {
                ceTbtFrl03Index     INTEGER,
                ceTbtFrl03FiberRecv INTEGER,
                ceTbtFrl03FiberLink INTEGER,
                ceTbtFrl03TPRecv    INTEGER,
                ceTbtFrl03TPLink    INTEGER,
                ceTbtFrl03Power     INTEGER
                }

ceTbtFrl03Index OBJECT-TYPE 
        SYNTAX INTEGER
        ACCESS read-only
        STATUS mandatory
        DESCRIPTION "The index of a slot in a media converter chassis"
        ::= { ceTbtFrl03Entry 1 }

ceTbtFrl03FiberRecv OBJECT-TYPE 
        SYNTAX INTEGER { on(1),off(2) }
        ACCESS read-only
        STATUS mandatory
        DESCRIPTION "The state of the converter's Fiber Receive LED"
        ::= { ceTbtFrl03Entry 2 }

ceTbtFrl03FiberLink OBJECT-TYPE 
        SYNTAX INTEGER { on(1),off(2) }
        ACCESS read-only
        STATUS mandatory
        DESCRIPTION "The state of the converter's Fiber Link LED"
        ::= { ceTbtFrl03Entry 3 }

ceTbtFrl03TPRecv OBJECT-TYPE 
        SYNTAX INTEGER { on(1),off(2) }
        ACCESS read-only
        STATUS mandatory
        DESCRIPTION "The state of the converter's Twisted Pair Receive LED"
        ::= { ceTbtFrl03Entry 4 }

ceTbtFrl03TPLink OBJECT-TYPE 
        SYNTAX INTEGER { on(1),off(2) }
        ACCESS read-only
        STATUS mandatory
        DESCRIPTION "The state of the converter's Twisted Pair Link LED"
        ::= { ceTbtFrl03Entry 5 }

ceTbtFrl03Power OBJECT-TYPE 
        SYNTAX INTEGER { on(1),off(2) }
        ACCESS read-only
        STATUS mandatory
        DESCRIPTION "The state of the converter's Power LED"
        ::= { ceTbtFrl03Entry 6 }


-- ==================================================================
--  Table for C/E-CX-TBT-04 media converters in a media converter chassis.
ceCxTbt04Table OBJECT-TYPE 
        SYNTAX SEQUENCE OF CeCxTbt04Entry
        ACCESS not-accessible
        STATUS mandatory
        DESCRIPTION "One table entry per slot in the media converter chassis.
             If physical slot 'n' contains a working C/E-CX-TBT-04 media 
             converter, then entry 'n' in this table exists and describes
             the state of the converter's LEDs  If slot 'n' is empty, does
             not exist, or contains a different type of device, then table
             entry 'n' does not exist."
        ::= { slotMc20p 2 }

ceCxTbt04Entry OBJECT-TYPE 
        SYNTAX CeCxTbt04Entry
        ACCESS not-accessible
        STATUS mandatory
        DESCRIPTION "State of LEDs on a single C/E-CX-TBT-04"
        INDEX { ceCxTbt04Index }
        ::= { ceCxTbt04Table 1 }

CeCxTbt04Entry ::= 
        SEQUENCE {
                ceCxTbt04Index          INTEGER,
                ceCxTbt04Jabber         INTEGER,
                ceCxTbt04CoaxRecv       INTEGER,
                ceCxTbt04TPRecv         INTEGER,
                ceCxTbt04TPLink         INTEGER,
                ceCxTbt04Power          INTEGER
                }

ceCxTbt04Index OBJECT-TYPE 
        SYNTAX INTEGER
        ACCESS read-only
        STATUS mandatory
        DESCRIPTION "The index of a slot in a media converter chassis"
        ::= { ceCxTbt04Entry 1 }

ceCxTbt04Jabber OBJECT-TYPE 
        SYNTAX INTEGER { on(1),off(2) }
        ACCESS read-only
        STATUS mandatory
        DESCRIPTION "The state of the converter's Jabber LED"
        ::= { ceCxTbt04Entry 2 }

ceCxTbt04CoaxRecv OBJECT-TYPE 
        SYNTAX INTEGER { on(1),off(2) }
        ACCESS read-only
        STATUS mandatory
        DESCRIPTION "The state of the converter's CoaxRecv LED"
        ::= { ceCxTbt04Entry 3 }

ceCxTbt04TPRecv OBJECT-TYPE 
        SYNTAX INTEGER { on(1),off(2) }
        ACCESS read-only
        STATUS mandatory
        DESCRIPTION "The state of the converter's TPRecv LED"
        ::= { ceCxTbt04Entry 4 }

ceCxTbt04TPLink OBJECT-TYPE 
        SYNTAX INTEGER { on(1),off(2) }
        ACCESS read-only
        STATUS mandatory
        DESCRIPTION "The state of the converter's TPLink LED"
        ::= { ceCxTbt04Entry 5 }

ceCxTbt04Power OBJECT-TYPE 
        SYNTAX INTEGER { on(1),off(2) }
        ACCESS read-only
        STATUS mandatory
        DESCRIPTION "The state of the converter's Power LED"
        ::= { ceCxTbt04Entry 6 }



-- ==================================================================
--  Table for C/E-CX-FRL-04 media converters in a media converter chassis.
ceCxFrl04Table OBJECT-TYPE 
        SYNTAX SEQUENCE OF CeCxFrl04Entry
        ACCESS not-accessible
        STATUS mandatory
        DESCRIPTION "One table entry per slot in the media converter chassis.
             If physical slot 'n' contains a working C/E-CX-FRL-04 media 
             converter, then entry 'n' in this table exists and describes
             the state of the converter's LEDs  If slot 'n' is empty, does
             not exist, or contains a different type of device, then table
             entry 'n' does not exist."
        ::= { slotMc20p 3 }

ceCxFrl04Entry OBJECT-TYPE 
        SYNTAX CeCxFrl04Entry
        ACCESS not-accessible
        STATUS mandatory
        DESCRIPTION "State of LEDs on a single C/E-CX-FRL-04"
        INDEX { ceCxFrl04Index }
        ::= { ceCxFrl04Table 1 }

CeCxFrl04Entry ::= 
        SEQUENCE {
                ceCxFrl04Index          INTEGER,
                ceCxFrl04Jabber         INTEGER,
                ceCxFrl04CoaxRecv       INTEGER,
                ceCxFrl04FLRecv         INTEGER,
                ceCxFrl04FLLink         INTEGER,
                ceCxFrl04Power          INTEGER
                }

ceCxFrl04Index OBJECT-TYPE 
        SYNTAX INTEGER
        ACCESS read-only
        STATUS mandatory
        DESCRIPTION "The index of a slot in a media converter chassis"
        ::= { ceCxFrl04Entry 1 }

ceCxFrl04Jabber OBJECT-TYPE 
        SYNTAX INTEGER { on(1),off(2) }
        ACCESS read-only
        STATUS mandatory
        DESCRIPTION "The state of the converter's Jabber LED"
        ::= { ceCxFrl04Entry 2 }

ceCxFrl04CoaxRecv OBJECT-TYPE 
        SYNTAX INTEGER { on(1),off(2) }
        ACCESS read-only
        STATUS mandatory
        DESCRIPTION "The state of the converter's CoaxRecv LED"
        ::= { ceCxFrl04Entry 3 }

ceCxFrl04FLRecv OBJECT-TYPE 
        SYNTAX INTEGER { on(1),off(2) }
        ACCESS read-only
        STATUS mandatory
        DESCRIPTION "The state of the converter's FLRecv LED"
        ::= { ceCxFrl04Entry 4 }

ceCxFrl04FLLink OBJECT-TYPE 
        SYNTAX INTEGER { on(1),off(2) }
        ACCESS read-only
        STATUS mandatory
        DESCRIPTION "The state of the converter's FLLink LED"
        ::= { ceCxFrl04Entry 5 }

ceCxFrl04Power OBJECT-TYPE 
        SYNTAX INTEGER { on(1),off(2) }
        ACCESS read-only
        STATUS mandatory
        DESCRIPTION "The state of the converter's Power LED"
        ::= { ceCxFrl04Entry 6 }


-- ==================================================================
--  Table for C/F-SM-MM-02 media converters in a media converter chassis.
cfSmMm02Table OBJECT-TYPE 
        SYNTAX SEQUENCE OF CfSmMm02Entry
        ACCESS not-accessible
        STATUS mandatory
        DESCRIPTION "One table entry per slot in the media converter chassis.
             If physical slot 'n' contains a working C/F-SM-MM-02 media 
             converter, then entry 'n' in this table exists and describes
             the state of the converter's LEDs  If slot 'n' is empty, does
             not exist, or contains a different type of device, then table
             entry 'n' does not exist."
        ::= { slotMc20p 4 }

cfSmMm02Entry OBJECT-TYPE 
        SYNTAX CfSmMm02Entry
        ACCESS not-accessible
        STATUS mandatory
        DESCRIPTION "State of LEDs on a single C/F-SM-MM-02"
        INDEX { cfSmMm02Index }
        ::= { cfSmMm02Table 1 }

CfSmMm02Entry ::=
        SEQUENCE {
                cfSmMm02Index          INTEGER,
                cfSmMm02MMSignalDetect INTEGER,
                cfSmMm02SMSignalDetect INTEGER,
                cfSmMm02Power          INTEGER
                }

cfSmMm02Index OBJECT-TYPE 
        SYNTAX INTEGER
        ACCESS read-only
        STATUS mandatory
        DESCRIPTION "The index of a slot in a media converter chassis"
        ::= { cfSmMm02Entry 1 }

cfSmMm02MMSignalDetect OBJECT-TYPE 
        SYNTAX INTEGER { on(1),off(2) }
        ACCESS read-only
        STATUS mandatory
        DESCRIPTION "The state of the converter's MMSignalDetect LED"
        ::= { cfSmMm02Entry 2 }

cfSmMm02SMSignalDetect OBJECT-TYPE 
        SYNTAX INTEGER { on(1),off(2) }
        ACCESS read-only
        STATUS mandatory
        DESCRIPTION "The state of the converter's SMSignalDetect LED"
        ::= { cfSmMm02Entry 3 }

cfSmMm02Power OBJECT-TYPE 
        SYNTAX INTEGER { on(1),off(2) }
        ACCESS read-only
        STATUS mandatory
        DESCRIPTION "The state of the converter's Power LED"
        ::= { cfSmMm02Entry 4 }

-- ==================================================================
--  Table for C/F-SM-MM-05 media converters in a media converter chassis.
cfSmMm05Table OBJECT-TYPE 
        SYNTAX SEQUENCE OF CfSmMm05Entry
        ACCESS not-accessible
        STATUS mandatory
        DESCRIPTION "One table entry per slot in the media converter chassis.
             If physical slot 'n' contains a working C/F-SM-MM-05 media 
             converter, then entry 'n' in this table exists and describes
             the state of the converter's LEDs  If slot 'n' is empty, does
             not exist, or contains a different type of device, then table
             entry 'n' does not exist."
        ::= { slotMc20p 5 }

cfSmMm05Entry OBJECT-TYPE 
        SYNTAX CfSmMm05Entry
        ACCESS not-accessible
        STATUS mandatory
        DESCRIPTION "State of LEDs on a single C/F-SM-MM-05"
        INDEX { cfSmMm05Index }
        ::= { cfSmMm05Table 1 }

CfSmMm05Entry ::= 
        SEQUENCE {
                cfSmMm05Index          INTEGER,
                cfSmMm05SMSignalDetect INTEGER,
                cfSmMm05MMSignalDetect INTEGER,
                cfSmMm05Power          INTEGER
                }

cfSmMm05Index OBJECT-TYPE 
        SYNTAX INTEGER
        ACCESS read-only
        STATUS mandatory
        DESCRIPTION "The index of a slot in a media converter chassis"
        ::= { cfSmMm05Entry 1 }

cfSmMm05SMSignalDetect OBJECT-TYPE 
        SYNTAX INTEGER { on(1),off(2) }
        ACCESS read-only
        STATUS mandatory
        DESCRIPTION "The state of the converter's SMSignalDetect LED"
        ::= { cfSmMm05Entry 2 }

cfSmMm05MMSignalDetect OBJECT-TYPE 
        SYNTAX INTEGER { on(1),off(2) }
        ACCESS read-only
        STATUS mandatory
        DESCRIPTION "The state of the converter's MMSignalDetect LED"
        ::= { cfSmMm05Entry 3}

cfSmMm05Power OBJECT-TYPE 
        SYNTAX INTEGER { on(1),off(2) }
        ACCESS read-only
        STATUS mandatory
        DESCRIPTION "The state of the converter's Power LED"
        ::= { cfSmMm05Entry 4 }

-- ==================================================================
-- Table for C/A-CF-02 media converters in a media converter chassis.
caCf02Table OBJECT-TYPE 
       SYNTAX SEQUENCE OF CaCf02Entry
       ACCESS not-accessible
       STATUS mandatory
       DESCRIPTION "One table entry per slot in the media converter chassis.
            If physical slot 'n' contains a working C/A-CF-02 media 
            converter, then entry 'n' in this table exists and describes
            the state of the converter's LEDs  If slot 'n' is empty, does
            not exist, or contains a different type of device, then table
            entry 'n' does not exist."
       ::= { slotMc20p 6 }

caCf02Entry OBJECT-TYPE 
       SYNTAX CaCf02Entry
       ACCESS not-accessible
       STATUS mandatory
       DESCRIPTION "State of LEDs on a single C/A-CF-02"
       INDEX { caCf02Index }
       ::= { caCf02Table 1 }

CaCf02Entry ::= 
       SEQUENCE {
               caCf02Index          INTEGER,
               caCf02CopperSignalDetect INTEGER,
               caCf02FiberSignalDetect INTEGER,
               caCf02Power          INTEGER
               }

caCf02Index OBJECT-TYPE 
       SYNTAX INTEGER
       ACCESS read-only
       STATUS mandatory
       DESCRIPTION "The index of a slot in a media converter chassis"
       ::= { caCf02Entry 1 }

caCf02CopperSignalDetect OBJECT-TYPE 
       SYNTAX INTEGER { on(1),off(2) }
       ACCESS read-only
       STATUS mandatory
       DESCRIPTION "The state of the converter's CopperSignalDetect LED"
       ::= { caCf02Entry 2 }

caCf02FiberSignalDetect OBJECT-TYPE 
       SYNTAX INTEGER { on(1),off(2) }
       ACCESS read-only
       STATUS mandatory
       DESCRIPTION "The state of the converter's FiberSignalDetect LED"
       ::= { caCf02Entry 3 }

caCf02Power OBJECT-TYPE 
       SYNTAX INTEGER { on(1),off(2) }
       ACCESS read-only
       STATUS mandatory
       DESCRIPTION "The state of the converter's Power LED"
       ::= { caCf02Entry 4 }

-- ==================================================================
--  Table for C/F-SM-MM-06 media converters in a media converter chassis.
cfSmMm06Table OBJECT-TYPE 
        SYNTAX SEQUENCE OF CfSmMm06Entry
        ACCESS not-accessible
        STATUS mandatory
        DESCRIPTION "One table entry per slot in the media converter chassis.
             If physical slot 'n' contains a working C/F-SM-MM-06 media 
             converter, then entry 'n' in this table exists and describes
             the state of the converter's LEDs  If slot 'n' is empty, does
             not exist, or contains a different type of device, then table
             entry 'n' does not exist."
        ::= { slotMc20p 7 }

cfSmMm06Entry OBJECT-TYPE 
        SYNTAX CfSmMm06Entry
        ACCESS not-accessible
        STATUS mandatory
        DESCRIPTION "State of LEDs on a single C/F-SM-MM-06"
        INDEX { cfSmMm06Index }
        ::= { cfSmMm06Table 1 }

CfSmMm06Entry ::= 
        SEQUENCE {
                cfSmMm06Index          INTEGER,
                cfSmMm06MMSignalDetect INTEGER,
                cfSmMm06SMSignalDetect INTEGER,
                cfSmMm06Power          INTEGER
                }

cfSmMm06Index OBJECT-TYPE 
        SYNTAX INTEGER
        ACCESS read-only
        STATUS mandatory
        DESCRIPTION "The index of a slot in a media converter chassis"
        ::= { cfSmMm06Entry 1 }

cfSmMm06MMSignalDetect OBJECT-TYPE 
        SYNTAX INTEGER { on(1),off(2) }
        ACCESS read-only
        STATUS mandatory
        DESCRIPTION "The state of the converter's MMSignalDetect LED"
        ::= { cfSmMm06Entry 2 }

cfSmMm06SMSignalDetect OBJECT-TYPE 
        SYNTAX INTEGER { on(1),off(2) }
        ACCESS read-only
        STATUS mandatory
        DESCRIPTION "The state of the converter's SMSignalDetect LED"
        ::= { cfSmMm06Entry 3 }

cfSmMm06Power OBJECT-TYPE 
        SYNTAX INTEGER { on(1),off(2) }
        ACCESS read-only
        STATUS mandatory
        DESCRIPTION "The state of the converter's Power LED"
        ::= { cfSmMm06Entry 4 }

-- ==================================================================
--  Table for C/T1E1-CF-01 media converters in a media converter chassis.
ct1e1Cf01Table OBJECT-TYPE 
        SYNTAX SEQUENCE OF Ct1e1Cf01Entry
        ACCESS not-accessible
        STATUS mandatory
        DESCRIPTION "One table entry per slot in the media converter chassis.
             If physical slot 'n' contains a working C/T1E1-CF-01 media 
             converter, then entry 'n' in this table exists and describes
             the state of the converter's LEDs  If slot 'n' is empty, does
             not exist, or contains a different type of device, then table
             entry 'n' does not exist."
        ::= { slotMc20p 8 }

ct1e1Cf01Entry OBJECT-TYPE 
        SYNTAX Ct1e1Cf01Entry
        ACCESS not-accessible
        STATUS mandatory
        DESCRIPTION "State of LEDs on a single C/T1E1-CF-01"
        INDEX { ct1e1Cf01Index }
        ::= { ct1e1Cf01Table 1 }

Ct1e1Cf01Entry ::= 
        SEQUENCE {
                ct1e1Cf01Index              INTEGER,
                ct1e1Cf01CopperSignalDetect INTEGER,
                ct1e1Cf01FiberSignalDetect  INTEGER,
                ct1e1Cf01CoaxActive         INTEGER
                }

ct1e1Cf01Index OBJECT-TYPE 
        SYNTAX INTEGER
        ACCESS read-only
        STATUS mandatory
        DESCRIPTION "The index of a slot in a media converter chassis"
        ::= { ct1e1Cf01Entry 1 }

ct1e1Cf01CopperSignalDetect OBJECT-TYPE 
        SYNTAX INTEGER { on(1),off(2) }
        ACCESS read-only
        STATUS mandatory
        DESCRIPTION "The state of the converter's CopperSignalDetect LED"
        ::= { ct1e1Cf01Entry 2 }

ct1e1Cf01FiberSignalDetect OBJECT-TYPE 
        SYNTAX INTEGER { on(1),off(2) }
        ACCESS read-only
        STATUS mandatory
        DESCRIPTION "The state of the converter's FiberSignalDetect LED"
        ::= { ct1e1Cf01Entry 3 }

ct1e1Cf01CoaxActive OBJECT-TYPE 
        SYNTAX INTEGER { on(1),off(2) }
        ACCESS read-only
        STATUS mandatory
        DESCRIPTION "The state of the converter's Coax Active LED"
        ::= { ct1e1Cf01Entry 4 }


-- ==================================================================
--  Table for C/E-R-TX-FX-01 media converters in a media converter chassis.
ceRTxFx01Table OBJECT-TYPE 
        SYNTAX SEQUENCE OF CeRTxFx01Entry
        ACCESS not-accessible
        STATUS mandatory
        DESCRIPTION "One table entry per slot in the media converter chassis.
             If physical slot 'n' contains a working C/E-R-TX-FX-01 media 
             converter, then entry 'n' in this table exists and describes
             the state of the converter's LEDs  If slot 'n' is empty, does
             not exist, or contains a different type of device, then table
             entry 'n' does not exist."
        ::= { slotMc20p 9 }

ceRTxFx01Entry OBJECT-TYPE 
        SYNTAX CeRTxFx01Entry
        ACCESS not-accessible
        STATUS mandatory
        DESCRIPTION "State of LEDs on a single C/E-R-TX-FX-01"
        INDEX { ceRTxFx01Index }
        ::= { ceRTxFx01Table 1 }

CeRTxFx01Entry ::= 
        SEQUENCE {
                ceRTxFx01Index              INTEGER,
                ceRTxFx01TPPrimary          INTEGER,
                ceRTxFx01FiberPrimary       INTEGER,
                ceRTxFx01TPSignalDetect     INTEGER,
                ceRTxFx01FiberSignalDetect  INTEGER
                }

ceRTxFx01Index OBJECT-TYPE 
        SYNTAX INTEGER
        ACCESS read-only
        STATUS mandatory
        DESCRIPTION "The index of a slot in a media converter chassis"
        ::= { ceRTxFx01Entry 1 }

ceRTxFx01TPPrimary OBJECT-TYPE 
        SYNTAX INTEGER { on(1),off(2) }
        ACCESS read-only
        STATUS mandatory
        DESCRIPTION "The state of the converter's Twisted Pair Primary LED"
        ::= { ceRTxFx01Entry 2 }

ceRTxFx01FiberPrimary OBJECT-TYPE 
        SYNTAX INTEGER { on(1),off(2) }
        ACCESS read-only
        STATUS mandatory
        DESCRIPTION "The state of the converter's Fiber Primary LED"
        ::= { ceRTxFx01Entry 3 }

ceRTxFx01TPSignalDetect OBJECT-TYPE 
        SYNTAX INTEGER { on(1),off(2) }
        ACCESS read-only
        STATUS mandatory
        DESCRIPTION "The state of the converter's Twisted Pair Signal Detect LED"
        ::= { ceRTxFx01Entry 4 }

ceRTxFx01FiberSignalDetect OBJECT-TYPE
        SYNTAX INTEGER { on(1),off(2) }
        ACCESS read-only
        STATUS mandatory
        DESCRIPTION "The state of the converter's Fiber Signal Detect LED"
        ::= { ceRTxFx01Entry 5 }


-- ==================================================================
--  Table for C/E-100-BTX-FX-04(ST/SC) media converters in a media 
--  converter chassis.
ce100BtxFx04Table OBJECT-TYPE 
        SYNTAX SEQUENCE OF Ce100BtxFx04Entry
        ACCESS not-accessible
        STATUS mandatory
        DESCRIPTION "One table entry per slot in the media converter chassis.
             If physical slot 'n' contains a working C/E-100-BTX-FX-04(ST/SC)
             media converter, then entry 'n' in this table exists and describes
             the state of the converter's LEDs  If slot 'n' is empty, does
             not exist, or contains a different type of device, then table
             entry 'n' does not exist."
        ::= { slotMc20p 10 }

ce100BtxFx04Entry OBJECT-TYPE 
        SYNTAX Ce100BtxFx04Entry
        ACCESS not-accessible
        STATUS mandatory
        DESCRIPTION "State of LEDs on a single C/E-100-BTX-FX-04(ST/SC)"
        INDEX { ce100BtxFx04Index }
        ::= { ce100BtxFx04Table 1 }

Ce100BtxFx04Entry ::= 
        SEQUENCE {
                ce100BtxFx04Index INTEGER,
                ce100BtxFx04TPRecv INTEGER,
                ce100BtxFx04FiberRecv INTEGER,
                ce100BtxFx04TPSignalDetect INTEGER,
                ce100BtxFx04FiberSignalDetect INTEGER,
                ce100BtxFx04Power INTEGER
                }

ce100BtxFx04Index OBJECT-TYPE 
        SYNTAX INTEGER
        ACCESS read-only
        STATUS mandatory
        DESCRIPTION "The index of a slot in a media converter chassis"
        ::= { ce100BtxFx04Entry 1 }

ce100BtxFx04TPRecv OBJECT-TYPE 
        SYNTAX INTEGER { on(1),off(2) }
        ACCESS read-only
        STATUS mandatory
        DESCRIPTION "The state of the converter's Twisted Pair Receive LED"
        ::= { ce100BtxFx04Entry 2 }

ce100BtxFx04FiberRecv OBJECT-TYPE 
        SYNTAX INTEGER { on(1),off(2) }
        ACCESS read-only
        STATUS mandatory
        DESCRIPTION "The state of the converter's Fiber Receive LED"
        ::= { ce100BtxFx04Entry 3 }

ce100BtxFx04TPSignalDetect OBJECT-TYPE 
        SYNTAX INTEGER { on(1),off(2) }
        ACCESS read-only
        STATUS mandatory
        DESCRIPTION "The state of the converter's Twisted Pair signal detect LED"
        ::= { ce100BtxFx04Entry 4 }

ce100BtxFx04FiberSignalDetect OBJECT-TYPE 
        SYNTAX INTEGER { on(1),off(2) }
        ACCESS read-only
        STATUS mandatory
        DESCRIPTION "The state of the converter's fiber signal detect LED"
        ::= { ce100BtxFx04Entry 5 }

ce100BtxFx04Power OBJECT-TYPE 
        SYNTAX INTEGER { on(1),off(2) }
        ACCESS read-only
        STATUS mandatory
        DESCRIPTION "The state of the converter's Power LED"
        ::= { ce100BtxFx04Entry 6 }


-- ==================================================================
--  Table for C/PS-CF-01 media converters in a media 
--  converter chassis.
--  Note that the first three letters of this name DO NOT indicate 
--  that this device is in any way related to the Point System. It
--  is an MCC16-only device. The naming is an unfortunate coincidence.
cpsCf01Table OBJECT-TYPE 
        SYNTAX SEQUENCE OF CpsCf01Entry
        ACCESS not-accessible
        STATUS mandatory
        DESCRIPTION "One table entry per slot in the media converter chassis.
             If physical slot 'n' contains a working C/PS-CF-01 
             media converter, then entry 'n' in this table exists and describes
             the state of the converter's LEDs  If slot 'n' is empty, does
             not exist, or contains a different type of device, then table
             entry 'n' does not exist."
        ::= { slotMc20p 12 }

cpsCf01Entry OBJECT-TYPE 
        SYNTAX CpsCf01Entry
        ACCESS not-accessible
        STATUS mandatory
        DESCRIPTION "State of LEDs on a single C/PS-CF-01"
        INDEX { cpsCf01Index }
        ::= { cpsCf01Table 1 }

CpsCf01Entry ::= 
        SEQUENCE {
                cpsCf01Index INTEGER,
                cpsCf01FiberRecv INTEGER,
                cpsCf01TPRecv INTEGER,
                cpsCf01Power INTEGER
                }

cpsCf01Index OBJECT-TYPE 
        SYNTAX INTEGER
        ACCESS read-only
        STATUS mandatory
        DESCRIPTION "The index of a slot in a media converter chassis"
        ::= { cpsCf01Entry 1 }

cpsCf01FiberRecv OBJECT-TYPE 
        SYNTAX INTEGER { on(1),off(2) }
        ACCESS read-only
        STATUS mandatory
        DESCRIPTION "The state of the converter's Fiber Receive LED"
        ::= { cpsCf01Entry 2 }

cpsCf01TPRecv OBJECT-TYPE 
        SYNTAX INTEGER { on(1),off(2) }
        ACCESS read-only
        STATUS mandatory
        DESCRIPTION "The state of the converter's Twisted Pair Receive LED"
        ::= { cpsCf01Entry 3 }

cpsCf01Power OBJECT-TYPE 
        SYNTAX INTEGER { on(1),off(2) }
        ACCESS read-only
        STATUS mandatory
        DESCRIPTION "The state of the converter's Power LED"
        ::= { cpsCf01Entry 4 }


-- ==================================================================
--  Table for C/B-CF-01 media converters in a media 
--  converter chassis.
cbCf01Table OBJECT-TYPE 
        SYNTAX SEQUENCE OF CbCf01Entry
        ACCESS not-accessible
        STATUS mandatory
        DESCRIPTION "One table entry per slot in the media converter chassis.
             If physical slot 'n' contains a working C/B-CF-01 
             media converter, then entry 'n' in this table exists and describes
             the state of the converter's LEDs  If slot 'n' is empty, does
             not exist, or contains a different type of device, then table
             entry 'n' does not exist."
        ::= { slotMc20p 13 }

cbCf01Entry OBJECT-TYPE 
        SYNTAX CbCf01Entry
        ACCESS not-accessible
        STATUS mandatory
        DESCRIPTION "State of LEDs on a single C/B-CF-01"
        INDEX { cbCf01Index }
        ::= { cbCf01Table 1 }

CbCf01Entry ::= 
        SEQUENCE {
                cbCf01Index INTEGER,
                cbCf01FiberRecv INTEGER,
                cbCf01TPCoaxRecv INTEGER,
                cbCf01Power INTEGER
                }

cbCf01Index OBJECT-TYPE 
        SYNTAX INTEGER
        ACCESS read-only
        STATUS mandatory
        DESCRIPTION "The index of a slot in a media converter chassis"
        ::= { cbCf01Entry 1 }

cbCf01FiberRecv OBJECT-TYPE 
        SYNTAX INTEGER { on(1),off(2) }
        ACCESS read-only
        STATUS mandatory
        DESCRIPTION "The state of the converter's Fiber Receive LED"
        ::= { cbCf01Entry 2 }

cbCf01TPCoaxRecv OBJECT-TYPE 
        SYNTAX INTEGER { on(1),off(2) }
        ACCESS read-only
        STATUS mandatory
        DESCRIPTION "The state of the converter's Twisted Pair/Coax Receive LED"
        ::= { cbCf01Entry 3 }

cbCf01Power OBJECT-TYPE 
        SYNTAX INTEGER { on(1),off(2) }
        ACCESS read-only
        STATUS mandatory
        DESCRIPTION "The state of the converter's Power LED"
        ::= { cbCf01Entry 4 }


-- ==================================================================
--  Table for C/AR-CF-01 media converters in a media 
--  converter chassis.
carCf01Table OBJECT-TYPE 
        SYNTAX SEQUENCE OF CarCf01Entry
        ACCESS not-accessible
        STATUS mandatory
        DESCRIPTION "One table entry per slot in the media converter chassis.
             If physical slot 'n' contains a working C/AR-CF-01 
             media converter, then entry 'n' in this table exists and describes
             the state of the converter's LEDs  If slot 'n' is empty, does
             not exist, or contains a different type of device, then table
             entry 'n' does not exist."
        ::= { slotMc20p 14 }

carCf01Entry OBJECT-TYPE 
        SYNTAX CarCf01Entry
        ACCESS not-accessible
        STATUS mandatory
        DESCRIPTION "State of LEDs on a single C/AR-CF-01"
        INDEX { carCf01Index }
        ::= { carCf01Table 1 }

CarCf01Entry ::= 
        SEQUENCE {
                carCf01Index INTEGER,
                carCf01FiberRecv INTEGER,
                carCf01TPRecv INTEGER,
                carCf01Power INTEGER
                }

carCf01Index OBJECT-TYPE 
        SYNTAX INTEGER
        ACCESS read-only
        STATUS mandatory
        DESCRIPTION "The index of a slot in a media converter chassis"
        ::= { carCf01Entry 1 }

carCf01FiberRecv OBJECT-TYPE 
        SYNTAX INTEGER { on(1),off(2) }
        ACCESS read-only
        STATUS mandatory
        DESCRIPTION "The state of the converter's Fiber Receive LED"
        ::= { carCf01Entry 2 }

carCf01TPRecv OBJECT-TYPE 
        SYNTAX INTEGER { on(1),off(2) }
        ACCESS read-only
        STATUS mandatory
        DESCRIPTION "The state of the converter's Twisted Pair Receive LED"
        ::= { carCf01Entry 3 }

carCf01Power OBJECT-TYPE 
        SYNTAX INTEGER { on(1),off(2) }
        ACCESS read-only
        STATUS mandatory
        DESCRIPTION "The state of the converter's Power LED"
        ::= { carCf01Entry 4 }


-- ==================================================================
--  Table for C/AR-CF-02 media converters in a media 
--  converter chassis.
carCf02Table OBJECT-TYPE 
        SYNTAX SEQUENCE OF CarCf02Entry
        ACCESS not-accessible
        STATUS mandatory
        DESCRIPTION "One table entry per slot in the media converter chassis.
             If physical slot 'n' contains a working C/AR-CF-02 
             media converter, then entry 'n' in this table exists and describes
             the state of the converter's LEDs  If slot 'n' is empty, does
             not exist, or contains a different type of device, then table
             entry 'n' does not exist."
        ::= { slotMc20p 15 }

carCf02Entry OBJECT-TYPE 
        SYNTAX CarCf02Entry
        ACCESS not-accessible
        STATUS mandatory
        DESCRIPTION "State of LEDs on a single C/AR-CF-02"
        INDEX { carCf02Index }
        ::= { carCf02Table 1 }

CarCf02Entry ::= 
        SEQUENCE {
                carCf02Index INTEGER,
                carCf02FiberRecv INTEGER,
                carCf02CoaxRecv INTEGER,
                carCf02Power INTEGER
                }

carCf02Index OBJECT-TYPE 
        SYNTAX INTEGER
        ACCESS read-only
        STATUS mandatory
        DESCRIPTION "The index of a slot in a media converter chassis"
        ::= { carCf02Entry 1 }

carCf02FiberRecv OBJECT-TYPE 
        SYNTAX INTEGER { on(1),off(2) }
        ACCESS read-only
        STATUS mandatory
        DESCRIPTION "The state of the converter's Fiber Receive LED"
        ::= { carCf02Entry 2 }

carCf02CoaxRecv OBJECT-TYPE 
        SYNTAX INTEGER { on(1),off(2) }
        ACCESS read-only
        STATUS mandatory
        DESCRIPTION "The state of the converter's Coax Receive LED"
        ::= { carCf02Entry 3 }

carCf02Power OBJECT-TYPE 
        SYNTAX INTEGER { on(1),off(2) }
        ACCESS read-only
        STATUS mandatory
        DESCRIPTION "The state of the converter's Power LED"
        ::= { carCf02Entry 4 }


-- ==================================================================
--  Table for C/E-PSW-FX-03 ethernet switch in a media converter chassis.
cePswFx03Table OBJECT-TYPE 
        SYNTAX SEQUENCE OF CePswFx03Entry
        ACCESS not-accessible
        STATUS mandatory
        DESCRIPTION "One table entry per slot in the media converter chassis.
             If physical slot 'n' contains a working C/E-PSW-FX-03 ethernet 
             switch, then entry 'n' in this table exists and describes
             the state of the switch's LEDs  If slot 'n' is empty, does
             not exist, or contains a different type of device, then table
             entry 'n' does not exist."
        ::= { slotMc20p 16 }

cePswFx03Entry OBJECT-TYPE 
        SYNTAX CePswFx03Entry
        ACCESS not-accessible
        STATUS mandatory
        DESCRIPTION "State of LEDs on a single C/E-PSW-FX-03"
        INDEX { cePswFx03Index }
        ::= { cePswFx03Table 1 }

CePswFx03Entry ::= 
        SEQUENCE {
                cePswFx03Index           INTEGER,
                cePswFx03TPFullDuplex    INTEGER,
                cePswFx03FiberFullDuplex INTEGER,
                cePswFx03TPLink          INTEGER,
                cePswFx03FiberLink       INTEGER,
                cePswFx03TP100Mbps       INTEGER
                }

cePswFx03Index OBJECT-TYPE 
        SYNTAX INTEGER
        ACCESS read-only
        STATUS mandatory
        DESCRIPTION "The index of a slot in a media converter chassis"
        ::= { cePswFx03Entry 1 }

cePswFx03TPFullDuplex OBJECT-TYPE 
        SYNTAX INTEGER { on(1),off(2) }
        ACCESS read-only
        STATUS mandatory
        DESCRIPTION "The state of the converter's Twisted Pair FDX LED"
        ::= { cePswFx03Entry 2 }

cePswFx03FiberFullDuplex OBJECT-TYPE 
        SYNTAX INTEGER { on(1),off(2) }
        ACCESS read-only
        STATUS mandatory
        DESCRIPTION "The state of the converter's Fiber FDX LED"
        ::= { cePswFx03Entry 3 }

cePswFx03TPLink OBJECT-TYPE 
        SYNTAX INTEGER { on(1),off(2) }
        ACCESS read-only
        STATUS mandatory
        DESCRIPTION "The state of the converter's Twisted Pair Link LED"
        ::= { cePswFx03Entry 4 }

cePswFx03FiberLink OBJECT-TYPE 
        SYNTAX INTEGER { on(1),off(2) }
        ACCESS read-only
        STATUS mandatory
        DESCRIPTION "The state of the converter's Fiber Link LED"
        ::= { cePswFx03Entry 5 }

cePswFx03TP100Mbps OBJECT-TYPE 
        SYNTAX INTEGER { on(1),off(2) }
        ACCESS read-only
        STATUS mandatory
        DESCRIPTION "The state of the converter's Twisted Pair 100Mbps LED"
        ::= { cePswFx03Entry 6 }


-- ==================================================================
--  Table for C/E-PSW-SX-01 ethernet switch in a media converter chassis.
cePswSx01Table OBJECT-TYPE 
        SYNTAX SEQUENCE OF CePswSx01Entry
        ACCESS not-accessible
        STATUS mandatory
        DESCRIPTION "One table entry per slot in the media converter chassis.
             If physical slot 'n' contains a working C/E-PSW-SX-01 ethernet 
             switch, then entry 'n' in this table exists and describes
             the state of the switch's LEDs  If slot 'n' is empty, does
             not exist, or contains a different type of device, then table
             entry 'n' does not exist."
        ::= { slotMc20p 17 }

cePswSx01Entry OBJECT-TYPE 
        SYNTAX CePswSx01Entry
        ACCESS not-accessible
        STATUS mandatory
        DESCRIPTION "State of LEDs on a single C/E-PSW-SX-01"
        INDEX { cePswSx01Index }
        ::= { cePswSx01Table 1 }

CePswSx01Entry ::= 
        SEQUENCE {
                cePswSx01Index           INTEGER,
                cePswSx01TPFullDuplex    INTEGER,
                cePswSx01FiberFullDuplex INTEGER,
                cePswSx01TPLink          INTEGER,
                cePswSx01FiberLink       INTEGER,
                cePswSx01TP100Mbps       INTEGER
                }

cePswSx01Index OBJECT-TYPE 
        SYNTAX INTEGER
        ACCESS read-only
        STATUS mandatory
        DESCRIPTION "The index of a slot in a media converter chassis"
        ::= { cePswSx01Entry 1 }

cePswSx01TPFullDuplex OBJECT-TYPE 
        SYNTAX INTEGER { on(1),off(2) }
        ACCESS read-only
        STATUS mandatory
        DESCRIPTION "The state of the converter's Twisted Pair FDX LED"
        ::= { cePswSx01Entry 2 }

cePswSx01FiberFullDuplex OBJECT-TYPE 
        SYNTAX INTEGER { on(1),off(2) }
        ACCESS read-only
        STATUS mandatory
        DESCRIPTION "The state of the converter's Fiber FDX LED"
        ::= { cePswSx01Entry 3 }

cePswSx01TPLink OBJECT-TYPE 
        SYNTAX INTEGER { on(1),off(2) }
        ACCESS read-only
        STATUS mandatory
        DESCRIPTION "The state of the converter's Twisted Pair Link LED"
        ::= { cePswSx01Entry 4 }

cePswSx01FiberLink OBJECT-TYPE 
        SYNTAX INTEGER { on(1),off(2) }
        ACCESS read-only
        STATUS mandatory
        DESCRIPTION "The state of the converter's Fiber Link LED"
        ::= { cePswSx01Entry 5 }

cePswSx01TP100Mbps OBJECT-TYPE 
        SYNTAX INTEGER { on(1),off(2) }
        ACCESS read-only
        STATUS mandatory
        DESCRIPTION "The state of the converter's Twisted Pair 100Mbps LED"
        ::= { cePswSx01Entry 6 }


-- ==================================================================
--  Table for C/RS232-CF-01 media converter in a media converter chassis.
cRs232Cf01Table OBJECT-TYPE 
        SYNTAX SEQUENCE OF CRs232Cf01Entry
        ACCESS not-accessible
        STATUS mandatory
        DESCRIPTION "One table entry per slot in the media converter chassis.
             If physical slot 'n' contains a working C/RS232-CF-01 media    
             converter, then entry 'n' in this table exists and describes
             the state of the converter's LEDs  If slot 'n' is empty, does
             not exist, or contains a different type of device, then table
             entry 'n' does not exist."
        ::= { slotMc20p 18 }

cRs232Cf01Entry OBJECT-TYPE 
        SYNTAX CRs232Cf01Entry
        ACCESS not-accessible
        STATUS mandatory
        DESCRIPTION "State of LEDs on a single C/RS232-CF-01"
        INDEX { cRs232Cf01Index }
        ::= { cRs232Cf01Table 1 }

CRs232Cf01Entry ::= 
        SEQUENCE {
                cRs232Cf01Index           INTEGER,
                cRs232Cf01FiberLock       INTEGER
                }

cRs232Cf01Index OBJECT-TYPE 
        SYNTAX INTEGER
        ACCESS read-only
        STATUS mandatory
        DESCRIPTION "The index of a slot in a media converter chassis"
        ::= { cRs232Cf01Entry 1 }

cRs232Cf01FiberLock OBJECT-TYPE 
        SYNTAX INTEGER { on(1),off(2) }
        ACCESS read-only
        STATUS mandatory
        DESCRIPTION "The state of the converter's Fiber Lock LED"
        ::= { cRs232Cf01Entry 2 }


-- ==================================================================
--  Table for C/F-SM-MM-04 media converters in a media converter chassis.
cfSmMm04Table OBJECT-TYPE 
        SYNTAX SEQUENCE OF CfSmMm04Entry
        ACCESS not-accessible
        STATUS mandatory
        DESCRIPTION "One table entry per slot in the media converter chassis.
             If physical slot 'n' contains a working C/F-SM-MM-04 media 
             converter, then entry 'n' in this table exists and describes
             the state of the converter's LEDs  If slot 'n' is empty, does
             not exist, or contains a different type of device, then table
             entry 'n' does not exist."
        ::= { slotMc20p 24 }

cfSmMm04Entry OBJECT-TYPE 
        SYNTAX CfSmMm04Entry
        ACCESS not-accessible
        STATUS mandatory
        DESCRIPTION "State of LEDs on a single C/F-SM-MM-04"
        INDEX { cfSmMm04Index }
        ::= { cfSmMm04Table 1 }

CfSmMm04Entry ::= 
        SEQUENCE {
                cfSmMm04Index          INTEGER,
                cfSmMm04MMSignalDetect INTEGER,
                cfSmMm04SMSignalDetect INTEGER,
                cfSmMm04Power          INTEGER
                }

cfSmMm04Index OBJECT-TYPE 
        SYNTAX INTEGER
        ACCESS read-only
        STATUS mandatory
        DESCRIPTION "The index of a slot in a media converter chassis"
        ::= { cfSmMm04Entry 1 }

cfSmMm04MMSignalDetect OBJECT-TYPE 
        SYNTAX INTEGER { on(1),off(2) }
        ACCESS read-only
        STATUS mandatory
        DESCRIPTION "The state of the converter's Multi-Mode signal detect LED"
        ::= { cfSmMm04Entry 2 }

cfSmMm04SMSignalDetect OBJECT-TYPE 
        SYNTAX INTEGER { on(1),off(2) }
        ACCESS read-only
        STATUS mandatory
        DESCRIPTION "The state of the converter's Single-Mode signal detect LED"
        ::= { cfSmMm04Entry 3 }

cfSmMm04Power OBJECT-TYPE 
        SYNTAX INTEGER { on(1),off(2) }
        ACCESS read-only
        STATUS mandatory
        DESCRIPTION "The state of the converter's Power LED"
        ::= { cfSmMm04Entry 4 }


-- ==================================================================
--  Table for C/E-100-BTX-SX-01 media converters in a media 
--  converter chassis.
ce100BtxSx01Table OBJECT-TYPE 
        SYNTAX SEQUENCE OF Ce100BtxSx01Entry
        ACCESS not-accessible
        STATUS mandatory
        DESCRIPTION "One table entry per slot in the media converter chassis.
             If physical slot 'n' contains a working C/E-100-BTX-SX-01
             media converter, then entry 'n' in this table exists and describes
             the state of the converter's LEDs  If slot 'n' is empty, does
             not exist, or contains a different type of device, then table
             entry 'n' does not exist."
        ::= { slotMc20p 26 }

ce100BtxSx01Entry OBJECT-TYPE 
        SYNTAX Ce100BtxSx01Entry
        ACCESS not-accessible
        STATUS mandatory
        DESCRIPTION "State of LEDs on a single C/E-100-BTX-SX-01"
        INDEX { ce100BtxSx01Index }
        ::= { ce100BtxSx01Table 1 }

Ce100BtxSx01Entry ::= 
        SEQUENCE {
                ce100BtxSx01Index INTEGER,
                ce100BtxSx01TPRecv INTEGER,
                ce100BtxSx01FiberRecv INTEGER,
                ce100BtxSx01TPSignalDetect INTEGER,
                ce100BtxSx01FiberSignalDetect INTEGER,
                ce100BtxSx01Power INTEGER
                }

ce100BtxSx01Index OBJECT-TYPE 
        SYNTAX INTEGER
        ACCESS read-only
        STATUS mandatory
        DESCRIPTION "The index of a slot in a media converter chassis"
        ::= { ce100BtxSx01Entry 1 }

ce100BtxSx01TPRecv OBJECT-TYPE 
        SYNTAX INTEGER { on(1),off(2) }
        ACCESS read-only
        STATUS mandatory
        DESCRIPTION "The state of the converter's Twisted Pair Receive LED"
        ::= { ce100BtxSx01Entry 2 }

ce100BtxSx01FiberRecv OBJECT-TYPE 
        SYNTAX INTEGER { on(1),off(2) }
        ACCESS read-only
        STATUS mandatory
        DESCRIPTION "The state of the converter's Fiber Receive LED"
        ::= { ce100BtxSx01Entry 3 }

ce100BtxSx01TPSignalDetect OBJECT-TYPE 
        SYNTAX INTEGER { on(1),off(2) }
        ACCESS read-only
        STATUS mandatory
        DESCRIPTION "The state of the converter's Twisted Pair signal detect LED"
        ::= { ce100BtxSx01Entry 4 }

ce100BtxSx01FiberSignalDetect OBJECT-TYPE 
        SYNTAX INTEGER { on(1),off(2) }
        ACCESS read-only
        STATUS mandatory
        DESCRIPTION "The state of the converter's fiber signal detect LED"
        ::= { ce100BtxSx01Entry 5 }

ce100BtxSx01Power OBJECT-TYPE 
        SYNTAX INTEGER { on(1),off(2) }
        ACCESS read-only
        STATUS mandatory
        DESCRIPTION "The state of the converter's Power LED"
        ::= { ce100BtxSx01Entry 6 }

-- ==================================================================
--  Table for C/E-100-BTX-FX-04(MT) media converters in a media 
--  converter chassis.
ce100BtxFx04MtTable OBJECT-TYPE 
        SYNTAX SEQUENCE OF Ce100BtxFx04MtEntry
        ACCESS not-accessible
        STATUS mandatory
        DESCRIPTION "One table entry per slot in the media converter chassis.
             If physical slot 'n' contains a working C/E-100-BTX-FX-04(MT)
             media converter, then entry 'n' in this table exists and describes
             the state of the converter's LEDs  If slot 'n' is empty, does
             not exist, or contains a different type of device, then table
             entry 'n' does not exist."
        ::= { slotMc20p 27 }

ce100BtxFx04MtEntry OBJECT-TYPE 
        SYNTAX Ce100BtxFx04MtEntry
        ACCESS not-accessible
        STATUS mandatory
        DESCRIPTION "State of LEDs on a single C/E-100-BTX-FX-04(MT)"
        INDEX { ce100BtxFx04MtIndex }
        ::= { ce100BtxFx04MtTable 1 }

Ce100BtxFx04MtEntry ::= 
        SEQUENCE {
                ce100BtxFx04MtIndex INTEGER,
                ce100BtxFx04MtTPRecv INTEGER,
                ce100BtxFx04MtFiberRecv INTEGER,
                ce100BtxFx04MtTPSignalDetect INTEGER,
                ce100BtxFx04MtFiberSignalDetect INTEGER,
                ce100BtxFx04MtPower INTEGER
                }

ce100BtxFx04MtIndex OBJECT-TYPE 
        SYNTAX INTEGER
        ACCESS read-only
        STATUS mandatory
        DESCRIPTION "The index of a slot in a media converter chassis"
        ::= { ce100BtxFx04MtEntry 1 }

ce100BtxFx04MtTPRecv OBJECT-TYPE 
        SYNTAX INTEGER { on(1),off(2) }
        ACCESS read-only
        STATUS mandatory
        DESCRIPTION "The state of the converter's Twisted Pair Receive LED"
        ::= { ce100BtxFx04MtEntry 2 }

ce100BtxFx04MtFiberRecv OBJECT-TYPE 
        SYNTAX INTEGER { on(1),off(2) }
        ACCESS read-only
        STATUS mandatory
        DESCRIPTION "The state of the converter's Fiber Receive LED"
        ::= { ce100BtxFx04MtEntry 3 }

ce100BtxFx04MtTPSignalDetect OBJECT-TYPE 
        SYNTAX INTEGER { on(1),off(2) }
        ACCESS read-only
        STATUS mandatory
        DESCRIPTION "The state of the converter's Twisted Pair signal detect LED"
        ::= { ce100BtxFx04MtEntry 4 }

ce100BtxFx04MtFiberSignalDetect OBJECT-TYPE 
        SYNTAX INTEGER { on(1),off(2) }
        ACCESS read-only
        STATUS mandatory
        DESCRIPTION "The state of the converter's fiber signal detect LED"
        ::= { ce100BtxFx04MtEntry 5 }

ce100BtxFx04MtPower OBJECT-TYPE 
        SYNTAX INTEGER { on(1),off(2) }
        ACCESS read-only
        STATUS mandatory
        DESCRIPTION "The state of the converter's Power LED"
        ::= { ce100BtxFx04MtEntry 6 }

-- ==================================================================
--  Table for C/FD-CD-01 media converters in a media converter chassis.
cfdCd01Table OBJECT-TYPE 
        SYNTAX SEQUENCE OF CfdCd01Entry
        ACCESS not-accessible
        STATUS mandatory
        DESCRIPTION "One table entry per slot in the media converter chassis.
             If physical slot 'n' contains a working C/FD-CD-01 media 
             converter, then entry 'n' in this table exists and describes
             the state of the converter's LEDs  If slot 'n' is empty, does
             not exist, or contains a different type of device, then table
             entry 'n' does not exist."
        ::= { slotMc20p 28 }

cfdCd01Entry OBJECT-TYPE 
        SYNTAX CfdCd01Entry
        ACCESS not-accessible
        STATUS mandatory
        DESCRIPTION "State of LEDs on a single C/FD-CD-01"
        INDEX { cfdCd01Index }
        ::= { cfdCd01Table 1 }

CfdCd01Entry ::= 
        SEQUENCE {
                cfdCd01Index          INTEGER,
                cfdCd01Lock           INTEGER,
                cfdCd01TPRecv         INTEGER,
                cfdCd01FiberRecv      INTEGER,
                cfdCd01TPSignalDetect INTEGER,
                cfdCd01FiberSignalDetect INTEGER
                }

cfdCd01Index OBJECT-TYPE 
        SYNTAX INTEGER
        ACCESS read-only
        STATUS mandatory
        DESCRIPTION "The index of a slot in a media converter chassis"
        ::= { cfdCd01Entry 1 }

cfdCd01Lock OBJECT-TYPE 
        SYNTAX INTEGER { on(1),off(2) }
        ACCESS read-only
        STATUS mandatory
        DESCRIPTION "The state of the converter's Lock LED"
        ::= { cfdCd01Entry 2 }

cfdCd01TPRecv OBJECT-TYPE 
        SYNTAX INTEGER { on(1),off(2) }
        ACCESS read-only
        STATUS mandatory
        DESCRIPTION "The state of the converter's TPRecv LED"
        ::= { cfdCd01Entry 3 }

cfdCd01FiberRecv OBJECT-TYPE 
        SYNTAX INTEGER { on(1),off(2) }
        ACCESS read-only
        STATUS mandatory
        DESCRIPTION "The state of the converter's FiberRecv LED"
        ::= { cfdCd01Entry 4 }

cfdCd01TPSignalDetect OBJECT-TYPE 
        SYNTAX INTEGER { on(1),off(2) }
        ACCESS read-only
        STATUS mandatory
        DESCRIPTION "The state of the converter's TPSignalDetect LED"
        ::= { cfdCd01Entry 5 }

cfdCd01FiberSignalDetect OBJECT-TYPE 
        SYNTAX INTEGER { on(1),off(2) }
        ACCESS read-only
        STATUS mandatory
        DESCRIPTION "The state of the converter's FiberSignalDetect LED"
        ::= { cfdCd01Entry 6 }


-- ==================================================================
--  Table for C/TR-CF-01 media converters in a media converter chassis.
ctrCf01Table OBJECT-TYPE 
        SYNTAX SEQUENCE OF CtrCf01Entry
        ACCESS not-accessible
        STATUS mandatory
        DESCRIPTION "One table entry per slot in the media converter chassis.
             If physical slot 'n' contains a working C/TR-CF-01 media 
             converter, then entry 'n' in this table exists and describes
             the state of the converter's LEDs  If slot 'n' is empty, does
             not exist, or contains a different type of device, then table
             entry 'n' does not exist."
        ::= { slotMc20p 29 }

ctrCf01Entry OBJECT-TYPE 
        SYNTAX CtrCf01Entry
        ACCESS not-accessible
        STATUS mandatory
        DESCRIPTION "State of LEDs on a single C/TR-CF-01"
        INDEX { ctrCf01Index }
        ::= { ctrCf01Table 1 }

CtrCf01Entry ::= 
        SEQUENCE {
                ctrCf01Index          INTEGER,
                ctrCf01FiberinOK      INTEGER,
                ctrCf01TPinOK         INTEGER,
                ctrCf01Inserted       INTEGER
                }

ctrCf01Index OBJECT-TYPE 
        SYNTAX INTEGER
        ACCESS read-only
        STATUS mandatory
        DESCRIPTION "The index of a slot in a media converter chassis"
        ::= { ctrCf01Entry 1 }

ctrCf01FiberinOK OBJECT-TYPE 
        SYNTAX INTEGER { on(1),off(2) }
        ACCESS read-only
        STATUS mandatory
        DESCRIPTION "The state of the converter's FiberinOK LED"
        ::= { ctrCf01Entry 2 }

ctrCf01TPinOK OBJECT-TYPE 
        SYNTAX INTEGER { on(1),off(2) }
        ACCESS read-only
        STATUS mandatory
        DESCRIPTION "The state of the converter's TPinOK LED"
        ::= { ctrCf01Entry 3 }

ctrCf01Inserted OBJECT-TYPE 
        SYNTAX INTEGER { on(1),off(2) }
        ACCESS read-only
        STATUS mandatory
        DESCRIPTION "The state of the converter's Inserted LED"
        ::= { ctrCf01Entry 4 }



-- ==================================================================
--  Table for C/E-100BTX-FRL-03 media converters in a media converter chassis.
ce100BtxFrl03Table OBJECT-TYPE 
        SYNTAX SEQUENCE OF Ce100BtxFrl03Entry
        ACCESS not-accessible
        STATUS mandatory
        DESCRIPTION "One table entry per slot in the media converter chassis.
             If physical slot 'n' contains a working C/E-100BTX-FRL-03 media 
             converter, then entry 'n' in this table exists and describes
             the state of the converter's LEDs  If slot 'n' is empty, does
             not exist, or contains a different type of device, then table
             entry 'n' does not exist."
        ::= { slotMc20p 30 }

ce100BtxFrl03Entry OBJECT-TYPE 
        SYNTAX Ce100BtxFrl03Entry
        ACCESS not-accessible
        STATUS mandatory
        DESCRIPTION "State of LEDs on a single C/E-100BTX-FRL-03"
        INDEX { ce100BtxFrl03Index }
        ::= { ce100BtxFrl03Table 1 }

Ce100BtxFrl03Entry ::= 
        SEQUENCE {
                ce100BtxFrl03Index             INTEGER,
                ce100BtxFrl03Lock              INTEGER,
                ce100BtxFrl03TPRecv            INTEGER,
                ce100BtxFrl03FiberRecv         INTEGER,
                ce100BtxFrl03TPSignalDetect    INTEGER,
                ce100BtxFrl03FiberSignalDetect INTEGER
                }

ce100BtxFrl03Index OBJECT-TYPE 
        SYNTAX INTEGER
        ACCESS read-only
        STATUS mandatory
        DESCRIPTION "The index of a slot in a media converter chassis"
        ::= { ce100BtxFrl03Entry 1 }

ce100BtxFrl03Lock OBJECT-TYPE 
        SYNTAX INTEGER { on(1),off(2) }
        ACCESS read-only
        STATUS mandatory
        DESCRIPTION "The state of the converter's signal lock pin"
        ::= { ce100BtxFrl03Entry 2 }

ce100BtxFrl03TPRecv OBJECT-TYPE 
        SYNTAX INTEGER { on(1),off(2) }
        ACCESS read-only
        STATUS mandatory
        DESCRIPTION "The state of the converter's Twisted pair receive LED"
        ::= { ce100BtxFrl03Entry 3 }

ce100BtxFrl03FiberRecv OBJECT-TYPE 
        SYNTAX INTEGER { on(1),off(2) }
        ACCESS read-only
        STATUS mandatory
        DESCRIPTION "The state of the converter's Fiber Receive LED"
        ::= { ce100BtxFrl03Entry 4 }

ce100BtxFrl03TPSignalDetect OBJECT-TYPE 
        SYNTAX INTEGER { on(1),off(2) }
        ACCESS read-only
        STATUS mandatory
        DESCRIPTION "The state of the converter's Twisted pair signal detect LED"
        ::= { ce100BtxFrl03Entry 5 }

ce100BtxFrl03FiberSignalDetect OBJECT-TYPE 
        SYNTAX INTEGER { on(1),off(2) }
        ACCESS read-only
        STATUS mandatory
        DESCRIPTION "The state of the converter's Fiber signal detect LED"
        ::= { ce100BtxFrl03Entry 6 }

-- ==================================================================
--  Table for C/HSTR-CF-01 media converters in a media 
--  converter chassis.
chstrCf01Table OBJECT-TYPE 
        SYNTAX SEQUENCE OF ChstrCf01Entry
        ACCESS not-accessible
        STATUS mandatory
        DESCRIPTION "One table entry per slot in the media converter chassis.
             If physical slot 'n' contains a working C/HSTR-CF-01
             media converter, then entry 'n' in this table exists and describes
             the state of the converter's LEDs  If slot 'n' is empty, does
             not exist, or contains a different type of device, then table
             entry 'n' does not exist."
        ::= { slotMc20p 34}

chstrCf01Entry OBJECT-TYPE 
        SYNTAX ChstrCf01Entry
        ACCESS not-accessible
        STATUS mandatory
        DESCRIPTION "State of LEDs on a single C/HSTR-CF-01"
        INDEX { chstrCf01Index }
        ::= { chstrCf01Table 1 }

ChstrCf01Entry ::= 
        SEQUENCE {
                chstrCf01Index INTEGER,
                chstrCf01TPRecv INTEGER,
                chstrCf01FiberRecv INTEGER,
                chstrCf01TPSignalDetect INTEGER,
                chstrCf01FiberSignalDetect INTEGER
                }

chstrCf01Index OBJECT-TYPE 
        SYNTAX INTEGER
        ACCESS read-only
        STATUS mandatory
        DESCRIPTION "The index of a slot in a media converter chassis"
        ::= { chstrCf01Entry 1 }

chstrCf01TPRecv OBJECT-TYPE 
        SYNTAX INTEGER { on(1),off(2) }
        ACCESS read-only
        STATUS mandatory
        DESCRIPTION "The state of the converter's Twisted Pair Receive LED"
        ::= { chstrCf01Entry 2 }

chstrCf01FiberRecv OBJECT-TYPE 
        SYNTAX INTEGER { on(1),off(2) }
        ACCESS read-only
        STATUS mandatory
        DESCRIPTION "The state of the converter's Fiber Receive LED"
        ::= { chstrCf01Entry 3 }

chstrCf01TPSignalDetect OBJECT-TYPE 
        SYNTAX INTEGER { on(1),off(2) }
        ACCESS read-only
        STATUS mandatory
        DESCRIPTION "The state of the converter's Twisted Pair signal detect LED"
        ::= { chstrCf01Entry 4 }

chstrCf01FiberSignalDetect OBJECT-TYPE 
        SYNTAX INTEGER { on(1),off(2) }
        ACCESS read-only
        STATUS mandatory
        DESCRIPTION "The state of the converter's fiber signal detect LED"
        ::= { chstrCf01Entry 5 }


-- ==================================================================
--  Table for C/E-TX-SX-02 media converters in a media converter chassis.
ceTxSx02Table OBJECT-TYPE 
        SYNTAX SEQUENCE OF CeTxSx02Entry
        ACCESS not-accessible
        STATUS mandatory
        DESCRIPTION "One table entry per slot in the media converter chassis.
             If physical slot 'n' contains a working C/E-TX-SX-02 media 
             converter, then entry 'n' in this table exists and describes
             the state of the converter's LEDs  If slot 'n' is empty, does
             not exist, or contains a different type of device, then table
             entry 'n' does not exist."
        ::= { slotMc20p 35 }

ceTxSx02Entry OBJECT-TYPE 
        SYNTAX CeTxSx02Entry
        ACCESS not-accessible
        STATUS mandatory
        DESCRIPTION "State of LEDs on a single C/E-TX-SX-02"
        INDEX { ceTxSx02Index }
        ::= { ceTxSx02Table 1 }

CeTxSx02Entry ::= 
        SEQUENCE {
                ceTxSx02Index      INTEGER,
                ceTxSx02TPLink     INTEGER,
                ceTxSx02FiberLink  INTEGER,
                ceTxSx02100Mbps    INTEGER
                }

ceTxSx02Index OBJECT-TYPE 
        SYNTAX INTEGER
        ACCESS read-only
        STATUS mandatory
        DESCRIPTION "The index of a slot in a media converter chassis"
        ::= { ceTxSx02Entry 1 }

ceTxSx02TPLink OBJECT-TYPE 
        SYNTAX INTEGER { on(1),off(2) }
        ACCESS read-only
        STATUS mandatory
        DESCRIPTION "The state of the converter's Twisted Pair Link LED"
        ::= { ceTxSx02Entry 2 }

ceTxSx02FiberLink OBJECT-TYPE 
        SYNTAX INTEGER { on(1),off(2) }
        ACCESS read-only
        STATUS mandatory
        DESCRIPTION "The state of the converter's Fiber Link LED"
        ::= { ceTxSx02Entry 3 }

ceTxSx02100Mbps OBJECT-TYPE 
        SYNTAX INTEGER { on(1),off(2) }
        ACCESS read-only
        STATUS mandatory
        DESCRIPTION "The state of the converter's 100 Megabit Per Second LED"
        ::= { ceTxSx02Entry 4 }

-- ==================================================================
--  Table for C/E-TBT-FRL-04 media converters in a media converter chassis.
ceTbtFrl04Table OBJECT-TYPE 
        SYNTAX SEQUENCE OF CeTbtFrl04Entry
        ACCESS not-accessible
        STATUS mandatory
        DESCRIPTION "One table entry per slot in the media converter chassis.
             If physical slot 'n' contains a working C/E-TBT-FRL-04 media 
             converter, then entry 'n' in this table exists and describes
             the state of the converter's LEDs  If slot 'n' is empty, does
             not exist, or contains a different type of device, then table
             entry 'n' does not exist."
        ::= { slotMc20p 36 }

ceTbtFrl04Entry OBJECT-TYPE 
        SYNTAX CeTbtFrl04Entry
        ACCESS not-accessible
        STATUS mandatory
        DESCRIPTION "State of LEDs on a single C/E-TBT-FRL-04"
        INDEX { ceTbtFrl04Index }
        ::= { ceTbtFrl04Table 1 }

CeTbtFrl04Entry ::= 
        SEQUENCE {
                ceTbtFrl04Index     INTEGER,
                ceTbtFrl04FiberRecv INTEGER,
                ceTbtFrl04FiberLink INTEGER,
                ceTbtFrl04TPRecv    INTEGER,
                ceTbtFrl04TPLink    INTEGER
                }

ceTbtFrl04Index OBJECT-TYPE 
        SYNTAX INTEGER
        ACCESS read-only
        STATUS mandatory
        DESCRIPTION "The index of a slot in a media converter chassis"
        ::= { ceTbtFrl04Entry 1 }

ceTbtFrl04FiberRecv OBJECT-TYPE 
        SYNTAX INTEGER { on(1),off(2) }
        ACCESS read-only
        STATUS mandatory
        DESCRIPTION "The state of the converter's Fiber Receive LED"
        ::= { ceTbtFrl04Entry 2 }

ceTbtFrl04FiberLink OBJECT-TYPE 
        SYNTAX INTEGER { on(1),off(2) }
        ACCESS read-only
        STATUS mandatory
        DESCRIPTION "The state of the converter's Fiber Link LED"
        ::= { ceTbtFrl04Entry 3 }

ceTbtFrl04TPRecv OBJECT-TYPE 
        SYNTAX INTEGER { on(1),off(2) }
        ACCESS read-only
        STATUS mandatory
        DESCRIPTION "The state of the converter's Twisted Pair Receive LED"
        ::= { ceTbtFrl04Entry 4 }

ceTbtFrl04TPLink OBJECT-TYPE 
        SYNTAX INTEGER { on(1),off(2) }
        ACCESS read-only
        STATUS mandatory
        DESCRIPTION "The state of the converter's Twisted Pair Link LED"
        ::= { ceTbtFrl04Entry 5 }


-- ==================================================================
-- ==================================================================
-- ==================================================================
-- ==================================================================
-- End MCC16 Conversion Center entries

-- Begin Point System entries
-- ==================================================================
-- ==================================================================
-- ==================================================================
-- ==================================================================

-- Note: All tables indexed by BiaIndex 'c' and SlotIndex 's' are
--       sparse tables, i.e. if there is no cabinet in the stack 
--       with serial number 'c' and/or there is no device installed in
--       slot 's', then the entry indexed 'c.s' in the table does not 
--       exist. 
--       All tables indexed by BiaIndex 'c' are sparse tables, i.e.
--       if there is no cabinet in the stack with serial number 'c',
--       then the entry indexed 'c' in the table does not exist.

-- ==================================================================

cpsModuleTable OBJECT-TYPE
        SYNTAX SEQUENCE OF CpsModuleEntry
        ACCESS not-accessible
        STATUS mandatory
        DESCRIPTION "A table from which one can extract the model number
                     of any device in the stack, given the serial number
                     (BIA) of the cabinet and the slot number in which 
                     the device is installed." 
        ::= { cpsSlotSummary 1 }

cpsModuleEntry OBJECT-TYPE
        SYNTAX CpsModuleEntry
        ACCESS not-accessible
        STATUS mandatory
        DESCRIPTION "The model number entry for a single device."
        INDEX { cpsModuleBiaIndex, cpsModuleSlotIndex }
        ::= { cpsModuleTable 1 }

CpsModuleEntry ::=
        SEQUENCE {
                 cpsModuleBiaIndex    INTEGER,
                 cpsModuleSlotIndex   INTEGER,
                 cpsModuleModel       OBJECT IDENTIFIER
                 }

cpsModuleBiaIndex OBJECT-TYPE
        SYNTAX INTEGER
        ACCESS read-only
        STATUS mandatory
        DESCRIPTION "The serial number (BIA) of the cabinet in which the
                     device is installed"
        ::= { cpsModuleEntry 1 }

cpsModuleSlotIndex OBJECT-TYPE
        SYNTAX INTEGER
        ACCESS read-only
        STATUS mandatory
        DESCRIPTION "The slot in which the device is installed"
        ::= { cpsModuleEntry 2 }

cpsModuleModel OBJECT-TYPE
        SYNTAX OBJECT IDENTIFIER
        ACCESS read-only
        STATUS mandatory
        DESCRIPTION "The model number of the device. 
                     See OIDs under chSlcps"
        ::= { cpsModuleEntry 3 }

-- ======================================================================
-- Table for cpsmm100 base management module
--
-- NOTE: This device is referred to in marketing literature as CPSMM200
--

cpsmm100Table OBJECT-TYPE
        SYNTAX SEQUENCE OF Cpsmm100Entry
        ACCESS not-accessible
        STATUS mandatory
        DESCRIPTION "Sparse table containing one entry for each CPSMM100-200 
                     and other CPSMM100-xxx Point System Base Management Module
                     in the stack, indexed by cabinet serial number and slot."
        ::= { cpsSlotDetail 1 }

cpsmm100Entry OBJECT-TYPE
        SYNTAX Cpsmm100Entry
        ACCESS not-accessible
        STATUS mandatory
        DESCRIPTION "Status and configuration entries for a single CPSMM100"
        INDEX { cpsmm100BiaIndex, cpsmm100SlotIndex }
        ::= { cpsmm100Table 1 }

Cpsmm100Entry ::=
        SEQUENCE {
                 cpsmm100BiaIndex            INTEGER,
                 cpsmm100SlotIndex           INTEGER,
                 cpsmm100Groups              DisplayString,
                 cpsmm100Reset               INTEGER,
                 cpsmm100SaveConfig          INTEGER,
                 cpsmm100HwRevision          DisplayString,
                 cpsmm100SwRevision          DisplayString,
                 cpsmm100IPAddress           IpAddress,
                 cpsmm100SubnetMask          IpAddress,
                 cpsmm100Gateway             IpAddress,
                 cpsmm100IsPrimary           INTEGER,
                 cpsmm100WantPrimary         INTEGER,
                 cpsmm100CanPrimary          INTEGER,
                 cpsmm100EthernetLink        INTEGER,
                 cpsmm100TntRIP              IpAddress,
                 cpsmm100TntRIPMask          IpAddress,
                 cpsmm100SNMPTrapMgr         IpAddress,
                 cpsmm100SNMPTrapInterval    INTEGER,
                 cpsmm100SysUpTime           TimeTicks,
                 cpsmm100SysContact          DisplayString,
                 cpsmm100SysName             DisplayString,
                 cpsmm100SysLocation         DisplayString,
                 cpsmm100CfgMatch            INTEGER,
                 cpsmm100SerialNumber        INTEGER,
                 cpsmm100ICIF                INTEGER,
                 cpsmm100MRevision           INTEGER,
                 cpsmm100LastGasp            INTEGER,
                 cpsmm100SNMPTrapMgr2        IpAddress,
                 cpsmm100SNMPTrapMgr3        IpAddress, 
                 cpsmm100SNMPTrapMgr4        IpAddress,
                 cpsmm100CacheClean          INTEGER 
                 }

cpsmm100BiaIndex OBJECT-TYPE
        SYNTAX INTEGER
        ACCESS read-only
        STATUS mandatory
        DESCRIPTION "The serial number (BIA) of the cabinet in which the 
                     device is installed"
        ::= { cpsmm100Entry 1 }

cpsmm100SlotIndex OBJECT-TYPE
        SYNTAX INTEGER
        ACCESS read-only
        STATUS mandatory
        DESCRIPTION "The slot in which the device is installed"
        ::= { cpsmm100Entry 2 }

cpsmm100Groups OBJECT-TYPE
        SYNTAX DisplayString
        ACCESS read-write
        STATUS mandatory
        DESCRIPTION "User-defined keywords that group this device together with
                     other devices under a user-defined scheme. By placing 
                     matching keywords in cpsGroupCtrl.0, the agent can be
                     instructed to apply configuration changes simultaneously
                     to all group members rather than to individual devices.
                     Every Groups string has three automatically defined
                     implied values: 
                     1) The model family of the device, e.g. 'CPSMM100'
                     2) The serial number of the cabinet in which the device
                        is installed, in decimal with no leading zeroes, 
                        e.g. '12345', and 
                     3) same as 2, with the slot in which the device is 
                        installed appended, enclosed in square brackets. 
                        e.g. '12345[9]'"
        ::= { cpsmm100Entry 3 }

cpsmm100Reset OBJECT-TYPE
        SYNTAX INTEGER { reset(1), noReset(2) }
        ACCESS read-write
        STATUS mandatory
        DESCRIPTION "Set this to reset(1) to cause the CPSMM100 to reboot."
        ::= { cpsmm100Entry 4 }

cpsmm100SaveConfig OBJECT-TYPE
        SYNTAX INTEGER { saveConfig(1), noSaveConfig(2) }
        ACCESS read-write
        STATUS mandatory
        DESCRIPTION "Set this to saveConfig(1) to force configuration changes
                     made since the last saveConfig to be copied from RAM to
                     flash memory. If changes are made to the configuration of
                     a CPSMM100 and SaveConfig is not subsequently set to 1, 
                     the changes will be made only in RAM and the device will
                     revert to its previous configuration at the next reboot.
                     After the save completes, SaveConfig automatically reverts
                     to noSaveConfig(2)."
        ::= { cpsmm100Entry 5 }

cpsmm100HwRevision OBJECT-TYPE
        SYNTAX DisplayString
        ACCESS read-only
        STATUS mandatory
        DESCRIPTION "The hardware revision of this device"
        ::= { cpsmm100Entry 6 }

cpsmm100SwRevision OBJECT-TYPE
        SYNTAX DisplayString
        ACCESS read-only
        STATUS mandatory
        DESCRIPTION "The revision of the agent firmware for this device."
        ::= { cpsmm100Entry 7 }

cpsmm100IPAddress OBJECT-TYPE
        SYNTAX IpAddress
        ACCESS read-write
        STATUS mandatory
        DESCRIPTION "The IP Address of the Ethernet interface of this device"
        ::= { cpsmm100Entry 8 }

cpsmm100SubnetMask OBJECT-TYPE
        SYNTAX IpAddress
        ACCESS read-write
        STATUS mandatory
        DESCRIPTION "The subnet mask used by the Ethernet interface of 
                     this device"
        ::= { cpsmm100Entry 9 }

cpsmm100Gateway OBJECT-TYPE
        SYNTAX IpAddress
        ACCESS read-write
        STATUS mandatory
        DESCRIPTION "The IP gateway used by the Ethernet interface of 
                     this device"
        ::= { cpsmm100Entry 10 }

cpsmm100IsPrimary OBJECT-TYPE
        SYNTAX INTEGER { yes(1), no(2) }
        ACCESS read-only
        STATUS mandatory
        DESCRIPTION "In a given Point System stack, multiple base management
                     modules can be installed, but only one can be the Primary.
                     The Primary is responsible for scanning the stack for
                     modules, collecting status information and distributing
                     new configuration settings. The Primary management module
                     is therefore the only one that can accept an SNMP SET PDU.
                     Compare this variable with cpsIsPrimary.0"
        ::= { cpsmm100Entry 11 }

cpsmm100WantPrimary OBJECT-TYPE
        SYNTAX INTEGER { yes(1), no(2), always(3) }
        ACCESS read-write
        STATUS mandatory
        DESCRIPTION "Normally, the Management Module installed in the cabinet
                     with the lowest serial number (BIA) in the lowest 
                     (leftmost) slot that has fully established network 
                     connectivity will be selected as the Primary. Setting
                     WantPrimary to yes(1) causes this device to be preferred
                     over all devices with a WantPrimary value of no(2) during
                     these Primary/Standby negotiations. If more than one 
                     device is configured with the value yes(1), these modules
                     negotiate amongst themselves using the default rule above.
                     Setting WantPrimary to always(3) causes the module to
                     ignore the results of the negotiations and immediately
                     and persistently assert primary status. Use of always(3)
                     is not recommended except on advice of Transition Networks
                     technical support, since it may cause your system
                     to behave unpredictably. Setting more than one module in
                     a stack to always(3) will cause erratic behavior."
        ::= { cpsmm100Entry 12 }

cpsmm100CanPrimary OBJECT-TYPE
        SYNTAX INTEGER { yes(1), no(2) }
        ACCESS read-only
        STATUS mandatory
        DESCRIPTION "Value is yes(1) if this device is eligible to become the
                     Primary Management Module. Currently, lack of IP/Ethernet
                     connectivity is the only reason that a module can be
                     ineligible."
        ::= { cpsmm100Entry 13 }

cpsmm100EthernetLink OBJECT-TYPE
        SYNTAX INTEGER { on(1), off(2) }
        ACCESS read-only
        STATUS mandatory
        DESCRIPTION "Does the management interface of this management module
                     have ethernet link?"
        ::= { cpsmm100Entry 14 }

cpsmm100TntRIP OBJECT-TYPE
        SYNTAX IpAddress
        ACCESS read-only
        STATUS mandatory
        DESCRIPTION "This feature in obsolete as of 08/17/2001.
                     
                     Telnet 'trusted' IP address. Telnet access to the CPSMM100
                     can be limited to a single station by placing its IP 
                     address in TntRIP. Any incoming Telnet request from a
                     station whose IP address does not match TntRIP is ignored.
                     The TntRIP can be modified to accept an entire
                     subnet or other group of IP stations by using TntRIPMask,
                     defined below."
        ::= { cpsmm100Entry 15 }

cpsmm100TntRIPMask OBJECT-TYPE
        SYNTAX IpAddress
        ACCESS read-only
        STATUS mandatory
        DESCRIPTION "This feature in obsolete as of 08/17/2001.
                     
                     Telnet 'trusted' address mask. See cpsmm100TntRIP.
                     This value can be used to exclude bit positions from 
                     consideration when applying TntRIP (above) to a Telnet
                     connection request. 
                     For each bit position in TntRIPMask that is a 1, the
                     corresponding bits in the TntRIP and the IP address of the
                     connecting client must be the same. If this is not true,
                     the connection attempt is ignored.
                     Note that the TntRIPMask differs from a true subnet
                     mask (which must have all '1' bits at the left and all '0'
                     bits at the right) in that it may use any bit pattern." 
        ::= { cpsmm100Entry 16 }

cpsmm100SNMPTrapMgr OBJECT-TYPE
        SYNTAX IpAddress
        ACCESS read-write
        STATUS mandatory
        DESCRIPTION "Traps generated by this management module will be sent
                     to this IP address."
        ::= { cpsmm100Entry 17 }

cpsmm100SNMPTrapInterval OBJECT-TYPE
        SYNTAX INTEGER
        ACCESS read-write
        STATUS mandatory
        DESCRIPTION "For future expansion, not currently implemented."
        ::= { cpsmm100Entry 18 }

cpsmm100SysUpTime OBJECT-TYPE
        SYNTAX TimeTicks
        ACCESS read-only
        STATUS mandatory
        DESCRIPTION "Mirror of this Management Module's system.sysUpTime.0"
        ::= { cpsmm100Entry 19 }

cpsmm100SysContact OBJECT-TYPE
        SYNTAX DisplayString
        ACCESS read-write
        STATUS mandatory
        DESCRIPTION "Mirror of this Management Module's system.sysContact.0"
        ::= { cpsmm100Entry 20 }

cpsmm100SysName OBJECT-TYPE
        SYNTAX DisplayString
        ACCESS read-write
        STATUS mandatory
        DESCRIPTION "Mirror of this Management Module's system.sysName.0"
        ::= { cpsmm100Entry 21 }

cpsmm100SysLocation OBJECT-TYPE
        SYNTAX DisplayString
        ACCESS read-write
        STATUS mandatory
        DESCRIPTION "Mirror of this Management Module's system.sysLocation.0"
        ::= { cpsmm100Entry 22 }

cpsmm100CfgMatch OBJECT-TYPE
        SYNTAX INTEGER { yes(1), no(2), notApplicable(3) }
        ACCESS read-write
        STATUS mandatory
        DESCRIPTION "yes(1) indicates that the conditions specified in 
                     cpsGroupCtrl.0 match the Groups value for this
                     device. no(2) means that there is no match.
                     notApplicable(3) indicates that cpsGroupCtrl.0 is null
                     and therefore no comparison was performed."
        ::= { cpsmm100Entry 23 }

cpsmm100SerialNumber OBJECT-TYPE
        SYNTAX INTEGER
        ACCESS read-only
        STATUS mandatory
        DESCRIPTION "The serial number of this device."
        ::= { cpsmm100Entry 24 }

cpsmm100ICIF OBJECT-TYPE
        SYNTAX INTEGER { yes(1), no(2) }
        ACCESS read-only
        STATUS mandatory
        DESCRIPTION "Multiple Management Modules can be installed in a Point
                     System stack. For each cabinet in the stack, exactly one
                     module must be selected to communicate configuration 
                     changes to the cabinet hardware and provide a 
                     communications pathway to other cabinets. This module
                     is known as the Inter-Cabinet Communications Interface.
                     If there are any Base Management Modules in the cabinet,
                     the one in the lowest slot will be the ICIF. Otherwise,
                     it will be the Expansion Management Module in the lowest
                     slot."
        ::= { cpsmm100Entry 25 }

cpsmm100MRevision OBJECT-TYPE 
        SYNTAX INTEGER
        ACCESS read-only
        STATUS mandatory
        DESCRIPTION "The marketing revision of this device"
        ::= { cpsmm100Entry 26 }

cpsmm100LastGasp OBJECT-TYPE
        SYNTAX INTEGER { yes(1), no(2) }
        ACCESS read-only
        STATUS mandatory
        DESCRIPTION "Last Gasp support for this device."
        ::= { cpsmm100Entry 27 }

cpsmm100SNMPTrapMgr2 OBJECT-TYPE
        SYNTAX IpAddress
        ACCESS read-write
        STATUS mandatory
        DESCRIPTION "Traps generated by this management module will be sent
                     to this IP address."
        ::= { cpsmm100Entry 28 }

cpsmm100SNMPTrapMgr3 OBJECT-TYPE
        SYNTAX IpAddress
        ACCESS read-write
        STATUS mandatory
        DESCRIPTION "Traps generated by this management module will be sent
                     to this IP address."
        ::= { cpsmm100Entry 29 }

cpsmm100SNMPTrapMgr4 OBJECT-TYPE
        SYNTAX IpAddress
        ACCESS read-write
        STATUS mandatory
        DESCRIPTION "Traps generated by this management module will be sent
                     to this IP address."
        ::= { cpsmm100Entry 30 }

cpsmm100CacheClean OBJECT-TYPE
        SYNTAX INTEGER { clean(1), dirty(2) }
        ACCESS read-only
        STATUS mandatory
        DESCRIPTION "When the value is clean(1)Device and Management Module
                     cache are synchronized, no automatic corrections to 
                     configuration will occur.  When the value is dirty(2)
                     Device and Management Module cache are not synchronized.
                     The configuration currently displayed by the application 
                     has not been validated by the device. The device may 
                     need to correct the configuration, in which case the 
                     displayed configuration will change."
        ::= { cpsmm100Entry 31 }

-- ==================================================================
-- Table for cpsmm200 expansion management module
--
-- NOTE: This device is referred to in marketing literature as CPSMM210
--

cpsmm200Table OBJECT-TYPE
        SYNTAX SEQUENCE OF Cpsmm200Entry
        ACCESS not-accessible
        STATUS mandatory
        DESCRIPTION "Sparse table containing one entry for each CPSMM200-210
                     and other CPSMM200-xxx Point System Expansion Management Module
                     in the stack, indexed by cabinet serial number and slot."
        ::= { cpsSlotDetail 2 }

cpsmm200Entry OBJECT-TYPE
        SYNTAX Cpsmm200Entry
        ACCESS not-accessible
        STATUS mandatory
        DESCRIPTION "Status entries for a single cpsmm200. (The CPSMM200
                     has no configuration)"
        INDEX { cpsmm200BiaIndex, cpsmm200SlotIndex }
        ::= { cpsmm200Table 1 }

Cpsmm200Entry ::=
        SEQUENCE {
                 cpsmm200BiaIndex            INTEGER,
                 cpsmm200SlotIndex           INTEGER,
                 cpsmm200SerialNumber        INTEGER,
                 cpsmm200ICIF                INTEGER,
                 cpsmm200MRevision           INTEGER
                 }

cpsmm200BiaIndex OBJECT-TYPE
        SYNTAX INTEGER
        ACCESS read-only
        STATUS mandatory
        DESCRIPTION "The serial number (BIA) of the cabinet in which the 
                     device is installed"
        ::= { cpsmm200Entry 1 }

cpsmm200SlotIndex OBJECT-TYPE
        SYNTAX INTEGER
        ACCESS read-only
        STATUS mandatory
        DESCRIPTION "The slot in which the device is installed"
        ::= { cpsmm200Entry 2 }

cpsmm200SerialNumber OBJECT-TYPE
        SYNTAX INTEGER
        ACCESS read-only
        STATUS mandatory
        DESCRIPTION "The serial number of this device"
        ::= { cpsmm200Entry 3 }

cpsmm200ICIF OBJECT-TYPE
        SYNTAX INTEGER { yes(1), no(2) }
        ACCESS read-only
        STATUS mandatory
        DESCRIPTION "Multiple Management Modules can be installed in a Point
                     System stack. For each cabinet in the stack, exactly one
                     module must be selected to communicate configuration 
                     changes to the cabinet hardware and provide a 
                     communications pathway to other cabinets. This module
                     is known as the Inter-Cabinet Communications Interface.
                     If there are any Base Management Modules in the cabinet,
                     the one in the lowest slot will be the ICIF. Otherwise,
                     it will be the Expansion Management Module in the lowest
                     slot."
        ::= { cpsmm200Entry 4 }

cpsmm200MRevision OBJECT-TYPE 
        SYNTAX INTEGER
        ACCESS read-only
        STATUS mandatory
        DESCRIPTION "The marketing revision of this device"
        ::= { cpsmm200Entry 5 }

-- ===================================================================
-- Table for a CETTF100 media converter

cettf100Table OBJECT-TYPE
        SYNTAX SEQUENCE OF Cettf100Entry
        ACCESS not-accessible
        STATUS mandatory
        DESCRIPTION "Sparse table containing one entry for each CETTF100
                     10Mbps Twisted-Pair to Fiber Ethernet Media Converter
                     in the stack, indexed by cabinet serial number and slot."
        ::= { cpsSlotDetail 3 }

cettf100Entry OBJECT-TYPE
        SYNTAX Cettf100Entry
        ACCESS not-accessible
        STATUS mandatory
        DESCRIPTION "Status and configuration entries for a single CETTF100"
        INDEX { cettf100BiaIndex, cettf100SlotIndex }
        ::= { cettf100Table 1 }

Cettf100Entry ::=
        SEQUENCE {
                 cettf100BiaIndex            INTEGER,
                 cettf100SlotIndex           INTEGER,
                 cettf100Groups              DisplayString,
                 cettf100MRevision           INTEGER,
                 cettf100CfgMatch            INTEGER,
                 cettf100SerialNumber        INTEGER,
                 cettf100ConnA               INTEGER,
                 cettf100ConnB               INTEGER,
                 cettf100TPLink              INTEGER,
                 cettf100FiberLink           INTEGER,
                 cettf100Fault               INTEGER,
                 cettf100TPActivity          INTEGER,
                 cettf100FiberActivity       INTEGER,
                 cettf100AutoCross           INTEGER,
                 cettf100LinkPassThrough     INTEGER,
                 cettf100ConfigMode          INTEGER,
                 cettf100Enabled             INTEGER,
                 cettf100CacheClean          INTEGER
                 }

cettf100BiaIndex OBJECT-TYPE
        SYNTAX INTEGER
        ACCESS read-only
        STATUS mandatory
        DESCRIPTION "The serial number (BIA) of the cabinet in which the 
                     device is installed"
        ::= { cettf100Entry 1 }

cettf100SlotIndex OBJECT-TYPE
        SYNTAX INTEGER
        ACCESS read-only
        STATUS mandatory
        DESCRIPTION "The slot in which the device is installed"
        ::= { cettf100Entry 2 }

cettf100Groups OBJECT-TYPE
        SYNTAX DisplayString
        ACCESS read-write
        STATUS mandatory
        DESCRIPTION "User-defined keywords that group this device together with
                     other devices under a user-defined scheme. By placing 
                     matching keywords in cpsGroupCtrl.0, the agent can be
                     instructed to apply configuration changes simultaneously
                     to all group members rather than to individual devices.
                     Every Groups string has three automatically defined
                     implied values: 
                     1) The model family of the device, e.g. 'CETTF100'
                     2) The serial number of the cabinet in which the device
                        is installed, in decimal with no leading zeroes, 
                        e.g. '12345', and 
                     3) same as 2, with the slot in which the device is 
                        installed appended, enclosed in square brackets. 
                        e.g. '12345[9]'"
        ::= { cettf100Entry 3 }

cettf100MRevision OBJECT-TYPE
        SYNTAX INTEGER
        ACCESS read-only
        STATUS mandatory
        DESCRIPTION "The marketing revision of this device"
        ::= { cettf100Entry 4 }

cettf100CfgMatch OBJECT-TYPE
        SYNTAX INTEGER { yes(1), no(2), notApplicable(3) }
        ACCESS read-only
        STATUS mandatory
        DESCRIPTION "yes(1) indicates that the conditions specified in 
                     cpsGroupCtrl.0 match the Groups value for this
                     device. no(2) means that there is no match.
                     notApplicable(3) indicates that cpsGroupCtrl.0 is null
                     and therefore no comparison was performed."
        ::= { cettf100Entry 5 }

cettf100SerialNumber OBJECT-TYPE
        SYNTAX INTEGER 
        ACCESS read-only
        STATUS mandatory
        DESCRIPTION "The serial number of this device"
        ::= { cettf100Entry 6 }

cettf100ConnA OBJECT-TYPE
        SYNTAX CpsConnector
        ACCESS read-only
        STATUS mandatory
        DESCRIPTION "The style of Fiber connector built into this device"
        ::= { cettf100Entry 7 }

cettf100ConnB OBJECT-TYPE
        SYNTAX CpsConnector
        ACCESS read-only
        STATUS mandatory
        DESCRIPTION "The style of Copper connector built into this device"
        ::= { cettf100Entry 8 }

cettf100TPLink OBJECT-TYPE
        SYNTAX INTEGER { linkUp(1), linkDown(2) }
        ACCESS read-only
        STATUS mandatory
        DESCRIPTION "Status of Copper Link for this device"
        ::= { cettf100Entry 9 }

cettf100FiberLink OBJECT-TYPE
        SYNTAX INTEGER { linkUp(1), linkDown(2) }
        ACCESS read-only
        STATUS mandatory
        DESCRIPTION "Status of Fiber Link for this device"
        ::= { cettf100Entry 10 }

cettf100Fault OBJECT-TYPE
        SYNTAX INTEGER { yes(1), no(2) }
        ACCESS read-only
        STATUS mandatory
        DESCRIPTION "Value is yes(1) when either TPLink or FiberLink 
                     has value linkDown(2)"
        ::= { cettf100Entry 11 }

cettf100TPActivity OBJECT-TYPE
        SYNTAX INTEGER { yes(1), no(2) }
        ACCESS read-only
        STATUS mandatory
        DESCRIPTION "Network traffic indicator for Copper side of this device"
        ::= { cettf100Entry 12 }

cettf100FiberActivity OBJECT-TYPE
        SYNTAX INTEGER { yes(1), no(2) }
        ACCESS read-only
        STATUS mandatory
        DESCRIPTION "Network traffic indicator for Fiber side of this device"
        ::= { cettf100Entry 13 }

cettf100AutoCross OBJECT-TYPE
        SYNTAX INTEGER { on(1), off(2) }
        ACCESS read-write
        STATUS mandatory
        DESCRIPTION "Enable/Disable for automatic copper TX/RX pair correction"
        ::= { cettf100Entry 14 }

cettf100LinkPassThrough OBJECT-TYPE
        SYNTAX INTEGER { on(1), off(2) }
        ACCESS read-write
        STATUS mandatory
        DESCRIPTION "Enable/Disable for Link Pass Through, a feature that
                     causes loss of link on one side of a media converter
                     to be passed through to the other side, so that 
                     upstream equipment can see the fault condition."
        ::= { cettf100Entry 15 }

cettf100ConfigMode OBJECT-TYPE
        SYNTAX INTEGER { software(1), hardware(2) }
        ACCESS read-only
        STATUS mandatory
        DESCRIPTION "This device has a jumper or switch that disables 
                     software management of the device. When ConfigMode is
                     hardware(2), SNMP management is disabled, and all
                     configuration control comes from physical switches or
                     jumpers on the device."
        ::= { cettf100Entry 16 }

cettf100Enabled OBJECT-TYPE
        SYNTAX INTEGER { yes(1), no(2) }
        ACCESS read-write
        STATUS mandatory
        DESCRIPTION "When this configuration item is set to no(2), the
                     device passes no network traffic."
        ::= { cettf100Entry 17 }

cettf100CacheClean OBJECT-TYPE
        SYNTAX INTEGER { clean(1), dirty(2) }
        ACCESS read-only
        STATUS mandatory
        DESCRIPTION "When the value is clean(1)Device and Management Module
                     cache are synchronized, no automatic corrections to 
                     configuration will occur.  When the value is dirty(2)
                     Device and Management Module cache are not synchronized.
                     The configuration currently displayed by the application 
                     has not been validated by the device. The device may 
                     need to correct the configuration, in which case the 
                     displayed configuration will change."
        ::= { cettf100Entry 18 }

-- ==================================================================
-- Table for a cfetf100 slide in card.

cfetf100Table OBJECT-TYPE
        SYNTAX SEQUENCE OF Cfetf100Entry
        ACCESS not-accessible
        STATUS mandatory
        DESCRIPTION "Sparse table containing one entry for each CFTEF100
                     100Mbps Twisted-Pair to Fiber Ethernet Media Converter
                     in the stack, indexed by cabinet serial number and slot."
        ::= { cpsSlotDetail 4 }

cfetf100Entry OBJECT-TYPE
        SYNTAX Cfetf100Entry
        ACCESS not-accessible
        STATUS mandatory
        DESCRIPTION "Status and configuration entries for a single CFETF100"
        INDEX { cfetf100BiaIndex, cfetf100SlotIndex }
        ::= { cfetf100Table 1 }

Cfetf100Entry ::=
        SEQUENCE {
                 cfetf100BiaIndex            INTEGER,
                 cfetf100SlotIndex           INTEGER,
                 cfetf100Groups              DisplayString,
                 cfetf100MRevision           INTEGER,
                 cfetf100CfgMatch            INTEGER,
                 cfetf100SerialNumber        INTEGER,
                 cfetf100ConnA               INTEGER,
                 cfetf100ConnB               INTEGER,
                 cfetf100TPLink              INTEGER,
                 cfetf100FiberLink           INTEGER,
                 cfetf100Fault               INTEGER,
                 cfetf100FastLinkPulse       INTEGER,
                 cfetf100Enabled             INTEGER,
                 cfetf100Pause               INTEGER,
                 cfetf100LinkPassThrough     INTEGER,
                 cfetf100AutoCross           INTEGER,
                 cfetf100TPActivity          INTEGER,
                 cfetf100FiberActivity       INTEGER,
                 cfetf100ConfigMode          INTEGER,
                 cfetf100FarEndFault         INTEGER,
                 cfetf100CacheClean          INTEGER
                 }

cfetf100BiaIndex OBJECT-TYPE
        SYNTAX INTEGER
        ACCESS read-only
        STATUS mandatory
        DESCRIPTION "The serial number (BIA) of the cabinet in which the 
                     device is installed"
        ::= { cfetf100Entry 1 }

cfetf100SlotIndex OBJECT-TYPE
        SYNTAX INTEGER
        ACCESS read-only
        STATUS mandatory
        DESCRIPTION "The slot in which the device is installed"
        ::= { cfetf100Entry 2 }

cfetf100Groups OBJECT-TYPE
        SYNTAX DisplayString
        ACCESS read-write
        STATUS mandatory
        DESCRIPTION "User-defined keywords that group this device together with
                     other devices under a user-defined scheme. By placing 
                     matching keywords in cpsGroupCtrl.0, the agent can be
                     instructed to apply configuration changes simultaneously
                     to all group members rather than to individual devices.
                     Every Groups string has three automatically defined
                     implied values: 
                     1) The model family of the device, e.g. 'CFETF100'
                     2) The serial number of the cabinet in which the device
                        is installed, in decimal with no leading zeroes, 
                        e.g. '12345', and 
                     3) same as 2, with the slot in which the device is 
                        installed appended, enclosed in square brackets. 
                        e.g. '12345[9]'"
        ::= { cfetf100Entry 3 }

cfetf100MRevision OBJECT-TYPE
        SYNTAX INTEGER
        ACCESS read-only
        STATUS mandatory
        DESCRIPTION "The marketing revision of this device"
        ::= { cfetf100Entry 4 }

cfetf100CfgMatch OBJECT-TYPE
        SYNTAX INTEGER { yes(1), no(2), notApplicable(3) }
        ACCESS read-only
        STATUS mandatory
        DESCRIPTION "yes(1) indicates that the conditions specified in 
                     cpsGroupCtrl.0 match the Groups value for this
                     device. no(2) means that there is no match.
                     notApplicable(3) indicates that cpsGroupCtrl.0 is null
                     and therefore no comparison was performed."
        ::= { cfetf100Entry 5 }

cfetf100SerialNumber OBJECT-TYPE
        SYNTAX INTEGER 
        ACCESS read-only
        STATUS mandatory
        DESCRIPTION "The serial number of this device"
        ::= { cfetf100Entry 6 }

cfetf100ConnA OBJECT-TYPE
        SYNTAX CpsConnector
        ACCESS read-only
        STATUS mandatory
        DESCRIPTION "The style of Fiber connector built into this device"
        ::= { cfetf100Entry 7 }

cfetf100ConnB OBJECT-TYPE
        SYNTAX CpsConnector
        ACCESS read-only
        STATUS mandatory
        DESCRIPTION "The style of Copper connector built into this device"
        ::= { cfetf100Entry 8 }

cfetf100TPLink OBJECT-TYPE
        SYNTAX INTEGER { linkUp(1), linkDown(2) }
        ACCESS read-only
        STATUS mandatory
        DESCRIPTION "Status of Twisted Pair Link for this device"
        ::= { cfetf100Entry 9 }

cfetf100FiberLink OBJECT-TYPE
        SYNTAX INTEGER { linkUp(1), linkDown(2) }
        ACCESS read-only
        STATUS mandatory
        DESCRIPTION "Status of Fiber Link for this device"
        ::= { cfetf100Entry 10 }

cfetf100Fault OBJECT-TYPE
        SYNTAX INTEGER { yes(1), no(2) }
        ACCESS read-only
        STATUS mandatory
        DESCRIPTION "Value is yes(1) when either TPLink or FiberLink 
                     has value linkDown(2)"
        ::= { cfetf100Entry 11 }

cfetf100FastLinkPulse OBJECT-TYPE
        SYNTAX INTEGER { autonegotiate(1), hdx100Btx(2) }
        ACCESS read-write
        STATUS mandatory
        DESCRIPTION "When set to autonegotiate(1), converter sends
                     Fast Link Pulses on its twisted pair port, thereby
                     participating in autonegotiation of duplex between 
                     the converter's twisted pair port and that of the
                     connected station. If that station supports Full-
                     Duplex (FDX) operation, FDX will be used. If not, the
                     twisted pair will operate in Half-Duplex (HDX) mode.
                     When set to hdx100Btx(2), the converter instead sends
                     100Mbps idles (rather than Fast Link Pulses) on its 
                     twisted pair port (i.e. it declines to negotiate), which
                     forces the twisted pair to operate in HDX mode
                     regardless of the capabilities of the connected station.
                     When operating in HDX mode, the twisted pair can support
                     traffic in only one direction at a time. In FDX mode,
                     traffic can pass in both directions simultaneously, thus
                     theoretically doubling network performance."
        ::= { cfetf100Entry 12 }

cfetf100Enabled OBJECT-TYPE
        SYNTAX INTEGER { yes(1), no(2) }
        ACCESS read-write
        STATUS mandatory
        DESCRIPTION "When this configuration item is set to no(2), the
                     device passes no network traffic."
        ::= { cfetf100Entry 13 }

cfetf100Pause OBJECT-TYPE
        SYNTAX INTEGER { enabled(1), disabled(2) }
        ACCESS read-write
        STATUS mandatory
        DESCRIPTION "The Pause feature allows Ethernet MACs that support it to
                     send data pacing 'Pause' messages to each other. 
                     Support for Pause is negotiated at the physical level and
                     passed up to the MAC. While the MAC's Pause messages 
                     themselves can pass over the fiber link that this pair
                     of media converters introduces, the TP physical layer
                     negotiations to enable Pause can not. Therefore, if both 
                     end station MACs support Pause and wish to use it, the
                     Pause negotiation must be re-generated by the media
                     converters on both ends. By setting this configuration
                     option to enabled(1), you are indicating to the local
                     twisted pair station that the twisted pair station on 
                     the other side of the other media converter supports 
                     Pause and wishes to use it. This variable must be set 
                     consistently on both of the paired media converters."
        ::= { cfetf100Entry 14 }

cfetf100LinkPassThrough OBJECT-TYPE
        SYNTAX INTEGER { enabled(1), disabled(2) }
        ACCESS read-write
        STATUS mandatory
        DESCRIPTION "Enable/Disable for Link Pass Through, a feature that
                     causes loss of link on one side of a media converter
                     to be passed through to the other side, so that 
                     upstream equipment can see the fault condition."
        ::= { cfetf100Entry 15 }

cfetf100AutoCross OBJECT-TYPE
        SYNTAX INTEGER { enabled(1), disabled(2) }
        ACCESS read-write
        STATUS mandatory
        DESCRIPTION "Enable/Disable for automatic copper TX/RX pair correction.
                     When disabled, the port operates in MDI mode."
        ::= { cfetf100Entry 16 }

cfetf100TPActivity OBJECT-TYPE
        SYNTAX INTEGER { yes(1), no(2), notSupported(3) }
        ACCESS read-only
        STATUS mandatory
        DESCRIPTION "Network traffic indicator for Copper side of this device"
        ::= { cfetf100Entry 17 }

cfetf100FiberActivity OBJECT-TYPE
        SYNTAX INTEGER { yes(1), no(2), notSupported(3) }
        ACCESS read-only
        STATUS mandatory
        DESCRIPTION "Network traffic indicator for Fiber side of this device"
        ::= { cfetf100Entry 18 }

cfetf100ConfigMode OBJECT-TYPE
        SYNTAX INTEGER { software(1), hardware(2) }
        ACCESS read-only
        STATUS mandatory
        DESCRIPTION "This device has a jumper or switch that disables 
                     software management of the device. When ConfigMode is
                     hardware(2), SNMP management is disabled, and all
                     configuration control comes from physical switches or
                     jumpers on the device."
        ::= { cfetf100Entry 19 }

cfetf100FarEndFault OBJECT-TYPE
        SYNTAX INTEGER { enabled(1), disabled(2), notSupported(3) }
        ACCESS read-write
        STATUS mandatory
        DESCRIPTION "Far End Fault configuration of this device.  This setting 
                     can only be changed by the physical jumper setting on the
                     slide in card, for some devices, if it is available.
                     Far End Fault is software read-write on other devices.
                     Far End Fault causes the fiber transmitter to generate
                     a Far End Fault pattern upon the loss of a receiver signal
                     detect.  When the receiver detects signal again, the
                     transmitter stops transmitting the Far End Fault pattern."
        ::= { cfetf100Entry 20 }

cfetf100CacheClean OBJECT-TYPE
        SYNTAX INTEGER { clean(1), dirty(2) }
        ACCESS read-only
        STATUS mandatory
        DESCRIPTION "When the value is clean(1)Device and Management Module
                     cache are synchronized, no automatic corrections to 
                     configuration will occur.  When the value is dirty(2)
                     Device and Management Module cache are not synchronized.
                     The configuration currently displayed by the application 
                     has not been validated by the device. The device may 
                     need to correct the configuration, in which case the 
                     displayed configuration will change."
        ::= { cfetf100Entry 21 }

-- ==================================================================
-- Table for a cfmff100 slide in device

cfmff100Table OBJECT-TYPE
        SYNTAX SEQUENCE OF Cfmff100Entry
        ACCESS not-accessible
        STATUS mandatory
        DESCRIPTION "Sparse table containing one entry for each CFMFF100
                     SingleMode to MultiMode Fiber Media Converter
                     in the stack, indexed by cabinet serial number and slot."
       ::= { cpsSlotDetail 5 }

cfmff100Entry OBJECT-TYPE
        SYNTAX Cfmff100Entry
        ACCESS not-accessible
        STATUS mandatory
        DESCRIPTION "Status and configuration entries for a single CFMFF100"
        INDEX { cfmff100BiaIndex, cfmff100SlotIndex }
        ::= { cfmff100Table 1 }

Cfmff100Entry ::=
        SEQUENCE {
                 cfmff100BiaIndex            INTEGER,
                 cfmff100SlotIndex           INTEGER,
                 cfmff100Groups              DisplayString,
                 cfmff100MRevision           INTEGER,
                 cfmff100CfgMatch            INTEGER,
                 cfmff100ConnA               INTEGER,
                 cfmff100ConnB               INTEGER,
                 cfmff100SerialNumber        INTEGER,
                 cfmff100SMSignal            INTEGER,
                 cfmff100MMSignal            INTEGER,
                 cfmff100Enabled             INTEGER,
                 cfmff100PortShutOff         INTEGER,
                 cfmff100ConfigMode          INTEGER,
                 cfmff100CacheClean          INTEGER
                 }

cfmff100BiaIndex OBJECT-TYPE
        SYNTAX INTEGER
        ACCESS read-only
        STATUS mandatory
        DESCRIPTION "The serial number (BIA) of the cabinet in which the 
                     device is installed"
        ::= { cfmff100Entry 1 }

cfmff100SlotIndex OBJECT-TYPE
        SYNTAX INTEGER
        ACCESS read-only
        STATUS mandatory
        DESCRIPTION "The slot in which the device is installed"
        ::= { cfmff100Entry 2 }

cfmff100Groups OBJECT-TYPE
        SYNTAX DisplayString
        ACCESS read-write
        STATUS mandatory
        DESCRIPTION "User-defined keywords that group this device together with
                     other devices under a user-defined scheme. By placing 
                     matching keywords in cpsGroupCtrl.0, the agent can be
                     instructed to apply configuration changes simultaneously
                     to all group members rather than to individual devices.
                     Every Groups string has three automatically defined
                     implied values: 
                     1) The model family of the device, e.g. 'CFMFF100'
                     2) The serial number of the cabinet in which the device
                        is installed, in decimal with no leading zeroes, 
                        e.g. '12345', and 
                     3) same as 2, with the slot in which the device is 
                        installed appended, enclosed in square brackets. 
                        e.g. '12345[9]'"
        ::= { cfmff100Entry 3 }

cfmff100MRevision OBJECT-TYPE
        SYNTAX INTEGER
        ACCESS read-only
        STATUS mandatory
        DESCRIPTION "The marketing revision of the device"
        ::= { cfmff100Entry 4 }

cfmff100CfgMatch OBJECT-TYPE
        SYNTAX INTEGER { yes(1), no(2), notApplicable(3) }
        ACCESS read-only
        STATUS mandatory
        DESCRIPTION "yes(1) indicates that the conditions specified in 
                     cpsGroupCtrl.0 match the Groups value for this
                     device. no(2) means that there is no match.
                     notApplicable(3) indicates that cpsGroupCtrl.0 is null
                     and therefore no comparison was performed."
        ::= { cfmff100Entry 5 }

cfmff100ConnA OBJECT-TYPE
        SYNTAX CpsConnector
        ACCESS read-only
        STATUS mandatory
        DESCRIPTION "The style of SingleMode connector built into this device"
        ::= { cfmff100Entry 6 }

cfmff100ConnB OBJECT-TYPE
        SYNTAX CpsConnector
        ACCESS read-only
        STATUS mandatory
        DESCRIPTION "The style of MultiMode connector built into this device"
        ::= { cfmff100Entry 7 }

cfmff100SerialNumber OBJECT-TYPE
        SYNTAX INTEGER
        ACCESS read-only
        STATUS mandatory
        DESCRIPTION "The serial number of this device"
        ::= { cfmff100Entry 8 }

cfmff100SMSignal OBJECT-TYPE
        SYNTAX INTEGER { signalUp(1), signalDown(2) }
        ACCESS read-only
        STATUS mandatory
        DESCRIPTION "Status of singlemode signal detect for this device"
        ::= { cfmff100Entry 9 }

cfmff100MMSignal OBJECT-TYPE
        SYNTAX INTEGER { signalUp(1), signalDown(2) }
        ACCESS read-only
        STATUS mandatory
        DESCRIPTION "Status of singlemode signal detect for this device"
        ::= { cfmff100Entry 10 }

cfmff100Enabled OBJECT-TYPE
        SYNTAX INTEGER { yes(1), noP1(2), noP2(3), no(4) }
        ACCESS read-write
        STATUS mandatory
        DESCRIPTION "Ports on this device can be disabled individually.
                     When this control is set to yes(1), the entire device
                     is enabled. When it is set to noP1(2), the SingleMode port
                     is disabled. noP2(3) disables the MultiMode port only, 
                     and no(4) disables both. For most purposes, the values
                     noP1(2), noP2(3), and no(4) are equivalent."
        ::= { cfmff100Entry 11 }

cfmff100PortShutOff OBJECT-TYPE
        SYNTAX INTEGER { enabled(1), disabled(2) }
        ACCESS read-only
        STATUS mandatory
        DESCRIPTION "This variable reflects the status of the DPT/OPP jumper
                     on the board. This jumper controls the behavior of the
                     converter when a loss of signal is detected. When the
                     jumper is in the default OPP position, the loss of signal
                     detect on one port causes the opposite port to be shut
                     down. In this case, Port Shutoff is said to be disabled(2).
                     In the DPT (enabled(1)) position, both ports are shut down.
                     Use of the DPT position is discouraged, as it is more likely
                     to lead to a signal loss condition from which the 
                     converter is unable to recover."
        ::= { cfmff100Entry 12 }

cfmff100ConfigMode OBJECT-TYPE
        SYNTAX INTEGER { software(1), hardware(2) }
        ACCESS read-only
        STATUS mandatory
        DESCRIPTION "This device has a jumper or switch that disables 
                     software management of the device. When ConfigMode is
                     hardware(2), SNMP management is disabled, and all
                     configuration control comes from physical switches or
                     jumpers on the device."
        ::= { cfmff100Entry 13 }

cfmff100CacheClean OBJECT-TYPE
        SYNTAX INTEGER { clean(1), dirty(2) }
        ACCESS read-only
        STATUS mandatory
        DESCRIPTION "When the value is clean(1)Device and Management Module
                     cache are synchronized, no automatic corrections to 
                     configuration will occur.  When the value is dirty(2)
                     Device and Management Module cache are not synchronized.
                     The configuration currently displayed by the application 
                     has not been validated by the device. The device may 
                     need to correct the configuration, in which case the 
                     displayed configuration will change."
        ::= { cfmff100Entry 14 }

-- ================================================================
-- Table for the cpsmp100

cpsmp100Table OBJECT-TYPE
        SYNTAX SEQUENCE OF Cpsmp100Entry
        ACCESS not-accessible
        STATUS mandatory
        DESCRIPTION "Sparse table containing one entry for each CPSMP100
                     IFO (Instant Fail-Over) Power Supply
                     in the stack, indexed by cabinet serial number and slot."
        ::= { cpsSlotDetail 6 }

cpsmp100Entry OBJECT-TYPE
        SYNTAX Cpsmp100Entry
        ACCESS not-accessible
        STATUS mandatory
        DESCRIPTION "Status and configuration entries for a single CPSMP100"
        INDEX { cpsmp100BiaIndex, cpsmp100SlotIndex }
        ::= { cpsmp100Table 1 }

Cpsmp100Entry ::=
        SEQUENCE {
                  cpsmp100BiaIndex           INTEGER,
                  cpsmp100SlotIndex          INTEGER,
                  cpsmp100Groups             DisplayString,
                  cpsmp100MRevision          INTEGER,
                  cpsmp100CfgMatch           INTEGER,
                  cpsmp100SerialNumber       INTEGER,
                  cpsmp100Mode               INTEGER,
                  cpsmp100ConfigMode         INTEGER,
                  cpsmp100RemoteFan          INTEGER,
                  cpsmp100PowerOK            INTEGER,
                  cpsmp100InUse              INTEGER,
                  cpsmp100ChassisPower       INTEGER,
                  cpsmp100ChassisTemp        INTEGER,
                  cpsmp100RFanFault          INTEGER,
                  cpsmp100LFanFault          INTEGER,
                  cpsmp100SupplyType         INTEGER,
                  cpsmp100CacheClean         INTEGER
                  }

cpsmp100BiaIndex OBJECT-TYPE
        SYNTAX INTEGER
        ACCESS read-only
        STATUS mandatory
        DESCRIPTION "The serial number (BIA) of the cabinet in which the 
                     device is installed"
        ::= { cpsmp100Entry 1 } 

cpsmp100SlotIndex OBJECT-TYPE
        SYNTAX INTEGER
        ACCESS read-only
        STATUS mandatory
        DESCRIPTION "The slot in which the device is installed. Power Supplies
                     occupy special slots numbered 125 and higher."
        ::= { cpsmp100Entry 2 }

cpsmp100Groups OBJECT-TYPE
        SYNTAX DisplayString
        ACCESS read-write
        STATUS mandatory
        DESCRIPTION "User-defined keywords that group this device together with
                     other devices under a user-defined scheme. By placing 
                     matching keywords in cpsGroupCtrl.0, the agent can be
                     instructed to apply configuration changes simultaneously
                     to all group members rather than to individual devices.
                     Every Groups string has three automatically defined
                     implied values: 
                     1) The model family of the device, e.g. 'CPSMP100'
                     2) The serial number of the cabinet in which the device
                        is installed, in decimal with no leading zeroes, 
                        e.g. '12345', and 
                     3) same as 2, with the slot in which the device is 
                        installed appended, enclosed in square brackets. 
                        e.g. '12345[9]'"
        ::= { cpsmp100Entry 3 }

cpsmp100MRevision OBJECT-TYPE
        SYNTAX INTEGER
        ACCESS read-only
        STATUS mandatory
        DESCRIPTION "The marketing revision of this device"
        ::= { cpsmp100Entry 4 }

cpsmp100CfgMatch OBJECT-TYPE
        SYNTAX INTEGER { yes(1), no(2), notApplicable(3) }
        ACCESS read-only
        STATUS mandatory
        DESCRIPTION "yes(1) indicates that the conditions specified in 
                     cpsGroupCtrl.0 match the Groups value for this
                     device. no(2) means that there is no match.
                     notApplicable(3) indicates that cpsGroupCtrl.0 is null
                     and therefore no comparison was performed."
        ::= { cpsmp100Entry 5 }

cpsmp100SerialNumber OBJECT-TYPE
        SYNTAX INTEGER
        ACCESS read-only
        STATUS mandatory
        DESCRIPTION "The serial number of this device"
        ::= { cpsmp100Entry 6 }

cpsmp100Mode OBJECT-TYPE
        SYNTAX INTEGER { master(1), slave(2) }
        ACCESS read-write
        STATUS mandatory
        DESCRIPTION "When one power supply is set to master(1) and the
                     other is set to slave(2), the master will supply
                     all power to the cabinet, and the slave will take 
                     over if the master stops supplying power. This is
                     useful when (for example) one supply is attached to a
                     wall socket and the other to a battery backup. The
                     cabinet can be directed to only draw power from
                     batteries when there is no alternative.
                     When both power supplies are set to master(1), the
                     results are determined automatically. 
                     WARNING: It is up to the system administrator to 
                     ensure that at least one power supply is set to
                     master(1). It is illegal to set all power supplies to 
                     slave(2). If this occurs, the cabinet may lose
                     all power under certain circumstances, even if
                     power is available."
        ::= { cpsmp100Entry 7 }

cpsmp100ConfigMode OBJECT-TYPE
        SYNTAX INTEGER { software(1), hardware(2) }
        ACCESS read-only
        STATUS mandatory
        DESCRIPTION "This device has a jumper or switch that disables 
                     software management of the device. When ConfigMode is
                     hardware(2), SNMP management is disabled, and all
                     configuration control comes from physical switches or
                     jumpers on the device."
        ::= { cpsmp100Entry 8 }

cpsmp100RemoteFan OBJECT-TYPE
        SYNTAX INTEGER { installed(1), notInstalled(2) }
        ACCESS read-only
        STATUS mandatory
        DESCRIPTION "A Remote Fan is a device that fits in a power supply
                     slot but contains no power supply, only a fan.
                     These devices are not manageable, but if present they
                     will be reported by the manageable supply that 
                     accompanies it."
        ::= { cpsmp100Entry 9 }

cpsmp100PowerOK OBJECT-TYPE
        SYNTAX INTEGER { yes(1), no(2) }
        ACCESS read-only
        STATUS mandatory
        DESCRIPTION "This variable has the value yes(1) any time this 
                     supply is capable of supplying at least 11.6 volts
                     to the cabinet. Note that a value of no(2) does not
                     necessarily indicate hard failure. A power supply can 
                     be detected even if it is powered down or not plugged in
                     as long as another power supply has PowerOK=yes(1) and
                     InUse=yes(1). In this case, PowerOK will be no(2) for
                     the disabled power supply."
        ::= { cpsmp100Entry 10 }

cpsmp100InUse OBJECT-TYPE
        SYNTAX INTEGER { yes(1), no(2) }
        ACCESS read-only
        STATUS mandatory
        DESCRIPTION "Value is yes(1) when this supply is currently selected
                     to supply power to the cabinet."
        ::= { cpsmp100Entry 11 }

cpsmp100ChassisPower OBJECT-TYPE
        SYNTAX INTEGER
        ACCESS read-only
        STATUS mandatory
        DESCRIPTION "Power currently supplied to the cabinet, in milliwatts"
        ::= { cpsmp100Entry 12 }

cpsmp100ChassisTemp OBJECT-TYPE
        SYNTAX INTEGER
        ACCESS read-only
        STATUS mandatory
        DESCRIPTION "The temperature inside the cabinet as detected by
                     the power supply, in tenths of degrees centigrade"
        ::= { cpsmp100Entry 13 }

cpsmp100RFanFault OBJECT-TYPE
        SYNTAX INTEGER { yes(1), no(2) }
        ACCESS read-only
        STATUS mandatory
        DESCRIPTION "Normally no(2), this value changes to yes(1) when
                     an installed Remote fan is drawing excessive current 
                     or none at all."
        ::= { cpsmp100Entry 14 }

cpsmp100LFanFault OBJECT-TYPE
        SYNTAX INTEGER { yes(1), no(2) }
        ACCESS read-only
        STATUS mandatory
        DESCRIPTION "Normally no(2), this value changes to yes(1) when
                     the Local fan is drawing excessive current or none
                     at all."
        ::= { cpsmp100Entry 15 }

cpsmp100SupplyType OBJECT-TYPE
        SYNTAX INTEGER { ac(1), dc48(2) }
        ACCESS read-only
        STATUS mandatory
        DESCRIPTION "The supply voltage that this unit is designed to accept.
                     If AC(1), the supply accepts 90-260VAC, 47 to 400Hz.
                     If DC48(2), the supply accepts 38-75VDC."
        ::= { cpsmp100Entry 16 }

cpsmp100CacheClean OBJECT-TYPE
        SYNTAX INTEGER { clean(1), dirty(2) }
        ACCESS read-only
        STATUS mandatory
        DESCRIPTION "When the value is clean(1)Device and Management Module
                     cache are synchronized, no automatic corrections to 
                     configuration will occur.  When the value is dirty(2)
                     Device and Management Module cache are not synchronized.
                     The configuration currently displayed by the application 
                     has not been validated by the device. The device may 
                     need to correct the configuration, in which case the 
                     displayed configuration will change."
        ::= { cpsmp100Entry 17 }

-- ================================================================
-- Table for the csetf100

csetf100Table OBJECT-TYPE
        SYNTAX SEQUENCE OF Csetf100Entry
        ACCESS not-accessible
        STATUS mandatory
        DESCRIPTION "Sparse table containing one entry for each CSETF100
                     10/100Mbps Twisted-Pair to Fiber Ethernet Media Converter
                     in the stack, indexed by cabinet serial number and slot."
        ::= { cpsSlotDetail 7 }

csetf100Entry OBJECT-TYPE
        SYNTAX Csetf100Entry
        ACCESS not-accessible
        STATUS mandatory
        DESCRIPTION "One table entry per piece of management module
                     information.  Entry 'n' does not exist."
        INDEX { csetf100BiaIndex, csetf100SlotIndex }
        ::= { csetf100Table 1 }

Csetf100Entry ::=
        SEQUENCE {
                 csetf100BiaIndex            INTEGER,
                 csetf100SlotIndex           INTEGER,
                 csetf100Groups              DisplayString,
                 csetf100MRevision           INTEGER,
                 csetf100CfgMatch            INTEGER,
                 csetf100SerialNumber        INTEGER,
                 csetf100ConnA               INTEGER,
                 csetf100ConnB               INTEGER,
                 csetf100TPLink              INTEGER,
                 csetf100FiberLink           INTEGER,
                 csetf100AutoCross           INTEGER,
                 csetf100SpeedConfig         INTEGER,
                 csetf100Speed100Mbps        INTEGER,
                 csetf100TPActivity          INTEGER,
                 csetf100FiberActivity       INTEGER,
                 csetf100ConfigMode          INTEGER,
                 csetf100CacheClean          INTEGER
                 }

csetf100BiaIndex OBJECT-TYPE
        SYNTAX INTEGER
        ACCESS read-only
        STATUS mandatory
        DESCRIPTION "The serial number (BIA) of the cabinet in which the 
                     device is installed"
        ::= { csetf100Entry 1 }

csetf100SlotIndex OBJECT-TYPE
        SYNTAX INTEGER
        ACCESS read-only
        STATUS mandatory
        DESCRIPTION "The slot in which the device is installed"
        ::= { csetf100Entry 2 }

csetf100Groups OBJECT-TYPE
        SYNTAX DisplayString
        ACCESS read-write
        STATUS mandatory
        DESCRIPTION "User-defined keywords that group this device together with
                     other devices under a user-defined scheme. By placing 
                     matching keywords in cpsGroupCtrl.0, the agent can be
                     instructed to apply configuration changes simultaneously
                     to all group members rather than to individual devices.
                     Every Groups string has three automatically defined
                     implied values: 
                     1) The model family of the device, e.g. 'CSETF100'
                     2) The serial number of the cabinet in which the device
                        is installed, in decimal with no leading zeroes, 
                        e.g. '12345', and 
                     3) same as 2, with the slot in which the device is 
                        installed appended, enclosed in square brackets. 
                        e.g. '12345[9]'"
        ::= { csetf100Entry 3 }

csetf100MRevision OBJECT-TYPE
        SYNTAX INTEGER
        ACCESS read-only
        STATUS mandatory
        DESCRIPTION "The marketing revision of this device"
        ::= { csetf100Entry 4 }

csetf100CfgMatch OBJECT-TYPE
        SYNTAX INTEGER { yes(1), no(2), inactive(3) }
        ACCESS read-only
        STATUS mandatory
        DESCRIPTION "yes(1) indicates that the conditions specified in 
                     cpsGroupCtrl.0 match the Groups value for this
                     device. no(2) means that there is no match.
                     notApplicable(3) indicates that cpsGroupCtrl.0 is null
                     and therefore no comparison was performed."
        ::= { csetf100Entry 5 }

csetf100SerialNumber OBJECT-TYPE
        SYNTAX INTEGER
        ACCESS read-only
        STATUS mandatory
        DESCRIPTION "The serial number of this device"
        ::= { csetf100Entry 6 }

csetf100ConnA OBJECT-TYPE
        SYNTAX CpsConnector
        ACCESS read-only
        STATUS mandatory
        DESCRIPTION "The style of Fiber connector built into this device"
        ::= { csetf100Entry 7 }

csetf100ConnB OBJECT-TYPE
        SYNTAX CpsConnector
        ACCESS read-only
        STATUS mandatory
        DESCRIPTION "The style of Copper connector built into this device"
        ::= { csetf100Entry 8 }

csetf100TPLink OBJECT-TYPE
        SYNTAX INTEGER { linkUp(1), linkDown(2) }
        ACCESS read-only
        STATUS mandatory
        DESCRIPTION "Status of Twisted Pair Link for this device"
        ::= { csetf100Entry 9 }

csetf100FiberLink OBJECT-TYPE
        SYNTAX INTEGER { linkUp(1), linkDown(2) }
        ACCESS read-only
        STATUS mandatory
        DESCRIPTION "Status of Fiber Link for this device"
        ::= { csetf100Entry 10 }

csetf100AutoCross OBJECT-TYPE
        SYNTAX INTEGER { enabled(1), disabled(2) }
        ACCESS read-write
        STATUS mandatory
        DESCRIPTION "Enable/Disable for automatic copper TX/RX pair correction"
        ::= { csetf100Entry 11 }

csetf100SpeedConfig OBJECT-TYPE
        SYNTAX INTEGER { auto(1), mbps10(2), mbps100(3) }
        ACCESS read-write
        STATUS mandatory
        DESCRIPTION "This variable allows the user to set the requested data
                     transfer rate for this converter."
        ::= { csetf100Entry 12 }

csetf100Speed100Mbps OBJECT-TYPE
        SYNTAX INTEGER { yes(1), no(2) }
        ACCESS read-only
        STATUS mandatory
        DESCRIPTION "This variable reports the current data transfer rate for 
                     this converter."
        ::= { csetf100Entry 13 }

csetf100TPActivity OBJECT-TYPE
        SYNTAX INTEGER { activity(1), noActivity(2) }
        ACCESS read-only
        STATUS mandatory
        DESCRIPTION "Network traffic indicator for Copper side of this device"
        ::= { csetf100Entry 14 }

csetf100FiberActivity OBJECT-TYPE
        SYNTAX INTEGER { activity(1), noActivity(2) }
        ACCESS read-only
        STATUS mandatory
        DESCRIPTION "Network traffic indicator for Fiber side of this device"
        ::= { csetf100Entry 15 }

csetf100ConfigMode OBJECT-TYPE
        SYNTAX INTEGER { software(1), hardware(2) }
        ACCESS read-only
        STATUS mandatory
        DESCRIPTION "This device has a jumper or switch that disables 
                     software management of the device. When ConfigMode is
                     hardware(2), SNMP management is disabled, and all
                     configuration control comes from physical switches or
                     jumpers on the device."
        ::= { csetf100Entry 16 }

csetf100CacheClean OBJECT-TYPE
        SYNTAX INTEGER { clean(1), dirty(2) }
        ACCESS read-only
        STATUS mandatory
        DESCRIPTION "When the value is clean(1)Device and Management Module
                     cache are synchronized, no automatic corrections to 
                     configuration will occur.  When the value is dirty(2)
                     Device and Management Module cache are not synchronized.
                     The configuration currently displayed by the application 
                     has not been validated by the device. The device may 
                     need to correct the configuration, in which case the 
                     displayed configuration will change."
        ::= { csetf100Entry 17 }

-- ================================================================
-- Table for the cgetf100

cgetf100Table OBJECT-TYPE
        SYNTAX SEQUENCE OF Cgetf100Entry
        ACCESS not-accessible
        STATUS mandatory
        DESCRIPTION "Sparse table containing one entry for each CGETF100
                     Gigabit Twisted-Pair to Fiber Ethernet Media Converter
                     in the stack, indexed by cabinet serial number and slot."
        ::= { cpsSlotDetail 8 }

cgetf100Entry OBJECT-TYPE
        SYNTAX Cgetf100Entry
        ACCESS not-accessible
        STATUS mandatory
        DESCRIPTION "One table entry per piece of management module
                     information.  Entry 'n' does not exist."
        INDEX { cgetf100BiaIndex, cgetf100SlotIndex }
        ::= { cgetf100Table 1 }

Cgetf100Entry ::=
        SEQUENCE {
                 cgetf100BiaIndex            INTEGER,
                 cgetf100SlotIndex           INTEGER,
                 cgetf100Groups              DisplayString,
                 cgetf100MRevision           INTEGER,
                 cgetf100CfgMatch            INTEGER,
                 cgetf100SerialNumber        INTEGER,
                 cgetf100ConnA               INTEGER,
                 cgetf100ConnB               INTEGER,
                 cgetf100TPLink              INTEGER,
                 cgetf100FiberLink           INTEGER,
                 cgetf100Fault               INTEGER,
                 cgetf100Enabled             INTEGER,
                 cgetf100Pause               INTEGER,
                 cgetf100LinkPassThrough     INTEGER,
                 cgetf100FullDuplex          INTEGER,
                 cgetf100ClockMaster         INTEGER,
                 cgetf100ConfigMode          INTEGER,
                 cgetf100TPLength            INTEGER,
                 cgetf100FiberAutoNegot      INTEGER,
                 cgetf100CacheClean          INTEGER,
                 cgetf100PauseType           INTEGER
                 }

cgetf100BiaIndex OBJECT-TYPE
        SYNTAX INTEGER
        ACCESS read-only
        STATUS mandatory
        DESCRIPTION "The serial number (BIA) of the cabinet in which the 
                     device is installed"
        ::= { cgetf100Entry 1 }

cgetf100SlotIndex OBJECT-TYPE
        SYNTAX INTEGER
        ACCESS read-only
        STATUS mandatory
        DESCRIPTION "The slot in which the device is installed"
        ::= { cgetf100Entry 2 }

cgetf100Groups OBJECT-TYPE
        SYNTAX DisplayString
        ACCESS read-write
        STATUS mandatory
        DESCRIPTION "User-defined keywords that group this device together with
                     other devices under a user-defined scheme. By placing 
                     matching keywords in cpsGroupCtrl.0, the agent can be
                     instructed to apply configuration changes simultaneously
                     to all group members rather than to individual devices.
                     Every Groups string has three automatically defined
                     implied values: 
                     1) The model family of the device, e.g. 'CGETF100'
                     2) The serial number of the cabinet in which the device
                        is installed, in decimal with no leading zeroes, 
                        e.g. '12345', and 
                     3) same as 2, with the slot in which the device is 
                        installed appended, enclosed in square brackets. 
                        e.g. '12345[9]'"
        ::= { cgetf100Entry 3 }

cgetf100MRevision OBJECT-TYPE
        SYNTAX INTEGER
        ACCESS read-only
        STATUS mandatory
        DESCRIPTION "The marketing revision of this device"
        ::= { cgetf100Entry 4 }

cgetf100CfgMatch OBJECT-TYPE
        SYNTAX INTEGER { yes(1), no(2), inactive(3) }
        ACCESS read-only
        STATUS mandatory
        DESCRIPTION "yes(1) indicates that the conditions specified in 
                     cpsGroupCtrl.0 match the Groups value for this
                     device. no(2) means that there is no match.
                     notApplicable(3) indicates that cpsGroupCtrl.0 is null
                     and therefore no comparison was performed."
        ::= { cgetf100Entry 5 }

cgetf100SerialNumber OBJECT-TYPE
        SYNTAX INTEGER
        ACCESS read-only
        STATUS mandatory
        DESCRIPTION "The serial number of this device"
        ::= { cgetf100Entry 6 }

cgetf100ConnA OBJECT-TYPE
        SYNTAX CpsConnector
        ACCESS read-only
        STATUS mandatory
        DESCRIPTION "The style of Fiber connector built into this device"
        ::= { cgetf100Entry 7 }

cgetf100ConnB OBJECT-TYPE
        SYNTAX CpsConnector
        ACCESS read-only
        STATUS mandatory
        DESCRIPTION "The style of Copper connector built into this device"
        ::= { cgetf100Entry 8 }

cgetf100TPLink OBJECT-TYPE
        SYNTAX INTEGER { linkUp(1), linkDown(2) }
        ACCESS read-only
        STATUS mandatory
        DESCRIPTION "Status of Twisted Pair Link for this device"
        ::= { cgetf100Entry 9 }

cgetf100FiberLink OBJECT-TYPE
        SYNTAX INTEGER { linkUp(1), linkDown(2) }
        ACCESS read-only
        STATUS mandatory
        DESCRIPTION "Status of Fiber Link for this device"
        ::= { cgetf100Entry 10 }

cgetf100Fault OBJECT-TYPE
        SYNTAX INTEGER { yes(1), no(2) }
        ACCESS read-only
        STATUS mandatory
        DESCRIPTION "Value is yes(1) when either TPLink or FiberLink 
                     has value linkDown(2)"
        ::= { cgetf100Entry 11 }

cgetf100Enabled OBJECT-TYPE
        SYNTAX INTEGER { yes(1), no(2) }
        ACCESS read-write
        STATUS mandatory
        DESCRIPTION "When this variable is set to no(1), the device
                     allows no traffic to pass."
        ::= { cgetf100Entry 12 }

cgetf100Pause OBJECT-TYPE
        SYNTAX INTEGER { enabled(1), disabled(2) }
        ACCESS read-write
        STATUS mandatory
        DESCRIPTION "Enable/Disable control for the advertising of Pause
                      capability on the copper interface.  This MIB variable
                      is retained for compatibility with older applications
                      and firmware. If you have a current version of the
                      CGETF100 device (which supports asymmetric pause), 
                      you should both read and write the MIB variable
                      cgetf100PauseType(21) for complete monitoring and 
                      control of pause capability advertising. If you are 
                      using a current Transition Networks application, this
                      is automatic.
                      On all versions of the CGETF100 device, this MIB variable
                      can be used to enable and disable advertising of symmetric
                      pause.
                      For current versions of the CGETF100, this variable reads
                      enabled(1) any time any type of pause is enabled, and 
                      forces cgetf100PauseType(21) to symmetric(1) when changed
                      from disabled(2) to enabled(1).
                      On new versions of the CGETF100 device, when
                      cgetf100FiberAutoNegot(19) has the value enabled(1), this
                      variable takes on the read-only value enabled(1)."
        ::= { cgetf100Entry 13 }

cgetf100LinkPassThrough OBJECT-TYPE
        SYNTAX INTEGER { enabled(1), disabled(2) }
        ACCESS read-write
        STATUS mandatory
        DESCRIPTION "Enable/Disable for Link Pass Through, a feature that
                     causes loss of link on one side of a media converter
                     to be passed through to the other side, so that 
                     upstream equipment can see the fault condition."
        ::= { cgetf100Entry 14 }

cgetf100FullDuplex OBJECT-TYPE
        SYNTAX INTEGER { fullDuplex(1), halfDuplex(2) }
        ACCESS read-write
        STATUS mandatory
        DESCRIPTION "Controls advertizing of duplex capability for the
                     copper side of the converter. When set to fullDuplex(1),
                     the converter advertizes full duplex capability. 
                     When set to halfDuplex(2), the converter advertizes
                     half duplex capability. The converter never advertizes 
                     both simultaneously. If the advertized setting is not
                     supported by the remote, link cannot be established."
        ::= { cgetf100Entry 15 }

cgetf100ClockMaster OBJECT-TYPE
        SYNTAX INTEGER { yes(1), no(2) }
        ACCESS read-only
        STATUS mandatory
        DESCRIPTION "When yes(1), the converter is supplying clock to the 
                     twisted pair. When no(2), the remote supplies the clock."
        ::= { cgetf100Entry 16 }

cgetf100ConfigMode OBJECT-TYPE
        SYNTAX INTEGER { software(1), hardware(2) }
        ACCESS read-only
        STATUS mandatory
        DESCRIPTION "This device has a jumper or switch that disables 
                     software management of the device. When ConfigMode is
                     hardware(2), SNMP management is disabled, and all
                     configuration control comes from physical switches or
                     jumpers on the device."
        ::= { cgetf100Entry 17 }

cgetf100TPLength OBJECT-TYPE
        SYNTAX INTEGER { ln-lt50(1), ln-50-80(2), ln-80-110(3), ln-110-140(4),
                         ln-gt140(5) }
        ACCESS read-only
        STATUS mandatory
        DESCRIPTION "Twisted-pair length estimated via the converter's 
                     internal Time Domain Reflectometer. 1 means less than 
                     50 meters, 2 means 50 to 80 meters, 3 means 80 to 110
                     meters, 4 means 110 to 140 meters, and 5 means more than
                     140 meters."
        ::= { cgetf100Entry 18 }

cgetf100FiberAutoNegot OBJECT-TYPE
        SYNTAX INTEGER  { enabled(1), disabled(2), notApplicable(3) }
        ACCESS read-write
        STATUS mandatory
        DESCRIPTION "Fiber port autonegotiation configuration."
        ::= { cgetf100Entry 19 }

cgetf100CacheClean OBJECT-TYPE
        SYNTAX INTEGER { clean(1), dirty(2) }
        ACCESS read-only
        STATUS mandatory
        DESCRIPTION "When the value is clean(1)Device and Management Module
                     cache are synchronized, no automatic corrections to 
                     configuration will occur.  When the value is dirty(2)
                     Device and Management Module cache are not synchronized.
                     The configuration currently displayed by the application 
                     has not been validated by the device. The device may 
                     need to correct the configuration, in which case the 
                     displayed configuration will change."
        ::= { cgetf100Entry 20 }

cgetf100PauseType OBJECT-TYPE
        SYNTAX INTEGER  { symmetric(1), asymRX(2), asymTX(3), disabled(4), 
                          notApplicable(5), symmetricRO(6), asymRXRO(7),
                          asymTXRO(8), disabledRO(9), all(10) }
        ACCESS read-write
        STATUS mandatory
        DESCRIPTION "Enable/Disable control for the advertising of Pause 
                     capability on the copper interface. This MIB variable 
                     is only functional on CGETF100 devices that support 
                     asymmetric pause (i.e. current versions). If your 
                     CGETF100 does not support asymmetric pause, this 
                     variable will return the read-only value notApplicable(5) 
                     regardless of any other factors.
                     On current CGETF100 devices, selectable values for this 
                     variable are symmetric(1), asymRX(2) (asymmetric, pause 
                     frames flow towards the converter), asymTX(3) (asymmetric,
                     pause frames flow towards the link partner), and 
                     disabled(4).
                     Note: Changing cgetf100PauseType(21) to disabled(4) causes 
                     cgetf100Pause(13) to take on the value disabled(2). Changing 
                     cgetf100PauseType(21) to any selectable value other than 
                     disabled(4) causes cgetf100Pause(13) to take on the value 
                     enabled(1).
                     If cgetf100FiberAutoNegot(19) has the value enabled(1), then 
                     this variable returns the read-only value all(10), which 
                     indicates that all advertised modes received from the twisted 
                     pair link partner are reflected back to the link partner.
                     Otherwise, if cgetf100ConfigMode(17) has the value hardware(2), 
                     one of the following read-only values will be returned: 
                     symmetricRO(6) or disabledRO(9). The read-only values asymRXRO(7) 
                     and asymTXRO(8) are defined for future expansion."
        ::= { cgetf100Entry 21 }

--=====================================================================
-- Table for the csdtf100

csdtf100Table OBJECT-TYPE
        SYNTAX SEQUENCE OF Csdtf100Entry
        ACCESS not-accessible
        STATUS mandatory
        DESCRIPTION "Sparse table containing one entry for each CSDTF100
                     T1/E1 Copper to Fiber Media Converter
                     in the stack, indexed by cabinet serial number and slot."
        ::= { cpsSlotDetail 9 }

csdtf100Entry OBJECT-TYPE
        SYNTAX Csdtf100Entry
        ACCESS not-accessible
        STATUS mandatory
        DESCRIPTION "Status and configuration entries for a single CSDTF100"
        INDEX { csdtf100BiaIndex, csdtf100SlotIndex }
        ::= { csdtf100Table 1 }

Csdtf100Entry ::=
        SEQUENCE {
                 csdtf100BiaIndex               INTEGER,
                 csdtf100SlotIndex              INTEGER,
                 csdtf100Groups                 DisplayString,
                 csdtf100MRevision              INTEGER,
                 csdtf100CfgMatch               INTEGER,
                 csdtf100SerialNumber           INTEGER,
                 csdtf100ConnA                  INTEGER,
                 csdtf100ConnB                  INTEGER,
                 csdtf100CopperLink             INTEGER,
                 csdtf100FiberLink              INTEGER,
                 csdtf100Fault                  INTEGER,
                 csdtf100TAOSFiber              INTEGER,
                 csdtf100TAOSCopper             INTEGER,
                 csdtf100AISFiber               INTEGER,
                 csdtf100AISCopper              INTEGER,
                 csdtf100CopperLoopback         INTEGER,
                 csdtf100CopperLongHaul         INTEGER,
                 csdtf100T1E1                   INTEGER,
                 csdtf100ConfigMode             INTEGER,
                 csdtf100TPCoax                 INTEGER,
                 csdtf100CopperLineBuildout     INTEGER,
                 csdtf100FiberLoopback          INTEGER,
                 csdtf100RmtSupported           INTEGER,
                 csdtf100RmtDetected            INTEGER,
                 csdtf100RmtMRevision           INTEGER,
                 csdtf100RmtSerialNumber        INTEGER,
                 csdtf100RmtConnA               INTEGER,
                 csdtf100RmtConnB               INTEGER,
                 csdtf100RmtCopperLink          INTEGER,
                 csdtf100RmtFiberLink           INTEGER,
                 csdtf100RmtFault               INTEGER,
                 csdtf100RmtTAOSFiber           INTEGER,
                 csdtf100RmtTAOSCopper          INTEGER,
                 csdtf100RmtAISFiber            INTEGER,
                 csdtf100RmtAISCopper           INTEGER,
                 csdtf100RmtCopperLoopback      INTEGER,
                 csdtf100RmtCopperLongHaul      INTEGER,
                 csdtf100RmtConfigMode          INTEGER,
                 csdtf100RmtTPCoax              INTEGER,
                 csdtf100RmtCopperLineBuildout  INTEGER,
                 csdtf100RmtFiberLoopback       INTEGER,
                 csdtf100CacheClean             INTEGER
                 }

csdtf100BiaIndex OBJECT-TYPE
        SYNTAX INTEGER
        ACCESS read-only
        STATUS mandatory
        DESCRIPTION "The serial number (BIA) of the cabinet in which the 
                     device is installed"
        ::= { csdtf100Entry 1 }

csdtf100SlotIndex OBJECT-TYPE
        SYNTAX INTEGER
        ACCESS read-only
        STATUS mandatory
        DESCRIPTION "The slot in which the device is installed"
        ::= { csdtf100Entry 2 }

csdtf100Groups OBJECT-TYPE
        SYNTAX DisplayString
        ACCESS read-write
        STATUS mandatory
        DESCRIPTION "User-defined keywords that group this device together with
                     other devices under a user-defined scheme. By placing 
                     matching keywords in cpsGroupCtrl.0, the agent can be
                     instructed to apply configuration changes simultaneously
                     to all group members rather than to individual devices.
                     Every Groups string has three automatically defined
                     implied values: 
                     1) The model family of the device, e.g. 'CSDTF100'
                     2) The serial number of the cabinet in which the device
                        is installed, in decimal with no leading zeroes, 
                        e.g. '12345', and 
                     3) same as 2, with the slot in which the device is 
                        installed appended, enclosed in square brackets. 
                        e.g. '12345[9]'"
        ::= { csdtf100Entry 3 }

csdtf100MRevision OBJECT-TYPE
        SYNTAX INTEGER
        ACCESS read-only
        STATUS mandatory
        DESCRIPTION "The marketing revision of this device"
        ::= { csdtf100Entry 4 }

csdtf100CfgMatch OBJECT-TYPE
        SYNTAX INTEGER { yes(1), no(2), inactive(3) }
        ACCESS read-only
        STATUS mandatory
        DESCRIPTION "yes(1) indicates that the conditions specified in 
                     cpsGroupCtrl.0 match the Groups value for this
                     device. no(2) means that there is no match.
                     notApplicable(3) indicates that cpsGroupCtrl.0 is null
                     and therefore no comparison was performed."
        ::= { csdtf100Entry 5 }

csdtf100SerialNumber OBJECT-TYPE
        SYNTAX INTEGER
        ACCESS read-only
        STATUS mandatory
        DESCRIPTION "The serial number of this device"
        ::= { csdtf100Entry 6 }

csdtf100ConnA OBJECT-TYPE
        SYNTAX CpsConnector
        ACCESS read-only
        STATUS mandatory
        DESCRIPTION "The style of Fiber connector built into this device"
        ::= { csdtf100Entry 7 }

csdtf100ConnB OBJECT-TYPE
        SYNTAX CpsConnector
        ACCESS read-only
        STATUS mandatory
        DESCRIPTION "The style of Copper connector built into this device"
        ::= { csdtf100Entry 8 }

csdtf100CopperLink OBJECT-TYPE
        SYNTAX INTEGER { linkUp(1), linkDown(2) }
        ACCESS read-only
        STATUS mandatory
        DESCRIPTION "Status of Copper Link for this device"
        ::= { csdtf100Entry 9 }

csdtf100FiberLink OBJECT-TYPE
        SYNTAX INTEGER { linkUp(1), linkDown(2) }
        ACCESS read-only
        STATUS mandatory
        DESCRIPTION "Status of Fiber Link for this device"
        ::= { csdtf100Entry 10 }

csdtf100Fault OBJECT-TYPE
        SYNTAX INTEGER { yes(1), no(2) }
        ACCESS read-only
        STATUS mandatory
        DESCRIPTION "Value is yes(1) when either CopperLink or FiberLink 
                     has value linkDown(2)"
        ::= { csdtf100Entry 11 }

csdtf100TAOSFiber OBJECT-TYPE
        SYNTAX INTEGER { enabled(1), disabled(2) }
        ACCESS read-write
        STATUS mandatory
        DESCRIPTION "Transmit All Ones on Fiber as an error signal when
                     Copper interface is down. When this error signal
                     is transmitted, the AIS of the device
                     on the other end is activated, if supported."
        ::= { csdtf100Entry 12 }

csdtf100TAOSCopper OBJECT-TYPE
        SYNTAX INTEGER { enabled(1), disabled(2) }
        ACCESS read-write
        STATUS mandatory
        DESCRIPTION "Transmit All Ones on Copper as an error signal when
                     Fiber interface is down.  When this error signal
                     is transmitted, the AIS of the device
                     on the other end is activated, if supported."
        ::= { csdtf100Entry 13 }

csdtf100AISFiber OBJECT-TYPE
        SYNTAX INTEGER { alarm(1), normal(2) }
        ACCESS read-only
        STATUS mandatory
        DESCRIPTION "Alarm Indication Signal. When equal to alarm(1),
                     this means that the other end has TAOS enabled
                     and is currently transmitting an alarm condition."
        ::= { csdtf100Entry 14 }

csdtf100AISCopper OBJECT-TYPE
        SYNTAX INTEGER { alarm(1), normal(2) }
        ACCESS read-only
        STATUS mandatory
        DESCRIPTION "Alarm Indication Signal. When equal to alarm(1),
                     this means that the other end has TAOS enabled
                     and is currently transmitting an alarm condition."
        ::= { csdtf100Entry 15 }

csdtf100CopperLoopback OBJECT-TYPE
        SYNTAX INTEGER { yes(1), no(2), notSupported(3) }
        ACCESS read-write
        STATUS mandatory
        DESCRIPTION "Enable loopback on the copper interface. Copper Loopback
                     causes all data that is sent to the copper interface to
                     be transmitted back out the copper interface.
                     NOT SUPPORTED on initial version of the product. "
        ::= { csdtf100Entry 16 }

csdtf100CopperLongHaul OBJECT-TYPE
        SYNTAX INTEGER { yes(1), no(2) }
        ACCESS read-only
        STATUS mandatory
        DESCRIPTION "This variable indicates the current position of the
                     device's long/short haul configuration switch."
        ::= { csdtf100Entry 17 }

csdtf100T1E1 OBJECT-TYPE
        SYNTAX INTEGER { t1(1), e1(2) }
        ACCESS read-only
        STATUS mandatory
        DESCRIPTION "This variable indicates whether the current device
                     is the T1 or the E1 version."
        ::= { csdtf100Entry 18 }

csdtf100ConfigMode OBJECT-TYPE
        SYNTAX INTEGER { software(1), hardware(2) }
        ACCESS read-only
        STATUS mandatory
        DESCRIPTION "This device has a jumper or switch that disables 
                     software management of the device. When ConfigMode is
                     hardware(2), SNMP management is disabled, and all
                     configuration control comes from physical switches or
                     jumpers on the device."
        ::= { csdtf100Entry 19 }

csdtf100TPCoax OBJECT-TYPE
        SYNTAX INTEGER { tp(1), coax(2) }
        ACCESS read-only
        STATUS mandatory
        DESCRIPTION "Indicates the connector type installed on the
                     copper interface. For E1 converters, this can
                     be either Twisted Pair or Coax. For T1, it
                     is always Twisted Pair."
        ::= { csdtf100Entry 20 }

csdtf100CopperLineBuildout OBJECT-TYPE
        SYNTAX INTEGER { e13-0V120ohm(1), e12-37V75ohm(2), 
                         t1SH-DSX-0-133ANSIT1403(3), t1SH-DSX-133-266(4),
                         t1SH-DSX-266-399(5), t1SH-DSX-399-533(6), 
                         t1SH-DSX-533-655(7), t1SH-DSX-6V(8), t1LH-0dB(9),
                         t1LH-m7-5dB(10), t1LH-m15dB(11), t1LH-m22-5dB(12) }
        ACCESS read-only
        STATUS mandatory
        DESCRIPTION "The characteristics of the copper interface"
        ::= { csdtf100Entry 21 }

csdtf100FiberLoopback OBJECT-TYPE
        SYNTAX INTEGER { yes(1), no(2) }
        ACCESS read-write
        STATUS mandatory
        DESCRIPTION "Enable loopback on the Fiber interface. Fiber Loopback
                     causes all data that is sent to the Fiber interface to
                     be transmitted back out the Fiber interface."
        ::= { csdtf100Entry 22 }

csdtf100RmtSupported OBJECT-TYPE
        SYNTAX INTEGER { yes(1), no(2) }
        ACCESS read-only
        STATUS mandatory
        DESCRIPTION "Has the value yes(1) if this converter is capable
                     of managing the media converter at the remote end
                     of the fiber."
        ::= { csdtf100Entry 23 }

csdtf100RmtDetected OBJECT-TYPE
        SYNTAX INTEGER { yes(1), no(2) }
        ACCESS read-only
        STATUS mandatory
        DESCRIPTION "Has the value yes(1) if management communcations
                     have been established with a remote media converter.
                     Always no(2) if TAOS is enabled or the remote
                     converter does not support remote management."
        ::= { csdtf100Entry 24 }

csdtf100RmtMRevision OBJECT-TYPE
        SYNTAX INTEGER
        ACCESS read-only
        STATUS mandatory
        DESCRIPTION "Remote Marketing Revision.  Same as csdtf100MRevision, 
                     only for the remote device."
        ::= { csdtf100Entry 25 }

csdtf100RmtSerialNumber OBJECT-TYPE
        SYNTAX INTEGER
        ACCESS read-only
        STATUS mandatory
        DESCRIPTION "Serial Number reported by remote device."
        ::= { csdtf100Entry 26 }

csdtf100RmtConnA OBJECT-TYPE
        SYNTAX CpsConnector
        ACCESS read-only
        STATUS mandatory
        DESCRIPTION "The style of Fiber connector reported by remote device."
        ::= { csdtf100Entry 27 }

csdtf100RmtConnB OBJECT-TYPE
        SYNTAX CpsConnector
        ACCESS read-only
        STATUS mandatory
        DESCRIPTION "The style of Fiber connector reported by remote device."
        ::= { csdtf100Entry 28 }

csdtf100RmtCopperLink OBJECT-TYPE
        SYNTAX INTEGER { linkUp(1), linkDown(2) }
        ACCESS read-only
        STATUS mandatory
        DESCRIPTION "Link status of remote Copper Port."
        ::= { csdtf100Entry 29 }

csdtf100RmtFiberLink OBJECT-TYPE
        SYNTAX INTEGER { linkUp(1), linkDown(2) }
        ACCESS read-only
        STATUS mandatory
        DESCRIPTION "Link status of remote Fiber Port."
        ::= { csdtf100Entry 30 }

csdtf100RmtFault OBJECT-TYPE
        SYNTAX INTEGER { yes(1), no(2) }
        ACCESS read-only
        STATUS mandatory
        DESCRIPTION "Remote Fault status.  Value is yes(1) when either
                     CopperLink or FiberLink has value linkDown(2)"
        ::= { csdtf100Entry 31 }

csdtf100RmtTAOSFiber OBJECT-TYPE
        SYNTAX INTEGER { enabled(1), disabled(2) }
        ACCESS read-write
        STATUS mandatory
        DESCRIPTION "Remote Fiber TAOS configuration.  Transmit All 
                     Ones on Fiber as an error signal when Copper
                     interface is down. When this error signal is
                     transmitted, the AIS of the device on the other
                     end is activated, if supported."
        ::= { csdtf100Entry 32 }

csdtf100RmtTAOSCopper OBJECT-TYPE
        SYNTAX INTEGER { enabled(1), disabled(2) }
        ACCESS read-write
        STATUS mandatory
        DESCRIPTION "Remote Copper TAOS configuration.  Transmit All
                     Ones on Copper as an error signal when Fiber
                     interface is down.  When this error signal
                     is transmitted, the AIS of the device
                     on the other end is activated, if supported."
        ::= { csdtf100Entry 33 }

csdtf100RmtAISFiber OBJECT-TYPE
        SYNTAX INTEGER { alarm(1), normal(2) }
        ACCESS read-only
        STATUS mandatory
        DESCRIPTION "Remote Fiber AIS status.  Alarm Indication Signal.
                     When equal to alarm(1), this means that the other
                     end has TAOS enabled and is currently transmitting
                     an alarm condition."
        ::= { csdtf100Entry 34 }

csdtf100RmtAISCopper OBJECT-TYPE
        SYNTAX INTEGER { alarm(1), normal(2) }
        ACCESS read-only
        STATUS mandatory
        DESCRIPTION "Remote Copper AIS status.  Alarm Indication Signal.
                     When equal to alarm(1), this means that the other
                     end has TAOS enabled and is currently transmitting
                     an alarm condition."
        ::= { csdtf100Entry 35 }

csdtf100RmtCopperLoopback OBJECT-TYPE
        SYNTAX INTEGER { yes(1), no(2) }
        ACCESS read-write
        STATUS mandatory
        DESCRIPTION "Remote Copper Loopback configuration.  Enable loopback
                     on the copper interface. Copper Loopback causes all
                     data that is sent to the copper interface to be 
                     transmitted back out the copper interface.
                     NOT SUPPORTED on initial version of the product."
        ::= { csdtf100Entry 36 }

csdtf100RmtCopperLongHaul OBJECT-TYPE
        SYNTAX INTEGER { yes(1), no(2) }
        ACCESS read-only
        STATUS mandatory
        DESCRIPTION "This variable indicates the current position of the 
                     remote device's Short/Long haul configuration switch."
        ::= { csdtf100Entry 37 }

csdtf100RmtConfigMode OBJECT-TYPE
        SYNTAX INTEGER { software(1), hardware(2) }
        ACCESS read-only
        STATUS mandatory
        DESCRIPTION "Remote Configuration Mode. This device has a jumper
                     or switch that disables software management of the
                     device. When ConfigMode is hardware(2), SNMP management
                     is disabled, and all configuration control comes
                     from physical switches or jumpers on the device."
        ::= { csdtf100Entry 38 }

csdtf100RmtTPCoax OBJECT-TYPE
        SYNTAX INTEGER { tp(1), coax(2) }
        ACCESS read-only
        STATUS mandatory
        DESCRIPTION "Indicates the connector type installed on the remote
                     copper interface. For E1 converters, this can be either
                     Twisted Pair or Coax. For T1, it is always Twisted Pair."
        ::= { csdtf100Entry 39 }

csdtf100RmtCopperLineBuildout OBJECT-TYPE
        SYNTAX INTEGER { e13-0V120ohm(1), e12-37V75ohm(2), 
                         t1SH-DSX-0-133ANSIT1403(3), t1SH-DSX-133-266(4),
                         t1SH-DSX-266-399(5), t1SH-DSX-399-533(6), 
                         t1SH-DSX-533-655(7), t1SH-DSX-6V(8), t1LH-0dB(9),
                         t1LH-m7-5dB(10), t1LH-m15dB(11), t1LH-m22-5dB(12) }
        ACCESS read-only
        STATUS mandatory
        DESCRIPTION "The electrical characteristics of the remote Copper
                     interface.  Values are the same as the values for
                     csdtf100CopperLineBuildout(21)"
        ::= { csdtf100Entry 40 }

csdtf100RmtFiberLoopback OBJECT-TYPE
        SYNTAX INTEGER { yes(1), no(2) }
        ACCESS read-write
        STATUS mandatory
        DESCRIPTION "Enable loopback on the remote Fiber interface. Fiber
                     Loopback causes all data that is sent to the Fiber
                     interface to be transmitted back out the Fiber interface."
        ::= { csdtf100Entry 41 }

csdtf100CacheClean OBJECT-TYPE
        SYNTAX INTEGER { clean(1), dirty(2) }
        ACCESS read-only
        STATUS mandatory
        DESCRIPTION "When the value is clean(1)Device and Management Module
                     cache are synchronized, no automatic corrections to 
                     configuration will occur.  When the value is dirty(2)
                     Device and Management Module cache are not synchronized.
                     The configuration currently displayed by the application 
                     has not been validated by the device. The device may 
                     need to correct the configuration, in which case the 
                     displayed configuration will change."
        ::= { csdtf100Entry 42 }

-- ================================================================
-- Table for the cpsmp110 

cpsmp110Table OBJECT-TYPE
        SYNTAX SEQUENCE OF Cpsmp110Entry
        ACCESS not-accessible
        STATUS mandatory
        DESCRIPTION "Sparse table containing one entry for each CPSMP110
                     IFO (Instant Fail-Over) Power Supply in the stack.
                     indexed by sub-device index, cabinet serial number, 
                     and slot. Note that some columns of this table 
                     support multiple subdevices, and some do not. 
                     For example, there is exactly one SerialNumber 
                     for each CPSMP110. No subdevices exist, so the 
                     placeholder value 1 is used as the subdevice index.
                     However, a CPSMP110 has zero or more current
                     sensors, which (if they exist) are indexed as
                     different subdevices, starting with 1.
                     Columns with subdevices have names ending in 'Tbl'"
        ::= { cpsSlotDetail 10 }

cpsmp110Entry OBJECT-TYPE
        SYNTAX Cpsmp110Entry
        ACCESS not-accessible
        STATUS mandatory
        DESCRIPTION "Status and configuration entries for a single CPSMP100"
        INDEX { cpsmp110SubDeviceIndex, cpsmp110BiaIndex, cpsmp110SlotIndex }
        ::= { cpsmp110Table 1 }

Cpsmp110Entry ::=
        SEQUENCE {
                  cpsmp110SubDeviceIndex          INTEGER,
                  cpsmp110BiaIndex                INTEGER,
                  cpsmp110SlotIndex               INTEGER,
                  cpsmp110Groups                  DisplayString,
                  cpsmp110MRevision               INTEGER,
                  cpsmp110CfgMatch                INTEGER,
                  cpsmp110SerialNumber            INTEGER,
                  cpsmp110ConfigMode              INTEGER,
                  cpsmp110MasterTempFault         INTEGER,
                  cpsmp110MasterCurrentFault      INTEGER,
                  cpsmp110MasterFanFault          INTEGER,
                  cpsmp110FirmwareRevision        INTEGER,
                  cpsmp110PSSupplyTbl             INTEGER,
                  cpsmp110PSRoleTbl               INTEGER,
                  cpsmp110PSReadyTbl              INTEGER,
                  cpsmp110PSInUseTbl              INTEGER,
                  cpsmp110TemperatureTbl          INTEGER,
                  cpsmp110CurrentTbl              INTEGER,
                  cpsmp110FanStatusTbl            INTEGER,
                  cpsmp110TempFaultTbl            INTEGER,
                  cpsmp110CurrFaultTbl            INTEGER,
                  cpsmp110PSCount                 INTEGER,
                  cpsmp110TempSensorCount         INTEGER,
                  cpsmp110CurrSensorCount         INTEGER,
                  cpsmp110FanCount                INTEGER,
                  cpsmp110CacheClean              INTEGER
                  }

cpsmp110SubDeviceIndex OBJECT-TYPE
        SYNTAX INTEGER
        ACCESS read-only
        STATUS mandatory
        DESCRIPTION "Generally, individual devices in this MIB are
                     distinguished by BiaIndex and SlotIndex. This 
                     device differs from many in that it contains
                     multiple subdevices (in this case, fans, temperature
                     sensors, current sensors, and power supplies).
                     The number of subdevices varies with the manufactured
                     configuration. Subdevices within devices are indexed
                     by BiaIndex, SlotIndex, and SubDeviceIndex.
                     When the subdevice column is read from the table, 
                     the value '1' is always returned."
        ::= { cpsmp110Entry 1 } 

cpsmp110BiaIndex OBJECT-TYPE
        SYNTAX INTEGER
        ACCESS read-only
        STATUS mandatory
        DESCRIPTION "The serial number (BIA) of the cabinet in which the 
                     device is installed.
                     There are no subdevices for this value, so the
                     placeholder value 1 is always used for that index."
        ::= { cpsmp110Entry 2 }

cpsmp110SlotIndex OBJECT-TYPE
        SYNTAX INTEGER
        ACCESS read-only
        STATUS mandatory
        DESCRIPTION "The slot in which the device is installed. Power Supplies
                     occupy special slots numbered 125 and higher.
                     There are no subdevices for this value, so the
                     placeholder value 1 is always used for that index."
        ::= { cpsmp110Entry 3 }

cpsmp110Groups OBJECT-TYPE
        SYNTAX DisplayString
        ACCESS read-write
        STATUS mandatory
        DESCRIPTION "User-defined keywords that group this device together with
                     other devices under a user-defined scheme. By placing 
                     matching keywords in cpsGroupCtrl.0, the agent can be
                     instructed to apply configuration changes simultaneously
                     to all group members rather than to individual devices.
                     Every Groups string has three automatically defined
                     implied values: 
                     1) The model family of the device, e.g. 'CPSMP110'
                     2) The serial number of the cabinet in which the device
                        is installed, in decimal with no leading zeroes, 
                        e.g. '12345', and 
                     3) same as 2, with the slot in which the device is 
                        installed appended, enclosed in square brackets. 
                        e.g. '12345[9]'
                     There are no subdevices for this value, so the
                     placeholder value 1 is always used for that index."
        ::= { cpsmp110Entry 4 }

cpsmp110MRevision OBJECT-TYPE
        SYNTAX INTEGER
        ACCESS read-only
        STATUS mandatory
        DESCRIPTION "The marketing revision of this device.
                     There are no subdevices for this value, so the
                     placeholder value 1 is always used for that index."
        ::= { cpsmp110Entry 5 }

cpsmp110CfgMatch OBJECT-TYPE
        SYNTAX INTEGER { yes(1), no(2), notApplicable(3) }
        ACCESS read-only
        STATUS mandatory
        DESCRIPTION "yes(1) indicates that the conditions specified in 
                     cpsGroupCtrl.0 match the Groups value for this
                     device. no(2) means that there is no match.
                     notApplicable(3) indicates that cpsGroupCtrl.0 is null
                     and therefore no comparison was performed.
                     There are no subdevices for this value, so the
                     placeholder value 1 is always used for that index."
        ::= { cpsmp110Entry 6 }

cpsmp110SerialNumber OBJECT-TYPE
        SYNTAX INTEGER
        ACCESS read-only
        STATUS mandatory
        DESCRIPTION "The serial number of this device.
                     There are no subdevices for this value, so the
                     placeholder value 1 is always used for that index."
        ::= { cpsmp110Entry 7 }

cpsmp110ConfigMode OBJECT-TYPE
        SYNTAX INTEGER { software(1), hardware(2) }
        ACCESS read-only
        STATUS mandatory
        DESCRIPTION "This device may have a jumper or switch that disables 
                     software management of the device. When ConfigMode is
                     hardware(2), SNMP management is disabled, and all
                     configuration control comes from physical switches or
                     jumpers on the device.
                     There are no subdevices for this value, so the
                     placeholder value 1 is always used for that index."
        ::= { cpsmp110Entry 8 }

cpsmp110MasterTempFault OBJECT-TYPE
        SYNTAX INTEGER { yes(1), no(2) }
        ACCESS read-only
        STATUS mandatory
        DESCRIPTION "The master temperature fault indicator for this device.
                     A value of yes(1) indicates that at least one temperature
                     sensor encountered a fault condition since the last
                     time the device was queried by the management module.
                     The statuses of individual temperature sensors can
                     be found in cpsmp110TemperatureTbl. Note that in the
                     unusual case that a sensor spikes (i.e. encounters a
                     fault, and then quickly returns to normal), it will be
                     difficult to determine which sensor faulted. However,
                     the fact that any sensor faulted is sufficient cause
                     to examine the cabinet further.
                     There are no subdevices for this value, so the
                     placeholder value 1 is always used for that index."
        ::= { cpsmp110Entry 9 }

cpsmp110MasterCurrentFault OBJECT-TYPE
        SYNTAX INTEGER { yes(1), no(2) }
        ACCESS read-only
        STATUS mandatory
        DESCRIPTION "The master current fault indicator for this device.
                     A value of yes(1) indicates that at least one current
                     sensor encountered a fault condition since the last
                     time the device was queried by the management module.
                     The statuses of individual current sensors can
                     be found in cpsmp110CurrentTbl. Note that in the
                     unusual case that a sensor spikes (i.e. encounters a
                     fault, and then quickly returns to normal), it will be
                     difficult to determine which sensor faulted. However,
                     the fact that any sensor faulted is sufficient cause
                     to examine the cabinet further.
                     There are no subdevices for this value, so the
                     placeholder value 1 is always used for that index."
        ::= { cpsmp110Entry 10 }

cpsmp110MasterFanFault OBJECT-TYPE
        SYNTAX INTEGER { yes(1), no(2) }
        ACCESS read-only
        STATUS mandatory
        DESCRIPTION "The master fan fault indicator for this device.
                     A value of yes(1) indicates that at least one fan current
                     sensor encountered a fault condition since the last
                     time the device was queried by the management module.
                     The statuses of individual fan current sensors can
                     be found in cpsmp110FanStatusTbl. Note that in the
                     unusual case that a sensor spikes (i.e. encounters a
                     fault, and then quickly returns to normal), it will be
                     difficult to determine which sensor faulted. However,
                     the fact that any sensor faulted is sufficient cause
                     to examine the cabinet further.
                     There are no subdevices for this value, so the
                     placeholder value 1 is always used for that index."
        ::= { cpsmp110Entry 11 }

cpsmp110FirmwareRevision OBJECT-TYPE
        SYNTAX INTEGER
        ACCESS read-only
        STATUS mandatory
        DESCRIPTION "The firmware revision level for this device.
                     There are no subdevices for this value, so the
                     placeholder value 1 is always used for that index."
        ::= { cpsmp110Entry 12 }

cpsmp110PSSupplyTbl OBJECT-TYPE
        SYNTAX INTEGER { ac(1), dc(2), reserved3(3), reserved4(4), 
                         notInstalled(5) }
        ACCESS read-only
        STATUS mandatory
        DESCRIPTION "The supply voltage that this unit is designed to accept.
                     If AC(1), the supply accepts VAC.
                     If DC(2), the supply accepts.
                     A single CPSMP110 control unit can support multiple
                     subdevices of this type.  There will be one entry per 
                     subdevice."
       ::= { cpsmp110Entry 13 }

cpsmp110PSRoleTbl OBJECT-TYPE
        SYNTAX INTEGER { master(1), slave(2), shared(3), notInstalled(4) }
        ACCESS read-write
        STATUS mandatory
        DESCRIPTION "Some power supplies support a Master/Slave relationship:
                     When one power supply is set to master(1) and the
                     other is set to slave(2), the master will supply
                     all power to the cabinet, and the slave will take 
                     over if the master stops supplying power. This is
                     useful when (for example) one supply is attached to a
                     wall socket and the other to a battery backup. The
                     cabinet can be directed to only draw power from
                     batteries when there is no alternative.
                     When both power supplies are set to master(1), the
                     results are determined automatically. 
                     WARNING: It is up to the system administrator to 
                     ensure that at least one power supply is set to
                     master(1). It is illegal to set all power supplies to 
                     slave(2). If this occurs, the cabinet may lose
                     all power under certain circumstances, even if
                     power is available.
                     In some cases, the Master/Slave relationship cannot
                     be configured via management; it is determined by
                     other means, such as the slot locations in which the 
                     supplies are installed, or switches on the supplies.
                     In this case, attempts to change the value of this
                     variable from management will be ignored. The 
                     ConfigMode variable will have the value hardware(2)
                     in this case. 
                     If a supply does not support (or can disable) Master/Slave
                     functionality, the value shared(3) is returned. In this
                     case, all ready power supplies share the load evenly.
                     A single CPSMP110 control unit can support multiple
                     subdevices of this type."
        ::= { cpsmp110Entry 14 }

cpsmp110PSReadyTbl OBJECT-TYPE
        SYNTAX INTEGER { yes(1), no(2) }
        ACCESS read-only
        STATUS mandatory
        DESCRIPTION "The readiness of this power supply module.  A value of 
                     yes(1) indicates the module is ready to supply power
                     to the cabinet. A value of no(2) indicates that the
                     supply has no output power to offer, either because it
                     is malfunctioning or because it has no input power.
                     A single CPSMP110 control unit can support multiple
                     subdevices of this type."
        ::= { cpsmp110Entry 15 }

cpsmp110PSInUseTbl OBJECT-TYPE
        SYNTAX INTEGER { yes(1), no(2) }
        ACCESS read-only
        STATUS mandatory
        DESCRIPTION "The use status of this power supply module. A value of 
                     yes(1) indicates the module is supplying power to the
                     cabinet. This variable is useful in configurations where
                     master/slave role functionality is supported to determine
                     whether the Master or the Slave is active. In shared
                     configurations, the value of PSReadyTbl is strongly 
                     preferred as an indication of the status of the supply.
                     A single CPSMP110 control unit can support multiple
                     subdevices of this type."
      ::= { cpsmp110Entry 16 }

cpsmp110TemperatureTbl OBJECT-TYPE
        SYNTAX INTEGER
        ACCESS read-only
        STATUS mandatory
        DESCRIPTION "The temperature, in tenths of degrees centigrade, read
                     by this temperature sensor.
                     A single CPSMP110 control unit can support multiple
                     subdevices of this type."

        ::= { cpsmp110Entry 17 }

cpsmp110CurrentTbl OBJECT-TYPE
        SYNTAX INTEGER
        ACCESS read-only
        STATUS mandatory
        DESCRIPTION "The current, in milliwatts, read by this current sensor.
                     A single CPSMP110 control unit can support multiple
                     subdevices of this type."
        ::= { cpsmp110Entry 18 }

cpsmp110FanStatusTbl OBJECT-TYPE
        SYNTAX INTEGER { ok(1), fault(2), notInstalled(3) }
        ACCESS read-only
        STATUS mandatory
        DESCRIPTION "The status of a fan. A value of fault(2) indicates
                     that the control unit has detected a problem with the
                     fan, usually that it is is drawing excessive current.
                     A single CPSMP110 control unit can support multiple
                     subdevices of this type."
        ::= { cpsmp110Entry 19 }

cpsmp110TempFaultTbl OBJECT-TYPE
        SYNTAX INTEGER { yes(1), no(2) }
        ACCESS read-only
        STATUS mandatory
        DESCRIPTION "Each entry in this column corresponds to an entry
                     with the same indices in cpsmp110TemperatureTable.
                     It indicates whether or not the temperature read
                     by the sensor is within the acceptable range.
                     A single CPSMP110 control unit can support multiple
                     subdevices of this type."
        ::= { cpsmp110Entry 20 }

cpsmp110CurrFaultTbl OBJECT-TYPE
        SYNTAX INTEGER { yes(1), no(2) }
        ACCESS read-only
        STATUS mandatory
        DESCRIPTION "Each entry in this column corresponds to an entry
                     with the same indices in cpsmp110CurrentTable.
                     It indicates whether or not the current read
                     by the sensor is within the acceptable range.
                     A single CPSMP110 control unit can support multiple
                     subdevices of this type."
        ::= { cpsmp110Entry 21 }

cpsmp110PSCount OBJECT-TYPE
        SYNTAX INTEGER
        ACCESS read-only
        STATUS mandatory
        DESCRIPTION "The maximum number of power supplies supported 
                     in this configuration."
        ::= { cpsmp110Entry 22 }

cpsmp110TempSensorCount OBJECT-TYPE
        SYNTAX INTEGER
        ACCESS read-only
        STATUS mandatory
        DESCRIPTION "The number of temperature sensors supported in this device."
        ::= { cpsmp110Entry 23 }

cpsmp110CurrSensorCount OBJECT-TYPE
        SYNTAX INTEGER
        ACCESS read-only
        STATUS mandatory
        DESCRIPTION "The number of current sensors supported in this device."
        ::= { cpsmp110Entry 24 }

cpsmp110FanCount OBJECT-TYPE
        SYNTAX INTEGER
        ACCESS read-only
        STATUS mandatory
        DESCRIPTION "The number of fans supported in this device."
        ::= { cpsmp110Entry 25 }

cpsmp110CacheClean OBJECT-TYPE
        SYNTAX INTEGER { clean(1), dirty(2) }
        ACCESS read-only
        STATUS mandatory
        DESCRIPTION "When the value is clean(1)Device and Management Module
                     cache are synchronized, no automatic corrections to 
                     configuration will occur.  When the value is dirty(2)
                     Device and Management Module cache are not synchronized.
                     The configuration currently displayed by the application 
                     has not been validated by the device. The device may 
                     need to correct the configuration, in which case the 
                     displayed configuration will change."
        ::= { cpsmp110Entry 26 }

-- ================================================================
-- Table for the cbftf100

cbftf100Table OBJECT-TYPE
        SYNTAX SEQUENCE OF Cbftf100Entry
        ACCESS not-accessible
        STATUS mandatory
        DESCRIPTION "Sparse table containing one entry for each CBFTF100
                     switch in the stack.
                     Indexed by sub-device index, cabinet serial number, 
                     and slot. Note that some columns of this table 
                     support multiple subdevices, and some do not. 
                     For example, there is exactly one SerialNumber 
                     for each CBFTF100. No subdevices exist, so the 
                     placeholder value 1 is used as the subdevice index.
                     However, a CBFTF100 has multiple switch ports, which
                     are indexed as different subdevices, starting with 1.
                     Columns with subdevices have names ending in 'Tbl'"
        ::= { cpsSlotDetail 11 }

cbftf100Entry OBJECT-TYPE
        SYNTAX Cbftf100Entry
        ACCESS not-accessible
        STATUS mandatory
        DESCRIPTION "Status and configuration entries for a single CBFTF100"
        INDEX { cbftf100SubDeviceIndex, cbftf100BiaIndex, cbftf100SlotIndex }
        ::= { cbftf100Table 1 }

Cbftf100Entry ::=
        SEQUENCE {
                  cbftf100SubDeviceIndex          INTEGER,
                  cbftf100BiaIndex                INTEGER,
                  cbftf100SlotIndex               INTEGER,
                  cbftf100Groups                  DisplayString,
                  cbftf100MRevision               INTEGER,
                  cbftf100CfgMatch                INTEGER,
                  cbftf100SerialNumber            INTEGER,
                  cbftf100ConfigMode              INTEGER,
                  cbftf100FirmwareRevision        INTEGER,
                  cbftf100SelfTestFailed          INTEGER,
                  cbftf100SpanningTree            INTEGER,
                  cbftf100MirrorCfg               INTEGER,
                  cbftf100SACMasterCfg            INTEGER,
                  cbftf100FormFactor              INTEGER,
                  cbftf100AutoNegotTbl            INTEGER,
                  cbftf100FullDuplexTbl           INTEGER,
                  cbftf100100MbpsTbl              INTEGER,
                  cbftf100Adv10HDXTbl             INTEGER,
                  cbftf100Adv10FDXTbl             INTEGER,
                  cbftf100Adv100HDXTbl            INTEGER,
                  cbftf100Adv100FDXTbl            INTEGER,
                  cbftf100CrossTbl                INTEGER,
                  cbftf100PauseCfgTbl             INTEGER,
                  cbftf100PauseStatTbl            INTEGER,
                  cbftf100FarEndFaultTbl          INTEGER,
                  cbftf100ConnectorTbl            INTEGER,
                  cbftf100SACCfgTbl               INTEGER,
                  cbftf100SACStatTbl              INTEGER,
                  cbftf100MirrorSelTbl            INTEGER,
                  cbftf100MirrorInTbl             INTEGER,
                  cbftf100MirrorOutTbl            INTEGER,
                  cbftf100LinkTbl                 INTEGER,
                  cbftf100PortCount               INTEGER,
                  cbftf100LinkPassThrough         INTEGER,
                  cbftf100CacheClean              INTEGER,
                  cbftf100RedundantPath           INTEGER
                  }

cbftf100SubDeviceIndex OBJECT-TYPE
        SYNTAX INTEGER
        ACCESS read-only
        STATUS mandatory
        DESCRIPTION "Generally, individual devices in this MIB are
                     distinguished by BiaIndex and SlotIndex. This 
                     device differs from many in that it contains
                     multiple subdevices (in this case, switch ports).
                     The number of subdevices varies with the manufactured
                     configuration. Subdevices within devices are indexed
                     by BiaIndex, SlotIndex, and SubDeviceIndex.
                     When the subdevice column is read from the table, 
                     the value '1' is always returned."
        ::= { cbftf100Entry 1 } 

cbftf100BiaIndex OBJECT-TYPE
        SYNTAX INTEGER
        ACCESS read-only
        STATUS mandatory
        DESCRIPTION "The serial number (BIA) of the cabinet in which the 
                     device is installed.
                     There are no subdevices for this value, so the
                     placeholder value 1 is always used for that index."
        ::= { cbftf100Entry 2 }

cbftf100SlotIndex OBJECT-TYPE
        SYNTAX INTEGER
        ACCESS read-only
        STATUS mandatory
        DESCRIPTION "The slot in which the device is installed. Power Supplies
                     occupy special slots numbered 125 and higher.
                     There are no subdevices for this value, so the
                     placeholder value 1 is always used for that index."
        ::= { cbftf100Entry 3 }

cbftf100Groups OBJECT-TYPE
        SYNTAX DisplayString
        ACCESS read-write
        STATUS mandatory
        DESCRIPTION "User-defined keywords that group this device together with
                     other devices under a user-defined scheme. By placing 
                     matching keywords in cpsGroupCtrl.0, the agent can be
                     instructed to apply configuration changes simultaneously
                     to all group members rather than to individual devices.
                     Every Groups string has three automatically defined
                     implied values: 
                     1) The model family of the device, e.g. 'cbftf100'
                     2) The serial number of the cabinet in which the device
                        is installed, in decimal with no leading zeroes, 
                        e.g. '12345', and 
                     3) same as 2, with the slot in which the device is 
                        installed appended, enclosed in square brackets. 
                        e.g. '12345[9]'
                     There are no subdevices for this value, so the
                     placeholder value 1 is always used for that index."
        ::= { cbftf100Entry 4 }

cbftf100MRevision OBJECT-TYPE
        SYNTAX INTEGER
        ACCESS read-only
        STATUS mandatory
        DESCRIPTION "The marketing revision of this device.
                     There are no subdevices for this value, so the
                     placeholder value 1 is always used for that index."
        ::= { cbftf100Entry 5 }

cbftf100CfgMatch OBJECT-TYPE
        SYNTAX INTEGER { yes(1), no(2), notApplicable(3) }
        ACCESS read-only
        STATUS mandatory
        DESCRIPTION "yes(1) indicates that the conditions specified in 
                     cpsGroupCtrl.0 match the Groups value for this
                     device. no(2) means that there is no match.
                     notApplicable(3) indicates that cpsGroupCtrl.0 is null
                     and therefore no comparison was performed.
                     There are no subdevices for this value, so the
                     placeholder value 1 is always used for that index."
        ::= { cbftf100Entry 6 }

cbftf100SerialNumber OBJECT-TYPE
        SYNTAX INTEGER
        ACCESS read-only
        STATUS mandatory
        DESCRIPTION "The serial number of this device.
                     There are no subdevices for this value, so the
                     placeholder value 1 is always used for that index."
        ::= { cbftf100Entry 7 }

cbftf100ConfigMode OBJECT-TYPE
        SYNTAX INTEGER { software(1), hardware(2) }
        ACCESS read-only
        STATUS mandatory
        DESCRIPTION "This device may have a jumper or switch that disables 
                     software management of the device. When ConfigMode is
                     hardware(2), SNMP management is disabled, and all
                     configuration control comes from physical switches or
                     jumpers on the device.
                     There are no subdevices for this value, so the
                     placeholder value 1 is always used for that index."
        ::= { cbftf100Entry 8 }

cbftf100FirmwareRevision OBJECT-TYPE
        SYNTAX INTEGER
        ACCESS read-only
        STATUS mandatory
        DESCRIPTION "The firmware revision level for this device.
                     There are no subdevices for this value, so the
                     placeholder value 1 is always used for that index."
        ::= { cbftf100Entry 9 }

cbftf100SelfTestFailed OBJECT-TYPE
        SYNTAX INTEGER { yes(1), no(2) }
        ACCESS read-only
        STATUS mandatory
        DESCRIPTION "This variable indicates the status of the pass/fail
                     power on test.  If the power on test fails,
                     normal operation of this device is probably not 
                     possible. "
        ::= { cbftf100Entry 10 }

cbftf100SpanningTree OBJECT-TYPE
        SYNTAX INTEGER { enabled(1), disabled(2), notSupported(3) }
        ACCESS read-write
        STATUS mandatory
        DESCRIPTION "This variable allows the agent to enable or disable 
                     Spanning Tree if it is supported. Not all versions 
                     of the hardware support Spanning Tree."
        ::= { cbftf100Entry 11 }

cbftf100MirrorCfg OBJECT-TYPE
        SYNTAX INTEGER { enabled(1), disabled(2), notSupported(3) }
        ACCESS read-write
        STATUS mandatory
        DESCRIPTION "Global enable/disable for mirror port functionality.
                     When this variable is set to disabled, the values of 
                     cbftf100MirrorSelTbl, cbftf100MirrorInTbl, and 
                     cbftf100MirrorOutTbl are ignored."
       ::= { cbftf100Entry 12 }

cbftf100SACMasterCfg OBJECT-TYPE
        SYNTAX INTEGER  { enabled(1), disabled(2) }
        ACCESS read-write
        STATUS mandatory
        DESCRIPTION "Global enable/disable for Source Address Change 
                     detection functionality.  When this variable is set to 
                     disabled the values in cbtf100SACCfgTbl are ignored."
        ::= { cbftf100Entry 13 }

cbftf100FormFactor OBJECT-TYPE
        SYNTAX INTEGER { s1W2a(1), s1W1N2a(2), s1W1N1a(3), s2W2N4a(4),
                         s2W1N5a(5) }
        ACCESS read-only
        STATUS mandatory
        DESCRIPTION "A code corresponding to a physical configuration 
                     of the product. This code indicates the number of 
                     slots occupied and the number of physical connectors 
                     present.
                     In the labels for the values above, s indicates the
                     number of slots occupied, W is a count of Wide
                     port positions (which can built as almost any type
                     of connector), and N is a count of narrow port 
                     positions (which are typically twisted pair ports).
                     The lowercase letter at the end differentiates
                     different form factors that would otherwise have
                     identical descriptions under this limited scheme."
        ::= { cbftf100Entry 14 }

cbftf100AutoNegotTbl OBJECT-TYPE
        SYNTAX INTEGER  { enabled(1), disabled(2), notSupported(3) }
        ACCESS read-write
        STATUS mandatory
        DESCRIPTION "Enables or disables autonegtiation of link speed and 
                     duplex for twisted pair ports.  Not supported on Fiber
                     ports.  There are multiple subdevices in this table, 
                     numbering one entry per port."
        ::= { cbftf100Entry 15 }

cbftf100FullDuplexTbl OBJECT-TYPE
        SYNTAX INTEGER { fullDuplex(1), halfDuplex(2), negotiating(3) }
        ACCESS read-write
        STATUS mandatory
        DESCRIPTION "In most cases this is a configuration setting that 
                     controls the duplex mode; fullDuplex is full duplex and 
                     halfDuplex is half duplex.  On twisted pair ports with 
                     autonegotiation enabled, this is a status indication 
                     showing the duplex value decided upon during the 
                     negotiation.  When link is down, autonegotiation has
                     not been completed yet, and the duplex setting is 
                     therefore unknown and the value is negotiating(3).  
                     There are multiple subdevices in this table, numbering 
                     one entry per port."
        ::= { cbftf100Entry 16 }

cbftf100100MbpsTbl OBJECT-TYPE
        SYNTAX INTEGER { mbps100(1), mbps10(2), negotiating(3) }
        ACCESS read-write
        STATUS mandatory
        DESCRIPTION "In most cases this is a configuration setting that 
                     controls the link speed.  On twisted pair ports with 
                     autonegotiation enabled, this is a status indication
                     showing the link speed decided upon during negotiation.  
                     When link is down, autonegotiation has not been completed
                     yet, and the link speed is therefore unknown and is
                     negotiating(3).  This variable is an indicator only for
                     fiber ports; all fiber ports report mbps100(1) at all 
                     times.  There are multiple subdevices in this table, 
                     numbering one entry per port."
        ::= { cbftf100Entry 17 }

cbftf100Adv10HDXTbl OBJECT-TYPE
        SYNTAX INTEGER { yes(1), no(2), notSupported(3) }
        ACCESS read-write
        STATUS mandatory
        DESCRIPTION "This configuration setting controls whether or not each 
                     port advertises willingness to connect at 10Mbps, half 
                     duplex.  This setting is not supported on fiber ports, 
                     and is ignored when autonegotiation is disabled.  There
                     are multiple subdevices in this table, numbering one 
                     entry per port."
        ::= { cbftf100Entry 18 }

cbftf100Adv10FDXTbl OBJECT-TYPE
        SYNTAX INTEGER { yes(1), no(2), notSupported(3) }
        ACCESS read-write
        STATUS mandatory
        DESCRIPTION "This configuration setting controls whether or not each 
                     port advertises willingness to connect at 10Mbps, full 
                     duplex.  This setting is not supported on fiber ports, 
                     and is ignored when autonegotiation is disabled.  There 
                     are multiple subdevices in this table, numbering one
                     entry per port."
        ::= { cbftf100Entry 19 }

cbftf100Adv100HDXTbl OBJECT-TYPE
        SYNTAX INTEGER { yes(1), no(2), notSupported(3) }
        ACCESS read-write
        STATUS mandatory
        DESCRIPTION "This configuration setting controls whether or not each 
                     port advertises willingness to connect at 100Mbps, half 
                     duplex.  This setting is not supported on fiber ports, 
                     and is ignored when autonegotiation is disabled.  There
                     are multiple subdevices in this table, numbering one
                     entry per port."
        ::= { cbftf100Entry 20 }

cbftf100Adv100FDXTbl OBJECT-TYPE
        SYNTAX INTEGER { yes(1), no(2), notSupported(3) }
        ACCESS read-write
        STATUS mandatory
        DESCRIPTION "This configuration setting controls whether or not each 
                     port advertises willingness to connect at 100Mbps, full 
                     duplex.  This setting is not supported on fiber ports, 
                     and is ignored when autonegotiation is disabled.  There
                     are multiple subdevices in this table, numbering one
                     entry per port."
        ::= { cbftf100Entry 21 }

cbftf100CrossTbl OBJECT-TYPE
        SYNTAX INTEGER { auto(1), mdi(2), mdix(3), notSupported(4) }
        ACCESS read-write
        STATUS mandatory
        DESCRIPTION "Configuration setting for copper TX/RX pair correction.  
                     A setting of auto(1) causes the port to automatically
                     correct TX/RX pairs if necessary.  If autonegotiation 
                     is disabled on the port, the auto(1) setting is not 
                     supported.  A setting of mdi(2) causes the TX/RX pairs 
                     to be passed straight through with no correction.  A 
                     setting of mdix(3) causes the TX/RX pairs to be swapped.
                     This setting is supprted for copper ports only; a 
                     read-only value of notSupported(4) is returned for
                     fiber ports.  There are multiple subdevices in this table, 
                     numbering one entry per port."
        ::= { cbftf100Entry 22 }

cbftf100PauseCfgTbl OBJECT-TYPE
        SYNTAX INTEGER { enabled(1), disabled(2), notSupported(3) }
        ACCESS read-write
        STATUS mandatory
        DESCRIPTION "The Pause feature allows Ethernet MACs that support it
                     to send data pacing 'Pause' messages to each other.
                     A setting of enabled(1) causes this port to advertise 
                     pause capability and a setting of disabled(2) disables
                     pause capability advertising.  On fiber ports, a 
                     read-only value of notSupported(3) is returned.  There
                     are multiple subdevices in this table, numbering one
                     entry per port."
        ::= { cbftf100Entry 23 }

cbftf100PauseStatTbl OBJECT-TYPE
        SYNTAX INTEGER { paused(1), normal(2) }
        ACCESS read-only
        STATUS mandatory
        DESCRIPTION "The Pause feature allows Ethernet MACs that support it
                     to send data pacing 'Pause' messages to each other.
                     A value of paused(1) indicated the port is in a paused
                     state, and a value of normal(2) indicates the port is 
                     operating normally.  There are multiple subdevices in
                     this table, numbering one entry per port."
        ::= { cbftf100Entry 24 }

cbftf100FarEndFaultTbl OBJECT-TYPE
        SYNTAX INTEGER { enabled(1), disabled(2), notSupported(3) }
        ACCESS read-write
        STATUS mandatory
        DESCRIPTION "When Far End Fault is set to enabled(1), a loss of
                     link on receive will cause the transmitter to shut down,
                     in order to inform the device at the far end of the
                     link that a fault has occurred. Far End Fault is only
                     supported on fiber ports. A read-only value of 
                     notSupported(3) is returned for copper ports.  There are
                     multiple subdevices in this table, numbering one entry
                     per port."
        ::= { cbftf100Entry 25 }

cbftf100ConnectorTbl OBJECT-TYPE
        SYNTAX CpsConnector
        ACCESS read-only
        STATUS mandatory
        DESCRIPTION "The style of connectors built into each port of this
                     device.  There are multiple subdevices in this table, 
                     numbering one entry per port."  
        ::= { cbftf100Entry 26 }

cbftf100SACCfgTbl OBJECT-TYPE
        SYNTAX INTEGER { enabled(1), disabled(2) }
        ACCESS read-write
        STATUS mandatory
        DESCRIPTION "This configuration setting controls whether changes in
                     source MAC address are reported. When set to enabled(1),
                     a change in MAC address will result in a momentary change
                     in the value of SACStatTbl from same(2) to changed(1) and
                     back, and the transmission of a trap, if the management 
                     module is so configured.  There are multiple subdevices
                     in this table, numbering one entry per port."
        ::= { cbftf100Entry 27 }

cbftf100SACStatTbl OBJECT-TYPE
        SYNTAX INTEGER { changed(1), same(2) }
        ACCESS read-only
        STATUS mandatory
        DESCRIPTION "This status value indicates whether or not the source
                     MAC address attached to this port changed in the last
                     polling period. This value tends to change quite quickly;
                     therefore, the 'ERROR' traps that are sent when SAC is
                     detected are a much more reliable indicator.  There are
                     multiple subdevices in this table, numbering one entry
                     per port."
        ::= { cbftf100Entry 28 }

cbftf100MirrorSelTbl OBJECT-TYPE
        SYNTAX INTEGER { mirror(1), normal(2) }
        ACCESS read-write
        STATUS mandatory
        DESCRIPTION "This configuration setting allows a mirror port to be
                     selected. The selected port will re-transmit copies of
                     all packets transmitted on ports whose MirrorOutTbl
                     value is set to mirrorOut(1), and will also transmit
                     copies of all packets received by all ports whose MirrorInTbl
                     value is set to mirrorIn(1). It is recommended that a 
                     maximum of one MirrorSelTbl, one MirrorInTbl, and one 
                     MirrorOutTbl port be selected at once, since the switch 
                     may have trouble handling the traffic that can result from
                     other configurations.  There are multiple subdevices in this
                     table, numbering one entry per port."
        ::= { cbftf100Entry 29 }

cbftf100MirrorInTbl OBJECT-TYPE
        SYNTAX INTEGER { mirrorIn(1), normal(2) }
        ACCESS read-write
        STATUS mandatory
        DESCRIPTION "This configuration setting allows a mirror source port to be
                     selected. All packets received on each port with a
                     MirrorInTbl setting of mirrorIn(1) will be retransmitted 
                     on all ports whose MirrorSelTbl setting is mirror(1). 
                     It is recommended that a maximum of one MirrorSelTbl, one
                     MirrorInTbl, and one MirrorOutTbl port be selected at once,
                     since the switch may have trouble handling the traffic that 
                     can result from other configurations.  There are multiple
                     subdevices in this table, numbering one entry per port."
        ::= { cbftf100Entry 30 }

cbftf100MirrorOutTbl OBJECT-TYPE
        SYNTAX INTEGER { mirrorOut(1), normal(2) }
        ACCESS read-write
        STATUS mandatory
        DESCRIPTION "This configuration setting allows a mirror source port to be
                     selected. All packets transmitted on each port with a
                     MirrorInTbl setting of mirrorOut(1) will be retransmitted 
                     on all ports whose MirrorSelTbl setting is mirror(1). 
                     It is recommended that a maximum of one MirrorSelTbl, one
                     MirrorInTbl, and one MirrorOutTbl port be selected at once,
                     since the switch may have trouble handling the traffic that 
                     can result from other configurations.  There are multiple
                     subdevices in this table, numbering one entry per port."
        ::= { cbftf100Entry 31 }

cbftf100LinkTbl OBJECT-TYPE
        SYNTAX INTEGER { up(1), down(2) }
        ACCESS read-only
        STATUS mandatory
        DESCRIPTION "This table contains the link status of each port in the
                     switch.  There are multiple subdevices in this table, 
                     numbering one entry per port."
        ::= { cbftf100Entry 32 }

cbftf100PortCount OBJECT-TYPE
        SYNTAX INTEGER
        ACCESS read-only
        STATUS mandatory
        DESCRIPTION "A count of the switch ports in this device. i.e. the
                     maximum subdevice index supported by this switch."
        ::= { cbftf100Entry 33 }

cbftf100LinkPassThrough OBJECT-TYPE
        SYNTAX INTEGER { enabled(1), disabled(2), notSupported(3) }
        ACCESS read-write
        STATUS mandatory
        DESCRIPTION "If Link Passthrough is enabled on a port, loss of link 
                     on the opposite port will be propegated through to 
                     this port so that the switch does not prevent one 
                     end device from detecting loss of link on the 
                     opposite end device. Far end fault is only 
                     supported on copper ports and only in switch 
                     configurations that have exactly two ports."
        ::= { cbftf100Entry 34 }

cbftf100CacheClean OBJECT-TYPE
        SYNTAX INTEGER { clean(1), dirty(2) }
        ACCESS read-only
        STATUS mandatory
        DESCRIPTION "When the value is clean(1)Device and Management Module
                     cache are synchronized, no automatic corrections to 
                     configuration will occur.  When the value is dirty(2)
                     Device and Management Module cache are not synchronized.
                     The configuration currently displayed by the application 
                     has not been validated by the device. The device may 
                     need to correct the configuration, in which case the 
                     displayed configuration will change."
        ::= { cbftf100Entry 35 }

cbftf100RedundantPath OBJECT-TYPE
        SYNTAX INTEGER { enabled(1), disabled(2), notSupported(3) }
        ACCESS read-only
        STATUS mandatory
        DESCRIPTION "This variable shows the status of the redundant fiber
                     capability. If the value is enabled(1), this means that
                     the hardware switch to enable redundant fiber is on, and
                     the two fiber ports on the device are presumed to be
                     connected to the same remote device. Even if both fibers
                     have link, traffic flows to and from that device through
                     only one of the two fiber pairs at once. This provides a
                     redundant path should one of the fibers be compromised.
                     If the value is disabled(2), the hardware switch to enable
                     redundant fiber is off, and the two fiber ports on the
                     device pass traffic normally (i.e. independently and
                     simultaneously). If the value is notSupported(3), the device
                     does not have redundant fiber capability."
        ::= { cbftf100Entry 36 }

-- ===================================================================
-- Table for a CETCT100 media converter

cetct100Table OBJECT-TYPE
        SYNTAX SEQUENCE OF Cetct100Entry
        ACCESS not-accessible
        STATUS mandatory
        DESCRIPTION "Sparse table containing one entry for each CETCT100
                     10Mbps Twisted-Pair to Fiber Ethernet Media Converter
                     in the stack, indexed by cabinet serial number and slot."
        ::= { cpsSlotDetail 12 }

cetct100Entry OBJECT-TYPE
        SYNTAX Cetct100Entry
        ACCESS not-accessible
        STATUS mandatory
        DESCRIPTION "Status and configuration entries for a single CETCT100"
        INDEX { cetct100BiaIndex, cetct100SlotIndex }
        ::= { cetct100Table 1 }

Cetct100Entry ::=
        SEQUENCE {
                 cetct100BiaIndex             INTEGER,
                 cetct100SlotIndex            INTEGER,
                 cetct100Groups               DisplayString,
                 cetct100MRevision            INTEGER,
                 cetct100CfgMatch             INTEGER,
                 cetct100SerialNumber         INTEGER,
                 cetct100ConfigMode           INTEGER,
                 cetct100FirmwareRevision     INTEGER,
                 cetct100TPLink               INTEGER,
                 cetct100Collision            INTEGER,
                 cetct100CoaxActivity         INTEGER,
                 cetct100TPActivity           INTEGER,
                 cetct100CollisionsPerMinute  INTEGER,
                 cetct100CollisionsPerHour    INTEGER,
                 cetct100ConnB                INTEGER,
                 cetct100ConnA                INTEGER,
                 cetct100CacheClean           INTEGER
                 }

cetct100BiaIndex OBJECT-TYPE
        SYNTAX INTEGER
        ACCESS read-only
        STATUS mandatory
        DESCRIPTION "The serial number (BIA) of the cabinet in which the 
                     device is installed"
        ::= { cetct100Entry 1 }

cetct100SlotIndex OBJECT-TYPE
        SYNTAX INTEGER
        ACCESS read-only
        STATUS mandatory
        DESCRIPTION "The slot in which the device is installed"
        ::= { cetct100Entry 2 }

cetct100Groups OBJECT-TYPE
        SYNTAX DisplayString
        ACCESS read-write
        STATUS mandatory
        DESCRIPTION "User-defined keywords that group this device together with
                     other devices under a user-defined scheme. By placing 
                     matching keywords in cpsGroupCtrl.0, the agent can be
                     instructed to apply configuration changes simultaneously
                     to all group members rather than to individual devices.
                     Every Groups string has three automatically defined
                     implied values: 
                     1) The model family of the device, e.g. 'CETCT100'
                     2) The serial number of the cabinet in which the device
                        is installed, in decimal with no leading zeroes, 
                        e.g. '12345', and 
                     3) same as 2, with the slot in which the device is 
                        installed appended, enclosed in square brackets. 
                        e.g. '12345[9]'"
        ::= { cetct100Entry 3 }

cetct100MRevision OBJECT-TYPE
        SYNTAX INTEGER
        ACCESS read-only
        STATUS mandatory
        DESCRIPTION "The marketing revision of this device"
        ::= { cetct100Entry 4 }

cetct100CfgMatch OBJECT-TYPE
        SYNTAX INTEGER { yes(1), no(2), notApplicable(3) }
        ACCESS read-only
        STATUS mandatory
        DESCRIPTION "yes(1) indicates that the conditions specified in 
                     cpsGroupCtrl.0 match the Groups value for this
                     device. no(2) means that there is no match.
                     notApplicable(3) indicates that cpsGroupCtrl.0 is null
                     and therefore no comparison was performed."
        ::= { cetct100Entry 5 }

cetct100SerialNumber OBJECT-TYPE
        SYNTAX INTEGER 
        ACCESS read-only
        STATUS mandatory
        DESCRIPTION "The serial number of this device"
        ::= { cetct100Entry 6 }

cetct100ConfigMode OBJECT-TYPE
        SYNTAX INTEGER { software(1), hardware(2) }
        ACCESS read-only
        STATUS mandatory
        DESCRIPTION "This device has a jumper or switch that disables 
                     software management of the device. When ConfigMode is
                     hardware(2), SNMP management is disabled, and all
                     configuration control comes from physical switches or
                     jumpers on the device."
        ::= { cetct100Entry 7 }

cetct100FirmwareRevision OBJECT-TYPE
        SYNTAX INTEGER
        ACCESS read-only
        STATUS mandatory
        DESCRIPTION "The firmware revision level for this device."
        ::= { cetct100Entry 8 }

cetct100TPLink OBJECT-TYPE
        SYNTAX INTEGER { linkUp(1), linkDown(2) }
        ACCESS read-only
        STATUS mandatory
        DESCRIPTION "Status of Copper Link for this device"
        ::= { cetct100Entry 9 }

cetct100Collision OBJECT-TYPE
        SYNTAX INTEGER { yes(1), no(2) }
        ACCESS read-only
        STATUS mandatory
        DESCRIPTION "This status variable indicates whether or not an Ethernet
                     collision occurred during the most recent polling cycle."
        ::= { cetct100Entry 10 }

cetct100CoaxActivity OBJECT-TYPE
        SYNTAX INTEGER { yes(1), no(2) }
        ACCESS read-only
        STATUS mandatory
        DESCRIPTION "This status variable indicates whether or not Ethernet
                     traffic was detected on the Coax interface during the most
                     recent polling cycle."
        ::= { cetct100Entry 11 }

cetct100TPActivity OBJECT-TYPE
        SYNTAX INTEGER { yes(1), no(2) }
        ACCESS read-only
        STATUS mandatory
        DESCRIPTION "This status variable indicates whether or not Ethernet
                     traffic was detected on the Twisted Pair interface during 
                     the most recent polling cycle."
        ::= { cetct100Entry 12 }

cetct100CollisionsPerMinute OBJECT-TYPE
        SYNTAX INTEGER 
        ACCESS read-only
        STATUS mandatory
        DESCRIPTION "The number of Ethernet collisions that occurred during
                     the most recently completed measured minute. Every 60
                     seconds, the device moves its previous collision count
                     into this variable, and restarts the counter at zero."
        ::= { cetct100Entry 13 }

cetct100CollisionsPerHour OBJECT-TYPE
        SYNTAX INTEGER 
        ACCESS read-only
        STATUS mandatory
        DESCRIPTION "The number of Ethernet collisions that occurred during
                     the most recently completed measured hour. Every 60
                     minutes, the device moves its previous collision count
                     into this variable, and restarts the counter at zero."
        ::= { cetct100Entry 14 }

cetct100ConnA OBJECT-TYPE
        SYNTAX CpsConnector 
        ACCESS read-only
        STATUS mandatory
        DESCRIPTION "The style of media connector built into this device."
        ::= { cetct100Entry 15 }

cetct100ConnB OBJECT-TYPE
        SYNTAX CpsConnector 
        ACCESS read-only
        STATUS mandatory
        DESCRIPTION "The style of media connector built into this device."
        ::= { cetct100Entry 16 }

cetct100CacheClean OBJECT-TYPE
        SYNTAX INTEGER { clean(1), dirty(2) }
        ACCESS read-only
        STATUS mandatory
        DESCRIPTION "When the value is clean(1)Device and Management Module
                     cache are synchronized, no automatic corrections to 
                     configuration will occur.  When the value is dirty(2)
                     Device and Management Module cache are not synchronized.
                     The configuration currently displayed by the application 
                     has not been validated by the device. The device may 
                     need to correct the configuration, in which case the 
                     displayed configuration will change."
        ::= { cetct100Entry 17 }

--=====================================================================
-- Table for the ccscf100

ccscf100Table OBJECT-TYPE
        SYNTAX SEQUENCE OF Ccscf100Entry
        ACCESS not-accessible
        STATUS mandatory
        DESCRIPTION "Sparse table containing one entry for each ccscf100
                     T3/E3 Copper to Fiber Media Converter in the stack, 
                     indexed by cabinet serial number and slot."
        ::= { cpsSlotDetail 13 }

ccscf100Entry OBJECT-TYPE
        SYNTAX Ccscf100Entry
        ACCESS not-accessible
        STATUS mandatory
        DESCRIPTION "Status and configuration entries for a single ccscf100"
        INDEX { ccscf100BiaIndex, ccscf100SlotIndex }
        ::= { ccscf100Table 1 }

Ccscf100Entry ::=
        SEQUENCE {
                 ccscf100BiaIndex             INTEGER,
                 ccscf100SlotIndex            INTEGER,
                 ccscf100Groups               DisplayString,
                 ccscf100MRevision            INTEGER,
                 ccscf100CfgMatch             INTEGER,
                 ccscf100SerialNumber         INTEGER,
                 ccscf100ConfigMode           INTEGER,
                 ccscf100FiberLink            INTEGER,
                 ccscf100CopperLink           INTEGER,
                 ccscf100AISFiber             INTEGER,
                 ccscf100AISCopper            INTEGER,
                 ccscf100DS3LineBuildout      INTEGER,
                 ccscf100E3DS3                INTEGER,
                 ccscf100CopperLoopback       INTEGER,
                 ccscf100FiberLoopback        INTEGER,
                 ccscf100ConnA                INTEGER,
                 ccscf100ConnB                INTEGER,
                 ccscf100CacheClean           INTEGER
                 }

ccscf100BiaIndex OBJECT-TYPE
        SYNTAX INTEGER
        ACCESS read-only
        STATUS mandatory
        DESCRIPTION "The serial number (BIA) of the cabinet in which the 
                     device is installed"
        ::= { ccscf100Entry 1 }

ccscf100SlotIndex OBJECT-TYPE
        SYNTAX INTEGER
        ACCESS read-only
        STATUS mandatory
        DESCRIPTION "The slot in which the device is installed"
        ::= { ccscf100Entry 2 }

ccscf100Groups OBJECT-TYPE
        SYNTAX DisplayString
        ACCESS read-write
        STATUS mandatory
        DESCRIPTION "User-defined keywords that group this device together with
                     other devices under a user-defined scheme. By placing 
                     matching keywords in cpsGroupCtrl.0, the agent can be
                     instructed to apply configuration changes simultaneously
                     to all group members rather than to individual devices.
                     Every Groups string has three automatically defined
                     implied values: 
                     1) The model family of the device, e.g. 'ccscf100'
                     2) The serial number of the cabinet in which the device
                        is installed, in decimal with no leading zeroes, 
                        e.g. '12345', and 
                     3) same as 2, with the slot in which the device is 
                        installed appended, enclosed in square brackets. 
                        e.g. '12345[9]'"
        ::= { ccscf100Entry 3 }

ccscf100MRevision OBJECT-TYPE
        SYNTAX INTEGER
        ACCESS read-only
        STATUS mandatory
        DESCRIPTION "The marketing revision of this device"
        ::= { ccscf100Entry 4 }

ccscf100CfgMatch OBJECT-TYPE
        SYNTAX INTEGER { yes(1), no(2), inactive(3) }
        ACCESS read-only
        STATUS mandatory
        DESCRIPTION "yes(1) indicates that the conditions specified in 
                     cpsGroupCtrl.0 match the Groups value for this
                     device. no(2) means that there is no match.
                     notApplicable(3) indicates that cpsGroupCtrl.0 is null
                     and therefore no comparison was performed."
        ::= { ccscf100Entry 5 }

ccscf100SerialNumber OBJECT-TYPE
        SYNTAX INTEGER
        ACCESS read-only
        STATUS mandatory
        DESCRIPTION "The serial number of this device"
        ::= { ccscf100Entry 6 }

ccscf100ConfigMode OBJECT-TYPE
        SYNTAX INTEGER { software(1), hardware(2) }
        ACCESS read-only
        STATUS mandatory
        DESCRIPTION "This device has a jumper or switch that disables 
                     software management of the device. When ConfigMode is
                     hardware(2), SNMP management is disabled, and all
                     configuration control comes from physical switches or
                     jumpers on the device."
        ::= { ccscf100Entry 7 }

ccscf100FiberLink OBJECT-TYPE
        SYNTAX INTEGER { linkUp(1), linkDown(2) }
        ACCESS read-only
        STATUS mandatory
        DESCRIPTION "Status of Fiber Link for this device"
        ::= { ccscf100Entry 8 }

ccscf100CopperLink OBJECT-TYPE
        SYNTAX INTEGER { linkUp(1), linkDown(2) }
        ACCESS read-only
        STATUS mandatory
        DESCRIPTION "Status of Copper Link for this device"
        ::= { ccscf100Entry 9 }

ccscf100AISFiber OBJECT-TYPE
        SYNTAX INTEGER { alarm(1), normal(2) }
        ACCESS read-only
        STATUS mandatory
        DESCRIPTION "Alarm Indication Signal. When equal to alarm(1),
                     this means that the other end has TAOS enabled
                     and is currently transmitting an alarm condition."
        ::= { ccscf100Entry 10 }

ccscf100AISCopper OBJECT-TYPE
        SYNTAX INTEGER { alarm(1), normal(2) }
        ACCESS read-only
        STATUS mandatory
        DESCRIPTION "Alarm Indication Signal. When equal to alarm(1),
                     this means that the other end has TAOS enabled
                     and is currently transmitting an alarm condition."
        ::= { ccscf100Entry 11 }

ccscf100DS3LineBuildout OBJECT-TYPE
        SYNTAX INTEGER { boost(1), normal(2), notSupported(3) }
        ACCESS read-write
        STATUS mandatory
        DESCRIPTION "The characteristics of the copper interface"
        ::= { ccscf100Entry 12 }

ccscf100E3DS3 OBJECT-TYPE
        SYNTAX INTEGER { e3(1), ds3(2) }
        ACCESS read-only
        STATUS mandatory
        DESCRIPTION "This variable indicates whether the current device
                     is the T1 or the E1 version."
        ::= { ccscf100Entry 13 }

ccscf100CopperLoopback OBJECT-TYPE
        SYNTAX INTEGER { yes(1), no(2) }
        ACCESS read-write
        STATUS mandatory
        DESCRIPTION "Enable loopback on the copper interface."
        ::= { ccscf100Entry 14 }

ccscf100FiberLoopback OBJECT-TYPE
        SYNTAX INTEGER { yes(1), no(2) }
        ACCESS read-write
        STATUS mandatory
        DESCRIPTION "Enable loopback on the copper interface."
        ::= { ccscf100Entry 15 }

ccscf100ConnA OBJECT-TYPE
        SYNTAX CpsConnector
        ACCESS read-only
        STATUS mandatory
        DESCRIPTION "The style of Fiber connector built into this device"
        ::= { ccscf100Entry 16 }

ccscf100ConnB OBJECT-TYPE
        SYNTAX CpsConnector
        ACCESS read-only
        STATUS mandatory
        DESCRIPTION "The style of Copper connector built into this device"
        ::= { ccscf100Entry 17 }

ccscf100CacheClean OBJECT-TYPE
        SYNTAX INTEGER { clean(1), dirty(2) }
        ACCESS read-only
        STATUS mandatory
        DESCRIPTION "When the value is clean(1)Device and Management Module
                     cache are synchronized, no automatic corrections to 
                     configuration will occur.  When the value is dirty(2)
                     Device and Management Module cache are not synchronized.
                     The configuration currently displayed by the application 
                     has not been validated by the device. The device may 
                     need to correct the configuration, in which case the 
                     displayed configuration will change."
        ::= { ccscf100Entry 18 }

-- ==================================================================
-- Table for a cfetf105 slide in card.

cfetf105Table OBJECT-TYPE
        SYNTAX SEQUENCE OF Cfetf105Entry
        ACCESS not-accessible
        STATUS mandatory
        DESCRIPTION "Sparse table containing one entry for each CFTEF105
                     100Mbps Twisted-Pair to Fiber Ethernet Media Converter
                     in the stack, indexed by cabinet serial number and slot."
        ::= { cpsSlotDetail 14 }

cfetf105Entry OBJECT-TYPE
        SYNTAX Cfetf105Entry
        ACCESS not-accessible
        STATUS mandatory
        DESCRIPTION "Status and configuration entries for a single CFETF105"
        INDEX { cfetf105BiaIndex, cfetf105SlotIndex }
        ::= { cfetf105Table 1 }

Cfetf105Entry ::=
        SEQUENCE {
                 cfetf105BiaIndex            INTEGER,
                 cfetf105SlotIndex           INTEGER,
                 cfetf105Groups              DisplayString,
                 cfetf105MRevision           INTEGER,
                 cfetf105CfgMatch            INTEGER,
                 cfetf105SerialNumber        INTEGER,
                 cfetf105ConnA               INTEGER,
                 cfetf105ConnB               INTEGER,
                 cfetf105TPLink              INTEGER,
                 cfetf105FiberLink           INTEGER,
                 cfetf105AutoNegot           INTEGER,
                 cfetf105LinkPassThrough     INTEGER,
                 cfetf105AutoCross           INTEGER,
                 cfetf105TPActivity          INTEGER,
                 cfetf105FiberActivity       INTEGER,
                 cfetf105ConfigMode          INTEGER,
                 cfetf105CacheClean          INTEGER
                 }

cfetf105BiaIndex OBJECT-TYPE
        SYNTAX INTEGER
        ACCESS read-only
        STATUS mandatory
        DESCRIPTION "The serial number (BIA) of the cabinet in which the 
                     device is installed"
        ::= { cfetf105Entry 1 }

cfetf105SlotIndex OBJECT-TYPE
        SYNTAX INTEGER
        ACCESS read-only
        STATUS mandatory
        DESCRIPTION "The slot in which the device is installed"
        ::= { cfetf105Entry 2 }

cfetf105Groups OBJECT-TYPE
        SYNTAX DisplayString
        ACCESS read-write
        STATUS mandatory
        DESCRIPTION "User-defined keywords that group this device together with
                     other devices under a user-defined scheme. By placing 
                     matching keywords in cpsGroupCtrl.0, the agent can be
                     instructed to apply configuration changes simultaneously
                     to all group members rather than to individual devices.
                     Every Groups string has three automatically defined
                     implied values: 
                     1) The model family of the device, e.g. 'CFETF105'
                     2) The serial number of the cabinet in which the device
                        is installed, in decimal with no leading zeroes, 
                        e.g. '12345', and 
                     3) same as 2, with the slot in which the device is 
                        installed appended, enclosed in square brackets. 
                        e.g. '12345[9]'"
        ::= { cfetf105Entry 3 }

cfetf105MRevision OBJECT-TYPE
        SYNTAX INTEGER
        ACCESS read-only
        STATUS mandatory
        DESCRIPTION "The marketing revision of this device"
        ::= { cfetf105Entry 4 }

cfetf105CfgMatch OBJECT-TYPE
        SYNTAX INTEGER { yes(1), no(2), notApplicable(3) }
        ACCESS read-only
        STATUS mandatory
        DESCRIPTION "yes(1) indicates that the conditions specified in 
                     cpsGroupCtrl.0 match the Groups value for this
                     device. no(2) means that there is no match.
                     notApplicable(3) indicates that cpsGroupCtrl.0 is null
                     and therefore no comparison was performed."
        ::= { cfetf105Entry 5 }

cfetf105SerialNumber OBJECT-TYPE
        SYNTAX INTEGER 
        ACCESS read-only
        STATUS mandatory
        DESCRIPTION "The serial number of this device"
        ::= { cfetf105Entry 6 }

cfetf105ConnA OBJECT-TYPE
        SYNTAX CpsConnector
        ACCESS read-only
        STATUS mandatory
        DESCRIPTION "The style of Fiber connector built into this device"
        ::= { cfetf105Entry 7 }

cfetf105ConnB OBJECT-TYPE
        SYNTAX CpsConnector
        ACCESS read-only
        STATUS mandatory
        DESCRIPTION "The style of Copper connector built into this device"
        ::= { cfetf105Entry 8 }

cfetf105TPLink OBJECT-TYPE
        SYNTAX INTEGER { linkUp(1), linkDown(2) }
        ACCESS read-only
        STATUS mandatory
        DESCRIPTION "Status of Twisted Pair Link for this device"
        ::= { cfetf105Entry 9 }

cfetf105FiberLink OBJECT-TYPE
        SYNTAX INTEGER { linkUp(1), linkDown(2) }
        ACCESS read-only
        STATUS mandatory
        DESCRIPTION "Status of Fiber Link for this device"
        ::= { cfetf105Entry 10 }

cfetf105AutoNegot OBJECT-TYPE
        SYNTAX INTEGER { enabled(1), disabled(2) }
        ACCESS read-write
        STATUS mandatory
        DESCRIPTION "Enable/Disable Autonegotiation"
        ::= { cfetf105Entry 11 }

cfetf105LinkPassThrough OBJECT-TYPE
        SYNTAX INTEGER { enabled(1), disabled(2) }
        ACCESS read-write
        STATUS mandatory
        DESCRIPTION "Enable/Disable for Link Pass Through, a feature that
                     causes loss of link on one side of a media converter
                     to be passed through to the other side, so that 
                     upstream equipment can see the fault condition."
        ::= { cfetf105Entry 12 }

cfetf105AutoCross OBJECT-TYPE
        SYNTAX INTEGER { enabled(1), disabled(2) }
        ACCESS read-write
        STATUS mandatory
        DESCRIPTION "Enable/Disable for automatic copper TX/RX pair correction"
        ::= { cfetf105Entry 13 }

cfetf105TPActivity OBJECT-TYPE
        SYNTAX INTEGER { yes(1), no(2), notSupported(3) }
        ACCESS read-only
        STATUS mandatory
        DESCRIPTION "Network traffic indicator for Copper side of this device"
        ::= { cfetf105Entry 14 }

cfetf105FiberActivity OBJECT-TYPE
        SYNTAX INTEGER { yes(1), no(2), notSupported(3) }
        ACCESS read-only
        STATUS mandatory
        DESCRIPTION "Network traffic indicator for Fiber side of this device"
        ::= { cfetf105Entry 15 }

cfetf105ConfigMode OBJECT-TYPE
        SYNTAX INTEGER { software(1), hardware(2) }
        ACCESS read-only
        STATUS mandatory
        DESCRIPTION "This device has a jumper or switch that disables 
                     software management of the device. When ConfigMode is
                     hardware(2), SNMP management is disabled, and all
                     configuration control comes from physical switches or
                     jumpers on the device."
        ::= { cfetf105Entry 16 }

cfetf105CacheClean OBJECT-TYPE
        SYNTAX INTEGER { clean(1), dirty(2) }
        ACCESS read-only
        STATUS mandatory
        DESCRIPTION "When the value is clean(1)Device and Management Module
                     cache are synchronized, no automatic corrections to 
                     configuration will occur.  When the value is dirty(2)
                     Device and Management Module cache are not synchronized.
                     The configuration currently displayed by the application 
                     has not been validated by the device. The device may 
                     need to correct the configuration, in which case the 
                     displayed configuration will change."
        ::= { cfetf105Entry 17 }

-- ====================================================================
-- Table for a smacf100 Ethernet port.

smacf100PTable OBJECT-TYPE
        SYNTAX SEQUENCE OF Smacf100PEntry
        ACCESS not-accessible
        STATUS mandatory
        DESCRIPTION "Sparse table containing one entry for each SMACF100P
                     virtual slide-in device.  This table dexcribes ONE port 
                     on a SMACFxxx colony switch"
        ::= { cpsSlotDetail 15 }

smacf100PEntry OBJECT-TYPE
        SYNTAX Smacf100PEntry
        ACCESS not-accessible
        STATUS mandatory
        DESCRIPTION "Status and configuration entries for a single SMACF100P"
        INDEX { smacf100PSubDeviceIndex, smacf100PBiaIndex, smacf100PSlotIndex }
        ::= { smacf100PTable 1 }

Smacf100PEntry ::=
        SEQUENCE {
                 smacf100PSubDeviceIndex         INTEGER,
                 smacf100PBiaIndex               INTEGER,
                 smacf100PSlotIndex              INTEGER,
                 smacf100PGroups                 DisplayString,
                 smacf100PCfgMatch               INTEGER,
                 smacf100PConnA                  INTEGER,
                 smacf100PLink                   INTEGER,
                 smacf100P100Mbps                INTEGER,
                 smacf100PFullDuplex             INTEGER,
                 smacf100PSACStat                INTEGER,
                 smacf100PEnabled                INTEGER,
                 smacf100PAutoNegot              INTEGER,
                 smacf100PAdv10HDX               INTEGER,
                 smacf100PAdv10FDX               INTEGER,
                 smacf100PAdv100HDX              INTEGER,
                 smacf100PAdv100FDX              INTEGER,
                 smacf100PSTPState               INTEGER,
                 smacf100PLastMAC                MacAddress,
                 smacf100PFarEndFaultCfg         INTEGER,
                 smacf100PFarEndFaultStat        INTEGER,
                 smacf100PTxOctets               INTEGER,
                 smacf100PWrapTxOctets           INTEGER,
                 smacf100PRxOctets               INTEGER,
                 smacf100PWrapRxOctets           INTEGER,
                 smacf100PSACCfg                 INTEGER,
                 smacf100PBlockMgmt              INTEGER,
                 smacf100PBlockPort              INTEGER,
                 smacf100PTxDropPkts             INTEGER,
                 smacf100PTxBroadcastPkts        INTEGER,
                 smacf100PTxMulticastPkts        INTEGER,
                 smacf100PTxUnicastPkts          INTEGER,
                 smacf100PTxCollisions           INTEGER,
                 smacf100PTxSingleCollision      INTEGER,
                 smacf100PTxMultipleCollision    INTEGER,
                 smacf100PTxDeferredTransmit     INTEGER,
                 smacf100PTxLateCollision        INTEGER,
                 smacf100PTxExcessiveCollision   INTEGER,
                 smacf100PTxFrameInDisc          INTEGER,
                 smacf100PTxPausePkts            INTEGER,
                 smacf100PRxUndersizePkts        INTEGER,
                 smacf100PRxPausePkts            INTEGER,
                 smacf100PPkts64Octets           INTEGER,
                 smacf100PPkts65to127Octets      INTEGER,
                 smacf100PPkts128to255Octets     INTEGER,
                 smacf100PPkts256to511Octets     INTEGER,
                 smacf100PPkts512to1023Octets    INTEGER,
                 smacf100PPkts1024to1522Octets   INTEGER,
                 smacf100PRxOversizePkts         INTEGER,
                 smacf100PRxJabbers              INTEGER,
                 smacf100PRxAlignmentErrors      INTEGER,
                 smacf100PRxFCSErrors            INTEGER,
                 smacf100PRxGoodOctets           INTEGER,
                 smacf100PWrapRxGoodOctets       INTEGER,
                 smacf100PRxDropPkts             INTEGER,
                 smacf100PRxUnicastPkts          INTEGER,
                 smacf100PRxMulticastPkts        INTEGER,
                 smacf100PRxBroadcastPkts        INTEGER,
                 smacf100PRxSAChanges            INTEGER,
                 smacf100PRxFragments            INTEGER,
                 smacf100PRxExcessSizeDisc       INTEGER,
                 smacf100PRxSymbolError          INTEGER,
                 smacf100PQosPriority            INTEGER,
                 smacf100PQosPause               INTEGER,
                 smacf100PAdvPause               INTEGER,
                 smacf100PCacheClean              INTEGER
                 }

smacf100PSubDeviceIndex OBJECT-TYPE
        SYNTAX INTEGER
        ACCESS read-only
        STATUS mandatory
        DESCRIPTION "Generally, individual devices in this MIB are
                     distinguished by BiaIndex and SlotIndex. This 
                     device differs from many in that it contains
                     multiple subdevices.   The number of subdevices
                     varies with the manufactured configuration. 
                     Subdevices within devices are indexed
                     by BiaIndex, SlotIndex, and SubDeviceIndex.
                     When the subdevice column is read from the table, 
                     the value '1' is always returned."
        ::= { smacf100PEntry 1 }

smacf100PBiaIndex OBJECT-TYPE
        SYNTAX INTEGER
        ACCESS read-only
        STATUS mandatory
        DESCRIPTION "The serial number (BIA) of the cabinet in which the 
                     device is installed"
        ::= { smacf100PEntry 2 }

smacf100PSlotIndex OBJECT-TYPE
        SYNTAX INTEGER
        ACCESS read-only
        STATUS mandatory
        DESCRIPTION "The slot in which the device is installed"
        ::= { smacf100PEntry 3 }

smacf100PGroups OBJECT-TYPE
        SYNTAX DisplayString
        ACCESS read-write
        STATUS mandatory
        DESCRIPTION "User-defined keywords that group this device together with
                     other devices under a user-defined scheme. By placing 
                     matching keywords in cpsGroupCtrl.0, the agent can be
                     instructed to apply configuration changes simultaneously
                     to all group members rather than to individual devices.
                     Every Groups string has three automatically defined
                     implied values: 
                     1) The model family of the device, e.g. 'SMACF100'
                     2) The serial number of the cabinet in which the device
                        is installed, in decimal with no leading zeroes, 
                        e.g. '12345', and 
                     3) same as 2, with the slot in which the device is 
                        installed appended, enclosed in square brackets. 
                        e.g. '12345[9]'"
        ::= { smacf100PEntry 4 }

smacf100PCfgMatch OBJECT-TYPE
        SYNTAX INTEGER { yes(1), no(2), notApplicable(3) }
        ACCESS read-only
        STATUS mandatory
        DESCRIPTION "yes(1) indicates that the conditions specified in 
                     cpsGroupCtrl.0 match the Groups value for this
                     device. no(2) means that there is no match.
                     notApplicable(3) indicates that cpsGroupCtrl.0 is null
                     and therefore no comparison was performed."
        ::= { smacf100PEntry 5 }

smacf100PConnA OBJECT-TYPE
        SYNTAX CpsConnector
        ACCESS read-only
        STATUS mandatory
        DESCRIPTION "The style of Fiber or Copper connector built into this
                     device"
        ::= { smacf100PEntry 6 }

smacf100PLink OBJECT-TYPE
        SYNTAX INTEGER { linkUp(1), linkDown(2) }
        ACCESS read-only
        STATUS mandatory
        DESCRIPTION "Status of Port Link for this device"
        ::= { smacf100PEntry 7 }

smacf100P100Mbps OBJECT-TYPE
        SYNTAX INTEGER { mbps100(1), mbps10(2) }
        ACCESS read-write
        STATUS mandatory
        DESCRIPTION "Communication speed for this port."
        ::= { smacf100PEntry 8 }

smacf100PFullDuplex OBJECT-TYPE
        SYNTAX INTEGER { fullDuplex(1), halfDuplex(2), negotiating(3) }
        ACCESS read-write
        STATUS mandatory
        DESCRIPTION "In most cases this is a configuration setting that 
                     controls the duplex mode; fullDuplex is full duplex and 
                     halfDuplex is half duplex.  On twisted pair ports with 
                     autonegotiation enabled, this is a status indication 
                     showing the duplex value decided upon during the 
                     negotiation.  When link is down, autonegotiation has
                     not been completed yet, and the duplex setting is 
                     therefore unknown and the value is negotiating(3)."
        ::= { smacf100PEntry 9 }

smacf100PSACStat OBJECT-TYPE
        SYNTAX INTEGER { changed(1), same(2) }
        ACCESS read-only
        STATUS mandatory
        DESCRIPTION "This status value indicates whether or not the source
                     MAC address attached to this port changed in the last
                     polling period. This value tends to change quite quickly;
                     therefore, the 'ERROR' traps that are sent when SAC is
                     detected are a much more reliable indicator."
        ::= { smacf100PEntry 10 }

smacf100PEnabled OBJECT-TYPE
        SYNTAX INTEGER { yes(1), no(2) }
        ACCESS read-write
        STATUS mandatory
        DESCRIPTION "Status of of this Port.  A value of yes(1) indicates
                     this port is 'enabled'.  A value of no(2) indicates this
                     port is 'disabled'."
        ::= { smacf100PEntry 11 }

smacf100PAutoNegot OBJECT-TYPE
        SYNTAX INTEGER  { enabled(1), disabled(2), notSupported(3) }
        ACCESS read-write
        STATUS mandatory
        DESCRIPTION "Enables or disables autonegtiation of link speed and 
                     duplex for twisted pair ports.  Not supported on Fiber
                     ports."
        ::= { smacf100PEntry 12 }

smacf100PAdv10HDX OBJECT-TYPE
        SYNTAX INTEGER { yes(1), no(2), notSupported(3) }
        ACCESS read-write
        STATUS mandatory
        DESCRIPTION "This configuration setting controls whether or not each 
                     port advertises willingness to connect at 10Mbps, half 
                     duplex.  This setting is not supported on fiber ports, 
                     and is ignored when autonegotiation is disabled."
        ::= { smacf100PEntry 13 }

smacf100PAdv10FDX OBJECT-TYPE
        SYNTAX INTEGER { yes(1), no(2), notSupported(3) }
        ACCESS read-write
        STATUS mandatory
        DESCRIPTION "This configuration setting controls whether or not each 
                     port advertises willingness to connect at 10Mbps, full 
                     duplex.  This setting is not supported on fiber ports, 
                     and is ignored when autonegotiation is disabled."
        ::= { smacf100PEntry 14 }

smacf100PAdv100HDX OBJECT-TYPE
        SYNTAX INTEGER { yes(1), no(2), notSupported(3) }
        ACCESS read-write
        STATUS mandatory
        DESCRIPTION "This configuration setting controls whether or not each 
                     port advertises willingness to connect at 100Mbps, half 
                     duplex.  This setting is not supported on fiber ports, 
                     and is ignored when autonegotiation is disabled."
        ::= { smacf100PEntry 15 }

smacf100PAdv100FDX OBJECT-TYPE
        SYNTAX INTEGER { yes(1), no(2), notSupported(3) }
        ACCESS read-write
        STATUS mandatory
        DESCRIPTION "This configuration setting controls whether or not each 
                     port advertises willingness to connect at 100Mbps, full 
                     duplex.  This setting is not supported on fiber ports, 
                     and is ignored when autonegotiation is disabled."
        ::= { smacf100PEntry 16 }

smacf100PSTPState OBJECT-TYPE
        SYNTAX INTEGER { notSupported(1), disabled(2), blocking(3), listening(4),
                         learning(5), forwarding(6) }
        ACCESS read-write
        STATUS mandatory
        DESCRIPTION "Port spanning tree state."
        ::= { smacf100PEntry 17 }

smacf100PLastMAC OBJECT-TYPE
        SYNTAX MacAddress
        ACCESS read-only
        STATUS mandatory
        DESCRIPTION "Last MAC Address this port communicated with."
        ::= { smacf100PEntry 18 }

smacf100PFarEndFaultCfg OBJECT-TYPE
        SYNTAX INTEGER { enabled(1), disabled(2), notSupported(3) }
        ACCESS read-write
        STATUS mandatory
        DESCRIPTION "Far end fault configuration of this Port."
        ::= { smacf100PEntry 19 }

smacf100PFarEndFaultStat OBJECT-TYPE
        SYNTAX INTEGER  { enabled(1), disabled(2), notSupported(3) }
        ACCESS read-only
        STATUS mandatory
        DESCRIPTION "Far end fault status of this port."
        ::= { smacf100PEntry 20 }

smacf100PTxOctets OBJECT-TYPE
        SYNTAX INTEGER
        ACCESS read-only
        STATUS mandatory
        DESCRIPTION "The number of bytes of data transmitted through this
                     interface."
        ::= { smacf100PEntry 21 }

smacf100PWrapTxOctets OBJECT-TYPE
        SYNTAX INTEGER
        ACCESS read-only
        STATUS mandatory
        DESCRIPTION "The number of times that the unsigned 32-bit 
                     smacf100PTxOctets(21) MIB variable has wrapped."
        ::= { smacf100PEntry 22 }

smacf100PRxOctets OBJECT-TYPE
        SYNTAX INTEGER 
        ACCESS read-only
        STATUS mandatory
        DESCRIPTION "The number of bytes of data received through this 
                     interface."
        ::= { smacf100PEntry 23 }

smacf100PWrapRxOctets OBJECT-TYPE
        SYNTAX INTEGER
        ACCESS read-only
        STATUS mandatory
        DESCRIPTION "The number of times that the unsigned 32-bit 
                     smacf100PRxOctets(23) MIB variable has wrapped."
        ::= { smacf100PEntry 24 }

smacf100PSACCfg OBJECT-TYPE
        SYNTAX INTEGER  { enabled(1), disabled(2) }
        ACCESS read-write
        STATUS mandatory
        DESCRIPTION "Source Address Change detection configuration. 
                     Enables or Disables the generation of traps related
                     to source address change for this port. When
                     disabled, the smacf100PSACStat(10) variable always
                     reads no."
        ::= { smacf100PEntry 25 }

smacf100PBlockMgmt OBJECT-TYPE
        SYNTAX INTEGER  { block(1), pass(2) }
        ACCESS read-write
        STATUS mandatory
        DESCRIPTION "Through this variable and others, the SMACF100 supports
                     port- based VLANs. The SMACF100 will pass tags for IEEE
                     802.3ac VLANs, but will neither insert nor strip them.
                     When this variable is set to block(1), this port may 
                     neither transmit packets to nor receive packets from
                     management entities within this switch, i.e. the
                     reporting unit (present in every SMACF100) and the 
                     management module (present in SMACF100 Main Management
                     Units). This feature is intended to block traffic 
                     between particular Ethernet interfaces inside a single
                     switch; it cannot identify or block management traffic
                     from external sources. A single port is selected for 
                     configuration via the slot index. The subdevice index 
                     for this variable must always be 1. The logical 
                     soundness of VLAN rules cannot be validated. If you 
                     set smacf100PBlockMgmt(26) to block(1) on a port that
                     provides a path between a reporting unit and its
                     management module, or between a management module and
                     its Network Management Station, you will be unable to
                     manage the SMACF100 until the situation is rectified
                     (by recabling to work around the misconfiguration, or 
                     by resetting the SMACF100 to factory defaults via the
                     serial port)."
        ::= { smacf100PEntry 26 }

smacf100PBlockPort OBJECT-TYPE
        SYNTAX INTEGER  { block(1), pass(2) }
        ACCESS read-write
        STATUS mandatory
        DESCRIPTION "Through this variable and others, the SMACF100 supports
                     port- based VLANs. The SMACF100 will pass tags for IEEE
                     802.3ac VLANs, but will neither insert nor strip them. 
                     This table allows the network administrator to block 
                     traffic between pairs of ports within a single SMACF100. 
                     A pair of ports is selected for configuration by 
                     specifying a slot index and a subdevice index. The order
                     in which the two ports are specified is unimportant, the
                     effects of the configuration are identical on both ports. 
                     Each port has a smacf100PBlockPort(27) entry for every 
                     other port. So, communication between ports <p1> and <p2>
                     in cabinet serial <serial> can be blocked by setting 
                     either  smacf100PBlockPort.<p1>.<serial>.<p2> or  
                     smacf100PBlockPort.<p2>.<serial>.<p1> to block(1). Attempts
                     to prevent a port from communicating with itself are 
                     ignored. Beyond that, the logical soundness of VLAN rules
                     cannot be validated.  There is one entry per subdevice, and
                     one subdevice per port on the SMACF100."
        ::= { smacf100PEntry 27 }

smacf100PTxDropPkts OBJECT-TYPE
        SYNTAX INTEGER
        ACCESS read-only
        STATUS mandatory
        DESCRIPTION "This counter is incremented every time a transmit packet
                     is dropped due to lack of resources (e.g. transmit FIFO 
                     underflow), or an internal MAC sublayer transmit error 
                     occurs that is not counted by either TxLateCollision or 
                     TxExcessiveCollision counters."
        ::= { smacf100PEntry 28 }

smacf100PTxBroadcastPkts OBJECT-TYPE
        SYNTAX INTEGER
        ACCESS read-only
        STATUS mandatory
        DESCRIPTION "The number of good packets transmitted by this port that
                     are directed to a broadcast address. This counter includes
                     neither errored broadcast packets nor valid multicast
                     packets."
        ::= { smacf100PEntry 29 }

smacf100PTxMulticastPkts OBJECT-TYPE
        SYNTAX INTEGER  
        ACCESS read-only
        STATUS mandatory
        DESCRIPTION "The number of good packets transmitted by this port that 
                     are directed to a multicast address. This counter includes
                     neither errored multicast packets nor valid broadcast
                     packets."
        ::= { smacf100PEntry 30 }

smacf100PTxUnicastPkts OBJECT-TYPE
        SYNTAX INTEGER
        ACCESS read-only
        STATUS mandatory
        DESCRIPTION "The number of good packets transmitted by this port that 
                     are directed to a unicast address."
        ::= { smacf100PEntry 31 }

smacf100PTxCollisions OBJECT-TYPE
        SYNTAX INTEGER 
        ACCESS read-only
        STATUS mandatory
        DESCRIPTION "The number of collisions experienced by this port during 
                     packet transmissions."
        ::= { smacf100PEntry 32 }

smacf100PTxSingleCollision OBJECT-TYPE
        SYNTAX INTEGER  
        ACCESS read-only
        STATUS mandatory
        DESCRIPTION "The number of packets successfully transmitted by this port 
                     that experienced exactly one collision."
        ::= { smacf100PEntry 33 }

smacf100PTxMultipleCollision OBJECT-TYPE
        SYNTAX INTEGER  
        ACCESS read-only
        STATUS mandatory
        DESCRIPTION "The number of packets successfully transmitted by this port 
                     that experienced more than one collision."
        ::= { smacf100PEntry 34 }

smacf100PTxDeferredTransmit OBJECT-TYPE
        SYNTAX INTEGER  
        ACCESS read-only
        STATUS mandatory
        DESCRIPTION "The number of packets transmitted by a this port for which 
                     the first transmission attempt was delayed because the 
                     medium was busy."
        ::= { smacf100PEntry 35 }

smacf100PTxLateCollision OBJECT-TYPE
        SYNTAX INTEGER  
        ACCESS read-only
        STATUS mandatory
        DESCRIPTION "The number of times that a collision was detected later
                     than 512 bit-times into the transmission of a packet."
        ::= { smacf100PEntry 36 }

smacf100PTxExcessiveCollision OBJECT-TYPE
        SYNTAX INTEGER  
        ACCESS read-only
        STATUS mandatory
        DESCRIPTION "The number of packets that were not transmitted from 
                     this port because 16 unsucessful attempts were made to
                     transmit the packet."
        ::= { smacf100PEntry 37 }

smacf100PTxFrameInDisc OBJECT-TYPE
        SYNTAX INTEGER 
        ACCESS read-only
        STATUS mandatory
        DESCRIPTION "The number of valid packets received which are 
                     discarded by the forwarding process due to lack of
                     space on an output queue. This attribute only increments
                     if a network device is not acting in compliance with a 
                     flow control request."
        ::= { smacf100PEntry 38 }

smacf100PTxPausePkts OBJECT-TYPE
        SYNTAX INTEGER  { enabled(1), disabled(2) }
        ACCESS read-write
        STATUS mandatory
        DESCRIPTION "The number of PAUSE frames transmitted by this port. 
                     This implies that the port is in full duplex mode and
                     that 802.3x flow control was enabled at the completion
                     of autonegotiation."
        ::= { smacf100PEntry 39 }

smacf100PRxUndersizePkts OBJECT-TYPE
        SYNTAX INTEGER
        ACCESS read-only
        STATUS mandatory
        DESCRIPTION "The number of good packets received by this port that
                     are less than 64 bytes long (excluding framing bits but
                     including the Frame Check Sequence)."
        ::= { smacf100PEntry 40 }

smacf100PRxPausePkts OBJECT-TYPE
        SYNTAX INTEGER  { enabled(1), disabled(2) }
        ACCESS read-write
        STATUS mandatory
        DESCRIPTION "The number of PAUSE frames recieved by this port. The
                     PAUSE frame must have a valid MAC Control Frame EtherType
                     field (88- 08h), have a destination MAC address of either
                     the MAC Control frame reseved multicast address
                     (01:80:C2:00:00:01), be a minimum of 64 bytes long 
                     (excluding preamble but including Frame Check Sequence),
                     and have a valid CRC. Although an 802.3 compliant MAC 
                     is only permitted to transmit PAUSE frames when in full
                     duplex mode with flow control enabled and with the transfer
                     of PAUSE frames determined by the result of autonegotiation,
                     an 802.3 MAC receiver is required to count all received 
                     PAUSE frames, regardless of its half/full-duplex status.
                     An indication that a MAC is in half-duplex mode with 
                     this counter incrementing indicates a non- compliant
                     transmitting device on the network."
        ::= { smacf100PEntry 41 }

smacf100PPkts64Octets OBJECT-TYPE
        SYNTAX INTEGER
        ACCESS read-only
        STATUS mandatory
        DESCRIPTION "The number of packets, including error packets, that
                     are 64 bytes long."
        ::= { smacf100PEntry 42 }

smacf100PPkts65to127Octets OBJECT-TYPE
        SYNTAX INTEGER
        ACCESS read-only
        STATUS mandatory
        DESCRIPTION "The number of packets, including error packets, that
                     are between 65 and 127 bytes long."
        ::= { smacf100PEntry 43 }

smacf100PPkts128to255Octets OBJECT-TYPE
        SYNTAX INTEGER
        ACCESS read-only
        STATUS mandatory
        DESCRIPTION "The number of packets, including error packets, 
                     that are between 128 and 255 bytes long."
        ::= { smacf100PEntry 44 }

smacf100PPkts256to511Octets OBJECT-TYPE
        SYNTAX INTEGER 
        ACCESS read-only
        STATUS mandatory
        DESCRIPTION "The number of packets, including error packets,
                     that are between 256 and 511 bytes long."
        ::= { smacf100PEntry 45 }

smacf100PPkts512to1023Octets OBJECT-TYPE
        SYNTAX INTEGER 
        ACCESS read-only
        STATUS mandatory
        DESCRIPTION "The number of packets, including error packets,
                     that are between 512 and 1023 bytes long."
        ::= { smacf100PEntry 46 }

smacf100PPkts1024to1522Octets OBJECT-TYPE
        SYNTAX INTEGER
        ACCESS read-only
        STATUS mandatory
        DESCRIPTION "The number of packets, including error packets,
                     that are between 1024 and 1522 bytes long."
        ::= { smacf100PEntry 47 }

smacf100PRxOversizePkts OBJECT-TYPE
        SYNTAX INTEGER  { enabled(1), disabled(2) }
        ACCESS read-only
        STATUS mandatory
        DESCRIPTION "The number of good packets received by this port
                     that are longer than 1522 bytes inclusive (excluding
                     framing bits but including the Frame Check Sequence).
                     Note that this counter alone will be incremented for
                     packets in the range 1523 to 1536 bytes inclusive, 
                     whereas both this counter and the RxExcessSizeDisc 
                     counter will be incremented for packets of 1537 bytes
                     and longer."
        ::= { smacf100PEntry 48 }

smacf100PRxJabbers OBJECT-TYPE
        SYNTAX INTEGER
        ACCESS read-only
        STATUS mandatory
        DESCRIPTION "The number of packets received by a port that are 
                     longer than 1522 bytes and have either a Frame Check 
                     Sequence error or an alignment error."
        ::= { smacf100PEntry 49 }

smacf100PRxAlignmentErrors OBJECT-TYPE
        SYNTAX INTEGER 
        ACCESS read-only
        STATUS mandatory
        DESCRIPTION "The number of packets received by this port that have a
                     length (excluding framing bits but including the Frame
                     Check Sequence) between 64 and 1522 bytes inclusive, and 
                     have a bad Frame Check Sequence with a non-integral number
                     of bytes."
        ::= { smacf100PEntry 50 }

smacf100PRxFCSErrors OBJECT-TYPE
        SYNTAX INTEGER
        ACCESS read-only
        STATUS mandatory
        DESCRIPTION "The number of packets received by this port that have a
                     length (excluding framing bits but including the Frame Check
                     Sequence) between 64 and 1522 bytes inclusive, and have a
                     bad Frame Check Sequence with a integral number of bytes."
        ::= { smacf100PEntry 51 }

smacf100PRxGoodOctets OBJECT-TYPE
        SYNTAX INTEGER
        ACCESS read-only
        STATUS mandatory
        DESCRIPTION "The total number of bytes in all good packets received by 
                     a port (excluding framing bits but including Frame Check
                     Sequences)."
        ::= { smacf100PEntry 52 }

smacf100PWrapRxGoodOctets OBJECT-TYPE
        SYNTAX INTEGER
        ACCESS read-only
        STATUS mandatory
        DESCRIPTION "The number of times that the unsigned 32-bit 
                     smacf100PRxGoodOctets(52) MIB variable for this port has
                     wrapped."
        ::= { smacf100PEntry 53 }

smacf100PRxDropPkts OBJECT-TYPE
        SYNTAX INTEGER
        ACCESS read-only
        STATUS mandatory
        DESCRIPTION "The number of good packets received by this port that were
                     dropped due to lack of resources (e.g. lack of input buffers)
                     or were dropped due to a lack of resources before a 
                     determination of the validity of the packet could be made 
                     (e.g. receive FIFO overflow). The counter is only 
                     incremented if the receive error was not counted by either
                     the RxExcessSizeDisc, the RxAlignmentErrors or the 
                     RxFCSErrors counters.)"
        ::= { smacf100PEntry 54 }

smacf100PRxUnicastPkts OBJECT-TYPE
        SYNTAX INTEGER
        ACCESS read-only
        STATUS mandatory
        DESCRIPTION "The number of good packets received by this port that are 
                     addressed to a unicast address."
        ::= { smacf100PEntry 55 }

smacf100PRxMulticastPkts OBJECT-TYPE
        SYNTAX INTEGER  
        ACCESS read-only
        STATUS mandatory
        DESCRIPTION "The number of good packets received by this port that are
                     directed to a multicast address. This counter includes
                     neither errored multicast packets nor valid broadcast
                     packets."
        ::= { smacf100PEntry 56 }

smacf100PRxBroadcastPkts OBJECT-TYPE
        SYNTAX INTEGER
        ACCESS read-only
        STATUS mandatory
        DESCRIPTION "The number of good packets received by this port that are
                     directed to the broadcast address. This counter includes
                     neither errored broadcast packets nor valid multicast
                     packets."
        ::= { smacf100PEntry 57 }

smacf100PRxSAChanges OBJECT-TYPE
        SYNTAX INTEGER
        ACCESS read-only
        STATUS mandatory
        DESCRIPTION "The number of times the Source Ethernet Address of good
                     receive packets has changed from the previous value. A 
                     count greater than one generally indicates that the port
                     is connected to a repeater-based network."
        ::= { smacf100PEntry 58 }

smacf100PRxFragments OBJECT-TYPE
        SYNTAX INTEGER
        ACCESS read-only
        STATUS mandatory
        DESCRIPTION "The number of packets received by a port that are shorter
                     than 64 bytes (excluding framing bits) and have either 
                     an Frame Check Sequence error or an alignment error."
        ::= { smacf100PEntry 59 }

smacf100PRxExcessSizeDisc OBJECT-TYPE
        SYNTAX INTEGER 
        ACCESS read-only
        STATUS mandatory
        DESCRIPTION "The number of good packets received by this port that are
                     longer than 1536 bytes (excluding framing bits but 
                     including Frame Check Sequences) and were discarded due 
                     to excessive length. Note that the RxOversizePkts counter
                     alone is incremented for packets in the range 1523-1536 
                     bytes inclusive, whereas both RxExcessSizeDisc and 
                     RxOversizePkts are incremented for packets of 1537 bytes
                     and longer."
        ::= { smacf100PEntry 60 }

smacf100PRxSymbolError OBJECT-TYPE
        SYNTAX INTEGER
        ACCESS read-only
        STATUS mandatory
        DESCRIPTION "The total number of times this port received a packet
                     which had a valid length, but contained at least one 
                     invalid symbol. The counter only increments once per
                     carrier event, and does not increment if a collision is
                     detected during the carrier event."
        ::= { smacf100PEntry 61 }

smacf100PQosPriority OBJECT-TYPE
        SYNTAX INTEGER 
        ACCESS read-write
        STATUS mandatory
        DESCRIPTION "When this variable is set to 'high(1)', this port becomes
                     a high-priority port. This means that all packets received
                     on this port for transission on other ports and all packets
                     received on other ports for transmission on this port are
                     placed in the high-priority queues. When the variable is set
                     to 'default(2)', the low priority queue is used unless other
                     conditions (i.e. an 802.1p tag or a high-priority setting
                     for another port) prompt the use of the high priority queue."
        ::= { smacf100PEntry 62 }

smacf100PQosPause OBJECT-TYPE
        SYNTAX INTEGER
        ACCESS read-write
        STATUS mandatory
        DESCRIPTION "When the global variable smacf100QosEnable(7) is set to
                     'enabled(1)', then the port-specific variable
                     smacf100PQosPause(63) controls whether or not the port
                     supports half-duplex back pressure and full-duplex flow
                     control. Otherwise, only dropping of frames is supported
                     for the port."
        ::= { smacf100PEntry 63 }

smacf100PAdvPause OBJECT-TYPE
        SYNTAX INTEGER
        ACCESS read-write
        STATUS mandatory
        DESCRIPTION "Enable/disable control for this advertised autonegotiation
                     mode. When Pause capability is autonegotiated (at the 
                     Physical level), the MAC layer may then send Pause packets
                     to pace data coming across the link. smacf100PAutoNegot(12)
                     must be set to 'enabled(1)'. The results of this
                     autonegotiation are ignored if smacf100QosEnable(7) is set
                     to 'enabled(1)' and smacf100PQosPause(63) is set to
                     'disabled(2)'. In this case, no 'Pause' capability is
                     supported."
        ::= { smacf100PEntry 64 }

smacf100PCacheClean OBJECT-TYPE
        SYNTAX INTEGER { clean(1), dirty(2) }
        ACCESS read-only
        STATUS mandatory
        DESCRIPTION "When the value is clean(1)Device and Management Module
                     cache are synchronized, no automatic corrections to 
                     configuration will occur.  When the value is dirty(2)
                     Device and Management Module cache are not synchronized.
                     The configuration currently displayed by the application 
                     has not been validated by the device. The device may 
                     need to correct the configuration, in which case the 
                     displayed configuration will change."
        ::= { smacf100PEntry 65 }

-- ===================================================================
-- Table for a CPSLD100 Slide-in LED card

cpsld100Table OBJECT-TYPE
        SYNTAX SEQUENCE OF Cpsld100Entry
        ACCESS not-accessible
        STATUS mandatory
        DESCRIPTION "Sparse table containing one entry for each CPSLD100
                     in the stack, indexed by cabinet serial number and slot."
        ::= { cpsSlotDetail 16 }

cpsld100Entry OBJECT-TYPE
        SYNTAX Cpsld100Entry
        ACCESS not-accessible
        STATUS mandatory
        DESCRIPTION "Status and configuration entries for a single CPSLD100"
        INDEX { cpsld100BiaIndex, cpsld100SlotIndex }
        ::= { cpsld100Table 1 }

Cpsld100Entry ::=
        SEQUENCE {
                 cpsld100BiaIndex            INTEGER,
                 cpsld100SlotIndex           INTEGER,
                 cpsld100SerialNumber        INTEGER,
                 cpsld100MRevision           INTEGER,
                 cpsld100Ps1Power            INTEGER,
                 cpsld100Ps1InUse            INTEGER,
                 cpsld100Ps2Power            INTEGER,
                 cpsld100Ps2InUse            INTEGER                 
                 }

cpsld100BiaIndex OBJECT-TYPE
        SYNTAX INTEGER
        ACCESS read-only
        STATUS mandatory
        DESCRIPTION "The serial number (BIA) of the cabinet in which the 
                     device is installed"
        ::= { cpsld100Entry 1 }

cpsld100SlotIndex OBJECT-TYPE
        SYNTAX INTEGER
        ACCESS read-only
        STATUS mandatory
        DESCRIPTION "The slot in which the device is installed"
        ::= { cpsld100Entry 2 }


cpsld100SerialNumber OBJECT-TYPE
        SYNTAX INTEGER 
        ACCESS read-only
        STATUS mandatory
        DESCRIPTION "The serial number of this device"
        ::= { cpsld100Entry 3 }

cpsld100MRevision OBJECT-TYPE
        SYNTAX INTEGER
        ACCESS read-only
        STATUS mandatory
        DESCRIPTION "The marketing revision of this device"
        ::= { cpsld100Entry 4 }

cpsld100Ps1Power OBJECT-TYPE
        SYNTAX INTEGER { on(1), off(2), notInstalled(3) }
        ACCESS read-only
        STATUS mandatory
        DESCRIPTION "Power status, first power supply slot. Value is
                     on(1) when the supply is capable of supplying power."
        ::= { cpsld100Entry 5 }


cpsld100Ps1InUse OBJECT-TYPE
        SYNTAX INTEGER { yes(1), no(2), notInstalled(3) }
        ACCESS read-only
        STATUS mandatory
        DESCRIPTION "Power status, first power supply slot. Value is yes(1)
                     when the power is selected to supply power to the cabinet."
        ::= { cpsld100Entry 6 }


cpsld100Ps2Power OBJECT-TYPE
        SYNTAX INTEGER { on(1), off(2), notInstalled(3) }
        ACCESS read-only
        STATUS mandatory
        DESCRIPTION "Power status, second power supply slot. Value is
                     on(1) when the supply is capable of supplying power."
        ::= { cpsld100Entry 7 }


cpsld100Ps2InUse OBJECT-TYPE
        SYNTAX INTEGER { yes(1), no(2), notInstalled(3) }
        ACCESS read-only
        STATUS mandatory
        DESCRIPTION "Power status, second power supply slot. Value is yes(1)
                     when the power is selected to supply power to the cabinet."
        ::= { cpsld100Entry 8 }

-- ==================================================================
-- Table for a cdftf100 slide in device

cdftf100Table OBJECT-TYPE
        SYNTAX SEQUENCE OF Cdftf100Entry
        ACCESS not-accessible
        STATUS mandatory
        DESCRIPTION "Sparse table containing one entry for each CDFTF100
                     Dual telco Media Converter in the stack, indexed by
                     cabinet serial number and slot."
       ::= { cpsSlotDetail 17 }

cdftf100Entry OBJECT-TYPE
        SYNTAX Cdftf100Entry
        ACCESS not-accessible
        STATUS mandatory
        DESCRIPTION "Status and configuration entries for a single CDFTF100"
        INDEX { cdftf100SubDeviceIndex, cdftf100BiaIndex, cdftf100SlotIndex }
        ::= { cdftf100Table 1 }

Cdftf100Entry ::=
        SEQUENCE {
                 cdftf100SubDeviceIndex      INTEGER,
                 cdftf100BiaIndex            INTEGER,
                 cdftf100SlotIndex           INTEGER,
                 cdftf100Groups              DisplayString,
                 cdftf100CfgMatch            INTEGER,
                 cdftf100SerialNumber        INTEGER,
                 cdftf100MRevision           INTEGER,
                 cdftf100TPLinkTbl           INTEGER,
                 cdftf100FiberLinkTbl        INTEGER,
                 cdftf100TPActivityTbl       INTEGER,
                 cdftf100FiberActivityTbl    INTEGER,
                 cdftf100ConnectorTbl        INTEGER,
                 cdftf100FirmwareRevision    INTEGER,
                 cdftf100CacheClean          INTEGER
                 }

cdftf100SubDeviceIndex OBJECT-TYPE
        SYNTAX INTEGER
        ACCESS read-only
        STATUS mandatory
        DESCRIPTION "Generally, individual devices in this MIB are
                     distinguished by BiaIndex and SlotIndex. This 
                     device differs from many in that it contains
                     multiple subdevices (in this case, switch ports).
                     The number of subdevices varies with the manufactured
                     configuration. Subdevices within devices are indexed
                     by BiaIndex, SlotIndex, and SubDeviceIndex.
                     When the subdevice column is read from the table, 
                     the value '1' is always returned."
        ::= { cdftf100Entry 1 } 

cdftf100BiaIndex OBJECT-TYPE
        SYNTAX INTEGER
        ACCESS read-only
        STATUS mandatory
        DESCRIPTION "The serial number (BIA) of the cabinet in which the 
                     device is installed"
        ::= { cdftf100Entry 2 }

cdftf100SlotIndex OBJECT-TYPE
        SYNTAX INTEGER
        ACCESS read-only
        STATUS mandatory
        DESCRIPTION "The slot in which the device is installed"
        ::= { cdftf100Entry 3 }

cdftf100Groups OBJECT-TYPE
        SYNTAX DisplayString
        ACCESS read-write
        STATUS mandatory
        DESCRIPTION "User-defined keywords that group this device together with
                     other devices under a user-defined scheme. By placing 
                     matching keywords in cpsGroupCtrl.0, the agent can be
                     instructed to apply configuration changes simultaneously
                     to all group members rather than to individual devices.
                     Every Groups string has three automatically defined
                     implied values: 
                     1) The model family of the device, e.g. 'CDFTF100'
                     2) The serial number of the cabinet in which the device
                        is installed, in decimal with no leading zeroes, 
                        e.g. '12345', and 
                     3) same as 2, with the slot in which the device is 
                        installed appended, enclosed in square brackets. 
                        e.g. '12345[9]'"
        ::= { cdftf100Entry 4 }

cdftf100CfgMatch OBJECT-TYPE
        SYNTAX INTEGER { yes(1), no(2), notApplicable(3) }
        ACCESS read-only
        STATUS mandatory
        DESCRIPTION "yes(1) indicates that the conditions specified in 
                     cpsGroupCtrl.0 match the Groups value for this
                     device. no(2) means that there is no match.
                     notApplicable(3) indicates that cpsGroupCtrl.0 is null
                     and therefore no comparison was performed."
        ::= { cdftf100Entry 5 }

cdftf100SerialNumber OBJECT-TYPE
        SYNTAX INTEGER
        ACCESS read-only
        STATUS mandatory
        DESCRIPTION "The serial number of this device"
        ::= { cdftf100Entry 6 }

cdftf100MRevision OBJECT-TYPE
        SYNTAX INTEGER
        ACCESS read-only
        STATUS mandatory
        DESCRIPTION "The marketing revision of the device"
        ::= { cdftf100Entry 7 }

cdftf100TPLinkTbl OBJECT-TYPE
        SYNTAX INTEGER { up(1), down(2) }
        ACCESS read-only
        STATUS mandatory
        DESCRIPTION "This table contains the link status of each twisted pair
                     port in the CDFTF100.  There are multiple subdevices in
                     this table, numbering one entry per port."
        ::= { cdftf100Entry 8 }

cdftf100FiberLinkTbl OBJECT-TYPE
        SYNTAX INTEGER { up(1), down(2) }
        ACCESS read-only
        STATUS mandatory
        DESCRIPTION "This table contains the link status of each fiber port
                     in the CDFTF100.  There are multiple subdevices in this
                     table, numbering one entry per port."
        ::= { cdftf100Entry 9 }

cdftf100TPActivityTbl OBJECT-TYPE
        SYNTAX INTEGER { yes(1), no(2) }
        ACCESS read-only
        STATUS mandatory
        DESCRIPTION "Netowrk traffic indicator for the copper port(s) 
                     on this device.  There are multiple subdevices in this
                     table, numbering one entry per port."
        ::= { cdftf100Entry 10 }

cdftf100FiberActivityTbl OBJECT-TYPE
        SYNTAX INTEGER { yes(1), no(2) }
        ACCESS read-only
        STATUS mandatory
        DESCRIPTION "Netowrk traffic indicator for the fiber port(s) 
                     on this device.  There are multiple subdevices in this
                     table, numbering one entry per port."
        ::= { cdftf100Entry 11 }

cdftf100ConnectorTbl OBJECT-TYPE
        SYNTAX INTEGER { up(1), down(2) }
        ACCESS read-only
        STATUS mandatory
        DESCRIPTION "This table contains the link status of each port of this
                     device.  There are multiple subdevices in this table, 
                     numbering one entry per port."
        ::= { cdftf100Entry 12 }

cdftf100FirmwareRevision OBJECT-TYPE
        SYNTAX CpsConnector
        ACCESS read-only
        STATUS mandatory
        DESCRIPTION "The style of connectors built into each port of 
                     this device."  
        ::= { cdftf100Entry 13 }

cdftf100CacheClean OBJECT-TYPE
        SYNTAX INTEGER { clean(1), dirty(2) }
        ACCESS read-only
        STATUS mandatory
        DESCRIPTION "When the value is clean(1)Device and Management Module
                     cache are synchronized, no automatic corrections to 
                     configuration will occur.  When the value is dirty(2)
                     Device and Management Module cache are not synchronized.
                     The configuration currently displayed by the application 
                     has not been validated by the device. The device may 
                     need to correct the configuration, in which case the 
                     displayed configuration will change."
        ::= { cdftf100Entry 14 }

--=====================================================================
-- Table for the cpsvt100

cpsvt100Table OBJECT-TYPE
        SYNTAX SEQUENCE OF Cpsvt100Entry
        ACCESS not-accessible
        STATUS mandatory
        DESCRIPTION "Sparse table containing one entry for each CPSVT100
                     in the stack, indexed by cabinet serial number and slot."
        ::= { cpsSlotDetail 18 }

cpsvt100Entry OBJECT-TYPE
        SYNTAX Cpsvt100Entry
        ACCESS not-accessible
        STATUS mandatory
        DESCRIPTION "Status and configuration entries for a single CPSVT100"
        INDEX { cpsvt100BiaIndex, cpsvt100SlotIndex }
        ::= { cpsvt100Table 1 }

Cpsvt100Entry ::=
        SEQUENCE {
                 cpsvt100BiaIndex               INTEGER,
                 cpsvt100SlotIndex              INTEGER,
                 cpsvt100Groups                 DisplayString,
                 cpsvt100MRevision              INTEGER,
                 cpsvt100CfgMatch               INTEGER,
                 cpsvt100SerialNumber           INTEGER,
                 cpsvt100FiberLink              INTEGER,
                 cpsvt100CopperLink             INTEGER,
                 cpsvt100Fault                  INTEGER,
                 cpsvt100ConnA                  INTEGER,
                 cpsvt100ConnB                  INTEGER,
                 cpsvt100TermTiming             INTEGER,
                 cpsvt100LoopBack               INTEGER,
                 cpsvt100CableMode              INTEGER,
                 cpsvt100DCE                    INTEGER,
                 cpsvt100InvertTX               INTEGER,
                 cpsvt100InvertRX               INTEGER,
                 cpsvt100ConfigMode             INTEGER,
                 cpsvt100FirmwareRev            INTEGER,
                 cpsvt100RmtDetected            INTEGER,
                 cpsvt100RmtTermTiming          INTEGER,
                 cpsvt100RmtLoopBack            INTEGER,
                 cpsvt100RmtCableMode           INTEGER,
                 cpsvt100RmtDCE                 INTEGER,
                 cpsvt100RmtInvertTX            INTEGER,
                 cpsvt100RmtInvertRX            INTEGER,
                 cpsvt100RmtConfigMode          INTEGER,
                 cpsvt100RmtFirmwareRev         INTEGER,
                 cpsvt100RmtCopperLink          INTEGER,
                 cpsvt100RmtFiberLink           INTEGER,
                 cpsvt100CacheClean             INTEGER
                 }

cpsvt100BiaIndex OBJECT-TYPE
        SYNTAX INTEGER
        ACCESS read-only
        STATUS mandatory
        DESCRIPTION "The serial number (BIA) of the cabinet in which the 
                     device is installed"
        ::= { cpsvt100Entry 1 }

cpsvt100SlotIndex OBJECT-TYPE
        SYNTAX INTEGER
        ACCESS read-only
        STATUS mandatory
        DESCRIPTION "The slot in which the device is installed"
        ::= { cpsvt100Entry 2 }

cpsvt100Groups OBJECT-TYPE
        SYNTAX DisplayString
        ACCESS read-write
        STATUS mandatory
        DESCRIPTION "User-defined keywords that group this device together with
                     other devices under a user-defined scheme. By placing 
                     matching keywords in cpsGroupCtrl.0, the agent can be
                     instructed to apply configuration changes simultaneously
                     to all group members rather than to individual devices.
                     Every Groups string has three automatically defined
                     implied values: 
                     1) The model family of the device, e.g. 'CPSVT100'
                     2) The serial number of the cabinet in which the device
                        is installed, in decimal with no leading zeroes, 
                        e.g. '12345', and 
                     3) same as 2, with the slot in which the device is 
                        installed appended, enclosed in square brackets. 
                        e.g. '12345[9]'"
        ::= { cpsvt100Entry 3 }

cpsvt100MRevision OBJECT-TYPE
        SYNTAX INTEGER
        ACCESS read-only
        STATUS mandatory
        DESCRIPTION "The marketing revision of this device"
        ::= { cpsvt100Entry 4 }

cpsvt100CfgMatch OBJECT-TYPE
        SYNTAX INTEGER { yes(1), no(2), inactive(3) }
        ACCESS read-only
        STATUS mandatory
        DESCRIPTION "yes(1) indicates that the conditions specified in 
                     cpsGroupCtrl.0 match the Groups value for this
                     device. no(2) means that there is no match.
                     notApplicable(3) indicates that cpsGroupCtrl.0 is null
                     and therefore no comparison was performed."
        ::= { cpsvt100Entry 5 }

cpsvt100SerialNumber OBJECT-TYPE
        SYNTAX INTEGER
        ACCESS read-only
        STATUS mandatory
        DESCRIPTION "The serial number of this device"
        ::= { cpsvt100Entry 6 }

cpsvt100FiberLink OBJECT-TYPE
        SYNTAX INTEGER { linkUp(1), linkDown(2) }
        ACCESS read-only
        STATUS mandatory
        DESCRIPTION "Status of Fiber Link for this device"
        ::= { cpsvt100Entry 7 }

cpsvt100CopperLink OBJECT-TYPE
        SYNTAX INTEGER { linkUp(1), linkDown(2) }
        ACCESS read-only
        STATUS mandatory
        DESCRIPTION "Status of Copper Link for this device"
        ::= { cpsvt100Entry 8 }

cpsvt100Fault OBJECT-TYPE
        SYNTAX INTEGER { yes(1), no(2) }
        ACCESS read-only
        STATUS mandatory
        DESCRIPTION "Value is yes(1) when either CopperLink or FiberLink 
                     has value linkDown(2)"
        ::= { cpsvt100Entry 9 }

cpsvt100ConnA OBJECT-TYPE
        SYNTAX CpsConnector
        ACCESS read-only
        STATUS mandatory
        DESCRIPTION "The style of Fiber connector built into this device"
        ::= { cpsvt100Entry 10 }

cpsvt100ConnB OBJECT-TYPE
        SYNTAX CpsConnector
        ACCESS read-only
        STATUS mandatory
        DESCRIPTION "The style of Copper connector built into this device"
        ::= { cpsvt100Entry 11 }

cpsvt100TermTiming OBJECT-TYPE
        SYNTAX INTEGER { rxc(1), kbps56(2), kbps64(3), kbps112(4), kbps128(5), 
                         kbps256(6), kbps384(7), kbps512(8), kbps768(9), 
                         kbps1024(10), kbps1554(11), kbps2048(12), kbps3072(13),
                         kbps4096(14), kbps6144(15), asynchronous(16) }
        ACCESS read-write
        STATUS mandatory
        DESCRIPTION "Local Terminal Timing setting.  Terminal timing is a 
                     signal sent from a DCE to a DTE to control the rate of
                     data the DTE sends to the DCE. Since this signal cannot 
                     be sent across the fiber after media converters are
                     introduced, the converter must generate this signal and
                     supply it to the DTE. The converter gets the setting from
                     a thumbwheel.  For converters attached to DTEs, the 
                     thumbwheel setting influences the transmit data rate. If
                     the Terminal Timing setting is RXC, the DTE derives its
                     transmit clock from the receive clock supplied by the DCE.
                     For converters attached to DCEs, the thumbwheel setting 
                     has no effect.  If two DTEs are connected via media
                     converters, the thumbwheel settings must not be RXC."
        ::= { cpsvt100Entry 12 }

cpsvt100LoopBack OBJECT-TYPE
        SYNTAX INTEGER { enabled(1), disabled(2) }
        ACCESS read-write
        STATUS mandatory
        DESCRIPTION "Remote fiber and copper loopback setting.  Loopback is 
                     a testing aid available on several different products. 
                     When Loopback is enabled on an interface, all data that
                     is sent to the interface is reflected back to the sender,
                     and the actual condition (or even existence) of the 
                     equipment on the opposite interface is ignored."
        ::= { cpsvt100Entry 13 }

cpsvt100CableMode OBJECT-TYPE
        SYNTAX INTEGER { notValid(1), rs-530A(2), rs-530(3), x-21(4), v-35(5), 
                         rs-449(6), rs-232(7), disconnected(8) }
        ACCESS read-only
        STATUS mandatory
        DESCRIPTION "A description of the type of cable that is attached to 
                     the Copper interface of the local device."
        ::= { cpsvt100Entry 14 }

cpsvt100DCE OBJECT-TYPE
        SYNTAX INTEGER { dce(1), dte(2) }
        ACCESS read-only
        STATUS mandatory
        DESCRIPTION "An indication of whether this device is attached to a 
                     DCE (a computer) or a DTE (a terminal). Like
                     cpsvt100CableMode(14), this status is derived from the
                     type of cable that is attached to the copper interface."
        ::= { cpsvt100Entry 15 }

cpsvt100InvertTX OBJECT-TYPE
        SYNTAX INTEGER { rising(1), falling(2) }
        ACCESS read-only
        STATUS mandatory
        DESCRIPTION "Local transmit clock usage.  Some types of high-speed
                     serial equipment read the data signal on the rising edge
                     of the clock, and others on the falling edge of the clock.
                     The CPSVT100-xxx High Speed Serial converter is compatible
                     with both types of equipment. The expectations of the
                     equipment attached to the copper interface can be matched
                     via jumper settings on the converter.
                     The cpsvt100InvertTX(16) and cpsvt100InvertRX(17) status
                     variables indicate the status of these jumpers.  Most
                     high-speed serial equipment uses the rising edge of
                     the clock."
        ::= { cpsvt100Entry 16 }

cpsvt100InvertRX OBJECT-TYPE
        SYNTAX INTEGER { rising(1), falling(2) }
        ACCESS read-only
        STATUS mandatory
        DESCRIPTION "Local receive clock usage.  Some types of high-speed
                     serial equipment read the data signal on the rising edge
                     of the clock, and others on the falling edge of the clock.
                     The CPSVT100-xxx High Speed Serial converter is compatible
                     with both types of equipment. The expectations of the
                     equipment attached to the copper interface can be matched
                     via jumper settings on the converter.
                     The cpsvt100InvertTX(16) and cpsvt100InvertRX(17) status
                     variables indicate the status of these jumpers.  Most
                     high-speed serial equipment uses the rising edge of
                     the clock."
        ::= { cpsvt100Entry 17 }

cpsvt100ConfigMode OBJECT-TYPE
        SYNTAX INTEGER { software(1), hardware(2) }
        ACCESS read-only
        STATUS mandatory
        DESCRIPTION "This device has a jumper or switch that disables 
                     software management of the device. When ConfigMode is
                     hardware(2), SNMP management is disabled, and all
                     configuration control comes from physical switches or
                     jumpers on the device."
        ::= { cpsvt100Entry 18 }

cpsvt100FirmwareRev OBJECT-TYPE
        SYNTAX INTEGER
        ACCESS read-only
        STATUS mandatory
        DESCRIPTION "Local firmware revision."
        ::= { cpsvt100Entry 19 }

cpsvt100RmtDetected OBJECT-TYPE
        SYNTAX INTEGER { yes(1), no(2) }
        ACCESS read-only
        STATUS mandatory
        DESCRIPTION "Has the value yes(1) if management communcations
                     have been established with a remote media converter."
        ::= { cpsvt100Entry 20 }

cpsvt100RmtTermTiming OBJECT-TYPE
        SYNTAX INTEGER { rxc(1), kbps56(2), kbps64(3), kbps112(4), kbps128(5), 
                         kbps256(6), kbps384(7), kbps512(8), kbps768(9), 
                         kbps1024(10), kbps1554(11), kbps2048(12), kbps3072(13),
                         kbps4096(14), kbps6144(15), asynchronous(16) }
        ACCESS read-write
        STATUS mandatory
        DESCRIPTION "Local Terminal Timing setting of the remotely managed
                     CPSVTxxx.  Terminal timing is a signal sent from a DCE 
                     to a DTE to control the rate of data the DTE sends to
                     the DCE. Since this signal cannot be sent across the 
                     fiber after media converters are introduced, the converter
                     must generate this signal and supply it to the DTE. The
                     converter gets the setting from a thumbwheel.  For
                     converters attached to DTEs, the thumbwheel setting
                     influences the transmit data rate. If the Terminal Timing
                     setting is RXC, the DTE derives its transmit clock from
                     the receive clock supplied by the DCE.  For converters
                     attached to DCEs, the thumbwheel setting has no effect.
                     If two DTEs are connected via media converters, the
                     thumbwheel settings must not be RXC."
        ::= { cpsvt100Entry 21 }

cpsvt100RmtLoopBack OBJECT-TYPE
        SYNTAX INTEGER { enabled(1), disabled(2) }
        ACCESS read-write
        STATUS mandatory
        DESCRIPTION "Remote fiber and copper loopback setting.  Loopback is 
                     a testing aid available on several different products. 
                     When Loopback is enabled on an interface, all data that
                     is sent to the interface is reflected back to the sender,
                     and the actual condition (or even existence) of the 
                     equipment on the opposite interface is ignored.  This
                     variable is identical to cpsvt100LoopBack, except that
                     it is for the remotely managed cpsvt100."
        ::= { cpsvt100Entry 22 }

cpsvt100RmtCableMode OBJECT-TYPE
        SYNTAX INTEGER 
        ACCESS read-write
        STATUS mandatory
        DESCRIPTION "A description of the type of cable that is attached to 
                     the Copper interface of the local device."
        ::= { cpsvt100Entry 23 }

cpsvt100RmtDCE OBJECT-TYPE
        SYNTAX INTEGER
        ACCESS read-write
        STATUS mandatory
        DESCRIPTION "An indication of whether this device is attached to a 
                     DCE (a computer) or a DTE (a terminal). Like
                     cpsvt100CableMode(14), this status is derived from the
                     type of cable that is attached to the copper interface."
        ::= { cpsvt100Entry 24 }

cpsvt100RmtInvertTX OBJECT-TYPE
        SYNTAX INTEGER
        ACCESS read-write
        STATUS mandatory
        DESCRIPTION "Local transmit clock usage.  Some types of high-speed
                     serial equipment read the data signal on the rising edge
                     of the clock, and others on the falling edge of the clock.
                     The CPSVT100-xxx High Speed Serial converter is compatible
                     with both types of equipment. The expectations of the
                     equipment attached to the copper interface can be matched
                     via jumper settings on the converter.
                     The cpsvt100InvertTX(16) and cpsvt100InvertRX(17) status
                     variables indicate the status of these jumpers.  Most
                     high-speed serial equipment uses the rising edge of
                     the clock."
        ::= { cpsvt100Entry 25 }

cpsvt100RmtInvertRX OBJECT-TYPE
        SYNTAX INTEGER
        ACCESS read-write
        STATUS mandatory
        DESCRIPTION "Local receive clock usage.  Some types of high-speed
                     serial equipment read the data signal on the rising edge
                     of the clock, and others on the falling edge of the clock.
                     The CPSVT100-xxx High Speed Serial converter is compatible
                     with both types of equipment. The expectations of the
                     equipment attached to the copper interface can be matched
                     via jumper settings on the converter.
                     The cpsvt100InvertTX(16) and cpsvt100InvertRX(17) status
                     variables indicate the status of these jumpers.  Most
                     high-speed serial equipment uses the rising edge of
                     the clock."
        ::= { cpsvt100Entry 26 }

cpsvt100RmtConfigMode OBJECT-TYPE
        SYNTAX INTEGER { software(1), hardware(2) }
        ACCESS read-only
        STATUS mandatory
        DESCRIPTION "This device has a jumper or switch that disables 
                     software management of the device. When ConfigMode is
                     hardware(2), SNMP management is disabled, and all
                     configuration control comes from physical switches or
                     jumpers on the device."
        ::= { cpsvt100Entry 27 }

cpsvt100RmtFirmwareRev OBJECT-TYPE
        SYNTAX INTEGER
        ACCESS read-only
        STATUS mandatory
        DESCRIPTION "Local firmware revision."
        ::= { cpsvt100Entry 28 }

cpsvt100RmtCopperLink OBJECT-TYPE
        SYNTAX INTEGER { linkUp(1), linkDown(2) }
        ACCESS read-only
        STATUS mandatory
        DESCRIPTION "Status of Copper Link for this device"
        ::= { cpsvt100Entry 29 }

cpsvt100RmtFiberLink OBJECT-TYPE
        SYNTAX INTEGER { linkUp(1), linkDown(2) }
        ACCESS read-only
        STATUS mandatory
        DESCRIPTION "Status of Fiber Link for this device"
        ::= { cpsvt100Entry 30 }

cpsvt100CacheClean OBJECT-TYPE
        SYNTAX INTEGER { clean(1), dirty(2) }
        ACCESS read-only
        STATUS mandatory
        DESCRIPTION "When the value is clean(1)Device and Management Module
                     cache are synchronized, no automatic corrections to 
                     configuration will occur.  When the value is dirty(2)
                     Device and Management Module cache are not synchronized.
                     The configuration currently displayed by the application 
                     has not been validated by the device. The device may 
                     need to correct the configuration, in which case the 
                     displayed configuration will change."
        ::= { cpsvt100Entry 31 }

-- ========================================================================
-- Table for a cemtf100 slide in card.

cemtf100Table OBJECT-TYPE
        SYNTAX SEQUENCE OF Cemtf100Entry
        ACCESS not-accessible
        STATUS mandatory
        DESCRIPTION "Sparse table containing one entry for each CEMTF100 
                     in the stack, indexed by cabinet serial number and slot."
        ::= { cpsSlotDetail 19 }

cemtf100Entry OBJECT-TYPE
        SYNTAX Cemtf100Entry
        ACCESS not-accessible
        STATUS mandatory
        DESCRIPTION "Status and configuration entries for a single CEMTF100"
        INDEX { cemtf100BiaIndex, cemtf100SlotIndex }
        ::= { cemtf100Table 1 }

Cemtf100Entry ::=
        SEQUENCE {
                 cemtf100BiaIndex            INTEGER,
                 cemtf100SlotIndex           INTEGER,
                 cemtf100Groups              DisplayString,
                 cemtf100MRevision           INTEGER,
                 cemtf100CfgMatch            INTEGER,
                 cemtf100SerialNumber        INTEGER,
                 cemtf100FiberLink           INTEGER,
                 cemtf100OffHook             INTEGER,
                 cemtf100Fault               INTEGER,
                 cemtf100ConnA               INTEGER,
                 cemtf100ConnB               INTEGER,
                 cemtf100CacheClean          INTEGER
                 }

cemtf100BiaIndex OBJECT-TYPE
        SYNTAX INTEGER
        ACCESS read-only
        STATUS mandatory
        DESCRIPTION "The serial number (BIA) of the cabinet in which the 
                     device is installed"
        ::= { cemtf100Entry 1 }

cemtf100SlotIndex OBJECT-TYPE
        SYNTAX INTEGER
        ACCESS read-only
        STATUS mandatory
        DESCRIPTION "The slot in which the device is installed"
        ::= { cemtf100Entry 2 }

cemtf100Groups OBJECT-TYPE
        SYNTAX DisplayString
        ACCESS read-write
        STATUS mandatory
        DESCRIPTION "User-defined keywords that group this device together with
                     other devices under a user-defined scheme. By placing 
                     matching keywords in cpsGroupCtrl.0, the agent can be
                     instructed to apply configuration changes simultaneously
                     to all group members rather than to individual devices.
                     Every Groups string has three automatically defined
                     implied values: 
                     1) The model family of the device, e.g. 'CEMTF100'
                     2) The serial number of the cabinet in which the device
                        is installed, in decimal with no leading zeroes, 
                        e.g. '12345', and 
                     3) same as 2, with the slot in which the device is 
                        installed appended, enclosed in square brackets. 
                        e.g. '12345[9]'"
        ::= { cemtf100Entry 3 }

cemtf100MRevision OBJECT-TYPE
        SYNTAX INTEGER
        ACCESS read-only
        STATUS mandatory
        DESCRIPTION "The marketing revision of this device"
        ::= { cemtf100Entry 4 }

cemtf100CfgMatch OBJECT-TYPE
        SYNTAX INTEGER { yes(1), no(2), notApplicable(3) }
        ACCESS read-only
        STATUS mandatory
        DESCRIPTION "yes(1) indicates that the conditions specified in 
                     cpsGroupCtrl.0 match the Groups value for this
                     device. no(2) means that there is no match.
                     notApplicable(3) indicates that cpsGroupCtrl.0 is null
                     and therefore no comparison was performed."
        ::= { cemtf100Entry 5 }

cemtf100SerialNumber OBJECT-TYPE
        SYNTAX INTEGER 
        ACCESS read-only
        STATUS mandatory
        DESCRIPTION "The serial number of this device"
        ::= { cemtf100Entry 6 }

cemtf100FiberLink OBJECT-TYPE
        SYNTAX INTEGER { linkUp(1), linkDown(2) }
        ACCESS read-only
        STATUS mandatory
        DESCRIPTION "Status of Fiber Link for this device"
        ::= { cemtf100Entry 7 }

cemtf100OffHook OBJECT-TYPE
        SYNTAX INTEGER { yes(1), no(2) }
        ACCESS read-only
        STATUS mandatory
        DESCRIPTION "Status of Twisted Pair Link for this device"
        ::= { cemtf100Entry 8 }

cemtf100Fault OBJECT-TYPE
        SYNTAX INTEGER { yes(1), no(2) }
        ACCESS read-only
        STATUS mandatory
        DESCRIPTION "Value is yes(1) when either OffHook or FiberLink 
                     has value of down"
        ::= { cemtf100Entry 9 }

cemtf100ConnA OBJECT-TYPE
        SYNTAX CpsConnector
        ACCESS read-only
        STATUS mandatory
        DESCRIPTION "The style of Fiber connector built into this device"
        ::= { cemtf100Entry 10 }

cemtf100ConnB OBJECT-TYPE
        SYNTAX CpsConnector
        ACCESS read-only
        STATUS mandatory
        DESCRIPTION "The style of Copper connector built into this device"
        ::= { cemtf100Entry 11 }

cemtf100CacheClean OBJECT-TYPE
        SYNTAX INTEGER { clean(1), dirty(2) }
        ACCESS read-only
        STATUS mandatory
        DESCRIPTION "When the value is clean(1)Device and Management Module
                     cache are synchronized, no automatic corrections to 
                     configuration will occur.  When the value is dirty(2)
                     Device and Management Module cache are not synchronized.
                     The configuration currently displayed by the application 
                     has not been validated by the device. The device may 
                     need to correct the configuration, in which case the 
                     displayed configuration will change."
        ::= { cemtf100Entry 12 }

-- ========================================================================
-- Table for a captf100 slide in card.

captf100Table OBJECT-TYPE
        SYNTAX SEQUENCE OF Captf100Entry
        ACCESS not-accessible
        STATUS mandatory
        DESCRIPTION "Sparse table containing one entry for each CAPTF100 
                     in the stack, indexed by cabinet serial number and slot."
        ::= { cpsSlotDetail 20 }

captf100Entry OBJECT-TYPE
        SYNTAX Captf100Entry
        ACCESS not-accessible
        STATUS mandatory
        DESCRIPTION "Status and configuration entries for a single CAPTF100"
        INDEX { captf100BiaIndex, captf100SlotIndex }
        ::= { captf100Table 1 }

Captf100Entry ::=
        SEQUENCE {
                 captf100BiaIndex            INTEGER,
                 captf100SlotIndex           INTEGER,
                 captf100Groups              DisplayString,
                 captf100MRevision           INTEGER,
                 captf100CfgMatch            INTEGER,
                 captf100SerialNumber        INTEGER,
                 captf100FiberLink           INTEGER,
                 captf100InUse               INTEGER,
                 captf100Fault               INTEGER,
                 captf100ConnA               INTEGER,
                 captf100ConnB               INTEGER,
                 captf100FirmwareRev         INTEGER,
                 captf100CacheClean          INTEGER,
                 captf100Emulates            INTEGER
                 }

captf100BiaIndex OBJECT-TYPE
        SYNTAX INTEGER
        ACCESS read-only
        STATUS mandatory
        DESCRIPTION "The serial number (BIA) of the cabinet in which the 
                     device is installed"
        ::= { captf100Entry 1 }

captf100SlotIndex OBJECT-TYPE
        SYNTAX INTEGER
        ACCESS read-only
        STATUS mandatory
        DESCRIPTION "The slot in which the device is installed"
        ::= { captf100Entry 2 }

captf100Groups OBJECT-TYPE
        SYNTAX DisplayString
        ACCESS read-write
        STATUS mandatory
        DESCRIPTION "User-defined keywords that group this device together with
                     other devices under a user-defined scheme. By placing 
                     matching keywords in cpsGroupCtrl.0, the agent can be
                     instructed to apply configuration changes simultaneously
                     to all group members rather than to individual devices.
                     Every Groups string has three automatically defined
                     implied values: 
                     1) The model family of the device, e.g. 'CAPTF100'
                     2) The serial number of the cabinet in which the device
                        is installed, in decimal with no leading zeroes, 
                        e.g. '12345', and 
                     3) same as 2, with the slot in which the device is 
                        installed appended, enclosed in square brackets. 
                        e.g. '12345[9]'"
        ::= { captf100Entry 3 }

captf100MRevision OBJECT-TYPE
        SYNTAX INTEGER
        ACCESS read-only
        STATUS mandatory
        DESCRIPTION "The marketing revision of this device"
        ::= { captf100Entry 4 }

captf100CfgMatch OBJECT-TYPE
        SYNTAX INTEGER { yes(1), no(2), notApplicable(3) }
        ACCESS read-only
        STATUS mandatory
        DESCRIPTION "yes(1) indicates that the conditions specified in 
                     cpsGroupCtrl.0 match the Groups value for this
                     device. no(2) means that there is no match.
                     notApplicable(3) indicates that cpsGroupCtrl.0 is null
                     and therefore no comparison was performed."
        ::= { captf100Entry 5 }

captf100SerialNumber OBJECT-TYPE
        SYNTAX INTEGER 
        ACCESS read-only
        STATUS mandatory
        DESCRIPTION "The serial number of this device"
        ::= { captf100Entry 6 }

captf100FiberLink OBJECT-TYPE
        SYNTAX INTEGER { linkUp(1), linkDown(2) }
        ACCESS read-only
        STATUS mandatory
        DESCRIPTION "Status of Fiber Link for this device"
        ::= { captf100Entry 7 }

captf100InUse OBJECT-TYPE
        SYNTAX INTEGER { yes(1), no(2) }
        ACCESS read-only
        STATUS mandatory
        DESCRIPTION "Status of Twisted Pair Link for this device"
        ::= { captf100Entry 8 }

captf100Fault OBJECT-TYPE
        SYNTAX INTEGER { yes(1), no(2) }
        ACCESS read-only
        STATUS mandatory
        DESCRIPTION "Value is yes(1) when either OffHook or FiberLink 
                     has value of down"
        ::= { captf100Entry 9 }

captf100ConnA OBJECT-TYPE
        SYNTAX CpsConnector
        ACCESS read-only
        STATUS mandatory
        DESCRIPTION "The style of Fiber connector built into this device"
        ::= { captf100Entry 10 }

captf100ConnB OBJECT-TYPE
        SYNTAX CpsConnector
        ACCESS read-only
        STATUS mandatory
        DESCRIPTION "The style of Copper connector built into this device"
        ::= { captf100Entry 11 }

captf100FirmwareRev OBJECT-TYPE
        SYNTAX INTEGER
        ACCESS read-only
        STATUS mandatory
        DESCRIPTION "The firmware revision level for this device."
        ::= { captf100Entry 12 }

captf100CacheClean OBJECT-TYPE
        SYNTAX INTEGER { clean(1), dirty(2) }
        ACCESS read-only
        STATUS mandatory
        DESCRIPTION "When the value is clean(1)Device and Management Module
                     cache are synchronized, no automatic corrections to 
                     configuration will occur.  When the value is dirty(2)
                     Device and Management Module cache are not synchronized.
                     The configuration currently displayed by the application 
                     has not been validated by the device. The device may 
                     need to correct the configuration, in which case the 
                     displayed configuration will change."
        ::= { captf100Entry 13 }

captf100Emulates OBJECT-TYPE
        SYNTAX INTEGER { phone(1), coStandard(2), coAutoRingDown(3) }
        ACCESS read-only
        STATUS mandatory
        DESCRIPTION "This read-only variable indicates the emulation type and
                     configuration of the device.
                     CAPTF100 devices exist in two varieties, the 
                     CAPTF10033xx-100, the copper port of which emulates a 
                     telephone, and the CAPTF10033xx-110, the copper port of 
                     which emulates the Central Office (CO) (i.e. a wall jack
                     that one would plug a telephone into).
                     The Standard CAPTF100 configuration is employed when a 
                     fiber extension between a wall jack and a distant telephone
                     is desired. The CAPTF100 whose copper port was plugged into
                     the wall jack must be of the variety that emulates a 
                     telephone. The value of the captf100Emulates(14) variable 
                     of such a device will be phone(1). The CAPTF100 whose copper 
                     port was plugged into the telephone must be of the variety 
                     that emulates the CO, and that device must be jumpered for
                     'Standard' operation. The value of its captf100Emulates(14)
                     variable would be coStandard(2).
                     Alternatively, CAPTF100 converters can be used to provide a
                     point-to-point fiber link between two telephones. This is 
                     known as the Automatic Ring-Down configuration. When one 
                     telephone goes off-hook, the other rings. When both are off
                     hook, voice communication is possible. In this configuration,
                     both CAPTF100 devices must be of the variety that emulates 
                     the CO, and both devices must be jumpered for 'Automatic 
                     Ring-Down' operation. The value of their captf100Emulates(14)
                     variables would be coAutoRingDown(3)."
        ::= { captf100Entry 14 }


-- ==================================================================
-- Table for a cfetf205 slide in card.

cfetf205Table OBJECT-TYPE
        SYNTAX SEQUENCE OF Cfetf205Entry
        ACCESS not-accessible
        STATUS mandatory
        DESCRIPTION "Sparse table containing one entry for each CFTEF205
                     100Mbps Twisted-Pair to Fiber Ethernet Media Converter
                     in the stack, indexed by cabinet serial number and slot."
        ::= { cpsSlotDetail 21 }

cfetf205Entry OBJECT-TYPE
        SYNTAX Cfetf205Entry
        ACCESS not-accessible
        STATUS mandatory
        DESCRIPTION "Status and configuration entries for a single CFETF205"
        INDEX { cfetf205BiaIndex, cfetf205SlotIndex }
        ::= { cfetf205Table 1 }

Cfetf205Entry ::=
        SEQUENCE {
                 cfetf205BiaIndex            INTEGER,
                 cfetf205SlotIndex           INTEGER,
                 cfetf205Groups              DisplayString,
                 cfetf205MRevision           INTEGER,
                 cfetf205CfgMatch            INTEGER,
                 cfetf205SerialNumber        INTEGER,
                 cfetf205ConnA               INTEGER,
                 cfetf205ConnB               INTEGER,
                 cfetf205TPLink              INTEGER,
                 cfetf205FiberLink           INTEGER,
                 cfetf205Fault               INTEGER,
                 cfetf205FastLinkPulse       INTEGER,
                 cfetf205Enabled             INTEGER,
                 cfetf205Pause               INTEGER,
                 cfetf205LinkPassThrough     INTEGER,
                 cfetf205AutoCross           INTEGER,
                 cfetf205TPActivity          INTEGER,
                 cfetf205FiberActivity       INTEGER,
                 cfetf205ConfigMode          INTEGER,
                 cfetf205FarEndFault         INTEGER,
                 cfetf205CacheClean          INTEGER
                 }

cfetf205BiaIndex OBJECT-TYPE
        SYNTAX INTEGER
        ACCESS read-only
        STATUS mandatory
        DESCRIPTION "The serial number (BIA) of the cabinet in which the 
                     device is installed"
        ::= { cfetf205Entry 1 }

cfetf205SlotIndex OBJECT-TYPE
        SYNTAX INTEGER
        ACCESS read-only
        STATUS mandatory
        DESCRIPTION "The slot in which the device is installed"
        ::= { cfetf205Entry 2 }

cfetf205Groups OBJECT-TYPE
        SYNTAX DisplayString
        ACCESS read-write
        STATUS mandatory
        DESCRIPTION "User-defined keywords that group this device together with
                     other devices under a user-defined scheme. By placing 
                     matching keywords in cpsGroupCtrl.0, the agent can be
                     instructed to apply configuration changes simultaneously
                     to all group members rather than to individual devices.
                     Every Groups string has three automatically defined
                     implied values: 
                     1) The model family of the device, e.g. 'CFETF205'
                     2) The serial number of the cabinet in which the device
                        is installed, in decimal with no leading zeroes, 
                        e.g. '12345', and 
                     3) same as 2, with the slot in which the device is 
                        installed appended, enclosed in square brackets. 
                        e.g. '12345[9]'"
        ::= { cfetf205Entry 3 }

cfetf205MRevision OBJECT-TYPE
        SYNTAX INTEGER
        ACCESS read-only
        STATUS mandatory
        DESCRIPTION "The marketing revision of this device"
        ::= { cfetf205Entry 4 }

cfetf205CfgMatch OBJECT-TYPE
        SYNTAX INTEGER { yes(1), no(2), notApplicable(3) }
        ACCESS read-only
        STATUS mandatory
        DESCRIPTION "yes(1) indicates that the conditions specified in 
                     cpsGroupCtrl.0 match the Groups value for this
                     device. no(2) means that there is no match.
                     notApplicable(3) indicates that cpsGroupCtrl.0 is null
                     and therefore no comparison was performed."
        ::= { cfetf205Entry 5 }

cfetf205SerialNumber OBJECT-TYPE
        SYNTAX INTEGER 
        ACCESS read-only
        STATUS mandatory
        DESCRIPTION "The serial number of this device"
        ::= { cfetf205Entry 6 }

cfetf205ConnA OBJECT-TYPE
        SYNTAX CpsConnector
        ACCESS read-only
        STATUS mandatory
        DESCRIPTION "The style of Fiber connector built into this device"
        ::= { cfetf205Entry 7 }

cfetf205ConnB OBJECT-TYPE
        SYNTAX CpsConnector
        ACCESS read-only
        STATUS mandatory
        DESCRIPTION "The style of Copper connector built into this device"
        ::= { cfetf205Entry 8 }

cfetf205TPLink OBJECT-TYPE
        SYNTAX INTEGER { linkUp(1), linkDown(2) }
        ACCESS read-only
        STATUS mandatory
        DESCRIPTION "Status of Twisted Pair Link for this device"
        ::= { cfetf205Entry 9 }

cfetf205FiberLink OBJECT-TYPE
        SYNTAX INTEGER { linkUp(1), linkDown(2) }
        ACCESS read-only
        STATUS mandatory
        DESCRIPTION "Status of Fiber Link for this device"
        ::= { cfetf205Entry 10 }

cfetf205Fault OBJECT-TYPE
        SYNTAX INTEGER { yes(1), no(2) }
        ACCESS read-only
        STATUS mandatory
        DESCRIPTION "Value is yes(1) when either TPLink or FiberLink 
                     has value linkDown(2)"
        ::= { cfetf205Entry 11 }

cfetf205FastLinkPulse OBJECT-TYPE
        SYNTAX INTEGER { autonegotiate(1), hdx100Btx(2) }
        ACCESS read-write
        STATUS mandatory
        DESCRIPTION "When set to autonegotiate(1), converter sends
                     Fast Link Pulses on its twisted pair port, thereby
                     participating in autonegotiation of duplex between 
                     the converter's twisted pair port and that of the
                     connected station. If that station supports Full-
                     Duplex (FDX) operation, FDX will be used. If not, the
                     twisted pair will operate in Half-Duplex (HDX) mode.
                     When set to hdx100Btx(2), the converter instead sends
                     100Mbps idles (rather than Fast Link Pulses) on its 
                     twisted pair port (i.e. it declines to negotiate), which
                     forces the twisted pair to operate in HDX mode
                     regardless of the capabilities of the connected station.
                     When operating in HDX mode, the twisted pair can support
                     traffic in only one direction at a time. In FDX mode,
                     traffic can pass in both directions simultaneously, thus
                     theoretically doubling network performance."
        ::= { cfetf205Entry 12 }

cfetf205Enabled OBJECT-TYPE
        SYNTAX INTEGER { yes(1), no(2) }
        ACCESS read-write
        STATUS mandatory
        DESCRIPTION "When this configuration item is set to no(2), the
                     device passes no network traffic."
        ::= { cfetf205Entry 13 }

cfetf205Pause OBJECT-TYPE
        SYNTAX INTEGER { enabled(1), disabled(2) }
        ACCESS read-write
        STATUS mandatory
        DESCRIPTION "The Pause feature allows Ethernet MACs that support it to
                     send data pacing 'Pause' messages to each other. 
                     Support for Pause is negotiated at the physical level and
                     passed up to the MAC. While the MAC's Pause messages 
                     themselves can pass over the fiber link that this pair
                     of media converters introduces, the TP physical layer
                     negotiations to enable Pause can not. Therefore, if both 
                     end station MACs support Pause and wish to use it, the
                     Pause negotiation must be re-generated by the media
                     converters on both ends. By setting this configuration
                     option to enabled(1), you are indicating to the local
                     twisted pair station that the twisted pair station on 
                     the other side of the other media converter supports 
                     Pause and wishes to use it. This variable must be set 
                     consistently on both of the paired media converters."
        ::= { cfetf205Entry 14 }

cfetf205LinkPassThrough OBJECT-TYPE
        SYNTAX INTEGER { enabled(1), disabled(2) }
        ACCESS read-write
        STATUS mandatory
        DESCRIPTION "Enable/Disable for Link Pass Through, a feature that
                     causes loss of link on one side of a media converter
                     to be passed through to the other side, so that 
                     upstream equipment can see the fault condition."
        ::= { cfetf205Entry 15 }

cfetf205AutoCross OBJECT-TYPE
        SYNTAX INTEGER { enabled(1), disabled(2) }
        ACCESS read-write
        STATUS mandatory
        DESCRIPTION "Enable/Disable for automatic copper TX/RX pair correction.
                     When disabled, the port operates in MDI mode."
        ::= { cfetf205Entry 16 }

cfetf205TPActivity OBJECT-TYPE
        SYNTAX INTEGER { yes(1), no(2), notSupported(3) }
        ACCESS read-only
        STATUS mandatory
        DESCRIPTION "Network traffic indicator for Copper side of this device"
        ::= { cfetf205Entry 17 }

cfetf205FiberActivity OBJECT-TYPE
        SYNTAX INTEGER { yes(1), no(2), notSupported(3) }
        ACCESS read-only
        STATUS mandatory
        DESCRIPTION "Network traffic indicator for Fiber side of this device"
        ::= { cfetf205Entry 18 }

cfetf205ConfigMode OBJECT-TYPE
        SYNTAX INTEGER { software(1), hardware(2) }
        ACCESS read-only
        STATUS mandatory
        DESCRIPTION "This device has a jumper or switch that disables 
                     software management of the device. When ConfigMode is
                     hardware(2), SNMP management is disabled, and all
                     configuration control comes from physical switches or
                     jumpers on the device."
        ::= { cfetf205Entry 19 }

cfetf205FarEndFault OBJECT-TYPE
        SYNTAX INTEGER { enabled(1), disabled(2), notSupported(3) }
        ACCESS read-write
        STATUS mandatory
        DESCRIPTION "Far End Fault configuration of this device.  Far End Fault
                     causes the fiber transmitter to generate a Far End Fault
                     pattern upon the loss of a receiver signal detect.  When
                     the receiver detects signal again, the transmitter stops
                     transmitting the Far End Fault pattern."
        ::= { cfetf205Entry 20 }

cfetf205CacheClean OBJECT-TYPE
        SYNTAX INTEGER { clean(1), dirty(2) }
        ACCESS read-only
        STATUS mandatory
        DESCRIPTION "When the value is clean(1)Device and Management Module
                     cache are synchronized, no automatic corrections to 
                     configuration will occur.  When the value is dirty(2)
                     Device and Management Module cache are not synchronized.
                     The configuration currently displayed by the application 
                     has not been validated by the device. The device may 
                     need to correct the configuration, in which case the 
                     displayed configuration will change."
        ::= { cfetf205Entry 21 }

-- ================================================================
-- Table for the cbftf150

cbftf150Table OBJECT-TYPE
        SYNTAX SEQUENCE OF Cbftf150Entry
        ACCESS not-accessible
        STATUS mandatory
        DESCRIPTION "Sparse table containing one entry for each CBFTF150
                     switch in the stack.
                     Indexed by sub-device index, cabinet serial number, 
                     and slot. Note that some columns of this table 
                     support multiple subdevices, and some do not. 
                     For example, there is exactly one SerialNumber 
                     for each CBFTF150. No subdevices exist, so the 
                     placeholder value 1 is used as the subdevice index.
                     However, a CBFTF150 has multiple switch ports, which
                     are indexed as different subdevices, starting with 1.
                     Columns with subdevices have names ending in 'Tbl'"
        ::= { cpsSlotDetail 22 }

cbftf150Entry OBJECT-TYPE
        SYNTAX Cbftf150Entry
        ACCESS not-accessible
        STATUS mandatory
        DESCRIPTION "Status and configuration entries for a single CBFTF150"
        INDEX { cbftf150SubDeviceIndex, cbftf150BiaIndex, cbftf150SlotIndex }
        ::= { cbftf150Table 1 }

Cbftf150Entry ::=
        SEQUENCE {
                  cbftf150SubDeviceIndex          INTEGER,
                  cbftf150BiaIndex                INTEGER,
                  cbftf150SlotIndex               INTEGER,
                  cbftf150Groups                  DisplayString,
                  cbftf150MRevision               INTEGER,
                  cbftf150CfgMatch                INTEGER,
                  cbftf150SerialNumber            INTEGER,
                  cbftf150ConfigMode              INTEGER,
                  cbftf150FirmwareRevision        INTEGER,
                  cbftf150FormFactor              INTEGER,
                  cbftf150AutoNegotTbl            INTEGER,
                  cbftf150FullDuplexTbl           INTEGER,
                  cbftf150100MbpsTbl              INTEGER,
                  cbftf150CrossTbl                INTEGER,
                  cbftf150FarEndFaultTbl          INTEGER,
                  cbftf150ConnectorTbl            INTEGER,
                  cbftf150LinkTbl                 INTEGER,
                  cbftf150PortCount               INTEGER,
                  cbftf150CacheClean              INTEGER
                  }

cbftf150SubDeviceIndex OBJECT-TYPE
        SYNTAX INTEGER
        ACCESS read-only
        STATUS mandatory
        DESCRIPTION "Generally, individual devices in this MIB are
                     distinguished by BiaIndex and SlotIndex. This 
                     device differs from many in that it contains
                     multiple subdevices (in this case, switch ports).
                     The number of subdevices varies with the manufactured
                     configuration. Subdevices within devices are indexed
                     by BiaIndex, SlotIndex, and SubDeviceIndex.
                     When the subdevice column is read from the table, 
                     the value '1' is always returned."
        ::= { cbftf150Entry 1 } 

cbftf150BiaIndex OBJECT-TYPE
        SYNTAX INTEGER
        ACCESS read-only
        STATUS mandatory
        DESCRIPTION "The serial number (BIA) of the cabinet in which the 
                     device is installed.
                     There are no subdevices for this value, so the
                     placeholder value 1 is always used for that index."
        ::= { cbftf150Entry 2 }

cbftf150SlotIndex OBJECT-TYPE
        SYNTAX INTEGER
        ACCESS read-only
        STATUS mandatory
        DESCRIPTION "The slot in which the device is installed. Power Supplies
                     occupy special slots numbered 125 and higher.
                     There are no subdevices for this value, so the
                     placeholder value 1 is always used for that index."
        ::= { cbftf150Entry 3 }

cbftf150Groups OBJECT-TYPE
        SYNTAX DisplayString
        ACCESS read-write
        STATUS mandatory
        DESCRIPTION "User-defined keywords that group this device together with
                     other devices under a user-defined scheme. By placing 
                     matching keywords in cpsGroupCtrl.0, the agent can be
                     instructed to apply configuration changes simultaneously
                     to all group members rather than to individual devices.
                     Every Groups string has three automatically defined
                     implied values: 
                     1) The model family of the device, e.g. 'cbftf150'
                     2) The serial number of the cabinet in which the device
                        is installed, in decimal with no leading zeroes, 
                        e.g. '12345', and 
                     3) same as 2, with the slot in which the device is 
                        installed appended, enclosed in square brackets. 
                        e.g. '12345[9]'
                     There are no subdevices for this value, so the
                     placeholder value 1 is always used for that index."
        ::= { cbftf150Entry 4 }

cbftf150MRevision OBJECT-TYPE
        SYNTAX INTEGER
        ACCESS read-only
        STATUS mandatory
        DESCRIPTION "The marketing revision of this device.
                     There are no subdevices for this value, so the
                     placeholder value 1 is always used for that index."
        ::= { cbftf150Entry 5 }

cbftf150CfgMatch OBJECT-TYPE
        SYNTAX INTEGER { yes(1), no(2), notApplicable(3) }
        ACCESS read-only
        STATUS mandatory
        DESCRIPTION "yes(1) indicates that the conditions specified in 
                     cpsGroupCtrl.0 match the Groups value for this
                     device. no(2) means that there is no match.
                     notApplicable(3) indicates that cpsGroupCtrl.0 is null
                     and therefore no comparison was performed.
                     There are no subdevices for this value, so the
                     placeholder value 1 is always used for that index."
        ::= { cbftf150Entry 6 }

cbftf150SerialNumber OBJECT-TYPE
        SYNTAX INTEGER
        ACCESS read-only
        STATUS mandatory
        DESCRIPTION "The serial number of this device.
                     There are no subdevices for this value, so the
                     placeholder value 1 is always used for that index."
        ::= { cbftf150Entry 7 }

cbftf150ConfigMode OBJECT-TYPE
        SYNTAX INTEGER { software(1), hardware(2) }
        ACCESS read-only
        STATUS mandatory
        DESCRIPTION "This device may have a jumper or switch that disables 
                     software management of the device. When ConfigMode is
                     hardware(2), SNMP management is disabled, and all
                     configuration control comes from physical switches or
                     jumpers on the device.
                     There are no subdevices for this value, so the
                     placeholder value 1 is always used for that index."
        ::= { cbftf150Entry 8 }

cbftf150FirmwareRevision OBJECT-TYPE
        SYNTAX INTEGER
        ACCESS read-only
        STATUS mandatory
        DESCRIPTION "The firmware revision level for this device.
                     There are no subdevices for this value, so the
                     placeholder value 1 is always used for that index."
        ::= { cbftf150Entry 9 }

cbftf150FormFactor OBJECT-TYPE
        SYNTAX INTEGER { s1W2a(1), s1W1N2a(2), s1W1N1a(3), s2W2N4a(4),
                         s2W1N5a(5) }
        ACCESS read-only
        STATUS mandatory
        DESCRIPTION "A code corresponding to a physical configuration 
                     of the product. This code indicates the number of 
                     slots occupied and the number of physical connectors 
                     present.
                     In the labels for the values above, s indicates the
                     number of slots occupied, W is a count of Wide
                     port positions (which can built as almost any type
                     of connector), and N is a count of narrow port 
                     positions (which are typically twisted pair ports).
                     The lowercase letter at the end differentiates
                     different form factors that would otherwise have
                     identical descriptions under this limited scheme."
        ::= { cbftf150Entry 10 }

cbftf150AutoNegotTbl OBJECT-TYPE
        SYNTAX INTEGER  { enabled(1), disabled(2), notSupported(3) }
        ACCESS read-write
        STATUS mandatory
        DESCRIPTION "Enables or disables autonegtiation of link speed and 
                     duplex for twisted pair ports.  Not supported on Fiber
                     ports.  There are multiple subdevices in this table, 
                     numbering one entry per port."
        ::= { cbftf150Entry 11 }

cbftf150FullDuplexTbl OBJECT-TYPE
        SYNTAX INTEGER { fullDuplex(1), halfDuplex(2), negotiating(3) }
        ACCESS read-write
        STATUS mandatory
        DESCRIPTION "In most cases this is a configuration setting that 
                     controls the duplex mode; fullDuplex is full duplex and 
                     halfDuplex is half duplex.  On twisted pair ports with 
                     autonegotiation enabled, this is a status indication 
                     showing the duplex value decided upon during the 
                     negotiation.  When link is down, autonegotiation has
                     not been completed yet, and the duplex setting is 
                     therefore unknown and the value is negotiating(3).  
                     There are multiple subdevices in this table, numbering 
                     one entry per port."
        ::= { cbftf150Entry 12 }

cbftf150100MbpsTbl OBJECT-TYPE
        SYNTAX INTEGER { mbps100(1), mbps10(2), negotiating(3) }
        ACCESS read-write
        STATUS mandatory
        DESCRIPTION "In most cases this is a configuration setting that 
                     controls the link speed.  On twisted pair ports with 
                     autonegotiation enabled, this is a status indication
                     showing the link speed decided upon during negotiation.  
                     When link is down, autonegotiation has not been completed
                     yet, and the link speed is therefore unknown and is
                     negotiating(3).  This variable is an indicator only for
                     fiber ports; all fiber ports report mbps100(1) at all 
                     times.  There are multiple subdevices in this table, 
                     numbering one entry per port."
        ::= { cbftf150Entry 13 }

cbftf150CrossTbl OBJECT-TYPE
        SYNTAX INTEGER { auto(1), mdi(2), mdix(3), notSupported(4) }
        ACCESS read-write
        STATUS mandatory
        DESCRIPTION "Configuration setting for copper TX/RX pair correction.  
                     A setting of auto(1) causes the port to automatically
                     correct TX/RX pairs if necessary.  If autonegotiation 
                     is disabled on the port, the auto(1) setting is not 
                     supported.  A setting of mdi(2) causes the TX/RX pairs 
                     to be passed straight through with no correction.  A 
                     setting of mdix(3) causes the TX/RX pairs to be swapped.
                     This setting is supprted for copper ports only; a 
                     read-only value of notSupported(4) is returned for
                     fiber ports.  There are multiple subdevices in this table, 
                     numbering one entry per port."
        ::= { cbftf150Entry 14 }

cbftf150FarEndFaultTbl OBJECT-TYPE
        SYNTAX INTEGER { enabled(1), disabled(2), notSupported(3) }
        ACCESS read-write
        STATUS mandatory
        DESCRIPTION "When Far End Fault is set to enabled(1), a loss of
                     link on receive will cause the transmitter to shut down,
                     in order to inform the device at the far end of the
                     link that a fault has occurred. Far End Fault is only
                     supported on fiber ports. A read-only value of 
                     notSupported(3) is returned for copper ports.  There are
                     multiple subdevices in this table, numbering one entry
                     per port."
        ::= { cbftf150Entry 15 }

cbftf150ConnectorTbl OBJECT-TYPE
        SYNTAX CpsConnector
        ACCESS read-only
        STATUS mandatory
        DESCRIPTION "The style of connectors built into each port of this
                     device.  There are multiple subdevices in this table, 
                     numbering one entry per port."  
        ::= { cbftf150Entry 16 }

cbftf150LinkTbl OBJECT-TYPE
        SYNTAX INTEGER { up(1), down(2) }
        ACCESS read-only
        STATUS mandatory
        DESCRIPTION "This table contains the link status of each port in the
                     switch.  There are multiple subdevices in this table, 
                     numbering one entry per port."
        ::= { cbftf150Entry 17 }

cbftf150PortCount OBJECT-TYPE
        SYNTAX INTEGER
        ACCESS read-only
        STATUS mandatory
        DESCRIPTION "A count of the switch ports in this device. i.e. the
                     maximum subdevice index supported by this switch."
        ::= { cbftf150Entry 18 }

cbftf150CacheClean OBJECT-TYPE
        SYNTAX INTEGER { clean(1), dirty(2) }
        ACCESS read-only
        STATUS mandatory
        DESCRIPTION "When the value is clean(1)Device and Management Module
                     cache are synchronized, no automatic corrections to 
                     configuration will occur.  When the value is dirty(2)
                     Device and Management Module cache are not synchronized.
                     The configuration currently displayed by the application 
                     has not been validated by the device. The device may 
                     need to correct the configuration, in which case the 
                     displayed configuration will change."
        ::= { cbftf150Entry 19 }

-- ==================================================================
-- Table for the cgfeb100

cgfeb100Table OBJECT-TYPE
        SYNTAX SEQUENCE OF Cgfeb100Entry
        ACCESS not-accessible
        STATUS mandatory
        DESCRIPTION "Sparse table containing one entry for each CGFEB100
                     10/100/1000 Ethernet to Fiber converter in the stack.
                     Indexed by cabinet serial number and slot."
        ::= { cpsSlotDetail 23 }

cgfeb100Entry OBJECT-TYPE
        SYNTAX Cgfeb100Entry
        ACCESS not-accessible
        STATUS mandatory
        DESCRIPTION "Status and configuration entries for a single CGFEB100"
        INDEX { cgfeb100BiaIndex, cgfeb100SlotIndex }
        ::= { cgfeb100Table 1 }

Cgfeb100Entry ::=
        SEQUENCE {
                  cgfeb100BiaIndex                INTEGER,
                  cgfeb100SlotIndex               INTEGER,
                  cgfeb100Groups                  DisplayString,
                  cgfeb100MRevision               INTEGER,
                  cgfeb100CfgMatch                INTEGER,
                  cgfeb100SerialNumber            INTEGER,
                  cgfeb100ConfigMode              INTEGER,
                  cgfeb100FirmwareRevision        INTEGER,
                  cgfeb100SelfTestFailed          INTEGER,
                  cgfeb100MonitorType             INTEGER,
                  cgfeb100LinkPassThrough         INTEGER,
                  cgfeb100QosEnabled              INTEGER,
                  cgfeb100QosHPThreshold          INTEGER,
                  cgfeb100QosLqWeight             INTEGER,
                  cgfeb100QosHqWeight             INTEGER,
                  cgfeb100ConnA                   INTEGER,
                  cgfeb100TPLink                  INTEGER,
                  cgfeb100TPSpeedCfg              INTEGER,
                  cgfeb100TPSpeedStat             INTEGER,
                  cgfeb100TPFullDuplexCfg         INTEGER,
                  cgfeb100TPFullDuplexStat        INTEGER,
                  cgfeb100TPCrossCfg              INTEGER,
                  cgfeb100TPCrossStat             INTEGER,
                  cgfeb100TPAutoNegot             INTEGER,
                  cgfeb100TPAdv10HDX              INTEGER,
                  cgfeb100TPAdv10FDX              INTEGER,
                  cgfeb100TPAdv100HDX             INTEGER,
                  cgfeb100TPAdv100FDX             INTEGER,
                  cgfeb100TPAdv1000HDX            INTEGER,
                  cgfeb100TPAdv1000FDX            INTEGER,
                  cgfeb100TPLpAdvPause            INTEGER,
                  cgfeb100TPLpAdv10HDX            INTEGER,
                  cgfeb100TPLpAdv10FDX            INTEGER,
                  cgfeb100TPLpAdv100HDX           INTEGER,
                  cgfeb100TPLpAdv100FDX           INTEGER,
                  cgfeb100TPLpAdv1000HDX          INTEGER,
                  cgfeb100TPLpAdv1000FDX          INTEGER,
                  cgfeb100TPAdvPause              INTEGER,
                  cgfeb100TPQosPause              INTEGER,
                  cgfeb100TPSacCfg                INTEGER,
                  cgfeb100TPSacStat               INTEGER,
                  cgfeb100ConnB                   INTEGER,
                  cgfeb100FiberLink               INTEGER,
                  cgfeb100FiberFullDuplexCfg      INTEGER,
                  cgfeb100FiberFullDuplexStat     INTEGER,
                  cgfeb100FiberAutoNegot          INTEGER,
                  cgfeb100FiberAdv1000HDX         INTEGER,
                  cgfeb100FiberAdv1000FDX         INTEGER,
                  cgfeb100FiberLpAdv1000HDX       INTEGER,
                  cgfeb100FiberLpAdv1000FDX       INTEGER,
                  cgfeb100FiberLpAdvPause         INTEGER,
                  cgfeb100FiberAdvPause           INTEGER,
                  cgfeb100FiberQosPause           INTEGER,
                  cgfeb100FiberSacCfg             INTEGER,
                  cgfeb100FiberSacStat            INTEGER,
                  cgfeb100MonitorTap              INTEGER,
                  cgfeb100CacheClean              INTEGER
                  }

cgfeb100BiaIndex OBJECT-TYPE
        SYNTAX INTEGER
        ACCESS read-only
        STATUS mandatory
        DESCRIPTION "The serial number (BIA) of the cabinet in which the 
                     device is installed."
        ::= { cgfeb100Entry 1 }

cgfeb100SlotIndex OBJECT-TYPE
        SYNTAX INTEGER
        ACCESS read-only
        STATUS mandatory
        DESCRIPTION "The slot in which the device is installed. Power Supplies
                     occupy special slots numbered 125 and higher."
        ::= { cgfeb100Entry 2 }

cgfeb100Groups OBJECT-TYPE
        SYNTAX DisplayString
        ACCESS read-write
        STATUS mandatory
        DESCRIPTION "User-defined keywords that group this device together with
                     other devices under a user-defined scheme. By placing 
                     matching keywords in cpsGroupCtrl.0, the agent can be
                     instructed to apply configuration changes simultaneously
                     to all group members rather than to individual devices.
                     Every Groups string has three automatically defined
                     implied values: 
                     1) The model family of the device, e.g. 'cgfeb100'
                     2) The serial number of the cabinet in which the device
                        is installed, in decimal with no leading zeroes, 
                        e.g. '12345', and 
                     3) same as 2, with the slot in which the device is 
                        installed appended, enclosed in square brackets. 
                        e.g. '12345[9]'."
        ::= { cgfeb100Entry 3 }

cgfeb100MRevision OBJECT-TYPE
        SYNTAX INTEGER
        ACCESS read-only
        STATUS mandatory
        DESCRIPTION "The marketing revision of this device."
        ::= { cgfeb100Entry 4 }

cgfeb100CfgMatch OBJECT-TYPE
        SYNTAX INTEGER { yes(1), no(2), notApplicable(3) }
        ACCESS read-only
        STATUS mandatory
        DESCRIPTION "yes(1) indicates that the conditions specified in 
                     cpsGroupCtrl.0 match the Groups value for this
                     device. no(2) means that there is no match.
                     notApplicable(3) indicates that cpsGroupCtrl.0 is null
                     and therefore no comparison was performed."
        ::= { cgfeb100Entry 5 }

cgfeb100SerialNumber OBJECT-TYPE
        SYNTAX INTEGER
        ACCESS read-only
        STATUS mandatory
        DESCRIPTION "The serial number of this device."
        ::= { cgfeb100Entry 6 }

cgfeb100ConfigMode OBJECT-TYPE
        SYNTAX INTEGER { software(1), hardware(2) }
        ACCESS read-only
        STATUS mandatory
        DESCRIPTION "This device may have a jumper or switch that disables 
                     software management of the device. When ConfigMode is
                     hardware(2), SNMP management is disabled, and all
                     configuration control comes from physical switches or
                     jumpers on the device."
        ::= { cgfeb100Entry 7 }

cgfeb100FirmwareRevision OBJECT-TYPE
        SYNTAX INTEGER
        ACCESS read-only
        STATUS mandatory
        DESCRIPTION "The firmware revision level for this device."
        ::= { cgfeb100Entry 8 }

cgfeb100SelfTestFailed OBJECT-TYPE
        SYNTAX INTEGER { yes(1), no(2) }
        ACCESS read-only
        STATUS mandatory
        DESCRIPTION "This variable indicates the status of the pass/fail
                     power on test.  If the power on test fails,
                     normal operation of this device is probably not 
                     possible."
        ::= { cgfeb100Entry 9 }

cgfeb100MonitorType OBJECT-TYPE
        SYNTAX INTEGER { fiber(1), twistedPair(2), notInstalled(3) }
        ACCESS read-only
        STATUS mandatory
        DESCRIPTION "Some versions of this device support the monitoring
                     of network traffic passing through the converter's
                     fiber interface via a dedicated monitoring port to
                     which a capture device can be attached. There are two
                     different versions of the monitoring capability. One
                     has a fiber connector, and the other has a twisted pair
                     connector. Both versions monitor the fiber port. If
                     this variable has the value fiber(1) or twistedPair(2),
                     this means that a monitoring port is present and that
                     port has the specified type of interface. In this case,
                     the device occupies two slots. If the value is
                     notInstalled(3), there is no monitoring capability and
                     the device occupies one slot. See also
                     cgfeb100MonitorTap(56)."
        ::= { cgfeb100Entry 10 }

cgfeb100LinkPassThrough OBJECT-TYPE
        SYNTAX INTEGER { enabled(1), disabled(2), notSupported(3) }
        ACCESS read-write
        STATUS mandatory
        DESCRIPTION "This configuration item allows Link Pass Through to be
                     enabled(1) or disabled(2). Link Passthrough causes loss
                     of link on one side of a media converter to be passed
                     through to the other side, so that upstream equipment can
                     see fault conditions that would otherwise be hidden by
                     the media converters.  On some models, the Link
                     Passthrough logic views receipt of a Far End Fault error
                     pattern as being equivalent to loss of link. The net
                     effect of this is that when either fiber is disconnected,
                     link is dropped on the other side of the converter. 
                     Normally, only the disconnection of the Receive fiber
                     would cause this reaction. "
        ::= { cgfeb100Entry 11 }

cgfeb100QosEnabled OBJECT-TYPE
        SYNTAX INTEGER { enabled(1), disabled(2), notSupported(3) }
        ACCESS read-write
        STATUS mandatory
        DESCRIPTION "This variable allows Quality of Service functions to be
                     enabled or disabled.  This includes the processing of
                     802.1p tags (See cgfeb100QosHPThreshold(13),
                     cgfeb100QosLqWeight(14), and smacf100QosHqWeight(15)),
                     and half-duplex back pressure and full-duplex flow control.
                     (See cgfeb100TpQosPause(39) and cgfeb100FiberQosPause(52))."
        ::= { cgfeb100Entry 12 }

cgfeb100QosHPThreshold OBJECT-TYPE
        SYNTAX INTEGER 
        ACCESS read-write
        STATUS mandatory
        DESCRIPTION "When an incoming 802.1p priority tag value is greater than
                     or equal to this value (from 0 to 7), the incoming packet
                     will be classified as high-priority. Ignored when
                     cgfeb100QosEnable(13) is set to 'disabled(2)'."
        ::= { cgfeb100Entry 13 }

cgfeb100QosLqWeight OBJECT-TYPE
        SYNTAX INTEGER
        ACCESS read-write
        STATUS mandatory
        DESCRIPTION "A value between 1 and 15 indicating the number of packets
                     that should be processed from the low-priority queue before
                     attention is turned to the high-priority queue. Ignored 
                     when cgfeb100QosEnable(13) is set to 'disabled(2)'."
        ::= { cgfeb100Entry 14 }

cgfeb100QosHqWeight OBJECT-TYPE
        SYNTAX INTEGER
        ACCESS read-write
        STATUS mandatory
        DESCRIPTION "A value between 1 and 15 indicating the number of packets
                     that should be processed from the high-priority queue before
                     attention is turned to the low-priority queue. Ignored when
                     cgfeb100QosEnable(13) is set to 'disabled(2)'."
        ::= { cgfeb100Entry 15 }

cgfeb100ConnA OBJECT-TYPE
        SYNTAX CpsConnector
        ACCESS read-only
        STATUS mandatory
        DESCRIPTION "The style of copper connector built into this device."
        ::= { cgfeb100Entry 16 }

cgfeb100TPLink OBJECT-TYPE
        SYNTAX INTEGER { up(1), down(2) }
        ACCESS read-only
        STATUS mandatory
        DESCRIPTION "Twisted Pair link status."
        ::= { cgfeb100Entry 17 }

cgfeb100TPSpeedCfg OBJECT-TYPE
        SYNTAX INTEGER { mbps10(1), mbps100(2), auto(3) }
        ACCESS read-write
        STATUS mandatory
        DESCRIPTION "The desired speed of the Twisted Pair interface. 
                     This speed can be set to 10Mbps(1) or 100Mbps(2).
                     Operation at 1000Mbps requires autonegotiation. When
                     cgfeb100TpAutonegot(24) has the value enabled(1) or
                     cgfeb100ConfigMode(7) has the value hardware(2), this
                     variable has the read-only value auto(3)."
        ::= { cgfeb100Entry 18 }

cgfeb100TPSpeedStat OBJECT-TYPE
        SYNTAX INTEGER { mbps10(1), mbps100(2), mbps1000(3), notApplicable(4) }
        ACCESS read-only
        STATUS mandatory
        DESCRIPTION "The actual speed of the Twisted Pair interface: 
                     10Mbps(1), 100Mbps(2), or 1000Mbps(3). If
                     cgfeb100TpAutonegot(24) has the value enabled(1)
                     and cgfeb100TpLink(17) has the value down(2),
                     this variable has the value notApplicable(4)."
        ::= { cgfeb100Entry 19 }

cgfeb100TPFullDuplexCfg OBJECT-TYPE
        SYNTAX INTEGER { fdx(1), hdx(2), auto(3) }
        ACCESS read-write
        STATUS mandatory
        DESCRIPTION "The desired duplex setting of the Twisted Pair
                     interface. This can be set to fdx(1) (full duplex) 
                     or hdx(2) (half duplex). When cgfeb100TpAutonegot(24)
                     has the value enabled(1) or cgfeb100ConfigMode(7) has
                     the value hardware(2), this variable has the 
                     read-only value auto(3)."
        ::= { cgfeb100Entry 20 }

cgfeb100TPFullDuplexStat OBJECT-TYPE
        SYNTAX INTEGER { fdx(1), hdx(2), notApplicable(3) }
        ACCESS read-only
        STATUS mandatory
        DESCRIPTION "The actual duplex behavior of the Twisted Pair
                     interface. If cgfeb100TpAutonegot(24) has the value
                     enabled(1) and cgfeb100TpLink(17) has the value
                     down(2), this variable has the value notApplicable(4)."
        ::= { cgfeb100Entry 21 }

cgfeb100TPCrossCfg OBJECT-TYPE
        SYNTAX INTEGER { mdi(1), mdix(2), auto(3), notApplicable(4) }
        ACCESS read-write
        STATUS mandatory
        DESCRIPTION "The desired TX/RX Pair orientation of the Twisted Pair
                     interface. This can be set to mdi(1) (straight through),
                     mdix(2) (crossed over), or auto(3). When
                     cgfeb100ConfigMode(7) has the value hardware(2), this 
                     variable has the read-only value notApplicable(4)."
        ::= { cgfeb100Entry 22 }

cgfeb100TPCrossStat OBJECT-TYPE
        SYNTAX INTEGER { mdi(1), mdix(2), auto(3) }
        ACCESS read-only
        STATUS mandatory
        DESCRIPTION "The actual TX/RX Pair orientation of the Twisted Pair
                     interface, usually mdi(1) (straight through) or mdix(2)
                     (crossed over). When the device does not know the pair
                     orientation, this variable has the value auto(3).
                     Depending on the version of the device, it may not be
                     able to report the pair orientation when it is decided
                     automatically. The device will never have an orientation
                     to report when If cgfeb100TpCrossConfig(22) has the
                     value auto(3) and cgfeb100TpLink(17) has the value down(2)."
        ::= { cgfeb100Entry 23 }

cgfeb100TPAutoNegot OBJECT-TYPE
        SYNTAX INTEGER  { enabled(1), disabled(2), notSupported(3) }
        ACCESS read-write
        STATUS mandatory
        DESCRIPTION "Enables or disables autonegtiation of link speed and 
                     duplex for twisted pair ports.  Not supported on Fiber
                     ports."
        ::= { cgfeb100Entry 24 }

cgfeb100TPAdv10HDX OBJECT-TYPE
        SYNTAX INTEGER { enabled(1), disabled(2), notApplicable(3), enabledRO(4),
                         disabledRO(5) }
        ACCESS read-write
        STATUS mandatory
        DESCRIPTION "Enable/disable control for these advertised autonegotiation
                     modes.  If autonegotiation is disabled (because 
                     cgfeb100TpAutonegot(24) has the value disabled(2) or 
                     cgfeb100ConfigMode(7) has the value hardware(2) and the 
                     Autonegotiation hardware switch is disabled), then these 
                     variables have no meaning and return read-only value 
                     notApplicable(3). If the value cannot be changed (because 
                     cgfeb100ConfigMode(7) has the value hardware(2)) and 
                     Autonegotiation is enabled, these variables return the read-
                     only values enabledRO(4) or disabledRO(5)."
        ::= { cgfeb100Entry 25 }

cgfeb100TPAdv10FDX OBJECT-TYPE
        SYNTAX INTEGER { enabled(1), disabled(2), notApplicable(3), enabledRO(4),
                         disabledRO(5) }
        ACCESS read-write
        STATUS mandatory
        DESCRIPTION "Enable/disable control for these advertised autonegotiation
                     modes.  If autonegotiation is disabled (because 
                     cgfeb100TpAutonegot(24) has the value disabled(2) or 
                     cgfeb100ConfigMode(7) has the value hardware(2) and the 
                     Autonegotiation hardware switch is disabled), then these 
                     variables have no meaning and return read-only value 
                     notApplicable(3). If the value cannot be changed (because 
                     cgfeb100ConfigMode(7) has the value hardware(2)) and 
                     Autonegotiation is enabled, these variables return the read-
                     only values enabledRO(4) or disabledRO(5)."
        ::= { cgfeb100Entry 26 }

cgfeb100TPAdv100HDX OBJECT-TYPE
        SYNTAX INTEGER { enabled(1), disabled(2), notApplicable(3), enabledRO(4),
                         disabledRO(5) }
         ACCESS read-write
        STATUS mandatory
        DESCRIPTION "Enable/disable control for these advertised autonegotiation
                     modes.  If autonegotiation is disabled (because 
                     cgfeb100TpAutonegot(24) has the value disabled(2) or 
                     cgfeb100ConfigMode(7) has the value hardware(2) and the 
                     Autonegotiation hardware switch is disabled), then these 
                     variables have no meaning and return read-only value 
                     notApplicable(3). If the value cannot be changed (because 
                     cgfeb100ConfigMode(7) has the value hardware(2)) and 
                     Autonegotiation is enabled, these variables return the read-
                     only values enabledRO(4) or disabledRO(5)."
        ::= { cgfeb100Entry 27 }

cgfeb100TPAdv100FDX OBJECT-TYPE
        SYNTAX INTEGER { enabled(1), disabled(2), notApplicable(3), enabledRO(4),
                         disabledRO(5) }
        ACCESS read-write
        STATUS mandatory
        DESCRIPTION "Enable/disable control for these advertised autonegotiation
                     modes.  If autonegotiation is disabled (because 
                     cgfeb100TpAutonegot(24) has the value disabled(2) or 
                     cgfeb100ConfigMode(7) has the value hardware(2) and the 
                     Autonegotiation hardware switch is disabled), then these 
                     variables have no meaning and return read-only value 
                     notApplicable(3). If the value cannot be changed (because 
                     cgfeb100ConfigMode(7) has the value hardware(2)) and 
                     Autonegotiation is enabled, these variables return the read-
                     only values enabledRO(4) or disabledRO(5)."
        ::= { cgfeb100Entry 28 }

cgfeb100TPAdv1000HDX OBJECT-TYPE
        SYNTAX INTEGER { enabled(1), disabled(2), notApplicable(3), enabledRO(4),
                         disabledRO(5) }
        ACCESS read-write
        STATUS mandatory
        DESCRIPTION "Enable/disable control for these advertised autonegotiation
                     modes.  If autonegotiation is disabled (because 
                     cgfeb100TpAutonegot(24) has the value disabled(2) or 
                     cgfeb100ConfigMode(7) has the value hardware(2) and the 
                     Autonegotiation hardware switch is disabled), then these 
                     variables have no meaning and return read-only value 
                     notApplicable(3). If the value cannot be changed (because 
                     cgfeb100ConfigMode(7) has the value hardware(2)) and 
                     Autonegotiation is enabled, these variables return the read-
                     only values enabledRO(4) or disabledRO(5)."
        ::= { cgfeb100Entry 29 }

cgfeb100TPAdv1000FDX OBJECT-TYPE
        SYNTAX INTEGER { enabled(1), disabled(2), notApplicable(3), enabledRO(4),
                         disabledRO(5) }
        ACCESS read-write
        STATUS mandatory
        DESCRIPTION "Enable/disable control for these advertised autonegotiation
                     modes.  If autonegotiation is disabled (because 
                     cgfeb100TpAutonegot(24) has the value disabled(2) or 
                     cgfeb100ConfigMode(7) has the value hardware(2) and the 
                     Autonegotiation hardware switch is disabled), then these 
                     variables have no meaning and return read-only value 
                     notApplicable(3). If the value cannot be changed (because 
                     cgfeb100ConfigMode(7) has the value hardware(2)) and 
                     Autonegotiation is enabled, these variables return the read-
                     only values enabledRO(4) or disabledRO(5)."
        ::= { cgfeb100Entry 30 }

cgfeb100TPLpAdvPause OBJECT-TYPE
        SYNTAX INTEGER { symetric(1), asymRX(2), asymTX(3), disabled(4), notApplicable(5) }
        ACCESS read-only
        STATUS mandatory
        DESCRIPTION "This read-only variable shows the pause capability
                     advertised by the twisted pair port's link partner.
                     Values 1 through 4 for this variable are the same as
                     those for cgfeb100TpAdvPause(38). If the device does
                     not support the reporting of link partner autonegotiation
                     or cgfeb100TpAutonegot(24) has the value disabled(2),
                     this variable will have the value notApplicable(5)."
        ::= { cgfeb100Entry 31 }

cgfeb100TPLpAdv10HDX OBJECT-TYPE
        SYNTAX INTEGER { yes(1), no(2), notApplicable(3) }
        ACCESS read-write
        STATUS mandatory
        DESCRIPTION "This read-only variable shows twisted pair port's
                     link partner's willingness to connect at 10Mbps Half
                     Duplex. If the device does not support the reporting
                     of link partner autonegotiation or
                     cgfeb100TpAutonegot(24) has the value disabled(2),
                     this variable will have the value notApplicable(3)."
        ::= { cgfeb100Entry 32 }

cgfeb100TPLpAdv10FDX OBJECT-TYPE
        SYNTAX INTEGER { yes(1), no(2), notApplicable(3) }
        ACCESS read-only
        STATUS mandatory
        DESCRIPTION "This read-only variable shows twisted pair port's
                     link partner's willingness to connect at 10Mbps Full
                     Duplex. If the device does not support the reporting
                     of link partner autonegotiation or
                     cgfeb100TpAutonegot(24) has the value disabled(2),
                     this variable will have the value notApplicable(3)."
        ::= { cgfeb100Entry 33 }

cgfeb100TPLpAdv100HDX OBJECT-TYPE
        SYNTAX INTEGER { yes(1), no(2), notApplicable(3) }
        ACCESS read-only
        STATUS mandatory
        DESCRIPTION "This read-only variable shows twisted pair port's
                     link partner's willingness to connect at 100Mbps Half
                     Duplex. If the device does not support the reporting
                     of link partner autonegotiation or
                     cgfeb100TpAutonegot(24) has the value disabled(2),
                     this variable will have the value notApplicable(3)."
        ::= { cgfeb100Entry 34 }

cgfeb100TPLpAdv100FDX OBJECT-TYPE
        SYNTAX INTEGER { yes(1), no(2), notApplicable(3) }
        ACCESS read-only
        STATUS mandatory
        DESCRIPTION "This read-only variable shows twisted pair port's
                     link partner's willingness to connect at 100Mbps Full
                     Duplex. If the device does not support the reporting
                     of link partner autonegotiation or
                     cgfeb100TpAutonegot(24) has the value disabled(2),
                     this variable will have the value notApplicable(3)."
        ::= { cgfeb100Entry 35 }

cgfeb100TPLpAdv1000HDX OBJECT-TYPE
        SYNTAX INTEGER { yes(1), no(2), notApplicable(3) }
        ACCESS read-only
        STATUS mandatory
        DESCRIPTION "This read-only variable shows twisted pair port's
                     link partner's willingness to connect at 1000Mbps Half
                     Duplex. If the device does not support the reporting
                     of link partner autonegotiation or
                     cgfeb100TpAutonegot(24) has the value disabled(2),
                     this variable will have the value notApplicable(3)."
        ::= { cgfeb100Entry 36 }

cgfeb100TPLpAdv1000FDX OBJECT-TYPE
        SYNTAX INTEGER { yes(1), no(2), notApplicable(3) }
        ACCESS read-only
        STATUS mandatory
        DESCRIPTION "This read-only variable shows twisted pair port's
                     link partner's willingness to connect at 1000Mbps Full
                     Duplex. If the device does not support the reporting
                     of link partner autonegotiation or
                     cgfeb100TpAutonegot(24) has the value disabled(2),
                     this variable will have the value notApplicable(3)."
        ::= { cgfeb100Entry 37 }

cgfeb100TPAdvPause OBJECT-TYPE
        SYNTAX INTEGER { symetric(1), asymRX(2), asymTX(3), disabled(4), notApplicable(5),
                         symmetricRO(6), asymRXRO(7), asymTXRO(8), disabledRO(9) }
        ACCESS read-write
        STATUS mandatory
        DESCRIPTION "Enable/disable control for autonegotiation advertising 
                     of Twisted Pair Pause capability.  Selectable values are 
                     symmetric(1), asymRX(2) (asymmetric, pause frames flow towards 
                     the converter), asymTX(3) (asymmetric, pause frames flow 
                     towards the link partner), and disabled(4).
                     If autonegotiation is disabled (because cgfeb100TpAutonegot(24)
                     has the value disabled(2) or cgfeb100ConfigMode(7) has the value
                     hardware(2) and the Autonegotiation hardware switch is disabled),
                     then this variable has no meaning and the read-only value 
                     notApplicable(5) is returned.
                     When cgfeb100TpQosPause(39) has the value disabled(2), negotiated 
                     pause is suppressed and the read-only value notApplicable(5) is 
                     returned.
                     If cgfeb100ConfigMode(7) has the value hardware(2) and the 
                     Autonegotiation hardware switch is enabled, then one of the 
                     following read-only values will be returned: symmetricRO(6), 
                     asymRXRO(7) (asymmetric, pause frames flow towards the converter),
                     asymTXRO(8) (asymmetric, pause frames flow towards the link partner),
                     and disabledRO(9)."
        ::= { cgfeb100Entry 38 }

cgfeb100TPQosPause OBJECT-TYPE
        SYNTAX INTEGER { enabled(1), disabled(2), notApplicable(3) }
        ACCESS read-write
        STATUS mandatory
        DESCRIPTION "This variable allows Twisted Pair Quality Of Service
                     Pause to be enabled or disabled. When cgfeb100QosEnabled(12)
                     is set to enabled(1) and this variable is set to disabled(2),
                     any pause functionality negotiated according to
                     cgfeb100TpAdvPause(38) is suppressed. When
                     cgfeb100QosEnabled(12) is set to disabled(2), this variable
                     has the read-only value notApplicable(3)."
        ::= { cgfeb100Entry 39 }

cgfeb100TPSacCfg OBJECT-TYPE
        SYNTAX INTEGER  { enabled(1), disabled(2) }
        ACCESS read-write
        STATUS mandatory
        DESCRIPTION "This variable allows Source Address Change traps to be
                     enabled or disabled. If enabled, 'Error' traps will be sent
                     as frequently one per polling cycle any time the ethernet
                     source address of any packet received on the Twisted Pair
                     interface is different from the last address received on 
                     that interface during the previous polling cycle."
        ::= { cgfeb100Entry 40 }

cgfeb100TPSacStat OBJECT-TYPE
        SYNTAX INTEGER  { changed(1), constant(2) }
        ACCESS read-only
        STATUS mandatory
        DESCRIPTION "This read-only variable has the value changed(1) if the
                     Ethernet source address received on the Twisted Pair
                     interface changed since the device's previous report to
                     the Mangement Module, and the value constant(2) otherwise.
                     To cause the Management Module to generate a trap when this
                     occurs, set cgfeb100SacConfig(41) to enabled(1)."
        ::= { cgfeb100Entry 41 }

cgfeb100ConnB OBJECT-TYPE
        SYNTAX CpsConnector
        ACCESS read-only
        STATUS mandatory
        DESCRIPTION "The style of Fiber connector built into this device."
        ::= { cgfeb100Entry 42 }

cgfeb100FiberLink OBJECT-TYPE
        SYNTAX INTEGER { up(1), down(2) }
        ACCESS read-only
        STATUS mandatory
        DESCRIPTION "The Fiber Link status for this device."
        ::= { cgfeb100Entry 43 }

cgfeb100FiberFullDuplexCfg OBJECT-TYPE
        SYNTAX INTEGER { fdx(1), hdx(2), auto(3) }
        ACCESS read-write
        STATUS mandatory
        DESCRIPTION "The desired duplex setting of the Fiber
                     interface. This can be set to fdx(1) (full duplex) 
                     or hdx(2) (half duplex). When cgfeb100TpAutonegot(24)
                     has the value enabled(1) or cgfeb100ConfigMode(7) has
                     the value hardware(2), this variable has the 
                     read-only value auto(3)."
        ::= { cgfeb100Entry 44 }

cgfeb100FiberFullDuplexStat OBJECT-TYPE
        SYNTAX INTEGER { fdx(1), hdx(2), notApplicable(3) }
        ACCESS read-only
        STATUS mandatory
        DESCRIPTION "The actual duplex behavior of the Fiber interface:
                     fdx(1) (full duplex) or hdx(2) (half duplex). If 
                     cgfeb100FiberAutonegot(46) has the value disabled(2)
                     and this version of the device does not support manual
                     fiber duplex control, Fiber duplex is forced to HDX.
                     If cgfeb100FiberAutonegot(46) has the value enabled(1)
                     and cgfeb100FiberLink(43) has the value down(2), then
                     no duplex setting is available, and this variable has
                     the value notApplicable(3)."
        ::= { cgfeb100Entry 45 }

cgfeb100FiberAutoNegot OBJECT-TYPE
        SYNTAX INTEGER  { enabled(1), disabled(2), notApplicable(3) }
        ACCESS read-write
        STATUS mandatory
        DESCRIPTION "Autonegotiation configuration. Fiber autonegotiation
                     is limited to the duplex setting. The fiber's speed
                     is fixed at 1000Mbps."
        ::= { cgfeb100Entry 46 }

cgfeb100FiberAdv1000HDX OBJECT-TYPE
        SYNTAX INTEGER { yes(1), no(2), notApplicable(3) }
        ACCESS read-write
        STATUS mandatory
        DESCRIPTION "Enable/disable control for these advertised 
                     autonegotiation modes.
                     If autonegotiation is disabled (because 
                     cgfeb100TpAutonegot(24) has the value disabled(2) or 
                     cgfeb100ConfigMode(7) has the value hardware(2) and the 
                     Autonegotiation hardware switch is disabled), then these 
                     variables have no meaning and return read-only value 
                     notApplicable(3). If the value cannot be changed (because
                     cgfeb100ConfigMode(7) has the value hardware(2)) and 
                     Autonegotiation is enabled, these variables return the 
                     read-only values enabledRO(4) or disabledRO(5).
                     If manual control of Fiber Autonegotiaion advertised
                     modes is not supported by the device, this variable has 
                     no meaning and the read-only value notApplicable(3) is
                     returned."
        ::= { cgfeb100Entry 47 }

cgfeb100FiberAdv1000FDX OBJECT-TYPE
        SYNTAX INTEGER { yes(1), no(2), notApplicable(3), enabledRO(4), disabledRO(5) }
        ACCESS read-write
        STATUS mandatory
        DESCRIPTION "Enable/disable control for these advertised 
                     autonegotiation modes.
                     If autonegotiation is disabled (because 
                     cgfeb100TpAutonegot(24) has the value disabled(2) or 
                     cgfeb100ConfigMode(7) has the value hardware(2) and the 
                     Autonegotiation hardware switch is disabled), then these 
                     variables have no meaning and return read-only value 
                     notApplicable(3). If the value cannot be changed (because
                     cgfeb100ConfigMode(7) has the value hardware(2)) and 
                     Autonegotiation is enabled, these variables return the 
                     read-only values enabledRO(4) or disabledRO(5).
                     If manual control of Fiber Autonegotiaion advertised
                     modes is not supported by the device, this variable has 
                     no meaning and the read-only value notApplicable(3) is
                     returned."
        ::= { cgfeb100Entry 48 }

cgfeb100FiberLpAdv1000HDX OBJECT-TYPE
        SYNTAX INTEGER { yes(1), no(2), notApplicable(3), enabledRO(4), disabledRO(5) }
        ACCESS read-write
        STATUS mandatory
        DESCRIPTION "This configuration setting controls whether or not each 
                     port advertises willingness to connect at 1000Mbps, half 
                     duplex.  This setting is not supported on fiber ports, 
                     and is ignored when autonegotiation is disabled."
        ::= { cgfeb100Entry 49 }

cgfeb100FiberLpAdv1000FDX OBJECT-TYPE
        SYNTAX INTEGER { yes(1), no(2), notApplicable(3) }
        ACCESS read-write
        STATUS mandatory
        DESCRIPTION "This configuration setting controls whether or not each 
                     port advertises willingness to connect at 1000Mbps, full 
                     duplex.  This setting is not supported on fiber ports, 
                     and is ignored when autonegotiation is disabled."
        ::= { cgfeb100Entry 50 }

cgfeb100FiberLpAdvPause OBJECT-TYPE
        SYNTAX INTEGER { symetric(1), asymRX(2), asymTX(3), disabled(4), notApplicable(5) }
        ACCESS read-only
        STATUS mandatory
        DESCRIPTION "This read-only variable shows the pause capability 
                     advertised by the fiber port's link partner. 
                     Values 1 through 4 for this variable are the same as those
                     for cgfeb100TpAdvPause(38). If the device does not support
                     the reporting of link partner autonegotiation or
                     cgfeb100FiberAutonegot(46) has the value disabled(2), this
                     variable will have the value notApplicable(5)."
        ::= { cgfeb100Entry 51 }

cgfeb100FiberAdvPause OBJECT-TYPE
        SYNTAX INTEGER { symetric(1), asymRX(2), asymTX(3), disabled(4), notApplicable(5),
                         symetricRO(6), asymRXRO(7), asymTXRO(8), disabledRO(9) }
        ACCESS read-write
        STATUS mandatory
        DESCRIPTION "Enable/disable control for autonegotiation advertising of Fiber 
                     Pause capability.
                     Selectable values are symmetric(1), asymRX(2) (asymmetric, pause
                     frames flow towards the converter), asymTX(3) (asymmetric, pause 
                     frames flow towards the link partner), and disabled(4).
                     If autonegotiation is disabled (because cgfeb100FiberAutonegot(46)
                     has the value disabled(2) or cgfeb100ConfigMode(7) has the value
                     hardware(2) and the Autonegotiation hardware switch is disabled),
                     then this variable has no meaning and the read-only value 
                     notApplicable(5) is returned.
                     cgfeb100FiberQosPause(53) has the value disabled(2), negotiated
                     pause is suppressed and the read-only value notApplicable(5) is
                     returned.
                     If cgfeb100ConfigMode(7) has the value hardware(2) and the 
                     Autonegotiation hardware switch is enabled, then one of the 
                     following read-only values will be returned: symmetricRO(6), 
                     asymRXRO(7) (asymmetric, pause frames flow towards the converter),
                     asymTXRO(8) (asymmetric, pause frames flow towards the link 
                     partner), and disabledRO(9)."
        ::= { cgfeb100Entry 52 }

cgfeb100FiberQosPause OBJECT-TYPE
        SYNTAX INTEGER { enabled(1), disabled(2), notApplicable(3) }
        ACCESS read-write
        STATUS mandatory
        DESCRIPTION "This variable allows Fiber Quality Of Service Pause to be
                     enabled or disabled. When cgfeb100QosEnabled(12) is set 
                     to enabled(1) and this variable is set to disabled(2), 
                     any pause functionality negotiated according to
                     cgfeb100FiberAdvPause(52) is suppressed. When
                     cgfeb100QosEnabled(12) is set to disabled(2), this 
                     variable has the read-only value notApplicable(3)."
       ::= { cgfeb100Entry 53 }

cgfeb100FiberSacCfg OBJECT-TYPE
        SYNTAX INTEGER  { enabled(1), disabled(2) }
        ACCESS read-write
        STATUS mandatory
        DESCRIPTION "This variable allows Source Address Change traps to be
                     enabled or disabled. If enabled, 'Error' traps will be
                     sent as frequently one per polling cycle any time the 
                     ethernet source address of any packet received on the 
                     Fiber interface is different from the last address 
                     received on that interface during the previous
                     polling cycle."
        ::= { cgfeb100Entry 54 }

cgfeb100FiberSacStat OBJECT-TYPE
        SYNTAX INTEGER  { changed(1), constant(2) }
        ACCESS read-write
        STATUS mandatory
        DESCRIPTION "This read-only variable has the value changed(1) if the
                     Ethernet source address received on the fiber interface
                     changed since the device's previous report to the 
                     Mangement Module, and the value constant(2) otherwise.
                     To cause the Management Module to generate a trap when
                     this occurs, set cgfeb100FiberSacConfig(54) to enabled(1)."
        ::= { cgfeb100Entry 55 }

cgfeb100MonitorTap OBJECT-TYPE
        SYNTAX INTEGER  { transmit(1), receive(2), notInstalled(3) }
        ACCESS read-write
        STATUS mandatory
        DESCRIPTION "Before reading this description, see cgfeb100MonitorType(10).
                     This variable controls which side of the fiber port 
                     (transmit(1) or receive(2)) is monitored by the monitoring
                     port. If no monitoring port is present, this variable has
                     the value notInstalled(3)."
        ::= { cgfeb100Entry 56 }

cgfeb100CacheClean OBJECT-TYPE
        SYNTAX INTEGER { clean(1), dirty(2) }
        ACCESS read-only
        STATUS mandatory
        DESCRIPTION "When the value is clean(1)Device and Management Module
                     cache are synchronized, no automatic corrections to 
                     configuration will occur.  When the value is dirty(2)
                     Device and Management Module cache are not synchronized.
                     The configuration currently displayed by the application 
                     has not been validated by the device. The device may 
                     need to correct the configuration, in which case the 
                     displayed configuration will change."
        ::= { cgfeb100Entry 57 }

--=====================================================================
-- Table for the crmfe100

crmfe100Table OBJECT-TYPE
        SYNTAX SEQUENCE OF Crmfe100Entry
        ACCESS not-accessible
        STATUS mandatory
        DESCRIPTION "Sparse table containing one entry for each CRMFE100
                     in the stack, indexed by cabinet serial number and slot."
        ::= { cpsSlotDetail 24 }

crmfe100Entry OBJECT-TYPE
        SYNTAX Crmfe100Entry
        ACCESS not-accessible
        STATUS mandatory
        DESCRIPTION "Status and configuration entries for a single CRMFE100"
        INDEX { crmfe100BiaIndex, crmfe100SlotIndex }
        ::= { crmfe100Table 1 }

Crmfe100Entry ::=
        SEQUENCE {
                 crmfe100BiaIndex               INTEGER,
                 crmfe100SlotIndex              INTEGER,
                 crmfe100Groups                 DisplayString,
                 crmfe100MRevision              INTEGER,
                 crmfe100CfgMatch               INTEGER,
                 crmfe100SerialNumber           INTEGER,
                 crmfe100ConnA                  INTEGER,
                 crmfe100ConnB                  INTEGER,
                 crmfe100TPLink                 INTEGER,
                 crmfe100FiberLink              INTEGER,
                 crmfe100Fault                  INTEGER,
                 crmfe100Autonegot              INTEGER,
                 crmfe100Enabled                INTEGER,
                 crmfe100Pause                  INTEGER,
                 crmfe100LinkPassThrough        INTEGER,
                 crmfe100AutoCross              INTEGER,
                 crmfe100TPActivity             INTEGER,
                 crmfe100FiberActivity          INTEGER,
                 crmfe100ConfigMode             INTEGER,
                 crmfe100FarEndFault            INTEGER,
                 crmfe100NetworkMode            INTEGER,
                 crmfe100UpTime                 TimeTicks,
                 crmfe100FirmwareRevision       INTEGER,
                 crmfe100RmtDetected            INTEGER,
                 crmfe100RmtTPLink              INTEGER,
                 crmfe100RmtFiberLink           INTEGER,
                 crmfe100RmtFault               INTEGER,
                 crmfe100RmtAutonegot           INTEGER,
                 crmfe100RmtPause               INTEGER,
                 crmfe100RmtLinkPassThrough     INTEGER,
                 crmfe100RmtAutoCross           INTEGER,
                 crmfe100RmtTPActivity          INTEGER,
                 crmfe100RmtFiberActivity       INTEGER,
                 crmfe100RmtConfigMode          INTEGER,
                 crmfe100RmtFarEndFault         INTEGER,
                 crmfe100RmtLoopback            INTEGER,
                 crmfe100RmtNetworkMode         INTEGER,
                 crmfe100RmtUpTime              TimeTicks,
                 crmfe100TxFxBwa                INTEGER,
                 crmfe100FxTxBwa                INTEGER,
                 crmfe100TxBytesH               INTEGER,
                 crmfe100TxBytesL               INTEGER,
                 crmfe100FxBytesH               INTEGER,
                 crmfe100FxBytesL               INTEGER,
                 crmfe100MscRxBytes             INTEGER,
                 crmfe100MscTxBytes             INTEGER,
                 crmfe100CacheClean             INTEGER,
                 crmfe100MbTxFxBwa              INTEGER,
                 crmfe100MbFxTxBwa              INTEGER
                 }

crmfe100BiaIndex OBJECT-TYPE
        SYNTAX INTEGER
        ACCESS read-only
        STATUS mandatory
        DESCRIPTION "The serial number (BIA) of the cabinet in which the 
                     device is installed"
        ::= { crmfe100Entry 1 }

crmfe100SlotIndex OBJECT-TYPE
        SYNTAX INTEGER
        ACCESS read-only
        STATUS mandatory
        DESCRIPTION "The slot in which the device is installed"
        ::= { crmfe100Entry 2 }

crmfe100Groups OBJECT-TYPE
        SYNTAX DisplayString
        ACCESS read-write
        STATUS mandatory
        DESCRIPTION "User-defined keywords that group this device together with
                     other devices under a user-defined scheme. By placing 
                     matching keywords in cpsGroupCtrl.0, the agent can be
                     instructed to apply configuration changes simultaneously
                     to all group members rather than to individual devices.
                     Every Groups string has three automatically defined
                     implied values: 
                     1) The model family of the device, e.g. 'CRMFE100'
                     2) The serial number of the cabinet in which the device
                        is installed, in decimal with no leading zeroes, 
                        e.g. '12345', and 
                     3) same as 2, with the slot in which the device is 
                        installed appended, enclosed in square brackets. 
                        e.g. '12345[9]'"
        ::= { crmfe100Entry 3 }

crmfe100MRevision OBJECT-TYPE
        SYNTAX INTEGER
        ACCESS read-only
        STATUS mandatory
        DESCRIPTION "The marketing revision of this device"
        ::= { crmfe100Entry 4 }

crmfe100CfgMatch OBJECT-TYPE
        SYNTAX INTEGER { yes(1), no(2), notApplicable(3) }
        ACCESS read-only
        STATUS mandatory
        DESCRIPTION "yes(1) indicates that the conditions specified in 
                     cpsGroupCtrl.0 match the Groups value for this
                     device. no(2) means that there is no match.
                     notApplicable(3) indicates that cpsGroupCtrl.0 is null
                     and therefore no comparison was performed."
        ::= { crmfe100Entry 5 }

crmfe100SerialNumber OBJECT-TYPE
        SYNTAX INTEGER
        ACCESS read-only
        STATUS mandatory
        DESCRIPTION "The serial number of this device"
        ::= { crmfe100Entry 6 }

crmfe100ConnA OBJECT-TYPE
        SYNTAX CpsConnector
        ACCESS read-only
        STATUS mandatory
        DESCRIPTION "The style of Fiber connector built into this device"
        ::= { crmfe100Entry 7 }

crmfe100ConnB OBJECT-TYPE
        SYNTAX CpsConnector
        ACCESS read-only
        STATUS mandatory
        DESCRIPTION "The style of Copper connector built into this device"
        ::= { crmfe100Entry 8 }

crmfe100TPLink OBJECT-TYPE
        SYNTAX INTEGER { linkUp(1), linkDown(2) }
        ACCESS read-only
        STATUS mandatory
        DESCRIPTION "Status of Copper Link for this device"
        ::= { crmfe100Entry 9 }

crmfe100FiberLink OBJECT-TYPE
        SYNTAX INTEGER { linkUp(1), linkDown(2) }
        ACCESS read-only
        STATUS mandatory
        DESCRIPTION "Status of Fiber Link for this device"
        ::= { crmfe100Entry 10 }

crmfe100Fault OBJECT-TYPE
        SYNTAX INTEGER { yes(1), no(2) }
        ACCESS read-only
        STATUS mandatory
        DESCRIPTION "Value is yes(1) when either CopperLink or FiberLink 
                     has value linkDown(2)"
        ::= { crmfe100Entry 11 }

crmfe100Autonegot OBJECT-TYPE
        SYNTAX INTEGER { enabled(1), disabled(2) }
        ACCESS read-write
        STATUS mandatory
        DESCRIPTION "Autonegotiation configuration for this device."
        ::= { crmfe100Entry 12 }

crmfe100Enabled OBJECT-TYPE
        SYNTAX INTEGER { yes(1), no(2) }
        ACCESS read-write
        STATUS mandatory
        DESCRIPTION "When the Enabled configuration item is set to no(2),
                     the converter passes no network traffic in either
                     direction."
        ::= { crmfe100Entry 13 }

crmfe100Pause OBJECT-TYPE
        SYNTAX INTEGER { enabled(1), disabled(2) }
        ACCESS read-write
        STATUS mandatory
        DESCRIPTION "The Pause feature allows Ethernet MACs that support it to
                     send data pacing 'Pause' messages to each other. 
                     Support for Pause is negotiated at the physical level and
                     passed up to the MAC. While the MAC's Pause messages 
                     themselves can pass over the fiber link that this pair
                     of media converters introduces, the TP physical layer
                     negotiations to enable Pause can not. Therefore, if both 
                     end station MACs support Pause and wish to use it, the
                     Pause negotiation must be re-generated by the media
                     converters on both ends. By setting this configuration
                     option to enabled(1), you are indicating to the local
                     twisted pair station that the twisted pair station on 
                     the other side of the other media converter supports 
                     Pause and wishes to use it. This variable must be set 
                     consistently on both of the paired media converters."
        ::= { crmfe100Entry 14 }

crmfe100LinkPassThrough OBJECT-TYPE
        SYNTAX INTEGER { enabled(1), disabled(2) }
        ACCESS read-write
        STATUS mandatory
        DESCRIPTION "This configuration item allows Link Pass Through to 
                     be enabled(1) or disabled(2). Link Passthrough causes
                     loss of link on one side of a media converter to be 
                     passed through to the other side, so that upstream 
                     equipment can see fault conditions that would otherwise
                     be hidden by the media converters."
        ::= { crmfe100Entry 15 }

crmfe100AutoCross OBJECT-TYPE
        SYNTAX INTEGER { enabled(1), disabled(2) }
        ACCESS read-write
        STATUS mandatory
        DESCRIPTION "On certain devices, it is possible for hardware to 
                     automatically correct errors in cable selection, making
                     the distinction between a 'straight through' cable and a
                     'crossover' cable unimportant. This capability is known
                     as Auto Cross. When disabled, the port reverts to MDI mode."
        ::= { crmfe100Entry 16 }

crmfe100TPActivity OBJECT-TYPE
        SYNTAX INTEGER { yes(1), no(2), notApplicable(3) }
        ACCESS read-only
        STATUS mandatory
        DESCRIPTION "Twisted Pair Activity. Some versions of the CRMFE100 do 
                     not support the reporting of interface activity. The value
                     of this variable for such a device will be notApplicable."
        ::= { crmfe100Entry 17 }

crmfe100FiberActivity OBJECT-TYPE
        SYNTAX INTEGER { yes(1), no(2), notSupported(3) }
        ACCESS read-only
        STATUS mandatory
        DESCRIPTION "Fiber Activity. Some versions of the CRMFE100 do not support
                     the reporting of interface activity. The value of this 
                     variable for such a device will be notApplicable."
        ::= { crmfe100Entry 18 }

crmfe100ConfigMode OBJECT-TYPE
        SYNTAX INTEGER { software(1), hardware(2) }
        ACCESS read-only
        STATUS mandatory
        DESCRIPTION "This device has a jumper or switch that disables 
                     software management of the device. When ConfigMode is
                     hardware(2), SNMP management is disabled, and all
                     configuration control comes from physical switches or
                     jumpers on the device."
        ::= { crmfe100Entry 19 }

crmfe100FarEndFault OBJECT-TYPE
        SYNTAX INTEGER { enabled(1), disabled(2) }
        ACCESS read-write
        STATUS mandatory
        DESCRIPTION "Far End Fault configuration of this device.  Far End Fault
                     causes the fiber transmitter to generate a Far End Fault
                     pattern upon the loss of a receiver signal detect.  When
                     the receiver detects signal again, the transmitter stops
                     transmitting the Far End Fault pattern."
        ::= { crmfe100Entry 20 }

crmfe100NetworkMode OBJECT-TYPE
        SYNTAX INTEGER { tokenRing(1), ethernet(2) }
        ACCESS read-only
        STATUS mandatory
        DESCRIPTION "Read-only indicator for High Speed Token Ring jumper 
                     configuration. If the variable reads tokenRing(1), then the
                     converter is jumpered for High Speed Token Ring mode. If 
                     the variable reads ethernet(2), then the converter is 
                     jumpered for Ethernet mode. The jumper settings for the 
                     converters on both ends of the fiber must be the same."
        ::= { crmfe100Entry 21 }

crmfe100UpTime OBJECT-TYPE
        SYNTAX TimeTicks 
        ACCESS read-write
        STATUS mandatory
        DESCRIPTION "Time since the last reboot in Time Ticks (hundredths of 
                     seconds). If the value 0 is written to this variable, the 
                     timer is reset. No other write value is accepted."
        ::= { crmfe100Entry 22 }

crmfe100FirmwareRevision OBJECT-TYPE
        SYNTAX INTEGER 
        ACCESS read-only
        STATUS mandatory
        DESCRIPTION "Firmware revision level of this CRMFE100."
        ::= { crmfe100Entry 23 }

crmfe100RmtDetected OBJECT-TYPE
        SYNTAX INTEGER { detected(1), notDetected(2) }
        ACCESS read-only
        STATUS mandatory
        DESCRIPTION "Has the value yes(1) if management communcations
                     have been established with a remote media converter."
        ::= { crmfe100Entry 24 }

crmfe100RmtTPLink OBJECT-TYPE
        SYNTAX INTEGER { linkUp(1), linkDown(2), notApplicable(3) }
        ACCESS read-only
        STATUS mandatory
        DESCRIPTION "Status of Copper Link for this device"
        ::= { crmfe100Entry 25 }

crmfe100RmtFiberLink OBJECT-TYPE
        SYNTAX INTEGER { linkUp(1), linkDown(2), notApplicable(3) }
        ACCESS read-only
        STATUS mandatory
        DESCRIPTION "Status of Fiber Link for this device"
        ::= { crmfe100Entry 26 }

crmfe100RmtFault OBJECT-TYPE
        SYNTAX INTEGER { yes(1), no(2), notApplicable(3) }
        ACCESS read-only
        STATUS mandatory
        DESCRIPTION "Value is yes(1) when either TPLink or FiberLink 
                     has value linkDown(2)"
        ::= { crmfe100Entry 27 }

crmfe100RmtAutonegot OBJECT-TYPE
        SYNTAX INTEGER { enabled(1), disabled(2), notApplicable(3) }
        ACCESS read-write
        STATUS mandatory
        DESCRIPTION "Autonegotiation configuration for this device."
        ::= { crmfe100Entry 28 }

crmfe100RmtPause OBJECT-TYPE
        SYNTAX INTEGER { enabled(1), disabled(2), notApplicable(3) }
        ACCESS read-write
        STATUS mandatory
        DESCRIPTION "The Pause feature allows Ethernet MACs that support it to
                     send data pacing 'Pause' messages to each other. 
                     Support for Pause is negotiated at the physical level and
                     passed up to the MAC. While the MAC's Pause messages 
                     themselves can pass over the fiber link that this pair
                     of media converters introduces, the TP physical layer
                     negotiations to enable Pause can not. Therefore, if both 
                     end station MACs support Pause and wish to use it, the
                     Pause negotiation must be re-generated by the media
                     converters on both ends. By setting this configuration
                     option to enabled(1), you are indicating to the local
                     twisted pair station that the twisted pair station on 
                     the other side of the other media converter supports 
                     Pause and wishes to use it. This variable must be set 
                     consistently on both of the paired media converters."
        ::= { crmfe100Entry 29 }

crmfe100RmtLinkPassThrough OBJECT-TYPE
        SYNTAX INTEGER { enabled(1), disabled(2), notApplicable(3) }
        ACCESS read-write
        STATUS mandatory
        DESCRIPTION "This configuration item allows Link Pass Through to 
                     be enabled(1) or disabled(2). Link Passthrough causes
                     loss of link on one side of a media converter to be 
                     passed through to the other side, so that upstream 
                     equipment can see fault conditions that would otherwise
                     be hidden by the media converters."
        ::= { crmfe100Entry 30 }

crmfe100RmtAutoCross OBJECT-TYPE
        SYNTAX INTEGER { enabled(1), disabled(2), notApplicable(3) }
        ACCESS read-write
        STATUS mandatory
        DESCRIPTION "On certain devices, it is possible for hardware to 
                     automatically correct errors in cable selection, making
                     the distinction between a 'straight through' cable and a
                     'crossover' cable unimportant. This capability is known
                     as Auto Cross. When disabled, the port reverts to MDI mode."
        ::= { crmfe100Entry 31 }

crmfe100RmtTPActivity OBJECT-TYPE
        SYNTAX INTEGER { yes(1), no(2), notSupported(3) }
        ACCESS read-only
        STATUS mandatory
        DESCRIPTION "Twisted Pair Activity. Some versions of the CRMFE100 do 
                     not support the reporting of interface activity. The value
                     of this variable for such a device will be notApplicable."
        ::= { crmfe100Entry 32 }

crmfe100RmtFiberActivity OBJECT-TYPE
        SYNTAX INTEGER { yes(1), no(2), notSupported(3) }
        ACCESS read-only
        STATUS mandatory
        DESCRIPTION "Fiber Activity. Some versions of the CRMFE100 do not support
                     the reporting of interface activity. The value of this 
                     variable for such a device will be notApplicable."
        ::= { crmfe100Entry 33 }

crmfe100RmtConfigMode OBJECT-TYPE
        SYNTAX INTEGER { software(1), hardware(2), notApplicable(3) }
        ACCESS read-only
        STATUS mandatory
        DESCRIPTION "This device has a jumper or switch that disables 
                     software management of the device. When ConfigMode is
                     hardware(2), SNMP management is disabled, and all
                     configuration control comes from physical switches or
                     jumpers on the device."
        ::= { crmfe100Entry 34 }

crmfe100RmtFarEndFault OBJECT-TYPE
        SYNTAX INTEGER { enabled(1), disabled(2), notApplicable(3) }
        ACCESS read-write
        STATUS mandatory
        DESCRIPTION "Far End Fault configuration of this device.  Far End Fault
                     causes the fiber transmitter to generate a Far End Fault
                     pattern upon the loss of a receiver signal detect.  When
                     the receiver detects signal again, the transmitter stops
                     transmitting the Far End Fault pattern."
        ::= { crmfe100Entry 35 }

crmfe100RmtLoopback OBJECT-TYPE
        SYNTAX INTEGER { enabled(1), disabled(2), notApplicable(3) }
        ACCESS read-write
        STATUS mandatory
        DESCRIPTION "When Remote Loopback is enabled, all packets sent out from 
                     the local fiber interface are reflected back by the remote
                     converter rather than being passed out through the remote 
                     twisted pair interface, and all packets received on the 
                     remote Twisted Pair interface are discarded."
        ::= { crmfe100Entry 36 }

crmfe100RmtNetworkMode OBJECT-TYPE
        SYNTAX INTEGER { tokenRing(1), ethernet(2), notApplicable(3) }
        ACCESS read-only
        STATUS mandatory
        DESCRIPTION "Read-only indicator for High Speed Token Ring jumper 
                     configuration. If the variable reads tokenRing(1), then the
                     converter is jumpered for High Speed Token Ring mode. If 
                     the variable reads ethernet(2), then the converter is 
                     jumpered for Ethernet mode. The jumper settings for the 
                     converters on both ends of the fiber must be the same."
        ::= { crmfe100Entry 37 }

crmfe100RmtUpTime OBJECT-TYPE
        SYNTAX TimeTicks 
        ACCESS read-write
        STATUS mandatory
        DESCRIPTION "Time since the last reboot in Time Ticks (hundredths of 
                     seconds). If the value 0 is written to this variable, the 
                     timer is reset. No other write value is accepted."
        ::= { crmfe100Entry 38 }

crmfe100TxFxBwa OBJECT-TYPE
        SYNTAX INTEGER
        ACCESS read-write
        STATUS mandatory
        DESCRIPTION "This variable allows the control of bandwidth allocation. 
                     The value of this variable is entered in Kilobytes per Second,
                     and is automatically rounded to the nearest 64KBps. A value of
                     zero disables data transfer, and the maximum value is 
                     12224KBps. Data traffic is measured from the beginning of each
                     second. Once the traffic reaches the cap specified, all traffic
                     is discarded until the start of the next second, when the 
                     counters are reset and traffic begins to flow again. 
                     crmfe100TxFxBwa(39) limits the data flowing from the Twisted 
                     Pair interface to the Fiber interface."
        ::= { crmfe100Entry 39 }

crmfe100FxTxBwa OBJECT-TYPE
        SYNTAX INTEGER
        ACCESS read-write
        STATUS mandatory
        DESCRIPTION "This variable allows the control of bandwidth allocation. 
                     The value of this variable is entered in Kilobytes per Second,
                     and is automatically rounded to the nearest 64KBps. A value of
                     zero disables data transfer, and the maximum value is 
                     12224KBps. Data traffic is measured from the beginning of each
                     second. Once the traffic reaches the cap specified, all traffic
                     is discarded until the start of the next second, when the 
                     counters are reset and traffic begins to flow again. 
                     crmfe100FxTxBwa(39) limits the data flowing from the fiber
                     interface to the twisted pair interface."
        ::= { crmfe100Entry 40 }

crmfe100TxBytesH OBJECT-TYPE
        SYNTAX INTEGER
        ACCESS read-write
        STATUS mandatory
        DESCRIPTION "These variables measure the traffic (in Bytes) received by the
                     two interfaces of the converter (and therefore transmitted by
                     the opposite interface). 'Tx' refers to data received by the 
                     Twisted Pair interface (and transmitted on the Fiber interface),
                     and 'Fx' refers to data received on the Fiber interface (and 
                     transmitted on the Twisted Pair interface).
                     In order to limit each variable to the 32-bit maximum commonly
                     supported in the SNMP world, these 64-bit counters are split 
                     into a high-order and low-order 32-bit sections. Transition 
                     Networks' applications generally treat the High order portion 
                     of the counter as a counter of the number of times the Low order
                     section has wrapped to 0. To reconstruct the original 64-bit 
                     value, multiply the 'High' section by 2^32 and add the 'Low'
                     section.
                     If you write the value 0 to any of these four variables, all
                     four are reset to zero."
        ::= { crmfe100Entry 41 }

crmfe100TxBytesL OBJECT-TYPE
        SYNTAX INTEGER
        ACCESS read-write
        STATUS mandatory
        DESCRIPTION "See the DESCRIPTION for cfmfe100TxBytesH(42) above."
        ::= { crmfe100Entry 42 }

crmfe100FxBytesH OBJECT-TYPE
        SYNTAX INTEGER
        ACCESS read-write
        STATUS mandatory
        DESCRIPTION "See the DESCRIPTION for cfmfe100TxBytesH(42) above."
        ::= { crmfe100Entry 43 }

crmfe100FxBytesL OBJECT-TYPE
        SYNTAX INTEGER
        ACCESS read-write
        STATUS mandatory
        DESCRIPTION "See the DESCRIPTION for cfmfe100TxBytesH(42) above."
        ::= { crmfe100Entry 44 }

crmfe100MscRxBytes OBJECT-TYPE
        SYNTAX INTEGER
        ACCESS read-write
        STATUS mandatory
        DESCRIPTION "This variable measures the traffic (in Bytes) received and
                     transmitted by the Management Subchannel within the Fiber 
                     interface. 'Management Subchannel' refers to the transfer of
                     management data to and from the Remote SRMFExxx in the 
                     inter-packet gaps normally found in Ethernet traffic. This 
                     allows management data to be transferred with no reduction 
                     in the bandwidth available for normal network traffic.
                     If you write the value 0 to this variable or 
                     crmfe100MscTxBytes(47), both are reset to zero."
        ::= { crmfe100Entry 45 }

crmfe100MscTxBytes OBJECT-TYPE
        SYNTAX INTEGER
        ACCESS read-write
        STATUS mandatory
        DESCRIPTION "This variable measures the traffic (in Bytes) received and
                     transmitted by the Management Subchannel within the Fiber 
                     interface. 'Management Subchannel' refers to the transfer of
                     management data to and from the Remote SRMFExxx in the 
                     inter-packet gaps normally found in Ethernet traffic. This 
                     allows management data to be transferred with no reduction 
                     in the bandwidth available for normal network traffic.
                     If you write the value 0 to this variable or 
                     crmfe100MscRxBytes(46), both are reset to zero."
        ::= { crmfe100Entry 46 }

crmfe100CacheClean OBJECT-TYPE
        SYNTAX INTEGER { clean(1), dirty(2) }
        ACCESS read-only
        STATUS mandatory
        DESCRIPTION "When the value is clean(1)Device and Management Module
                     cache are synchronized, no automatic corrections to 
                     configuration will occur.  When the value is dirty(2)
                     Device and Management Module cache are not synchronized.
                     The configuration currently displayed by the application 
                     has not been validated by the device. The device may 
                     need to correct the configuration, in which case the 
                     displayed configuration will change."
        ::= { crmfe100Entry 47 }

crmfe100MbTxFxBwa OBJECT-TYPE
        SYNTAX INTEGER
        ACCESS read-write
        STATUS mandatory
        DESCRIPTION "This variable allows the control of bandwidth allocation. 
                     The value of this variable is entered in Megabits per Second,
                     and is automatically rounded to the nearest 64KBps. A value of
                     zero disables data transfer, and the maximum value is 
                     12224KBps. Data traffic is measured from the beginning of each
                     second. Once the traffic reaches the cap specified, all traffic
                     is discarded until the start of the next second, when the 
                     counters are reset and traffic begins to flow again. 
                     crmfe100MbTxFxBwa(48) limits the data flowing from the Twisted 
                     Pair interface to the Fiber interface.  This variable does the
                     same thing as crmfe100TxFxBwa(39), only the units are different."
        ::= { crmfe100Entry 48 }

crmfe100MbFxTxBwa OBJECT-TYPE
        SYNTAX INTEGER
        ACCESS read-write
        STATUS mandatory
        DESCRIPTION "This variable allows the control of bandwidth allocation. 
                     The value of this variable is entered in Megabits per Second,
                     and is automatically rounded to the nearest 64KBps. A value of
                     zero disables data transfer, and the maximum value is 
                     12224KBps. Data traffic is measured from the beginning of each
                     second. Once the traffic reaches the cap specified, all traffic
                     is discarded until the start of the next second, when the 
                     counters are reset and traffic begins to flow again. 
                     crmfe100MbFxTxBwa(49) limits the data flowing from the fiber
                     interface to the twisted pair interface.    This variable does the
                     same thing as crmfe100TxFxBwa(40), only the units are different."
        ::= { crmfe100Entry 49 }

-- ==================================================================
-- Table for a crs2f100 slide in card.

crs2f100Table OBJECT-TYPE
        SYNTAX SEQUENCE OF Crs2f100Entry
        ACCESS not-accessible
        STATUS mandatory
        DESCRIPTION "Sparse table containing one entry for each CRS2F100
                     in the stack, indexed by cabinet serial number and slot."
        ::= { cpsSlotDetail 25 }

crs2f100Entry OBJECT-TYPE
        SYNTAX Crs2f100Entry
        ACCESS not-accessible
        STATUS mandatory
        DESCRIPTION "Status and configuration entries for a single CRS2F100"
        INDEX { crs2f100BiaIndex, crs2f100SlotIndex }
        ::= { crs2f100Table 1 }

Crs2f100Entry ::=
        SEQUENCE {
                 crs2f100BiaIndex            INTEGER,
                 crs2f100SlotIndex           INTEGER,
                 crs2f100Groups              DisplayString,
                 crs2f100MRevision           INTEGER,
                 crs2f100CfgMatch            INTEGER,
                 crs2f100SerialNumber        INTEGER,
                 crs2f100ConnA               INTEGER,
                 crs2f100ConnB               INTEGER,
                 crs2f100FiberLink           INTEGER,
                 crs2f100Fault               INTEGER,
                 crs2f100FirmwareRevision    INTEGER,
                 crs2f100Loopback            INTEGER,
                 crs2f100DCE                 INTEGER,
                 crs2f100CopperActivity      INTEGER,
                 crs2f100ConfigMode          INTEGER,
                 crs2f100RmtDetected         INTEGER,
                 crs2f100RmtLoopback         INTEGER,
                 crs2f100RmtDCE              INTEGER,
                 crs2f100RmtCopperActivity   INTEGER,
                 crs2f100RmtConfigMode       INTEGER,
                 crs2f100CacheClean          INTEGER
                 }

crs2f100BiaIndex OBJECT-TYPE
        SYNTAX INTEGER
        ACCESS read-only
        STATUS mandatory
        DESCRIPTION "The serial number (BIA) of the cabinet in which the 
                     device is installed"
        ::= { crs2f100Entry 1 }

crs2f100SlotIndex OBJECT-TYPE
        SYNTAX INTEGER
        ACCESS read-only
        STATUS mandatory
        DESCRIPTION "The slot in which the device is installed"
        ::= { crs2f100Entry 2 }

crs2f100Groups OBJECT-TYPE
        SYNTAX DisplayString
        ACCESS read-write
        STATUS mandatory
        DESCRIPTION "User-defined keywords that group this device together with
                     other devices under a user-defined scheme. By placing 
                     matching keywords in cpsGroupCtrl.0, the agent can be
                     instructed to apply configuration changes simultaneously
                     to all group members rather than to individual devices.
                     Every Groups string has three automatically defined
                     implied values: 
                     1) The model family of the device, e.g. 'CRS2F100'
                     2) The serial number of the cabinet in which the device
                        is installed, in decimal with no leading zeroes, 
                        e.g. '12345', and 
                     3) same as 2, with the slot in which the device is 
                        installed appended, enclosed in square brackets. 
                        e.g. '12345[9]'"
        ::= { crs2f100Entry 3 }

crs2f100MRevision OBJECT-TYPE
        SYNTAX INTEGER
        ACCESS read-only
        STATUS mandatory
        DESCRIPTION "The marketing revision of this device"
        ::= { crs2f100Entry 4 }

crs2f100CfgMatch OBJECT-TYPE
        SYNTAX INTEGER { yes(1), no(2), notApplicable(3) }
        ACCESS read-only
        STATUS mandatory
        DESCRIPTION "yes(1) indicates that the conditions specified in 
                     cpsGroupCtrl.0 match the Groups value for this
                     device. no(2) means that there is no match.
                     notApplicable(3) indicates that cpsGroupCtrl.0 is null
                     and therefore no comparison was performed."
        ::= { crs2f100Entry 5 }

crs2f100SerialNumber OBJECT-TYPE
        SYNTAX INTEGER 
        ACCESS read-only
        STATUS mandatory
        DESCRIPTION "The serial number of this device"
        ::= { crs2f100Entry 6 }

crs2f100ConnA OBJECT-TYPE
        SYNTAX CpsConnector
        ACCESS read-only
        STATUS mandatory
        DESCRIPTION "The style of Fiber connector built into this device"
        ::= { crs2f100Entry 7 }

crs2f100ConnB OBJECT-TYPE
        SYNTAX CpsConnector
        ACCESS read-only
        STATUS mandatory
        DESCRIPTION "The style of Copper connector built into this device"
        ::= { crs2f100Entry 8 }

crs2f100FiberLink OBJECT-TYPE
        SYNTAX INTEGER { linkUp(1), linkDown(2) }
        ACCESS read-only
        STATUS mandatory
        DESCRIPTION "Status of Fiber Link for this device"
        ::= { crs2f100Entry 9 }

crs2f100Fault OBJECT-TYPE
        SYNTAX INTEGER { yes(1), no(2) }
        ACCESS read-only
        STATUS mandatory
        DESCRIPTION "Value is yes(1) when FiberLink has value linkDown(2)"
        ::= { crs2f100Entry 10 }

crs2f100FirmwareRevision OBJECT-TYPE
        SYNTAX INTEGER
        ACCESS read-only
        STATUS mandatory
        DESCRIPTION "The Firmware Revision MIB Variable reports the revision 
                     of software running on the processor on this particular
                     device.  You can discover the revisions on these devices
                     by entering the PICREV command at the command line 
                     interface.  Device Firmware Revisions are normally 
                     discussed in terms of a single letter, e.g. revision 'B'.
                     However, when the firmware revision is displayed by 
                     generic MIB processing code that is unaware of this 
                     convention, the revision is displayed as a decimal value. 
                     The table in crs2f100.html provides some examples of how 
                     decimal revision values correspond to letter revision 
                     values."
        ::= { crs2f100Entry 11 }

crs2f100Loopback OBJECT-TYPE
        SYNTAX INTEGER { enabled(1), disabled(2) }
        ACCESS read-write
        STATUS mandatory
        DESCRIPTION "Loopback is a testing aid available on several different 
                     products. When Loopback is enabled on an interface, all 
                     data that is sent to the interface is reflected back to 
                     the sender, and the actual condition (or even existence) 
                     of the equipment on the opposite interface is ignored."
        ::= { crs2f100Entry 12 }

crs2f100DCE OBJECT-TYPE
        SYNTAX INTEGER { dCE(1), dTE(2) }
        ACCESS read-only
        STATUS mandatory
        DESCRIPTION "An indication of whether this device is attached to a DCE
                     (a modem) or a DTE (a terminal or computer)."
        ::= { crs2f100Entry 13 }

crs2f100CopperActivity OBJECT-TYPE
        SYNTAX INTEGER { yes(1), no(2) }
        ACCESS read-only
        STATUS mandatory
        DESCRIPTION "The activity indicator has the value yes(1) when the 
                     hardware has recently detected network traffic on the 
                     associated network port, and no(2) otherwise."
        ::= { crs2f100Entry 14 }

crs2f100ConfigMode OBJECT-TYPE
        SYNTAX INTEGER { software(1), hardware(2) }
        ACCESS read-only
        STATUS mandatory
        DESCRIPTION "This device has a jumper or switch that disables 
                     software management of the device. When ConfigMode is
                     hardware(2), SNMP management is disabled, and all
                     configuration control comes from physical switches or
                     jumpers on the device."
        ::= { crs2f100Entry 15 }

crs2f100RmtDetected OBJECT-TYPE
        SYNTAX INTEGER { yes(1), no(2) }
        ACCESS read-only
        STATUS mandatory
        DESCRIPTION "Has the value yes(1) if management communcations have 
                     been established with a remote media device."
        ::= { crs2f100Entry 16 }

crs2f100RmtLoopback OBJECT-TYPE
        SYNTAX INTEGER { enabled(1), disabled(2), notApplicable(3) }
        ACCESS read-write
        STATUS mandatory
        DESCRIPTION "Loopback is a testing aid available on several different 
                     products. When Loopback is enabled on an interface, all 
                     data that is sent to the interface is reflected back to 
                     the sender, and the actual condition (or even existence) 
                     of the equipment on the opposite interface is ignored.
                     When no remote device is present, this variable has the 
                     value notApplicable(3)."
        ::= { crs2f100Entry 17 }

crs2f100RmtDCE OBJECT-TYPE
        SYNTAX INTEGER { dCE(1), dTE(2), notApplicable(3) }
        ACCESS read-only
        STATUS mandatory
        DESCRIPTION "This variable describes the status of a remotely managed
                     device.  This is an indicator of whether this device is 
                     attached to a DCE (a modem) or a DTE (a terminal or computer).
                     When no remote device is present, this variable has the 
                     value notApplicable(3)."
        ::= { crs2f100Entry 18 }

crs2f100RmtCopperActivity OBJECT-TYPE
        SYNTAX INTEGER { yes(1), no(2), notApplicable(3) }
        ACCESS read-only
        STATUS mandatory
        DESCRIPTION "The activity indicator has the value yes(1) when the 
                     hardware has recently detected network traffic on the 
                     associated network port, and no(2) otherwise.
                     When no remote device is present, this variable has the 
                     value notApplicable(3)."
        ::= { crs2f100Entry 19 }

crs2f100RmtConfigMode OBJECT-TYPE
        SYNTAX INTEGER { software(1), hardware(2), notApplicable(3) }
        ACCESS read-only
        STATUS mandatory
        DESCRIPTION "This device has a jumper or switch that disables 
                     software management of the device. When ConfigMode is
                     hardware(2), SNMP management is disabled, and all
                     configuration control comes from physical switches or
                     jumpers on the device.
                     When no remote device is present, this variable has the 
                     value notApplicable(3)."
        ::= { crs2f100Entry 20 }

crs2f100CacheClean OBJECT-TYPE
        SYNTAX INTEGER { clean(1), dirty(2) }
        ACCESS read-only
        STATUS mandatory
        DESCRIPTION "When the value is clean(1)Device and Management Module
                     cache are synchronized, no automatic corrections to 
                     configuration will occur.  When the value is dirty(2)
                     Device and Management Module cache are not synchronized.
                     The configuration currently displayed by the application 
                     has not been validated by the device. The device may 
                     need to correct the configuration, in which case the 
                     displayed configuration will change."
        ::= { crs2f100Entry 21 }

-- ==================================================================
-- Table for a crs4f100 slide in card.

crs4f100Table OBJECT-TYPE
        SYNTAX SEQUENCE OF Crs4f100Entry
        ACCESS not-accessible
        STATUS mandatory
        DESCRIPTION "Sparse table containing one entry for each CRS4F100
                     in the stack, indexed by cabinet serial number and slot."
        ::= { cpsSlotDetail 26 }

crs4f100Entry OBJECT-TYPE
        SYNTAX Crs4f100Entry
        ACCESS not-accessible
        STATUS mandatory
        DESCRIPTION "Status and configuration entries for a single CRS4F100"
        INDEX { crs4f100BiaIndex, crs4f100SlotIndex }
        ::= { crs4f100Table 1 }

Crs4f100Entry ::=
        SEQUENCE {
                 crs4f100BiaIndex            INTEGER,
                 crs4f100SlotIndex           INTEGER,
                 crs4f100Groups              DisplayString,
                 crs4f100MRevision           INTEGER,
                 crs4f100CfgMatch            INTEGER,
                 crs4f100SerialNumber        INTEGER,
                 crs4f100ConnA               INTEGER,
                 crs4f100ConnB               INTEGER,
                 crs4f100FiberLink           INTEGER,
                 crs4f100Fault               INTEGER,
                 crs4f100FirmwareRevision    INTEGER,
                 crs4f100CopperActivity      INTEGER,
                 crs4f100CacheClean          INTEGER
                 }

crs4f100BiaIndex OBJECT-TYPE
        SYNTAX INTEGER
        ACCESS read-only
        STATUS mandatory
        DESCRIPTION "The serial number (BIA) of the cabinet in which the 
                     device is installed"
        ::= { crs4f100Entry 1 }

crs4f100SlotIndex OBJECT-TYPE
        SYNTAX INTEGER
        ACCESS read-only
        STATUS mandatory
        DESCRIPTION "The slot in which the device is installed"
        ::= { crs4f100Entry 2 }

crs4f100Groups OBJECT-TYPE
        SYNTAX DisplayString
        ACCESS read-write
        STATUS mandatory
        DESCRIPTION "User-defined keywords that group this device together with
                     other devices under a user-defined scheme. By placing 
                     matching keywords in cpsGroupCtrl.0, the agent can be
                     instructed to apply configuration changes simultaneously
                     to all group members rather than to individual devices.
                     Every Groups string has three automatically defined
                     implied values: 
                     1) The model family of the device, e.g. 'CRS4F100'
                     2) The serial number of the cabinet in which the device
                        is installed, in decimal with no leading zeroes, 
                        e.g. '12345', and 
                     3) same as 2, with the slot in which the device is 
                        installed appended, enclosed in square brackets. 
                        e.g. '12345[9]'"
        ::= { crs4f100Entry 3 }

crs4f100MRevision OBJECT-TYPE
        SYNTAX INTEGER
        ACCESS read-only
        STATUS mandatory
        DESCRIPTION "The marketing revision of this device"
        ::= { crs4f100Entry 4 }

crs4f100CfgMatch OBJECT-TYPE
        SYNTAX INTEGER { yes(1), no(2), notApplicable(3) }
        ACCESS read-only
        STATUS mandatory
        DESCRIPTION "yes(1) indicates that the conditions specified in 
                     cpsGroupCtrl.0 match the Groups value for this
                     device. no(2) means that there is no match.
                     notApplicable(3) indicates that cpsGroupCtrl.0 is null
                     and therefore no comparison was performed."
        ::= { crs4f100Entry 5 }

crs4f100SerialNumber OBJECT-TYPE
        SYNTAX INTEGER 
        ACCESS read-only
        STATUS mandatory
        DESCRIPTION "The serial number of this device"
        ::= { crs4f100Entry 6 }

crs4f100ConnA OBJECT-TYPE
        SYNTAX CpsConnector
        ACCESS read-only
        STATUS mandatory
        DESCRIPTION "The style of Fiber connector built into this device"
        ::= { crs4f100Entry 7 }

crs4f100ConnB OBJECT-TYPE
        SYNTAX CpsConnector
        ACCESS read-only
        STATUS mandatory
        DESCRIPTION "The style of Copper connector built into this device"
        ::= { crs4f100Entry 8 }

crs4f100FiberLink OBJECT-TYPE
        SYNTAX INTEGER { linkUp(1), linkDown(2) }
        ACCESS read-only
        STATUS mandatory
        DESCRIPTION "Status of Fiber Link for this device"
        ::= { crs4f100Entry 9 }

crs4f100Fault OBJECT-TYPE
        SYNTAX INTEGER { yes(1), no(2) }
        ACCESS read-only
        STATUS mandatory
        DESCRIPTION "Value is yes(1) when FiberLink has value linkDown(2)"
        ::= { crs4f100Entry 10 }

crs4f100FirmwareRevision OBJECT-TYPE
        SYNTAX INTEGER
        ACCESS read-only
        STATUS mandatory
        DESCRIPTION "The Firmware Revision MIB Variable reports the revision 
                     of software running on the processor on this particular
                     device.  You can discover the revisions on these devices
                     by entering the PICREV command at the command line 
                     interface.  Device Firmware Revisions are normally 
                     discussed in terms of a single letter, e.g. revision 'B'.
                     However, when the firmware revision is displayed by 
                     generic MIB processing code that is unaware of this 
                     convention, the revision is displayed as a decimal value. 
                     The table in crs4f100.html provides some examples of how 
                     decimal revision values correspond to letter revision 
                     values."
        ::= { crs4f100Entry 11 }

crs4f100CopperActivity OBJECT-TYPE
        SYNTAX INTEGER { yes(1), no(2) }
        ACCESS read-only
        STATUS mandatory
        DESCRIPTION "The activity indicator has the value yes(1) when the 
                     hardware has recently detected network traffic on the 
                     associated network port, and no(2) otherwise."
        ::= { crs4f100Entry 12 }

crs4f100CacheClean OBJECT-TYPE
        SYNTAX INTEGER { clean(1), dirty(2) }
        ACCESS read-only
        STATUS mandatory
        DESCRIPTION "When the value is clean(1)Device and Management Module
                     cache are synchronized, no automatic corrections to 
                     configuration will occur.  When the value is dirty(2)
                     Device and Management Module cache are not synchronized.
                     The configuration currently displayed by the application 
                     has not been validated by the device. The device may 
                     need to correct the configuration, in which case the 
                     displayed configuration will change."
        ::= { crs4f100Entry 13 }

-- ==================================================================
-- Table for a cmefg100 slide in card.

cmefg100Table OBJECT-TYPE
        SYNTAX SEQUENCE OF Cmefg100Entry
        ACCESS not-accessible
        STATUS mandatory
        DESCRIPTION "Generated CMEFG100 MIB Version 041110a "
        ::= { cpsSlotDetail 27 }

cmefg100Entry OBJECT-TYPE
        SYNTAX Cmefg100Entry
        ACCESS not-accessible
        STATUS mandatory
        DESCRIPTION "Status and configuration entries for a
                     single CMEFG100"
        INDEX { cmefg100SubDeviceIndex, cmefg100BiaIndex, cmefg100SlotIndex }
        ::= { cmefg100Table 1 }

Cmefg100Entry ::=
        SEQUENCE {
                 cmefg100SubDeviceIndex                   INTEGER,
                 cmefg100BiaIndex                         INTEGER,
                 cmefg100SlotIndex                        INTEGER,
                 cmefg100Groups                           DisplayString,
                 cmefg100MRevision                        INTEGER,
                 cmefg100CfgMatch                         INTEGER,
                 cmefg100ImcLocEnable                     INTEGER,
                 cmefg100ImcLocReset                      INTEGER,
                 cmefg100ImcRmtEnable                     INTEGER,
                 cmefg100ImcRmtReset                      INTEGER,
                 cmefg100ImcRxAlignmentErrorsTbl          INTEGER,
                 cmefg100ImcRxBroadcastPktsTbl            INTEGER,
                 cmefg100ImcRxDropPktsTbl                 INTEGER,
                 cmefg100ImcRxExcessSizeDiscTbl           INTEGER,
                 cmefg100ImcRxFCSErrorsTbl                INTEGER,
                 cmefg100ImcRxFragmentsTbl                INTEGER,
                 cmefg100ImcRxGoodOctetsTbl               INTEGER,
                 cmefg100ImcRxGoodOctetsWrapTbl           INTEGER,
                 cmefg100ImcRxJabbersTbl                  INTEGER,
                 cmefg100ImcRxMulticastPktsTbl            INTEGER,
                 cmefg100ImcRxOctetsTbl                   INTEGER,
                 cmefg100ImcRxOctetsWrapTbl               INTEGER,
                 cmefg100ImcRxOversizePktsTbl             INTEGER,
                 cmefg100ImcRxPausePktsTbl                INTEGER,
                 cmefg100ImcRxPkts1024to1522OctetsTbl     INTEGER,
                 cmefg100ImcRxPkts128to255OctetsTbl       INTEGER,
                 cmefg100ImcRxPkts256to511OctetsTbl       INTEGER,
                 cmefg100ImcRxPkts512to1023OctetsTbl      INTEGER,
                 cmefg100ImcRxPkts64OctetsTbl             INTEGER,
                 cmefg100ImcRxPkts65to127OctetsTbl        INTEGER,
                 cmefg100ImcRxQosOctetsTbl                INTEGER,
                 cmefg100ImcRxQosOctetsWrapTbl            INTEGER,
                 cmefg100ImcRxQosPktsTbl                  INTEGER,
                 cmefg100ImcRxSAChangesTbl                INTEGER,
                 cmefg100ImcRxSymbolErrorTbl              INTEGER,
                 cmefg100ImcRxUndersizePktsTbl            INTEGER,
                 cmefg100ImcRxUnicastPktsTbl              INTEGER,
                 cmefg100ImcTxBroadcastPktsTbl            INTEGER,
                 cmefg100ImcTxCollisionsTbl               INTEGER,
                 cmefg100ImcTxDeferredTransmitTbl         INTEGER,
                 cmefg100ImcTxDropPktsTbl                 INTEGER,
                 cmefg100ImcTxExcessiveCollisionTbl       INTEGER,
                 cmefg100ImcTxFrameInDiscTbl              INTEGER,
                 cmefg100ImcTxLateCollisionTbl            INTEGER,
                 cmefg100ImcTxMulticastPktsTbl            INTEGER,
                 cmefg100ImcTxMultipleCollisionTbl        INTEGER,
                 cmefg100ImcTxOctetsTbl                   INTEGER,
                 cmefg100ImcTxOctetsWrapTbl               INTEGER,
                 cmefg100ImcTxPausePktsTbl                INTEGER,
                 cmefg100ImcTxQosOctetsTbl                INTEGER,
                 cmefg100ImcTxQosOctetsWrapTbl            INTEGER,
                 cmefg100ImcTxQosPktsTbl                  INTEGER,
                 cmefg100ImcTxSingleCollisionTbl          INTEGER,
                 cmefg100ImcTxUnicastPktsTbl              INTEGER,
                 cmefg100LadCacheCmd                      INTEGER,
                 cmefg100LadCacheState                    INTEGER,
                 cmefg100LadEditCmd                       INTEGER,
                 cmefg100LadEditMac                       OCTET STRING,
                 cmefg100LadEditPort                      INTEGER,
                 cmefg100LadEditVid                       INTEGER,
                 cmefg100LadEntries                       INTEGER,
                 cmefg100LadMacTbl                        MacAddress,
                 cmefg100LadPortTbl                       INTEGER,
                 cmefg100LadStaticTbl                     INTEGER,
                 cmefg100LadVidTbl                        INTEGER,
                 cmefg100LocColdstart                     INTEGER,
                 cmefg100LocDmiRxPower                    INTEGER,
                 cmefg100LocDmiRxPowerAlarm               INTEGER,
                 cmefg100LocDmiTemp                       INTEGER,
                 cmefg100LocDmiTempAlarm                  INTEGER,
                 cmefg100LocDmiTxBiasAlarm                INTEGER,
                 cmefg100LocDmiTxBiasCurrent              INTEGER,
                 cmefg100LocDmiTxPower                    INTEGER,
                 cmefg100LocDmiTxPowerAlarm               INTEGER,
                 cmefg100LocFiberAdv1000FDX               INTEGER,
                 cmefg100LocFiberAdv1000HDX               INTEGER,
                 cmefg100LocFiberAutoNegot                INTEGER,
                 cmefg100LocFiberConnA                    CpsConnector,
                 cmefg100LocFiberDuplex                   INTEGER,
                 cmefg100LocFiberLink                     INTEGER,
                 cmefg100LocFiberPause                    INTEGER,
                 cmefg100LocFiberQosPause                 INTEGER,
                 cmefg100LocFiberSacEnable                INTEGER,
                 cmefg100LocFiberSacStatus                INTEGER,
                 cmefg100LocFirmwareRevision              INTEGER,
                 cmefg100LocFpgaRev                       INTEGER,
                 cmefg100LocFxTxBwaKb                     INTEGER,
                 cmefg100LocFxTxBwaMb                     INTEGER,
                 cmefg100LocOamActiveMode                 INTEGER,
                 cmefg100LocOamAdminControl               INTEGER,
                 cmefg100LocOamConfigRevision             INTEGER,
                 cmefg100LocOamControlInUnknownOpcodes    INTEGER,
                 cmefg100LocOamCriticalEvent              INTEGER,
                 cmefg100LocOamDuplicateEventNotificationRx INTEGER,
                 cmefg100LocOamFramesLostDueToOamError    INTEGER,
                 cmefg100LocOamInformationRx              INTEGER,
                 cmefg100LocOamInformationTx              INTEGER,
                 cmefg100LocOamLastGasp                   INTEGER,
                 cmefg100LocOamLinkEvents                 INTEGER,
                 cmefg100LocOamLinkFault                  INTEGER,
                 cmefg100LocOamLocDteDisc                 INTEGER,
                 cmefg100LocOamLoopbackControlRx          INTEGER,
                 cmefg100LocOamLoopbackControlTx          INTEGER,
                 cmefg100LocOamMacAddress                 MacAddress,
                 cmefg100LocOamMaxOamPduSize              INTEGER,
                 cmefg100LocOamMultiplexorState           INTEGER,
                 cmefg100LocOamOperStatus                 INTEGER,
                 cmefg100LocOamOrgSpecificRx              INTEGER,
                 cmefg100LocOamOrgSpecificTx              INTEGER,
                 cmefg100LocOamParserState                INTEGER,
                 cmefg100LocOamRmtDteDisc                 INTEGER,
                 cmefg100LocOamRmtLoopback                INTEGER,
                 cmefg100LocOamUnidirectional             INTEGER,
                 cmefg100LocOamVarRetrieval               INTEGER,
                 cmefg100LocSelfTestFailed                INTEGER,
                 cmefg100LocSerialNumber                  INTEGER,
                 cmefg100LocTpAdv1000FDX                  INTEGER,
                 cmefg100LocTpAdv1000HDX                  INTEGER,
                 cmefg100LocTpAdv100FDX                   INTEGER,
                 cmefg100LocTpAdv100HDX                   INTEGER,
                 cmefg100LocTpAdv10FDX                    INTEGER,
                 cmefg100LocTpAdv10HDX                    INTEGER,
                 cmefg100LocTpAutoNegot                   INTEGER,
                 cmefg100LocTpConnB                       CpsConnector,
                 cmefg100LocTpCross                       INTEGER,
                 cmefg100LocTpDuplex                      INTEGER,
                 cmefg100LocTpLink                        INTEGER,
                 cmefg100LocTpPause                       INTEGER,
                 cmefg100LocTpQosPause                    INTEGER,
                 cmefg100LocTpSacEnable                   INTEGER,
                 cmefg100LocTpSacStatus                   INTEGER,
                 cmefg100LocTpSpeed                       INTEGER,
                 cmefg100LocTxFxBwaKb                     INTEGER,
                 cmefg100LocTxFxBwaMb                     INTEGER,
                 cmefg100LocUptime                        TimeTicks,
                 cmefg100QosHqWeight                      INTEGER,
                 cmefg100QosLqWeight                      INTEGER,
                 cmefg100QosPriority                      INTEGER,
                 cmefg100RmtColdStart                     INTEGER,
                 cmefg100RmtDetected                      INTEGER,
                 cmefg100RmtDmiRxPower                    INTEGER,
                 cmefg100RmtDmiRxPowerAlarm               INTEGER,
                 cmefg100RmtDmiTemp                       INTEGER,
                 cmefg100RmtDmiTempAlarm                  INTEGER,
                 cmefg100RmtDmiTxBiasAlarm                INTEGER,
                 cmefg100RmtDmiTxBiasCurrent              INTEGER,
                 cmefg100RmtDmiTxPower                    INTEGER,
                 cmefg100RmtDmiTxPowerAlarm               INTEGER,
                 cmefg100RmtFactoryReset                  INTEGER,
                 cmefg100RmtFiberAutoNegot                INTEGER,
                 cmefg100RmtFiberLink                     INTEGER,
                 cmefg100RmtFiberPause                    INTEGER,
                 cmefg100RmtFiberQosPause                 INTEGER,
                 cmefg100RmtFirmwareRevision              INTEGER,
                 cmefg100RmtFpgaRev                       INTEGER,
                 cmefg100RmtOamActiveMode                 INTEGER,
                 cmefg100RmtOamCriticalEvent              INTEGER,
                 cmefg100RmtOamLastGasp                   INTEGER,
                 cmefg100RmtOamLinkEvents                 INTEGER,
                 cmefg100RmtOamLinkFault                  INTEGER,
                 cmefg100RmtOamLocDteDisc                 INTEGER,
                 cmefg100RmtOamPeerConfigRevision         INTEGER,
                 cmefg100RmtOamPeerMacAddress             MacAddress,
                 cmefg100RmtOamPeerMaxOamPduSize          INTEGER,
                 cmefg100RmtOamPeerMultiplexorState       INTEGER,
                 cmefg100RmtOamPeerParserState            INTEGER,
                 cmefg100RmtOamPeerVendorInfo             OCTET STRING,
                 cmefg100RmtOamPeerVendorOui              OCTET STRING,
                 cmefg100RmtOamRmtDteDisc                 INTEGER,
                 cmefg100RmtOamRmtLoopback                INTEGER,
                 cmefg100RmtOamUnidirectional             INTEGER,
                 cmefg100RmtOamVarRetrieval               INTEGER,
                 cmefg100RmtSelfTestFailed                INTEGER,
                 cmefg100RmtSerialNumber                  INTEGER,
                 cmefg100RmtTpAdv1000FDX                  INTEGER,
                 cmefg100RmtTpAdv1000HDX                  INTEGER,
                 cmefg100RmtTpAdv100FDX                   INTEGER,
                 cmefg100RmtTpAdv100HDX                   INTEGER,
                 cmefg100RmtTpAdv10FDX                    INTEGER,
                 cmefg100RmtTpAdv10HDX                    INTEGER,
                 cmefg100RmtTpAutoNegot                   INTEGER,
                 cmefg100RmtTpCross                       INTEGER,
                 cmefg100RmtTpDuplex                      INTEGER,
                 cmefg100RmtTpLink                        INTEGER,
                 cmefg100RmtTpPause                       INTEGER,
                 cmefg100RmtTpQosPause                    INTEGER,
                 cmefg100RmtTpSpeed                       INTEGER,
                 cmefg100RmtUptime                        TimeTicks,
                 cmefg100VlanCacheCmd                     INTEGER,
                 cmefg100VlanCacheState                   INTEGER,
                 cmefg100VlanEditCmd                      INTEGER,
                 cmefg100VlanEditFwdFiber                 INTEGER,
                 cmefg100VlanEditFwdTp                    INTEGER,
                 cmefg100VlanEditUntagFiber               INTEGER,
                 cmefg100VlanEditUntagTp                  INTEGER,
                 cmefg100VlanEditVid                      INTEGER,
                 cmefg100VlanEnable                       INTEGER,
                 cmefg100VlanEntries                      INTEGER,
                 cmefg100VlanFiberDefaultPri              INTEGER,
                 cmefg100VlanFiberDefaultVid              INTEGER,
                 cmefg100VlanFiberInUntaggedDrop          INTEGER,
                 cmefg100VlanFwdFiberTbl                  INTEGER,
                 cmefg100VlanFwdTpTbl                     INTEGER,
                 cmefg100VlanIngressVidHitNoMem           INTEGER,
                 cmefg100VlanIngressVidMiss               INTEGER,
                 cmefg100VlanPriMapTbl                    INTEGER,
                 cmefg100VlanPriTagCtrl                   INTEGER,
                 cmefg100VlanSetFailed                    INTEGER,
                 cmefg100VlanTagIn                        INTEGER,
                 cmefg100VlanTpDefaultPri                 INTEGER,
                 cmefg100VlanTpDefaultVid                 INTEGER,
                 cmefg100VlanTpInUntaggedDrop             INTEGER,
                 cmefg100VlanUntagFiberTbl                INTEGER,
                 cmefg100VlanUntagTpTbl                   INTEGER,
                 cmefg100VlanVidTagCtrl                   INTEGER,
                 cmefg100VlanVidTbl                       INTEGER,
                 cmefg100CacheClean                       INTEGER 
                 }

cmefg100SubDeviceIndex OBJECT-TYPE
        SYNTAX INTEGER 
        ACCESS read-only
        STATUS mandatory
        DESCRIPTION "If the name of a particular MIB variable does not 
                     end in 'Tbl', then it uses the placeholder value 
                     '1' in the subdevice index column. "
        ::= { cmefg100Entry 1 }

cmefg100BiaIndex OBJECT-TYPE
        SYNTAX INTEGER 
        ACCESS read-only
        STATUS mandatory
        DESCRIPTION ""
        ::= { cmefg100Entry 2 }

cmefg100SlotIndex OBJECT-TYPE
        SYNTAX INTEGER 
        ACCESS read-only
        STATUS mandatory
        DESCRIPTION ""
        ::= { cmefg100Entry 3 }

cmefg100Groups OBJECT-TYPE
        SYNTAX DisplayString 
        ACCESS read-write
        STATUS mandatory
        DESCRIPTION ""
        ::= { cmefg100Entry 4 }

cmefg100MRevision OBJECT-TYPE
        SYNTAX INTEGER 
        ACCESS read-only
        STATUS mandatory
        DESCRIPTION ""
        ::= { cmefg100Entry 5 }

cmefg100CfgMatch OBJECT-TYPE
        SYNTAX INTEGER { yes(1), no(2) }
        ACCESS read-only
        STATUS mandatory
        DESCRIPTION ""
        ::= { cmefg100Entry 6 }

cmefg100ImcLocEnable OBJECT-TYPE
        SYNTAX INTEGER { enabled(1), disabled(2) }
        ACCESS read-write
        STATUS mandatory
        DESCRIPTION "Enable periodic upload of local Interface MIB 
                     Counters from CMEFG100 to Agent. cmefg100ImcxxxTbl 
                     subdevice 1=local tp, subdevice 2=local fiber. "
        ::= { cmefg100Entry 7 }

cmefg100ImcLocReset OBJECT-TYPE
        SYNTAX INTEGER { reset(1), doNothing(2) }
        ACCESS read-write
        STATUS mandatory
        DESCRIPTION "set to reset(1) to clear all local cmefg100Imc 
                     counters. "
        ::= { cmefg100Entry 8 }

cmefg100ImcRmtEnable OBJECT-TYPE
        SYNTAX INTEGER { enabled(1), disabled(2) }
        ACCESS read-write
        STATUS mandatory
        DESCRIPTION "Enable periodic upload of remote Interface MIB 
                     Counters from CMEFG100 to Agent. cmefg100ImcxxxTbl 
                     subdevice 3=remote tp, subdevice 4=remote fiber. "
        ::= { cmefg100Entry 9 }

cmefg100ImcRmtReset OBJECT-TYPE
        SYNTAX INTEGER { reset(1), doNothing(2) }
        ACCESS read-write
        STATUS mandatory
        DESCRIPTION "set to reset(1) to clear all remote cmefg100Imc 
                     counters. "
        ::= { cmefg100Entry 10 }

cmefg100ImcRxAlignmentErrorsTbl OBJECT-TYPE
        SYNTAX INTEGER 
        ACCESS read-only
        STATUS mandatory
        DESCRIPTION ""
        ::= { cmefg100Entry 11 }

cmefg100ImcRxBroadcastPktsTbl OBJECT-TYPE
        SYNTAX INTEGER 
        ACCESS read-only
        STATUS mandatory
        DESCRIPTION ""
        ::= { cmefg100Entry 12 }

cmefg100ImcRxDropPktsTbl OBJECT-TYPE
        SYNTAX INTEGER 
        ACCESS read-only
        STATUS mandatory
        DESCRIPTION ""
        ::= { cmefg100Entry 13 }

cmefg100ImcRxExcessSizeDiscTbl OBJECT-TYPE
        SYNTAX INTEGER 
        ACCESS read-only
        STATUS mandatory
        DESCRIPTION ""
        ::= { cmefg100Entry 14 }

cmefg100ImcRxFCSErrorsTbl OBJECT-TYPE
        SYNTAX INTEGER 
        ACCESS read-only
        STATUS mandatory
        DESCRIPTION ""
        ::= { cmefg100Entry 15 }

cmefg100ImcRxFragmentsTbl OBJECT-TYPE
        SYNTAX INTEGER 
        ACCESS read-only
        STATUS mandatory
        DESCRIPTION ""
        ::= { cmefg100Entry 16 }

cmefg100ImcRxGoodOctetsTbl OBJECT-TYPE
        SYNTAX INTEGER 
        ACCESS read-only
        STATUS mandatory
        DESCRIPTION ""
        ::= { cmefg100Entry 17 }

cmefg100ImcRxGoodOctetsWrapTbl OBJECT-TYPE
        SYNTAX INTEGER 
        ACCESS read-only
        STATUS mandatory
        DESCRIPTION ""
        ::= { cmefg100Entry 18 }

cmefg100ImcRxJabbersTbl OBJECT-TYPE
        SYNTAX INTEGER 
        ACCESS read-only
        STATUS mandatory
        DESCRIPTION ""
        ::= { cmefg100Entry 19 }

cmefg100ImcRxMulticastPktsTbl OBJECT-TYPE
        SYNTAX INTEGER 
        ACCESS read-only
        STATUS mandatory
        DESCRIPTION ""
        ::= { cmefg100Entry 20 }

cmefg100ImcRxOctetsTbl OBJECT-TYPE
        SYNTAX INTEGER 
        ACCESS read-only
        STATUS mandatory
        DESCRIPTION ""
        ::= { cmefg100Entry 21 }

cmefg100ImcRxOctetsWrapTbl OBJECT-TYPE
        SYNTAX INTEGER 
        ACCESS read-only
        STATUS mandatory
        DESCRIPTION ""
        ::= { cmefg100Entry 22 }

cmefg100ImcRxOversizePktsTbl OBJECT-TYPE
        SYNTAX INTEGER 
        ACCESS read-only
        STATUS mandatory
        DESCRIPTION ""
        ::= { cmefg100Entry 23 }

cmefg100ImcRxPausePktsTbl OBJECT-TYPE
        SYNTAX INTEGER 
        ACCESS read-only
        STATUS mandatory
        DESCRIPTION ""
        ::= { cmefg100Entry 24 }

cmefg100ImcRxPkts1024to1522OctetsTbl OBJECT-TYPE
        SYNTAX INTEGER 
        ACCESS read-only
        STATUS mandatory
        DESCRIPTION ""
        ::= { cmefg100Entry 25 }

cmefg100ImcRxPkts128to255OctetsTbl OBJECT-TYPE
        SYNTAX INTEGER 
        ACCESS read-only
        STATUS mandatory
        DESCRIPTION ""
        ::= { cmefg100Entry 26 }

cmefg100ImcRxPkts256to511OctetsTbl OBJECT-TYPE
        SYNTAX INTEGER 
        ACCESS read-only
        STATUS mandatory
        DESCRIPTION ""
        ::= { cmefg100Entry 27 }

cmefg100ImcRxPkts512to1023OctetsTbl OBJECT-TYPE
        SYNTAX INTEGER 
        ACCESS read-only
        STATUS mandatory
        DESCRIPTION ""
        ::= { cmefg100Entry 28 }

cmefg100ImcRxPkts64OctetsTbl OBJECT-TYPE
        SYNTAX INTEGER 
        ACCESS read-only
        STATUS mandatory
        DESCRIPTION ""
        ::= { cmefg100Entry 29 }

cmefg100ImcRxPkts65to127OctetsTbl OBJECT-TYPE
        SYNTAX INTEGER 
        ACCESS read-only
        STATUS mandatory
        DESCRIPTION ""
        ::= { cmefg100Entry 30 }

cmefg100ImcRxQosOctetsTbl OBJECT-TYPE
        SYNTAX INTEGER 
        ACCESS read-only
        STATUS mandatory
        DESCRIPTION ""
        ::= { cmefg100Entry 31 }

cmefg100ImcRxQosOctetsWrapTbl OBJECT-TYPE
        SYNTAX INTEGER 
        ACCESS read-only
        STATUS mandatory
        DESCRIPTION ""
        ::= { cmefg100Entry 32 }

cmefg100ImcRxQosPktsTbl OBJECT-TYPE
        SYNTAX INTEGER 
        ACCESS read-only
        STATUS mandatory
        DESCRIPTION ""
        ::= { cmefg100Entry 33 }

cmefg100ImcRxSAChangesTbl OBJECT-TYPE
        SYNTAX INTEGER 
        ACCESS read-only
        STATUS mandatory
        DESCRIPTION ""
        ::= { cmefg100Entry 34 }

cmefg100ImcRxSymbolErrorTbl OBJECT-TYPE
        SYNTAX INTEGER 
        ACCESS read-only
        STATUS mandatory
        DESCRIPTION ""
        ::= { cmefg100Entry 35 }

cmefg100ImcRxUndersizePktsTbl OBJECT-TYPE
        SYNTAX INTEGER 
        ACCESS read-only
        STATUS mandatory
        DESCRIPTION ""
        ::= { cmefg100Entry 36 }

cmefg100ImcRxUnicastPktsTbl OBJECT-TYPE
        SYNTAX INTEGER 
        ACCESS read-only
        STATUS mandatory
        DESCRIPTION ""
        ::= { cmefg100Entry 37 }

cmefg100ImcTxBroadcastPktsTbl OBJECT-TYPE
        SYNTAX INTEGER 
        ACCESS read-only
        STATUS mandatory
        DESCRIPTION ""
        ::= { cmefg100Entry 38 }

cmefg100ImcTxCollisionsTbl OBJECT-TYPE
        SYNTAX INTEGER 
        ACCESS read-only
        STATUS mandatory
        DESCRIPTION ""
        ::= { cmefg100Entry 39 }

cmefg100ImcTxDeferredTransmitTbl OBJECT-TYPE
        SYNTAX INTEGER 
        ACCESS read-only
        STATUS mandatory
        DESCRIPTION ""
        ::= { cmefg100Entry 40 }

cmefg100ImcTxDropPktsTbl OBJECT-TYPE
        SYNTAX INTEGER 
        ACCESS read-only
        STATUS mandatory
        DESCRIPTION ""
        ::= { cmefg100Entry 41 }

cmefg100ImcTxExcessiveCollisionTbl OBJECT-TYPE
        SYNTAX INTEGER 
        ACCESS read-only
        STATUS mandatory
        DESCRIPTION ""
        ::= { cmefg100Entry 42 }

cmefg100ImcTxFrameInDiscTbl OBJECT-TYPE
        SYNTAX INTEGER 
        ACCESS read-only
        STATUS mandatory
        DESCRIPTION ""
        ::= { cmefg100Entry 43 }

cmefg100ImcTxLateCollisionTbl OBJECT-TYPE
        SYNTAX INTEGER 
        ACCESS read-only
        STATUS mandatory
        DESCRIPTION ""
        ::= { cmefg100Entry 44 }

cmefg100ImcTxMulticastPktsTbl OBJECT-TYPE
        SYNTAX INTEGER 
        ACCESS read-only
        STATUS mandatory
        DESCRIPTION ""
        ::= { cmefg100Entry 45 }

cmefg100ImcTxMultipleCollisionTbl OBJECT-TYPE
        SYNTAX INTEGER 
        ACCESS read-only
        STATUS mandatory
        DESCRIPTION ""
        ::= { cmefg100Entry 46 }

cmefg100ImcTxOctetsTbl OBJECT-TYPE
        SYNTAX INTEGER 
        ACCESS read-only
        STATUS mandatory
        DESCRIPTION ""
        ::= { cmefg100Entry 47 }

cmefg100ImcTxOctetsWrapTbl OBJECT-TYPE
        SYNTAX INTEGER 
        ACCESS read-only
        STATUS mandatory
        DESCRIPTION ""
        ::= { cmefg100Entry 48 }

cmefg100ImcTxPausePktsTbl OBJECT-TYPE
        SYNTAX INTEGER 
        ACCESS read-only
        STATUS mandatory
        DESCRIPTION ""
        ::= { cmefg100Entry 49 }

cmefg100ImcTxQosOctetsTbl OBJECT-TYPE
        SYNTAX INTEGER 
        ACCESS read-only
        STATUS mandatory
        DESCRIPTION ""
        ::= { cmefg100Entry 50 }

cmefg100ImcTxQosOctetsWrapTbl OBJECT-TYPE
        SYNTAX INTEGER 
        ACCESS read-only
        STATUS mandatory
        DESCRIPTION ""
        ::= { cmefg100Entry 51 }

cmefg100ImcTxQosPktsTbl OBJECT-TYPE
        SYNTAX INTEGER 
        ACCESS read-only
        STATUS mandatory
        DESCRIPTION ""
        ::= { cmefg100Entry 52 }

cmefg100ImcTxSingleCollisionTbl OBJECT-TYPE
        SYNTAX INTEGER 
        ACCESS read-only
        STATUS mandatory
        DESCRIPTION ""
        ::= { cmefg100Entry 53 }

cmefg100ImcTxUnicastPktsTbl OBJECT-TYPE
        SYNTAX INTEGER 
        ACCESS read-only
        STATUS mandatory
        DESCRIPTION ""
        ::= { cmefg100Entry 54 }

cmefg100LadCacheCmd OBJECT-TYPE
        SYNTAX INTEGER { loadCache(1), doNothing(2), release(3) }
        ACCESS read-write
        STATUS mandatory
        DESCRIPTION "All variables starting with cmefg100Lad relate to 
                     the Learned MAC Address Database. Due to the large 
                     size of the LAD database and the limited memory 
                     within the Agent, the cache is loaded into the 
                     cache memory buffer only when it is requested via 
                     this MIB variable. Setting this var to loadCache 
                     commands the agent to upload the LAD from the 
                     device exactly one time. Note that the contents of 
                     this cache are NOT automatically refreshed. 
                     Setting this variable to 'release' causes the data 
                     in the cache to be purged, even if the cache 
                     buffer contains data of an entirely different 
                     type, such as the VLAN table cache. Thus, it is 
                     not necessary to know what type of data was most 
                     recently loaded into the cache buffer, but it is 
                     necessary to take care not to release data that is 
                     currently in use. A genErr will be returned if any 
                     other command involving reading or writing the LAD 
                     or the VLAN table is in progress. "
        ::= { cmefg100Entry 55 }

cmefg100LadCacheState OBJECT-TYPE
        SYNTAX INTEGER { ready(1), empty(2), transferring(3), 
                         bufferBusy(4), stale(5) }
        ACCESS read-write
        STATUS mandatory
        DESCRIPTION "This variable shows the current state of the 
                     Agent's cache buffer with respect to the Learned 
                     Address Database. A value of 'ready' means that 
                     the cache buffer contains a complete copy of the 
                     LAD that is less than 300 seconds old. A value of 
                     'stale' means that the cache buffer contains a 
                     complete copy of the LAD that is more than 300 
                     seconds old. A value of 'empty' means that the 
                     buffer has been purged, and the system is ready to 
                     accept a cmefg100LadCacheCmd of 'loadCache.' A 
                     value of 'transferring' means that no command can 
                     be issued and the cache cannot be read because 
                     data is currently being transferred into the cache 
                     buffer. The data may or may not be related to the 
                     LAD. A value of 'bufferBusy' means that the buffer 
                     contains a complete copy (ready or stale) of 
                     something other than the LAD. The contents of the 
                     buffer can be overwritten with the LAD by issuing 
                     a 'loadCache' command. "
        ::= { cmefg100Entry 56 }

cmefg100LadEditCmd OBJECT-TYPE
        SYNTAX INTEGER { write(1), delete(2), doNothing(3) }
        ACCESS read-write
        STATUS mandatory
        DESCRIPTION "Setting this var to 'write' causes LadEditMac, 
                     LadEditPort, and LadEditVid to be written 
                     (insert/overwrite as required) to the LAD. Setting 
                     this var to 'delete' causes the address 
                     represented by LadEditMac to be deleted from the 
                     LAD. Changes made are not reflected in the LAD 
                     cache until the device accepts them and the cache 
                     is reloaded. A genErr will be returned if any 
                     other command involving reading or writing the LAD 
                     or the VLAN table is in progress. "
        ::= { cmefg100Entry 57 }

cmefg100LadEditMac OBJECT-TYPE
        SYNTAX OCTET STRING 
        ACCESS read-write
        STATUS mandatory
        DESCRIPTION "A plain-text representation of a MAC address to be 
                     used the next time cmefg100LadEditCmd is set to 
                     write or delete. "
        ::= { cmefg100Entry 58 }

cmefg100LadEditPort OBJECT-TYPE
        SYNTAX INTEGER { twistedPair(1), fiber(2), drop(3) }
        ACCESS read-write
        STATUS mandatory
        DESCRIPTION "A port to be used the next time cmefg100LadEditCmd 
                     is set to write. "
        ::= { cmefg100Entry 59 }

cmefg100LadEditVid OBJECT-TYPE
        SYNTAX INTEGER 
        ACCESS read-write
        STATUS mandatory
        DESCRIPTION "A VLAN Id to be used the next time 
                     cmefg100LadEditCmd is set to write. Not valid when 
                     cmefg100VlanEnable is disabled(2) "
        ::= { cmefg100Entry 60 }

cmefg100LadEntries OBJECT-TYPE
        SYNTAX INTEGER 
        ACCESS read-only
        STATUS mandatory
        DESCRIPTION "A count of the number of entries currently in the 
                     LAD Cache. See also cmefg100LadCacheState. If a 
                     LAD cache-filling transfer is in progress, this 
                     variable can be read for a progress report. "
        ::= { cmefg100Entry 61 }

cmefg100LadMacTbl OBJECT-TYPE
        SYNTAX MacAddress 
        ACCESS read-only
        STATUS mandatory
        DESCRIPTION "An Ethernet MAC address in the LAD table. The 
                     SubDeviceIndex is an arbitrary integer sequence 
                     number, range 1..cmefg100LadEntries. If 
                     cmefg100LadEntries is 0 (either because 
                     cmefg100LadCacheState is not 'ready/stale' or 
                     because there simply are no entries), this table 
                     contains a solitary dummy entry, 
                     SubDeviceIndex==1. "
        ::= { cmefg100Entry 62 }

cmefg100LadPortTbl OBJECT-TYPE
        SYNTAX INTEGER { twistedPair(1), fiber(2), drop(3), 
                         notApplicable(4) }
        ACCESS read-only
        STATUS mandatory
        DESCRIPTION "A port in the LAD table. Drop means 'forward to 
                     neither port' The SubDeviceIndex is an arbitrary 
                     integer sequence number, range 
                     1..cmefg100LadEntries. If cmefg100LadEntries is 0 
                     (either because cmefg100LadCacheState is not 
                     'ready/stale' or because there simply are no 
                     entries), this table contains a solitary entry, 
                     SubDeviceIndex==1, value notApplicable. "
        ::= { cmefg100Entry 63 }

cmefg100LadStaticTbl OBJECT-TYPE
        SYNTAX INTEGER { static(1), dynamic(2), notApplicable(3) }
        ACCESS read-only
        STATUS mandatory
        DESCRIPTION "An indication of whether the indexed entry in the 
                     LAD is static or dynamic. The SubDeviceIndex is an 
                     arbitrary integer sequence number, range 
                     1..cmefg100LadEntries. If cmefg100LadEntries is 0 
                     (either because cmefg100LadCacheState is not 
                     'ready/stale' or because there simply are no 
                     entries), this table contains a solitary entry, 
                     SubDeviceIndex==1, value notApplicable. "
        ::= { cmefg100Entry 64 }

cmefg100LadVidTbl OBJECT-TYPE
        SYNTAX INTEGER 
        ACCESS read-only
        STATUS mandatory
        DESCRIPTION "A VLAN Id in the LAD table. The SubDeviceIndex is 
                     an arbitrary integer sequence number, range 
                     1..cmefg100LadEntries. If cmefg100LadEntries is 0 
                     (either because cmefg100LadCacheState is not 
                     'ready/stale' or because there simply are no 
                     entries), this table contains a solitary dummy 
                     entry, SubDeviceIndex==1. Always returns the dummy 
                     value '0' when cmefg100VlanEnable is disabled(2). "
        ::= { cmefg100Entry 65 }

cmefg100LocColdstart OBJECT-TYPE
        SYNTAX INTEGER { yes(1), no(2) }
        ACCESS read-only
        STATUS mandatory
        DESCRIPTION ""
        ::= { cmefg100Entry 66 }

cmefg100LocDmiRxPower OBJECT-TYPE
        SYNTAX INTEGER 
        ACCESS read-only
        STATUS mandatory
        DESCRIPTION "DMI: Diagnostic Monitoring Interface for fiber 
                     transceivers "
        ::= { cmefg100Entry 67 }

cmefg100LocDmiRxPowerAlarm OBJECT-TYPE
        SYNTAX INTEGER { normal(1), notSupported(2), lowWarn(3), 
                         highWarn(4), lowAlarm(5), highAlarm(6) }
        ACCESS read-only
        STATUS mandatory
        DESCRIPTION ""
        ::= { cmefg100Entry 68 }

cmefg100LocDmiTemp OBJECT-TYPE
        SYNTAX INTEGER 
        ACCESS read-only
        STATUS mandatory
        DESCRIPTION "In tenths of degrees C "
        ::= { cmefg100Entry 69 }

cmefg100LocDmiTempAlarm OBJECT-TYPE
        SYNTAX INTEGER { normal(1), notSupported(2), lowWarn(3), 
                         highWarn(4), lowAlarm(5), highAlarm(6) }
        ACCESS read-only
        STATUS mandatory
        DESCRIPTION ""
        ::= { cmefg100Entry 70 }

cmefg100LocDmiTxBiasAlarm OBJECT-TYPE
        SYNTAX INTEGER { normal(1), notSupported(2), lowWarn(3), 
                         highWarn(4), lowAlarm(5), highAlarm(6) }
        ACCESS read-only
        STATUS mandatory
        DESCRIPTION ""
        ::= { cmefg100Entry 71 }

cmefg100LocDmiTxBiasCurrent OBJECT-TYPE
        SYNTAX INTEGER 
        ACCESS read-only
        STATUS mandatory
        DESCRIPTION "In microamperes "
        ::= { cmefg100Entry 72 }

cmefg100LocDmiTxPower OBJECT-TYPE
        SYNTAX INTEGER 
        ACCESS read-only
        STATUS mandatory
        DESCRIPTION "In microwatts "
        ::= { cmefg100Entry 73 }

cmefg100LocDmiTxPowerAlarm OBJECT-TYPE
        SYNTAX INTEGER { normal(1), notSupported(2), lowWarn(3), 
                         highWarn(4), lowAlarm(5), highAlarm(6) }
        ACCESS read-only
        STATUS mandatory
        DESCRIPTION ""
        ::= { cmefg100Entry 74 }

cmefg100LocFiberAdv1000FDX OBJECT-TYPE
        SYNTAX INTEGER { enabled(1), disabled(2), notApplicable(3) }
        ACCESS read-write
        STATUS mandatory
        DESCRIPTION "Read-only value notApplicable returned when 
                     autonegotiation is disabled "
        ::= { cmefg100Entry 75 }

cmefg100LocFiberAdv1000HDX OBJECT-TYPE
        SYNTAX INTEGER { enabled(1), disabled(2), notApplicable(3) }
        ACCESS read-write
        STATUS mandatory
        DESCRIPTION "Read-only value notApplicable returned when 
                     autonegotiation is disabled "
        ::= { cmefg100Entry 76 }

cmefg100LocFiberAutoNegot OBJECT-TYPE
        SYNTAX INTEGER { enabled(1), disabled(2) }
        ACCESS read-write
        STATUS mandatory
        DESCRIPTION ""
        ::= { cmefg100Entry 77 }

cmefg100LocFiberConnA OBJECT-TYPE
        SYNTAX CpsConnector 
        ACCESS read-only
        STATUS mandatory
        DESCRIPTION ""
        ::= { cmefg100Entry 78 }

cmefg100LocFiberDuplex OBJECT-TYPE
        SYNTAX INTEGER { forceFDX(1), forceHDX(2), autoFDX(3), 
                         autoHDX(4), negotiating(5) }
        ACCESS read-write
        STATUS mandatory
        DESCRIPTION "Read-only values 3..5 are returned when 
                     autonegotiation is enabled "
        ::= { cmefg100Entry 79 }

cmefg100LocFiberLink OBJECT-TYPE
        SYNTAX INTEGER { up(1), down(2) }
        ACCESS read-only
        STATUS mandatory
        DESCRIPTION ""
        ::= { cmefg100Entry 80 }

cmefg100LocFiberPause OBJECT-TYPE
        SYNTAX INTEGER { asymmetricRx(1), asymmetricTx(2), symmetric(3), 
                         disabled(4) }
        ACCESS read-write
        STATUS mandatory
        DESCRIPTION ""
        ::= { cmefg100Entry 81 }

cmefg100LocFiberQosPause OBJECT-TYPE
        SYNTAX INTEGER { enabled(1), disabled(2) }
        ACCESS read-write
        STATUS mandatory
        DESCRIPTION ""
        ::= { cmefg100Entry 82 }

cmefg100LocFiberSacEnable OBJECT-TYPE
        SYNTAX INTEGER { enabled(1), disabled(2) }
        ACCESS read-write
        STATUS mandatory
        DESCRIPTION "Enable/disable traps for Source Address Change "
        ::= { cmefg100Entry 83 }

cmefg100LocFiberSacStatus OBJECT-TYPE
        SYNTAX INTEGER { changed(1), constant(2) }
        ACCESS read-only
        STATUS mandatory
        DESCRIPTION ""
        ::= { cmefg100Entry 84 }

cmefg100LocFirmwareRevision OBJECT-TYPE
        SYNTAX INTEGER 
        ACCESS read-only
        STATUS mandatory
        DESCRIPTION ""
        ::= { cmefg100Entry 85 }

cmefg100LocFpgaRev OBJECT-TYPE
        SYNTAX INTEGER 
        ACCESS read-only
        STATUS mandatory
        DESCRIPTION "Field-Programmable Gate Array revision "
        ::= { cmefg100Entry 86 }

cmefg100LocFxTxBwaKb OBJECT-TYPE
        SYNTAX INTEGER (1..122112)
        ACCESS read-write
        STATUS mandatory
        DESCRIPTION "FX to TX bandwidth allocation, in Kbps "
        ::= { cmefg100Entry 87 }

cmefg100LocFxTxBwaMb OBJECT-TYPE
        SYNTAX INTEGER (1..1000)
        ACCESS read-write
        STATUS mandatory
        DESCRIPTION "FX to TX bandwidth allocation, in Mbps "
        ::= { cmefg100Entry 88 }

cmefg100LocOamActiveMode OBJECT-TYPE
        SYNTAX INTEGER { active(1), passive(2) }
        ACCESS read-only
        STATUS mandatory
        DESCRIPTION "OAM: Operation, Administration, and Maintenance "
        ::= { cmefg100Entry 89 }

cmefg100LocOamAdminControl OBJECT-TYPE
        SYNTAX INTEGER { enabled(1), disabled(2) }
        ACCESS read-write
        STATUS mandatory
        DESCRIPTION ""
        ::= { cmefg100Entry 90 }

cmefg100LocOamConfigRevision OBJECT-TYPE
        SYNTAX INTEGER 
        ACCESS read-only
        STATUS mandatory
        DESCRIPTION ""
        ::= { cmefg100Entry 91 }

cmefg100LocOamControlInUnknownOpcodes OBJECT-TYPE
        SYNTAX INTEGER 
        ACCESS read-only
        STATUS mandatory
        DESCRIPTION ""
        ::= { cmefg100Entry 92 }

cmefg100LocOamCriticalEvent OBJECT-TYPE
        SYNTAX INTEGER { critical(1), normal(2) }
        ACCESS read-only
        STATUS mandatory
        DESCRIPTION ""
        ::= { cmefg100Entry 93 }

cmefg100LocOamDuplicateEventNotificationRx OBJECT-TYPE
        SYNTAX INTEGER 
        ACCESS read-only
        STATUS mandatory
        DESCRIPTION ""
        ::= { cmefg100Entry 94 }

cmefg100LocOamFramesLostDueToOamError OBJECT-TYPE
        SYNTAX INTEGER 
        ACCESS read-only
        STATUS mandatory
        DESCRIPTION ""
        ::= { cmefg100Entry 95 }

cmefg100LocOamInformationRx OBJECT-TYPE
        SYNTAX INTEGER 
        ACCESS read-only
        STATUS mandatory
        DESCRIPTION ""
        ::= { cmefg100Entry 96 }

cmefg100LocOamInformationTx OBJECT-TYPE
        SYNTAX INTEGER 
        ACCESS read-only
        STATUS mandatory
        DESCRIPTION ""
        ::= { cmefg100Entry 97 }

cmefg100LocOamLastGasp OBJECT-TYPE
        SYNTAX INTEGER { failure(1), normal(2) }
        ACCESS read-only
        STATUS mandatory
        DESCRIPTION ""
        ::= { cmefg100Entry 98 }

cmefg100LocOamLinkEvents OBJECT-TYPE
        SYNTAX INTEGER { supported(1), notSupported(2) }
        ACCESS read-only
        STATUS mandatory
        DESCRIPTION ""
        ::= { cmefg100Entry 99 }

cmefg100LocOamLinkFault OBJECT-TYPE
        SYNTAX INTEGER { fault(1), normal(2) }
        ACCESS read-only
        STATUS mandatory
        DESCRIPTION ""
        ::= { cmefg100Entry 100 }

cmefg100LocOamLocDteDisc OBJECT-TYPE
        SYNTAX INTEGER { completed(1), notCompleted(2), unsatisfied(3) }
        ACCESS read-only
        STATUS mandatory
        DESCRIPTION "discovery state "
        ::= { cmefg100Entry 101 }

cmefg100LocOamLoopbackControlRx OBJECT-TYPE
        SYNTAX INTEGER 
        ACCESS read-only
        STATUS mandatory
        DESCRIPTION ""
        ::= { cmefg100Entry 102 }

cmefg100LocOamLoopbackControlTx OBJECT-TYPE
        SYNTAX INTEGER 
        ACCESS read-only
        STATUS mandatory
        DESCRIPTION ""
        ::= { cmefg100Entry 103 }

cmefg100LocOamMacAddress OBJECT-TYPE
        SYNTAX MacAddress 
        ACCESS read-only
        STATUS mandatory
        DESCRIPTION "The MAC address of the OAM entity. "
        ::= { cmefg100Entry 104 }

cmefg100LocOamMaxOamPduSize OBJECT-TYPE
        SYNTAX INTEGER 
        ACCESS read-only
        STATUS mandatory
        DESCRIPTION ""
        ::= { cmefg100Entry 105 }

cmefg100LocOamMultiplexorState OBJECT-TYPE
        SYNTAX INTEGER { forwarding(1), discarding(2) }
        ACCESS read-only
        STATUS mandatory
        DESCRIPTION ""
        ::= { cmefg100Entry 106 }

cmefg100LocOamOperStatus OBJECT-TYPE
        SYNTAX INTEGER { linkFault(1), activeSendLocal(2), 
                         passiveWait(3), sendLocalRemote(4), 
                         sendLocalRemoteOk(5), sendAny(6) }
        ACCESS read-only
        STATUS mandatory
        DESCRIPTION ""
        ::= { cmefg100Entry 107 }

cmefg100LocOamOrgSpecificRx OBJECT-TYPE
        SYNTAX INTEGER 
        ACCESS read-only
        STATUS mandatory
        DESCRIPTION ""
        ::= { cmefg100Entry 108 }

cmefg100LocOamOrgSpecificTx OBJECT-TYPE
        SYNTAX INTEGER 
        ACCESS read-only
        STATUS mandatory
        DESCRIPTION ""
        ::= { cmefg100Entry 109 }

cmefg100LocOamParserState OBJECT-TYPE
        SYNTAX INTEGER { forwarding(1), discarding(2), looping(3) }
        ACCESS read-only
        STATUS mandatory
        DESCRIPTION ""
        ::= { cmefg100Entry 110 }

cmefg100LocOamRmtDteDisc OBJECT-TYPE
        SYNTAX INTEGER { completed(1), notCompleted(2), unsatisfied(3) }
        ACCESS read-only
        STATUS mandatory
        DESCRIPTION ""
        ::= { cmefg100Entry 111 }

cmefg100LocOamRmtLoopback OBJECT-TYPE
        SYNTAX INTEGER { supported(1), notSupported(2) }
        ACCESS read-only
        STATUS mandatory
        DESCRIPTION "Indicates whether or not local has support to 
                     allow remote to initiate remote loopback mode. "
        ::= { cmefg100Entry 112 }

cmefg100LocOamUnidirectional OBJECT-TYPE
        SYNTAX INTEGER { supported(1), notSupported(2) }
        ACCESS read-only
        STATUS mandatory
        DESCRIPTION ""
        ::= { cmefg100Entry 113 }

cmefg100LocOamVarRetrieval OBJECT-TYPE
        SYNTAX INTEGER { supported(1), notSupported(2) }
        ACCESS read-only
        STATUS mandatory
        DESCRIPTION ""
        ::= { cmefg100Entry 114 }

cmefg100LocSelfTestFailed OBJECT-TYPE
        SYNTAX INTEGER { yes(1), no(2) }
        ACCESS read-only
        STATUS mandatory
        DESCRIPTION ""
        ::= { cmefg100Entry 115 }

cmefg100LocSerialNumber OBJECT-TYPE
        SYNTAX INTEGER 
        ACCESS read-only
        STATUS mandatory
        DESCRIPTION ""
        ::= { cmefg100Entry 116 }

cmefg100LocTpAdv1000FDX OBJECT-TYPE
        SYNTAX INTEGER { enabled(1), disabled(2), notApplicable(3) }
        ACCESS read-write
        STATUS mandatory
        DESCRIPTION "Read-only value notApplicable returned when 
                     autonegotiation is disabled "
        ::= { cmefg100Entry 117 }

cmefg100LocTpAdv1000HDX OBJECT-TYPE
        SYNTAX INTEGER { enabled(1), disabled(2), notApplicable(3) }
        ACCESS read-write
        STATUS mandatory
        DESCRIPTION "Read-only value notApplicable returned when 
                     autonegotiation is disabled "
        ::= { cmefg100Entry 118 }

cmefg100LocTpAdv100FDX OBJECT-TYPE
        SYNTAX INTEGER { enabled(1), disabled(2), notApplicable(3) }
        ACCESS read-write
        STATUS mandatory
        DESCRIPTION "Read-only value notApplicable returned when 
                     autonegotiation is disabled "
        ::= { cmefg100Entry 119 }

cmefg100LocTpAdv100HDX OBJECT-TYPE
        SYNTAX INTEGER { enabled(1), disabled(2), notApplicable(3) }
        ACCESS read-write
        STATUS mandatory
        DESCRIPTION "Read-only value notApplicable returned when 
                     autonegotiation is disabled "
        ::= { cmefg100Entry 120 }

cmefg100LocTpAdv10FDX OBJECT-TYPE
        SYNTAX INTEGER { enabled(1), disabled(2), notApplicable(3) }
        ACCESS read-write
        STATUS mandatory
        DESCRIPTION "Read-only value notApplicable returned when 
                     autonegotiation is disabled "
        ::= { cmefg100Entry 121 }

cmefg100LocTpAdv10HDX OBJECT-TYPE
        SYNTAX INTEGER { enabled(1), disabled(2), notApplicable(3) }
        ACCESS read-write
        STATUS mandatory
        DESCRIPTION "Read-only value notApplicable returned when 
                     autonegotiation is disabled "
        ::= { cmefg100Entry 122 }

cmefg100LocTpAutoNegot OBJECT-TYPE
        SYNTAX INTEGER { enabled(1), disabled(2) }
        ACCESS read-write
        STATUS mandatory
        DESCRIPTION ""
        ::= { cmefg100Entry 123 }

cmefg100LocTpConnB OBJECT-TYPE
        SYNTAX CpsConnector 
        ACCESS read-only
        STATUS mandatory
        DESCRIPTION ""
        ::= { cmefg100Entry 124 }

cmefg100LocTpCross OBJECT-TYPE
        SYNTAX INTEGER { forceMDI(1), forceMDI-X(2), auto(3) }
        ACCESS read-write
        STATUS mandatory
        DESCRIPTION ""
        ::= { cmefg100Entry 125 }

cmefg100LocTpDuplex OBJECT-TYPE
        SYNTAX INTEGER { forceFDX(1), forceHDX(2), autoFDX(3), 
                         autoHDX(4), negotiating(5) }
        ACCESS read-write
        STATUS mandatory
        DESCRIPTION "Read-only values 3..5 are returned when 
                     autonegotiation is enabled "
        ::= { cmefg100Entry 126 }

cmefg100LocTpLink OBJECT-TYPE
        SYNTAX INTEGER { up(1), down(2) }
        ACCESS read-only
        STATUS mandatory
        DESCRIPTION ""
        ::= { cmefg100Entry 127 }

cmefg100LocTpPause OBJECT-TYPE
        SYNTAX INTEGER { asymmetricRx(1), asymmetricTx(2), symmetric(3), 
                         disabled(4) }
        ACCESS read-write
        STATUS mandatory
        DESCRIPTION ""
        ::= { cmefg100Entry 128 }

cmefg100LocTpQosPause OBJECT-TYPE
        SYNTAX INTEGER { enabled(1), disabled(2) }
        ACCESS read-write
        STATUS mandatory
        DESCRIPTION "QOS: Quality of Service "
        ::= { cmefg100Entry 129 }

cmefg100LocTpSacEnable OBJECT-TYPE
        SYNTAX INTEGER { enabled(1), disabled(2) }
        ACCESS read-write
        STATUS mandatory
        DESCRIPTION "Enable/disable traps for Source Address Change "
        ::= { cmefg100Entry 130 }

cmefg100LocTpSacStatus OBJECT-TYPE
        SYNTAX INTEGER { changed(1), constant(2) }
        ACCESS read-only
        STATUS mandatory
        DESCRIPTION ""
        ::= { cmefg100Entry 131 }

cmefg100LocTpSpeed OBJECT-TYPE
        SYNTAX INTEGER { force10Mbps(1), force100Mbps(2), auto10Mbps(3), 
                         auto100Mbps(4), auto1000Mbps(5), 
                         negotiating(6) }
        ACCESS read-write
        STATUS mandatory
        DESCRIPTION "Read-only values 3..6 are returned when 
                     autonegotiation is enabled "
        ::= { cmefg100Entry 132 }

cmefg100LocTxFxBwaKb OBJECT-TYPE
        SYNTAX INTEGER (1..122112)
        ACCESS read-write
        STATUS mandatory
        DESCRIPTION "TX to FX bandwidth allocation, in Kbps "
        ::= { cmefg100Entry 133 }

cmefg100LocTxFxBwaMb OBJECT-TYPE
        SYNTAX INTEGER (1..1000)
        ACCESS read-write
        STATUS mandatory
        DESCRIPTION "TX to FX bandwidth allocation, in Mbps "
        ::= { cmefg100Entry 134 }

cmefg100LocUptime OBJECT-TYPE
        SYNTAX TimeTicks 
        ACCESS read-write
        STATUS mandatory
        DESCRIPTION "Write with 0 to reset. "
        ::= { cmefg100Entry 135 }

cmefg100QosHqWeight OBJECT-TYPE
        SYNTAX INTEGER (0..15)
        ACCESS read-write
        STATUS mandatory
        DESCRIPTION ""
        ::= { cmefg100Entry 136 }

cmefg100QosLqWeight OBJECT-TYPE
        SYNTAX INTEGER (0..15)
        ACCESS read-write
        STATUS mandatory
        DESCRIPTION ""
        ::= { cmefg100Entry 137 }

cmefg100QosPriority OBJECT-TYPE
        SYNTAX INTEGER (0..7)
        ACCESS read-write
        STATUS mandatory
        DESCRIPTION ""
        ::= { cmefg100Entry 138 }

cmefg100RmtColdStart OBJECT-TYPE
        SYNTAX INTEGER { yes(1), no(2) }
        ACCESS read-only
        STATUS mandatory
        DESCRIPTION ""
        ::= { cmefg100Entry 139 }

cmefg100RmtDetected OBJECT-TYPE
        SYNTAX INTEGER { yes(1), no(2) }
        ACCESS read-only
        STATUS mandatory
        DESCRIPTION ""
        ::= { cmefg100Entry 140 }

cmefg100RmtDmiRxPower OBJECT-TYPE
        SYNTAX INTEGER 
        ACCESS read-only
        STATUS mandatory
        DESCRIPTION ""
        ::= { cmefg100Entry 141 }

cmefg100RmtDmiRxPowerAlarm OBJECT-TYPE
        SYNTAX INTEGER { normal(1), notSupported(2), lowWarn(3), 
                         highWarn(4), lowAlarm(5), highAlarm(6) }
        ACCESS read-only
        STATUS mandatory
        DESCRIPTION ""
        ::= { cmefg100Entry 142 }

cmefg100RmtDmiTemp OBJECT-TYPE
        SYNTAX INTEGER 
        ACCESS read-only
        STATUS mandatory
        DESCRIPTION "In tenths of degrees C "
        ::= { cmefg100Entry 143 }

cmefg100RmtDmiTempAlarm OBJECT-TYPE
        SYNTAX INTEGER { normal(1), notSupported(2), lowWarn(3), 
                         highWarn(4), lowAlarm(5), highAlarm(6) }
        ACCESS read-only
        STATUS mandatory
        DESCRIPTION ""
        ::= { cmefg100Entry 144 }

cmefg100RmtDmiTxBiasAlarm OBJECT-TYPE
        SYNTAX INTEGER { normal(1), notSupported(2), lowWarn(3), 
                         highWarn(4), lowAlarm(5), highAlarm(6) }
        ACCESS read-only
        STATUS mandatory
        DESCRIPTION ""
        ::= { cmefg100Entry 145 }

cmefg100RmtDmiTxBiasCurrent OBJECT-TYPE
        SYNTAX INTEGER 
        ACCESS read-only
        STATUS mandatory
        DESCRIPTION "In microamperes "
        ::= { cmefg100Entry 146 }

cmefg100RmtDmiTxPower OBJECT-TYPE
        SYNTAX INTEGER 
        ACCESS read-only
        STATUS mandatory
        DESCRIPTION "In microwatts "
        ::= { cmefg100Entry 147 }

cmefg100RmtDmiTxPowerAlarm OBJECT-TYPE
        SYNTAX INTEGER { normal(1), notSupported(2), lowWarn(3), 
                         highWarn(4), lowAlarm(5), highAlarm(6) }
        ACCESS read-only
        STATUS mandatory
        DESCRIPTION ""
        ::= { cmefg100Entry 148 }

cmefg100RmtFactoryReset OBJECT-TYPE
        SYNTAX INTEGER { reset(1), doNothing(2) }
        ACCESS read-write
        STATUS mandatory
        DESCRIPTION ""
        ::= { cmefg100Entry 149 }

cmefg100RmtFiberAutoNegot OBJECT-TYPE
        SYNTAX INTEGER { enabled(1), disabled(2) }
        ACCESS read-write
        STATUS mandatory
        DESCRIPTION ""
        ::= { cmefg100Entry 150 }

cmefg100RmtFiberLink OBJECT-TYPE
        SYNTAX INTEGER { up(1), down(2) }
        ACCESS read-only
        STATUS mandatory
        DESCRIPTION ""
        ::= { cmefg100Entry 151 }

cmefg100RmtFiberPause OBJECT-TYPE
        SYNTAX INTEGER { asymmetricRx(1), asymmetricTx(2), symmetric(3), 
                         notSupported(4) }
        ACCESS read-write
        STATUS mandatory
        DESCRIPTION ""
        ::= { cmefg100Entry 152 }

cmefg100RmtFiberQosPause OBJECT-TYPE
        SYNTAX INTEGER { enabled(1), disabled(2) }
        ACCESS read-write
        STATUS mandatory
        DESCRIPTION ""
        ::= { cmefg100Entry 153 }

cmefg100RmtFirmwareRevision OBJECT-TYPE
        SYNTAX INTEGER 
        ACCESS read-only
        STATUS mandatory
        DESCRIPTION ""
        ::= { cmefg100Entry 154 }

cmefg100RmtFpgaRev OBJECT-TYPE
        SYNTAX INTEGER 
        ACCESS read-only
        STATUS mandatory
        DESCRIPTION "Field-Programmable Gate Array revision "
        ::= { cmefg100Entry 155 }

cmefg100RmtOamActiveMode OBJECT-TYPE
        SYNTAX INTEGER { active(1), passive(2) }
        ACCESS read-only
        STATUS mandatory
        DESCRIPTION ""
        ::= { cmefg100Entry 156 }

cmefg100RmtOamCriticalEvent OBJECT-TYPE
        SYNTAX INTEGER { critical(1), normal(2) }
        ACCESS read-only
        STATUS mandatory
        DESCRIPTION ""
        ::= { cmefg100Entry 157 }

cmefg100RmtOamLastGasp OBJECT-TYPE
        SYNTAX INTEGER { failure(1), normal(2) }
        ACCESS read-only
        STATUS mandatory
        DESCRIPTION ""
        ::= { cmefg100Entry 158 }

cmefg100RmtOamLinkEvents OBJECT-TYPE
        SYNTAX INTEGER { supported(1), notSupported(2) }
        ACCESS read-only
        STATUS mandatory
        DESCRIPTION ""
        ::= { cmefg100Entry 159 }

cmefg100RmtOamLinkFault OBJECT-TYPE
        SYNTAX INTEGER { fault(1), normal(2) }
        ACCESS read-only
        STATUS mandatory
        DESCRIPTION ""
        ::= { cmefg100Entry 160 }

cmefg100RmtOamLocDteDisc OBJECT-TYPE
        SYNTAX INTEGER { completed(1), notCompleted(2), unsatisfied(3) }
        ACCESS read-only
        STATUS mandatory
        DESCRIPTION ""
        ::= { cmefg100Entry 161 }

cmefg100RmtOamPeerConfigRevision OBJECT-TYPE
        SYNTAX INTEGER 
        ACCESS read-only
        STATUS mandatory
        DESCRIPTION ""
        ::= { cmefg100Entry 162 }

cmefg100RmtOamPeerMacAddress OBJECT-TYPE
        SYNTAX MacAddress 
        ACCESS read-only
        STATUS mandatory
        DESCRIPTION ""
        ::= { cmefg100Entry 163 }

cmefg100RmtOamPeerMaxOamPduSize OBJECT-TYPE
        SYNTAX INTEGER 
        ACCESS read-only
        STATUS mandatory
        DESCRIPTION ""
        ::= { cmefg100Entry 164 }

cmefg100RmtOamPeerMultiplexorState OBJECT-TYPE
        SYNTAX INTEGER { forwarding(1), discarding(2) }
        ACCESS read-only
        STATUS mandatory
        DESCRIPTION ""
        ::= { cmefg100Entry 165 }

cmefg100RmtOamPeerParserState OBJECT-TYPE
        SYNTAX INTEGER { forwarding(1), discarding(2), looping(3) }
        ACCESS read-only
        STATUS mandatory
        DESCRIPTION ""
        ::= { cmefg100Entry 166 }

cmefg100RmtOamPeerVendorInfo OBJECT-TYPE
        SYNTAX OCTET STRING (SIZE(4))
        ACCESS read-only
        STATUS mandatory
        DESCRIPTION ""
        ::= { cmefg100Entry 167 }

cmefg100RmtOamPeerVendorOui OBJECT-TYPE
        SYNTAX OCTET STRING (SIZE(3))
        ACCESS read-only
        STATUS mandatory
        DESCRIPTION ""
        ::= { cmefg100Entry 168 }

cmefg100RmtOamRmtDteDisc OBJECT-TYPE
        SYNTAX INTEGER { completed(1), notCompleted(2), unsatisfied(3) }
        ACCESS read-only
        STATUS mandatory
        DESCRIPTION ""
        ::= { cmefg100Entry 169 }

cmefg100RmtOamRmtLoopback OBJECT-TYPE
        SYNTAX INTEGER { enabledOam(1), enabledAlternate(2), disabled(3), notSupported(4) }
        ACCESS read-write
        STATUS mandatory
        DESCRIPTION "Initiates remote loopback mode if the remote 
                     supports it. See RmtOamPeerParserState for status 
                     information "
        ::= { cmefg100Entry 170 }
        
cmefg100RmtOamUnidirectional OBJECT-TYPE
        SYNTAX INTEGER { supported(1), notSupported(2) }
        ACCESS read-only
        STATUS mandatory
        DESCRIPTION ""
        ::= { cmefg100Entry 171 }

cmefg100RmtOamVarRetrieval OBJECT-TYPE
        SYNTAX INTEGER { supported(1), notSupported(2) }
        ACCESS read-only
        STATUS mandatory
        DESCRIPTION ""
        ::= { cmefg100Entry 172 }

cmefg100RmtSelfTestFailed OBJECT-TYPE
        SYNTAX INTEGER { yes(1), no(2) }
        ACCESS read-only
        STATUS mandatory
        DESCRIPTION ""
        ::= { cmefg100Entry 173 }

cmefg100RmtSerialNumber OBJECT-TYPE
        SYNTAX INTEGER 
        ACCESS read-only
        STATUS mandatory
        DESCRIPTION ""
        ::= { cmefg100Entry 174 }

cmefg100RmtTpAdv1000FDX OBJECT-TYPE
        SYNTAX INTEGER { enabled(1), disabled(2), notApplicable(3) }
        ACCESS read-write
        STATUS mandatory
        DESCRIPTION "Read-only value notApplicable returned when 
                     autonegotiation is disabled "
        ::= { cmefg100Entry 175 }

cmefg100RmtTpAdv1000HDX OBJECT-TYPE
        SYNTAX INTEGER { enabled(1), disabled(2), notApplicable(3) }
        ACCESS read-write
        STATUS mandatory
        DESCRIPTION "Read-only value notApplicable returned when 
                     autonegotiation is disabled "
        ::= { cmefg100Entry 176 }

cmefg100RmtTpAdv100FDX OBJECT-TYPE
        SYNTAX INTEGER { enabled(1), disabled(2), notApplicable(3) }
        ACCESS read-write
        STATUS mandatory
        DESCRIPTION "Read-only value notApplicable returned when 
                     autonegotiation is disabled "
        ::= { cmefg100Entry 177 }

cmefg100RmtTpAdv100HDX OBJECT-TYPE
        SYNTAX INTEGER { enabled(1), disabled(2), notApplicable(3) }
        ACCESS read-write
        STATUS mandatory
        DESCRIPTION "Read-only value notApplicable returned when 
                     autonegotiation is disabled "
        ::= { cmefg100Entry 178 }

cmefg100RmtTpAdv10FDX OBJECT-TYPE
        SYNTAX INTEGER { enabled(1), disabled(2), notApplicable(3) }
        ACCESS read-write
        STATUS mandatory
        DESCRIPTION "Read-only value notApplicable returned when 
                     autonegotiation is disabled "
        ::= { cmefg100Entry 179 }

cmefg100RmtTpAdv10HDX OBJECT-TYPE
        SYNTAX INTEGER { enabled(1), disabled(2), notApplicable(3) }
        ACCESS read-write
        STATUS mandatory
        DESCRIPTION "Read-only value notApplicable returned when 
                     autonegotiation is disabled "
        ::= { cmefg100Entry 180 }

cmefg100RmtTpAutoNegot OBJECT-TYPE
        SYNTAX INTEGER { enabled(1), disabled(2) }
        ACCESS read-write
        STATUS mandatory
        DESCRIPTION ""
        ::= { cmefg100Entry 181 }

cmefg100RmtTpCross OBJECT-TYPE
        SYNTAX INTEGER { forceMDI(1), forceMDI-X(2), auto(3) }
        ACCESS read-write
        STATUS mandatory
        DESCRIPTION ""
        ::= { cmefg100Entry 182 }

cmefg100RmtTpDuplex OBJECT-TYPE
        SYNTAX INTEGER { forceFDX(1), forceHDX(2), autoFDX(3), 
                         autoHDX(4), negotiating(5) }
        ACCESS read-write
        STATUS mandatory
        DESCRIPTION "Read-only values 3..5 are returned when 
                     autonegotiation is enabled "
        ::= { cmefg100Entry 183 }

cmefg100RmtTpLink OBJECT-TYPE
        SYNTAX INTEGER { up(1), down(2) }
        ACCESS read-only
        STATUS mandatory
        DESCRIPTION ""
        ::= { cmefg100Entry 184 }

cmefg100RmtTpPause OBJECT-TYPE
        SYNTAX INTEGER { asymmetricRx(1), asymmetricTx(2), symmetric(3), 
                         notSupported(4) }
        ACCESS read-write
        STATUS mandatory
        DESCRIPTION ""
        ::= { cmefg100Entry 185 }

cmefg100RmtTpQosPause OBJECT-TYPE
        SYNTAX INTEGER { enabled(1), disabled(2) }
        ACCESS read-write
        STATUS mandatory
        DESCRIPTION ""
        ::= { cmefg100Entry 186 }

cmefg100RmtTpSpeed OBJECT-TYPE
        SYNTAX INTEGER { force10Mbps(1), force100Mbps(2), auto10Mbps(3), 
                         auto100Mbps(4), auto1000Mbps(5), 
                         negotiating(6) }
        ACCESS read-write
        STATUS mandatory
        DESCRIPTION "Read-only values 3..6 are returned when 
                     autonegotiation is enabled "
        ::= { cmefg100Entry 187 }

cmefg100RmtUptime OBJECT-TYPE
        SYNTAX TimeTicks 
        ACCESS read-write
        STATUS mandatory
        DESCRIPTION "Write with 0 to reset. "
        ::= { cmefg100Entry 188 }

cmefg100VlanCacheCmd OBJECT-TYPE
        SYNTAX INTEGER { loadCache(1), doNothing(2), release(3) }
        ACCESS read-write
        STATUS mandatory
        DESCRIPTION "All variables starting with cmefg100Lad relate to 
                     802.1Q VLAN controls. Setting this var to 
                     loadCache commands the agent to upload the VLAN 
                     table from the device exactly one time. Note that 
                     the contents of this cache are NOT automatically 
                     refreshed. A genErr will be returned if any other 
                     command involving reading or writing the LAD or 
                     the VLAN table is in progress. "
        ::= { cmefg100Entry 189 }

cmefg100VlanCacheState OBJECT-TYPE
        SYNTAX INTEGER { ready(1), empty(2), transferring(3), 
                         bufferBusy(4) }
        ACCESS read-write
        STATUS mandatory
        DESCRIPTION "The agent discards the VLAN table shortly after 
                     uploading it to prevent the reporting of outdated 
                     information. This variable shows the current state 
                     of the cache. If it reads 'empty,' set 
                     VlanCacheCmd to loadCache to upload the VLAN 
                     table. "
        ::= { cmefg100Entry 190 }

cmefg100VlanEditCmd OBJECT-TYPE
        SYNTAX INTEGER { write(1), delete(2), doNothing(3) }
        ACCESS read-write
        STATUS mandatory
        DESCRIPTION "Setting this var to write causes VlanEditFwdFiber, 
                     VlanEditFwdTp, VlanEditUntagFiber, 
                     VlanEditUntagTp, and VlanEditVid to be written to 
                     the VLAN tablei (i.e. insert/overwrite). Setting 
                     this var to delete causes the VLAN Id represented 
                     by VlanEditVlanId to be deleted from the VLAN 
                     table. A genErr will be returned if any other 
                     command involving reading or writing the LAD or 
                     the VLAN table is in progress. "
        ::= { cmefg100Entry 191 }

cmefg100VlanEditFwdFiber OBJECT-TYPE
        SYNTAX INTEGER { drop(1), forward(2) }
        ACCESS read-only
        STATUS mandatory
        DESCRIPTION "A fiber egress rule to be acted upon by 
                     VlanEditCmd "
        ::= { cmefg100Entry 192 }

cmefg100VlanEditFwdTp OBJECT-TYPE
        SYNTAX INTEGER { drop(1), forward(2) }
        ACCESS read-only
        STATUS mandatory
        DESCRIPTION "A twisted pair egress rule to be acted upon by 
                     VlanEditCmd "
        ::= { cmefg100Entry 193 }

cmefg100VlanEditUntagFiber OBJECT-TYPE
        SYNTAX INTEGER { untag(1), asIs(2) }
        ACCESS read-only
        STATUS mandatory
        DESCRIPTION "A fiber untag rule to be acted upon by VlanEditCmd "
        ::= { cmefg100Entry 194 }

cmefg100VlanEditUntagTp OBJECT-TYPE
        SYNTAX INTEGER { untag(1), asIs(2) }
        ACCESS read-only
        STATUS mandatory
        DESCRIPTION "A twisted pair untag rule to be acted upon by 
                     VlanEditCmd "
        ::= { cmefg100Entry 195 }

cmefg100VlanEditVid OBJECT-TYPE
        SYNTAX INTEGER 
        ACCESS read-write
        STATUS mandatory
        DESCRIPTION "A VLAN Id to be acted upon by VlanEditCmd "
        ::= { cmefg100Entry 196 }

cmefg100VlanEnable OBJECT-TYPE
        SYNTAX INTEGER { enabled(1), disabled(2) }
        ACCESS read-write
        STATUS mandatory
        DESCRIPTION "Enable/disable for 802.1Q VLAN tag processing. "
        ::= { cmefg100Entry 197 }

cmefg100VlanEntries OBJECT-TYPE
        SYNTAX INTEGER 
        ACCESS read-only
        STATUS mandatory
        DESCRIPTION "A count of the number of entries currently in the 
                     VLAN table cache. See also VlanCacheState. If a 
                     VLAN cache-filling transfer is in progress, this 
                     variable can be read for a progress report. "
        ::= { cmefg100Entry 198 }

cmefg100VlanFiberDefaultPri OBJECT-TYPE
        SYNTAX INTEGER (0..7)
        ACCESS read-write
        STATUS mandatory
        DESCRIPTION ""
        ::= { cmefg100Entry 199 }

cmefg100VlanFiberDefaultVid OBJECT-TYPE
        SYNTAX INTEGER (0..4095)
        ACCESS read-write
        STATUS mandatory
        DESCRIPTION ""
        ::= { cmefg100Entry 200 }

cmefg100VlanFiberInUntaggedDrop OBJECT-TYPE
        SYNTAX INTEGER { drop(1), forward(2), notApplicable(3) }
        ACCESS read-write
        STATUS mandatory
        DESCRIPTION ""
        ::= { cmefg100Entry 201 }

cmefg100VlanFwdFiberTbl OBJECT-TYPE
        SYNTAX INTEGER { drop(1), forward(2) }
        ACCESS read-only
        STATUS mandatory
        DESCRIPTION "Indicates whether packets with the VLAN Id 
                     specified by the corresponding cmefg100VlanVidTbl 
                     entry (i.e. the one with the same SubDeviceIndex) 
                     are forwarded or dropped when they are routed for 
                     fiber egress. The SubDeviceIndex is an arbitrary 
                     integer sequence number, range 
                     1..cmefg100VlanEntries. "
        ::= { cmefg100Entry 202 }

cmefg100VlanFwdTpTbl OBJECT-TYPE
        SYNTAX INTEGER { drop(1), forward(2) }
        ACCESS read-only
        STATUS mandatory
        DESCRIPTION "Indicates whether packets with the VLAN Id 
                     specified by the corresponding cmefg100VlanVidTbl 
                     entry (i.e. the one with the same SubDeviceIndex) 
                     are forwarded or dropped when they are routed for 
                     twisted pair egress. The SubDeviceIndex is an 
                     arbitrary integer sequence number, range 
                     1..cmefg100VlanEntries. "
        ::= { cmefg100Entry 203 }

cmefg100VlanIngressVidHitNoMem OBJECT-TYPE
        SYNTAX INTEGER { forward(1), drop(2), learn(3) }
        ACCESS read-write
        STATUS mandatory
        DESCRIPTION "Ingress violation - port from which frame 
                     originates is not a member of the VLAN indicated 
                     by the frame's tag "
        ::= { cmefg100Entry 204 }

cmefg100VlanIngressVidMiss OBJECT-TYPE
        SYNTAX INTEGER { flood(1), drop(2) }
        ACCESS read-write
        STATUS mandatory
        DESCRIPTION "Ingress violation - the VLAN indicated by the 
                     frame's tag is undefined in the VLAN table. "
        ::= { cmefg100Entry 205 }

cmefg100VlanPriMapTbl OBJECT-TYPE
        SYNTAX INTEGER (0..7)
        ACCESS read-write
        STATUS mandatory
        DESCRIPTION "A table containing new priority values for 
                     priority remapping. The SubDeviceIndex is 
                     'original priority', range 0..7. "
        ::= { cmefg100Entry 206 }

cmefg100VlanPriTagCtrl OBJECT-TYPE
        SYNTAX INTEGER { asIs(1), remapPriority(2), remapVid(3), 
                         remapBoth(4), notApplicable(5) }
        ACCESS read-write
        STATUS mandatory
        DESCRIPTION ""
        ::= { cmefg100Entry 207 }

cmefg100VlanSetFailed OBJECT-TYPE
        SYNTAX INTEGER { yes(1), no(2) }
        ACCESS read-only
        STATUS mandatory
        DESCRIPTION ""
        ::= { cmefg100Entry 208 }

cmefg100VlanTagIn OBJECT-TYPE
        SYNTAX INTEGER { tag(1), noTag(2), notApplicable(3) }
        ACCESS read-write
        STATUS mandatory
        DESCRIPTION ""
        ::= { cmefg100Entry 209 }

cmefg100VlanTpDefaultPri OBJECT-TYPE
        SYNTAX INTEGER (0..7)
        ACCESS read-write
        STATUS mandatory
        DESCRIPTION ""
        ::= { cmefg100Entry 210 }

cmefg100VlanTpDefaultVid OBJECT-TYPE
        SYNTAX INTEGER (0..4095)
        ACCESS read-write
        STATUS mandatory
        DESCRIPTION ""
        ::= { cmefg100Entry 211 }

cmefg100VlanTpInUntaggedDrop OBJECT-TYPE
        SYNTAX INTEGER { drop(1), forward(2) }
        ACCESS read-write
        STATUS mandatory
        DESCRIPTION ""
        ::= { cmefg100Entry 212 }

cmefg100VlanUntagFiberTbl OBJECT-TYPE
        SYNTAX INTEGER { untag(1), asIs(2) }
        ACCESS read-only
        STATUS mandatory
        DESCRIPTION "Indicates whether VLAN Ids are stripped from 
                     packets with the VLAN Id specified by the 
                     corresponding cmefg100VlanVidTbl entry (i.e. the 
                     one with the same SubDeviceIndex) when they are 
                     routed for fiber egress. The SubDeviceIndex is an 
                     arbitrary integer sequence number, range 
                     1..cmefg100VlanEntries. "
        ::= { cmefg100Entry 213 }

cmefg100VlanUntagTpTbl OBJECT-TYPE
        SYNTAX INTEGER { untag(1), asIs(2) }
        ACCESS read-only
        STATUS mandatory
        DESCRIPTION "Indicates whether VLAN Ids are stripped from 
                     packets with the VLAN Id specified by the 
                     corresponding cmefg100VlanVidTbl entry (i.e. the 
                     one with the same SubDeviceIndex) when they are 
                     routed for twisted pair egress. The SubDeviceIndex 
                     is an arbitrary integer sequence number, range 
                     1..cmefg100VlanEntries. "
        ::= { cmefg100Entry 214 }

cmefg100VlanVidTagCtrl OBJECT-TYPE
        SYNTAX INTEGER { asIs(1), remapPriority(2), remapVid(3), 
                         remapBoth(4), notApplicable(5) }
        ACCESS read-write
        STATUS mandatory
        DESCRIPTION ""
        ::= { cmefg100Entry 215 }

cmefg100VlanVidTbl OBJECT-TYPE
        SYNTAX INTEGER 
        ACCESS read-only
        STATUS mandatory
        DESCRIPTION "The SubDeviceIndex is an arbitrary integer 
                     sequence number, range 1..cmefg100VlanEntries. "
        ::= { cmefg100Entry 216 }

cmefg100CacheClean OBJECT-TYPE
        SYNTAX INTEGER 
        ACCESS read-write
        STATUS mandatory
        DESCRIPTION "And all of the MIB variables lived happily ever 
                     after. The End. "
        ::= { cmefg100Entry 217 }




-- ==================================================================
--  MCC-16 MEDIA CONVERTER CHASSIS, a chassis containing 16 mc20p
--  (20 pin media converter) slots.
--
mcc16ComHwReset OBJECT-TYPE 
     SYNTAX INTEGER { noReset(1), reset(2) } 
     ACCESS read-write 
     STATUS mandatory 
     DESCRIPTION "Save configuration to FLASH and perform a hardware reset"
     ::= { mcc16Common 1 } 

mcc16ComMgmtHwRev OBJECT-TYPE 
        SYNTAX  DisplayString (SIZE (0..255)) 
        ACCESS  read-only 
        STATUS  mandatory 
        DESCRIPTION "The management h/w board revision." 
        ::= { mcc16Common 2 } 

mcc16ComMgmtSwRev OBJECT-TYPE 
        SYNTAX  DisplayString (SIZE (0..255)) 
        ACCESS  read-only 
        STATUS  mandatory 
        DESCRIPTION "The downloadable management s/w code revision." 
        ::= { mcc16Common 3 } 

mcc16ComIpAddr OBJECT-TYPE 
        SYNTAX  IpAddress 
        ACCESS  read-write 
        STATUS  mandatory 
        DESCRIPTION "The IP address of the management interface."  
        ::= { mcc16Common 4 } 

mcc16ComNetMask OBJECT-TYPE 
        SYNTAX  IpAddress 
        ACCESS  read-write 
        STATUS  mandatory 
        DESCRIPTION "The subnet mask associated with the IP address of the
                    management interface.  The value of the mask is an IP
                    address with all the network bits set to 1 and all
                    the hosts bits set to 0."  
        ::= { mcc16Common 5 }  

mcc16ComGateway OBJECT-TYPE 
        SYNTAX  IpAddress 
        ACCESS  read-write 
        STATUS  mandatory 
        DESCRIPTION "The managment interface's default gateway."  
        ::= { mcc16Common 6 }  

mcc16ComPS1Power OBJECT-TYPE
        SYNTAX INTEGER { on(1), off(2) }
        ACCESS read-only
        STATUS mandatory
        DESCRIPTION "On if power supply 1 is installed and powered"
        ::= { mcc16Common 7 }

mcc16ComPS1InUse OBJECT-TYPE
        SYNTAX INTEGER { on(1), off(2) }
        ACCESS read-only
        STATUS mandatory
        DESCRIPTION "On if power supply 1 is currently active"
        ::= { mcc16Common 8 }

mcc16ComPS2Power OBJECT-TYPE
        SYNTAX INTEGER { on(1), off(2) }
        ACCESS read-only
        STATUS mandatory
        DESCRIPTION "On if power supply 2 is installed and powered"
        ::= { mcc16Common 9 }

mcc16ComPS2InUse OBJECT-TYPE
        SYNTAX INTEGER { on(1), off(2) }
        ACCESS read-only
        STATUS mandatory
        DESCRIPTION "On if power supply 2 is currently active"
        ::= { mcc16Common 10 }

mcc16ComNotes OBJECT-TYPE
        SYNTAX  DisplayString (SIZE (0..4096)) 
        ACCESS  read-write
        STATUS  mandatory 
        DESCRIPTION "Enduser-defined text notes"
        ::= { mcc16Common 11 } 

-- ===========================================================================
--
-- NOTE: The following datums have been deliberately omitted from this MIB:
--    MCC16 MANAGEMENT MODULE POWER 
--    MCC16 MANAGEMENT MODULE ETHERNET LINK 
--    MCC16 MANAGEMENT MODULE ETHERNET TRANSMIT 
--    MCC16 MANAGEMENT MODULE ETHERNET RECEIVE 
-- This is due to the fact that if you receive any response at all from the
-- management module, you may safely assume that all four of these items are
-- 'on.' Any time one or more of these four conditions fails, the management 
-- module is obviously unable to report this fact to the NMS. Therefore, if 
-- these items *were* supported, they would *always* read 'on.'
--
-- ===========================================================================

--  The slot table contains one entry per slot. Each entry contains OID of
--  the device that is contained in the slot.
mcc16SlotTable OBJECT-TYPE 
        SYNTAX SEQUENCE OF Mcc16SlotEntry
        ACCESS not-accessible
        STATUS mandatory
        DESCRIPTION "One table entry per slot in the media converter chassis.
                     Value of entry is type of device in the slot, or a value
                     indicating that the slot is empty."
        ::= { mcc16Ver1 1 }

mcc16SlotEntry OBJECT-TYPE 
        SYNTAX Mcc16SlotEntry
        ACCESS not-accessible
        STATUS mandatory
        DESCRIPTION "The type of device inserted in a single chassis slot"
        INDEX { mcc16Index }
        ::= { mcc16SlotTable 1 }

Mcc16SlotEntry ::= 
        SEQUENCE {
                mcc16Index INTEGER,
                mcc16DeviceType OBJECT IDENTIFIER
                }

mcc16Index OBJECT-TYPE 
        SYNTAX INTEGER (1..16)
        ACCESS read-only
        STATUS mandatory
        DESCRIPTION "The index of a slot in a media converter chassis"
        ::= { mcc16SlotEntry 1 }

mcc16DeviceType OBJECT-TYPE 
        SYNTAX OBJECT IDENTIFIER
        ACCESS read-only
        STATUS mandatory
        DESCRIPTION "The object ID of the device in the a slot"
        ::= { mcc16SlotEntry 2 }

--
-- MCC-16 specific traps. 
--
mcc16Error TRAP-TYPE
        ENTERPRISE chassisMcc16Id
        DESCRIPTION
                "A monitored MIB variable has changed from its 'operational'
                 state to 'not present' or its 'error' state."
        ::= 101

mcc16ErrorClear TRAP-TYPE
        ENTERPRISE chassisMcc16Id
        DESCRIPTION
                "A monitored MIB variable has changed from a 'not present' 
                 or 'error' state to its 'operational' state."
        ::= 102

mcc16PSState TRAP-TYPE
        ENTERPRISE chassisMcc16Id
        DESCRIPTION
                "The power indication on a power supply has changed, or a
                 power supply was non-operational at the time of a warm start."
        ::= 103

--
-- Point System specific traps. 
--
pSError TRAP-TYPE
        ENTERPRISE cpsmM100Id
        DESCRIPTION
                "A monitored MIB variable has changed from its 'operational'
                 state to its 'error' state."
        ::= 111

pSErrorClear TRAP-TYPE
        ENTERPRISE cpsmM100Id
        DESCRIPTION
                "A monitored MIB variable has changed from its 'error'
                 state to its 'operational' state."
        ::= 112

pSDeviceInserted TRAP-TYPE
        ENTERPRISE cpsmM100Id
        DESCRIPTION
                "A new slide-in device (this includes some power supplies) 
                 was detected on the bus."
        ::= 113

pSDeviceRemoved TRAP-TYPE
        ENTERPRISE cpsmM100Id
        DESCRIPTION
                "A slide-in device that had previously been detected on
                 the bus has not been heard from in a long time, and 
                 is presumed to have been physically removed."
        ::= 114

pSDeviceColdStart TRAP-TYPE
        ENTERPRISE cpsmM100Id
        DESCRIPTION
                "A slide-in device has indicated that it has rebooted.
                 This is most common when the device is inserted into
                 its slot, but in a few cases this trap indicates a
                 warm start."
        ::= 115

pSPowerLost TRAP-TYPE
        ENTERPRISE cpsmM100Id
        DESCRIPTION
                "The cabinet into which this management module is 
                 installed has lost power. Both the cabinet and the
                 management module must support this feature for
                 this trap to be sent."
        ::= 116

pSCabinetAdded TRAP-TYPE
        ENTERPRISE cpsmM100Id
        DESCRIPTION
                "A new cabinet was detected on the bus."
        ::= 117

pSCabinetRemoved TRAP-TYPE
        ENTERPRISE cpsmM100Id
        DESCRIPTION
                "A cabinet that had previously been detected on
                 the bus has not been heard from in a long time, and 
                 is presumed to have been physically removed."
        ::= 118


-- ================================================================
--  Table of Cabinets in a Point System stack.

cpsCabinetTable OBJECT-TYPE
        SYNTAX SEQUENCE OF CpsCabinetEntry
        ACCESS not-accessible
        STATUS mandatory
        DESCRIPTION "Sparse table containing one entry for each Cabinet
                     in the stack, indexed by cabinet serial number."
        ::= { cpsCabSummary 1 }

cpsCabinetEntry OBJECT-TYPE
        SYNTAX CpsCabinetEntry
        ACCESS not-accessible
        STATUS mandatory
        DESCRIPTION "Status and Configuration entries for a single Cabinet."
        INDEX { cpsCabinetBiaIndex }
        ::= { cpsCabinetTable 1 }

CpsCabinetEntry ::= 
        SEQUENCE {
                cpsCabinetBiaIndex     INTEGER,
                cpsCabinetModel        OBJECT IDENTIFIER,
                cpsCabinetDescription  DisplayString,
                cpsCabinetSequence     INTEGER
                 }

cpsCabinetBiaIndex OBJECT-TYPE 
        SYNTAX INTEGER
        ACCESS read-only
        STATUS mandatory
        DESCRIPTION "The serial number (BIA) of the Cabinet"
        ::= { cpsCabinetEntry 1 }

cpsCabinetModel OBJECT-TYPE 
        SYNTAX OBJECT IDENTIFIER
        ACCESS read-only
        STATUS mandatory
        DESCRIPTION "The model number of the cabinet"
        ::= { cpsCabinetEntry 2 }

cpsCabinetDescription OBJECT-TYPE 
        SYNTAX DisplayString
        ACCESS read-write
        STATUS mandatory
        DESCRIPTION "User defined text description of the cabinet.
                     This description is a mirror of the ones that can
                     be found under cpsCabDetail."
        ::= { cpsCabinetEntry 3 }

cpsCabinetSequence OBJECT-TYPE 
        SYNTAX INTEGER
        ACCESS read-only
        STATUS mandatory
        DESCRIPTION "An arbitrary sequence number assigned to the cabinet
                     by the agent for the use of the Focal Point application.
                     Cabinets are sorted by BiaIndex in the table, and
                     numbered sequentially."
        ::= { cpsCabinetEntry 4 }


-- ================================================================
--  Cabinet detail table for CPSMC1800 18 slot Point System cabinet

cpsMc1800Table OBJECT-TYPE
        SYNTAX SEQUENCE OF CpsMc1800Entry
        ACCESS not-accessible
        STATUS mandatory
        DESCRIPTION "Sparse table containing one entry for each CPSMC1800
                     in the stack, indexed by cabinet serial number."
        ::= { cpsCabDetail 1 }

cpsMc1800Entry OBJECT-TYPE
        SYNTAX CpsMc1800Entry
        ACCESS not-accessible
        STATUS mandatory
        DESCRIPTION "Status and configuration entries for a single CPSMC1800"
        INDEX { cpsMc1800BiaIndex }
	  ::= { cpsMc1800Table 1 }

CpsMc1800Entry ::= 
        SEQUENCE {
                cpsMc1800BiaIndex     INTEGER,
                cpsMc1800Description  DisplayString,
                cpsMc1800PSPower1     INTEGER,
                cpsMc1800PSInUse1     INTEGER,
                cpsMc1800PSPower2     INTEGER,
                cpsMc1800PSInUse2     INTEGER,
                cpsMc1800MRevision    INTEGER
                 }


cpsMc1800BiaIndex OBJECT-TYPE 
        SYNTAX INTEGER
        ACCESS read-only
        STATUS mandatory
        DESCRIPTION "The serial number (BIA) of the cabinet"
        ::= { cpsMc1800Entry 1 }

cpsMc1800Description OBJECT-TYPE 
        SYNTAX DisplayString
        ACCESS read-only
        STATUS mandatory
        DESCRIPTION "User defined text description of the cabinet.
                     A mirror of cpsCabinetDescription."
        ::= { cpsMc1800Entry 2 }

cpsMc1800PSPower1 OBJECT-TYPE 
        SYNTAX INTEGER { on(1), off(2) }
        ACCESS read-only
        STATUS mandatory
        DESCRIPTION "Power status, first power supply slot. Value is
                     on(1) when the supply is capable of supplying power."
        ::= { cpsMc1800Entry 3 }

cpsMc1800PSInUse1 OBJECT-TYPE 
        SYNTAX INTEGER { yes(1), no(2) }
        ACCESS read-only
        STATUS mandatory
        DESCRIPTION "Power status, first power supply slot. Value is yes(1)
                     when the power is selected to supply power to the cabinet"
        ::= { cpsMc1800Entry 4 }

cpsMc1800PSPower2 OBJECT-TYPE 
        SYNTAX INTEGER { yes(1), no(2) }
        ACCESS read-only
        STATUS mandatory
        DESCRIPTION "Power status, second power supply slot. Value is
                     on(1) when the supply is capable of supplying power."
        ::= { cpsMc1800Entry 5 }

cpsMc1800PSInUse2 OBJECT-TYPE 
        SYNTAX INTEGER { yes(1), no(2) }
        ACCESS read-only
        STATUS mandatory
        DESCRIPTION "Power status, second power supply slot. Value is yes(1)
                     when the power is selected to supply power to the cabinet"
        ::= { cpsMc1800Entry 6 }

cpsMc1800MRevision OBJECT-TYPE 
        SYNTAX INTEGER
        ACCESS read-only
        STATUS mandatory
        DESCRIPTION "The marketing revision of this device"
        ::= { cpsMc1800Entry 7 }

-- ================================================================
--  Cabinet detail table for CPSMC1300 13 slot Point System cabinet

cpsMc1300Table OBJECT-TYPE
        SYNTAX SEQUENCE OF CpsMc1300Entry
        ACCESS not-accessible
        STATUS mandatory
        DESCRIPTION "Sparse table containing one entry for each CPSMC1300
                     in the stack, indexed by cabinet serial number."
        ::= { cpsCabDetail 2 }

cpsMc1300Entry OBJECT-TYPE
        SYNTAX CpsMc1300Entry
        ACCESS not-accessible
        STATUS mandatory
        DESCRIPTION "Status and configuration entries for a single CPSMC1300"
        INDEX { cpsMc1300BiaIndex }
	  ::= { cpsMc1300Table 1 }

CpsMc1300Entry ::= 
        SEQUENCE {
                cpsMc1300BiaIndex     INTEGER,
                cpsMc1300Description  DisplayString,
                cpsMc1300PSPower1     INTEGER,
                cpsMc1300PSInUse1     INTEGER,
                cpsMc1300PSPower2     INTEGER,
                cpsMc1300PSInUse2     INTEGER,
                cpsMc1300MRevision    INTEGER
                 }


cpsMc1300BiaIndex OBJECT-TYPE 
        SYNTAX INTEGER
        ACCESS read-only
        STATUS mandatory
        DESCRIPTION "The serial number (BIA) of the cabinet"
        ::= { cpsMc1300Entry 1 }

cpsMc1300Description OBJECT-TYPE 
        SYNTAX DisplayString
        ACCESS read-only
        STATUS mandatory
        DESCRIPTION "User defined text description of the cabinet.
                     A mirror of cpsCabinetDescription."
        ::= { cpsMc1300Entry 2 }

cpsMc1300PSPower1 OBJECT-TYPE 
        SYNTAX INTEGER { on(1), off(2) }
        ACCESS read-only
        STATUS mandatory
        DESCRIPTION "Power status, first power supply slot. Value is
                     on(1) when the supply is capable of supplying power."
        ::= { cpsMc1300Entry 3 }

cpsMc1300PSInUse1 OBJECT-TYPE 
        SYNTAX INTEGER { yes(1), no(2) }
        ACCESS read-only
        STATUS mandatory
        DESCRIPTION "For future expansion. At the time of this writing,
                     the CPSMC1300 did not accept any power supplies 
                     capable of supporting a master/slave relationship,
                     meaning that all 'ready' power supplies share load
                     and therefore are 'in use'. If master/slave support
                     were present, inuse would indicate whether or not this
                     supply was currently supplying power to the cabinet."
        ::= { cpsMc1300Entry 4 }

cpsMc1300PSPower2 OBJECT-TYPE 
        SYNTAX INTEGER { yes(1), no(2) }
        ACCESS read-only
        STATUS mandatory
        DESCRIPTION "Power status, second power supply slot. Value is
                     on(1) when the supply is capable of supplying power."
        ::= { cpsMc1300Entry 5 }

cpsMc1300PSInUse2 OBJECT-TYPE 
        SYNTAX INTEGER { yes(1), no(2) }
        ACCESS read-only
        STATUS mandatory
        DESCRIPTION "For future expansion. At the time of this writing,
                     the CPSMC1300 did not accept any power supplies 
                     capable of supporting a master/slave relationship,
                     meaning that all 'ready' power supplies share load
                     and therefore are 'in use'. If master/slave support
                     were present, inuse would indicate whether or not this
                     supply was currently supplying power to the cabinet."
        ::= { cpsMc1300Entry 6 }

cpsMc1300MRevision OBJECT-TYPE 
        SYNTAX INTEGER
        ACCESS read-only
        STATUS mandatory
        DESCRIPTION "The marketing revision of this device"
        ::= { cpsMc1300Entry 7 }

-- ================================================================
--  Cabinet detail table for CPSMC0200 2 slot Point System cabinet

cpsMc0200Table OBJECT-TYPE
        SYNTAX SEQUENCE OF CpsMc0200Entry
        ACCESS not-accessible
        STATUS mandatory
        DESCRIPTION "Sparse table containing one entry for each CPSMC0200
                     in the stack, indexed by cabinet serial number."
        ::= { cpsCabDetail 3 }

cpsMc0200Entry OBJECT-TYPE
        SYNTAX CpsMc0200Entry
        ACCESS not-accessible
        STATUS mandatory
        DESCRIPTION "Status and configuration entries for a single CPSMC0200"
        INDEX { cpsMc0200BiaIndex }
	  ::= { cpsMc0200Table 1 }

CpsMc0200Entry ::= 
        SEQUENCE {
                cpsMc0200BiaIndex     INTEGER,
                cpsMc0200Description  DisplayString,
                cpsMc0200MRevision    INTEGER
                 }

cpsMc0200BiaIndex OBJECT-TYPE 
        SYNTAX INTEGER
        ACCESS read-only
        STATUS mandatory
        DESCRIPTION "The serial number (BIA) of the cabinet"
        ::= { cpsMc0200Entry 1 }

cpsMc0200Description OBJECT-TYPE 
        SYNTAX DisplayString
        ACCESS read-only
        STATUS mandatory
        DESCRIPTION "User defined text description of the cabinet.
                     A mirror of cpsCabinetDescription."
        ::= { cpsMc0200Entry 2 }


cpsMc0200MRevision OBJECT-TYPE 
        SYNTAX INTEGER
        ACCESS read-only
        STATUS mandatory
        DESCRIPTION "The marketing revision of this device"
        ::= { cpsMc0200Entry 3 }


-- ================================================================
--  Cabinet detail table for CPSMC1900 19 slot Point System cabinet

cpsMc1900Table OBJECT-TYPE
        SYNTAX SEQUENCE OF CpsMc1900Entry
        ACCESS not-accessible
        STATUS mandatory
        DESCRIPTION "Sparse table containing one entry for each CPSMC1900
                     in the stack, indexed by cabinet serial number."
        ::= { cpsCabDetail 4 }

cpsMc1900Entry OBJECT-TYPE
        SYNTAX CpsMc1900Entry
        ACCESS not-accessible
        STATUS mandatory
        DESCRIPTION "Status and configuration entries for a single CPSMC1900"
        INDEX { cpsMc1900BiaIndex }
	  ::= { cpsMc1900Table 1 }

CpsMc1900Entry ::= 
        SEQUENCE {
                cpsMc1900BiaIndex     INTEGER,
                cpsMc1900Description  DisplayString,
                cpsMc1900MRevision    INTEGER
                 }


cpsMc1900BiaIndex OBJECT-TYPE 
        SYNTAX INTEGER
        ACCESS read-only
        STATUS mandatory
        DESCRIPTION "The serial number (BIA) of the cabinet"
        ::= { cpsMc1900Entry 1 }

cpsMc1900Description OBJECT-TYPE 
        SYNTAX DisplayString
        ACCESS read-only
        STATUS mandatory
        DESCRIPTION "User defined text description of the cabinet.
                     A mirror of cpsCabinetDescription."
        ::= { cpsMc1900Entry 2 }

cpsMc1900MRevision OBJECT-TYPE 
        SYNTAX INTEGER
        ACCESS read-only
        STATUS mandatory
        DESCRIPTION "The marketing revision of this device"
        ::= { cpsMc1900Entry 3 }

-- ================================================================
--  Cabinet detail table for CPSMC0200 2 slot Point System cabinet

smacf100Table OBJECT-TYPE
        SYNTAX SEQUENCE OF Smacf100Entry
        ACCESS not-accessible
        STATUS mandatory
        DESCRIPTION "Sparse table containing one entry for each SMACF100
                     in the stack, indexed by cabinet serial number."
        ::= { cpsCabDetail 5}

smacf100Entry OBJECT-TYPE
        SYNTAX Smacf100Entry
        ACCESS not-accessible
        STATUS mandatory
        DESCRIPTION "Status and configuration entries for a single SMACF100"
        INDEX { smacf100BiaIndex }
	  ::= { smacf100Table 1 }

Smacf100Entry  ::= 
        SEQUENCE {
                smacf100BiaIndex                INTEGER,
                smacf100Description             DisplayString,
                smacf100MRevision               INTEGER,
                smacf100SpanningTree            INTEGER,
                smacf100ResetCounters           INTEGER,
                smacf100SelfTest                INTEGER,
                smacf100QosEnable               INTEGER,
                smacf100QosHPThreshold          INTEGER,
                smacf100QosLqWeight             INTEGER,
                smacf100QosHqWeight             INTEGER,
                smacf100SNMPModuleInstalled     INTEGER,
                smacf100AgingTimer              INTEGER
                }

smacf100BiaIndex OBJECT-TYPE 
        SYNTAX INTEGER
        ACCESS read-only
        STATUS mandatory
        DESCRIPTION "The serial number (BIA) of the cabinet"
        ::= { smacf100Entry 1 }

smacf100Description OBJECT-TYPE 
        SYNTAX DisplayString
        ACCESS read-only
        STATUS mandatory
        DESCRIPTION "User defined text description of the cabinet.
                     A mirror of cpsCabinetDescription."
        ::= { smacf100Entry 2 }

smacf100MRevision OBJECT-TYPE 
        SYNTAX INTEGER
        ACCESS read-only
        STATUS mandatory
        DESCRIPTION "The marketing revision of this device"
        ::= { smacf100Entry 3 }

smacf100SpanningTree OBJECT-TYPE 
        SYNTAX INTEGER { enabled(1), disabled(2), notSupported(3) }
        ACCESS read-write
        STATUS mandatory
        DESCRIPTION "This variable allows the agent to enable or disable 
                     Spanning Tree if it is supported. Not all versions 
                     of the hardware support Spanning Tree."
        ::= { smacf100Entry 4 }

smacf100ResetCounters OBJECT-TYPE 
        SYNTAX INTEGER { reset(1), doNothing(2) }
        ACCESS read-write
        STATUS mandatory
        DESCRIPTION "When this variable is set to reset(1), all counters
                     for all ports are reset to zero."
        ::= { smacf100Entry 5 }

smacf100SelfTest OBJECT-TYPE 
        SYNTAX INTEGER { selfTest(1), doNothing(2) }
        ACCESS read-write
        STATUS mandatory
        DESCRIPTION "When this variable is set to selfTest(1), the cabinet
                     will perform a self test."
        ::= { smacf100Entry 6 }

smacf100QosEnable OBJECT-TYPE 
        SYNTAX INTEGER { enabled(1), disabled(2), notSupported(3) }
        ACCESS read-write
        STATUS mandatory
        DESCRIPTION "This variable allows Quality of Service functions
                     to be enabled or disabled. This includes the
                     processing of 802.1p tags 
                     (See smacf100QosHPThreshold(8), smacf100QosLqWeight(9),
                     and smacf100QosHqWeight(10)), half-duplex back pressure
                     and full-duplex flow control. (See
                     smacf100PQosPause(63)). Port priority functionality
                     (smacf100PQosPriority(62)) is always enabled."
        ::= { smacf100Entry 7 }

smacf100QosHPThreshold OBJECT-TYPE 
        SYNTAX INTEGER
        ACCESS read-write
        STATUS mandatory
        DESCRIPTION "When an incoming 802.1p priority tag value is greater
                     than or equal to this value (from 0 to 7), the incoming
                     packet will be classified as high-priority. Ignored
                     when smacf100QosEnable(7) is set to 'disabled(2)'."
        ::= { smacf100Entry 8 }

smacf100QosLqWeight OBJECT-TYPE 
        SYNTAX INTEGER
        ACCESS read-write
        STATUS mandatory
        DESCRIPTION "A value between 1 and 15 indicating the number of
                     packets that should be processed from the low-priority
                     queue before attention is turned to the high-priority
                     queue. Ignored when smacf100QosEnable(7) is set to
                     'disabled(2)'."
        ::= { smacf100Entry 9 }

smacf100QosHqWeight OBJECT-TYPE 
        SYNTAX INTEGER 
        ACCESS read-write
        STATUS mandatory
        DESCRIPTION "A value between 1 and 15 indicating the number of
                     packets that should be processed from the high-priority
                     queue before attention is turned to the low-priority
                     queue. Ignored when smacf100QosEnable(7) is set to 
                     'disabled(2)'."
        ::= { smacf100Entry 10 }

smacf100SNMPModuleInstalled OBJECT-TYPE 
        SYNTAX INTEGER { yes(1), no(2) }
        ACCESS read-only
        STATUS mandatory
        DESCRIPTION "When this variable is set to yes(1), a management 
                     module is installed in this particular SMACF100 cabinet."
        ::= { smacf100Entry 11 }

smacf100AgingTimer OBJECT-TYPE 
        SYNTAX INTEGER 
        ACCESS read-write
        STATUS mandatory
        DESCRIPTION "This configuration varible allows the MAC address aging
                     timer to be adjusted. When an automatically discovered
                     MAC address has not been heard from (i.e. no packets with
                     this source address have been received) for longer than
                     the time specified by this variable, it is deleted from 
                     the SMACF100's address cache. The time is specified in 
                     seconds (up to 1,048,575). If smacf100AgingTimer(12) is
                     set to 0, MAC address aging is disabled."
        ::= { smacf100Entry 12 }

-- ================================================================
--  Cabinet detail table for CPSMC0800 8 slot Point System cabinet

cpsMc0800Table OBJECT-TYPE
        SYNTAX SEQUENCE OF CpsMc0800Entry
        ACCESS not-accessible
        STATUS mandatory
        DESCRIPTION "Sparse table containing one entry for each CPSMC0800
                     in the stack, indexed by cabinet serial number."
        ::= { cpsCabDetail 6 }

cpsMc0800Entry OBJECT-TYPE
        SYNTAX CpsMc0800Entry
        ACCESS not-accessible
        STATUS mandatory
        DESCRIPTION "Status and configuration entries for a single CPSMC0800"
        INDEX { cpsMc0800BiaIndex }
	  ::= { cpsMc0800Table 1 }

CpsMc0800Entry ::= 
        SEQUENCE {
                cpsMc0800BiaIndex     INTEGER,
                cpsMc0800Description  DisplayString,
                cpsMc0800MRevision    INTEGER
                 }


cpsMc0800BiaIndex OBJECT-TYPE 
        SYNTAX INTEGER
        ACCESS read-only
        STATUS mandatory
        DESCRIPTION "The serial number (BIA) of the cabinet"
        ::= { cpsMc0800Entry 1 }

cpsMc0800Description OBJECT-TYPE 
        SYNTAX DisplayString
        ACCESS read-only
        STATUS mandatory
        DESCRIPTION "User defined text description of the cabinet.
                     A mirror of cpsCabinetDescription."
        ::= { cpsMc0800Entry 2 }

cpsMc0800MRevision OBJECT-TYPE 
        SYNTAX INTEGER
        ACCESS read-only
        STATUS mandatory
        DESCRIPTION "The marketing revision of this device"
        ::= { cpsMc0800Entry 3 }

-- ==================================================================
-- Group Control String for Point System

cpsGroupCtrl OBJECT-TYPE
        SYNTAX  DisplayString (SIZE (0..256)) 
        ACCESS  read-write
        STATUS  mandatory 
        DESCRIPTION "This string is used to select one or more groups of 
                     devices to receive mass configuration operations. When
                     cpsGroupCtrl.0 is null, SNMP operations are performed in 
                     the standard way for SNMPv1. When cpsGroupCtrl.0 is not
                     null, the Cabinet (BiaIndex) and Slot (SlotIndex) index 
                     values that uniquely identify a device are ignored, and 
                     instead the operation is applied to all devices that have
                     Groups variables that contain user- or system-defined
                     keywords that match those in cpsGroupCtrl.0. The CfgMatch
                     variables (cpsSlotDetail) for each of these devices will
                     be yes(1).
                     Advanced options are invoked by prepending one of the
                     following command characters to the keywords in
                     cpsGroupCtrl.0:
                     1) '.' means 'Pick-One'. When any 'Pick-One' operators are
                        present in the Group Control String, then one or more
                        of the keywords so marked must appear in the Device
                        Group String of the slide-in device for configuration
                        changes to be allowed. 'Pick-One' is the default
                        operation that is used when no command character is
                        present on a keyword.
                     2) '-' or '!' means 'Prohibited'. When any 'Prohibited'
                        operators are present in the Group Control String, 
                        then if any of the keywords so marked appears in the
                        Device Group String of the slide-in device, then no
                        configuration changes are applied.
                     3) '+' is the 'Required' operator. When any 'Required'
                        operators are present in the Group Control String, 
                        then all of the keywords so marked must appear in the
                        Device Group String of the slide-in device for 
                        configuration changes to be allowed.
                     4) '*' is a Wildcard that matches zero or more characters.
                        It is the only command character that does not need
                        to appear at the beginning of the keyword. It is also
                        the only one that can be used in combination with the
                        others within a single keyword."
        ::= { cpsAgent 1 }

-- =====================================

cpsSlotPwrTable OBJECT-TYPE
        SYNTAX SEQUENCE OF CpsSlotPwrEntry
        ACCESS not-accessible
        STATUS mandatory
        DESCRIPTION "Sparse table containing one power control entry for each
                     slot in the stack, indexed by cabinet serial number and
                     slot."
        ::= { cpsAgent 2 }

cpsSlotPwrEntry OBJECT-TYPE
        SYNTAX CpsSlotPwrEntry
        ACCESS not-accessible
        STATUS mandatory
        DESCRIPTION "The power on/off control for a single Point System slot."
        INDEX { cpsSlotPwrBiaIndex, cpsSlotPwrSlotIndex }
        ::= { cpsSlotPwrTable 1 }

CpsSlotPwrEntry ::=
        SEQUENCE {
                  cpsSlotPwrBiaIndex    INTEGER,
                  cpsSlotPwrSlotIndex   INTEGER,
                  cpsSlotPwrState       INTEGER
                  }

cpsSlotPwrBiaIndex OBJECT-TYPE 
        SYNTAX INTEGER
        ACCESS read-only
        STATUS mandatory
        DESCRIPTION "The cabinet serial number (BIA) of the slot"
        ::= { cpsSlotPwrEntry 1 }

cpsSlotPwrSlotIndex OBJECT-TYPE 
        SYNTAX INTEGER
        ACCESS read-only
        STATUS mandatory
        DESCRIPTION "The slot number of the slot"
        ::= { cpsSlotPwrEntry 2 }

cpsSlotPwrState OBJECT-TYPE 
        SYNTAX INTEGER { on(1), off(2) }
        ACCESS read-write
        STATUS mandatory
        DESCRIPTION "The power control for the slot. When off(2), no power
                     is supplied to the slot. If examined, the slot will
                     appear empty."
        ::= { cpsSlotPwrEntry 3 }

-- =====================================

cpsIsPrimary OBJECT-TYPE
        SYNTAX INTEGER { yes(1), no(2) }
        ACCESS read-write
        STATUS mandatory 
        DESCRIPTION "Indicates whether or not this Management Module is the
                     primary Management Module in the stack.
                     This variable contains the same information as the 
                     cpsmm100IsPrimary variable, but answers a slightly
                     different question: cpsmm100IsPrimary answers 'what is
                     the primary status of the management module in cabinet
                     C slot S?' and cpsIsPrimary answers 'what is the primary
                     status of the management module I am talking to now?'
                     The difference is that cpsIsPrimary does not require that
                     the requestor translate the IP address of the management
                     module they are communicating with into a cabinet serial
                     number (BIA) and slot index. This could otherwise only be
                     accomplished via a sequential search through cpsmm100Table"
        ::= { cpsAgent 3 }

END
