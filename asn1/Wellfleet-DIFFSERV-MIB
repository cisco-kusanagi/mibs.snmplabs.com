Wellfleet-DIFFSERV-MIB DEFINITIONS ::= BEGIN


    IMPORTS

      IpAddress
        FROM RFC1155-SMI
      OBJECT-TYPE
        FROM RFC-1212
      wfDiffServAppGroup
        FROM Wellfleet-COMMON-MIB;

    wfDiffServ	OBJECT IDENTIFIER ::= { wfDiffServAppGroup 1 }

    wfDiffServCreate OBJECT-TYPE
        SYNTAX	INTEGER {
    		    created(1),
    		    deleted(2)
    		}
        ACCESS	read-write
        STATUS	mandatory
        DESCRIPTION
                "Create/Delete parameter. Default is created."
        DEFVAL	{ created }
        ::= { wfDiffServ 1 }

    wfDiffServEnable OBJECT-TYPE
        SYNTAX	INTEGER {
    		    enabled(1),
    		    disabled(2)
    		}
        ACCESS	read-write
        STATUS	mandatory
        DESCRIPTION
                "Enable/Disable parameter. Default is enabled."
        DEFVAL	{ enabled }
        ::= { wfDiffServ 2 }

    wfDiffServDsByteMask OBJECT-TYPE
        SYNTAX        INTEGER
        ACCESS        read-write
        STATUS        mandatory
        DESCRIPTION
                "Bitmask which is AND'ed with DS-byte stting and then
		 OR'ed with DS-byte in the packet. It masks out bits."
        ::= { wfDiffServ 3 }


-- End of wfDiffServ --


    wfDiffServIntfTable OBJECT-TYPE
        SYNTAX	SEQUENCE OF WfDiffServIntfEntry
        ACCESS	not-accessible
        STATUS	mandatory
        DESCRIPTION
                "Table of DiffServ capable interfaces."
        ::= { wfDiffServAppGroup 2 }

    wfDiffServIntfEntry OBJECT-TYPE
        SYNTAX	WfDiffServIntfEntry
        ACCESS	not-accessible
        STATUS	mandatory
        DESCRIPTION
                "DiffServ interface table entry."
        INDEX	{ wfDiffServIntfIpAddr,
                  wfDiffServIntfIfIndex }
        ::= { wfDiffServIntfTable 1 }

    WfDiffServIntfEntry ::= SEQUENCE {
    	    wfDiffServIntfCreate
    		INTEGER,
    	    wfDiffServIntfEnable
    		INTEGER,
    	    wfDiffServIntfState
    		INTEGER,
    	    wfDiffServIntfIpAddr
    		IpAddress,
    	    wfDiffServIntfIfIndex
    		INTEGER,
    	    wfDiffServIntfLogMask
    		INTEGER,
    	    wfDiffServIntfCfgType
    		INTEGER,
            wfDiffServIntfUrlIdleOutTimer
                INTEGER
        }

    wfDiffServIntfCreate OBJECT-TYPE
        SYNTAX  INTEGER {
                    created(1),
                    deleted(2)
                }
        ACCESS	read-write
        STATUS	mandatory
        DESCRIPTION
                "Create/Delete parameter. Default is created."
        DEFVAL  { created }
        ::= { wfDiffServIntfEntry 1 }

    wfDiffServIntfEnable OBJECT-TYPE
        SYNTAX  INTEGER {
                    enabled(1),
                    disabled(2)
                }
        ACCESS	read-write
        STATUS	mandatory
        DESCRIPTION
                "Enable/Disable parameter. Default is enabled."
        DEFVAL  { enabled }
        ::= { wfDiffServIntfEntry 2 }

    wfDiffServIntfState OBJECT-TYPE
        SYNTAX  INTEGER {
                    up(1),
                    down(2),
                    notpres(3)
                }
        ACCESS	read-only
        STATUS	mandatory
        DESCRIPTION
                "Current state of this interface."
        DEFVAL  { notpres }
        ::= { wfDiffServIntfEntry 3 }

    wfDiffServIntfIpAddr OBJECT-TYPE
        SYNTAX  IpAddress
        ACCESS	read-only
        STATUS	mandatory
        DESCRIPTION
                "IP address this interface is associated with."
        ::= { wfDiffServIntfEntry 4 }

    wfDiffServIntfIfIndex OBJECT-TYPE
        SYNTAX  INTEGER
        ACCESS	read-only
        STATUS	mandatory
        DESCRIPTION
                "Circuit number/if index this interface is associated with."
        ::= { wfDiffServIntfEntry 5 }

    wfDiffServIntfLogMask OBJECT-TYPE
        SYNTAX  INTEGER
        ACCESS	read-write
        STATUS	mandatory
        DESCRIPTION
                "Specifies which events to log.
                 0x00000001 - Filter events: Add/Del/Enb/Dis
                 0x00000002 - Interaction with cops.
                 0x00000004 - Trigger events.
                 0x00000008 - Interaction with IP interface.
                 0x00000020 - Filter debugging events."
        DEFVAL  { 1 }
        ::= { wfDiffServIntfEntry 6 }

    wfDiffServIntfCfgType OBJECT-TYPE
        SYNTAX  INTEGER {
                    static(1),
                    cops(2)
                }
        ACCESS	read-write
        STATUS	mandatory
        DESCRIPTION
                "Interface config type."
        DEFVAL  { static }
        ::= { wfDiffServIntfEntry 7 }

    wfDiffServIntfUrlIdleOutTimer OBJECT-TYPE
        SYNTAX  INTEGER
        ACCESS  read-write
        STATUS  mandatory
        DESCRIPTION
                "Number of seconds to wait before a dynamic Url filter
                 is idled out."
        DEFVAL  { 120 }
        ::= { wfDiffServIntfEntry 8 }


    END  -- Wellfleet-DIFFSERV-MIB
