TVD-MIB DEFINITIONS ::= BEGIN

IMPORTS
    enterprises                        FROM RFC1155-SMI
    OBJECT-TYPE                        FROM RFC-1212
    TRAP-TYPE                          FROM RFC-1215
    DisplayString 		       FROM RFC1213-MIB
    nai,
	naiTrapAgent,				
	naiTrapShortDescription,	
	naiTrapSeverity,            
	naiTrapAgentVersion,
	naiTrapLongDescription,		 
	naiTrapProblemResolution,	
	naiTrapDiagID,              
	naiTrapURL,                 
	naiTrapSourceDNSName,		
	naiTrapTargetDNSName		FROM NAI-MIB;
 

-- 
-- McAfee MIB DEFINITION
-- 
-- mcafee was assigned the new ID of 12 (as opposed to the older 4)
-- for SNMP structures conforming to the NAI and mcafee standards


mcafee					OBJECT IDENTIFIER ::= { nai 12 }
-- mcafeeTVDTrapBase			OBJECT IDENTIFIER ::= { mcafee 0 }
mcafeeTVDTrap				OBJECT IDENTIFIER ::= { mcafee 0 }
mcafeeStandardTrapField			OBJECT IDENTIFIER ::= { mcafee 1 }

--
-- The following trap is a sample that contains all of the nai standard 
-- trap fields. 



-- 
-- mcafee MIB DEFINITION
-- 
-- mcafee was assigned the new ID of 12 (as opposed to the older 4)
-- for SNMP structures conforming to the NAI and mcafee standards

--  
 
--mcafeeFields MODULE-IDENTITY
--	LAST-UPDATED  "Wed August 1, 1999"
--    ORGANIZATION "Network Associates Inc. mcafee Div."
--    CONTACT-INFO
--    	"Postal:   Network Associates, Inc.
--                   3965 Freedom Circle
--                   Santa Clara, CA  95054
--        Phone:     +1 408 988-3832
--        Internet:  www.nai.com"
--	DESCRIPTION
--    	"mcafee agent MIB definition"
--        	::= { mcafee 1 }
--
--

--
	-- The nai standard trap group
	-- This group contains objects describing NAI standard alarm variable 
	-- definitions which shall be included in each product's trap extension
	-- resulting in transmission of a SNMP trap message.



mcafee_TRAPID  OBJECT-TYPE	
	SYNTAX	INTEGER
	ACCESS  read-only
    STATUS  mandatory
    DESCRIPTION
    "mcafee Event/Alert Id number"		
	::= { mcafeeStandardTrapField 1 }             


mcafee_ENGINEVERSION OBJECT-TYPE		        
        SYNTAX          DisplayString
        ACCESS          read-only
        STATUS          mandatory
        DESCRIPTION
	  "Version string for the current Av Scanner Engine"
            ::= { mcafeeStandardTrapField 2 }

mcafee_DATVERSION OBJECT-TYPE		        
        SYNTAX          DisplayString
        ACCESS          read-only
        STATUS          mandatory
        DESCRIPTION
	  "Version string for the current Av DAT File"
        ::= { mcafeeStandardTrapField 3 }

mcafee_ENGINESTATUS OBJECT-TYPE
	SYNTAX  INTEGER
	ACCESS  read-only
    STATUS  mandatory
    DESCRIPTION
		"The status at the end of the last engine scan"
    ::= { mcafeeStandardTrapField 4  }

mcafee_VIRUSNAME OBJECT-TYPE		        
    SYNTAX          DisplayString
    ACCESS          read-only
    STATUS          mandatory
    DESCRIPTION
	"Name of virus detected"
     ::= { mcafeeStandardTrapField 5 }
    
mcafee_VIRUSTYPE	OBJECT-TYPE	
    SYNTAX          DisplayString
    ACCESS          read-only
    STATUS          mandatory
    DESCRIPTION
	"Type of infection (virus/trojan/etc)"
	 ::= { mcafeeStandardTrapField 6 }
	 
mcafee_FILENAME	OBJECT-TYPE	
    SYNTAX          DisplayString
    ACCESS          read-only
    STATUS          mandatory
    DESCRIPTION
	"File name and path"
	 ::= { mcafeeStandardTrapField 7 }
	 
mcafee_USERNAME	OBJECT-TYPE	
    SYNTAX          DisplayString
    ACCESS          read-only
    STATUS          mandatory
    DESCRIPTION
	"User Name"
	 ::= { mcafeeStandardTrapField 8 }   
	 
mcafee_OS	OBJECT-TYPE	
    SYNTAX          DisplayString
    ACCESS          read-only
    STATUS          mandatory
    DESCRIPTION
	"Operating System and Version"
	 ::= { mcafeeStandardTrapField 9 }
	 
mcafee_PROCESSORSERIAL	OBJECT-TYPE	
    SYNTAX          DisplayString
    ACCESS          read-only
    STATUS          mandatory
    DESCRIPTION
	"Processor Serial number"
	 ::= { mcafeeStandardTrapField 10 }
	 
mcafee_TASKNAME	OBJECT-TYPE	
    SYNTAX          DisplayString
    ACCESS          read-only
    STATUS          mandatory
    DESCRIPTION
	"Sub Task Name"
	 ::= { mcafeeStandardTrapField 11 }

mcafee_NUMVIRS		OBJECT-TYPE	
	SYNTAX  INTEGER
    ACCESS  read-only
    STATUS  mandatory
    DESCRIPTION
    "Number of infections detected."
	 ::= { mcafeeStandardTrapField 15 }
	 
mcafee_NUMCLEANED	OBJECT-TYPE	
	SYNTAX  INTEGER
    ACCESS  read-only
    STATUS  mandatory
    DESCRIPTION
    "Number of infections cleaned."
	 ::= { mcafeeStandardTrapField 16 }
	 
mcafee_NUMDELETED		OBJECT-TYPE	
	SYNTAX  INTEGER
    ACCESS  read-only
    STATUS  mandatory
    DESCRIPTION
    "Number of infected files deleted."
	 ::= { mcafeeStandardTrapField 17 }
	 
mcafee_NUMQUARANTINED	OBJECT-TYPE	
	SYNTAX  INTEGER
    ACCESS  read-only
    STATUS  mandatory
    DESCRIPTION
    "Number of viruses quarantined."
	 ::= { mcafeeStandardTrapField 18 }
	 
mcafee_SCANRETURNCODE	OBJECT-TYPE	
	SYNTAX  INTEGER
    ACCESS  read-only
    STATUS  mandatory
    DESCRIPTION
    "Return Code from Scan Engine"
	 ::= { mcafeeStandardTrapField 19 }
	 
mcafee_MAILFROMNAME	OBJECT-TYPE	
    SYNTAX          DisplayString
    ACCESS          read-only
    STATUS          mandatory
    DESCRIPTION
	"Mail From Field"
	 ::= { mcafeeStandardTrapField 30 }
	 
mcafee_MAILTONAME	OBJECT-TYPE	
    SYNTAX          DisplayString
    ACCESS          read-only
    STATUS          mandatory
    DESCRIPTION
	"Mail To Field Contents"
	 ::= { mcafeeStandardTrapField 31 }
	 
mcafee_MAILCCNAME	OBJECT-TYPE	
    SYNTAX          DisplayString
    ACCESS          read-only
    STATUS          mandatory
    DESCRIPTION
	"Mail CC Name"
	 ::= { mcafeeStandardTrapField 32 }
	 
mcafee_MAILSUBJECTLINE		OBJECT-TYPE	
    SYNTAX          DisplayString
    ACCESS          read-only
    STATUS          optional
    DESCRIPTION
	"Mail Subject Line"
	 ::= { mcafeeStandardTrapField 33 }
	 
mcafee_MAILIDENTIFIERINFO	OBJECT-TYPE	
    SYNTAX          DisplayString
    ACCESS          read-only
    STATUS          optional
    DESCRIPTION
	"Mail item identifier info"
	 ::= { mcafeeStandardTrapField 34 }

mcafee_NOTEID	OBJECT-TYPE	
    SYNTAX          DisplayString
    ACCESS          read-only
    STATUS          optional
    DESCRIPTION
	"Notes identifier info"
	 ::= { mcafeeStandardTrapField 35 }

mcafee_NOTESSERVERNAME	OBJECT-TYPE	
    SYNTAX          DisplayString
    ACCESS          read-only
    STATUS          optional
    DESCRIPTION
	"Notes Server Name"
	 ::= { mcafeeStandardTrapField 36 }

mcafee_NOTESDBNAME	OBJECT-TYPE	
    SYNTAX          DisplayString
    ACCESS          read-only
    STATUS          optional
    DESCRIPTION
	"Notes Database Name "
	 ::= { mcafeeStandardTrapField 37 }

mcafee_DOMAIN	OBJECT-TYPE	
    SYNTAX          DisplayString
    ACCESS          read-only
    STATUS          optional
    DESCRIPTION
	"Domain Name."
	 ::= { mcafeeStandardTrapField 38 }

mcafee_OBRULE	OBJECT-TYPE	
    SYNTAX          DisplayString
    ACCESS          read-only
    STATUS          optional
    DESCRIPTION
	"OB Rule "
	 ::= { mcafeeStandardTrapField 39 }

mcafee_LANGUAGECODE	OBJECT-TYPE	
    SYNTAX          DisplayString
    ACCESS          read-only
    STATUS          optional
    DESCRIPTION
	"Language Code of Machine where Event Originated"
	 ::= { mcafeeStandardTrapField 40 }
		
mcafee_CLIENTCOMPUTER	OBJECT-TYPE	
    SYNTAX          DisplayString
    ACCESS          read-only
    STATUS          optional
    DESCRIPTION
	"Name of Terminal Services Client Computer"
	 ::= { mcafeeStandardTrapField 41 }


mcafee_TSCLIENTID	OBJECT-TYPE	
    SYNTAX          INTEGER
    ACCESS          read-only
    STATUS          optional
    DESCRIPTION
	"Terminal Services Client Id number"
	 ::= { mcafeeStandardTrapField 42 }

mcafee_ACCESSPROCESSNAME	OBJECT-TYPE	
    SYNTAX          DisplayString
    ACCESS          read-only
    STATUS          optional
    DESCRIPTION
	"Name of Process triggering on-access scan"
	 ::= { mcafeeStandardTrapField 43 }

mcafee_EVENTNAME	OBJECT-TYPE	
    SYNTAX          DisplayString
    ACCESS          read-only
    STATUS          optional
    DESCRIPTION
	"Name of this event for McAfee Diagnostics"
	 ::= { mcafeeStandardTrapField 44 }

mcafee_GMTTIME	OBJECT-TYPE	
    SYNTAX          DisplayString
    ACCESS          read-only
    STATUS          optional
    DESCRIPTION
	"GMT time at the time the event was sent"
	 ::= { mcafeeStandardTrapField 45 }

mcafee_TIME	OBJECT-TYPE	
    SYNTAX          DisplayString
    ACCESS          read-only
    STATUS          optional
    DESCRIPTION
	"Local Time when the event was sent"
	 ::= { mcafeeStandardTrapField 46 }

mcafee_SOURCEIP	OBJECT-TYPE	
    SYNTAX          DisplayString
    ACCESS          read-only
    STATUS          optional
    DESCRIPTION
	"Source IP where event was generated"
	 ::= { mcafeeStandardTrapField 47 }

mcafee_TARGETIP	OBJECT-TYPE	
    SYNTAX          DisplayString
    ACCESS          read-only
    STATUS          optional
    DESCRIPTION
	"IP of machine which the infection occurred if different from Source IP"
	 ::= { mcafeeStandardTrapField 48 }


-- mcafee TRAP DEFINITIONS
--
-- sample with all fields NOTE all mcafee traps for 4.5 will have all fields




mcafee_EVENT_TEST_TRAP TRAP-TYPE
	ENTERPRISE mcafeeTVDTrap
	VARIABLES
	{
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		

		mcafee_TIME,           
		mcafee_TARGETIP,
		naiTrapTargetDNSName,
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME
	}
	DESCRIPTION
		"mcafee Alert Manager Test Trap"
	::= 9999



mcafee_EVENT_VIRFOUND TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		mcafee_TIME,           
		mcafee_TARGETIP,
		naiTrapTargetDNSName,

		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME

	}
	DESCRIPTION
  	"Infected file found."
  ::= 1024

mcafee_EVENT_FILECLEANED 	TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		mcafee_TIME,           
		mcafee_TARGETIP,
		naiTrapTargetDNSName,
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"File was cleaned."
  ::=             1025
  
mcafee_EVENT_FILECLEANERROR	 TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
	 
		mcafee_TIME,           
		mcafee_TARGETIP,
		naiTrapTargetDNSName,

		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Error while cleaning file."
  ::=        1026
  
mcafee_EVENT_FILEDELETED	TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		mcafee_TIME,           
		mcafee_TARGETIP,
		naiTrapTargetDNSName,
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Infected file deleted."
  ::=             1027
  
mcafee_EVENT_FILEDELETEERROR	TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		mcafee_TIME,           
		mcafee_TARGETIP,
		naiTrapTargetDNSName,

		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Error while deleting Infected file."
  ::=         1028
  
mcafee_EVENT_FILEEXCLUDING	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		mcafee_TIME,           
		mcafee_TARGETIP,
		naiTrapTargetDNSName,
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Excluding file while scanning"
  ::=       1029	
 

  
mcafee_EVENT_EXCLUDEERR	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		mcafee_TIME,           
		mcafee_TARGETIP,
		naiTrapTargetDNSName,
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Unable to exclude from scan"
  ::=       1030
 


  
mcafee_EVENT_INFECTION_ACESSDENIED	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		mcafee_TIME,           
		mcafee_TARGETIP,
		naiTrapTargetDNSName,

		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Infected file access denied"
  ::= 1031       
 
   
mcafee_EVENT_VIRUS_QUARANTINED	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		mcafee_TIME,           
		mcafee_TARGETIP,
		naiTrapTargetDNSName,
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Infected file moved to quarantine"
  ::=       1032
 

  
mcafee_EVENT_VIRUS_QUARANTINE_FAILURE	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Unable to move infected file to quarantine"
  ::=       1033
 
  
mcafee_EVENT_SCANEND_NO_VIRUSES	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Scan complete no viruses found"
  ::=       1034
 
  
mcafee_EVENT_SCAN_CANCELED	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Scan canceled"
  ::=       1035
 
   
mcafee_EVENT_VIRUS_FOUND_IN_MEMORY	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Virus found in memory"
  ::=       1036
 
  
mcafee_EVENT_VIRUS_IN_BOOT_RECORD	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Infected boot record found"
  ::=       1037
 
  
mcafee_EVENT_SCAN_FOUND_INFECTED_FILES	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Scan found infected files"
  ::=       1038
 
  
mcafee_EVENT_SCAN_FOUND_AND_CLEANED_INFECTIONS	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Scan found and cleaned infected files"
  ::=       1039
 
  
mcafee_EVENT_ALOG_ERROR	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Error accessing activity log file"
  ::=       1040
 
  
mcafee_EVENT_MEMALLOC_ERROR	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Memory allocation error while scanning"
  ::=       1041
 
  
mcafee_EVENT_DIR_ACCESS_ERROR	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Directory access error (path too long)"
  ::=       1042
 
  
mcafee_EVENT_WRITE_PROTECT_ERR	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Media write protected"
  ::=       1043
 
  
mcafee_EVENT_MEDIA_NOT_FOUND_ERR	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Specified media not found"
  ::=       1044
 
  
mcafee_EVENT_SCAN_ITEM_INVALID	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Specified scan item invalid"
  ::=       1045
 
  
mcafee_EVENT_FILE_IO_ERRORS	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"File i/o errors"
  ::=       1046
 
  
mcafee_EVENT_DISK_IO_ERR	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Disk I/O errors"
  ::=       1047
 
  
mcafee_EVENT_GEN_SYSTEM_ERROR      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Scan reports general system error"
  ::=       1048
 
  
mcafee_EVENT_INTERNAL_APP_ERROR	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Scan reported internal application error"
  ::=       1049
 
  
mcafee_EVENT_INFECTION_PASSWORD_PROTECTED	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Infected file password protected"
  ::=       1050
 
  
mcafee_EVENT_NOT_SCANNED_PASSWORD	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Not scanned password protected"
  ::=       1051
 
  
mcafee_EVENT_INFECTED_BINDARY	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Infected bindery object"
  ::=       1052
 
  
mcafee_EVENT_INFECTED_HEURISTICS	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Heuristics detected infected file"
  ::=       1053
 
  
mcafee_EVENT_DELETED_HEURISTICS	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Heuristics deleted infected file"
  ::=       1054
 
  
mcafee_EVENT_DELETE_ERR_HEURISTICS	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Delete error Heuristics detected infection"
  ::=       1055
 
  
mcafee_EVENT_QUARANTINED_HEURISTICS	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Heuristics detected infection quarantined"
  ::=       1056
 
  
mcafee_EVENT_QUAR_ERROR_HEURISTICS	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Move error on heuristics detected infection"
  ::=       1057
 
  
mcafee_EVENT_SCAN_TIMEOUT	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Scan timed out"
  ::=       1059
 
  
mcafee_EVENT_BOOT_SECTOR_CLEANED	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Boot sector cleaned"
  ::=       1060
 
  
mcafee_EVENT_CLEANERROR_BOOTSECTOR	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Clean error on boot sector"
  ::=       1061
 
  
mcafee_EVENT_ALERTERROR	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Alert error"
  ::=       1062
 
  
mcafee_EVENT_OPTIONSERROR      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Options error"
  ::=       1063
 
  
mcafee_EVENT_SERVICE_STARTED_1064	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Service started"
  ::=       1064
 
  
mcafee_EVENT_SERVICE_ENDING_1065	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Service ending"
  ::=       1065
 
  
mcafee_EVENT_SCED_START_TASK_OK      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Scheduled task started ok"
  ::=       1066
 
  
mcafee_EVENT_SCHED_START_TASK_ERROR	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Scheduled task start error"
  ::=       1067
 
  
mcafee_EVENT_SCED_TASK_END_OK	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Scheduled task completed ok"
  ::=       1068
 
  
mcafee_EVENT_SCHED_TASK_STOP_ERROR     TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Scheduled task stop error"
  ::=       1069
 
  
mcafee_EVENT_SCHED_TASK_SUCCESS      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Task success"
  ::=       1070
 
  
mcafee_EVENT_SCHED_TASK_CANCELED	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Task canceled"
  ::=       1071
 
  
mcafee_EVENT_TASKERR_LOGFILE	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Task error logfile"
  ::=       1076
 
  
mcafee_EVENT_TASK_ERR_MEMALLOC     TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Task error memory allocation"
  ::=       1077
 
  
mcafee_EVENT_SCAN_PROC_ERR     TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Scan proc error"
  ::=       1086
 
  
mcafee_EVENT_OAS_START	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"On access Scan starting"
  ::=       1087
 
  
mcafee_EVENT_OAS_STOP      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"On access scan stopping"
  ::=       1088
 
  
mcafee_EVENT_SCAN_SETTINGS	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Scan settings"
  ::=       1089
 
  
mcafee_EVENT_MACRO_VIRUS_DETECTED	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Macro virus detected"
  ::=     1100  
 
  
mcafee_EVENT_MACRO_VIRUS_DELETED	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Macro virus deleted"
  ::=       1101
 
  
mcafee_EVENT_UPDATEOK	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Update was successful"
  ::=       1118
 
  
mcafee_EVENT_UPDATEFAILED	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Update failed see event log"
  ::=       1119
 
  
mcafee_EVENT_UPDATE_RUNNING	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Update is running"
  ::=       1120
 
  
mcafee_EVENT_UPDATECANCELED      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Update was canceled"
  ::=       1121
 
  
mcafee_EVENT_UPGRADE_RUNNING      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Upgrade is running"
  ::=       1122
 
  
mcafee_EVENT_UPGRADE_FAILED	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Upgrade failed see event log"
  ::=       1123
 
  
mcafee_EVENT_UPGRADE_CANCELED	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Upgrade was canceled"
  ::=       1124
 
  
mcafee_EVENT_UPDATE_VERSION_OLDER	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"DAT version is older than current"
  ::=       1125
 
  
mcafee_EVENT_SCAN_CANCELED_BY_UPD	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Scan canceled by autoupdate or autoupgrade"
  ::=       1126
 
  
mcafee_EVENT_SCANNER_DISABLED	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Scanner disabled"
  ::=       1127
 
  
mcafee_EVENT_START_PROCESS	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Process started"
  ::=       1200
 
  
mcafee_EVENT_PROCESS_ENDED	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Process Ended"
  ::=       1201
 
  
mcafee_EVENT_ODS_SCAN_STARTED	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"On demand scan started"
  ::=       1202
 


mcafee_EVENT_ODS_SCAN_ENDED	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"On Demand Scan Complete"
  ::=       1203	
 
  
mcafee_EVENT_SCAN_REPORT_OS	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Report P3 OS and Serial Number"
  ::=       1204
 
  
mcafee_EVENT_MAIL_VIRUSCLEANED	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Mail Virus cleaned"
  ::=       1500
 
  
mcafee_EVENT_MAIL_VIRUSQUARANTINED	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Mail virus quarantined"
  ::=       1501
 
  
mcafee_EVENT_MAIL_VIRUS_NOTCLEANED	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Mail Virus not cleaned"
  ::=       1502
 
  
mcafee_EVENT_MAIL_VIRUS_DETECTED	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Mail Virus detected"
  ::=       1503
 
  
mcafee_EVENT_MAIL_VIRUS_DELETED	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Mail Virus Deleted"
  ::=       1504
 
  
mcafee_EVENT_MAIL_VIRUS_FILTERED	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Mail Content Filtered"
  ::=       1505
 
  
mcafee_EVENT_MAIL_CONTENTBLOCK	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Mail Content blocked"
  ::=       1506
 
  
mcafee_EVENT_MAIL_LOWDISKLIMIT      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Mail Low Disk Limit"
  ::=       1507
 
  
mcafee_EVENT_MAIL_UPPERDISKLIMIT	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Mail Upper Disk Limit"
  ::=       1508
 
  
mcafee_EVENT_MAIL_SERVICE_START	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Mail service startup"
  ::=       1509
 
  
mcafee_EVENT_MAIL_SERVICE_SHUTDOWN_OK	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Mail service shutdown successful"
  ::=       1510
 
  
mcafee_EVENT_MAIL_SERVICE_ABEND	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Mail service abnormal shutdown"
  ::=       1511
 
  
mcafee_EVENT_MAIL_SERVICE_MAX_LOAD	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Mail Maximum load"
  ::=       1512
 
  
mcafee_EVENT_MAIL_VIRUS_QUARANTINEDCLEANED	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Mail virus quarantined and cleaned"
  ::=       1513
 
  
mcafee_EVENT_MAIL_VIRUS_QUARANTINED	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Mail virus quarantined (not cleaned)"
  ::=       1514
 
  
mcafee_EVENT_NEW_MIB	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Alert Manager New MIB available"
  ::=       1900
 
  
mcafee_EVENT_EPO_FAILE_INSTPRODUCT	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Epo agent failed to install a software product"
  ::=       2201
 
  
mcafee_EVENT_EPO_AGENT_RETRYLIMIT	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Epo agent retry limit for a product"
  ::=       2202
 
  
mcafee_EVENT_EPO_AGENT_DISKSPACE	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Epo agent not enough disk space"
  ::=       2204
 
  
mcafee_EVENT_EPO_SPIPE_DISKSPACE	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Epo agent spipe not enough disk space"
  ::=       2208
 
  
mcafee_EVENT_EPO_AGENT_WRONG_PLATFORM	      TRAP-TYPE	
	ENTERPRISE mcafeeTVDTrap
    VARIABLES
    {
		naiTrapAgent,				
		naiTrapShortDescription,	
		naiTrapSeverity,            
		mcafee_SOURCEIP,		
		mcafee_GMTTIME,             
		naiTrapAgentVersion,
		naiTrapLongDescription,		 
		naiTrapProblemResolution,	
		naiTrapDiagID,              
		naiTrapURL,                 
		naiTrapSourceDNSName,		
		 
			 
		mcafee_TIME,           
		mcafee_TARGETIP,
		naiTrapTargetDNSName,
		
		
		mcafee_TRAPID,             
		mcafee_ENGINEVERSION,
		mcafee_DATVERSION,
		mcafee_ENGINESTATUS,
		mcafee_VIRUSNAME,
		mcafee_VIRUSTYPE,         
		mcafee_FILENAME,         
		mcafee_USERNAME,          
		mcafee_OS,          
		mcafee_PROCESSORSERIAL,
		
		mcafee_NUMVIRS,  
		mcafee_NUMCLEANED,
		mcafee_NUMDELETED,
		mcafee_NUMQUARANTINED,
		mcafee_SCANRETURNCODE,

		mcafee_MAILFROMNAME,   
		mcafee_MAILTONAME,
		mcafee_MAILCCNAME,
		mcafee_MAILSUBJECTLINE,
		mcafee_MAILIDENTIFIERINFO,

		mcafee_LANGUAGECODE,
		mcafee_CLIENTCOMPUTER,
		mcafee_TSCLIENTID,
		mcafee_ACCESSPROCESSNAME,

		mcafee_NOTEID,
		mcafee_NOTESSERVERNAME,
		mcafee_NOTESDBNAME,
		mcafee_DOMAIN,
		mcafee_OBRULE,
		mcafee_EVENTNAME


	}
	DESCRIPTION
  	"Epo agent wrong software platform"
  ::=       2216
 


END
