--
-- Based on Network Address Client document Dated: 4-10-96
-- MIB Revision Dated: 05-31-96
--
-- 
-- MIB Revision : 1.0 dated 1-17-97
-- Change Desc. : None. 
-- 
-- MIB Revision : 1.1 dated 3-20-97
-- Change Desc. : Specified ranges for different objects. 
-- 
-- 
--
-- MIB Revision : 1.2 dated  4/22/97
-- Change Desc. : Added access privilages to capabilities field  - S. Gaur
-- 
--
-- MIB Revision : 1.3 dated 9-16-97
-- Change Desc  : Renamed nodes to unique names in order to comply 
--                with Nortel CSU tool - S. Gaur
--
-- *** RELEASE 3.0 *** 
-- MIB Revision : 1.4 dated 6-22-98
-- Change Desc  : Changed the maximum range from 25 to 40 
--                for the nacCacheEgressString object.
--                                                        - S. Gaur
--				  Obsoleted the reset counter object,
--				  "nacCfgCounterReset".
--				  Changed DisplayString range for
--				  nvmNacCacheEgressNumber to (SIZE(1..40)). 
--				  Changed nacCacheEntryStatus to support 
--				  the enumeration of "active" and an access 
--				  of read-write.
--				  Corrected the  range for nvmNacCacheDnaAddress 
--				  to (SIZE(3..30). -A. Llanes
--
-- MIB Revision : 1.5 dated 8-7-98
-- Change Desc  : Increased the range to 1 to 34 for nacCacheDnaAddress,
--                and nvmNacCacheDnaAddress.
--                                                 S. Gaur
--
-- MIB Revision : 1.6 dated 11-02-98
-- Change Desc. : Add Severity Levels to Traps.
--						-F. Kottab

MICOM-NAC-MIB DEFINITIONS ::= BEGIN
	IMPORTS
		Counter, IpAddress 
                   		 	FROM RFC1155-SMI
		OBJECT-TYPE
                    			FROM RFC-1212
		TRAP-TYPE
                			FROM RFC-1215
		mcmSysAsciiTimeOfDay
					FROM MICOM-SYS-MIB
    	micom-oscar 
		    		FROM MICOM-OSCAR-MIB
		DisplayString 
				FROM SNMPv2-TC;


-- group OBJECT IDENTIFIERs

	micom-nac			OBJECT IDENTIFIER ::= {micom-oscar 15}
	nac-configuration	        OBJECT IDENTIFIER ::= {micom-nac 1}
	nac-statistics			OBJECT IDENTIFIER ::= {micom-nac 2}

--
--	Network Address Client Parameter Objects
--
nacCfgGroup    OBJECT IDENTIFIER ::= { nac-configuration 1 }

nacCfgAddressResolutionTriesNumber OBJECT-TYPE
	SYNTAX	INTEGER (1..5)
	ACCESS	read-write
	STATUS	mandatory
	DESCRIPTION
	  "NAME = NumberOfAddressResolutionRetries;
	   DESC = The number of times an address resolution \
		  request is sent to the server to get DNA \
		  address;
	   HELP = ;
	   CAPABILITIES = NET_CFG, VPN_CFG;"
	::= { nacCfgGroup 1}

nacCfgAddressResolutionTimeout OBJECT-TYPE
	SYNTAX	INTEGER (5..30)
	ACCESS	read-write
	STATUS	mandatory
	DESCRIPTION
	  "NAME = AddressResolutionTimeout;
	   DESC = The time in milliseconds after which an \
		  address resolution request will be resent \
		  in case the previous one is not answered;
	   HELP = Setting a very low value in a heavily \
		  loaded IP network would result in \
		  transmissions of multiple requests \
		  further increasing the network load. \
		  It is recommended to tune this value \
		  by considering the IP netwrok load and \
		  performance;
	   CAPABILITIES = NET_CFG, VPN_CFG;"
	::= { nacCfgGroup 2}

nacCfgCacheStatus OBJECT-TYPE
	SYNTAX	INTEGER {
		disable (1),
		enable (2),
		flush (3)
		}
	ACCESS	read-write
	STATUS	mandatory
	DESCRIPTION
	  "NAME = AddressCachingFunctionality;
	   DESC = Ability to enable or disable Caching of \
		  previously resolved Addresses and to \
		  remove previously resolved addresses \
		  from the cache.;
	   HELP = It is recommended that caching be enabled as \
		  it helps relieve the load on the server \
		  reduces network traffic and speeds up \
		  address resolution and hence call-setup. \
		  Flushing of cache is recommended if the \
		  network configuration has changed resulting \
		  in changes in the DNA and/or DNs, rendering \
		  the previously cached resolutions incorrect;
	   CAPABILITIES = NET_CFG, VPN_CFG;"
	::= { nacCfgGroup 3}

nacCfgNumberOfCacheEntries OBJECT-TYPE
	SYNTAX	INTEGER (100..1000)
	ACCESS	read-only
	STATUS	mandatory
	DESCRIPTION
	  "NAME = CacheSize;
	   DESC = Max number of Address Resolutions to be \
		  cached in memory;
	   HELP = If this value is very high the \
		  free memory space on the unit will be \
		  reduced which may affect the unit's performance \
		  A too low value would cause the unit to \
		  frequently consult the server if diverse \
		  numbers are dialed, beating the purpose of \
		  having a local cache. The optimum value \
		  will depend on the network size and the \
		  number of frequently dialed DNs. It is \
		  recommended to start with the minimum value \
		  (100) and tune it to the optimum value \
		  by observing the performance;
	   CAPABILITIES = NET_CFG, VPN_CFG;"
	::= { nacCfgGroup 4}

nacCfgCounterReset OBJECT-TYPE
	SYNTAX	INTEGER {
		reset(1),
		other(2)
	}
	ACCESS	write-only
	STATUS	obsolete	
	DESCRIPTION
	  "NAME = CounterReset;
       DESC = This object was obsoleted as of release \
	      3.0; and is included here only to support \
	      backwards compatibility for software \
	      versions prior to release 3.0. \
	   	  Setting this to reset will clear out \
		  the counters for Statistics for the \
		  Address Client.;
	   HELP = ;
	   CAPABILITIES = NET_CFG, VPN_CFG;"
	::= { nacCfgGroup 5}

nacCfgCustomerId OBJECT-TYPE
	SYNTAX	INTEGER (1..99)
	ACCESS	read-only
	STATUS	mandatory
	DESCRIPTION
	  "NAME = CustomerId;
	   DESC = An unique number allocated to a Customer \
		  thereby allowing a single server to serve \
		  more than one customer;
	   HELP = The Customer Id helps to identify all units \
		  belonging to a particular Customer. If a \
		  server is shared by many customers, the \
		  server uses the Id to firewall the voice \
		  networks of one customer from the others;
	   CAPABILITIES = NET_CFG, VPN_CFG;"
	::= { nacCfgGroup 6}

--
-- 	Network Address Client Cache Table
--

nacCacheTable OBJECT-TYPE
	SYNTAX	SEQUENCE OF NacCacheEntry
	ACCESS	not-accessible
	STATUS	mandatory
	DESCRIPTION
	  "NAME = DNA cache table;
	   DESC = DNA cache table;
	   HELP = ;
	   CAPABILITIES = NET_CFG, VPN_CFG;"
	::= {nac-configuration 2}

nacCacheEntry OBJECT-TYPE
	SYNTAX	NacCacheEntry
	ACCESS	not-accessible
	STATUS	mandatory
	DESCRIPTION
	  "NAME = Entry of DNA cache table;
	   DESC = Entry of DNA cache table;
	   HELP = ;
	   CAPABILITIES = ;"
	INDEX		{nacCacheEgressString}
	::= {nacCacheTable 1}

NacCacheEntry ::= SEQUENCE {
	nacCacheEgressString			DisplayString,
	nacCacheServerIpAddress			IpAddress,
	nacCacheDnaAddress			DisplayString,
	nacCacheEntryType			INTEGER,
	nacCacheNumberOfHits			INTEGER,
	nacCacheEntryStatus			INTEGER
	}

nacCacheEgressString OBJECT-TYPE
	SYNTAX	DisplayString (SIZE(1..40))
	ACCESS	read-write
	STATUS	mandatory
	DESCRIPTION
	  "NAME = EgressDialString;
	   DESC = EgressDialString associated with a voice channel.\
		  	  For software releases prior to 3.0, the \
		  	  string range was restricted to (SIZE(1..25)).;
	   HELP = EgressDialString represents the rule which helps \
		  in associating dialed digits to a voice channel. \
		  The string allows digits and wild cards;
	   CAPABILITIES = ;"
	::= { nacCacheEntry 1}

nacCacheServerIpAddress OBJECT-TYPE
	SYNTAX	IpAddress
	ACCESS	read-write
	STATUS	mandatory
	DESCRIPTION
	  "NAME = ServerIpAddress;
	   DESC = Network Address of server which resolved this entry.; 
	   HELP = Value of this object is valid only when \
		  EntryType is learned. It is unique to a given server and helps \
		  in tracking the address resolution to the server;
	   CAPABILITIES = ;"
	::= { nacCacheEntry 2}

nacCacheDnaAddress OBJECT-TYPE
	SYNTAX	DisplayString (SIZE(1..34))
	ACCESS	read-write
	STATUS	mandatory
	DESCRIPTION
	  "NAME = DNAAddress;
	   DESC = DNA address of the unit to which this voice information \
		  belongs;
	   HELP = ;
	   CAPABILITIES = ;"
	::= { nacCacheEntry 3}

nacCacheEntryType OBJECT-TYPE
	SYNTAX	INTEGER {
		learnt (1),
		static (2)
		}
	ACCESS	read-only
	STATUS	mandatory
	DESCRIPTION
	  "NAME = CacheEntryType;
	   DESC = Indicates whether the entry was provisioned \
		  (static) by user or was previously resolved \
		  by a server (learned);
	   HELP = If no server is available \
		  entries must be provisioned \
		  for voice networking;
	   CAPABILITIES = ;"
	::= { nacCacheEntry 4}

nacCacheNumberOfHits OBJECT-TYPE
	SYNTAX	INTEGER 
	ACCESS	read-only
	STATUS	mandatory
	DESCRIPTION
	  "NAME = CacheEntryUsage;
	   DESC = The number of times this entry was used to \
		  by this unit for resolving dialed digits;
	   HELP = This value is useful in identifying \
		  frequently dialed numbers;
	   CAPABILITIES = ;"
	::= { nacCacheEntry 5}

nacCacheEntryStatus OBJECT-TYPE
	SYNTAX	INTEGER {
		add (1),
		delete (2),
		active (3)
		}
	ACCESS	read-write
	STATUS	mandatory
	DESCRIPTION
	  "NAME = StaticEntryInsertionDeletion;
	   DESC = For software releases prior to 3.0 \
		  this object only supports add and delete \
		  with an access of write-only.  Used to insert \
		  or remove a static address resolution entry;
	   HELP = ;
	   CAPABILITIES = ;"
	::= { nacCacheEntry 6}

--
-- NAC Server Table
--

nacServerTable OBJECT-TYPE
	SYNTAX	SEQUENCE OF NacServerEntry
	ACCESS	not-accessible
	STATUS	mandatory
	DESCRIPTION
	  "NAME = ServerTable;
	   DESC = List of servers this unit can use to \
		  request an address resolution from;
	   HELP = ;
	   CAPABILITIES = NET_CFG, VPN_CFG;"
	::= {nac-configuration 3}

nacServerEntry OBJECT-TYPE
	SYNTAX	NacServerEntry
	ACCESS	not-accessible
	STATUS	mandatory
	DESCRIPTION
	  "NAME = ServerEntry;
	   DESC = A server this unit can use to \
		  request an address resolution from;
	   HELP = ;
	   CAPABILITIES = ;"
	INDEX		{nacServerIpAddress}
	::= { nacServerTable 1}

NacServerEntry ::= SEQUENCE {
	nacServerIpAddress			IpAddress,
	nacServerName				DisplayString,
	nacServerAvailStatus			INTEGER,
	nacServerStatus				INTEGER,
	nacServerHelloTime			INTEGER,
	nacServerType 				INTEGER,
	nacServerRegistrationCount 		Counter,
	nacServerHello1Count 			Counter,
	nacServerHello2Count 			Counter,
	nacServerHello3Count 			Counter,
	nacServerRequestCount 			Counter,
	nacServerResolvedCount			Counter,
	nacServerNoNumberCount			Counter,
	nacServerTimeoutCount 			Counter
	}

nacServerIpAddress OBJECT-TYPE
	SYNTAX	IpAddress
	ACCESS	read-write
	STATUS	mandatory
	DESCRIPTION
	  "NAME = ServerIpAddress;
	   DESC = Network address of server which resolved this \
		  address.;
	   HELP = It is unique for a given server and \
		  is used by this unit to reach the server;
	   CAPABILITIES = ;"
	::= { nacServerEntry 1}

nacServerName OBJECT-TYPE
	SYNTAX	DisplayString (SIZE(1..50))
	ACCESS	read-write
	STATUS	mandatory
	DESCRIPTION
	  "NAME = ServerName;
	   DESC = A user supplied name of a server;
	   HELP = Useful in \
		  identifying a server;
	   CAPABILITIES = ;"
	::= { nacServerEntry 2}

nacServerAvailStatus OBJECT-TYPE
	SYNTAX	INTEGER {
		available (1),
		transition (2),
		notAvailable (3)
		}
	ACCESS	read-only
	STATUS	mandatory
	DESCRIPTION
	  "NAME = ServerAvailablity;
	   DESC = Availability of the server for address resolution;
	   HELP = A server is said to be available if this \
		  unit has been successfully communicating \
		  the said server. \
                  A server is said to be in transistion if \
		  this unit is in the process of establishing \
		  full communication with the said server. \
                  A server is said to be notAvailable if this \
		  unit is temporarily lost communication with \
		  the said server;
	   CAPABILITIES = ;"
	::= { nacServerEntry 3}

nacServerStatus OBJECT-TYPE
	SYNTAX	INTEGER {
		enable (1),
		disable (2),
		delete (3)
		}
	ACCESS	read-write
	STATUS	mandatory
	DESCRIPTION
	  "NAME = ServerStatus;
	   DESC = Ability to insert, disable or delete a server;
	   HELP = Setting the value to enable results in insertion \
		  of server for address resolution \
                  Setting the value to disable will refrain this \
		  unit from using the said server for address \
		  resolution. This may be done if the server is \
		  known to be temporarily out of service. \
		  Setting the value to delete will remove the \
		  entry from the table;
	   CAPABILITIES = ;"
	::= { nacServerEntry 4}

nacServerHelloTime OBJECT-TYPE
	SYNTAX	INTEGER (30..180)
	ACCESS	read-write
	STATUS	mandatory
	DESCRIPTION
	  "NAME = HelloTimeInterval;
	   DESC = The interval of time in seconds between transmission \
		  of two consecutive Hello messages to the server;
	   HELP = The interval of time in seconds between transmission \
		  of two consecutive Hello messages to the server. \
		  If the server doesnot see a HELLO message within \
		  a specified period it will purge it's database \
		  of all entries belonging to this unit. \
		  It is recommended that this value be such that \
		  this unit will transmit atleast two HELLO packets \
		  within the server's timeout period. \
		  Having a very low value will result in large \
		  number of HELLO packets, increasing traffic. \
		  The value should be tuned based on the IP traffic \
		  and the timeout value provisioned in the server;
	   CAPABILITIES = ;"
	DEFVAL	{60}
	::= { nacServerEntry 5}

nacServerType OBJECT-TYPE
	SYNTAX	INTEGER {
		primary (1),
		secondary (2)
		}
	ACCESS	read-write
	STATUS	mandatory
	DESCRIPTION
	  "NAME = ServerType;
	   DESC = Type of NAS to which this information is assigned.;
	   HELP = A primary Server is the preferred server which \
		  will be first consulted for address resolution. \
		  A secondary server is used as an alternative \
		  if the primary is not responding. \
		  All servers have to be marked secondary if \
		  round-robin load sharing is desired between servers;
	   CAPABILITIES = ;"
	::= { nacServerEntry 6}

nacServerRegistrationCount OBJECT-TYPE
	SYNTAX	Counter
	ACCESS	read-only
	STATUS	mandatory
	DESCRIPTION
	  "NAME = ServerRegistrationCount;
	   DESC = The number of times this server has acknowledged \
		  a registration change;
	   HELP = ;
	   CAPABILITIES = ;"
	::= { nacServerEntry 7}

nacServerHello1Count OBJECT-TYPE
	SYNTAX	Counter
	ACCESS	read-only
	STATUS	mandatory
	DESCRIPTION
	  "NAME = ServerHello1Count;
	   DESC = The number of keep alive hellos sent to this server;
	   HELP = ;
	   CAPABILITIES = ;"
	::= { nacServerEntry 8}

nacServerHello2Count OBJECT-TYPE
	SYNTAX	Counter
	ACCESS	read-only
	STATUS	mandatory
	DESCRIPTION
	  "NAME = ServerHello2Count;
	   DESC = The number of hellos indicating a change in \
		  registration table to this server;
	   HELP = ;
	   CAPABILITIES = ;"
	::= { nacServerEntry 9}

nacServerHello3Count OBJECT-TYPE
	SYNTAX	Counter
	ACCESS	read-only
	STATUS	mandatory
	DESCRIPTION
	  "NAME = ServerHello3Count;
	   DESC = The number of hellos sent that request a response.\
		  Used to revive a notAvailable server;
	   HELP = ;
	   CAPABILITIES = ;"
	::= { nacServerEntry 10}

nacServerRequestCount OBJECT-TYPE
	SYNTAX	Counter
	ACCESS	read-only
	STATUS	mandatory
	DESCRIPTION
	  "NAME = ServerRequestCount;
	   DESC = The number of DN-DNA requests to this \
		  server since start up;
	   HELP = ;
	   CAPABILITIES = ;"
	::= { nacServerEntry 11}

nacServerResolvedCount OBJECT-TYPE
	SYNTAX	Counter
	ACCESS	read-only
	STATUS	mandatory
	DESCRIPTION
	  "NAME = ServerResolvedCount;
	   DESC = The number of DN-DNA's resolved by this \
		  server since start up;
	   HELP = ;
	   CAPABILITIES = ;"
	::= { nacServerEntry 12}

nacServerNoNumberCount OBJECT-TYPE
	SYNTAX	Counter
	ACCESS	read-only
	STATUS	mandatory
	DESCRIPTION
	  "NAME = ServerNoNumberCount;
	   DESC = The number of DN-DNA requests with phone number \
		  not found in server since start up;
	   HELP = ;
	   CAPABILITIES = ;"
	::= { nacServerEntry 13}

nacServerTimeoutCount OBJECT-TYPE
	SYNTAX	Counter
	ACCESS	read-only
	STATUS	mandatory
	DESCRIPTION
	  "NAME = ServerTimeoutCount;
	   DESC = The number of entries resent due to timeouts \
		  since start up.
	   HELP = ;
	   CAPABILITIES = ;"
	::= { nacServerEntry 14}

-- Parallel Objects

nvmNacCfgGroup    OBJECT IDENTIFIER ::= { nac-configuration 4 }

nvmNacCfgAddressResolutionTriesNumber OBJECT-TYPE
	SYNTAX	INTEGER (1..5)
	ACCESS	read-only
	STATUS	mandatory
	DESCRIPTION
	  "NAME = NumberOfAddressResolutionRetries;
	   DESC = The number of times an address resolution \
		  request is sent to the server to get DNA \
		  address on the next reset;
	   HELP = This is the value this unit will \
		  use next time the unit is reset or rebooted;
	   CAPABILITIES = NET_CFG, VPN_CFG;"
	::= { nvmNacCfgGroup 1}

nvmNacCfgAddressResolutionTimeout OBJECT-TYPE
	SYNTAX	INTEGER (5..30)
	ACCESS	read-only
	STATUS	mandatory
	DESCRIPTION
	  "NAME = AddressResolutionTimeout;
	   DESC = The time in milliseconds after which an \
		  address resolution request will be resent \
		  in case the previous one is not answer.;
	   HELP = Setting a very low value in a heavily \
		  loaded IP network would result in \
		  transmissions of multiple requests \
		  furthur increasing the network load. \
		  It is recommended to tune this value \
		  by considering the IP netwrok load and \
		  performance. \
		  This is the value this unit will \
		  use next time the unit is reset or rebooted;
	   CAPABILITIES = NET_CFG, VPN_CFG;"
	::= { nvmNacCfgGroup 2}

nvmNacCfgCacheStatus OBJECT-TYPE
	SYNTAX	INTEGER {
		disable (1),
		enable (2)
		}
	ACCESS	read-only
	STATUS	mandatory
	DESCRIPTION
	  "NAME = AddressCachingFunctionality;
	   DESC = Ability to enable or disable caching of \
		  previously resolved Addresses. \
	   HELP = It is recommended that caching be enabled as \
		  it helps relieve the load on the server \
		  reduces network traffic and speeds up \
		  address resolution and hence call-setup. \
		  This is the value this unit will \
		  use next time the unit is reset or rebooted;
	   CAPABILITIES = NET_CFG, VPN_CFG;"
	DEFVAL	{2}
	::= { nvmNacCfgGroup 3}

nvmNacCfgNumberOfCacheEntries OBJECT-TYPE
	SYNTAX	INTEGER (100..1000)
	ACCESS	read-write
	STATUS	mandatory
	DESCRIPTION
	  "NAME = CacheSize;
	   DESC = Max number of Address Resolutions to be \
		  cached in memory.;
	   HELP = If this value is very high the \
		  free memory space on the unit will be \
		  reduced which may affect the unit's performance \
		  A too low value would cause the unit to \
		  frequently consult the server if diverse \
		  numbers are dialed, beating the purpose of \
		  having a local cache. The optimum value \
		  will depend on the network size and the \
		  number of frequently dialed DNs. It is \
		  recommended to start with the minimum value \
		  (100) and tune it to the optimum value \
		  by observing the performance. \
		  This is the value this unit will \
		  use next time the unit is reset or rebooted;
	   CAPABILITIES = NET_CFG, VPN_CFG;"
	DEFVAL	{100}
	::= { nvmNacCfgGroup 4}

nvmNacCfgCustomerId OBJECT-TYPE
	SYNTAX	INTEGER (1..99)
	ACCESS	read-write
	STATUS	mandatory
	DESCRIPTION
	  "NAME = CustomerId;
	   DESC = An unique number allocated to a Customer \
		  thereby allowing a single server to serve \
		  more than one customer.;
	   HELP = The Customer Id helps to identify all units \
		  belonging to a particular Customer. If a \
		  server is shared by many customers, the \
		  server uses the Id to firewall the voice \
		  networks of one customer from the others;
		  This is the value this unit will \
		  use next time the unit is reset or rebooted;
	   CAPABILITIES = NET_CFG, VPN_CFG;"
	::= { nvmNacCfgGroup 5}

--
-- 	Parallel Network Address Client Cache Table
--

nvmNacCacheTable OBJECT-TYPE
	SYNTAX	SEQUENCE OF NvmNacCacheEntry
	ACCESS	not-accessible
	STATUS	mandatory
	DESCRIPTION
	  "NAME = DNA cache table;
	   DESC = DNA cache table;
	   HELP = ;
	   CAPABILITIES = NET_CFG, VPN_CFG;"
	::= {nac-configuration 5}

nvmNacCacheEntry OBJECT-TYPE
	SYNTAX	NvmNacCacheEntry
	ACCESS	not-accessible
	STATUS	mandatory
	DESCRIPTION
	  "NAME = Entry of DNA cache table;
	   DESC = Entry of DNA cache table;
	   HELP = ;
	   CAPABILITIES = ;"
	INDEX		{nvmNacCacheEgressNumber}
	::= {nvmNacCacheTable 1}

NvmNacCacheEntry ::= SEQUENCE {
	nvmNacCacheEgressNumber			DisplayString,
	nvmNacCacheServerIpAddress		IpAddress,
	nvmNacCacheDnaAddress			DisplayString
	}

nvmNacCacheEgressNumber OBJECT-TYPE
	SYNTAX	DisplayString (SIZE(1..40))
	ACCESS	read-only
	STATUS	mandatory
	DESCRIPTION
	  "NAME = EgressDialString;
	   DESC = EgressDialString associated with a voice channel.;
	   HELP = EgressDialString represents the rule which helps \
		  in associating dialed digits to a voice channel. \
		  The string allows digits and wild cards. \
		  This is the value this unit will \
		  use next time the unit is reset or rebooted \
		  For software releases prior to 3.0, the \
		  string range was restricted to (SIZE(1..25)).;
	   CAPABILITIES = ;"
	::= { nvmNacCacheEntry 1}

nvmNacCacheServerIpAddress OBJECT-TYPE
	SYNTAX	IpAddress
	ACCESS	read-only
	STATUS	mandatory
	DESCRIPTION
	  "NAME = ServerIpAddress;
	   DESC = Network Address of server which resolved this entry. \
	   HELP = It is unique to a given server and helps \
		  in tracking the address resolution to the server. \
		  This is the value this unit will \
		  use next time the unit is reset or rebooted;
	   CAPABILITIES = ;"
	::= { nvmNacCacheEntry 2}

nvmNacCacheDnaAddress OBJECT-TYPE
	SYNTAX	DisplayString (SIZE(1..34))
	ACCESS	read-only
	STATUS	mandatory
	DESCRIPTION
	  "NAME = DNAAddress;
	   DESC = DNA address of the unit to which this voice \
		  belongs.;
	   HELP = ;
	   CAPABILITIES = ;"
	::= { nvmNacCacheEntry 3}

--
-- Parallel NAC Server Table
--

nvmNacServerTable OBJECT-TYPE
	SYNTAX	SEQUENCE OF NvmNacServerEntry
	ACCESS	not-accessible
	STATUS	mandatory
	DESCRIPTION
	  "NAME = ServerTable;
	   DESC = List of servers this unit can use to \
		  request address resolution from;
	   HELP = ;
	   CAPABILITIES = NET_CFG, VPN_CFG;"
	::= {nac-configuration 6}

nvmNacServerEntry OBJECT-TYPE
	SYNTAX	NvmNacServerEntry
	ACCESS	not-accessible
	STATUS	mandatory
	DESCRIPTION
	  "NAME = ServerEntry;
	   DESC = A server this unit can use to \
		  request address resolution from;
	   HELP = ;
	   CAPABILITIES = ;"
	INDEX		{nvmNacServerIpAddress}
	::= { nvmNacServerTable 1}

NvmNacServerEntry ::= SEQUENCE {
	nvmNacServerIpAddress			IpAddress,
	nvmNacServerName			DisplayString,
	nvmNacServerStatus			INTEGER,
	nvmNacServerHelloTime			INTEGER,
	nvmNacServerType 			INTEGER
	}

nvmNacServerIpAddress OBJECT-TYPE
	SYNTAX	IpAddress
	ACCESS	read-only
	STATUS	mandatory
	DESCRIPTION
	  "NAME = ServerIpAddress;
	   DESC = Network Address of server.;
	   HELP = It is unique to a given server and \
		  is used by this unit to communicate with the server.;
	   CAPABILITIES = ;"
	::= { nvmNacServerEntry 1}

nvmNacServerName OBJECT-TYPE
	SYNTAX	DisplayString (SIZE(1..50))
	ACCESS	read-only
	STATUS	mandatory
	DESCRIPTION
	  "NAME = ServerName;
	   DESC = A user supplied name of a server.;
	   HELP = ;
	   CAPABILITIES = ;"
	::= { nvmNacServerEntry 2}

nvmNacServerStatus OBJECT-TYPE
	SYNTAX	INTEGER {
		enable (1),
		disable (2)
		}
	ACCESS	read-only
	STATUS	mandatory
	DESCRIPTION
	  "NAME = ServerStatus;
	   DESC = Ability to enable, disable a server.;
	   HELP = A value of enable means this \
		  server will be used for address resolution \
                  A value of disable will refrain this \
		  unit from using the said server for address \
		  resolution. This may be done if the server is \
		  known to be temporarily out of service. \
		  This is the value this unit will \
		  use next time the unit is reset or rebooted;
	   CAPABILITIES = ;"
	::= { nvmNacServerEntry 3}

nvmNacServerHelloTime OBJECT-TYPE
	SYNTAX	INTEGER (30..180)
	ACCESS	read-only
	STATUS	mandatory
	DESCRIPTION
	  "NAME = HelloTimeInterval;
	   DESC = The interval of time in seconds between transmission \
		  of two consecutive Hello messages to the server.;
	   HELP = If the server does not see a HELLO message within \
		  a specified period it will purge it's database \
		  of all entries belonging to this unit. \
		  It is recommended that this value be such that \
		  this unit will transmit atleast two HELLO packets \
		  within the server's timeout period. \
		  Having a very low value will result in large \
		  number of HELLO packets, increasing traffic. \
		  The value should be tuned based on the IP traffic \
		  and the timeout value provisioned in the server. \
		  This is the value this unit will \
		  use next time the unit is reset or rebooted;
	   CAPABILITIES = ;"
	::= { nvmNacServerEntry 4}

nvmNacServerType OBJECT-TYPE
	SYNTAX	INTEGER {
		primary (1),
		secondary (2)
		}
	ACCESS	read-only
	STATUS	mandatory
	DESCRIPTION
	  "NAME = ServerType;
	   DESC = The NAS server type to which this information is assigned;
	   HELP = A primary Server is the preferred server which \
		  will be first consulted for address resolution. \
		  A secondary server is used as an alternative \
		  if the primary is not responding. \
		  All servers have to be marked secondary if \
		  round-robin load sharing is desired between servers.;
	   CAPABILITIES = ;"
	::= { nvmNacServerEntry 5}


-- NAC Statistics

nacStatisticsGroup    OBJECT IDENTIFIER ::= {nac-statistics 1}

nacStatisticsCacheCount OBJECT-TYPE
	SYNTAX	Counter
	ACCESS	read-only
	STATUS	mandatory
	DESCRIPTION
	  "NAME = StatCacheCount;
	   DESC = Total number of entries currently in cache. \
		  Includes learned and static entries. (Not \
		  cleared by nacCfgCounterZero); 
	   HELP = ;
	   CAPABILITIES = NET_CFG, VPN_CFG;"
	::= { nacStatisticsGroup 1}

nacStatisticsStaticCount OBJECT-TYPE
	SYNTAX	Counter
	ACCESS	read-only
	STATUS	mandatory
	DESCRIPTION
	  "NAME = StatStaticCount;
	   DESC = Number of static entries currently in cache. \
		  (Not cleared by nacCfgCounterZero);
	   HELP = ;
	   CAPABILITIES = NET_CFG, VPN_CFG;"
	::= { nacStatisticsGroup 2}

nacStatisticsRequestAllCount OBJECT-TYPE
	SYNTAX	Counter
	ACCESS	read-only
	STATUS	mandatory
	DESCRIPTION
	  "NAME = StatRequestAllCount;
	   DESC = Total DN-DNA requests received from voice;
	   HELP = ;
	   CAPABILITIES = NET_CFG, VPN_CFG;"
	::= { nacStatisticsGroup 3}

nacStatisticsLocalResolvedCount OBJECT-TYPE
	SYNTAX	Counter
	ACCESS	read-only
	STATUS	mandatory
	DESCRIPTION
	  "NAME = StatLocalResolvedCount;
	   DESC = Total DN-DNA requests resolved out of local cache;
	   HELP = ;
	   CAPABILITIES = NET_CFG, VPN_CFG;"
	::= { nacStatisticsGroup 4}

nacStatisticsPurgeCount OBJECT-TYPE
	SYNTAX	Counter
	ACCESS	read-only
	STATUS	mandatory
	DESCRIPTION
	  "NAME = StatPurgeCount;
	   DESC = Total purge requests received from voice;
	   HELP = ;
	   CAPABILITIES = NET_CFG, VPN_CFG;"
	::= { nacStatisticsGroup 5}

nacStatisticsVoiceRegCount OBJECT-TYPE
	SYNTAX	Counter
	ACCESS	read-only
	STATUS	mandatory
	DESCRIPTION
	  "NAME = StatVoiceRegCount;
	   DESC = Total re-register requests received from voice;
	   HELP = ;
	   CAPABILITIES = NET_CFG, VPN_CFG;"
	::= { nacStatisticsGroup 6}

nacStatisticsDNAChangeCount OBJECT-TYPE
	SYNTAX	Counter
	ACCESS	read-only
	STATUS	mandatory
	DESCRIPTION
	  "NAME = StatDNAChangeCount;
	   DESC = Total DNA changes (learnt or provisioned) \
		  received from driver;
	   HELP = ;
	   CAPABILITIES = NET_CFG, VPN_CFG;"
	::= { nacStatisticsGroup 7}

nacStatisticsServerCount OBJECT-TYPE
	SYNTAX	Counter
	ACCESS	read-only
	STATUS	mandatory
	DESCRIPTION
	  "NAME = StatServerCount;
	   DESC = Total number of servers configured to \
		  resolve addresses. (not cleared by \
		  nacCfgCounterZero);
	   HELP = ;
	   CAPABILITIES = NET_CFG, VPN_CFG;"
	::= { nacStatisticsGroup 8}

nacStatisticsServerRequestCount OBJECT-TYPE
	SYNTAX	Counter
	ACCESS	read-only
	STATUS	mandatory
	DESCRIPTION
	  "NAME = StatServerRequestCount;
	   DESC = Total DN-DNA requests made to all servers;
	   HELP = ;
	   CAPABILITIES = NET_CFG, VPN_CFG;"
	::= { nacStatisticsGroup 9}

nacStatisticsServerResolvedCount OBJECT-TYPE
	SYNTAX	Counter
	ACCESS	read-only
	STATUS	mandatory
	DESCRIPTION
	  "NAME = StatServerResolvedCount;
	   DESC = Total DN-DNA requests resolved by all servers;
	   HELP = ;
	   CAPABILITIES = NET_CFG, VPN_CFG;"
	::= { nacStatisticsGroup 10}

nacStatisticsServerNoNumberCount OBJECT-TYPE
	SYNTAX	Counter
	ACCESS	read-only
	STATUS	mandatory
	DESCRIPTION
	  "NAME = StatServerNoNumberCount;
	   DESC = Total DN-DNA requests resolved with phone \
		  number not found in server;
	   HELP = ;
	   CAPABILITIES = NET_CFG, VPN_CFG;"
	::= { nacStatisticsGroup 11}

nacStatisticsTimeoutCount OBJECT-TYPE
	SYNTAX	Counter
	ACCESS	read-only
	STATUS	mandatory
	DESCRIPTION
	  "NAME = StatTimeoutCount;
	   DESC = Total DN-DNA requests timed out;
	   HELP = ;
	   CAPABILITIES = NET_CFG, VPN_CFG;"
	::= { nacStatisticsGroup 12}

nacStatisticsHello1Count OBJECT-TYPE
	SYNTAX	Counter
	ACCESS	read-only
	STATUS	mandatory
	DESCRIPTION
	  "NAME = StatHello1Count;
	   DESC = Total hello keep alives to all servers;
	   HELP = ;
	   CAPABILITIES = NET_CFG, VPN_CFG;"
	::= { nacStatisticsGroup 13}

nacStatisticsHello2Count OBJECT-TYPE
	SYNTAX	Counter
	ACCESS	read-only
	STATUS	mandatory
	DESCRIPTION
	  "NAME = ;
	   DESC = Total hello, registration has changed, sent to\
		  all servers;
	   HELP = ;
	   CAPABILITIES = NET_CFG, VPN_CFG;"
	::= { nacStatisticsGroup 14}

nacStatisticsHello3Count OBJECT-TYPE
	SYNTAX	Counter
	ACCESS	read-only
	STATUS	mandatory
	DESCRIPTION
	  "NAME = ;
	   DESC = Total hello, are you there, sent to solicit \
		  response from all servers;
	   HELP = ;
	   CAPABILITIES = NET_CFG, VPN_CFG;"
	::= { nacStatisticsGroup 15}

nacStatisticsRegistrationCount OBJECT-TYPE
	SYNTAX	Counter
	ACCESS	read-only
	STATUS	mandatory
	DESCRIPTION
	  "NAME = ;
	   DESC = Total registration acknowledged count from all servers;
	   HELP = ;
	   CAPABILITIES = NET_CFG, VPN_CFG;"
	::= { nacStatisticsGroup 16}

-- Trap Messages

mcmAlarmNacFailedToLocateNAS TRAP-TYPE
	ENTERPRISE	micom-nac
	VARIABLES	{ mcmSysAsciiTimeOfDay}
	DESCRIPTION
	  "NAME = ServerUnreachable;
	   DESC = This unit is unable to communicate with the server\
		  Severity Level: MAJOR.;
	   HELP = The server could not be reached by this MPA. \
		  This could indicate a problem with the IP \
		  network, or the server is temporarily out-of-service. \
		  Or the remote unit may not be provisioned as \
		  a server. \
		  Doing a ping to the server will help determine \
		  reachability to it over the IP network;"
	::= 1

mcmAlarmNacNASIsDown TRAP-TYPE
	ENTERPRISE	micom-nac
	VARIABLES	{ mcmSysAsciiTimeOfDay, nacServerIpAddress }
	DESCRIPTION
	  "NAME = ServerCommunicationLost;
	   DESC = This unit is now unable to communicate with a \
		  previously available server.\
		  Severity Level: MAJOR.;
	   HELP = Communication is lost with a previously available server \
		  This could indicate a problem with the IP \
		  network, or the server is temporarily out-of-service. \
		  Hence it can no longer be used for address resolution. \
		  Doing a ping to the server will help determine \
		  reachability to it over the IP network. This MPA will \
		  periodically attempt to re-establish \
		  communication with the server;"
	::= 2

mcmAlarmNacNASIsUp TRAP-TYPE
	ENTERPRISE	micom-nac
	VARIABLES	{ mcmSysAsciiTimeOfDay, nacServerIpAddress }
	DESCRIPTION
	  "NAME = ServerCommunicationRestored;
	   DESC = This unit is now able to communicate with a \
		  server with which it had previously lost communication\
		  Severity Level: INFORMATIVE.;
	   HELP = Communication is restored with a previously 
		  non-responsive server. \
		  It will henceforth be used for address resolution.;"
	::= 3

-- End of Trap Messages

END
