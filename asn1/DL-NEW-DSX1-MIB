DL-NEW-DSX1-MIB 

DEFINITIONS ::= BEGIN
-- V1.19 6/17/00 Todd Zehler
 -- Added drop & insert and dte2 feature keys.
-- V1.18 1/25/00 Jim Holeman
 -- Changed object dlcUnitModelType to include DL4200 and DL5440
-- V1.17 10/07/99 Jerry Sugiarto
 -- Changed objects dlcDLCInumber, dlcDTECIR, and dlcNETCIR access to
 --   'read-only' in dlcDLCItable.
-- V1.16 08/27/99 Jerry Sugiarto
 -- Changed object name 'dlcLMINetworkPhysicalInterface' to 'dlcLMIUnitLocation'
-- V1.15 06/21/99 Jerry Sugiarto
 -- Took out the range from dlcUniRam, dlcUnitRom and dlcUnitFlash.
 -- Added more description in dlcLinkTestState and dlcDelayMonitorState.
 -- Changed the value assignments on object dlcDLCIStatus
-- V1.14 06/10/99 Jerry Sugiarto
 -- Added LMI objects..
-- V1.13 04/30/99 Jerry Sugiarto
 -- Added configurations for Ethernet port.
-- V1.12 12/17/98 James Holeman
 -- new dlci table mib object
 -- new unit type for solo select
 -- move some function definitions to control.mib
 -- Added "Ethernet" option for dlcSnmpTrapDirection, dlcLinkTestPort,
 -- and dlcDelayMonitorPort.
 --
-- V1.11 01/22/98 Jerry Sugiarto
 -- Added Link based and Delay monitor tests objects.
 -- Added IPM related objects and changed Inband Mode object.
 --
-- V1.10 11/04/97 James Holeman
 -- One new item added dclRemoteCommunicationsMode (dlcUnitConfig 32)
 --
-- V1.9 07/11/97 Dana Polyak
 -- For Solo E1 VTRD
 --
 -- DLC Part Number 076-01901-01
-- V1.8 04/06/97 Shubha Ramachandrappa
 -- Two new items were added dialOuTimeInterval, FramedUnframed
 --
-- V1.7 02/25/97 Hao Zheng
 -- For Solo T1 Inband Management.
 --
-- V1.6 09/15/96 Shubha Ramachandrappa
 -- Contains Orion mib items + unstructured item for E1
 -- This mib is the Latest mib with all kind of merges.
 -- Hope the MIB versions will be sequential and no 
 -- Parallel MIB verions grow ...;(((
 --
 -- 960924 jho
 -- updated commentary to call out E1- and CSU-specific objects
 -- & describe operation of some mis-placed objects
 --
 -- There were two V1.5 mibs.. One for T1 and one for E1.
 -- V1.5 MIB T1 - based from V1.2 MIB  later added orion mib items.
 -- V1.6 LATEST MIB
-- V1.5 MIB E1 - based from V1.4 MIB - later added unstructured.
 -- V1.5 06/28/96 Hao Zheng
 --
 -- THIS VERSION OF THE MIB
 -- IS COMPATIBLE WITH ECLIPSE SOFTWARE REVISIONS
 -- 1.2 (SOLO E1), 3.0 (VX FAMILY), 2.0 (ENSEMBLE FAMILY) AND EARLIER.
 --
-- V1.4 03/04/96 Hao Zheng
 --
 -- THIS VERSION OF THE MIB
 -- IS COMPATIBLE WITH ECLIPSE SOFTWARE REVISIONS
 -- 3.0 (VX FAMILY), 2.0 (ENSEMBLE FAMILY) AND EARLIER.
 --

-- V1.3 01/18/95 John Olney
 --
 -- THIS VERSION OF THE MIB
 -- IS COMPATIBLE WITH ECLIPSE SOFTWARE REVISIONS
 -- 2.8 (VX FAMILY), 1.5 (ENSEMBLE FAMILY) AND EARLIER.
 --
 -- The rev is bumped because the old MIB had errors
 -- when compiled with Epilogue Technology's Emissary SNMP MIB Compiler,
 -- version 4.0.
 --
-- V1.2 11/14/95 Hao Zheng
 --
 -- THIS VERSION OF THE MIB
 -- IS COMPATIBLE WITH ECLIPSE SOFTWARE REVISIONS
 -- 2.8 (VX FAMILY), 1.5 (ENSEMBLE FAMILY) AND EARLIER.
 --
-- V1.1 3/25/95 Bharat Mota 
 --
 -- THIS VERSION OF THE MIB
 -- IS COMPATIBLE WITH ECLIPSE SOFTWARE REVISIONS 
 -- 2.6 (VX FAMILY), 1.1 (ENSEMBLE FAMILY) AND EARLIER.
 --
-- V1.0  12/28/94 Bharat Mota 
 --
 -- THIS VERSION OF THE MIB
 -- IS COMPATIBLE WITH ECLIPSE SOFTWARE REVISIONS 
 -- 2.6 (VX FAMILY), 1.0 (ENSEMBLE FAMILY) AND EARLIER.
 --
-- V0.10 11/2/93 John Olney
 --
 -- THIS VERSION OF THE MIB
 -- IS COMPATIBLE WITH ECLIPSE SOFTWARE REV 2.04
 --
-- V0.9  10/26/93 John Olney
 --
 -- THIS VERSION OF THE MIB
 -- IS COMPATIBLE WITH ECLIPSE SOFTWARE REV 2.03
 --
-- V0.8  8/27/93 John Olney
-- V0.7  8/26/93 John Olney
-- V0.6  8/4/93 John Olney
-- V0.5  8/3/93 John Olney
-- V0.4  6/29/93  Josh Sakov
-- This MIB has not been officially released to the N.I.C.

IMPORTS
 enterprises, IpAddress, Counter, Gauge FROM RFC1155-SMI
 DisplayString FROM RFC1213-MIB
 OBJECT-TYPE FROM RFC-1212
 TRAP-TYPE FROM RFC-1215;

-- All representations of MAC addresses in this MIB Module use,
-- as a textual convention (i.e., this convention does not affect
-- their encoding), the data type:

MacAddress ::= OCTET STRING (SIZE (6))    -- a 6 octet address in
                                             -- the "canonical" order


digital-link OBJECT IDENTIFIER ::= { enterprises 300 }
dl-new-t1 OBJECT IDENTIFIER ::= { digital-link 200 }

-- ****************************************************************************
-- ****************************************************************************
-- ****************************************************************************
-- ****************************************************************************
--
-- New types defined in this MIB
--

-- Boolean is ... well, it should be obvious.
--
Boolean ::= INTEGER {
  true (1),
  false (2)
 }

-- PortId identifies a port on the unit.
-- PortId can be a network port or a DTE port.
-- `ext-clock' isn't really a "port", but it's handy to include it here
-- so we can use a PortId to describe the unit clock source.
-- Likewise for `int-clock'.
--
PortId ::= INTEGER {
  mainNet  ( 1),
  aux  ( 2),
  otherNet ( 3),
  reserved1 ( 4),
  reserved2 ( 5),
  reserved3 ( 6),
  ethPort  ( 7),
  commPort ( 8),
  int-clock ( 9),
  ext-clock (10),
  data1  (11),
  data2  (12),
  data3  (13),
  data4  (14),
  data5  (15),
  data6  (16),
  data7  (17),
  data8  (18),
  data9  (19),
  data10  (20),
  data11  (21),
  data12  (22),
  data13  (23),
  data14  (24),
  data15  (25),
  data16  (26),
  data17  (27),
  data18  (28),
  data19  (29),
  data20  (30),
  data21  (31),
  data22  (32),
  data23  (33),
  data24  (34),
  data25  (35),
  data26  (36),
  data27  (37),
  data28  (38),
  data29  (39),
  data30  (40),
  data31  (41),
  data32  (42),
  noPort  (43)
 } 

-- AlarmType identifies one of the generic types of alarms
-- that an Eclipse might raise.
-- An AlarmType must be further qualified with a PortId
-- to know what's really going on in the unit.
--
AlarmType ::= INTEGER {
  lostSignal  ( 1),
  lostSync  ( 2),
  detectedYellow  ( 3),
  detectedAIS  ( 4),
  detectedExternalAlarm ( 5),
  exceededBpvThreshold ( 6),
  exceededOofThreshold ( 7),
  exceededCrcThreshold ( 8),
  remoteAlarmBitSet ( 9),
  detectedPSfailure (10),
  detectedCntlCardMissing (11),
  lostDlcFdlLink (12),
  exceededIbCrcThreshold (13),
  lostDlcInbandLink  (14),
  lmiSpoofing (15)
 } 

-- TestType identifies one of the many sorts of tests
-- that can be run on an Eclipse.
--
TestType ::= INTEGER {
  noTest   ( 1),
  selfTest  ( 2),
  netLoopback  ( 3),
  payloadLoopback  ( 4),
  dteLoopback  ( 5),
  loopUpRemote  ( 6),
  loopDownRemote  ( 7),
  sendQrwPattern  ( 8),
  send1in8Pattern  ( 9),
  send1in1Pattern  (10),
  send1in3Pattern  (11),
  send1in5Pattern  (12),
  send2in3Pattern  (14),
  send4in5Pattern  (15),
  send3in24Pattern (16),
  sendAllOnePattern (17),
  sendAllZeroPattern (18),
  sendUser1Pattern (19),
  sendUser2Pattern (20),
  sendSmartJackSet (21),
  sendSmartJackReset (22),
  sendAPatternError (23),
  dteNetLoopback  (24),
  reserved1  (25),
  reserved2  (26),
  reserved3  (27),
  reserved4  (28),
  reserved5  (29),
  reserved6  (30),
  lampTest  (31)
 } 

-- ****************************************************************************
-- ****************************************************************************
-- ****************************************************************************
-- ****************************************************************************
--
-- Unit Configuration Group
--

-- ============================================================================
--
-- The following variables describe the (not-user-settable) configuration
-- of the unit: its type, number of ports, etc.
--
dlcUnitHwConfig OBJECT IDENTIFIER ::= { dl-new-t1 1 }

 dlcUnitModelType OBJECT-TYPE
  SYNTAX INTEGER {
   vxEncore         ( 1),
   dl100Encore      ( 2),
   dl1200           ( 3),
   dl2400           ( 4),
   dl600            ( 5),
   dl600Encore      ( 6),
   ensembleEncore   ( 7),
   soloEncore       ( 8),
   soloE1Encore     ( 9),
   ensembleE1Encore (10),
   soloT1CSU        (11),
   ensembleT1CSU    (12),
   soloSelectT1Module (13),
   soloSelectE1Module (14),
   soloSelectT1     (15),
   soloSelectE1     (16),
   dl4200T1         (17),
   dl4200E1         (18),
   dl5440T1         (19),
   dl5440E1         (20)
  }
  ACCESS read-only
  STATUS mandatory
  DESCRIPTION
   "The unit model type."
  --DEFAULT test-function it_exists
  ::= { dlcUnitHwConfig 1 }


 dlcUnitHwRev OBJECT-TYPE
  SYNTAX DisplayString (SIZE (1..4))
  ACCESS read-only
  STATUS mandatory
  DESCRIPTION
   "The ASCII code of the hardware revision number."
  --DEFAULT test-function it_exists
  ::= { dlcUnitHwConfig 2 }


 dlcUnitHwOptions OBJECT-TYPE
  SYNTAX INTEGER ( 0..1023 )
  ACCESS read-only
  STATUS mandatory
  DESCRIPTION
   "A bit map, reported as the sum of all the values that
   correspond to installed options:
    realTimeClock  (  1)
    netPortT1  (  2)
    netPortE1  (  4)
    auxPortT1  (  8)
    auxPortE1  ( 16)
    otherNetT1  ( 32)
    otherNetE1  ( 64)
    reserved1   (128)
    reserved2   (256)
    reserved3   (512)

   `netPortT1' and `netPortE1' are mutually exclusive
   and one of the two will always be TRUE.
   `auxPortT1' and `auxPortE1' are mutually exclusive;
   if both are FALSE, there is no AUX port present.
   `otherNetT1' and `otherNetE1' are mutually exclusive;
   if both are FALSE, there is no CSU port present.
   "
  --DEFAULT test-function it_exists
  ::= { dlcUnitHwConfig 3 }


 dlcUnitSwRev OBJECT-TYPE
  SYNTAX DisplayString (SIZE (1..4))
  ACCESS read-only
  STATUS mandatory
  DESCRIPTION
   "The ASCII code of the software revision number."
  --DEFAULT test-function it_exists
  --DEFAULT get-function get_string
  --DEFAULT cookie  (char *)EclipseSwRev
  ::= { dlcUnitHwConfig 4 }


 dlcUnitDataPorts OBJECT-TYPE
  SYNTAX INTEGER (1..32)
  ACCESS read-only
  STATUS mandatory
  DESCRIPTION
   "The number of data ports installed on the unit."
  --DEFAULT test-function it_exists
  ::= { dlcUnitHwConfig 5 }

 dlcUnitRam OBJECT-TYPE
  SYNTAX INTEGER
  ACCESS read-only
  STATUS mandatory
  DESCRIPTION
   "The amount of usable ram in the unit,
   in KBytes."
  --DEFAULT test-function it_exists
  --DEFAULT get-function get_u16_supplier
  --DEFAULT cookie  (char *)&GDB.Hw.ext_1.config.ramSize
  ::= { dlcUnitHwConfig 6 }

 dlcUnitRom OBJECT-TYPE
  SYNTAX INTEGER
  ACCESS read-only
  STATUS mandatory
  DESCRIPTION
   "The amount of usable rom in the unit,
   in KBytes."
  --DEFAULT test-function it_exists
  --DEFAULT get-function get_u16_supplier
  --DEFAULT cookie  (char *)&GDB.Hw.ext_1.config.romSize
  ::= { dlcUnitHwConfig 7 }

 dlcUnitFlash OBJECT-TYPE
  SYNTAX INTEGER
  ACCESS read-only
  STATUS mandatory
  DESCRIPTION
   "The amount of FLASH ROM in the unit, in KBytes.
   If dlcUnitFlash is 0, the Downloadable Code option
   is not installed."
  --DEFAULT test-function it_exists
  --DEFAULT get-function get_u16_supplier
  --DEFAULT cookie  (char *)&GDB.Hw.ext_1.config.flashSize
  ::= { dlcUnitHwConfig 8 }


 dlcUnitSlotNum OBJECT-TYPE
  SYNTAX INTEGER (0..16)
  ACCESS read-only
  STATUS mandatory
  DESCRIPTION
   "The slot number the unit is in. If it's a stand alone unit,
    this object will return 0."
  --DEFAULT get-function get_u8_supplier
  --DEFAULT cookie (char *)&GDB.Hw.ext_3.config.SlotNum
  ::= { dlcUnitHwConfig 9 }


 dlcUnitMibRev OBJECT-TYPE
  SYNTAX DisplayString (SIZE (1..4))
  ACCESS read-only
  STATUS mandatory
  DESCRIPTION
   "The ASCII code of the MIB revision number."
  --DEFAULT test-function it_exists
  --DEFAULT get-function get_string
  --DEFAULT cookie  (char *)EclipseMibRev
  ::= { dlcUnitHwConfig 10 }


 dlcUnitFeatures OBJECT-TYPE
  SYNTAX INTEGER {
   inband         (    1),
   ipm32          (    2),
   ipm96          (    4),
   rmon2          (    8),
   sla            (   16),
   dni            (   32),
   dte2           (   64),
   reserved4      (  128),
   reserved5      (  256),
   reserved6      (  512),
   reserved7      ( 1024),
   reserved8      ( 2048)
  }
  ACCESS read-only
  STATUS mandatory
  DESCRIPTION
   "Feature configuration for Solo Select. The value returned is a bit mask
    of which feature key is on/capable when the corresponding bit is 1."
  --DEFAULT test-function it_exists
  ::= { dlcUnitHwConfig 11 }


-- ============================================================================
--
-- Following are the user-settable configuration items
-- that affect the unit as a whole
-- (vs. configuration items that are specific to a port).
--
dlcUnitConfig OBJECT IDENTIFIER ::= { dl-new-t1 2 }

 dlcUnitId OBJECT-TYPE
  SYNTAX DisplayString (SIZE (1..6))
  ACCESS read-write
  STATUS mandatory
  DESCRIPTION
   "A name that uniquely and globally identifies the unit.
   The Unit ID must consist of (upper-case) letters 'A'..'Z'
   and digits '0'..'9'.
   The first character of the Unit ID may not be a digit."
  --DEFAULT get-function get_string_supplier
  --DEFAULT cookie  (char *)&GDB.Dbms.config.unit.id
  ::= { dlcUnitConfig 1 }

 dlcUnitProtectMode OBJECT-TYPE
  SYNTAX Boolean
  ACCESS read-write
  STATUS mandatory
  DESCRIPTION
   "When true, the unit configuration
   can not be changed from the front panel
   nor can tests be initiated or terminated
   from the front panel."
  --DEFAULT test-function test_bool_supplier
  --DEFAULT get-function get_bool_supplier
  --DEFAULT cookie  (char *)&GDB.Dbms.config.unit.protect
  ::= { dlcUnitConfig 2 }

 dlcUnitYellowEnable OBJECT-TYPE
  SYNTAX Boolean
  ACCESS read-write
  STATUS mandatory
  DESCRIPTION
   "When false, yellow alarm conditions are ignored
   when received from a Dsx1 port,
   and the unit will never transmit a Yellow Alarm signal
   on a Dsx1 port.
   This applies to all ports: mainNet, aux, otherNet."
  --DEFAULT get-function get_bool_supplier
  --DEFAULT cookie  (char *)&GDB.Dbms.config.unit.yellowAlarm
  ::= { dlcUnitConfig 3 }

 dlcUnitNetPassFdl OBJECT-TYPE
  SYNTAX PortId
  ACCESS read-write
  STATUS mandatory
  DESCRIPTION
   "Indicates which Dsx1 DTE port's FDL
   is connected to the `mainNet' FDL
   when this unit has no traffic of its own.
   Meaninigful values are `aux', `otherNet', and `noPort'."
  ::= { dlcUnitConfig 4 }


-- -----------------------------------------------------------------------------
--
-- Configuration items for determining where a unit derives its timing.
--
 dlcUnitMainClockSource OBJECT-TYPE
  SYNTAX PortId 
  ACCESS read-write
  STATUS mandatory
  DESCRIPTION
   "This is the primary transmit timing source."
  --DEFAULT test-function test_clockSource_supplier
  --DEFAULT get-function get_clockSource_supplier
  --DEFAULT cookie (char *)&GDB.Dbms.config.unit.clock.main
  ::= { dlcUnitConfig 5 }

 dlcUnitAltClockSource OBJECT-TYPE
  SYNTAX PortId 
  ACCESS read-write
  STATUS mandatory
  DESCRIPTION
   "This is the alternate transmit timing source.
   It is used when the primary source is not available."
  --DEFAULT test-function test_clockSource_supplier
  --DEFAULT get-function get_clockSource_supplier
  --DEFAULT cookie (char *)&GDB.Dbms.config.unit.clock.backup
  ::= { dlcUnitConfig 6 }

 dlcUnitExtClockRate OBJECT-TYPE
  SYNTAX INTEGER (56..2048)
  ACCESS read-write
  STATUS mandatory
  DESCRIPTION
   "The signal arriving at the BNC connector
   on the back of the unit, in units of KHz.
   Must be a multiple of 56 or 64 KHz (n*56 or n*64)
   or 1544.

   For T1 units, the largest acceptable value is 1544.
   For E1 units, the value can go up to 2048.

   For Solo CSU products, the value is fixed at 1544
   and cannot be changed."
  --DEFAULT test-function test_u16_supplier
  --DEFAULT get-function get_u16_supplier
  --DEFAULT cookie (char *)&GDB.Dbms.config.unit.clock.extRate
  ::= { dlcUnitConfig 7 }

-- ----------------------------------------------------------------------------
--
-- Configuration items that control how and when the unit performs diagnostics
--
 LoopCodeType ::= INTEGER {
   standard (1),
   alternate (2),
   v54  (3),
   reserved1 (4),
   reserved2 (5),
   reserved3 (6),
   disable  (7)
  }

 dlcUnitFullBandwidthLoopCode OBJECT-TYPE
  SYNTAX LoopCodeType
  ACCESS read-write
  STATUS mandatory
  DESCRIPTION
   "Determines the loop codes we transmit for the
   Full Bandwidth Loop Up Remote and Loop Down Remote tests
   and the code we respond to
   when it's received on the NET port.
   For the fullBandwidthLoopCode,
   `v54' is an invalid value."
  --DEFAULT test-function test_loopCode_supplier
  --DEFAULT get-function get_loopCode_supplier
  --DEFAULT cookie (char *)&GDB.Dbms.config.unit.loopCode
  ::= { dlcUnitConfig 8 }

 dlcUnitFractionalLoopCode OBJECT-TYPE
  SYNTAX LoopCodeType
  ACCESS read-write
  STATUS mandatory
  DESCRIPTION
   "Determines the loop codes we transmit for the
   Fractional Loop Up Remote and Loop Down Remote tests
   and the code we respond to
   when it's received on fractional bandwidth."
  --DEFAULT test-function test_loopCode_supplier
  --DEFAULT get-function get_loopCode_supplier
  --DEFAULT cookie (char *)&GDB.Dbms.config.unit.fracLoopCode
  ::= { dlcUnitConfig 9 }

 dlcUnitTestLength OBJECT-TYPE
  SYNTAX INTEGER
  ACCESS read-write
  STATUS mandatory
  DESCRIPTION
   "Determines the time interval after which
   tests are automatically terminated.
   Valid values are 0, 1, 15 and 60.
    0 stands for unlimited,
    1 for 1 minute,
    15 for 15 minutes
    and 60 for 60 minutes."
  ::= { dlcUnitConfig 10 }

 dlcUnitUserPattern1 OBJECT-TYPE
  SYNTAX DisplayString (SIZE (0..24))
  ACCESS read-write
  STATUS mandatory
  DESCRIPTION
   "This is a sequence of the characters '0' and '1'
   that represents the first of two user patterns.
   The first character represents the first
   bit in the sequence."
  --DEFAULT test-function test_userTestPattern_supplier
  --DEFAULT get-function get_userTestPattern_supplier
  --DEFAULT cookie (char *)&GDB.Dbms.config.diag.pattern[0]
  ::= { dlcUnitConfig 11 }

 dlcUnitUserPattern2 OBJECT-TYPE
  SYNTAX DisplayString (SIZE (0..24))
  ACCESS read-write
  STATUS mandatory
  DESCRIPTION
   "This is a sequence of the characters '0' and '1'
   that represents the second of two user patterns.
   The first character represents the first
   bit in the sequence."
  --DEFAULT test-function test_userTestPattern_supplier
  --DEFAULT get-function get_userTestPattern_supplier
  --DEFAULT cookie (char *)&GDB.Dbms.config.diag.pattern[1]
  ::= { dlcUnitConfig 12 }

-- ----------------------------------------------------------------------------
--
-- Configuration items controlling what alarms we report
-- and when we report them.
--
 dlcUnitBlockAllAlarms OBJECT-TYPE
  SYNTAX Boolean 
  ACCESS read-write
  STATUS mandatory
  DESCRIPTION
   "When dlcUnitBlockAllAlarms is TRUE,
   the unit will never send any traps."
  --DEFAULT test-function test_bool_supplier
  --DEFAULT get-function get_bool_supplier
  --DEFAULT cookie (char *)&GDB.Dbms.config.alarm.unit.blockAllAlarms
  ::= { dlcUnitConfig 13 }

 dlcUnitDsx1TrapEnableTable OBJECT-TYPE
  SYNTAX SEQUENCE OF DlcDsx1TrapEnableEntry
  ACCESS not-accessible
  STATUS mandatory
  DESCRIPTION
   "A list of traps that are related to a Dsx1 port."
  --DEFAULT test-function test_dlcDsx1AlarmTrapEnable
  --DEFAULT get-function get_dlcDsx1AlarmTrapEnable
  --DEFAULT next-function next_dlcDsx1Table
  ::= { dlcUnitConfig 14 }

 dlcDsx1TrapEnableEntry OBJECT-TYPE
  SYNTAX DlcDsx1TrapEnableEntry
  ACCESS not-accessible
  STATUS mandatory
  DESCRIPTION
   "An entry in the Dsx1 Trap Enable table."
  INDEX { dlcDsx1TrapPortId }
  ::= { dlcUnitDsx1TrapEnableTable 1 }

 DlcDsx1TrapEnableEntry ::=
  SEQUENCE {
   dlcDsx1TrapPortId                    PortId,
   dlcDsx1BpvThresholdTrap              INTEGER,
   dlcDsx1OofThresholdTrap              INTEGER,
   dlcDsx1CrcThresholdTrap              INTEGER,
   dlcDsx1LossOfSignalTrapEnable        Boolean,
   dlcDsx1LossOfSyncTrapEnable          Boolean,
   dlcDsx1ReceiveAIStrapEnable          Boolean,
   dlcDsx1ReceiveYellowAlarmTrapEnable  Boolean,
   dlcDsx1ReceiveRemoteAlarmTrapEnable  Boolean,
   dlcDsx1PSfailureTrapEnable           Boolean,
   dlcDsx1CntlCrdMissingTrapEnable      Boolean,
   dlcDsx1FdlLinkTrapEnable             Boolean,
   dlcDsx1IbCrcThresholdTrap            INTEGER,
   dlcDsx1InbandLinkTrapEnable          Boolean
  }

  dlcDsx1TrapPortId OBJECT-TYPE
   SYNTAX PortId
   ACCESS read-only
   STATUS mandatory
   DESCRIPTION
    "Uniquely identifies this port.
    Valid values are `mainNet', `aux', `otherNet'."
   --DEFAULT test-function test_%n
   --DEFAULT get-function get_compl_0
   ::= { dlcDsx1TrapEnableEntry 1 }

  dlcDsx1BpvThresholdTrap OBJECT-TYPE
   SYNTAX INTEGER ( 0..99 ) 
   ACCESS read-write
   STATUS mandatory
   DESCRIPTION
    "Defines Bipolar Violation Error Rate threshold
    in units of BPV errors per minute.
    When this threshold is exceeded,
    the unit will send a trap to the SNMP manager.
    The threshold is of the form M x 10 ^ -E
    where M is a mantissa and E the exponent.
    Both are single digit values.
    M and E are represented in this value
    as one number:
     (M) x 10 + (E).
    For example, the threshold 7x10^-3 BPVs/min
    is encoded as the integer 73.
    A value of 0 disables the trap altogether.

    Valid values for dlcDsx1BpvThresholdTrap are:
        13 23 33 43 53 63
        14 24 34 44 54 64 74 84 94
        15 25 35 45 55 65 75 85 95
        16 26 36 46 56 66 76 86 96
        17 27 37 47 57 67 77 87 97
           28 38 48 58 68 78 88 98
    or, from 6E-3 to 2E-8.

    N.B. The BPV Threshold Alarm exists only for
    the mainNet and otherNet Port IDs,
    so setting the Threshold for the aux PortId
    will always fail.
    The BPV Threshold is always reported as 0
    for the aux PortId."
   --DEFAULT test-function test_dlcDsx1ThresholdTrap
   --DEFAULT get-function get_dlcDsx1ThresholdTrap
   ::= { dlcDsx1TrapEnableEntry 2 }

  dlcDsx1OofThresholdTrap OBJECT-TYPE
   SYNTAX INTEGER ( 0..99 )
   ACCESS read-write
   STATUS mandatory
   DESCRIPTION
    "Defines the Out Of Frame Error Rate threshold
    in units of OOF errors per minute.
    The threshold is encoded
    the same as dlcDsx1BpvThresholdTrap.
    A value of 0 disables the trap altogether.

    Valid values for dlcDsx1OofThresholdTap are:
        12 22 22 42 52 62 72
        13 23 33 43 53 63 73 83 93
        14 24 34 44 54 64 74 84 94
        15 25 35 45 55 65 75 85 95
              36 46 56 66 76 86 96
    or, from 7E-2 to 3E-6.

    N.B. The OOF Threshold Alarm exists only for
    the mainNet and otherNet Port IDs,
    so setting the Threshold for the aux PortId
    will always fail.
    The OOF Threshold is always reported as 0
    for the aux PortId."
   --DEFAULT test-function test_dlcDsx1ThresholdTrap
   --DEFAULT get-function get_dlcDsx1ThresholdTrap
   ::= { dlcDsx1TrapEnableEntry 3 }

  dlcDsx1CrcThresholdTrap OBJECT-TYPE
   SYNTAX INTEGER ( 0..99 )
   ACCESS read-write
   STATUS mandatory
   DESCRIPTION
    "Defines the CRC-6 Error Rate threshold
    in units of CRC errors per minute.
    The threshold is encoded
    the same as dlcDsx1BpvThresholdTrap.
    A value of 0 disables the trap altogether.

    Valid values for dlcDsx1CrcThresholdTrap are:
        10
        11 21 31 41 51 61 71 81 91
        12 22 32 42 52 62 72 82 92
        13 23 33 43 53 63 73 83 93
        14 24 34 44 54 64 74 84 94
                    55 65 75 85 95
    or, from 1E0 to 5E-5.

    N.B. The CRC Threshold Alarm exists only for
    the mainNet and otherNet Port IDs,
    so setting the Threshold for the aux PortId
    will always fail.
    The CRC Threshold is always reported as 0
    for the aux PortId."
   --DEFAULT test-function test_dlcDsx1ThresholdTrap
   --DEFAULT get-function get_dlcDsx1ThresholdTrap
   ::= { dlcDsx1TrapEnableEntry 4 }

  dlcDsx1LossOfSignalTrapEnable OBJECT-TYPE
   SYNTAX Boolean
   ACCESS read-write
   STATUS mandatory
   DESCRIPTION
    "Enables or disables a trap
    upon loss of network signal (LOS)
    on a Dsx1 port."
   ::= { dlcDsx1TrapEnableEntry 5 }

  dlcDsx1LossOfSyncTrapEnable OBJECT-TYPE
   SYNTAX Boolean
   ACCESS read-write
   STATUS mandatory
   DESCRIPTION
    "Enables or disables a trap
    upon loss of network framing (LOF)
    on a Dsx1 port."
   ::= { dlcDsx1TrapEnableEntry 6 }

  dlcDsx1ReceiveAIStrapEnable OBJECT-TYPE
   SYNTAX Boolean
   ACCESS read-write
   STATUS mandatory
   DESCRIPTION
    "Enables or disables a trap
    upon detection of AIS (Blue Alarm Signal)
    on a Dsx1 port."
   ::= { dlcDsx1TrapEnableEntry 7 }

  dlcDsx1ReceiveYellowAlarmTrapEnable OBJECT-TYPE
   SYNTAX Boolean
   ACCESS read-write
   STATUS mandatory
   DESCRIPTION
    "Enables or disables a trap
    upon detection of Yellow Alarm Signal
    on a Dsx1 port."
   ::= { dlcDsx1TrapEnableEntry 8 }

  dlcDsx1ReceiveRemoteAlarmTrapEnable OBJECT-TYPE
   SYNTAX Boolean
   ACCESS read-write
   STATUS mandatory
   DESCRIPTION
    "Enables or disables a trap
    upon detection of Remote Alarm Indicator
    on an E1 Dsx1 port.

    For T1 units, this object's value
    will always be read as 0
    and set operations will succeed,
    but the value will not be changed."
   --DEFAULT test-function test_%n
   ::= { dlcDsx1TrapEnableEntry 9 }

  dlcDsx1PSfailureTrapEnable OBJECT-TYPE
   SYNTAX Boolean
   ACCESS read-write
   STATUS mandatory
   DESCRIPTION
    "Enables or disables a trap
    upon a power supply failure.

    This object doesn't really belong
    in the dlcDsx1TrapEnableTable.
    It is specific to units
    that are installed in a shelf.
    When accessing this object,
    the index (portId) is ignored."
   ::= { dlcDsx1TrapEnableEntry 10 }

  dlcDsx1CntlCrdMissingTrapEnable OBJECT-TYPE
   SYNTAX Boolean
   ACCESS read-write
   STATUS mandatory
   DESCRIPTION
    "Enables or disables a trap
    upon detection of a missing 
    controller card.

    This object doesn't really belong
    in the dlcDsx1TrapEnableTable.
    It is specific to units
    that are installed in a shelf.
    When accessing this object,
    the index (portId) is ignored."
   ::= { dlcDsx1TrapEnableEntry 11 }

  dlcDsx1FdlLinkTrapEnable OBJECT-TYPE
   SYNTAX Boolean
   ACCESS read-write
   STATUS mandatory
   DESCRIPTION
    "Enables or disables a trap
    upon detection of the remote unit is 
    not responding to DLC FDL messages."
   ::= { dlcDsx1TrapEnableEntry 12 }

 dlcDsx1IbCrcThresholdTrap OBJECT-TYPE
  SYNTAX INTEGER ( 0..99 )
  ACCESS read-write
  STATUS mandatory
  DESCRIPTION
   "Defines the In-Band CRC Error Rate threshold
   in units of CRC errors per minute.
   The threshold is encoded
   the same as dlcDsx1BpvThresholdTrap.
   A value of 0 disables the trap altogether.
   For the Eclipse, valid values of
   dlcDsx1IbCrcThresholdTrap range from 47 to 91.
   N.B. The CRC Threshold Alarm exists only for
   the mainNet port."
  --DEFAULT test-function	test_dlcDsx1ThresholdTrap
  --DEFAULT get-function	get_dlcDsx1ThresholdTrap
  ::= { dlcDsx1TrapEnableEntry 13 }

  dlcDsx1InbandLinkTrapEnable OBJECT-TYPE
   SYNTAX Boolean
   ACCESS read-write
   STATUS mandatory
   DESCRIPTION
    "Enables or disables a trap
    upon detection of the inband link."
   ::= { dlcDsx1TrapEnableEntry 14 }

 dlcUnitDataDteLossTrapEnableTable OBJECT-TYPE
  SYNTAX SEQUENCE OF DlcDataDteLossTrapEnableEntry
  ACCESS not-accessible
  STATUS mandatory
  DESCRIPTION
   "Enables or disables a trap
   upon the loss of signal on a Data DTE port."
  --DEFAULT next-function next_dlcDataTable 
  ::= { dlcUnitConfig 15 }

 dlcDataDteLossTrapEnableEntry OBJECT-TYPE
  SYNTAX DlcDataDteLossTrapEnableEntry
  ACCESS not-accessible
  STATUS mandatory
  DESCRIPTION
   "An entry in the Data DTE Loss Trap Enable table."
  INDEX { dlcDataLossPortId }
  ::= { dlcUnitDataDteLossTrapEnableTable 1 }

 DlcDataDteLossTrapEnableEntry ::=
  SEQUENCE {
   dlcDataLossPortId PortId,
   dlcDataLossEnable Boolean
  }


  dlcDataLossPortId OBJECT-TYPE
   SYNTAX PortId
   ACCESS read-only
   STATUS mandatory
   DESCRIPTION
    "Uniquely identifies this port.
    Valid values are `data1' through `data32'."
   --DEFAULT get-function get_compl_0
   ::= { dlcDataDteLossTrapEnableEntry 1 }

  dlcDataLossEnable OBJECT-TYPE
   SYNTAX Boolean
   ACCESS read-write
   STATUS mandatory
   DESCRIPTION
    "Says whether to enable this trap."
   ::= { dlcDataDteLossTrapEnableEntry 2 }

 dlcUnitExternalAlarmInputTrapEnable OBJECT-TYPE
  SYNTAX Boolean
  ACCESS read-write
  STATUS mandatory
  DESCRIPTION
   "Enables or disables a trap
   upon detection of an alarm condition
   on the External Alarm Input."
  --DEFAULT get-function get_bool_supplier
  --DEFAULT cookie (char *)&GDB.Dbms.config.alarm.external.enableInput
  ::= { dlcUnitConfig 16 }

 dlcUnitExternalAlarmInputContacts OBJECT-TYPE
  SYNTAX INTEGER {
   normallyOpen (1),
   normallyClosed (2)
  }
  ACCESS read-write
  STATUS mandatory
  DESCRIPTION
   "When set to normallyOpen, an alarm is declared
   when the contacts close ... and vice-versa."
  ::= { dlcUnitConfig 17 }

 dlcUnitExternalAlarmInputMessage OBJECT-TYPE
  SYNTAX DisplayString (SIZE (0..20))
  ACCESS read-write
  STATUS mandatory
  DESCRIPTION
   "A character string that describes what's going on
   when an alarm on the External Alarm Input is detected."
  --DEFAULT get-function get_string_supplier
  --DEFAULT cookie (char *)&GDB.Dbms.config.alarm.external.msg
  ::= { dlcUnitConfig 18 }

 dlcUnitExternalAlarmOutputContacts OBJECT-TYPE
  SYNTAX INTEGER {
   normallyOpen (1),
   normallyClosed (2)
  }
  ACCESS read-write
  STATUS mandatory
  DESCRIPTION
   "When set to normallyOpen,
   the contacts close when any enabled alarm occurs
   and vice-versa.
   Pushing any button on the units Front Panel
   will cause the alarm contacts to open again
   until another alarm is recognized."
  ::= { dlcUnitConfig 19 }

 dlcUnitExternalAlarmOutputTrapEnable OBJECT-TYPE
  SYNTAX Boolean
  ACCESS read-write
  STATUS mandatory
  DESCRIPTION
   "Enables or disables the external alarm output contacts."
  --DEFAULT get-function get_bool_supplier
  --DEFAULT cookie (char *)&GDB.Dbms.config.alarm.external.enableOutput
  ::= { dlcUnitConfig 20 }

-- ============================================================================
--
-- Configuration items controlling the configuration and operation
-- of all our Dsx1 ports.
--

 dlcUnitDsx1ConfigTable OBJECT-TYPE
  SYNTAX SEQUENCE OF DlcDsx1ConfigEntry
  ACCESS not-accessible
  STATUS mandatory
  DESCRIPTION
   "A table of configuration items for a Dsx1 port."
  --DEFAULT next-function next_dlcDsx1Table 
  ::= { dlcUnitConfig 21 }

 dlcDsx1ConfigEntry OBJECT-TYPE
  SYNTAX DlcDsx1ConfigEntry
  ACCESS not-accessible
  STATUS mandatory
  DESCRIPTION
   "An entry in the Dsx1 configuration table."
  INDEX { dlcDsx1ConfigPortId }
  ::= { dlcUnitDsx1ConfigTable 1 }

 DlcDsx1ConfigEntry ::=
  SEQUENCE {
   dlcDsx1ConfigPortId  PortId,
   dlcDsx1Framing   INTEGER,
   dlcDsx1LineCode   INTEGER,
   dlcDsx1LineMatching  INTEGER,
   dlcDsx1DacsMode   Boolean,
   dlcDsx1UseDlcFdlProtocol Boolean,
   dlcDsx1UseAnsiProtocol  Boolean,
   dlcDsx1Bit7Stuffing  Boolean,
   dlcDsx1InBandBit  INTEGER
  }


  dlcDsx1ConfigPortId OBJECT-TYPE
   SYNTAX PortId
   ACCESS read-only
   STATUS mandatory
   DESCRIPTION
    "Uniquely identifies this port.
    Valid values are `mainNet', `aux', `otherNet'."
   --DEFAULT get-function get_compl_0
   ::= { dlcDsx1ConfigEntry 1 }

  dlcDsx1Framing OBJECT-TYPE
   SYNTAX INTEGER {
    esfFraming (1),
    d4Framing (2),
    crc4Enabled (3),
    crc4Disabled (4),
    unstructured (5)
   }
   ACCESS read-write
   STATUS mandatory
   DESCRIPTION
    "Dsx1 framing type:
    T1 --> D4 or ESF;
    E1 --> CRC4 or not.
    Unstructured is E1 only,
    when in this mode, the E1 line acts like
    a 2048 Bps pipe with no framing information."
   ::= { dlcDsx1ConfigEntry 2 }

  dlcDsx1LineCode OBJECT-TYPE
   SYNTAX INTEGER {
    b8zsCode (1),
    amiCode  (2),
    hdb3Code (3)
   }
   ACCESS read-write
   STATUS mandatory
   DESCRIPTION
    "Dsx1 line code type, AMI or B8ZS.
    E1 lines are always HDB3."
   ::= { dlcDsx1ConfigEntry 3 }

  dlcDsx1LineMatching OBJECT-TYPE
   SYNTAX INTEGER {
    buildOut0 ( 1),
    buildOut7p5 ( 2),
    buildOut15 ( 3),
    length0  ( 4),
    length133 ( 5),
    length266 ( 6),
    length399 ( 7),
    length533 ( 8),
    ohms75  ( 9),
    ohms120  (10)
   }
   ACCESS read-write
   STATUS mandatory
   DESCRIPTION
    "Dsx1 line build out or equalization:
    For a T1 NET port, LBO is 0, -7.5 or -15dB.
    For a T1 AUX port, EQ is 0..533 feet.
    For any E1 port, impedance is 75 or 120 Ohms."
   ::= { dlcDsx1ConfigEntry 4 }

  dlcDsx1DacsMode OBJECT-TYPE
   SYNTAX Boolean
   ACCESS read-write
   STATUS mandatory
   DESCRIPTION
    "True if DACS mode is in effect for this port."
   --DEFAULT get-function get_bool_supplier
   --DEFAULT cookie (char *)&GDB.Dbms.config.unit.dacsMode
   ::= { dlcDsx1ConfigEntry 5 }

  dlcDsx1UseDlcFdlProtocol OBJECT-TYPE
   SYNTAX Boolean
   ACCESS read-write
   STATUS mandatory
   DESCRIPTION
    "True when DLC FDL protocol is enabled
    over this port's FDL."
   ::= { dlcDsx1ConfigEntry 6 }

  dlcDsx1UseAnsiProtocol OBJECT-TYPE
   SYNTAX Boolean
   ACCESS read-write
   STATUS mandatory
   DESCRIPTION
    "True if ANSI Dsx1.403 is enabled over the FDL."
   ::= { dlcDsx1ConfigEntry 7 }

  dlcDsx1Bit7Stuffing OBJECT-TYPE
   SYNTAX Boolean
   ACCESS read-write
   STATUS mandatory
   DESCRIPTION
    "When true, bit 7 stuffing
    is turned on for a T1 Aux port
    to provide pulse density protection.
    Valid only on a T1 AUX port."
   ::= { dlcDsx1ConfigEntry 8 }

  dlcDsx1InBandBit OBJECT-TYPE
   SYNTAX INTEGER (1..8)
   ACCESS read-write
   STATUS mandatory
   DESCRIPTION
    "Specifies which bit in Timeslot 1
    of an E1 link is used to pass message traffic.
    Not implemented for T1 ports."
   ::= { dlcDsx1ConfigEntry 9 }

-- ============================================================================
--
-- Configuration items controlling the configuration and operation
-- of our DATA ports.
--

 dlcUnitDataDteConfigTable OBJECT-TYPE
  SYNTAX SEQUENCE OF DlcDataDteConfigEntry
  ACCESS not-accessible
  STATUS mandatory
  DESCRIPTION
   "The data DTE configuration table."
  --DEFAULT next-function next_dlcDataTable 
  ::= { dlcUnitConfig 22 }

 dlcDataDteConfigEntry OBJECT-TYPE
  SYNTAX DlcDataDteConfigEntry
  ACCESS not-accessible
  STATUS mandatory
  DESCRIPTION
   "An entry in the data DTE configuration table."
  INDEX { dlcDataConfigPortId }
  ::= { dlcUnitDataDteConfigTable 1 }

 DlcDataDteConfigEntry ::=
  SEQUENCE {
   dlcDataConfigPortId  PortId,
   dlcDataConfigEncoding  INTEGER,
   dlcDataConfigLoss  INTEGER,
   dlcDataConfigMode  INTEGER,
   dlcDataConfigFormat  INTEGER,
   dlcDataConfigTransmitTiming INTEGER
  }


  dlcDataConfigPortId OBJECT-TYPE
   SYNTAX PortId
   ACCESS read-only
   STATUS mandatory
   DESCRIPTION
    "Uniquely identifies this port.
    Valid values are `data1' through `data32'."
   --DEFAULT get-function get_compl_0
   ::= { dlcDataDteConfigEntry 1 }

  dlcDataConfigEncoding OBJECT-TYPE
   SYNTAX INTEGER {
    normal  (1),
    hdlc  (2),
    deferred (3),
    forced  (4)
   }
   ACCESS read-write
   STATUS mandatory
   DESCRIPTION
    "Data DTE encoding type."
   ::= { dlcDataDteConfigEntry 2 }

  dlcDataConfigLoss OBJECT-TYPE
   SYNTAX INTEGER {
    never   (1),
    rtsLoss   (2),
    dtrLoss   (3),
    dataDependentLoss (4)
   }
   ACCESS read-write
   STATUS mandatory
   DESCRIPTION
    "The criterion to declare a Loss of Data DTE."
   ::= { dlcDataDteConfigEntry 3 }

  dlcDataConfigMode OBJECT-TYPE
   SYNTAX INTEGER {
    dteMode (1),
    dceMode (2)
   }
   ACCESS read-write
   STATUS mandatory
   DESCRIPTION
    "In dteMode the unit is the DTE
    and the external equipment the DCE."
   ::= { dlcDataDteConfigEntry 4 }

  dlcDataConfigFormat OBJECT-TYPE
   SYNTAX INTEGER {
    v35 (1),
    rs449 (2)
   }
   ACCESS read-write
   STATUS mandatory
   DESCRIPTION
    "Selects V.35 or RS449 format."
   ::= { dlcDataDteConfigEntry 5 }

  dlcDataConfigTransmitTiming OBJECT-TYPE
   SYNTAX INTEGER {
    scte  (1),
    sct  (2),
    sctInverted (3)
   }
   ACCESS read-write
   STATUS mandatory
   DESCRIPTION
    "Selects the Data DTE tramsmit timing source.
    Can be SCTE, SCT or inverted SCT."
   ::= { dlcDataDteConfigEntry 6 }

-- ============================================================================
--
-- Configuration items controlling the unit multiplexer.
--
-- There are two mux-buses in the Eclipse,
-- so we define a table with two indexes: primary/secondary and slot number.
--

 dlcUnitMuxConfigTable OBJECT-TYPE
  SYNTAX SEQUENCE OF DlcMuxConfigEntry
  ACCESS not-accessible
  STATUS mandatory
  DESCRIPTION
   "This is the timeslot map configuration."
  --DEFAULT next-function next_dlcUnitMuxConfigTable 
  ::= { dlcUnitConfig 23 }

 dlcMuxConfigEntry OBJECT-TYPE
  SYNTAX DlcMuxConfigEntry
  ACCESS not-accessible
  STATUS mandatory
  DESCRIPTION
   "An entry in the timeslot map."
  INDEX { dlcMuxConfigBusId, dlcMuxConfigSlotNumber }
  ::= { dlcUnitMuxConfigTable 1 }
 
 DlcMuxConfigEntry ::=
  SEQUENCE {
   dlcMuxConfigBusId INTEGER,
   dlcMuxConfigSlotNumber INTEGER,
   dlcMuxConfigPortId PortId
  }


  dlcMuxConfigBusId OBJECT-TYPE
   SYNTAX INTEGER {
    primary  (1),
    secondary (2)
   }
   ACCESS read-only
   STATUS mandatory
   DESCRIPTION
    "Identifies which muxBus this timeslot is on."
   --DEFAULT get-function get_compl_0
   ::= { dlcMuxConfigEntry 1 }

  dlcMuxConfigSlotNumber OBJECT-TYPE
   SYNTAX INTEGER (1..31)
   ACCESS read-only
   STATUS mandatory
   DESCRIPTION
    "Uniquely identifies this timeslot."
   --DEFAULT get-function get_compl_1
   ::= { dlcMuxConfigEntry 2 }

  dlcMuxConfigPortId OBJECT-TYPE
   SYNTAX PortId
   ACCESS read-write
   STATUS mandatory
   DESCRIPTION
    "Says which DTE port receives data
    from the indicated muxBus
    during this timeslot."
   ::= { dlcMuxConfigEntry 3 }

 
-- ============================================================================
--
-- Configuration items controlling the unit SNMP agent.
--

 dlcUnitSnmpConfig OBJECT IDENTIFIER ::= { dlcUnitConfig 24 }

  dlcSnmpUnitIpAddr OBJECT-TYPE
   SYNTAX IpAddress
   ACCESS read-write
   STATUS mandatory
   DESCRIPTION
    "Specifies the IP address
    that is assigned to this unit."
   --DEFAULT test-function test_u32_supplier
   --DEFAULT get-function get_inetAddr_supplier
   --DEFAULT cookie (char *)&GDB.Dbms.ext_1.config.comm.ipAddr
   ::= { dlcUnitSnmpConfig 1 }

  dlcSnmpUnitNetMask OBJECT-TYPE
   SYNTAX IpAddress
   ACCESS read-write
   STATUS mandatory
   DESCRIPTION
    "Specifies the net mask
    that this unit uses."
   --DEFAULT test-function test_u32_supplier
   --DEFAULT get-function get_inetAddr_supplier
   --DEFAULT cookie (char *)&GDB.Dbms.ext_1.config.comm.ipMask
   ::= { dlcUnitSnmpConfig 2 }

  dlcSnmpTrapAddr1 OBJECT-TYPE
   SYNTAX IpAddress
   ACCESS read-write
   STATUS mandatory
   DESCRIPTION
    "Specifies the IP address
    of the management station
    to which this unit sends traps."
   --DEFAULT test-function test_u32_supplier
   --DEFAULT get-function get_inetAddr_supplier
   --DEFAULT cookie (char *)&GDB.Dbms.ext_1.config.snmp.trapAddr[0]
   ::= { dlcUnitSnmpConfig 3 }

  dlcSnmpTrapAddr2 OBJECT-TYPE
   SYNTAX IpAddress
   ACCESS read-write
   STATUS mandatory
   DESCRIPTION
    "Specifies the IP address
    of the management station
    to which this unit sends traps."
   --DEFAULT test-function test_u32_supplier
   --DEFAULT get-function get_inetAddr_supplier
   --DEFAULT cookie (char *)&GDB.Dbms.ext_1.config.snmp.trapAddr[1]
   ::= { dlcUnitSnmpConfig 4 }

  dlcSnmpTrapAddr3 OBJECT-TYPE
   SYNTAX IpAddress
   ACCESS read-write
   STATUS mandatory
   DESCRIPTION
    "Specifies the IP address
    of the management station
    to which this unit sends traps."
   --DEFAULT test-function test_u32_supplier
   --DEFAULT get-function get_inetAddr_supplier
   --DEFAULT cookie (char *)&GDB.Dbms.ext_1.config.snmp.trapAddr[2]
   ::= { dlcUnitSnmpConfig 5 }

  dlcSnmpTrapDlci1 OBJECT-TYPE
   SYNTAX Gauge
   ACCESS read-write
   STATUS mandatory
   DESCRIPTION
    "Specifies the first of three DLCI value
    to which this unit sends TRAP PDUs."
   ::= { dlcUnitSnmpConfig 6 }

  dlcSnmpTrapDlci2 OBJECT-TYPE
   SYNTAX Gauge
   ACCESS read-write
   STATUS mandatory
   DESCRIPTION
    "Specifies the second of three DLCI value
    to which this unit sends TRAP PDUs."
   ::= { dlcUnitSnmpConfig 7 }

  dlcSnmpTrapDlci3 OBJECT-TYPE
   SYNTAX Gauge
   ACCESS read-write
   STATUS mandatory
   DESCRIPTION
    "Specifies the third of three DLCI value
    to which this unit sends TRAP PDUs."
   ::= { dlcUnitSnmpConfig 8 }

  dlcSnmpTrapDirection1 OBJECT-TYPE
   SYNTAX INTEGER {
   	commDirection    ( 1 ),
   	netDirection     ( 2 ),
   	dteDirection     ( 3 ),
   	fdlDirection     ( 4 ),
	ethDirection     ( 5 )
   }
   ACCESS read-write
   STATUS mandatory
   DESCRIPTION
    "Specifies the first of three Port
    to which this unit sends TRAP PDUs."
   ::= { dlcUnitSnmpConfig 9 }

  dlcSnmpTrapDirection2 OBJECT-TYPE
   SYNTAX INTEGER {
   	commDirection    ( 1 ),
   	netDirection     ( 2 ),
   	dteDirection     ( 3 ),
   	fdlDirection     ( 4 ),
        ethDirection     ( 5 )
   }
   ACCESS read-write
   STATUS mandatory
   DESCRIPTION
    "Specifies the second of three Port
    to which this unit sends TRAP PDUs."
   ::= { dlcUnitSnmpConfig 10 }

  dlcSnmpTrapDirection3 OBJECT-TYPE
   SYNTAX INTEGER {
   	commDirection    ( 1 ),
   	netDirection     ( 2 ),
   	dteDirection     ( 3 ),
   	fdlDirection     ( 4 ),
        ethDirection     ( 5 )
   }
   ACCESS read-write
   STATUS mandatory
   DESCRIPTION
    "Specifies the third of three Port
    to which this unit sends TRAP PDUs."
   ::= { dlcUnitSnmpConfig 11 }

  dlcSnmpTrapDirection OBJECT-TYPE
   SYNTAX INTEGER {
   	commDirection    ( 1 ),
        ibcDirection     ( 2 )

   }
   ACCESS read-write
   STATUS mandatory
   DESCRIPTION
    "Specifies where  this unit sends TRAP PDUs."
   --DEFAULT test-function test_dir_supplier
   --DEFAULT get-function get_dir_supplier
   --DEFAULT cookie (char *)&GDB.Dbms.ext_1.config.snmp.connect
   ::= { dlcUnitSnmpConfig 12 }

  dlcSnmpEthernetConfiguration OBJECT IDENTIFIER
   ::= { dlcUnitSnmpConfig 13 }

  dlcEthernetIpAddr OBJECT-TYPE
   SYNTAX IpAddress
   ACCESS read-write
   STATUS mandatory
   DESCRIPTION
    "Specifies the IP address of Ethernet port."
   ::= { dlcSnmpEthernetConfiguration 1 }

  dlcEthernetIpMask OBJECT-TYPE
   SYNTAX IpAddress
   ACCESS read-write
   STATUS mandatory
   DESCRIPTION
    "Specifies the subnet mask of Ethernet port."
   ::= { dlcSnmpEthernetConfiguration 2 }
  
  dlcEthernetGatewayAddr OBJECT-TYPE
   SYNTAX IpAddress
   ACCESS read-write
   STATUS mandatory
   DESCRIPTION
    "Specifies the gateway address of Ethernet port."
   ::= { dlcSnmpEthernetConfiguration 3 }

  dlcEthernetMacAddr OBJECT-TYPE
   SYNTAX MacAddress
   ACCESS read-only
   STATUS mandatory
   DESCRIPTION
    "The MAC address of the Ethernet port."
   ::= { dlcSnmpEthernetConfiguration 4 }

-- ============================================================================
--
-- Last but not least: the unit's current date and time
--
 dlcUnitConfigTime OBJECT IDENTIFIER ::= { dlcUnitConfig 25 }

  dlcUnitTimeYear  OBJECT-TYPE
   SYNTAX INTEGER (1992..2037)
   ACCESS read-write
   STATUS mandatory
   DESCRIPTION
    "The unit's notion of the current year."
   --DEFAULT test-function test_unitTime
   --DEFAULT get-function get_unitTime
   ::= { dlcUnitConfigTime 1 }

  dlcUnitTimeMonth  OBJECT-TYPE
   SYNTAX INTEGER (1..12)
   ACCESS read-write
   STATUS mandatory
   DESCRIPTION
    "The unit's notion of the current month."
   --DEFAULT test-function test_unitTime
   --DEFAULT get-function get_unitTime
   ::= { dlcUnitConfigTime 2 }

  dlcUnitTimeDay  OBJECT-TYPE
   SYNTAX INTEGER (1..31)
   ACCESS read-write
   STATUS mandatory
   DESCRIPTION
    "The unit's notion of the current day."
   --DEFAULT test-function test_unitTime
   --DEFAULT get-function get_unitTime
   ::= { dlcUnitConfigTime 3 }

  dlcUnitTimeHour  OBJECT-TYPE
   SYNTAX INTEGER (0..23)
   ACCESS read-write
   STATUS mandatory
   DESCRIPTION
    "The the unit's notion of the current hour."
   --DEFAULT test-function test_unitTime
   --DEFAULT get-function get_unitTime
   ::= { dlcUnitConfigTime 4 }

  dlcUnitTimeMinute  OBJECT-TYPE
   SYNTAX INTEGER (0..59)
   ACCESS read-write
   STATUS mandatory
   DESCRIPTION
    "The the unit's notion of the current minute."
   --DEFAULT test-function test_unitTime
   --DEFAULT get-function get_unitTime
   ::= { dlcUnitConfigTime 5 }

  dlcUnitTimeSecond  OBJECT-TYPE
   SYNTAX INTEGER (0..59)
   ACCESS read-write
   STATUS mandatory
   DESCRIPTION
    "The the unit's notion of the current second."
   --DEFAULT test-function test_unitTime
   --DEFAULT get-function get_unitTime
   ::= { dlcUnitConfigTime 6 }

-- ============================================================================
--
-- The unit's serial number
--
 dlcUnitSerialNum OBJECT-TYPE
  SYNTAX DisplayString (SIZE (0..20))
  ACCESS read-only
  STATUS mandatory
  DESCRIPTION
   "An ID that uniquely and globally identifies the unit.
   A Serial Number must consist of printable ASCII
   characters 0x20 ..0x7E."
  --DEFAULT test-function it_exists
  --DEFAULT get-function get_string_supplier
  --DEFAULT cookie  (char *)&GDB.Dbms.ext_5.config.unit.serialNum
  ::= { dlcUnitConfig 26 }

-- ============================================================================
-- =============================================================================
--
-- Configuration items controlling the unit Modem connection. 
--
 dlcUnitModemConfig OBJECT IDENTIFIER ::= { dlcUnitConfig 27 }

  dlcModemPhoneNum1 OBJECT-TYPE
   SYNTAX DisplayString (SIZE (0..20))
   ACCESS read-write
   STATUS mandatory
   DESCRIPTION
    "The first phone number to dial
    when the unit needs to set up a 
    modem connection."
   --DEFAULT test-function test_string_supplier
   --DEFAULT get-function get_string_supplier
   --DEFAULT cookie (char *)&GDB.Dbms.config.comm.phoneNumber[0]
   ::= { dlcUnitModemConfig 1 }

  dlcModemPhoneNum2 OBJECT-TYPE
   SYNTAX DisplayString (SIZE (0..20))
   ACCESS read-write
   STATUS mandatory
   DESCRIPTION
    "The second phone number to try 
    if the phone number failed in 
    setting up a modem connection."
   --DEFAULT test-function test_string_supplier
   --DEFAULT get-function get_string_supplier
   --DEFAULT cookie (char *)&GDB.Dbms.config.comm.phoneNumber[1]
   ::= { dlcUnitModemConfig 2 }

  dlcModemInitString1 OBJECT-TYPE
   SYNTAX DisplayString (SIZE (1..20))
   ACCESS read-write
   STATUS mandatory
   DESCRIPTION
    "In setting up a modem connection, 
    the first group of commands used  
    to initialize the modem."
   --DEFAULT test-function test_string_supplier
   --DEFAULT get-function get_string_supplier
   --DEFAULT cookie (char *)&GDB.Dbms.ext_5.config.comm.modemInitStr1
   ::= { dlcUnitModemConfig 3 }

  dlcModemInitString2 OBJECT-TYPE
   SYNTAX DisplayString (SIZE (1..60))
   ACCESS read-write
   STATUS mandatory
   DESCRIPTION
    "In setting up a modem connection, 
    the second group of commands used
    to initialize the modem.  There is a
    delay between sending the first and 
    second groups of initialzation commands."
   --DEFAULT test-function test_string_supplier
   --DEFAULT get-function get_string_supplier
   --DEFAULT cookie (char *)&GDB.Dbms.ext_5.config.comm.modemInitStr2
   ::= { dlcUnitModemConfig 4 }

-- ============================================================================
--
-- Configuration items related to inband management
--
	dlcUnitInbandMode OBJECT-TYPE
	SYNTAX INTEGER {
		noInband	( 1 ),
		frameRelay 	( 2 ),
		ciscoHdlc	( 3 )
	}
	ACCESS read-only
	STATUS mandatory
	DESCRIPTION
	"The type of traffic expected on the link for inband management and IPM."
	::= { dlcUnitConfig 28 }


-- ****************************************************************************
-- ****************************************************************************
-- ****************************************************************************
-- ****************************************************************************
--
-- Unit Status Group
--
--
-- New types defined in this MIB
--

-- UnitStatusItem is used to represent the status of the unit.
-- It is the sum of the following binary values.
-- More than one such item can be in effect, thus it is a bitmap.
-- When `normal' is active, no other item is active.
--
 UnitStatusItem ::= INTEGER {
   normal    (  1),
   noClock    (  2),
   testInProgress   (  4),
   sendKeepAlive   (  8),
   sendYellowAlarm   ( 16),
   reserved1   ( 32),
   reserved2   ( 64),
   reserved3   (128),
   reserved4   (256),
   reserved5   (512)
  }


-- PortStatusItem represents the status of the received signal on a port.
-- More than one such item can be in effect.
-- When `normal' is active, no other item is active.
--
-- Note that PortStatusItem is used for all ports (Dsx1 and Data DTE).
--
-- For E1 ports, the Eclipse reports "yellowAlarmDetected" upon recognition
-- of Remote Alarm Indication.
--
 PortStatusItem ::= INTEGER {
   normal    ( 1),
   lossOfSignal   ( 2),
   lossOfSync   ( 3),
   yellowAlarmDetected  ( 4),
   blueAlarmDetected  ( 5),
   setCodeReceived   ( 6),
   resetCodeReceived  ( 7),
   excessiveErrorRate  ( 8),
   localTest   ( 9),
    eBitReceived   (10),
    reserved1   (11),
    reserved2   (12),
    reserved3   (13),
    reserved4   (14)
  }

-- =============================================================================
-- =============================================================================
--
-- The following variables describe the (not-user-settable) status
-- of the unit.
--
dlcUnitStatus OBJECT IDENTIFIER ::= { dl-new-t1 3 }

 dlcUnitCurrentStatus OBJECT-TYPE
  SYNTAX UnitStatusItem
  ACCESS read-only
  STATUS mandatory
  DESCRIPTION
   "What's going on in this unit?"
  --DEFAULT test-function it_exists
  ::= { dlcUnitStatus 1 }

 dlcUnitErrorFreeSeconds OBJECT-TYPE
  SYNTAX Gauge
  ACCESS read-only
  STATUS mandatory
  DESCRIPTION
   "Represents the percent of error free seconds
   over the last 24 hours.
   The number is multiplied by 10
   and rounded to the nearest integer.
   For example, 94.2% is encoded as 942."
  --DEFAULT test-function it_exists
  --DEFAULT get-function get_u16_supplier
  --DEFAULT cookie (char *)&GDB.Dbms.archive.local.misc.efs
  ::= { dlcUnitStatus 2 }

 dlcUnitLastSelfTestResult OBJECT-TYPE
  SYNTAX INTEGER ( 0..1023 )
  ACCESS read-only
  STATUS mandatory
  DESCRIPTION
   "The result of the last self test.
   unitLastSelfTest is a bitmap ... the sum of:
      0 Selftest passed 
      1 ROM checksum failure
      2 RAM test failure
      4 EEPROM CRC failure
      8 DTE test failure
     16 Pattern loss during test
     32 FLASH checksum failure
     64 reserved
    128 reserved
    256 reserved
    512 reserved
   A result of 0 means no errors occurred.
   "
  --DEFAULT test-function it_exists
  ::= { dlcUnitStatus 3 }

-- -----------------------------------------------------------------------------
--
-- Port status
--

 dlcUnitPortStatusTable OBJECT-TYPE
  SYNTAX SEQUENCE OF DlcPortStatusEntry
  ACCESS not-accessible
  STATUS mandatory
  DESCRIPTION
   "A table of all port-related status"
  --DEFAULT next-function next_dlcPortStatusTable 
  ::= { dlcUnitStatus 4 }

 dlcPortStatusEntry OBJECT-TYPE
  SYNTAX DlcPortStatusEntry
  ACCESS not-accessible
  STATUS mandatory
  DESCRIPTION
   "An entry in the port status table."
  INDEX { dlcPortStatusId, dlcPortStatus }
  ::= { dlcUnitPortStatusTable 1 }

 DlcPortStatusEntry ::=
  SEQUENCE {
   dlcPortStatusId  PortId,
   dlcPortStatus  PortStatusItem,
   dlcPortStatusNetRxBwUtilization Gauge,
   dlcPortStatusNetTxBwUtilization Gauge
  }

  dlcPortStatusId OBJECT-TYPE
   SYNTAX PortId
   ACCESS read-only
   STATUS mandatory
   DESCRIPTION
    "Identifies which port
    (NET, AUX, Data DTE, or whatever)
    this status entry is describing."
   --DEFAULT get-function get_compl_0
   ::= { dlcPortStatusEntry 1 }

  dlcPortStatus OBJECT-TYPE
   SYNTAX PortStatusItem
   ACCESS read-only
   STATUS mandatory
   DESCRIPTION
    "Gives the actual status value
    for to this port."
   --DEFAULT get-function get_compl_1
   ::= { dlcPortStatusEntry 2 }

 dlcPortStatusNetRxBwUtilization OBJECT-TYPE
  SYNTAX Gauge
  ACCESS read-only
  STATUS mandatory
  DESCRIPTION
   "Represents the percent of net receive bandwidth utilization
   over the last 60 seconds.  The number is multiplied by 10
   and rounded to the nearest integer.  For example, 94.2% is
   encoded as 942."
   --DEFAULT test-function test_dlcPortStatus
   --DEFAULT get-function get_dlci_u16_supplier
   --DEFAULT cookie (char *)0
  ::= { dlcPortStatusEntry 3 }

 dlcPortStatusNetTxBwUtilization OBJECT-TYPE
  SYNTAX Gauge
  ACCESS read-only
  STATUS mandatory
  DESCRIPTION
   "Represents the percent of net receive bandwidth utilization
   over the last 60 seconds.  The number is multiplied by 10
   and rounded to the nearest integer.  For example, 94.2% is
   encoded as 942."
   --DEFAULT test-function test_dlcPortStatus
   --DEFAULT get-function get_dlci_u16_supplier
   --DEFAULT cookie (char *)1
  ::= { dlcPortStatusEntry 4 }

-- -----------------------------------------------------------------------------
--
-- Alarms
--

 dlcUnitAlarmTable OBJECT-TYPE
  SYNTAX SEQUENCE OF DlcAlarmEntry
  ACCESS not-accessible
  STATUS mandatory
  DESCRIPTION
   "A table of all currently-raised alarms"
  --DEFAULT next-function next_dlcAlarmTable 
  ::= { dlcUnitStatus 5 }

 dlcAlarmEntry OBJECT-TYPE
  SYNTAX DlcAlarmEntry
  ACCESS not-accessible
  STATUS mandatory
  DESCRIPTION
   "An entry in the alarm table."
  INDEX { dlcAlarmPort, dlcAlarmType }
  ::= { dlcUnitAlarmTable 1 }

 DlcAlarmEntry ::=
  SEQUENCE {
   dlcAlarmPort PortId,
   dlcAlarmType AlarmType
  }

  dlcAlarmPort OBJECT-TYPE
   SYNTAX PortId
   ACCESS read-only
   STATUS mandatory
   DESCRIPTION
    "Identifies which port
    (NET, AUX, Data DTE, or whatever)
    this alarm relates to."
   --DEFAULT get-function get_compl_0
   ::= { dlcAlarmEntry 1 }

  dlcAlarmType OBJECT-TYPE
   SYNTAX AlarmType
   ACCESS read-only
   STATUS mandatory
   DESCRIPTION
    "Identifies an alarm
    that's currently outstanding
    against this port."
   --DEFAULT get-function get_compl_1
   ::= { dlcAlarmEntry 2 }

--------------------------------------------------------------------------------------------
  dlcUnitErrorSecondsRatio OBJECT-TYPE
	SYNTAX Gauge
	ACCESS read-only
	STATUS mandatory
	DESCRIPTION
		"Represents the percent of error seconds
		over the last 24 hours.
		The number is multiplied by 10
		and rounded to the nearest integer.
		For example, 94.2% is encoded as 942."
	--DEFAULT test-function	it_exists
	--DEFAULT get-function	get_u16_supplier
	--DEFAULT cookie	(char *)&GDB.Dbms.ext_9.archive.misc.total.esr
	::= { dlcUnitStatus 6 }
  dlcUnitSeverelyErroredSecondsRatio OBJECT-TYPE
	SYNTAX Gauge
	ACCESS read-only
	STATUS mandatory
	DESCRIPTION
		"Represents the percent of severely errored 
		seconds over the last 24 hours.
		The number is multiplied by 10
		and rounded to the nearest integer.
		For example, 94.2% is encoded as 942."
	--DEFAULT test-function	it_exists
	--DEFAULT get-function	get_u16_supplier
	--DEFAULT cookie	(char *)&GDB.Dbms.ext_9.archive.misc.total.sesr
	::= { dlcUnitStatus 7 }
  dlcUnitBackgroundBlockErrorRatio OBJECT-TYPE
	SYNTAX Gauge
	ACCESS read-only
	STATUS mandatory
	DESCRIPTION
		"Represents the percent of background block 
		errors over the last 24 hours.
		The number is multiplied by 10
		and rounded to the nearest integer.
		For example, 94.2% is encoded as 942."
	--DEFAULT test-function	it_exists
	--DEFAULT get-function	get_u16_supplier
	--DEFAULT cookie	(char *)&GDB.Dbms.ext_9.archive.misc.total.bber
	::= { dlcUnitStatus 8 }
--

-- =============================================================================
-- =============================================================================
--
-- Unit User Archives
--
-- The eclipse has the capability to support two NET ports,
-- so we define several sets of User Archives.
--

dlcUnitUserArchive OBJECT IDENTIFIER ::= { dl-new-t1 4 }

 dlcUnitUserArchiveValidTable OBJECT-TYPE
  SYNTAX SEQUENCE OF DlcUserArchiveValidEntry
  ACCESS not-accessible
  STATUS mandatory
  DESCRIPTION
   "A table of all port-related status"
  --DEFAULT next-function next_dlcArchiveTable 
  ::= { dlcUnitUserArchive 1 }

 dlcUserArchiveValidEntry OBJECT-TYPE
  SYNTAX DlcUserArchiveValidEntry
  ACCESS not-accessible
  STATUS mandatory
  DESCRIPTION
   "An entry in the user archive valid-intervals table."
  INDEX { dlcValidPortId }
  ::= { dlcUnitUserArchiveValidTable 1 }

 DlcUserArchiveValidEntry ::=
  SEQUENCE {
   dlcValidPortId  PortId,
   dlcValidIntervals INTEGER
  }

  dlcValidPortId OBJECT-TYPE
   SYNTAX PortId
   ACCESS read-only
   STATUS mandatory
   DESCRIPTION
    "Identifies which port
    (`net' or `otherNet')
    this entry is describing."
   --DEFAULT get-function get_compl_0
   ::= { dlcUserArchiveValidEntry 1 }

  dlcValidIntervals OBJECT-TYPE
   SYNTAX INTEGER ( 1..96 )
   ACCESS read-write
   STATUS mandatory
   DESCRIPTION
    "The number of valid intervals
    in the user's error register database
    for this port.
    Writing a 0 to this variable
    will clear the entire archive
    for this port.
    Writing any other value is a no-op."
   --DEFAULT get-function get_u8_supplier
   --DEFAULT cookie (char *)&GDB.Dbms.archive.local.misc.validIntervals
   ::= { dlcUserArchiveValidEntry 2 }

-- -----------------------------------------------------------------------------
--
-- User Lifetime Counters
--
-- The Carrier's registers are covered by RFC1406.
--

 dlcUnitUserLifetimeTable OBJECT-TYPE
  SYNTAX SEQUENCE OF DlcUserLifetimeEntry
  ACCESS not-accessible
  STATUS mandatory
  DESCRIPTION
   "A table of the lifetime error counts, per-port."
  --DEFAULT test-function test_dlcLifetime
  --DEFAULT get-function get_dlcLifetime
  --DEFAULT next-function next_dlcLifetime 
  ::= { dlcUnitUserArchive 2 }

 dlcUserLifetimeEntry OBJECT-TYPE
  SYNTAX DlcUserLifetimeEntry
  ACCESS not-accessible
  STATUS mandatory
  DESCRIPTION
   "An entry in the user archive lifetime-totals table."
  INDEX { dlcLifetimePortId }
  ::= { dlcUnitUserLifetimeTable 1 }

 DlcUserLifetimeEntry ::=
  SEQUENCE {
   dlcLifetimePortId PortId,
   dlcLifetimeES  Gauge,
   dlcLifetimeUAS  Gauge,
   dlcLifetimeCrcErrors Gauge,
   dlcLifetimeBpvErrors Gauge,
   dlcLifetimeOofErrors Gauge,
   dlcLifetimeIbCrcErrors Gauge
  }

  dlcLifetimePortId OBJECT-TYPE
   SYNTAX PortId
   ACCESS read-only
   STATUS mandatory
   DESCRIPTION
    "Identifies which port
    (`net' or `otherNet')
    this entry relates to."
   --DEFAULT get-function get_compl_0
   ::= { dlcUserLifetimeEntry 1 }

  dlcLifetimeES OBJECT-TYPE
   SYNTAX Gauge
   ACCESS read-write
   STATUS mandatory
   DESCRIPTION
    "An ongoing count of Errored Seconds
    detected on this network port.
    Can be read and written (to zero)."
   ::= { dlcUserLifetimeEntry 2 }

  dlcLifetimeUAS OBJECT-TYPE
   SYNTAX Gauge
   ACCESS read-write
   STATUS mandatory
   DESCRIPTION
    "An ongoing count of Unavailable Seconds
    detected on this network port.
    Can be read and written (to zero)."
   ::= { dlcUserLifetimeEntry 3 }

  dlcLifetimeCrcErrors OBJECT-TYPE
   SYNTAX Gauge
   ACCESS read-write
   STATUS mandatory
   DESCRIPTION
    "An ongoing count of the CRC errors
    detected on this network port.
    Can be read and written (to zero)."
   ::= { dlcUserLifetimeEntry 4 }

  dlcLifetimeBpvErrors OBJECT-TYPE
   SYNTAX Gauge
   ACCESS read-write
   STATUS mandatory
   DESCRIPTION
    "An ongoing count of the Code Violation errors
    detected on this network port.
    Can be read and written (to zero)."
   ::= { dlcUserLifetimeEntry 5 }

  dlcLifetimeOofErrors OBJECT-TYPE
   SYNTAX Gauge
   ACCESS read-write
   STATUS mandatory
   DESCRIPTION
    "For an ESF T1 port, an ongoing count
    of Out-Of-Frame errors.
    For a D4 T1 port, an ongoing count
    of Framing Errors.
    Available only for the network port.
    Can be read and written (to zero)."
   ::= { dlcUserLifetimeEntry 6 }

  dlcLifetimeIbCrcErrors OBJECT-TYPE
   SYNTAX Gauge
   ACCESS read-write
   STATUS mandatory
   DESCRIPTION
    "An ongoing count of the FCS errors
    detected on this network port."
   ::= { dlcUserLifetimeEntry 7 }

-- -----------------------------------------------------------------------------
--
-- User Current Interval
--
-- The Carrier's registers are covered by RFC1406.
--

 dlcUnitUserCurrentTable OBJECT-TYPE
  SYNTAX SEQUENCE OF DlcUserCurrentEntry
  ACCESS not-accessible
  STATUS mandatory
  DESCRIPTION
   "A table of all the current interval error counts,
   per-port."
  --DEFAULT test-function test_dlcCurrent
  --DEFAULT get-function get_dlcCurrent
  --DEFAULT next-function next_dlcCurrent 
  ::= { dlcUnitUserArchive 3 }

 dlcUserCurrentEntry OBJECT-TYPE
  SYNTAX DlcUserCurrentEntry
  ACCESS not-accessible
  STATUS mandatory
  DESCRIPTION
   "An entry in the user archive current interval table."
  INDEX { dlcCurrentPortId }
  ::= { dlcUnitUserCurrentTable 1 }

 DlcUserCurrentEntry ::=
  SEQUENCE {
   dlcCurrentPortId PortId,
   dlcCurrentES  Counter,
   dlcCurrentUAS  Counter,
   dlcCurrentCrcErrors Counter,
   dlcCurrentBpvErrors Counter,
   dlcCurrentOofErrors Counter,
   dlcCurrentTimeElapsed INTEGER,
   dlcCurrentIbCrcErrors Counter
  }


  dlcCurrentPortId OBJECT-TYPE
   SYNTAX PortId
   ACCESS read-only
   STATUS mandatory
   DESCRIPTION
    "Identifies which port
    (`net' or `otherNet')
    this entry relates to."
   --DEFAULT get-function get_compl_0
   ::= { dlcUserCurrentEntry 1 }

  dlcCurrentES OBJECT-TYPE
   SYNTAX Counter
   ACCESS read-only
   STATUS mandatory
   DESCRIPTION
    "Errored seconds in the interval."
   ::= { dlcUserCurrentEntry 2 }

  dlcCurrentUAS OBJECT-TYPE
   SYNTAX Counter
   ACCESS read-only
   STATUS mandatory
   DESCRIPTION
    "Unavailable seconds in the interval."
   ::= { dlcUserCurrentEntry 3 }

  dlcCurrentCrcErrors OBJECT-TYPE
   SYNTAX Counter
   ACCESS read-only
   STATUS mandatory
   DESCRIPTION
    "CRC Errors in the interval."
   ::= { dlcUserCurrentEntry 4 }

  dlcCurrentBpvErrors OBJECT-TYPE
   SYNTAX Counter
   ACCESS read-only
   STATUS mandatory
   DESCRIPTION
    "Code Violation Errors in the interval."
   ::= { dlcUserCurrentEntry 5 }

  dlcCurrentOofErrors OBJECT-TYPE
   SYNTAX Counter
   ACCESS read-only
   STATUS mandatory
   DESCRIPTION
    "OOF or Framing Errors in the interval."
   ::= { dlcUserCurrentEntry 6 }

   dlcCurrentTimeElapsed OBJECT-TYPE
        SYNTAX  INTEGER (0..899)
        ACCESS  read-only
       STATUS  mandatory
      DESCRIPTION
    "The number of seconds that have elapsed 
    since the beginning of the current 
    error-measurement period.
    Available only for the network port."
   --DEFAULT cookie (char *)&GDB.Dbms.archive.local.misc.timeInCurrentInterval
   --DEFAULT test-function test_%n 
   --DEFAULT get-function  get_u16_supplier 
     ::= { dlcUserCurrentEntry 7 }

  dlcCurrentIbCrcErrors OBJECT-TYPE
   SYNTAX Counter
   ACCESS read-only
   STATUS mandatory
   DESCRIPTION
    "FCS Errors in the interval."
   ::= { dlcUserCurrentEntry 8 }

-- -----------------------------------------------------------------------------
--
-- User Archive
-- Statistics: 15-minute Interval Registers Group.
--
-- The Carrier's registers are covered by RFC1406.
--

 dlcUnitUserArchiveTable OBJECT-TYPE
  SYNTAX SEQUENCE OF DlcUserArchiveEntry
  ACCESS not-accessible
  STATUS mandatory
  DESCRIPTION
   "A table of all the archive intervals' error counts,
   per-port."
  --DEFAULT test-function test_dlcArchive
  --DEFAULT get-function get_dlcArchive
  --DEFAULT next-function next_dlcArchive 
  ::= { dlcUnitUserArchive 4 }

 dlcUserArchiveEntry OBJECT-TYPE
  SYNTAX DlcUserArchiveEntry
  ACCESS not-accessible
  STATUS mandatory
  DESCRIPTION
   "An entry in the user archive table."
  INDEX { dlcArchivePortId, dlcArchiveInterval }
  ::= { dlcUnitUserArchiveTable 1 }

 DlcUserArchiveEntry ::=
  SEQUENCE {
   dlcArchivePortId PortId,
   dlcArchiveInterval INTEGER,
   dlcArchiveES  Counter,
   dlcArchiveUAS  Counter,
   dlcArchiveCrcErrors Counter,
   dlcArchiveBpvErrors Counter,
   dlcArchiveOofErrors Counter,
   dlcArchiveIbCrcErrors Counter,
   dlcArchiveNetRxBwUtilization Gauge,
   dlcArchiveNetRxPackets Counter,
   dlcArchiveNetTxBwUtilization Gauge,
   dlcArchiveNetTxPackets Counter
  }

  dlcArchivePortId OBJECT-TYPE
   SYNTAX PortId
   ACCESS read-only
   STATUS mandatory
   DESCRIPTION
    "Identifies which port
    (`net' or `otherNet')
    this entry relates to."
   --DEFAULT get-function get_compl_0
   ::= { dlcUserArchiveEntry 1 }

  dlcArchiveInterval OBJECT-TYPE
   SYNTAX INTEGER ( 1..96 )
   ACCESS read-only
   STATUS mandatory
   DESCRIPTION
    "Identifies which interval
    this secondaryArchiveEntry describes.
    1 indicates the most-recent interval."
   --DEFAULT get-function get_compl_1
   ::= { dlcUserArchiveEntry 2 }

  dlcArchiveES OBJECT-TYPE
   SYNTAX Counter
   ACCESS read-only
   STATUS mandatory
   DESCRIPTION
    "Errored seconds in the interval."
   ::= { dlcUserArchiveEntry 3 }

  dlcArchiveUAS OBJECT-TYPE
   SYNTAX Counter
   ACCESS read-only
   STATUS mandatory
   DESCRIPTION
    "Unavailable seconds in the interval."
   ::= { dlcUserArchiveEntry 4 }

  dlcArchiveCrcErrors OBJECT-TYPE
   SYNTAX Counter
   ACCESS read-only
   STATUS mandatory
   DESCRIPTION
    "CRC Errors in the interval."
   ::= { dlcUserArchiveEntry 5 }

  dlcArchiveBpvErrors OBJECT-TYPE
   SYNTAX Counter
   ACCESS read-only
   STATUS mandatory
   DESCRIPTION
    "Code Violation Errors in the interval."
   ::= { dlcUserArchiveEntry 6 }

  dlcArchiveOofErrors OBJECT-TYPE
   SYNTAX Counter
   ACCESS read-only
   STATUS mandatory
   DESCRIPTION
    "OOF or Framing Errors in the interval."
   ::= { dlcUserArchiveEntry 7 }

  dlcArchiveIbCrcErrors OBJECT-TYPE
   SYNTAX Counter
   ACCESS read-only
   STATUS mandatory
   DESCRIPTION
    "FCS Errors in the interval."
   ::= { dlcUserArchiveEntry 8 }

  dlcArchiveNetRxBwUtilization OBJECT-TYPE
   SYNTAX Gauge
   ACCESS read-only
   STATUS mandatory
   DESCRIPTION
    "Net Rx Bandwidth Utilization in the interval."
   ::= { dlcUserArchiveEntry 9 }

  dlcArchiveNetRxPackets OBJECT-TYPE
   SYNTAX Counter
   ACCESS read-only
   STATUS mandatory
   DESCRIPTION
    "Net Rx Packets in the interval."
   ::= { dlcUserArchiveEntry 10 }

  dlcArchiveNetTxBwUtilization OBJECT-TYPE
   SYNTAX Gauge
   ACCESS read-only
   STATUS mandatory
   DESCRIPTION
    "Net Tx Bandwidth Utilization in the interval."
   ::= { dlcUserArchiveEntry 11 }

  dlcArchiveNetTxPackets OBJECT-TYPE
   SYNTAX Counter
   ACCESS read-only
   STATUS mandatory
   DESCRIPTION
    "Net Tx Packets in the interval."
   ::= { dlcUserArchiveEntry 12 }


-- *****************************************************************************
-- *****************************************************************************
-- *****************************************************************************
-- *****************************************************************************
--
-- Unit Test Group
--
-- To start a test running against a port,
-- just set one of the values in the dlcUnitTestTable.
-- To stop a test, set the testType to `noTest'.
--

dlcUnitTest OBJECT IDENTIFIER ::= { dl-new-t1 5 }

 dlcUnitTestTable OBJECT-TYPE
  SYNTAX SEQUENCE OF DlcUnitTestEntry
  ACCESS not-accessible
  STATUS mandatory
  DESCRIPTION
   "A table containing all currently active tests.
   The initial release of the product's firmware
   does not include multiple tests.
   However, a later version will allow
   a number of tests to be active at a time.
   This MIB object structure allows any number of tests
   to be running at any time.
   Upon receiving a SET request,
   the unit compares this table
   with the list of currently active tests
   and terminates or initiates any tests as required.
   However, this does not apply to Link Based Test.
   dlcUnitConfigLinkTest group contains objects to
   configure and start Link Based Test.
   This table only contains the statistics for Link
   Based Test."
  ::= { dlcUnitTest 1 }

 dlcUnitTestEntry OBJECT-TYPE
  SYNTAX DlcUnitTestEntry
  ACCESS not-accessible
  STATUS mandatory
  DESCRIPTION
   "An entry in the network configuration table."
  INDEX { dlcUnitTestPortId }
  ::= { dlcUnitTestTable 1 }

 DlcUnitTestEntry ::=
  SEQUENCE {
   dlcUnitTestPortId		PortId,
   dlcUnitTestType		TestType,
   dlcUnitTestPatternStatus	INTEGER,
   dlcUnitTestPatternErrors	Gauge,
   dlcLinkTestSentPackets	Gauge,
   dlcLinkTestReceivedPackets	Gauge,
   dlcLinkTestErroredPackets	Gauge,
   dlcLinkTestMissingPackets	Gauge,
   dlcLinkTestAverageRoundTrip	Gauge,
   dlcLinkTestMaximumRoundTrip	Gauge
  }

  dlcUnitTestPortId OBJECT-TYPE
   SYNTAX PortId
   ACCESS read-only
   STATUS mandatory
   DESCRIPTION
    "Identifies a port
    that a test might be running on.
    By convention, Self Test and all
    full-bandwidth tests (loopbacks, patterns, etc.)
    are assigned to the netPort.
    For E1 unit, if it is in unstructured mode,
    only full-bandwidth tests can be performed."
   --DEFAULT get-function get_compl_0
   --DEFAULT next-function next_dlcPortTable 
   ::= { dlcUnitTestEntry 1 }

  dlcUnitTestType OBJECT-TYPE
   SYNTAX TestType
   ACCESS read-write
   STATUS mandatory
   DESCRIPTION
    "Says what test is running on this port.
                 Note that the following test nomenclature
                 is equivalent:
                 SNMP        Terminal UI    Front Panel
                 1in8           1:7             1:7
                 3in24          3:24            3.24
                 1in1           1:1             1:1
                 AllOne         All 1           1's
                 AllZero        All 0           0's
                 1in3           1:2             1:2
                 1in5           1:4             1:4
                 The SNMP test identifiers use the names on the left.
                 The terminal User Interface uses the names in the
                 middle column, and the unit's front panel uses the 
                 names in the right column."
   --DEFAULT next-function next_dlcPortTable 
   ::= { dlcUnitTestEntry 2 }

  dlcUnitTestPatternStatus OBJECT-TYPE
   SYNTAX INTEGER {
    search  (1),
    locked  (2),
    overflow (3),
    off  (4),
    lockedAfterLoss (5)
   }
   ACCESS read-only
   STATUS mandatory
   DESCRIPTION
    "The current state of the Pattern Test module."
   --DEFAULT next-function next_dlcPortTable 
   ::= { dlcUnitTestEntry 3 }

  dlcUnitTestPatternErrors OBJECT-TYPE
   SYNTAX Gauge
   ACCESS read-write
   STATUS mandatory
   DESCRIPTION
    "An ongoing count of errors detected by
    the Pattern Generator/Detector.
    Can be read and written (to zero)."
   --DEFAULT next-function next_dlcPortTable 
   ::= { dlcUnitTestEntry 4 }

  dlcLinkTestSentPackets OBJECT-TYPE
   SYNTAX Gauge
   ACCESS read-only
   STATUS mandatory
   DESCRIPTION
    "Number of sent packets for the currently running link based
    test."
   ::= { dlcUnitTestEntry 5 }

  dlcLinkTestReceivedPackets OBJECT-TYPE
   SYNTAX Gauge
   ACCESS read-only
   STATUS mandatory
   DESCRIPTION
    "Number of good received packets for the currently running
    link based test."
   ::= { dlcUnitTestEntry 6 }

  dlcLinkTestErroredPackets OBJECT-TYPE
   SYNTAX Gauge
   ACCESS read-only
   STATUS mandatory
   DESCRIPTION
    "Number of errored received packets for the currently running
    link based test."
   ::= { dlcUnitTestEntry 7 }

  dlcLinkTestMissingPackets OBJECT-TYPE
   SYNTAX Gauge
   ACCESS read-only
   STATUS mandatory
   DESCRIPTION
    "Number of missing packets for the currently running link
    based test."
   ::= { dlcUnitTestEntry 8 }

  dlcLinkTestAverageRoundTrip OBJECT-TYPE
   SYNTAX Gauge
   ACCESS read-only
   STATUS mandatory
   DESCRIPTION
    "Average round trip time in milli seconds for the currently
    running link based test."
    ::= { dlcUnitTestEntry 9 }

  dlcLinkTestMaximumRoundTrip OBJECT-TYPE
   SYNTAX Gauge
   ACCESS read-only
   STATUS mandatory
   DESCRIPTION
    "Maximum round trip time in milli seconds for the currently
    running link based test."
    ::= { dlcUnitTestEntry 10 }

-- =============================================================================
--
-- The dialout time interval
--
	dlcUnitDialOutTimeInterval OBJECT-TYPE
		SYNTAX INTEGER (0..255)
		ACCESS read-write
		STATUS mandatory
		DESCRIPTION
			"A time interval for the dialout.
			 The value should be between 0 and 255."
		--DEFAULT test-function	test_u8_supplier
		--DEFAULT get-function	get_u8_supplier
		--DEFAULT cookie 	(char *)&GDB.Dbms.ext_8.config.unit.dialOutTimeInterval
		::= { dlcUnitConfig 29 }

-- =============================================================================
--
-- The framed/unframed aux alarm signal option
--

FramedUnframed ::= INTEGER {
		framed	        (1),
		unframed	(2)
	}

	dlcAlarmSignal OBJECT-TYPE
		SYNTAX FramedUnframed
		ACCESS read-write
		STATUS mandatory
		DESCRIPTION
			"Framed/unframed aux alarm signal option"
		--DEFAULT test-function	test_alarmSignal_supplier
		--DEFAULT get-function	get_alarmSignal_supplier
		--DEFAULT cookie 	(char *)&GDB.Dbms.ext_8.config.unit.alarmSignal
		::= { dlcUnitConfig 30 }

-- =============================================================================
--
-- The idleCode
--
	dlcUnitIdleCode OBJECT-TYPE
		SYNTAX INTEGER (0..255)
		ACCESS read-write
		STATUS mandatory
		DESCRIPTION
			"Idle Code that is send on unassigned time slots"
		--DEFAULT test-function	test_u8_supplier
		--DEFAULT get-function	get_u8_supplier
		--DEFAULT cookie 	(char *)&GDB.Dbms.ext_9.config.unit.idleCode
		::= { dlcUnitConfig 31 }
--
-- =============================================================================
--
-- The remote communication mode
--

RemoteCommunicationsMode ::= INTEGER {
		none	        (1),
		digital-link	(2),
		att-TR54016	(3),
		ansi-T1-403	(4)
	}

	dlcRemoteCommunicationsMode OBJECT-TYPE
		SYNTAX RemoteCommunicationsMode
		ACCESS read-write
		STATUS mandatory
		DESCRIPTION
			"Framed/unframed aux alarm signal option"
		--DEFAULT test-function	test_remoteCommunicationsMode_supplier
		--DEFAULT get-function	get_remoteCommunicationsMode_supplier
		--DEFAULT cookie 	(char *)&GDB.Dbms.ext_10.config.remoteCommunicationsMode
		::= { dlcUnitConfig 32 }


-- =============================================================================
--
-- Link Based Test parameters
--
	dlcUnitConfigLinkTest OBJECT IDENTIFIER ::= { dlcUnitConfig 33 }


	dlcLinkTestState OBJECT-TYPE
	SYNTAX INTEGER {
			disabled (1),
			enabled (2),
			running (3),
			idle (4)
	}
	ACCESS read-write
	STATUS mandatory
	DESCRIPTION
	"Specifies the status configuration of link based test.
	Only setable to values disabled(1) and enabled(2) to end and start
        the test respectively. Values running(3) and idle(4) are returned
        for status of the test."
	::= { dlcUnitConfigLinkTest 1 }

	dlcLinkTestAddress OBJECT-TYPE
	SYNTAX IpAddress
	ACCESS read-write
	STATUS mandatory
	DESCRIPTION
	"Specifies the address for the next link based test to run."
	::= { dlcUnitConfigLinkTest 2 }

	dlcLinkTestDlci OBJECT-TYPE
	SYNTAX INTEGER ( 0..1023 )
	ACCESS read-write
	STATUS mandatory
	DESCRIPTION
	"Specifies the frame relay DLCI for the next link based test
	to run. This value is used when the unit is in frameRelay
	InbandMode only and if the next link based test is not done
	on the commPort."
	::= { dlcUnitConfigLinkTest 3 }

	dlcLinkTestPort OBJECT-TYPE
	SYNTAX INTEGER {
		comm	(1),
		net	(2),
		dte	(3),
                eth     (4)
	}
	ACCESS read-write
	STATUS mandatory
	DESCRIPTION
	"Specifies which port to run the next link based test."
	::= { dlcUnitConfigLinkTest 4 }

	dlcLinkTestLength OBJECT-TYPE
	SYNTAX INTEGER
	ACCESS read-write
	STATUS mandatory
	DESCRIPTION
	"Specifies the time length of the next test to run in minutes."
	::= { dlcUnitConfigLinkTest 5 }

	dlcLinkTestInterval OBJECT-TYPE
	SYNTAX INTEGER (1..3600)
	ACCESS read-write
	STATUS mandatory
	DESCRIPTION
	"Specifies the repetition interval in seconds between packets
	 for the next link based test."
	::= { dlcUnitConfigLinkTest 6 }

	dlcLinkTestPacketSize OBJECT-TYPE
	SYNTAX INTEGER (0..1500)
	ACCESS read-write
	STATUS mandatory
	DESCRIPTION
	"Specifies the packet size for the next link based test."
	::= { dlcUnitConfigLinkTest 7 }

	dlcLinkTestPattern OBJECT-TYPE
	SYNTAX INTEGER {
		ping511	(1),
		ping2047 (2),
		ping1-0 (3),
		ping-all-1 (4),
		ping-all-0 (5)
	}
	ACCESS read-write
	STATUS mandatory
	DESCRIPTION
	"Specifies the test pattern for the next link based test."
	::= { dlcUnitConfigLinkTest 8 }


-- =============================================================================
--
-- InbandManagement
--
	dlcUnitInbandConfig OBJECT-TYPE
	SYNTAX Boolean
	ACCESS read-only
	STATUS mandatory
	DESCRIPTION
	"When true (== 2), inband management is enabled."
	::= { dlcUnitConfig 34 }

	dlcUnitInbandTrafficType OBJECT-TYPE
	SYNTAX INTEGER {
		frameRelay ( 1 ),
		ciscoHdlc  ( 2 )
	}
	ACCESS read-only
	STATUS mandatory
	DESCRIPTION
	"The type of traffic expected on the link for inband management and IPM."
	::= { dlcUnitConfig 35 }

-- =============================================================================
--
-- IntegratedPerformanceMonitoring
--
	dlcUnitPerformanceMonitoring OBJECT-TYPE
	SYNTAX Boolean
	ACCESS read-write
	STATUS mandatory
	DESCRIPTION
	"When true (== 2), the integrated performance monitoring (IPM) is enabled"
	::= { dlcUnitConfig 36 }

	dlcUnitPvcAutoDiscovery OBJECT-TYPE
	SYNTAX Boolean
	ACCESS read-write
	STATUS mandatory
	DESCRIPTION
	"When true (== 2), automatic discovery of DLCIs is enabled"
	::= { dlcUnitConfig 37 }


-- =============================================================================
--
-- Delay Monitoring parameters
--

	dlcUnitDelayMonitorConfig OBJECT IDENTIFIER ::= { dlcUnitConfig 38 }

	dlcDelayMonitorConfigTable OBJECT-TYPE
	SYNTAX SEQUENCE OF DlcDelayMonitorConfigEntry
	ACCESS not-accessible
	STATUS mandatory
	DESCRIPTION
	"Table of Delay Monitor test configuration."
	::= { dlcUnitDelayMonitorConfig 1 }

	dlcDelayMonitorConfigEntry OBJECT-TYPE
	SYNTAX DlcDelayMonitorConfigEntry
	ACCESS not-accessible
	STATUS mandatory
	DESCRIPTION
	"An entry in the network configuration table."
	INDEX { dlcDelayMonitorConfigIndex }
	::= { dlcDelayMonitorConfigTable 1 }

	DlcDelayMonitorConfigEntry ::=
	SEQUENCE {
	dlcDelayMonitorConfigIndex	INTEGER,
	dlcDelayMonitorState		INTEGER,
	dlcDelayMonitorTargetAddress	IpAddress,
	dlcDelayMonitorDlci		INTEGER,
	dlcDelayMonitorPort		INTEGER,
	dlcDelayMonitorInterval		INTEGER,
	dlcDelayMonitorPacketSize	INTEGER,
	dlcDelayMonitorPattern		INTEGER
	}

	dlcDelayMonitorConfigIndex OBJECT-TYPE
	SYNTAX INTEGER ( 1..4 )
	ACCESS read-only
	STATUS mandatory
	DESCRIPTION
	"Uniquely identifies which delay monitor test in the
	configuration table."
	::= { dlcDelayMonitorConfigEntry 1 }

	dlcDelayMonitorState OBJECT-TYPE
	SYNTAX INTEGER {
			disabled (1),
			enabled (2),
			running (3),
			idle (4)
	}
	ACCESS read-write
	STATUS mandatory
	DESCRIPTION
	"Specifies the status configuration of this delay monitor.
	Only setable to values disabled(1) and enabled(2) to end and start
        the test respectively. Values running(3) and idle(4) are returned
        for status of the test."
	::= { dlcDelayMonitorConfigEntry 2 }

	dlcDelayMonitorTargetAddress OBJECT-TYPE
	SYNTAX IpAddress
	ACCESS read-write
	STATUS mandatory
	DESCRIPTION
	"Specifies the address for the next delay monitor to run."
	::= { dlcDelayMonitorConfigEntry 3 }

	dlcDelayMonitorDlci OBJECT-TYPE
	SYNTAX INTEGER ( 0..1023 )
	ACCESS read-write
	STATUS mandatory
	DESCRIPTION
	"Specifies the frame relay DLCI for the next delay monitor
	to run. This value is used when the unit is in frameRelay
	InbandMode only and if the next delay monitor is not done
	on the commPort."
	::= { dlcDelayMonitorConfigEntry 4 }

	dlcDelayMonitorPort OBJECT-TYPE
	SYNTAX INTEGER {
		comm	(1),
		net	(2),
		dte	(3),
                eth     (4)
	}
	ACCESS read-write
	STATUS mandatory
	DESCRIPTION
	"Specifies which port to run the next delay monitor."
	::= { dlcDelayMonitorConfigEntry 5 }

	dlcDelayMonitorInterval OBJECT-TYPE
	SYNTAX INTEGER (1..3600)
	ACCESS read-write
	STATUS mandatory
	DESCRIPTION
	"Specifies the repetition interval in seconds between
	 packets for the next delay monitor to run."
	::= { dlcDelayMonitorConfigEntry 6 }

	dlcDelayMonitorPacketSize OBJECT-TYPE
	SYNTAX INTEGER (0..1500)
	ACCESS read-write
	STATUS mandatory
	DESCRIPTION
	"Specifies the packet size for the next delay monitor."
	::= { dlcDelayMonitorConfigEntry 7 }

	dlcDelayMonitorPattern OBJECT-TYPE
	SYNTAX INTEGER {
		ping511	(1),
		ping2047 (2),
		ping1-0 (3),
		ping-all-1 (4),
		ping-all-0 (5)
	}
	ACCESS read-write
	STATUS mandatory
	DESCRIPTION
	"Specifies the test pattern for the next delay monitor."
	::= { dlcDelayMonitorConfigEntry 8 }


-- *****************************************************************************
-- *****************************************************************************
-- *****************************************************************************
-- *****************************************************************************
--
-- Delay Monitor Status Group
--
-- To start a test running against a port,
-- just set one of the values in the dlcDelayMonitorStatusTable.
-- To stop a test, set the testType to `noTest'.
--

 dlcUnitDelayMonitorStatus OBJECT IDENTIFIER ::= { dl-new-t1 6 }

 dlcDelayMonitorStatusTable OBJECT-TYPE
  SYNTAX SEQUENCE OF DlcDelayMonitorStatusEntry
  ACCESS not-accessible
  STATUS mandatory
  DESCRIPTION
  "Table of Delay Monitor status."
  ::= { dlcUnitDelayMonitorStatus 1 }

 dlcDelayMonitorStatusEntry OBJECT-TYPE
  SYNTAX DlcDelayMonitorStatusEntry
  ACCESS not-accessible
  STATUS mandatory
  DESCRIPTION
   "An entry in the network configuration table."
  INDEX { dlcDelayMonitorStatusIndex }
  ::= { dlcDelayMonitorStatusTable 1 }

 DlcDelayMonitorStatusEntry ::=
  SEQUENCE {
   dlcDelayMonitorStatusIndex		INTEGER,
   dlcDelayMonitorSentPackets		Gauge,
   dlcDelayMonitorReceivedPackets	Gauge,
   dlcDelayMonitorErroredPackets	Gauge,
   dlcDelayMonitorMissingPackets	Gauge,
   dlcDelayMonitorAverageRoundTrip	Gauge,
   dlcDelayMonitorMaximumRoundTrip	Gauge
  }

  dlcDelayMonitorStatusIndex OBJECT-TYPE
   SYNTAX INTEGER ( 1..4 )
   ACCESS read-only
   STATUS mandatory
   DESCRIPTION
    "Uniquely identifies which Delay Monitor test in the
    configuration table."
   ::= { dlcDelayMonitorStatusEntry 1 }

  dlcDelayMonitorSentPackets OBJECT-TYPE
   SYNTAX Gauge
   ACCESS read-only
   STATUS mandatory
   DESCRIPTION
    "Number of sent packets for the currently running delay monitor
    test."
   ::= { dlcDelayMonitorStatusEntry 2 }

  dlcDelayMonitorReceivedPackets OBJECT-TYPE
   SYNTAX Gauge
   ACCESS read-only
   STATUS mandatory
   DESCRIPTION
    "Number of good received packets for the currently running
    delay monitor test."
   ::= { dlcDelayMonitorStatusEntry 3 }

  dlcDelayMonitorErroredPackets OBJECT-TYPE
   SYNTAX Gauge
   ACCESS read-only
   STATUS mandatory
   DESCRIPTION
    "Number of errored received packets for the currently running
    delay monitor test."
   ::= { dlcDelayMonitorStatusEntry 4 }

  dlcDelayMonitorMissingPackets OBJECT-TYPE
   SYNTAX Gauge
   ACCESS read-only
   STATUS mandatory
   DESCRIPTION
    "Number of missing packets for the currently running delay
    monitor test."
   ::= { dlcDelayMonitorStatusEntry 5 }

  dlcDelayMonitorAverageRoundTrip OBJECT-TYPE
   SYNTAX Gauge
   ACCESS read-only
   STATUS mandatory
   DESCRIPTION
    "Average round trip time in milli seconds for the currently
    running delay monitor test."
    ::= { dlcDelayMonitorStatusEntry 6 }

  dlcDelayMonitorMaximumRoundTrip OBJECT-TYPE
   SYNTAX Gauge
   ACCESS read-only
   STATUS mandatory
   DESCRIPTION
    "Maximum round trip time in milli seconds for the currently
    running delay monitor test."
    ::= { dlcDelayMonitorStatusEntry 7 }

-- *****************************************************************************
-- *****************************************************************************
--
-- DLCI Table
--

  dlcDLCItable OBJECT-TYPE
  SYNTAX SEQUENCE OF DlcDLCItableEntry
  ACCESS not-accessible
  STATUS mandatory
  DESCRIPTION
	"Table for current DLCI"
  ::= { dlcUnitConfig 39 }

  dlcDLCItableEntry OBJECT-TYPE
  SYNTAX DlcDLCItableEntry
  ACCESS not-accessible
  STATUS mandatory
  DESCRIPTION
	"An entry for a DLCI"
  INDEX { dlcDLCInumber, dlcDTECIR, dlcNETCIR }
  --DEFAULT get-function-async get_async_dlcDLCITable
  --DEFAULT set-function-async null_set_async
  --DEFAULT test-function-async test_async_dlcDLCITable
  --DEFAULT next-function-async next_async_dlcDLCITable
  ::= { dlcDLCItable 1 }

  DlcDLCItableEntry ::=
  SEQUENCE {
	dlcDLCInumber	INTEGER,
	dlcDTECIR	INTEGER,
	dlcNETCIR	INTEGER,
	dlcDLCIstatus	INTEGER
  }

  dlcDLCInumber OBJECT-TYPE
  SYNTAX INTEGER (1..1023)
  ACCESS read-only
  STATUS mandatory
  DESCRIPTION
	"Identifies DLCI number."
  ::= { dlcDLCItableEntry 1 }

  dlcDTECIR OBJECT-TYPE
  SYNTAX INTEGER
  ACCESS read-only
  STATUS mandatory
  DESCRIPTION
	"This DLCI's DTE Confirmed Information Rate (CIR)"
  ::= { dlcDLCItableEntry 2 }

  dlcNETCIR OBJECT-TYPE
  SYNTAX INTEGER
  ACCESS read-only
  STATUS mandatory
  DESCRIPTION
	"This DLCI's NET Confirmed Information Rate (CIR)"
  ::= { dlcDLCItableEntry 3 }

  dlcDLCIstatus OBJECT-TYPE
  SYNTAX  INTEGER {
	enabled	(1),
	disabled (2),
	active (3),
	inactive (4)
  }
  ACCESS read-write
  STATUS mandatory
  DESCRIPTION
	"This object represents status of the entry.
	When read, it will return status 'active' or 'inactive'
	representing the status of the row.
	When written, this object is used to add or delete entry.
	Setting to 'enabled' will add a new entry, setting to
	'disabled' will delete the entry."
  ::= { dlcDLCItableEntry 4 }

--
-- Utilization Table
--

  dlcUtilizationTable OBJECT-TYPE
  SYNTAX SEQUENCE OF DlcUtilTableEntry
  ACCESS not-accessible
  STATUS mandatory
  DESCRIPTION
	"Table for lifetime Utilization statistics."
  ::= { dl-new-t1 7 }

  dlcUtilTableEntry OBJECT-TYPE
  SYNTAX DlcUtilTableEntry
  ACCESS not-accessible
  STATUS mandatory
  DESCRIPTION
	"An entry for the utilization table."
  INDEX { dlcUtilDLCINumber }
  --DEFAULT get-function-async get_async_dlcUtilTable_counter
  --DEFAULT set-function-async null_set_async
  --DEFAULT test-function-async null_test_async
  --DEFAULT next-function-async next_async_dlcUtilTable
  ::= { dlcUtilizationTable 1 }

  DlcUtilTableEntry ::=
  SEQUENCE {
	dlcUtilDLCINumber	INTEGER,
	dlcUtilEncodedValue	OCTET STRING,
	dlcUtilTimestamp	Counter,
	dlcUtilLessThan20	Counter,
	dlcUtil20-40		Counter,
	dlcUtil40-60		Counter,
	dlcUtil60-80		Counter,
	dlcUtil80-100		Counter,
	dlcUtilMoreThan100	Counter
  }

  dlcUtilDLCINumber OBJECT-TYPE
  SYNTAX INTEGER
  ACCESS read-only
  STATUS mandatory
  DESCRIPTION
	"Identifies the DLCI number of the utilization statistics
	of this entry/row."
  ::= { dlcUtilTableEntry 1 }

  dlcUtilEncodedValue OBJECT-TYPE
  SYNTAX OCTET STRING
  ACCESS read-only
  STATUS mandatory
  DESCRIPTION
	"This object represents the value of the whole row	
	of the table. The intent of object is to increase
	the efficiency of retrieving the table. For each
	object value in this table, which are all of Counter
	type, it will be represented with 4 bytes of data."
  --DEFAULT get-function-async get_async_dlcUtilEncodedValue
  ::= { dlcUtilTableEntry 2 }

  dlcUtilTimestamp OBJECT-TYPE
  SYNTAX Counter
  ACCESS read-only
  STATUS mandatory
  DESCRIPTION
	"Identifies timestamp when this entry is last updated."
  ::= { dlcUtilTableEntry 3 }

  dlcUtilLessThan20 OBJECT-TYPE
  SYNTAX Counter
  ACCESS read-only
  STATUS mandatory
  DESCRIPTION
	"The number of times utilization is less than 20% of
        Committed Information Rate (CIR)."
  ::= { dlcUtilTableEntry 4 }

  dlcUtil20-40 OBJECT-TYPE
  SYNTAX Counter
  ACCESS read-only
  STATUS mandatory
  DESCRIPTION
	"The number of times utilization is between 20% and 40% of
        Committed Information Rate (CIR)."
  ::= { dlcUtilTableEntry 5 }

  dlcUtil40-60 OBJECT-TYPE
  SYNTAX Counter
  ACCESS read-only
  STATUS mandatory
  DESCRIPTION
	"The number of times utilization is between 40% and 60% of
        Committed Information Rate (CIR)."
  ::= { dlcUtilTableEntry 6 }

  dlcUtil60-80 OBJECT-TYPE
  SYNTAX Counter
  ACCESS read-only
  STATUS mandatory
  DESCRIPTION
	"The number of times utilization is between 60% and 80% of
        Committed Information Rate (CIR)."
  ::= { dlcUtilTableEntry 7 }

  dlcUtil80-100 OBJECT-TYPE
  SYNTAX Counter
  ACCESS read-only
  STATUS mandatory
  DESCRIPTION
	"The number of times utilization is between 80% and 100% of
        Committed Information Rate (CIR)."
  ::= { dlcUtilTableEntry 8 }

  dlcUtilMoreThan100 OBJECT-TYPE
  SYNTAX Counter
  ACCESS read-only
  STATUS mandatory
  DESCRIPTION
	"The number of times utilization is more than 100% of
        Committed Information Rate (CIR)."
  ::= { dlcUtilTableEntry 9 }

--
--   LMI Group
--

  dlcLMIConditioningGroup OBJECT IDENTIFIER
  ::= { dlcUnitConfig 41 }

  dlcLMIConfiguration OBJECT IDENTIFIER
  ::= { dlcLMIConditioningGroup 1}

  dlcLMIEnable OBJECT-TYPE
  SYNTAX INTEGER {
          enabled (1),
          disabled (2)
         }
  ACCESS read-write
  STATUS mandatory
  DESCRIPTION
	"This object specifies whether to enable or disable LMI
	Conditioning."
  ::= { dlcLMIConfiguration 1 }

  dlcMaintenanceDLCI OBJECT-TYPE
  SYNTAX INTEGER (16..991)
  ACCESS read-write
  STATUS mandatory
  DESCRIPTION
	"This objects specifies the status of the LMI Spoofing."
  ::= { dlcLMIConfiguration 2 }

  dlcManagementDLCI OBJECT-TYPE
  SYNTAX INTEGER (16..991)
  ACCESS read-write
  STATUS mandatory
  DESCRIPTION
	"This objects specifies the number of management DLCI
	between 16 and 991 inclusive. Must not be the same as
	maintenance DLCI. Default is 989."
  ::= { dlcLMIConfiguration 3 }

  dlcManagementDLCIEnable OBJECT-TYPE
  SYNTAX INTEGER {
          enabled (1),
          disabled (2)
         }
  ACCESS read-write
  STATUS mandatory
  DESCRIPTION
	"This object specifies whether to enable or disable
	Management DLCI."
  ::= { dlcLMIConfiguration 4 }

  dlcSpoofingProtocolType OBJECT-TYPE
  SYNTAX INTEGER {
          frf1-0  (1),
	  annex-d (2),
          annex-a (3)
         }
  ACCESS read-write
  STATUS mandatory
  DESCRIPTION
	"This objects configures which LMI message type to 'spoof',
	in the event that spoofing is activated. The possible choices
        are FRF 1.0 (Frame Relay Forum's early LMI adaptation),
	Annex A (ITU Q.933, annex A), and Annex D (ANSI T1.617, annex D).
	Default is Annex D."
  ::= { dlcLMIConfiguration 5 }
  
  dlcDTESpoofingEnable OBJECT-TYPE
  SYNTAX INTEGER {
          enabled (1),
          disabled (2)
         }
  ACCESS read-write
  STATUS mandatory
  DESCRIPTION
	"If the value of this object is 'enabled', LMI spoofing to
         the DTE port is done automatically."
  ::= { dlcLMIConfiguration 6 }
  
  dlcNetSpoofingEnable OBJECT-TYPE
  SYNTAX INTEGER {
          enabled (1),
          disabled (2)
         }
  ACCESS read-write
  STATUS mandatory
  DESCRIPTION
	"If the value of this object is 'enabled', LMI spoofing to
         the Network port is done automatically."
  ::= { dlcLMIConfiguration 7 }
  
  dlcLinkIntegrityVerificationPollingTimer OBJECT-TYPE
  SYNTAX INTEGER (5..30)
  ACCESS read-write
  STATUS mandatory
  DESCRIPTION
	"This object is the interval in seconds between Link
	Integrity Verification Messages. This is known as T391
	in the standards. Possible values are 5 to 30 seconds
	in increments of 5. Default is 10 seconds." 
  ::= { dlcLMIConfiguration 8 }

  dlcFullStatusPollingCounter OBJECT-TYPE
  SYNTAX INTEGER (1..255)
  ACCESS read-write
  STATUS mandatory
  DESCRIPTION
	"This value corresponds to N391 in the ITU and ANSI standards.
        It is the number of polling cycles of the type before the
        unit generates the full status request.
	Possible values are 1 to 255. Default is 10." 
  ::= { dlcLMIConfiguration 9 }

  dlcLMIErrorEvent OBJECT-TYPE
  SYNTAX INTEGER (1..10)
  ACCESS read-write
  STATUS mandatory
  DESCRIPTION
	"This object configures the parameter which sets the number
        of errors that can occur on the LMI link in LMI Error
        Monitored Events before reporting an interface down.
        Applies to the DTE and Network	ports. This is used in the
        same manner as the N392 parameter (N2) in the standards.
        Possible values are 1 to 10. Default is 1." 
  ::= { dlcLMIConfiguration 10 }

  dlcLMIErrorMonitorEvent OBJECT-TYPE
  SYNTAX INTEGER (1..10)
  ACCESS read-write
  STATUS mandatory
  DESCRIPTION
	"This object configures parameter which	sets the number of
        events that are used with the LMI Error Event to define
        the error ratio that is used to report when the LMI link
        is down. Applies to the DTE and Network	ports.
        This value is used in the same manner as the N393 parameter
        (N3) in the standards."
  ::= { dlcLMIConfiguration 11 }

  dlcLMIErrorFreeEvent OBJECT-TYPE
  SYNTAX INTEGER (1..10)
  ACCESS read-write
  STATUS mandatory
  DESCRIPTION
	"This object configures the parameter which sets the number
        of error-free messages that must be received in LMI Error
        Free Monitored Events prior to declaring an interface is up.
        Applies to the DTE and Network	ports. For network spoofing,
        this is the number of error-free events that will cause the
        DSU to believe the network is back up and runnig, and the
        DSU will stop spoofing. This is used in the same manner as
        the N392 parameter (N2) in the standards.
        Possible values are 1 to 10. Default is 1." 
  ::= { dlcLMIConfiguration 12 }

  dlcLMIErrorFreeMonitorEvent OBJECT-TYPE
  SYNTAX INTEGER (1..10)
  ACCESS read-write
  STATUS mandatory
  DESCRIPTION
	"This object configures parameter which	sets the number of
        events that are used with the LMI Error Free Event to define
        the error ratio that is used to report that the LMI link
        is up. Applies to the DTE and Network ports.
        This is used in the same manner as the N393 parameter (N3)
        in the standards."
  ::= { dlcLMIConfiguration 13 }

  dlcDTEResponseTimer OBJECT-TYPE
  SYNTAX INTEGER (5..30)
  ACCESS read-write
  STATUS mandatory
  DESCRIPTION
	"This object configures the parameter which sets the number
        of seconds between the sending of a status enquiry message
        and the receipt of a response. Applies to the DTE port.
        This value is similar in nature to the T392 (T2) parameter
        in the standards. Possible values are 5 to 30 in increments
        of 5. Default is 15."
  ::= { dlcLMIConfiguration 14 }

  dlcLMIUnitLocation OBJECT-TYPE
  SYNTAX INTEGER {
          cpe (1),
          co (2)
         }
  ACCESS read-write
  STATUS mandatory
  DESCRIPTION
	"This object configures where the unit is located so that LMI
         spoofing could be done properly. If 'cpe' is selected, it means
         the unit is located in Customer Premise. If 'co' is selected,
         the unit is in Central Office."
  ::= { dlcLMIConfiguration 15 }


  dlcLMIStatus OBJECT IDENTIFIER
  ::= { dlcLMIConditioningGroup 2 }

  dlcSpoofingStatus OBJECT-TYPE
  SYNTAX INTEGER {
          normal (1),
          dte-spoofing (2),
          net-spoofing (3),
          dte-and-net-spoofing (4)
         }
  ACCESS read-only
  STATUS mandatory
  DESCRIPTION
	"This object configures automatic LMI spoofing to the router.
	'True' means LMI spoofing will occur automatically,
	'False' means it's disabled."
  ::= { dlcLMIStatus 1 }

  dlcDTEInterfaceLMIStatus OBJECT-TYPE
  SYNTAX INTEGER {
          unknown (1),
          lmi-up (2),
          lmi-down (3)
         }
  ACCESS read-only
  STATUS mandatory
  DESCRIPTION
	"This object indicates the LMI status of DTE interface."
  ::= { dlcLMIStatus 2 }
  
  dlcNetInterfaceLMIStatus OBJECT-TYPE
  SYNTAX INTEGER {
          unknown (1),
          lmi-up (2),
          lmi-down (3)
         }
  ACCESS read-only
  STATUS mandatory
  DESCRIPTION
	"This object indicates the LMI status of Net interface."
  ::= { dlcLMIStatus 3 }
  
--
--   DL4200 MIB object
--

  dlcInbandDtePort OBJECT-TYPE
  SYNTAX INTEGER {
          data1 (1),
          data2 (2)
         }
  ACCESS read-write
  STATUS mandatory
  DESCRIPTION
	"This object configures which DTE port has inband management."
  ::= { dlcUnitConfig 42 }

-- *****************************************************************************
-- *****************************************************************************
-- *****************************************************************************
-- *****************************************************************************
--
-- Traps
--
 
  startTest TRAP-TYPE
  ENTERPRISE dl-new-t1
  VARIABLES { dlcUnitTestPortId, dlcUnitTestType }
  DESCRIPTION
  "Sent upon the initiation of a new test condition."
  ::= 1
 
 
  endTest TRAP-TYPE
  ENTERPRISE dl-new-t1
  VARIABLES { dlcUnitTestPortId, dlcUnitTestType }
  DESCRIPTION
  "Sent upon the termination of a test condition."
  ::= 2
 

  startAlarm TRAP-TYPE
  ENTERPRISE dl-new-t1
  VARIABLES { dlcAlarmPort, dlcAlarmType }
  DESCRIPTION
  "Indicates the beginning of a new alarm condition."
  ::= 3

 
  endAlarm TRAP-TYPE
  ENTERPRISE dl-new-t1
  VARIABLES { dlcAlarmPort, dlcAlarmType }
  DESCRIPTION
  "Indicates the end of an alarm condition."
  ::= 4


  manualConfigChange TRAP-TYPE
  ENTERPRISE dl-new-t1
  DESCRIPTION
  "Generated when the configuration was changed manually
   on the unit."
  ::= 5

END
