--
 -- retix-rx7000 MIB definitions.
 --
 -- Retix,
 -- Suite 200,
 -- Colorado Ave.,
 -- Santa Monica,
 -- CA 90404-3563.
 --
 -- Copyright Retix 1995
 --
 -- Version 3.2
 --
 -- Date July 26th 1995.
 --
 -- Purpose of This Release:
 --
 -- To support the features and functionality of the current software releases 
 -- on the ROUTERXchange product family.
 -- 
 -- Products Supported by this MIB:
 --
 -- This MIB supports the following products and software releases of the 
 -- ROUTERXchange family:
 --
 -- RX7500 and RX7550 Release 3.20 and Release 2.50
 -- RX7260 and RX7240 Release 2.30
 --
 -- This MIB contains all the objects supported by all previous releases of the
 -- products listed above, it also includes objects which earlier releases do not
 -- support.
 --
 -- This document also contains the following Draft MIBs:
 --
 --     a) dot5 (Token Ring) MIB
 --     b) ppp MIB
 --     c) a couple of ATM MIBs, one for enterprises 353 , the other for ATM
 --        Forum.
 --
 -- Since these MIBs are still on the experimental branch, they have
 -- been placed in the private retix enterprise-specific tree for now.
 --
 -- As well as the above objects the RX7000 Agent also supports RFC1213,
 -- except the EGP and TCP groups, and the following non-MIB II standard
 -- MIBs :
 --
 --     a) Dot1d Bridge MIB (RFC1286)
 --     b) frame relay MIB  (RFC1315)
 --     c) OSPF MIB         (RFC1253)
 --     d) snmpFddi MIB (RFC1285) only on the RX7500 and RX7550.
 --
 -- The frame relay tables are instanced by ifIndex which in the
 -- RX7000 is considered to be a logical port identifier, whereas
 -- Frame relay information is kept on a physical port basis, so for
 -- the purposes of this group the ifIndex considered to be a physical
 -- port instance.
 --
 --
 -- Retix Specific Traps
 --
 -- This MIB also includes a list of the propriteary traps supported by this 
 -- product family. These are defined using the recommended Trap-definition 
 -- MACRO but are commented out, for compilation purposes.
 --


      RETIX-RX7000-MIB { iso org(3) dod(6) internet(1) mgmt(2) 1}
         
      DEFINITIONS ::= BEGIN

      IMPORTS
                  mgmt, experimental, NetworkAddress, IpAddress, Counter, Gauge,
                  TimeTicks
                  FROM RFC1155-SMI
                  OBJECT-TYPE
                  FROM RFC-1212;

  --  This MIB module uses the extended  OBJECT-TYPE macro

  --  Textual conventions

          MacAddress ::= OCTET STRING (SIZE (6))    -- a 6 octet address in
                                                    -- the "canonical" order


          -- This data type is used to model textual information taken
          -- from the NVT ASCII character set.  By convention, objects
          -- with this SYNTAX  are declared as having
          --
          --      SIZE (0..255)
          DisplayString  ::= OCTET STRING

          -- 0 to 17 bytes in length containing the ASCII
          -- characters [0-9], each octet contains one digit
          -- of the address.
          X121Address    ::= OCTET STRING (SIZE(0..17))

          -- This data type is used to model media addresses.  For many
          -- types of media, this will be in a binary representation.
          -- For example, an ethernet address would be represented as
          -- a string of 6 octets.
          PhysAddress    ::= OCTET STRING

          --  The Area ID, in OSPF, has the same format as an IP Address,
          --  but has the function of defining a summarization point for
          --  Link State Advertisements

             AreaID ::= IpAddress

          --  The Router ID, in OSPF, has the same format as an IP Address,
          --  but identifies the router independent of its IP Address.

             RouterID ::= IpAddress

          --  The OSPF Metric is defined as an unsigned value in the range

             Metric    ::= INTEGER (1..'FFFF'h)
             BigMetric ::= INTEGER (1..'FFFFFF'h)

          --  Boolean Values

             TruthValue ::= INTEGER { true (1), false (2) }

          --  Status Values

             Status ::= INTEGER { enabled (1), disabled (2) }

          --  Row Creation/Deletion Values

             Validation ::= INTEGER { valid (1), invalid (2) }

          --  Time Durations measured in seconds

             PositiveInteger ::= INTEGER (1..'FFFFFFFF'h)
             HelloRange      ::= INTEGER (1..'FFFF'h)
             UpToMaxAge      ::= INTEGER (1..3600)

          --  The range of ifIndex, i.e. (1..ifNumber)

             InterfaceIndex ::= INTEGER

          --  Potential Priorities for the Designated Router Election

             DesignatedRouterPriority ::= INTEGER (0..'FF'h)

          --  Type of Service is defined as a mapping to the IP Type of
          --  Service Flags as defined in the Router Requirements
          --  Document:
          --
          --      D => Low Delay          R => Reliable Route
          --      T => High Bandwidth

          --  D T R   TOS      D T R   TOS
          --  0 0 0 =>  0      0 0 1 =>  4
          --  0 1 0 =>  8      0 1 1 => 12
          --  1 0 0 => 16      1 0 1 => 20
          --  1 1 0 => 24      1 1 1 => 28

          --  The remaining values are left for future definition.

             TOSType ::= INTEGER (0..31)

          -- Type definitions

             AtmAddress ::= OCTET STRING (SIZE (0..32))
    
          --
          -- Retix defined groups
          --

          retix        OBJECT IDENTIFIER ::= { enterprises 72 }
          rx7000       OBJECT IDENTIFIER ::= { retix 14 }
     
          station      OBJECT IDENTIFIER ::= { rx7000 1 }
          bridge       OBJECT IDENTIFIER ::= { rx7000 2 }
          ipRouter     OBJECT IDENTIFIER ::= { rx7000 3 }
          port         OBJECT IDENTIFIER ::= { rx7000 4 }
          physical     OBJECT IDENTIFIER ::= { rx7000 5 }
          multilink    OBJECT IDENTIFIER ::= { rx7000 6 }
          lapb         OBJECT IDENTIFIER ::= { rx7000 7 }
          retixwan     OBJECT IDENTIFIER ::= { rx7000 8 }
          tokenring    OBJECT IDENTIFIER ::= { rx7000 9 }
          ipx          OBJECT IDENTIFIER ::= { rx7000 10 }
          decnet       OBJECT IDENTIFIER ::= { rx7000 11 }
          x25          OBJECT IDENTIFIER ::= { rx7000 12 }
          rtxisis      OBJECT IDENTIFIER ::= { rx7000 13 }
          ethernet     OBJECT IDENTIFIER ::= { rx7000 14 }
          frmrelay     OBJECT IDENTIFIER ::= { rx7000 15 }
          bootp        OBJECT IDENTIFIER ::= { rx7000 16 }
          product      OBJECT IDENTIFIER ::= { rx7000 17 }
          rtxospf      OBJECT IDENTIFIER ::= { rx7000 18 }
          rtxfddi      OBJECT IDENTIFIER ::= { rx7000 19 }
          rtxppp       OBJECT IDENTIFIER ::= { rx7000 20 }
          rtxatm       OBJECT IDENTIFIER ::= { rx7000 21 }
          rtxsrt       OBJECT IDENTIFIER ::= { rx7000 22 }
          rtxrptr      OBJECT IDENTIFIER ::= { rx7000 23 }
          cmprsn       OBJECT IDENTIFIER ::= { rx7000 24 }
          rtxvines     OBJECT IDENTIFIER ::= { rx7000 25 }
          rtxisdn      OBJECT IDENTIFIER ::= { rx7000 26 }

        -- The experimental groups are here as part of the retix private groups
        -- when they reach RFCstatus they will be removed to the MIB 2 section.
        -- This is done to avoid incompatibility problems with vendors who may
        -- be using a different (more or less recent) version of the group.

         dot5         OBJECT IDENTIFIER ::= { rx7000 30 }
         ppp          OBJECT IDENTIFIER ::= { rx7000 32 }

         pppLink      OBJECT IDENTIFIER ::= { ppp 1 }
         pppLqr       OBJECT IDENTIFIER ::= { ppp 2 }
         pppIp        OBJECT IDENTIFIER ::= { ppp 3 }
         pppBridge    OBJECT IDENTIFIER ::= { ppp 4 }
         pppSecurity  OBJECT IDENTIFIER ::= { ppp 5 }
         pppTests     OBJECT IDENTIFIER ::= { ppp 6 }

        --
        -- The following are place holders for later
        -- elements of the PPP MIBs. When the
        -- dicated encapsulation is finished, the
        -- MIB for that encapsulation will be placed
        -- under the given OID.
        --

         pppIpx       OBJECT IDENTIFIER ::= { ppp 7 }
         pppIso       OBJECT IDENTIFIER ::= { ppp 8 }
         pppAppleTalk OBJECT IDENTIFIER ::= { ppp 9 }
         pppDECNet    OBJECT IDENTIFIER ::= { ppp 10 }

        --
        -- The retix repeater group definitions
        --

         rtxRptrBasicGroup     OBJECT IDENTIFIER ::= { rtxrptr 1 }
         rtxRptrMonitorGroup   OBJECT IDENTIFIER ::= { rtxrptr 2 }
         rtxRptrAddrTrackGroup OBJECT IDENTIFIER ::= { rtxrptr 3 }
         rtxRptrIOCard         OBJECT IDENTIFIER ::= { rtxrptr 4 }
 
          -- ATM private object groups
 
         atmRtxAtmLayerGroup  OBJECT IDENTIFIER ::= { rtxatm 1 }
         atmRtxAtmStatsGroup  OBJECT IDENTIFIER ::= { rtxatm 2 }
         atmRtxLgclPortGroup  OBJECT IDENTIFIER ::= { rtxatm 3 }
         atmRtxVcGroup        OBJECT IDENTIFIER ::= { rtxatm 4 }
         atmRtxVcStatsGroup   OBJECT IDENTIFIER ::= { rtxatm 5 }
         atmRtxPVCLayerGroup  OBJECT IDENTIFIER ::= { rtxatm 6 }
 

          -- groups for the ATM MIB module
  
          atmForum         OBJECT IDENTIFIER ::= { enterprises 353 }
          atmForumAdmin    OBJECT IDENTIFIER ::= { atmForum 1}
          atmForumUni      OBJECT IDENTIFIER ::= { atmForum 2 }
   
    
         -- Object Identifier definitions 
         -- Transmission Types
      
         atmfTransmissionTypes OBJECT IDENTIFIER ::= { atmForumAdmin 2 }
         atmfUnknownType       OBJECT IDENTIFIER ::= { atmfTransmissionTypes 1 }
         atmfSonetSTS3c        OBJECT IDENTIFIER ::= { atmfTransmissionTypes 2 }
         atmfDs3               OBJECT IDENTIFIER ::= { atmfTransmissionTypes 3 }
         atmf4B5B              OBJECT IDENTIFIER ::= { atmfTransmissionTypes 4 }
         atmf8B10B             OBJECT IDENTIFIER ::= { atmfTransmissionTypes 5 }
       
         -- Media Types
  
          atmfMediaTypes          OBJECT IDENTIFIER ::= { atmForumAdmin 3 }
          atmfMediaUnknownType    OBJECT IDENTIFIER ::= { atmfMediaTypes 1 }
          atmfMediaCoaxCable      OBJECT IDENTIFIER ::= { atmfMediaTypes 2 }
          atmfMediaSingleMode     OBJECT IDENTIFIER ::= { atmfMediaTypes 3 }
          atmfMediaMultiMode      OBJECT IDENTIFIER ::= { atmfMediaTypes 4 }
          atmfMediaStp            OBJECT IDENTIFIER ::= { atmfMediaTypes 5 }
          atmfMediaUtp            OBJECT IDENTIFIER ::= { atmfMediaTypes 6 }
   
         -- Traffic Descriptor Types
    
         atmfTrafficDescrTypes    OBJECT IDENTIFIER ::= { atmForumAdmin 4 }
         atmfNoDescriptor         OBJECT IDENTIFIER ::= { atmfTrafficDescrTypes 1 }
         atmfPeakRate             OBJECT IDENTIFIER ::= { atmfTrafficDescrTypes 2 }
     
      
         --      The MIB groups - ATM Forum
         atmfPhysicalGroup    OBJECT IDENTIFIER ::= { atmForumUni 1 }
         atmfAtmLayerGroup    OBJECT IDENTIFIER ::= { atmForumUni 2 }
         atmfAtmStatsGroup    OBJECT IDENTIFIER ::= { atmForumUni 3 }
         -- atmfVpcGroup      OBJECT IDENTIFIER ::= { atmForumUni 4 } - not supported
         -- atmfVccGroup      OBJECT IDENTIFIER ::= { atmForumUni 5 } - not supported


    --
    -- Retix Private MIB extensions, object definitions start here
    --
    -- The station Group
    --

    stationTime  OBJECT-TYPE
        SYNTAX  DisplayString (SIZE(11..13))
        ACCESS  read-write
        STATUS  mandatory
        DESCRIPTION
            "This is the current time as perceived by the station. The string
             returned is a subset of the UTC Time as specified in the Draft
             Recommendation X.409 Message Handling Systems : Presentation
             Transfer SYNTAX  and Notation (ASN.1).

             The formats acceptable when the time is being set are :

             1. 11 Octets
                    YYMMDDhhmmZ and
            
             2. 13 Octets
                    YYMMDDhhmmssZ

            Where   YY are the two digits representing the year,
                    MM are the two digits representing the month,
                    DD are the two digits representing the day,
                    hh are the two digits representing the hour,
                    mm are the two digits representing the minute,
                    ss are the two digits representing the second,
                    Z is the ASCII character 'Z'.

            The time returned by the station in response to a Get or GetNext
            request will always be the 13 octet variant.
           
            It should be noted that changing this object also changes the
            value of timestamp objects and the value of objects which return
            a time-since-an-event-occurred value. Thus, if the stationTime
            is altered the validity of time dependent objects cannot be
            guaranteed."

        ::= { station 1 }

    stationActionOnNextReset  OBJECT-TYPE
        SYNTAX  INTEGER {
                    coldStart (1),
                    warmStart (2)
                        }
        ACCESS  read-write
        STATUS  mandatory
        DESCRIPTION
            "This object is used to configure the action to be taken the next
             time the station is reset. If this object has a value of
             coldStart(1) then the station will re-initalize itself such that
             the factory default configuration is loaded from memory.
             If this object is  configured to warmStart(2) then upon the next
             reset the station will initialize with the same configuration,
             however the statistics counters and other statistics may have been
             reinitialized."
        ::= { station 2 }

    stationReset  OBJECT-TYPE
        SYNTAX  INTEGER {
                     reset    (1),
                     noAction (2)
                     }
        ACCESS  read-write
        STATUS  mandatory
        DESCRIPTION
            "This parameter is used to reset the station. The type of reset
             which occurs is dependent on the value of the
             stationActionOnNextReset object (station.2). The reset occurs
             a predefined time after the SetRequest in order that a response
             may be sent.
             Only the value reset(1) is valid for the Set operation,
             all other values will cause the generation of a badValue error.
             A value of noAction(2) is always returned in response to a
             GetRequest on this object."
        ::= { station 3 }

    stationSwRevision  OBJECT-TYPE
        SYNTAX  DisplayString (SIZE(1..16))
        ACCESS  read-only
        STATUS  mandatory
        DESCRIPTION
            "This string identifies the current system software revision.
             The maximum length of the returned string is 16 characters.
             The returned string is in ASCII format."
        ::= { station 4 }

    stationHwRevision  OBJECT-TYPE
        SYNTAX  INTEGER
        ACCESS  read-only
        STATUS  mandatory
        DESCRIPTION
            "This number identifies the current system hardware revision."
        ::= { station 5 }

    stationChassisType  OBJECT-TYPE
        SYNTAX  INTEGER {
                         typeA (1),
                         typeBMinus (2),
                         typeB (3),
                         typeC (4),
                         typeBRedundant (5),
                         typeLC (6),
                         type7240 (7),
                         type7220 (8),
                         typeENS (9),
                         type7221 (10)
                         -- chpcomSwitch6e(20),
                         -- chpcomBridge6e(21),
                         -- chpcomRouter6e(22)
                        }
        ACCESS  read-only
        STATUS  mandatory
        DESCRIPTION
            "This number identifies the chassis type of this system."
        ::= { station 6 }

    stationLEDIndication  OBJECT-TYPE
        SYNTAX  INTEGER {
                         normal (1),
                         error (2)
                        }
        ACCESS  read-only
        STATUS  mandatory
        DESCRIPTION
            "This is a number which returns an interpretation of the state of
             the LEDs on the front panel of the chassis. A value of error(2)
             indicates that the unit has encountered some error condition.
             could be one of a tempreature overheat, a software failure or a
             diagnostic error."
        ::= { station 7 }

    stationFreePFlash  OBJECT-TYPE
        SYNTAX  INTEGER
        ACCESS  read-only
        STATUS  mandatory
        DESCRIPTION
            "This is the number of free bytes remaining in Parameter Flash
             memory. This value can vary depending on the use of the device,
             as it changes as you configure the device."
        ::= { station 8 }

    stationFreeFlash  OBJECT-TYPE
        SYNTAX  INTEGER
        ACCESS  read-only
        STATUS  mandatory
        DESCRIPTION
            "This is the number of bytes which remain free in Code Flash memory,
             this is the memory used to store the code image. This figure will
             be fixed between each reload of software to the device."
        ::= { station 9 }

    stationProcessorLoading  OBJECT-TYPE
        SYNTAX  INTEGER
        ACCESS  read-only
        STATUS  mandatory
        DESCRIPTION
            "This is a measure of the loading on the RMP's processor. The
             processor loading is expressed as a percentage. The higher the
             value the greater the loading on the processor."
        ::= { station 10 }

    stationBufBytesAvailable  OBJECT-TYPE
        SYNTAX  INTEGER
        ACCESS  read-only
        STATUS  mandatory
        DESCRIPTION
            "The value of this object indicates the number of bytes remaining
             on the RMP for use in buffer allocation. It is the total number
             of bytes which remain after all the RMP's software has
             been loaded."
        ::= { station 11 }

    stationBufNumOfFreeSmlBufs  OBJECT-TYPE
        SYNTAX  INTEGER
        ACCESS  read-only
        STATUS  mandatory
        DESCRIPTION
            "The value of this object indicates the number of free small
             buffers which remain unused by the RMP."
        ::= { station 12 }

    stationBufNumOfFreeMedBufs  OBJECT-TYPE
        SYNTAX  INTEGER
        ACCESS  read-only
        STATUS  mandatory
        DESCRIPTION
            "The value of this object indicates the number of free medium
             buffers which remain unused by the RMP."
        ::= { station 13 }

    stationBufNumOfFreeLgeBufs  OBJECT-TYPE
        SYNTAX  INTEGER
        ACCESS  read-only
        STATUS  mandatory
        DESCRIPTION
            "The value of this object indicates the number of free large
             buffers which remain unused by the RMP."
        ::= { station 14 }

    stationBufNumOfSmlBufs  OBJECT-TYPE
        SYNTAX  INTEGER
        ACCESS  read-only
        STATUS  mandatory
        DESCRIPTION
            "This is the total number of free small buffers available
             at the start of day or after a reinitialization of the unit."
        ::= { station 15 }

    stationBufNumOfMedBufs  OBJECT-TYPE
        SYNTAX  INTEGER
        ACCESS  read-only
        STATUS  mandatory
        DESCRIPTION
            "This is the total number of free medium buffers available
             at the start of day or after a reinitialization of the unit."
        ::= { station 16 }

    stationBufNumOfLgeBufs  OBJECT-TYPE
        SYNTAX  INTEGER
        ACCESS  read-only
        STATUS  mandatory
        DESCRIPTION
            "This is the total number of free large buffers available
             at the start of day or after a reinitialization of the unit."
        ::= { station 17 }

    stationSlotTable  OBJECT-TYPE
        SYNTAX  SEQUENCE OF StnSlotEntry
        ACCESS  not-accessible
        STATUS  mandatory
        DESCRIPTION
            "A table of status and configuration parameters for the
             processors in each slot."
        ::= { station 18 }

    stnSlotEntry  OBJECT-TYPE
        SYNTAX  StnSlotEntry
        ACCESS  not-accessible
        STATUS  mandatory
        DESCRIPTION
             "This is an entry in the station Slot Entry Table."
        INDEX  { stnSlotIndex }
        ::= { stationSlotTable 1 }

    StnSlotEntry ::= SEQUENCE {
            stnSlotIndex
                INTEGER,
            stnSlotType
                INTEGER,
            stnSlotOperState
                INTEGER,
            stnSlotDesiredState
                INREGER,
            stnSlotProcessorLoading
                INTEGER
            }

    stnSlotIndex  OBJECT-TYPE
        SYNTAX  INTEGER
        ACCESS  read-only
        STATUS  mandatory
        DESCRIPTION
            "The value of this index uniquely identifies the Slot to which
             this entry is applicable."
        ::= { stnSlotEntry 1 }

    stnSlotType  OBJECT-TYPE
        SYNTAX  INTEGER{
                    empty (1),
                    stdFp  (2),
                    fddiFp (3)
                    }
        ACCESS  read-only
        STATUS  mandatory
        DESCRIPTION
            "This parameter indicates the type of processing card present in
             a slot. It returns empty when no FP is present."
        ::= { stnSlotEntry 2}

    stnSlotOperState  OBJECT-TYPE
        SYNTAX  INTEGER{
                   testing     (1),
                   operational (2),
                   configuring (3),
                   configMismatch (4),
                   active      (5),
                   deconfiguring (6),
                   partitioned (7),
                   removed     (8),
                   empty       (9),
                   other       (10)
                   }
        ACCESS  read-only
        STATUS  mandatory
        DESCRIPTION
            "This object indicates the current status of the particular
             processing card."
        ::= { stnSlotEntry 3}

    stnSlotDesiredState  OBJECT-TYPE
        SYNTAX  INTEGER {
                    testing     (1),
                    operational (2),
                    configuring (3),
                    configMismatch (4),
                    active        (5),
                    deconfiguring (6),
                    partitioned (7),
                    removed     (8),
                    empty       (9),
                    other       (10)
                    }
        ACCESS  read-write
        STATUS  mandatory
        DESCRIPTION
            "This object is used to alter the state of the processing card and
             display the current state.
             When the user wishes to run continuous tests on a particular
             processing card the testing(2) state is used.
             If testing is complete and the users wishes to bring the card back
             on-line then a set with a value of operational(3) is made on this
             object.
             The partitioned(7) state is used to take a particular processing
             card off-line.
             This object can only be set with values of testing(1),
             operational(2), partitioned(7) and empty(8)."
        ::= { stnSlotEntry 4 }

    stnSlotProcessorLoading  OBJECT-TYPE
        SYNTAX  INTEGER
        ACCESS  read-only
        STATUS  mandatory
        DESCRIPTION
            "This is a measure of the percentage loading on an FP's processor.
             The higher the value the greater the loading on the processor."
        ::= { stnSlotEntry 5 }

    stationSlotBufferTable  OBJECT-TYPE
        SYNTAX  SEQUENCE OF StnSlotBufEntry
        ACCESS  not-accessible
        STATUS  mandatory
        DESCRIPTION
            "This table contains configuration and statistic parameters for
             the buffers used by each forwarding processor card."
        ::= { station 19 }

    stnSlotBufEntry  OBJECT-TYPE
        SYNTAX  StnSlotBufEntry
        ACCESS  not-accessible
        STATUS  mandatory
        DESCRIPTION
             "This is an entry in the station Slot Buffer Entry Table."
        INDEX  { stnSlotBufIndex }
        ::= { stationSlotBufferTable 1 }

    StnSlotBufEntry ::= SEQUENCE {
            stnSlotBufIndex
                INTEGER,
            stnSlotBufBytesAvailable
                INTEGER,
            stnSlotBufNumOfFreeSmlBufs
                INTEGER,
            stnSlotBufNumOfFreeMedBufs
                INTEGER,
            stnSlotBufNumOfFreeLgeBufs
                INTEGER,
            stnSlotBufNumOfSmlBufs
                INTEGER,
            stnSlotBufNumOfMedBufs
                INTEGER,
            stnSlotBufNumOfLgeBufs
                INTEGER,
            stnSlotHeapBytesFree
                INTEGER,
            stnSlotHeapBytesUsed
                INTEGER,
        stnSlotBufSizeOfSmlBufs
        INTEGER,
        stnSlotBufSizeOfMedBufs
        INTEGER,
        stnSlotBufSizeOfLgeBufs
        INTEGER
            }

    stnSlotBufIndex  OBJECT-TYPE
        SYNTAX  INTEGER
        ACCESS  read-only
        STATUS  mandatory
        DESCRIPTION
            "The value of this index uniquely identifies the Slot to which
             this entry is applicable. This identifies the FP to which this 
             entry pertains."
        ::= { stnSlotBufEntry 1 }
       
    stnSlotBufBytesAvailable  OBJECT-TYPE
        SYNTAX  INTEGER
        ACCESS  read-only
        STATUS  mandatory
        DESCRIPTION
            "The value of this object indicates the number of bytes remaining
             on this card for use in buffer allocation. It is the total number
             of bytes which remain after all the processing card's software has
             been loaded."
        ::= { stnSlotBufEntry 2 }

    stnSlotBufNumOfFreeSmlBufs  OBJECT-TYPE
        SYNTAX  INTEGER
        ACCESS  read-only
        STATUS  mandatory
        DESCRIPTION
            "The value of this object indicates the number of free small
             buffers which remain unused by this processing card."
        ::= { stnSlotBufEntry 3 }

    stnSlotBufNumOfFreeMedBufs  OBJECT-TYPE
        SYNTAX  INTEGER
        ACCESS  read-only
        STATUS  mandatory
        DESCRIPTION
            "The value of this object indicates the number of free medium
             buffers which remain unused by this processing card."
        ::= { stnSlotBufEntry 4 }

    stnSlotBufNumOfFreeLgeBufs  OBJECT-TYPE
        SYNTAX  INTEGER
        ACCESS  read-only
        STATUS  mandatory
        DESCRIPTION
            "The value of this object indicates the number of free large
             buffers which remain unused by this processing card."
        ::= { stnSlotBufEntry 5 }

    stnSlotBufNumOfSmlBufs  OBJECT-TYPE
        SYNTAX  INTEGER
        ACCESS  read-only
        STATUS  mandatory
        DESCRIPTION
            "This is the total number of free small buffers available
             at the start of day or after a reinitialization of the unit."
        ::= { stnSlotBufEntry 6 }

    stnSlotBufNumOfMedBufs  OBJECT-TYPE
        SYNTAX  INTEGER
        ACCESS  read-only
        STATUS  mandatory
        DESCRIPTION
            "This is the total number of free medium buffers available
             at the start of day or after a reinitialization of the unit."
        ::= { stnSlotBufEntry 7 }

    stnSlotBufNumOfLgeBufs  OBJECT-TYPE
        SYNTAX  INTEGER
        ACCESS  read-only
        STATUS  mandatory
        DESCRIPTION
            "This is the total number of free large buffers available
             at the start of day or after a reinitialization of the unit."
        ::= { stnSlotBufEntry 8 }


    stnSlotHeapBytesFree  OBJECT-TYPE
        SYNTAX  INTEGER
        ACCESS  read-only
        STATUS  mandatory
        DESCRIPTION
            "This is the total number of free (unallocated) bytes available
             in this FP's heap space."
        ::= { stnSlotBufEntry 9 }

    stnSlotHeapBytesUsed  OBJECT-TYPE
        SYNTAX  INTEGER
        ACCESS  read-only
        STATUS  mandatory
        DESCRIPTION
            "This is the total number of used (allocated) bytes in this
             FP's heap space."
        ::= { stnSlotBufEntry 10 }

    stnSlotBufSizeOfSmlBufs  OBJECT-TYPE
        SYNTAX  INTEGER
        ACCESS  read-only
        STATUS  mandatory
        DESCRIPTION
            "The value of this object indicates the size of small
             buffers used by this processing card."
        ::= { stnSlotBufEntry 11 }

    stnSlotBufSizeOfMedBufs  OBJECT-TYPE
        SYNTAX  INTEGER
        ACCESS  read-only
        STATUS  mandatory
        DESCRIPTION
            "The value of this object indicates the size of medium
             buffers used by this processing card."
        ::= { stnSlotBufEntry 12 }

    stnSlotBufSizeOfLgeBufs  OBJECT-TYPE
        SYNTAX  INTEGER
        ACCESS  read-only
        STATUS  mandatory
        DESCRIPTION
            "The value of this object indicates the size of Large
             buffers used by this processing card."
        ::= { stnSlotBufEntry 13 }

    stationTrapDestinationTable  OBJECT-TYPE
        SYNTAX  SEQUENCE OF StationTrapDestEntry
        ACCESS  not-accessible
        STATUS  mandatory
        DESCRIPTION
            "This is the table of ip address of the stations to which the
             unit sends Trap PDUs. There is a maximum of eight entries in
             this table. To set an entry in this table, all the objects must 
             be sent in a single SET PDU."
        ::= { station 20 }

    stationTrapDestEntry  OBJECT-TYPE
        SYNTAX  StationTrapDestEntry
        ACCESS  not-accessible
        STATUS  mandatory
        DESCRIPTION
             "This is an entry in the station trap destination table."
        INDEX  { stationTrapDestIpAddr }
        ::= { stationTrapDestinationTable 1 }

    StationTrapDestEntry ::= SEQUENCE {
            stationTrapDestIpAddr
                IpAddress,
            stationTrapDestCommunityName
                DisplayString,
            stationTrapDestType
                INTEGER
            }

    stationTrapDestIpAddr  OBJECT-TYPE
        SYNTAX  IpAddress
        ACCESS  read-write
        STATUS  mandatory
        DESCRIPTION
            "This is the IP Address of a station/manager to which Trap PDU
             messages will be sent."
        ::= { stationTrapDestEntry 1 }

    stationTrapDestCommunityName  OBJECT-TYPE
        SYNTAX  DisplayString (SIZE(1..10))
        ACCESS  read-write
        STATUS  mandatory
        DESCRIPTION
            "This is the community name string which is inserted into the
             Trap PDU."
        ::= { stationTrapDestEntry 2 }

    stationTrapDestType  OBJECT-TYPE
        SYNTAX  INTEGER {
                      valid   (1),
                      invalid (2)
                        }
        ACCESS  read-write
        STATUS  mandatory
        DESCRIPTION
            "The value of this object indicates if the requested entry is valid
             or invalid.
             The value of this parameter is used to determine if the entry
             is to be added or made invalid. If an entry has a type of
             invalid(2) then it can be overwritten. A GetNext request on this
             table returns all the entries and this type field indicates
             whether they are valid (i.e. being used) or invalid."
        ::= { stationTrapDestEntry 3 }

    snmpAccessPolicyTable  OBJECT-TYPE
        SYNTAX  SEQUENCE OF SnmpAccessPolicyEntry
        ACCESS  not-accessible
        STATUS  mandatory
        DESCRIPTION
            "A table of access policy entries. There is a maximum of eight
             entries in this table. To set an entry in this table, all the 
             objects must be sent in a single SET PDU."
        ::=  { station 21 }

    snmpAccessPolicyEntry  OBJECT-TYPE
        SYNTAX  SnmpAccessPolicyEntry
        ACCESS  not-accessible
        STATUS  mandatory
        DESCRIPTION
            "This is an entry in the SNMP Access Policy Table."
        INDEX  { snmpAccessPolicyIndex }
        ::=  { snmpAccessPolicyTable 1 }

     SnmpAccessPolicyEntry ::= SEQUENCE {
            snmpAccessPolicyIndex
                INTEGER,
            snmpAccessPolicyCommunityName
                DisplayString,
            snmpAccessPolicyAccessMode
                INTEGER,
            snmpAccessPolicyType
                INTEGER
        }

    snmpAccessPolicyIndex  OBJECT-TYPE
        SYNTAX  INTEGER
        ACCESS  read-write
        STATUS  mandatory
        DESCRIPTION
            "The value of this index uniquely identifies an entry in this
             table."
        ::=  { snmpAccessPolicyEntry 1 }

    snmpAccessPolicyCommunityName  OBJECT-TYPE
        SYNTAX  DisplayString ( SIZE (0..10))
        ACCESS  read-write
        STATUS  mandatory
        DESCRIPTION
            "This is an octet string, against which the communityName field
             of the request PDU is compared. If the communityName in the request
             has been compared with all the community names in this table and
             no match has been found then authentication of the PDU fails.
             If there is an authentication failure than an authenticationFailure
             trap will be sent if the snmpEnableAuthenTraps object has a
             value of enabled(1)."
        ::=  { snmpAccessPolicyEntry 2 }

    snmpAccessPolicyAccessMode  OBJECT-TYPE
        SYNTAX  INTEGER
        ACCESS  read-write
        STATUS  mandatory
        DESCRIPTION
            "This is a bit significant field as follows :

                bit 0 - read access
                bit 1 - write access

             Setting the individual bit to 1 enables the type of access, setting
             it to 0 disables it. Thus, a value of 3 (b11) indicates
             read-write access for a PDU with the corresponding communityName."
        ::=  { snmpAccessPolicyEntry 3 }

    snmpAccessPolicyType  OBJECT-TYPE
        SYNTAX  INTEGER {
                     valid   (1),
                     invalid (2)
                     }   
        ACCESS  read-write
        STATUS  mandatory
        DESCRIPTION
            "This object is used to indicate if a particular entry in the table
             is valid or invalid. If the entry is valid(1) then  the entry's
             community name is used in the SNMP authentication process."
        ::=  { snmpAccessPolicyEntry 4 }

    stationInitiateDownload  OBJECT-TYPE
        SYNTAX  INTEGER {
                     initiate   (1),
                     noAction (2)
                     }
        ACCESS  read-write
        STATUS  mandatory
        DESCRIPTION
            "This object is used to initiate a parallel download of the
             software image to the unit. 
             This object is set to a value of initiate(1) to begin the
             parallel download procedure. A value of noAction(2) is always
             returned to a GetRequest.  This object can only be set to a
             value of initiate(1)."
        ::=  { station 22 }

    stationHeapBytesFree  OBJECT-TYPE
        SYNTAX  INTEGER
        ACCESS  read-only
        STATUS  mandatory
        DESCRIPTION
            "This object indicates the number of free (unallocated) bytes
             in the system heap area."
        ::= { station 23 }

    stationHeapBytesUsed  OBJECT-TYPE
        SYNTAX  INTEGER
        ACCESS  read-only
        STATUS  mandatory
        DESCRIPTION
            "This object indicates the number of bytes which are in use
             (allocated) by tasks using the system heap."
        ::= { station 24 }

  stationNoOfResets  OBJECT-TYPE
        SYNTAX  Counter
        ACCESS  read-only
        STATUS  mandatory
        DESCRIPTION
            "This object is a count of the number of times this station reset
             since the last coldStart was performed."
        ::= { station 25 }

   stationLastResetReason  OBJECT-TYPE
        SYNTAX  OCTET STRING (SIZE(20))
        ACCESS  read-only
        STATUS  mandatory
        DESCRIPTION
           "This string contains a description of the reason for the
           last station reset, this maybe power cycle, reset due to
           management action or some other error."
        ::= { station 26 }


    stationPowerSupplyStatus  OBJECT-TYPE
        SYNTAX  INTEGER {
                         ok (1),
                         fail (2)
                        }
        ACCESS  read-only
        STATUS  mandatory
        DESCRIPTION
        "This object gives an indication of the status of the unit's
         power supply. If this object has a value of fail(2)
         this means that a power supply failure has occurred.

         On units which do not have a redundant power supply this
         object will only have a value of ok(1)."
        ::= { station 27 }


    stationConsolePortState  OBJECT-TYPE
        SYNTAX  INTEGER {
                         active (1),
                         inactive (2)
                        }
        ACCESS  read-only
        STATUS  mandatory
        DESCRIPTION
            "This object indicates if there is a Local Management Session 
     in progress for this unit."
        ::= { station 28 }


    stationModemPortState  OBJECT-TYPE
        SYNTAX  INTEGER {
                         active (1),
                         inactive (2)
                        }
        ACCESS  read-only
        STATUS  mandatory
        DESCRIPTION
            "This object indicates if a modem port is in use."
        ::= { station 29 }


    stationNoOfTelnets  OBJECT-TYPE
        SYNTAX  Counter
        ACCESS  read-only
        STATUS  mandatory
        DESCRIPTION
            "This object is a count of the number of active telnet sessions
             for the unit."
        ::= { station 30 }


    stationTelnetTable  OBJECT-TYPE
        SYNTAX  SEQUENCE OF StationTelnetEntry
        ACCESS  not-accessible
        STATUS  mandatory
        DESCRIPTION
            "This is the table of ip address of the stations to which the
             unit can telnet. There is a maximum of eight entries in
             this table. To set an entry in this table, all the objects must 
             be sent in a single SET PDU."
        ::= { station 31 }

    stationTelnetEntry  OBJECT-TYPE
        SYNTAX  StationTelnetEntry
        ACCESS  not-accessible
        STATUS  mandatory
        DESCRIPTION
             "This is an entry in the station trap destination table."
        INDEX  { stationTelnetIpAddr }
        ::= { stationTelnetTable 1 }

    StationTelnetEntry ::= SEQUENCE {
            stationTelnetIpAddr
                IpAddress,
            stationTelnetHostName
                DisplayString,
            stationTelnetType
                INTEGER
            }

    stationTelnetIpAddr  OBJECT-TYPE
        SYNTAX  IpAddress
        ACCESS  read-write
        STATUS  mandatory
        DESCRIPTION
            "This is the IP Address of a station/manager to which you Telnet."  
        ::= { stationTelnetEntry 1 }

    stationTelnetHostName  OBJECT-TYPE
        SYNTAX  DisplayString (SIZE(1..10))
        ACCESS  read-write
        STATUS  mandatory
        DESCRIPTION
            "This is the community name string which is inserted into the
             Trap PDU."
        ::= { stationTelnetEntry 2 }

    stationTelnetType  OBJECT-TYPE
        SYNTAX  INTEGER {
                      valid   (1),
                      invalid (2)
                        }
        ACCESS  read-write
        STATUS  mandatory
        DESCRIPTION
            "The value of this object indicates if the requested entry is valid
             or invalid.
             The value of this parameter is used to determine if the entry
             is to be added or made invalid. If an entry has a type of
             invalid(2) then it can be overwritten. A GetNext request on this
             table returns all the entries and this type field indicates
             whether they are valid (i.e. being used) or invalid."
        ::= { stationTelnetEntry 3 }

    stationPflashServerIpAddress  OBJECT-TYPE
        SYNTAX  IpAddress
        ACCESS  read-write
        STATUS  mandatory
        DESCRIPTION
           "The IP Address of the server for the Parameter 
            Configuration Save/Restore."
        ::= { station 32 }

    stationPflashFileName  OBJECT-TYPE
        SYNTAX  DisplayString (SIZE (0..256))
        ACCESS  read-write
        STATUS  mandatory
        DESCRIPTION
           "The path and name of the file to be save/restore
            for the Parameter Configuration Save/Restore."
         ::= { station 33 }

     stationPflashAction  OBJECT-TYPE
         SYNTAX  INTEGER {
                    noAction (1),
                    startSave (2),
                    startRestore (3)
                    }
          ACCESS  read-write
          STATUS  mandatory
          DESCRIPTION
            "This object is used to initiate parameter save or restore.
             A value of noAction is always returned to a GetRequest"
          ::= { station 34 }

    
     stationPflashStatus  OBJECT-TYPE
        SYNTAX  INTEGER {
                    idle (1),
                    saving(2),
                    restoring (3),
                    failTFTPNoFile (4),
                    failFileExists (5),
                    errorServerResponse (6),
                    failTFTPInvalidFile (7),
                    failNetworkTimeout (8),
                    failFlashProgError (9),
                    failFlashChksumError (10),
                    errorServerData (11),
                    saveResultUnknown (12),
                    saveSuccess (13),
                    restoreSuccess (14),
                    genFailure (15)
                    }
        ACCESS  read-only
        STATUS  mandatory
        DESCRIPTION
           "This is the current status of the parameter 
            Configuration Save/Restore process."
        ::= { station 35 }


    stationInactivityTimeout  OBJECT-TYPE
     SYNTAX  INTEGER (0..60)
     ACCESS  read-write
     STATUS  mandatory
     DESCRIPTION
       "If a session is inactive for this length of time in
        minutes then it will timeout.  A value of 0 means never
             timeout.  "
     ::= {station 36}

    stationBufSizeOfSmlBufs  OBJECT-TYPE
        SYNTAX  INTEGER
        ACCESS  read-only
        STATUS  mandatory
        DESCRIPTION
            "The value of this object indicates the size of small
             buffers used by the RMP."
        ::= { station 37 }

    stationBufSizeOfMedBufs  OBJECT-TYPE
        SYNTAX  INTEGER
        ACCESS  read-only
        STATUS  mandatory
        DESCRIPTION
            "The value of this object indicates the size of medium
             buffers used by the RMP."
        ::= { station 38 }

    stationBufSizeOfLgeBufs  OBJECT-TYPE
        SYNTAX  INTEGER
        ACCESS  read-only
        STATUS  mandatory
        DESCRIPTION
            "The value of this object indicates the size of Large
             buffers used by the RMP."
        ::= { station 39 }

    stationBufferExceptions  OBJECT-TYPE
        SYNTAX  Counter
        ACCESS  read-only
        STATUS  mandatory
        DESCRIPTION
            "The value of this object indicates the number of times
             all the pools have been exhausted."
        ::= { station 40 }


   -- And heap exceptions will be 41 and there are 4 PCMCIA objects which 
   -- will be 42, 43, 44 and 45.
   --

    --
    -- The Bridge Group
    --
    -- This group augments the dot1dBridge standard MIB, RFC1286.
    --
          bridgingFacility  OBJECT-TYPE
              SYNTAX  INTEGER {
                          enabled(1),   
                          disabled(2)
                      }
              ACCESS  read-write
              STATUS  mandatory
              DESCRIPTION
                      "This object enables/disables the bridging element
              on the unit. When disabled, the unit shall not bridge
              any frames, nor shall it take part in the Spanning
              Tree protocol.  Each logical port must also be
              enabled separately"
              ::= { bridge 1 }


          brARSupport  OBJECT-TYPE
              SYNTAX  INTEGER {
                    enabled (1),
                    disabled (2)
                    }
              ACCESS  read-write
              STATUS  mandatory
              DESCRIPTION
                      "This object allows you to enable/disable Retix 4000
              series Adaptive Routing support on this box. If the
              value of this object is enabled (1) then this unit will
              allow an Adaptive Routing session to be set up across
              it."
              ::= { bridge 2 }


           brSNAPConversion  OBJECT-TYPE
              SYNTAX  INTEGER {
                    enabled (1),
                    disabled (2)
                    }
              ACCESS  read-write
              STATUS  mandatory
              DESCRIPTION
                      "This enables/disables the conversion between Ethernet
              V.2 and SNAP bridged frames on the unit. When enabled,
              EthernetV2 frames to be bridged to Token Ring or fddi
              ports are converted to SNAP Encapsulation. "
              ::= { bridge 3 }


           brSTPFacility  OBJECT-TYPE
              SYNTAX  INTEGER {
                    enabled (1),
                    disabled (2)
                    }
              ACCESS  read-write
              STATUS  mandatory
              DESCRIPTION
                      "This enables/disables the use of Spanning Tree
              Protocol on the unit. When disabled, all bridging ports
              will forward traffic and learn addresses, regardless
              of network topology."
              ::= { bridge 4 }


           brSTPVersion  OBJECT-TYPE
              SYNTAX  INTEGER {
                    revisionC ( 3 ),
                    draft9 ( 9 )
                    }
              ACCESS  read-write
              STATUS  mandatory
              DESCRIPTION
                      "This object defines which version of Spanning Tree
              is running on the unit. "
              ::= { bridge 5 }


           brSTPDomAddress  OBJECT-TYPE
              SYNTAX  PhysAddress
              ACCESS  read-write
              STATUS  mandatory
              DESCRIPTION
                      "This is the MAC Address to be used for STP Draft 9
              traffic. It is only meaningful when running STP Draft 9. "
              ::= { bridge 6 }


           brSTPResetDelayTime  OBJECT-TYPE
              SYNTAX  INTEGER (0..1800)  
              ACCESS  read-write
              STATUS  mandatory
              DESCRIPTION
                      "This is the time in seconds for which a serial port is
              assigned the maximum path Cost after it has reset. This
              is to avoid unreliable links forming the active path in
              Spanning Tree."
              ::= { bridge 7 }

          brTimeToDelete  OBJECT-TYPE
              SYNTAX  INTEGER (10..1000000)
              ACCESS  read-write
              STATUS  mandatory
              DESCRIPTION
                      "This is the time in seconds after which forgotten
              Addresses are deleted from the Filtering Database."
              ::= { bridge 8 }

    -- The Bridge Port Configuration Table

          brPortConfigTable  OBJECT-TYPE
              SYNTAX  SEQUENCE OF BrPortConfigEntry
              ACCESS  not-accessible
              STATUS  mandatory
              DESCRIPTION
                      "The Port Configuration Table."
              ::= { bridge 9 }

          brPortConfigEntry  OBJECT-TYPE
              SYNTAX  BrPortConfigEntry
              ACCESS  not-accessible
              STATUS  mandatory
              DESCRIPTION
                      "Each entry contains configurables for each port on the
              system."
              INDEX   { brPCIndex }
              ::= { brPortConfigTable 1 }

          BrPortConfigEntry ::= SEQUENCE {
                  brPCIndex
                      INTEGER,
                  brPCSecurityMode
                      INTEGER,
                  brPCSrcAddrLearning
                      INTEGER,
                  brPCSrcAddrFiltering
                      INTEGER,
                  brPCAcceptMcastAddr
                      INTEGER,
                  brPCCustomFiltering
                      INTEGER,
                  brPCTinygramComp
                      INTEGER,
                  brPCSTPFacility
                      INTEGER,
                  brPCPathCostMode
                      INTEGER,
                  brPCManPortPathCost
                      INTEGER,
                  brPCNCPState
                      INTEGER,
                  brPCGroupCheck
                      INTEGER,
                  brPCGroupMembership
                      INTEGER
                  }


          brPCIndex  OBJECT-TYPE
              SYNTAX  INTEGER
              ACCESS  read-only
              STATUS  mandatory
              DESCRIPTION
                      "This is the Logical Port Id to which this entry
              pertains."
              ::= { brPortConfigEntry 1 }

          brPCSecurityMode  OBJECT-TYPE
              SYNTAX  INTEGER {
                    enabled (1),
                    disabled (2)
                    }
              ACCESS  read-write
              STATUS  mandatory
              DESCRIPTION
                      "This sets the mode of operation for this particular
              port. When in Security Mode, frames are forwarded
              only to destination addresses which appear as FIXED
              entries in the Filtering Database"
              ::= { brPortConfigEntry 2 }

          brPCSrcAddrLearning  OBJECT-TYPE
              SYNTAX  INTEGER {
                    enabled (1),
                    disabled (2)
                    }
              ACCESS  read-write
              STATUS  mandatory
              DESCRIPTION
                      "This enables/disables Source Address Learning on this
              port."
              ::= { brPortConfigEntry 3 }
        

          brPCSrcAddrFiltering  OBJECT-TYPE
              SYNTAX  INTEGER {
                    enabled (1),
                    disabled (2)
                    }
              ACCESS  read-write
              STATUS  mandatory
              DESCRIPTION
                      "This enables/disables Source Address Filtering on this
              port. When enabled, frames will only be forwarded if their
              source address is a FIXED( non-learnt) entry in the
              Filtering database."
              ::= { brPortConfigEntry 4 }
        

          brPCAcceptMcastAddr  OBJECT-TYPE
              SYNTAX  INTEGER {
                    enabled (1),
                    disabled (2)
                    }
              ACCESS  read-write
              STATUS  mandatory
              DESCRIPTION
                      "This configures the port to either accept or ignore
              broadcast/multicast packets. In a network of bridges
              in Security Mode, this allows a path to be provided
              for multicast/broadcast frames.  If disabled, the
              port will filter these packets as normal."
              ::= { brPortConfigEntry 5 }
        
          brPCCustomFiltering  OBJECT-TYPE
              SYNTAX  INTEGER {
                    enabled (1),
                    disabled (2)
                    }
              ACCESS  read-write
              STATUS  mandatory
              DESCRIPTION
                      "This enables/disables Custom Filtering on this port.
              If enabled, then Filtering is carried out according to
              the tests and actions described in the Custom Filter
              Statement Table for this port."
              ::= { brPortConfigEntry 6 }
        

          brPCTinygramComp  OBJECT-TYPE
              SYNTAX  INTEGER {
                   enabled (1),
                   disabled (2)
                   }
              ACCESS  read-write
              STATUS  mandatory
              DESCRIPTION
                      "This enables/disables Tinygram Compression on this
              port. This is only valid for  WAN ports, using Retix
              encapsulation, connected to other RX7000 units. "
              ::= { brPortConfigEntry 7 }
        

          brPCSTPFacility  OBJECT-TYPE
              SYNTAX  INTEGER {
                    enabled (1),
                    disabled (2)
                    }
              ACCESS  read-write
              STATUS  mandatory
              DESCRIPTION
                      "This enables/disables the Spanning Tree protocol on
              a per port basis. If disabled, the port will still
              forward and learn as a bridging port but will never
              forward or transmit spanning tree BPDUs. "
              ::= { brPortConfigEntry 8 }
        

          brPCPathCostMode  OBJECT-TYPE
              SYNTAX  INTEGER {
                    manual (1),
                    low (2),
                        normal (3),
                        high (4)
                    }
              ACCESS  read-write
              STATUS  mandatory
              DESCRIPTION
                      "This sets the mode for how the Port Path Cost is to
              be calculated. If manual, then the port Path Cost is
              configureable, if any of the others, then the Path Cost
              is calculated by the system, using the attached network's
              speed. Low, medium and high modes act as scaling values
              in this calculation."
              ::= { brPortConfigEntry 9 }
        
          brPCManPortPathCost  OBJECT-TYPE
              SYNTAX  INTEGER (1..65535 )
              ACCESS  read-write
              STATUS  mandatory
              DESCRIPTION
                      "This is the manually configured Port Path Cost. It takes
              effect if the PortPathCostMode is 'manual', otherwise
              this value is not used."
              ::= { brPortConfigEntry 10 }
       
          brPCNCPState  OBJECT-TYPE
              SYNTAX  INTEGER {
                               enable (1),
                               disable (2)
                               }
              ACCESS  read-write
              STATUS  mandatory
              DESCRIPTION
                "Setting this object to a value of enable (1) causes NCP
                 negotiation to commence for this bridging element. This
                 is for use with Logical ports which are attached to PPP
                 physical ports."
              ::= { brPortConfigEntry 11 }

          brPCGroupCheck  OBJECT-TYPE
              SYNTAX  INTEGER {
                               enable (1),
                               disable (2)
                               }
              ACCESS  read-write
              STATUS  mandatory
              DESCRIPTION
                "Setting this object to a value of enable (1) causes 
                 the bridging element to invoke group checking, i.e. it 
                 checks for membership of particular groups, when forwarding
                 packets to/from this port."
              ::= { brPortConfigEntry 12 }

          brPCGroupMembership  OBJECT-TYPE
              SYNTAX  INTEGER 
              ACCESS  read-write
              STATUS  mandatory
              DESCRIPTION
                "This object is an integer which allows the user to specify
                 which groups this port belongs to. There are 32 groups,
                 1 bit per group. This value initially takes the value zero,
                 then for each of the group that the port belongs to, 2 raised
                 to the power of the group number is added to value of the
                 Membership object."
              ::= { brPortConfigEntry 13 }

    --
    -- The Custom Filter Test Table
    --
          brCstmFilterTestTable  OBJECT-TYPE
              SYNTAX  SEQUENCE OF BrCstmFilterTestEntry
              ACCESS  not-accessible
              STATUS  mandatory
              DESCRIPTION
                      "The Custom Filter Test Table "
              ::= { bridge 10 }

          brCstmFilterTestEntry  OBJECT-TYPE
              SYNTAX  BrCstmFilterTestEntry
              ACCESS  not-accessible
              STATUS  mandatory
              DESCRIPTION
                      "Each entry is a Test to be applied to frames on any
              particular port. There can be up to 64 entries in the
              table. Each test is carried out in the following manner:-
              The position in the frame which is to be filtered is found
              by using the FilterStart and Offset fields. Then the
              Mask is applied, and the resulting value is compared with
              the Value field, using the Operator to define the
              comparison. Tests are carried out according to the
              the Port's Statement table. To set an entry in the table,
              all the objects must be present in the SET PDU."
              INDEX   { brCFTTestIndex }
              ::= { brCstmFilterTestTable 1 }

          BrCstmFilterTestEntry ::= SEQUENCE {
                  brCFTTestIndex
                      INTEGER,
                  brCFTTestName
                      DisplayString,
                  brCFTFilterStart
                      INTEGER,
                  brCFTOffset
                      INTEGER,
                  brCFTMask
                      OCTET STRING,
                  brCFTOperator
                      INTEGER,
                  brCFTValue
                      OCTET STRING
          }        


          brCFTTestIndex  OBJECT-TYPE
              SYNTAX  INTEGER ( 0..63 )
              ACCESS  read-only
              STATUS  mandatory
              DESCRIPTION
                    " This is the table index number"
              ::= { brCstmFilterTestEntry 1 }

          brCFTTestName  OBJECT-TYPE
              SYNTAX  DisplayString (SIZE(0..20))
              ACCESS  read-write
              STATUS  mandatory
              DESCRIPTION
                        "This is the name given to the Test, and can be up
              to 20 characters long. It should be an ascii string."
              ::= { brCstmFilterTestEntry 2 }

          brCFTFilterStart  OBJECT-TYPE
              SYNTAX  INTEGER {
                    mac (1),
                    llc (2),
                        framelength (3)
                    }
              ACCESS  read-write
              STATUS  mandatory
              DESCRIPTION
                    "This defines the position in the frame where the
              offset is to be applied."
              ::= { brCstmFilterTestEntry 3 }

          brCFTOffset  OBJECT-TYPE
              SYNTAX  INTEGER ( 0..65535 )
              ACCESS  read-write
              STATUS  mandatory
              DESCRIPTION
                    "This is the offset to the position in the frame where
              the filter Mask is to be applied. If the FilterStart
              field is set to 'framelength' this field has no
              meaning."
              ::= { brCstmFilterTestEntry 4 }

          brCFTMask  OBJECT-TYPE
              SYNTAX  OCTET STRING (SIZE(4))
              ACCESS  read-write
              STATUS  mandatory
              DESCRIPTION
                    "This is a bit-mask value, values 0x00..0xffff ffff
              This is the filter-mask, applied to the bits specified
              by filterStart and offset."
              ::= { brCstmFilterTestEntry 5 }


          brCFTOperator  OBJECT-TYPE
              SYNTAX  INTEGER {
                    equal        (1),
                    notEqual    (2),
                    lessThan    (3),
                    greaterThan (4)
                    }
              ACCESS  read-write
              STATUS  mandatory
              DESCRIPTION
                    "The operator defines the comparison check being made."
              ::= { brCstmFilterTestEntry 6 }

          brCFTValue  OBJECT-TYPE
              SYNTAX  OCTET STRING (SIZE(4))
              ACCESS  read-write
              STATUS  mandatory
              DESCRIPTION
                    "This is the value to which the result of applying
              the mask is compared, using the operator. "
              ::= { brCstmFilterTestEntry 7 }


    --
    -- The Custom Filter Statement Table
    --
          brCstmFilterStmtTable  OBJECT-TYPE
              SYNTAX  SEQUENCE OF BrCstmFilterStmtEntry
              ACCESS  not-accessible
              STATUS  mandatory
              DESCRIPTION
                      "The Custom Filter Statement Table "
              ::= { bridge 11 }

          brCstmFilterStmtEntry  OBJECT-TYPE
              SYNTAX  BrCstmFilterStmtEntry
              ACCESS  not-accessible
              STATUS  mandatory
              DESCRIPTION
                      "Each entry is a Test statement. There are up to 16
              entries per port. Each entry links a Test with the
              actions to be carried out depending on the test's
              success or failure. To set an entry in the table,
              all the objects must be present in the SET PDU."
              INDEX   { brCFSPortNumber, brCFSStmtIndex }
              ::= { brCstmFilterStmtTable 1 }

          BrCstmFilterStmtEntry ::= SEQUENCE {
          brCFSPortNumber
              INTEGER,
                  brCFSStmtIndex
                      INTEGER,
                  brCFSTestName
                      DisplayString,
                  brCFSActionOnSuccess
                      INTEGER,
                  brCFSActionOnFailure
                      INTEGER
          }        


          brCFSPortNumber  OBJECT-TYPE
              SYNTAX  INTEGER ( 1..253 )
              ACCESS  read-only
              STATUS  mandatory
              DESCRIPTION
                    "This is the Logical Port No. for which the table
              exists."
              ::= { brCstmFilterStmtEntry 1 }

          brCFSStmtIndex  OBJECT-TYPE
              SYNTAX  INTEGER (1..16)
              ACCESS  read-only
              STATUS  mandatory
              DESCRIPTION
                      " This is the table index number"
              ::= { brCstmFilterStmtEntry 2 }

          brCFSTestName  OBJECT-TYPE
              SYNTAX  DisplayString (SIZE(1..20))
              ACCESS  read-write
              STATUS  mandatory
              DESCRIPTION
                    "This is the name of the Test to apply for this
              statement. It should match a Test name in the Custom
              Filter Test Table. It is an ascii string, of up to
              20 characters."
              ::= { brCstmFilterStmtEntry 3 }

          brCFSActionOnSuccess  OBJECT-TYPE
              SYNTAX  INTEGER (0..32784)
              ACCESS  read-write
              STATUS  mandatory
              DESCRIPTION
                    "This can have the following values and meanings:
                Values 0..7 - Forward at priority 0..7
                Value 0x7fff - Discard
                Values 0x8001..0x8010 - Use Statement No 1..16.
              This object can only be set to the values listed
              above."
              ::= { brCstmFilterStmtEntry 4 }

          brCFSActionOnFailure  OBJECT-TYPE
              SYNTAX  INTEGER (0..32784)
              ACCESS  read-write
              STATUS  mandatory
              DESCRIPTION
                    "This can have the following values and meanings:
                Values 0..7 - Forward at priority 0..7
                Value 0x7fff - Discard
                Values 0x8001..0x8010 - Use Statement No 1..16.
              This object can only be set to the values listed
              above."
              ::= { brCstmFilterStmtEntry 5 }


    --
    -- The Filtering Database Table
    --
          brFilteringDbTable  OBJECT-TYPE
              SYNTAX  SEQUENCE OF BrFilteringDbEntry
              ACCESS  not-accessible
              STATUS  mandatory
              DESCRIPTION
                      "The Filtering Database Table"
              ::= { bridge 12 }

          brFilteringDbEntry  OBJECT-TYPE
              SYNTAX  BrFilteringDbEntry
              ACCESS  not-accessible
              STATUS  mandatory
              DESCRIPTION
                    "Each entry comprises a MacAddress, a disposition,
              a port number and a type field. A Set on an entry
              of this table must set an entire entry. No partial
              sets are allowed."
              INDEX   { brFDbMacAddress, brFDbPortNumber }
              ::= { brFilteringDbTable 1 }

          BrFilteringDbEntry ::= SEQUENCE {
                  brFDbMacAddress
                      PhysAddress,
                  brFDbPortNumber
                      INTEGER,
                  brFDbDisposition
                      INTEGER,
                  brFDbType
                      INTEGER
          }        


          brFDbMacAddress  OBJECT-TYPE
              SYNTAX  PhysAddress
              ACCESS  read-write
              STATUS  mandatory
              DESCRIPTION
                    "The MacAddress in question"
              ::= { brFilteringDbEntry 1 }

          brFDbPortNumber  OBJECT-TYPE
              SYNTAX  INTEGER( 0..253 )
              ACCESS  read-write
              STATUS  mandatory
              DESCRIPTION
                    "This is the port for which this entry applies. A
              value of zero indicates that the entry applies to all
              bridge ports on the unit. All learnt entries will have
              a zero in this field."
              ::= { brFilteringDbEntry 2 }

          brFDbDisposition  OBJECT-TYPE
              SYNTAX  INTEGER (0..65535)
              ACCESS  read-write
              STATUS  mandatory
              DESCRIPTION
                    "The disposition can have the following values :-
                0 - Discard
                1..253 - Port Number to forward on.
                16385(0x4001)..16416(0x4020) - Group No. 1 to 32
                65,534( 0xfffe ) - Internal Entry
                65,535( 0xffff ) - Flood.
              All these values, except for the Internal Entry( 65534 ) can
              be used in a SET request."
              ::= { brFilteringDbEntry 3 }

          brFDbType  OBJECT-TYPE
              SYNTAX  INTEGER {
                      learnt (1),
                      fixedVolatile (2),
                      forgotten (4),
                      fixedNonVolatile (8),
                      internal (16),
                      delete (32)
              }
              ACCESS  read-write
              STATUS  mandatory
              DESCRIPTION
                      "This defines the type of the entry. A set pdu may only set
              this object to either fixedVolatile, fixedNonVolatile or delete,
              the other entries may be returned by a GET. Internal entries
              cannot be deleted."
              ::= { brFilteringDbEntry 4 }

    --
    -- Bridge Statistics
    --
          brIdentifier  OBJECT-TYPE
              SYNTAX  OCTET STRING (SIZE(8))
              ACCESS  read-only
              STATUS  mandatory
              DESCRIPTION
                      "This is the bridge Identifier, which consists of an
              8-byte hexadecimal string, the first 2 bytes specify
              the Spanning Tree priority, and the last 6, a MacAddress."
              ::= { bridge 13 }

          brTopologyChange  OBJECT-TYPE
              SYNTAX  INTEGER {
                    true (1),
                    false (2)
                    }
              ACCESS  read-only
              STATUS  mandatory
              DESCRIPTION
                    "This flag indicates that there has been a change in
              the active topology in part of the bridged Network.
              When this is true, then Filtering Db entries are
              'forgotten' when their age reaches the Forward delay
              time for the unit."
              ::= { bridge 14 }

          brLastTCNSource  OBJECT-TYPE
              SYNTAX  DisplayString (SIZE(0..20))
              ACCESS  read-only
              STATUS  mandatory
              DESCRIPTION
                    "This string tells us the source of the last topology
              change. This may be a MAC Address, if the bridge has
              received a TC BPDU, from another STP bridge, if it
              detected the change itself, then this will be a reason
              string indicating the cause of the TC. If no such TC
              has occurred then the string will have the value
              'NONE'. The maximum length of this string is 20 bytes."
              ::= { bridge 15 }

          brLastTCN  OBJECT-TYPE
              SYNTAX  INTEGER
              ACCESS  read-only
              STATUS  mandatory
              DESCRIPTION
                    "The time in seconds since the last TCN. If this has
              never happened then this will have a value of zero."
              ::= { bridge 16 }

          brActiveAddresses  OBJECT-TYPE
              SYNTAX  Counter
              ACCESS  read-only
              STATUS  mandatory
              DESCRIPTION
                    "This is a count of the Active Addresses in the
              Filtering Db, including learnt, fixed and internal entries."
              ::= { bridge 17 }

          brForgottenAddresses  OBJECT-TYPE
              SYNTAX  Counter
              ACCESS  read-only
              STATUS  mandatory
              DESCRIPTION
                    "This is a count of the forgotten addresses in the
              Filtering Database."
              ::= { bridge 18 }

      --
      -- Per Port Statistics
      --
      brPortStatsTable  OBJECT-TYPE
              SYNTAX  SEQUENCE OF BrPortStatsEntry
              ACCESS  not-accessible
              STATUS  mandatory
              DESCRIPTION
                    "This is a table of statistics which are kept per
              logical port"
              ::= { bridge 19 }

          brPortStatsEntry  OBJECT-TYPE
              SYNTAX  BrPortStatsEntry
              ACCESS  not-accessible
              STATUS  mandatory
              DESCRIPTION
                    "An entry in the Port Statistics table."
                INDEX    { brPSPortNumber }
              ::= { brPortStatsTable 1 }

      BrPortStatsEntry ::= SEQUENCE {
            brPSPortNumber
                    INTEGER,
                brPSPortState
                    INTEGER,
               brPSLastReset
                    INTEGER,
            brPSTopologyChangeAck
                INTEGER,
            brPSResetDelayTimer
                INTEGER,
            brPSForwardedFrames
                Counter,
            brPSDeletedFrames
                Counter,
            brPSNCPStatus
                INTEGER
            }


          brPSPortNumber  OBJECT-TYPE
              SYNTAX  INTEGER
              ACCESS  read-only
              STATUS  mandatory
              DESCRIPTION
                    "The Logical port number to which these statistics
              belong."
              ::= { brPortStatsEntry 1 }

          brPSPortState  OBJECT-TYPE
              SYNTAX  INTEGER {
                    active (1),
                    inactive (2)
                    }
              ACCESS  read-only
              STATUS  mandatory
              DESCRIPTION
                    "This is the forwarding state of the port."
              ::= { brPortStatsEntry 2 }

          brPSLastReset  OBJECT-TYPE
              SYNTAX  INTEGER
              ACCESS  read-only
              STATUS  mandatory
              DESCRIPTION
                       "This is the time in seconds, since the port was last
              reset or initialised."
              ::= { brPortStatsEntry 3 }

          brPSTopologyChangeAck  OBJECT-TYPE
              SYNTAX  INTEGER {
                    ack (1),
                    noAck (2)
                    }
              ACCESS  read-only
              STATUS  mandatory
              DESCRIPTION
                    "This is the state of the Spanning Tree Topology
              change acknowledge flag."
              ::= { brPortStatsEntry 4 }

          brPSResetDelayTimer  OBJECT-TYPE
              SYNTAX  INTEGER (0..65535)
              ACCESS  read-only
              STATUS  mandatory
              DESCRIPTION
                    "This is the current value of this timer, in seconds,
              for this port. This indicates the time since the last
              reset for a WAN port. When the timer is running, then
              the portPathCost for this port is set to a maximum. When
              the timer reaches the Reset DelayTime, then the
              portPathCost is reset to its normal value, and the timer
              is stopped. When the timer is stopped, it has a value
              of 0. It also has this value if this port is a LAN port."
              ::= { brPortStatsEntry 5 }

          brPSForwardedFrames  OBJECT-TYPE
              SYNTAX  Counter
              ACCESS  read-only
              STATUS  mandatory
              DESCRIPTION
                    "This is the number of transparent bridge frames
              forwarded received on this port, that have been
              forwarded to at least one other bridge port."
              ::= { brPortStatsEntry 6 }

          brPSDeletedFrames  OBJECT-TYPE
              SYNTAX  Counter
              ACCESS  read-only
              STATUS  mandatory
              DESCRIPTION
                    "This is the no. of transparent bridge frames received
              in this port, that would have been forwarded, but were
              deleted due to a lack of resources."
              ::= { brPortStatsEntry 7 }

            brPSNCPStatus  OBJECT-TYPE
              SYNTAX  INTEGER {
                    initialState  (1),
                    startingState (2),
                    closed (3),
                    stopped (4),
                    closing (5),
                    stopping (6),
                    requestSend (7),
                    ackReceived (8),
                    ackSent (9),
                    opened (10),
                    notApplicable(11)
                    }
              ACCESS  read-only
              STATUS  mandatory
              DESCRIPTION
                    "The current status of the bridging Network Control 
              Protocol. If this logical port is attached to a non-PPP 
              physical port, then the value will be notApplicable(11)."
             ::= { brPortStatsEntry 8 }


           brIPXConversion  OBJECT-TYPE
              SYNTAX  INTEGER {
                    enabled  (1),
                    disabled (2)
                    }
              ACCESS  read-write
              STATUS  mandatory
              DESCRIPTION
                      "When enabled, this object causes the bridging process
              to recognise IPX packets, and NOT perform MAC Address byte-
              swapping on them, when going to and from Token Ring networks.
              Otherwise they are treated as ordinary bridging traffic and have
              their addresses byte-swapped."
              ::= { bridge 20 }

    --
    -- The ipRouter Group
    --
    -- This group augments the MIB-II ip group.
    --
         ipARPTimeout  OBJECT-TYPE
             SYNTAX  INTEGER
             ACCESS  read-write
             STATUS  mandatory
             DESCRIPTION
                    "This parameter determines the amount of time an
             entry can stay in the Address Resolution Table.
             When the specified time elapses, the entry is
             deleted. A value of zero disables aging of entries
             in the table, this object can take the following values
             0, and any number from 3 to 1500 inclusive.. "
             ::= { ipRouter 1 }

         ipReassemblyTimeout  OBJECT-TYPE
             SYNTAX  INTEGER (1..255)
             ACCESS  read-write
             STATUS  mandatory
             DESCRIPTION
                   "This parameter specifies the number of seconds that
             the IP layer waits for all IP fragments of an IP datagram
             to be received."
             ::= { ipRouter 2 }

         ipProxyARPState  OBJECT-TYPE
             SYNTAX  INTEGER {
                         enabled (1),
                         disabled (2)
                     }
             ACCESS  read-write
             STATUS  mandatory
             DESCRIPTION
               "This parameter determines whether the ipRouter Proxy
             ARP functionality is on or off."
             ::= { ipRouter 3 }

         ipSrcQuenchState  OBJECT-TYPE
             SYNTAX  INTEGER {
                         enabled (1),
                         disabled (2)
                     }
             ACCESS  read-write
             STATUS  mandatory
             DESCRIPTION
               "This parameter determines whether ICMP Source Quench
             messages will be generated by the ipRouter."
             ::= { ipRouter 4 }

        ipRedirectState  OBJECT-TYPE
            SYNTAX  INTEGER {
                        enabled (1),
                        disabled (2)
                    }
            ACCESS  read-write
            STATUS  mandatory
            DESCRIPTION
              "This parameter determines whether ICMP Redirect
            messages will be generated by the ipRouter."
            ::= { ipRouter 5 }

        ipICMPTxRate  OBJECT-TYPE
            SYNTAX  INTEGER (1..1000)
            ACCESS  read-write
            STATUS  mandatory
            DESCRIPTION
              "This parameter controls the rate (in seconds) at which ICMP error
            messages are generated."
            ::= { ipRouter 6 }

        ipRtHashSize  OBJECT-TYPE
            SYNTAX  INTEGER (128..512)
            ACCESS  read-write
            STATUS  mandatory
            DESCRIPTION
              "This parameter determines the size of the IP routing
            hash table."
            ::= { ipRouter 7 }


        ipRIPState  OBJECT-TYPE
            SYNTAX  INTEGER {
                        enabled (1),
                        disabled (2)
                    }
            ACCESS  read-write
            STATUS  mandatory
            DESCRIPTION
              "This parameter determines if the RIP routing protocol
            is enabled globally. This parameter is set to DISABLED
            if IP routing is disabled globally."
            ::= { ipRouter 8 }

        ipBoothelperState  OBJECT-TYPE
            SYNTAX  INTEGER {
                        enabled (1),
                        disabled (2)
                    }
            ACCESS  read-write
            STATUS  mandatory
            DESCRIPTION
              "This parameter disables or enables the boothelper
            function in the ipRouter."
            ::= { ipRouter 9 }

        ipBoothelperFwdAddress  OBJECT-TYPE
            SYNTAX  IpAddress
            ACCESS  read-write
            STATUS  mandatory
            DESCRIPTION
              "This parameter is the boothelper IP forwarding address"
            ::= { ipRouter 10 }

        ipBoothelperHopCount  OBJECT-TYPE
            SYNTAX  INTEGER (1..255)
            ACCESS  read-write
            STATUS  mandatory
            DESCRIPTION
                   "This parameter is the maximum number of hops a BOOTP
                    packet can traverse."
            ::= { ipRouter 11 }

        ipSecurity  OBJECT-TYPE
            SYNTAX  INTEGER {
                   enabled (1),
                   disabled (2)
                   }
            ACCESS  read-write
            STATUS  mandatory
            DESCRIPTION
                  "This parameter enables or disables the security mechanism."
            ::= { ipRouter 12 }

        ipRouterId  OBJECT-TYPE
            SYNTAX  IpAddress
            ACCESS  read-write
            STATUS  mandatory
            DESCRIPTION
              " This Address uniquely identifies the Router in the autonomous
            system. "
            ::= { ipRouter 13 }

        ipPortConfigTable  OBJECT-TYPE
            SYNTAX  SEQUENCE OF IpPortConfigEntry
            ACCESS  not-accessible
            STATUS  mandatory
            DESCRIPTION
               "This is a table of configurable IP parameters."
            ::= { ipRouter 14 }

        ipPortConfigEntry  OBJECT-TYPE
            SYNTAX  IpPortConfigEntry
            ACCESS  not-accessible
            STATUS  mandatory
            DESCRIPTION
               "This is an entry of the ipPortConfigTable."
            INDEX   { ipPortConfigIndex }
            ::= { ipPortConfigTable 1 }

        IpPortConfigEntry ::= SEQUENCE {
            ipPortConfigIndex
                 INTEGER,
            ipPortForwarding
                 INTEGER,
            ipPortRIPState
                 INTEGER,
            ipPortPathCost
                 INTEGER,
            ipPortMACEncapsulation
                 INTEGER,
            ipPortBcastForm
                 INTEGER,
            ipPortFwdBroadcast
                 INTEGER,
            ipPortMTU
                 INTEGER,
            ipPortDisposition
                 INTEGER,
            ipPortAccessList1
                 INTEGER,
            ipPortAccessList2
                 INTEGER,
            ipPortHideNullNets
                 INTEGER,
            ipPortUDPBroadcasts
                 INTEGER
            }
  
        ipPortConfigIndex  OBJECT-TYPE
            SYNTAX  INTEGER
            ACCESS  read-only
            STATUS  mandatory
            DESCRIPTION
                    "This is the Logical Port No. to which this Table entry
            pertains."
            ::= { ipPortConfigEntry 1 }

        ipPortForwarding  OBJECT-TYPE
            SYNTAX  INTEGER {
                    enabled (1),
                    disabled (2)
                    }
            ACCESS  read-write
            STATUS  mandatory
            DESCRIPTION
                  "The indication of whether this entity is acting as
            a gateway in respect to the forwarding of datagrams
            received by, but not addressed to, this entity. IP
            gateways forward datagrams. IP hosts do not ( except
            those source-routed via the host.) Even if enabled, this
            port will not forward unless the global ipForwarding flag is
            enabled and at least one IP Address has been configured on 
            the unit."
            ::= { ipPortConfigEntry 2 }

  
        ipPortRIPState  OBJECT-TYPE
            SYNTAX  INTEGER {
                    enabled (1),
                    disabled (2)
                    }
            ACCESS  read-write
            STATUS  mandatory
            DESCRIPTION
              "This parameter determines if the RIP routing protocol
            is enabled on this interface. This parameter is set to
            DISABLED if IP routing is disabled on this port. If the global
            RIPState flag is not enabled then this port will not be enabled, 
            no matter what value this object has."
            ::= { ipPortConfigEntry 3 }

        ipPortPathCost  OBJECT-TYPE
            SYNTAX  INTEGER (1..16)
            ACCESS  read-write
            STATUS  mandatory
            DESCRIPTION
              "This parameter is the RIP path cost associated with
            logical port which is used by RIP."
            ::= { ipPortConfigEntry 4 }

        ipPortMACEncapsulation  OBJECT-TYPE
            SYNTAX  INTEGER {
                    ethernet (1),
                    ieee8023 (2)
                    }
            ACCESS  read-write
            STATUS  mandatory
            DESCRIPTION
              "This parameter determines the LAN encapsulation used
            when transmitting a datagram on this logical port.
            This parameter is only applicable for logical ports which
            are attached to LAN physical ports."
            ::= { ipPortConfigEntry 5 }

        ipPortBcastForm  OBJECT-TYPE
            SYNTAX  INTEGER {
                    ones (1),
                        zeros (2)
                        }
            ACCESS  read-write
            STATUS  mandatory
            DESCRIPTION
              "This parameter determines the directed broadcast form
            used on this interface."
            ::= { ipPortConfigEntry 6 }

        ipPortFwdBroadcast  OBJECT-TYPE
            SYNTAX  INTEGER {
                    enabled (1),
                    disabled (2)
                    }
            ACCESS  read-write
            STATUS  mandatory
            DESCRIPTION
              "This parameter determines whether directed broadcast
            datagrams are forwarded."
            ::= { ipPortConfigEntry 7 }

        ipPortMTU  OBJECT-TYPE
            SYNTAX  INTEGER 
            ACCESS  read-write
            STATUS  mandatory
            DESCRIPTION
              " Maximum size of an IP packet that can be transferred through
            this interface. Ethernet packets can have a maximum size of
            1500, IEEE802.3 packets have a maximum size of 1492. Token Ring
            have a maximum size of 4464 and FDDI has a maximum size of 4390."
            ::= { ipPortConfigEntry 8 }

        ipPortDisposition  OBJECT-TYPE
            SYNTAX  INTEGER {
                    bridge (1),
                    discard (2)
                    }
            ACCESS  read-write
            STATUS  mandatory
            DESCRIPTION
              " This parameter determines the action taken on a received IP
            datagram if routing is disabled for this port, and the
            global routing flag is set to enabled (2). If routing is
            disabled for this port and this object has a value of
            discard (2), than all IP datagrams received on this port
            which are not addressed to the unit, will be discarded."
            ::= { ipPortConfigEntry 9 }

        ipPortAccessList1  OBJECT-TYPE
            SYNTAX  INTEGER (0..31)
            ACCESS  read-write
            STATUS  mandatory
            DESCRIPTION
              "The first set of security parameters associated with this port.
            This number identifies an entry in the ipAccessList table for this
            port.  A value of 0 indicates that the default entry is used in
            which case no access checking is done."
            ::= { ipPortConfigEntry 10 }

        ipPortAccessList2  OBJECT-TYPE
            SYNTAX  INTEGER (0..31)
            ACCESS  read-write
            STATUS  mandatory
            DESCRIPTION
              "The second set of security parameters associated with this port.
            This number identifies an entry in the ipAccessList table for this
            port.  A value of 0 indicates that the default entry is used in
            which case no access checking is done."
            ::= { ipPortConfigEntry 11 }

        ipPortHideNullNets  OBJECT-TYPE
            SYNTAX  INTEGER {
                    enabled (1),
                    disabled (2)
                    }
            ACCESS  read-write
            STATUS  mandatory
            DESCRIPTION
              "Locally connected WANs are not advertised in RIP
               messages.  This allows subnetting over WANs without
               consuming large numbers of IP addresses."
            ::= { ipPortConfigEntry 12 }

        ipPortUDPBroadcasts   OBJECT-TYPE
            SYNTAX  INTEGER {
                    enabled (1),
                    disabled (2)
                    }
            ACCESS  read-write
            STATUS  mandatory
            DESCRIPTION
              "When enabled UDP broadcasts are frowarded on this port.
               Set to a value of disabled (2) to prevent UDP broadcast 
               from being forwardrd on this port and so prevent broadcast 
               stroms arising from loops in the network etc."
            ::= { ipPortConfigEntry 13 }

        ipPortAddrTable  OBJECT-TYPE
            SYNTAX  SEQUENCE OF IpPortAddrEntry
            ACCESS  not-accessible
            STATUS  mandatory
            DESCRIPTION
              "This table is a table of IP addresses and masks associated
            with each logical port."
            ::= { ipRouter 15 }

        ipPortAddrEntry  OBJECT-TYPE
            SYNTAX  IpPortAddrEntry
            ACCESS  not-accessible
            STATUS  mandatory
            DESCRIPTION
              "An entry of the IP port address table. All the objects in an 
            entry must be supplied in a single SET PDU."
            INDEX   { ipPortAddrIndex, ipPortIpAddress }
            ::= { ipPortAddrTable 1 }

        IpPortAddrEntry ::= SEQUENCE {
            ipPortAddrIndex
                 INTEGER,
            ipPortIpAddress
                 IpAddress,
            ipPortIpAddressMask
                 IpAddress,
            ipPortAddrType
                INTEGER    
            }

        ipPortAddrIndex  OBJECT-TYPE
            SYNTAX  INTEGER
            ACCESS  read-only
            STATUS  mandatory
            DESCRIPTION
              "An index into the ipPortAddr Table which identifies the 
            Logical Port No, for which the address is valid."
            ::= { ipPortAddrEntry 1 }

        ipPortIpAddress  OBJECT-TYPE
            SYNTAX  IpAddress
            ACCESS  read-write
            STATUS  mandatory
            DESCRIPTION
              "The IP Address of the logical port. There can be up to five IP
            addresses associated with each port. This object combined
            with the ipPortAddrIndex object constitutes the instance value
            used to uniquely identify and entry in this table."
            ::= { ipPortAddrEntry 2 }

        ipPortIpAddressMask  OBJECT-TYPE
            SYNTAX  IpAddress
            ACCESS  read-write
            STATUS  mandatory
            DESCRIPTION
              "The IP address mask associated with the IP address. "
            ::= { ipPortAddrEntry 3 }

          ipPortAddrType  OBJECT-TYPE
            SYNTAX  INTEGER {
                    valid(1),        -- none of the following
                    invalid(2)      -- an invalidated mapping
                    }
            ACCESS  read-write
            STATUS  mandatory
            DESCRIPTION
                "If the value of this object is valid(1) and we are performing
            a SetRequest then this is a request to add an entry to the
            table. If a value of invalid(2) is passed in the SetRequest,
            along with the other objects in an entry then this is a
            request to  delete the entry from the table."
              ::= { ipPortAddrEntry 4 }

        -- The ICMP timer values

        ipDestUnreachLastRx  OBJECT-TYPE
            SYNTAX  DisplayString (SIZE(13))
            ACCESS  read-only
            STATUS  mandatory
            DESCRIPTION
              " The last time an ICMP Destination Unreachable message was
            received. The format of the returned OctetString is the same
            as that define in section b. of the definition of the
            stationTime (station.1) object."
            ::= { ipRouter 16 }

        ipDestUnreachLastTx  OBJECT-TYPE
            SYNTAX  DisplayString (SIZE(13))
            ACCESS  read-only
            STATUS  mandatory
            DESCRIPTION
              " This is the last time an ICMP Destination Unreachable Message
            was sent. The format of the returned OctetString is the same
            as that define in section b. of the definition of the
            stationTime (station.1) object."
            ::= { ipRouter 17 }

        ipSourceQuenchLastRx  OBJECT-TYPE
            SYNTAX  DisplayString (SIZE(13))
            ACCESS  read-only
            STATUS  mandatory
            DESCRIPTION
              "This is the last time an ICMP Source Quench message was received.
            The format of the returned OctetString is the same
            as that define in section b. of the definition of the
            stationTime (station.1) object."
            ::= { ipRouter 18 }

        ipSourceQuenchLastTx  OBJECT-TYPE
            SYNTAX  DisplayString (SIZE(13))
            ACCESS  read-only
            STATUS  mandatory
            DESCRIPTION
              " This is the last time an ICMP Source Quench message was sent.
            The format of the returned OctetString is the same
            as that define in section b. of the definition of the
            stationTime (station.1) object."
            ::= { ipRouter 19 }

        ipRedirectsLastRx  OBJECT-TYPE
            SYNTAX  DisplayString (SIZE(13))
            ACCESS  read-only
            STATUS  mandatory
            DESCRIPTION
              " This is the last time an ICMP Redirects message was received.
            The format of the returned OctetString is the same
            as that define in section b. of the definition of the
            stationTime (station.1) object."
            ::= { ipRouter 20 }

        ipRedirectsLastTx  OBJECT-TYPE
            SYNTAX  DisplayString (SIZE(13))
            ACCESS  read-only
            STATUS  mandatory
            DESCRIPTION
              " This is the last time an ICMP Redirects message was sent.
            The format of the returned OctetString is the same
            as that define in section b. of the definition of the
               stationTime (station.1) object."
            ::= { ipRouter 21 }

        ipEchoRequestLastRx  OBJECT-TYPE
            SYNTAX  DisplayString (SIZE(13))
            ACCESS  read-only
            STATUS  mandatory
            DESCRIPTION
              " This is the last time an ICMP Echo Requests message was sent.
            The format of the returned OctetString is the same
            as that define in section b. of the definition of the
            stationTime (station.1) object."
            ::= { ipRouter 22 }

        ipEchoRequestLastTx  OBJECT-TYPE
            SYNTAX  DisplayString (SIZE(13))
            ACCESS  read-only
            STATUS  mandatory
            DESCRIPTION
              " This is the last time an ICMP Echo Request message was sent.
            The format of the returned OctetString is the same
            as that define in section b. of the definition of the
            stationTime (station.1) object."
            ::= { ipRouter 23 }

        ipTimeExceededLastRx  OBJECT-TYPE
            SYNTAX  DisplayString (SIZE(13))
            ACCESS  read-only
            STATUS  mandatory
            DESCRIPTION
              "This is the last time an ICMP Time Exceeded message was received.
            The format of the returned OctetString is the same
            as that define in section b. of the definition of the
            stationTime (station.1) object."
            ::= { ipRouter 24 }

        ipTimeExceededLastTx  OBJECT-TYPE
            SYNTAX  DisplayString (SIZE(13))
            ACCESS  read-only
            STATUS  mandatory
            DESCRIPTION
               " This is the last time an ICMP Time Exceeded message was sent.
            The format of the returned OctetString is the same
            as that define in section b. of the definition of the
            stationTime (station.1) object."
            ::= { ipRouter 25 }

        ipParamProbLastRx  OBJECT-TYPE
            SYNTAX  DisplayString (SIZE(13))
            ACCESS  read-only
            STATUS  mandatory
            DESCRIPTION
               " This is the last time an ICMP Parameter Problem message was
            received. The format of the returned OctetString is the same
            as that define in section b. of the definition of the
            stationTime (station.1) object."
            ::= { ipRouter 26 }

        ipParamProbLastTx  OBJECT-TYPE
            SYNTAX  DisplayString (SIZE(13))
            ACCESS  read-only
            STATUS  mandatory
            DESCRIPTION
               " This is the last time an ICMP Parameter Problem message was
            sent. The format of the  returned OctetString is the same
            as that define in section b. of the definition of the
            stationTime (station.1) object."
             ::= { ipRouter 27 }

        ipAccessViolations  OBJECT-TYPE
            SYNTAX  Counter
            ACCESS  read-only
            STATUS  mandatory
            DESCRIPTION
               " This is a count of the number of access violations which have
            occurred for the entire unit."
            ::= { ipRouter 28 }

        ipOtherDiscards  OBJECT-TYPE
            SYNTAX  Counter
            ACCESS  read-only
            STATUS  mandatory
            DESCRIPTION
              "This is the total number of IP datagrams discarded for the 
            entire unit, for other reasons, eg the incorrect configuration 
            of a WAN port, etc"
            ::= { ipRouter 29 }

        ipOutTransmits  OBJECT-TYPE
            SYNTAX  Counter
            ACCESS  read-only
            STATUS  mandatory
            DESCRIPTION
              "This is the total number of IP datagrams which have been
            transmitted by this unit."
            ::= { ipRouter 30 }


    -- Table of per port statistics

        ipPortStatsTable  OBJECT-TYPE
            SYNTAX  SEQUENCE OF IpPortStatsEntry
            ACCESS  not-accessible
            STATUS  mandatory
            DESCRIPTION
              "This is a table of IP logical port statistics parameters."
            ::= { ipRouter 31 }

    ipPortStatsEntry  OBJECT-TYPE
            SYNTAX  IpPortStatsEntry
            ACCESS  not-accessible
            STATUS  mandatory
            DESCRIPTION
              "An entry of the Stats table."
            INDEX   { ipPortStatsIndex }
            ::= { ipPortStatsTable 1 }

        IpPortStatsEntry ::= SEQUENCE {
            ipPortStatsIndex
                 INTEGER,
            ipPortInReceives
                 Counter,
            ipPortInHdrErrors
                 Counter,
            ipPortInAddrErrors
                 Counter,
            ipPortForwDatagrams
                 Counter,
            ipPortInDiscards
                 Counter,
            ipPortInDelivers
                 Counter,
            ipPortOutTransmits
                 Counter,
            ipPortOutNoRoutes
                 Counter,
            ipPortOtherDiscards
                 Counter,
            ipPortICMPInMsgs
                 Counter,
            ipPortICMPInErrors
                 Counter,
            ipPortICMPInDestUnreachs
                 Counter,
            ipPortICMPInTimeExcds
                 Counter,
            ipPortICMPInParmProbs
                 Counter,
            ipPortICMPInSrcQuenchs
                 Counter,
            ipPortICMPInRedirects
                 Counter,
            ipPortICMPInEchos
                 Counter,
            ipPortICMPInEchoReps
                 Counter,
            ipPortICMPInTimestamps
                 Counter,
            ipPortICMPInTimestampReps
                 Counter,
            ipPortICMPInAddrMasks
                 Counter,
            ipPortICMPInAddrMaskReps
                 Counter,
            ipPortICMPOutMsgs
                 Counter,
            ipPortICMPOutErrors
                 Counter,
            ipPortICMPOutDestUnreachs
                 Counter,
            ipPortICMPOutTimeExcds
                 Counter,
            ipPortICMPOutParmProbs
                 Counter,
            ipPortICMPOutSrcQuenchs
                 Counter,
            ipPortICMPOutRedirects
                 Counter,
            ipPortICMPOutEchos
                 Counter,
            ipPortICMPOutEchoReps
                 Counter,
            ipPortICMPOutTimestamps
                 Counter,
            ipPortICMPOutTimestampReps
                 Counter,
            ipPortICMPOutAddrMasks
                 Counter,
            ipPortICMPOutAddrMaskReps
                 Counter
                }

        ipPortStatsIndex  OBJECT-TYPE
            SYNTAX  INTEGER
            ACCESS  read-only
            STATUS  mandatory
            DESCRIPTION
              "This index is a logical port number and uniquely identifies an 
               entry in this table."
            ::= { ipPortStatsEntry 1 }

        ipPortInReceives  OBJECT-TYPE
            SYNTAX  Counter
            ACCESS  read-only
            STATUS  mandatory
            DESCRIPTION
              "The total number of input datagrams received on this
               port, including those received in errors."
            ::= { ipPortStatsEntry 2 }
  
        ipPortInHdrErrors  OBJECT-TYPE
            SYNTAX  Counter
            ACCESS  read-only
            STATUS  mandatory
            DESCRIPTION
              "The number of input datagrams discarded due to errors
               in their IP headers, including bad checksums, version
               number mismatch, other format errors, time-to-live
               exceeded errors, errors discovered in processing
               their routines, etc."
            ::= { ipPortStatsEntry 3 }
  
        ipPortInAddrErrors  OBJECT-TYPE
            SYNTAX  Counter
            ACCESS  read-only
            STATUS  mandatory
            DESCRIPTION
              "The number of input datagrams discarded because the
               IP headers destination field was not a valid address
               to be received at this entity. This count includes
               invalid addresses (e.g. 0.0.0.0) and addresses of
               unsupported classes (e.g. class E). For entities which
               are not IP gateways and therefore do not forward
               datagrams, this counter includes datagrams discarded
               because the destination address was not a local
               address."
            ::= { ipPortStatsEntry 4 }

        ipPortForwDatagrams  OBJECT-TYPE
            SYNTAX  Counter
            ACCESS  read-only
            STATUS  mandatory
            DESCRIPTION
              "The number of input datagrams forwarded or
               source-routed via this entity."
            ::= { ipPortStatsEntry 5 }
  

        ipPortInDiscards  OBJECT-TYPE
            SYNTAX  Counter
            ACCESS  read-only
            STATUS  mandatory
            DESCRIPTION
              "The number of input IP datagrams for which no problem
               was encountered to prevent their further processing,
               but were discarded (e.g. lack of buffer space). This
               does not include datagrams discarded while awaiting
               reassembly."
           ::= { ipPortStatsEntry 6 }

        ipPortInDelivers  OBJECT-TYPE
            SYNTAX  Counter
            ACCESS  read-only
            STATUS  mandatory
            DESCRIPTION
              "The total number of input datagrams successfully
               delivered to IP user protocols ( including ICMP)."
            ::= { ipPortStatsEntry 7 }

        ipPortOutTransmits  OBJECT-TYPE
            SYNTAX  Counter
            ACCESS  read-only
            STATUS  mandatory
            DESCRIPTION
              "The total number of IP datagrams which have been
               transmitted on this port."
            ::= { ipPortStatsEntry 8 }


        ipPortOutNoRoutes  OBJECT-TYPE
            SYNTAX  Counter
            ACCESS  read-only
            STATUS  mandatory
            DESCRIPTION
              "The number of IP datagrams discarded because no route
               could be found to transmit them to their destination."
            ::= { ipPortStatsEntry 9 }

        ipPortOtherDiscards  OBJECT-TYPE
            SYNTAX  Counter
            ACCESS  read-only
            STATUS  mandatory
            DESCRIPTION
              "The number of IP datagrams discarded for other reasons, eg
               the incorrect configuration of a WAN port, etc"
            ::= { ipPortStatsEntry 10 }

          ipPortICMPInMsgs  OBJECT-TYPE
              SYNTAX  Counter
              ACCESS  read-only
              STATUS  mandatory
              DESCRIPTION
                "The number of ICMP messages which the entity received
                 on this port. Note that this counter includes
                 all those counted by icmpInErrors."
              ::= { ipPortStatsEntry 11 }

         ipPortICMPInErrors  OBJECT-TYPE
              SYNTAX  Counter
              ACCESS  read-only
              STATUS  mandatory
              DESCRIPTION
                "The number of ICMP messages which the entity
                 received on this port, but determined as having
                 ICMP-specific errors (bad ICMP checksums, bad length,
                 etc.)."
              ::= { ipPortStatsEntry 12 }

          ipPortICMPInDestUnreachs  OBJECT-TYPE
              SYNTAX  Counter
              ACCESS  read-only
              STATUS  mandatory
              DESCRIPTION
                "The number of ICMP Destination Unreachable
                 messages received on this port."
              ::= { ipPortStatsEntry 13 }

          ipPortICMPInTimeExcds  OBJECT-TYPE
              SYNTAX  Counter
              ACCESS  read-only
              STATUS  mandatory
              DESCRIPTION
                "The number of ICMP Time Exceeded messages received on 
                 this port."
              ::= { ipPortStatsEntry 14 }

          ipPortICMPInParmProbs  OBJECT-TYPE
              SYNTAX  Counter
              ACCESS  read-only
              STATUS  mandatory
              DESCRIPTION
                "The number of ICMP Parameter Problem messages
                 received on this port."
              ::= { ipPortStatsEntry 15 }

          ipPortICMPInSrcQuenchs  OBJECT-TYPE
              SYNTAX  Counter
              ACCESS  read-only
              STATUS  mandatory
              DESCRIPTION
                "The number of ICMP Source Quench messages received on 
                 this port."
              ::= { ipPortStatsEntry 16 }

          ipPortICMPInRedirects  OBJECT-TYPE
              SYNTAX  Counter
              ACCESS  read-only
              STATUS  mandatory
              DESCRIPTION
                "The number of ICMP Redirect messages received on this
                 port."
              ::= { ipPortStatsEntry 17 }

          ipPortICMPInEchos  OBJECT-TYPE
              SYNTAX  Counter
              ACCESS  read-only
              STATUS  mandatory
              DESCRIPTION
                "The number of ICMP Echo (request) messages
                 received on this port."
              ::= { ipPortStatsEntry 18 }

          ipPortICMPInEchoReps  OBJECT-TYPE
              SYNTAX  Counter
              ACCESS  read-only
              STATUS  mandatory
              DESCRIPTION
                "The number of ICMP Echo Reply messages received
                 on this port."
              ::= { ipPortStatsEntry 19 }

          ipPortICMPInTimestamps  OBJECT-TYPE
              SYNTAX  Counter
              ACCESS  read-only
              STATUS  mandatory
              DESCRIPTION
                "The number of ICMP Timestamp (request) messages
                 received on this port."
              ::= { ipPortStatsEntry 20 }

          ipPortICMPInTimestampReps  OBJECT-TYPE
              SYNTAX  Counter
              ACCESS  read-only
              STATUS  mandatory
              DESCRIPTION
                "The number of ICMP Timestamp Reply messages
                received on this port."
              ::= { ipPortStatsEntry 21 }

          ipPortICMPInAddrMasks  OBJECT-TYPE
              SYNTAX  Counter
              ACCESS  read-only
              STATUS  mandatory
              DESCRIPTION
                "The number of ICMP Address Mask Request messages
                received on this port."
              ::= { ipPortStatsEntry 22 }

          ipPortICMPInAddrMaskReps  OBJECT-TYPE
              SYNTAX  Counter
              ACCESS  read-only
              STATUS  mandatory
              DESCRIPTION
                "The number of ICMP Address Mask Reply messages
                received on this port."
              ::= { ipPortStatsEntry 23 }

          ipPortICMPOutMsgs  OBJECT-TYPE
              SYNTAX  Counter
              ACCESS  read-only
              STATUS  mandatory
              DESCRIPTION
                "The total number of ICMP messages which this
                entity attempted to send on this port.  Note that
                this counter includes all those counted by
                ipPortICMPOutErrors."
              ::= { ipPortStatsEntry 24 }

          ipPortICMPOutErrors  OBJECT-TYPE
              SYNTAX  Counter
              ACCESS  read-only
              STATUS  mandatory
              DESCRIPTION
                "The number of ICMP messages which this entity did
                not send on this port due to problems discovered within
                ICMP such as a lack of buffers.  This value should not
                include errors discovered outside the ICMP layer
                such as the inability of IP to route the resultant
                datagram.  In some implementations there may be no
                types of error which contribute to this counter's
                value."
              ::= { ipPortStatsEntry 25 }

          ipPortICMPOutDestUnreachs  OBJECT-TYPE
              SYNTAX  Counter
              ACCESS  read-only
              STATUS  mandatory
              DESCRIPTION
                "The number of ICMP Destination Unreachable
                messages sent from this port."
              ::= { ipPortStatsEntry 26 }

          ipPortICMPOutTimeExcds  OBJECT-TYPE
              SYNTAX  Counter
              ACCESS  read-only
              STATUS  mandatory
              DESCRIPTION
                "The number of ICMP Time Exceeded messages sent
                 from this port."
              ::= { ipPortStatsEntry 27 }

          ipPortICMPOutParmProbs  OBJECT-TYPE
              SYNTAX  Counter
              ACCESS  read-only
              STATUS  mandatory
              DESCRIPTION
                "The number of ICMP Parameter Problem messages
                sent from this port."
              ::= { ipPortStatsEntry 28 }

          ipPortICMPOutSrcQuenchs  OBJECT-TYPE
              SYNTAX  Counter
              ACCESS  read-only
              STATUS  mandatory
              DESCRIPTION
                "The number of ICMP Source Quench messages sent
                 from this port."
              ::= { ipPortStatsEntry 29 }

          ipPortICMPOutRedirects  OBJECT-TYPE
              SYNTAX  Counter
              ACCESS  read-only
              STATUS  mandatory
              DESCRIPTION
                "The number of ICMP Redirect messages sent from this port.
                For a host, this object will always be zero, since hosts
                do not send redirects."
              ::= { ipPortStatsEntry 30 }

          ipPortICMPOutEchos  OBJECT-TYPE
              SYNTAX  Counter
              ACCESS  read-only
              STATUS  mandatory
              DESCRIPTION
                "The number of ICMP Echo (request) messages sent
                from this port."
              ::= { ipPortStatsEntry 31 }

          ipPortICMPOutEchoReps  OBJECT-TYPE
              SYNTAX  Counter
              ACCESS  read-only
              STATUS  mandatory
              DESCRIPTION
                "The number of ICMP Echo Reply messages sent from
                 this port."
              ::= { ipPortStatsEntry 32 }

          ipPortICMPOutTimestamps  OBJECT-TYPE
              SYNTAX  Counter
              ACCESS  read-only
              STATUS  mandatory
              DESCRIPTION
                "The number of ICMP Timestamp (request) messages
                sent from this port."
              ::= { ipPortStatsEntry 33 }

          ipPortICMPOutTimestampReps  OBJECT-TYPE
              SYNTAX  Counter
              ACCESS  read-only
              STATUS  mandatory
              DESCRIPTION
                "The number of ICMP Timestamp Reply messages
                sent from this port."
              ::= { ipPortStatsEntry 34 }

          ipPortICMPOutAddrMasks  OBJECT-TYPE
              SYNTAX  Counter
              ACCESS  read-only
              STATUS  mandatory
              DESCRIPTION
                "The number of ICMP Address Mask Request messages
                sent from this port."
              ::= { ipPortStatsEntry 35 }

          ipPortICMPOutAddrMaskReps  OBJECT-TYPE
              SYNTAX  Counter
              ACCESS  read-only
              STATUS  mandatory
              DESCRIPTION
                "The number of ICMP Address Mask Reply messages
                sent from this port."
              ::= { ipPortStatsEntry 36 }


    -- Part of the security objects, its the access list table

        ipAccessListTable  OBJECT-TYPE
           SYNTAX  SEQUENCE OF IpAccessListEntry
           ACCESS  not-accessible
           STATUS  mandatory
           DESCRIPTION
             " This is a list of the parameters used for access checking."
           ::= { ipRouter 32 }

        ipAccessListEntry  OBJECT-TYPE
           SYNTAX  IpAccessListEntry
           ACCESS  not-accessible
           STATUS  mandatory
           DESCRIPTION
             " An entry in the Access List Table. To set an entry in this table
             ALL the objects must be supplied in a single SET PDU.?"
           INDEX  { ipAccessListIndex }
           ::= { ipAccessListTable 1 }
    
        IpAccessListEntry  ::= SEQUENCE {
               ipAccessListIndex
                   INTEGER,
               ipTxCheck
                   INTEGER,
               ipNoMatchTxAction
                   INTEGER,
               ipRxCheck
                   INTEGER,
               ipNoMatchRxAction
                   INTEGER,
               ipIcmpGeneration
                   INTEGER
            }

       ipAccessListIndex  OBJECT-TYPE
          SYNTAX  INTEGER
          ACCESS  read-only
          STATUS  mandatory
          DESCRIPTION
             " The index which uniquely identifies this entry.
               There is a maximum of 32 entries in this table."
          ::= { ipAccessListEntry 1 }

       ipTxCheck  OBJECT-TYPE
          SYNTAX  INTEGER {
                  enabled (1),
                  disabled (2)
                  }
          ACCESS  read-write
          STATUS  mandatory
          DESCRIPTION
             "Indicates whether checking of IP packets to be transmitted is
              enabled or not."
          ::= { ipAccessListEntry 2 }

        ipNoMatchTxAction  OBJECT-TYPE
           SYNTAX  INTEGER {
                    pass (1),
                    block (2)
                    }
           ACCESS  read-write
           STATUS  mandatory
           DESCRIPTION
              " When an IP datagram is to be transmitted, the source and
                destination addresses are &ed with their masks and compared
                with those in the security entry. This object indicates the
                action to be taken if these two don't match."
           ::= { ipAccessListEntry 3 }

         ipRxCheck  OBJECT-TYPE
            SYNTAX  INTEGER {
                    enabled (1),
                    disabled (2)
                    }
            ACCESS  read-write
            STATUS  mandatory
            DESCRIPTION
               " If this parameter has a value of enabled(1), then all received
                 IP packets are checked."
            ::= { ipAccessListEntry 4 }

        ipNoMatchRxAction  OBJECT-TYPE
           SYNTAX  INTEGER {
                   pass (1),
                   block (2)
                   }
           ACCESS  read-write
           STATUS  mandatory
           DESCRIPTION
              " When an IP datagram is received, the source and
                destination addresses are &ed with their masks and compared
                with those in the security entry. This object indicates the
                action to be taken if these two don't match."
           ::= { ipAccessListEntry 5 }
         
        ipIcmpGeneration  OBJECT-TYPE
           SYNTAX  INTEGER {
                   enabled (1),
                   disabled (2)
                   }
           ACCESS  read-write
           STATUS  mandatory
           DESCRIPTION
             " This parameter indicates whether ICMP messages are generated
               or not."
           ::= { ipAccessListEntry 6 } 
          

        ipIfSecurityTable  OBJECT-TYPE
           SYNTAX  SEQUENCE OF IpIfSecurityEntry
           ACCESS  not-accessible
           STATUS  mandatory
           DESCRIPTION
              "A table of security parameters."
           ::= { ipRouter 33 }

        ipIfSecurityEntry  OBJECT-TYPE
           SYNTAX  IpIfSecurityEntry
           ACCESS  not-accessible
           STATUS  mandatory
           DESCRIPTION
             "An entry in the security table. For each entry in the Access List
             Table, there is a list(table) of Security entries. Therefore, as 
             each port has 2 access List entries associated with it, then the
             port has access to two separate lists of security entries within
             this table. To set an entry in this table, ALL the objects must be
             supplied in a single SET PDU."
           INDEX  { ipIfSecurityAccessListNum,
                    ipIfSecurityIndex  }
           ::= { ipIfSecurityTable 1 }

        IpIfSecurityEntry  ::= SEQUENCE {
           ipIfSecurityAccessListNum
               INTEGER,
           ipIfSecurityIndex
               INTEGER,
           ipIfSecurityAction
               INTEGER,
           ipIfSecurityProtocol
               INTEGER,
           ipIfSecuritySrcAddress
               IpAddress,
           ipIfSecuritySrcMask
               IpAddress,
           ipIfSecurityDestAddress
               IpAddress,
           ipIfSecurityDestMask
               IpAddress,
           ipIfSecurityOperator
               INTEGER,
           ipIfSecurityOperand
               INTEGER,
           ipIfSecurityOption
               INTEGER,
           ipIfSecurityType
               INTEGER
           }

        ipIfSecurityAccessListNum  OBJECT-TYPE
            SYNTAX  INTEGER (1..31)
            ACCESS  read-write
            STATUS  mandatory
            DESCRIPTION
              "The entry number of the Access List with which this security 
              entry is associated."
            ::= { ipIfSecurityEntry 1 }

        ipIfSecurityIndex  OBJECT-TYPE
            SYNTAX  INTEGER
            ACCESS  read-write
            STATUS  mandatory
            DESCRIPTION
              "An index into the security table."
            ::= { ipIfSecurityEntry 2 }
  
        ipIfSecurityAction  OBJECT-TYPE
           SYNTAX  INTEGER {
                   pass (1),
                   block (2)
                   }
           ACCESS  read-write
           STATUS  mandatory
           DESCRIPTION
             "Indicates the action in case of a match occurring between the
              src/dest addr and mask in the ip packet rxd/txd and the src/dest
              addr and mask in the security entry."
           ::= { ipIfSecurityEntry 3 }

        ipIfSecurityProtocol  OBJECT-TYPE
           SYNTAX  INTEGER (0..254)
           ACCESS  read-write
           STATUS  mandatory
           DESCRIPTION
             "The protocol for which this entry is valid. 0 is used for IP 
			 filtering"
           ::= { ipIfSecurityEntry 4 }

        ipIfSecuritySrcAddress  OBJECT-TYPE
           SYNTAX  IpAddress
           ACCESS  read-write
           STATUS  mandatory
           DESCRIPTION
             "The IP Address of the source. A value of 0.0.0.0 means that no
             checking is to be done on the Source Address"
           ::= { ipIfSecurityEntry 5 }

        ipIfSecuritySrcMask  OBJECT-TYPE
           SYNTAX  IpAddress
           ACCESS  read-write
           STATUS  mandatory
           DESCRIPTION
              "The mask used with the source address, if SrcAddress is not
              null."
           ::= { ipIfSecurityEntry 6 }

        ipIfSecurityDestAddress  OBJECT-TYPE
           SYNTAX  IpAddress
           ACCESS  read-write
           STATUS  mandatory
           DESCRIPTION
             "The destination IP address. A value of 0.0.0.0 means that no
             checking is to be done on the Destination Address"
           ::= { ipIfSecurityEntry 7 }

        ipIfSecurityDestMask  OBJECT-TYPE
           SYNTAX  IpAddress
           ACCESS  read-write
           STATUS  mandatory
           DESCRIPTION
              "The mask used with the destination address, if the address is
              not null."
           ::= { ipIfSecurityEntry 8 }

        ipIfSecurityOperator  OBJECT-TYPE
           SYNTAX  INTEGER {
                   lt (1),
                   gt (2),
                   eq (3),
                   neq (4)
                   }
           ACCESS  read-write
           STATUS  mandatory
           DESCRIPTION
              "The operator used in the comparison."
           ::= { ipIfSecurityEntry 9 }

        ipIfSecurityOperand  OBJECT-TYPE
           SYNTAX  INTEGER(0..65535)
           ACCESS  read-write
           STATUS  mandatory
           DESCRIPTION
              "This is the destination user port number to which the IP
                 datagram is addressed. The ipIfSecurityProtocol objects 
               indicates whether the port is a TCP or UDP port."
           ::= { ipIfSecurityEntry 10 }

        ipIfSecurityOption  OBJECT-TYPE
           SYNTAX  INTEGER {
                    true (1),
                    false (2)
                       }
           ACCESS  read-write
           STATUS  mandatory
           DESCRIPTION
             "This object indicates whether access checking should be 
             performed on an IP datagram that contains one or more IP 
             options and match the source and destination IP addresses 
             of this entry. If the object is set to Enabled then access 
             checking is performed on the IP datagram containing IP Options. 
             An IP datagrams that does not contain any options is not
             affected by this object."
           ::= { ipIfSecurityEntry 11 }

        ipIfSecurityType  OBJECT-TYPE
           SYNTAX  INTEGER {
                   valid (1),
                   invalid (2)
                   }
           ACCESS  read-write
           STATUS  mandatory
           DESCRIPTION
              " If this field has a value of valid(1) then the entry in the
                request is added to the table. If a value of invalid(2) is
                used then the entry will be deleted."
           ::= { ipIfSecurityEntry 12 }

    --
    -- The Port group
    --
    portLgclPortStatusTable  OBJECT-TYPE
        SYNTAX  SEQUENCE OF PortLgclPortStatusEntry
        ACCESS  not-accessible
        STATUS  mandatory
        DESCRIPTION
            "This is the logical port status table."
        ::= { port 1 }

    portLgclPortStatusEntry  OBJECT-TYPE
        SYNTAX  PortLgclPortStatusEntry
        ACCESS  not-accessible
        STATUS  mandatory
        DESCRIPTION
            "This is an entry in the logical port status table."
        INDEX  { portLgclPortID }
        ::= { portLgclPortStatusTable 1 }

    PortLgclPortStatusEntry ::= SEQUENCE {
            portLgclPortID
                INTEGER,
            portLgclPortPartnerMacAddress
                OCTET STRING,
            portLgclPortPartnerType
                INTEGER,
            portLgclPortName
                DisplayString,
            portLgclPortEncaps
                INTEGER,
            portLgclPortSlotID
                INTEGER,
            portLgclPortType
                INTEGER,
            portLgclPortThruput
                INTEGER,
            portLgclPortMaxTransit
                INTEGER,
            portLgclPortMinTransit
                INTEGER,
            portLgclPortMaxMTUSize
                INTEGER,
            portLgclPortStatus
                INTEGER,
            portLgclPortQueueSize
                INTEGER
            }

    portLgclPortID  OBJECT-TYPE
        SYNTAX  INTEGER
        ACCESS  read-only
        STATUS  mandatory
        DESCRIPTION
            "The index value which uniquely identifies the logical port
             to which this entry is applicable. "
        ::= { portLgclPortStatusEntry 1 }


    portLgclPortPartnerMacAddress  OBJECT-TYPE
        SYNTAX  OCTET STRING (SIZE(6))
        ACCESS  read-only
        STATUS  mandatory
        DESCRIPTION
            "The parameter contains the MAC address of the physical port
             to which this logical port is mapped. In the case of WAN ports
             this will return the base MAC address for the RX7000 station."
        ::= { portLgclPortStatusEntry 2 }

    portLgclPortPartnerType  OBJECT-TYPE
        SYNTAX  INTEGER {
                rx7000Series  (1),
                b4800Series    (2),
                other         (3),
                notApplicable (4),
                br4900Series    (5)
                }
        ACCESS  read-write
        STATUS  mandatory
        DESCRIPTION
            "This is the type of the partner to which this logical port is
             mapped. A value of notApplicable is returned for logical ports
             which are LAN ports, and for WAN ports which are not connected to
             any partner."
        ::= { portLgclPortStatusEntry 3 }

    portLgclPortName  OBJECT-TYPE
        SYNTAX  DisplayString (SIZE(16))
        ACCESS  read-write
        STATUS  mandatory
        DESCRIPTION
            "The is the name of this logical port."
        ::= { portLgclPortStatusEntry 4 }

    portLgclPortEncaps  OBJECT-TYPE
        SYNTAX  INTEGER {
                retix (1),
                ppp (2),
                rfc877 (3),
                osisndcf (4),
                frameRelay (5),
                lapb (6),
                hdlc (7),
                x25 (8),
                noencaps (15),
                csmaLan (16),
                tokenRing (17),
                fddi (18),
                ieee802-6SVC (19),
                ieee802-6PVC (20)
                }
        ACCESS  read-write
        STATUS  mandatory
        DESCRIPTION
            "This parameter indicates the Encapsulation used for the WAN port
             to which this logical port is attached. The values between 9 and
             14 inclusive are reserved."
        ::= { portLgclPortStatusEntry 5 }

    portLgclPortSlotID  OBJECT-TYPE
        SYNTAX  INTEGER
        ACCESS  read-only
        STATUS  mandatory
        DESCRIPTION
            "This identifies the slot on which the logical port resides."
        ::= { portLgclPortStatusEntry 6 }

    portLgclPortType  OBJECT-TYPE
        SYNTAX  INTEGER{
                ethernet  (1),
                fddi      (2),
                tokenRing (3),
                lan10BaseT   (4),
                lan10Base5   (5),
				lan10BaseT1port (6),
                x25       (11),
    --          backplane (30),
                rs232     (134),
                t1        (135),
                rs449     (136),
                v35       (137),
                x21       (138),
                g703      (139)
                }
        ACCESS  read-write
        STATUS  mandatory
        DESCRIPTION
            "This is the type of the underlying physical port."
        ::= { portLgclPortStatusEntry 7 }

    portLgclPortThruput  OBJECT-TYPE
        SYNTAX  INTEGER
        ACCESS  read-only
        STATUS  mandatory
        DESCRIPTION
            "This is the thruput measurement for the logical port."
        ::= { portLgclPortStatusEntry 8 }

    portLgclPortMaxTransit  OBJECT-TYPE
        SYNTAX  INTEGER
        ACCESS  read-only
        STATUS  mandatory
        DESCRIPTION
            "This is the value of the maximum transit delay in ******* for this
             port."
        ::= { portLgclPortStatusEntry 9 }

    portLgclPortMinTransit  OBJECT-TYPE
        SYNTAX  INTEGER
        ACCESS  read-only
        STATUS  mandatory
        DESCRIPTION
            "This is the value of the minimum transit delay in ******* for this
             port."
        ::= { portLgclPortStatusEntry 10 }

    portLgclPortMaxMTUSize  OBJECT-TYPE
        SYNTAX  INTEGER
        ACCESS  read-only
        STATUS  mandatory
        DESCRIPTION
            "This is the value of the maximum transmission unit size for this
             port."
        ::= { portLgclPortStatusEntry 11 }

    portLgclPortStatus  OBJECT-TYPE
        SYNTAX  INTEGER {
                other      (1),
                notReady   (3),
                ready      (4)
                }
        ACCESS  read-only
        STATUS  mandatory
        DESCRIPTION
            "This is the status of the logical port. The value other(1)
             represents  an undefined state which may indicate that the port
             is not active or there has been some failure on the card. In
             general the only states which will be reported to a manager are
             notReady(3) which indicates that the port is configured but
             not ready to transmit and receive, and ready(4) which indicates
             that this logical port is configured and can receive and transmit."
        ::= { portLgclPortStatusEntry 12 }

    portLgclPortQueueSize  OBJECT-TYPE
        SYNTAX  INTEGER (6..127)
        ACCESS  read-write
        STATUS  mandatory
        DESCRIPTION
            "This defines the maximum queue length of the logical port."
        ::= { portLgclPortStatusEntry 13 }

    portAttachLgclPortTable  OBJECT-TYPE
        SYNTAX  SEQUENCE OF PortAttachLgclPortEntry
        ACCESS  not-accessible
        STATUS  mandatory
        DESCRIPTION
            "This table is used to attach a logical port to a physical port and
             channel on the physical port."
        ::= { port 2 }
   
    portAttachLgclPortEntry  OBJECT-TYPE
        SYNTAX  PortAttachLgclPortEntry
        ACCESS  not-accessible
        STATUS  mandatory
        DESCRIPTION
            "This is an entry in the attach logical port to physical port
             table. An entry in this table indicates if the logical port
             is attached to the physical port and what channel on the physical
             port the logical port is attached to, if applicable. To set an
             entry in this table, aALL the objects in the entry must be present
             in a single SET PDU."
        INDEX  { portAttachLgclPortID, portAttachPhysPortID, portAttachChanID }
        ::= { portAttachLgclPortTable 1 }

    PortAttachLgclPortEntry ::= SEQUENCE {
            portAttachLgclPortID
                INTEGER,
            portAttachPhysPortID
                INTEGER,
            portAttachChanID
                INTEGER,
            portAttachAction
                INTEGER
            }

    portAttachLgclPortID  OBJECT-TYPE
        SYNTAX  INTEGER
        ACCESS  read-write
        STATUS  mandatory
        DESCRIPTION
            "The index value which uniquely identifies the logical port to
             which this entry is applicable."
        ::= { portAttachLgclPortEntry 1 }

    portAttachPhysPortID  OBJECT-TYPE
        SYNTAX  INTEGER
        ACCESS  read-write
        STATUS  mandatory
        DESCRIPTION
            "The value of this parameter is the physical port to which the
             logical port identified by portAttachLgclPortID is attached or
             it is physical port to which this logical port is to be attached."
        ::= { portAttachLgclPortEntry 2 }

    portAttachChanID  OBJECT-TYPE
        SYNTAX  INTEGER
        ACCESS  read-write
        STATUS  mandatory
        DESCRIPTION
            "The value of this object indicates the channel to which the port,
             identified by portLgclPortID, is attached or is to be attached.
             If the physical port has a portPhysPortLinkProtocol value of
             anything other than x.25(1) or framerelay(2) then this this
             parameter will have a value of zero."
        ::= { portAttachLgclPortEntry 3 }

    portAttachAction  OBJECT-TYPE
        SYNTAX  INTEGER {
            attach (1),
            remove (2)
            }
        ACCESS  read-write
        STATUS  mandatory
        DESCRIPTION
            "The value of this object indicates whether the logical port,
             identified by portLgclPortID, is to be attached or removed
             from the physical port and channel, identified by
             portAttachPhysPortID and portAttachChanID respectively.
             A value of attach has the effect of adding an entry to this table,
             and either to create the logical port, or to attach it to another
             physical port.  A value of remove has the effect of removing
             an entry from the table and if the logical port is the last logical
             port attached to the physical port then the remove action has the
             effect of deleting the logical port also."
        ::= { portAttachLgclPortEntry 4 }


    portPhysPortStatusTable  OBJECT-TYPE
        SYNTAX  SEQUENCE OF PortPhysPortStatusEntry
        ACCESS  not-accessible
        STATUS  mandatory
        DESCRIPTION
            "This table contains physical port status parameters."
        ::= { port 3 }

    portPhysPortStatusEntry  OBJECT-TYPE
        SYNTAX  PortPhysPortStatusEntry
        ACCESS  not-accessible
        STATUS  mandatory
        DESCRIPTION
            "This is an entry in the portPhysPortStatusTable."
        INDEX  { portPhysPortID }
        ::= { portPhysPortStatusTable 1 }

    PortPhysPortStatusEntry ::= SEQUENCE {
            portPhysPortID
                INTEGER,
            portPhysPortSlotID
                INTEGER,
            portPhysPortCardID
                INTEGER,
            portPhysPortName
                DisplayString,
            portPhysPortIOCardType
                INTEGER,
            portPhysPortLinkProtocol
                INTEGER,
            portPhysPortStatus
                INTEGER
            }

    portPhysPortID  OBJECT-TYPE
        SYNTAX  INTEGER
        ACCESS  read-only
        STATUS  mandatory
        DESCRIPTION
            "The value of this parameter uniquely identifies the physical port
             to which this entry is applicable."
        ::= { portPhysPortStatusEntry 1 }

    portPhysPortSlotID  OBJECT-TYPE
        SYNTAX  INTEGER
        ACCESS  read-only
        STATUS  mandatory
        DESCRIPTION
            "The value of this parameter uniquely identifies the slot where
             the physical port identified by the value portPhysPortID resides."
        ::= { portPhysPortStatusEntry 2 }

    portPhysPortCardID  OBJECT-TYPE
        SYNTAX  INTEGER
        ACCESS  read-only
        STATUS  mandatory
        DESCRIPTION
            "The value of this parameter identifies the IO card on which the
             physical port identified by the value portPhysPortID resides."
        ::= { portPhysPortStatusEntry 3 }

    portPhysPortName  OBJECT-TYPE
        SYNTAX  DisplayString (SIZE(16))
        ACCESS  read-write
        STATUS  mandatory
        DESCRIPTION
            "The used defined name for this physical port. this parameter has
             no operational significance, but serves to identify the port in
             a user friendly fashion."
        ::= { portPhysPortStatusEntry 4 }

    portPhysPortIOCardType  OBJECT-TYPE
        SYNTAX  INTEGER{
                ethernet (1),
                fddi (2),
                tokenRing (3),
                lan10BaseT (4),
                lan10Base5 (5),
                lan10BaseT1 (6),
                atm (7), 
    --          backplane (30),
                rs232 (134),
                t1 (135),
                rs449 (136),
                v35 (137),
                x21 (138),
	            dualWAN(140)	
            }
        ACCESS  read-write
        STATUS  mandatory
        DESCRIPTION
            "The type of I/O card on which this port resides."
        ::= { portPhysPortStatusEntry 5 }

    portPhysPortLinkProtocol  OBJECT-TYPE
        SYNTAX  INTEGER{
                retix (1),
                ppp (2),
                rfc877 (3),
                osisndcf (4),
                frameRelay (5),
                lapb (6),
                hdlc (7),
                x25 (8),
                noEncaps (15),
                csmaLan (16),
                tokenRing (17),
                fddi (18),
                atmsvc (19),
                atmpvc (20)
                }
        ACCESS  read-write
        STATUS  mandatory
        DESCRIPTION
            "The link protocol to be run over the physical port link. The
             values between 9 and 14 inclusive are reserved."
        ::= { portPhysPortStatusEntry 6 }

    portPhysPortStatus  OBJECT-TYPE
        SYNTAX  INTEGER{
                other (1),
                notReady (3),
                ready (4)
                }
        ACCESS  read-only
        STATUS  mandatory
        DESCRIPTION
            "The current operating status of the physical port. This mirrors
             the state of the logical port which is attached to it."
        ::= { portPhysPortStatusEntry 7 }

    portNextUnassignedLgclPrtNum  OBJECT-TYPE
        SYNTAX  INTEGER
        ACCESS  read-only
        STATUS  mandatory
        DESCRIPTION
            "This is the next unassigned number which can be used for a
             logical port create/attach operation."
        ::= { port 4 }

    --
    -- The Physical Serial group
    --

      phySerIfGeneralTable  OBJECT-TYPE
         SYNTAX  SEQUENCE OF PhySerIfGeneralEntry
         ACCESS  not-accessible
         STATUS  mandatory
         DESCRIPTION
           "A table of general parameters applicable to any type
            of serial interface physical port."
         ::= { physical 1 }

      phySerIfGeneralEntry  OBJECT-TYPE
         SYNTAX  PhySerIfGeneralEntry
         ACCESS  not-accessible
         STATUS  mandatory
         DESCRIPTION
           "An entry in the general table."
         INDEX { phySerIfGeneralIndex }
      ::= { phySerIfGeneralTable 1 }

      PhySerIfGeneralEntry  ::= SEQUENCE {
            phySerIfGeneralIndex
                  INTEGER,
            phySerIfOperationalMode
                  INTEGER,
            phySerIfPhysicalPortType
                  INTEGER,
            phySerIfPhysicalPortState
                  INTEGER,
            phySerIfPhysicalInterfaceState
                  INTEGER,
            phySerIfOnboardLoopback
                  INTEGER,
            phySerIfNoOfLinkResets
                  Counter,
            phySerIfLastLinkResetReason
                  INTEGER,
            phySerIfTimeSinceLastLinkReset
                  INTEGER,
            phySerIfSenseCtrlSgnls
              INTEGER
            }

      phySerIfGeneralIndex  OBJECT-TYPE
         SYNTAX  INTEGER
         ACCESS  read-only
         STATUS  mandatory
         DESCRIPTION
           "The index value which uniquely identifies the physical port
            to which this entry is applicable."
         ::= { phySerIfGeneralEntry 1 }

      phySerIfOperationalMode  OBJECT-TYPE
         SYNTAX  INTEGER {
                 dataMode (1),
                 bertMode (2)
                 }
         ACCESS  read-write
         STATUS  mandatory
         DESCRIPTION
           "This parameter is used to determine whether the physical port is
           available to the higher layers. If the value of this object is
           dataMode (1) then it is available otherwise a value of bertMode(2)
           indicates that the physical port is in a Bit Error Rate Test mode."
         ::= { phySerIfGeneralEntry 2 }

      phySerIfPhysicalPortType  OBJECT-TYPE
         SYNTAX  INTEGER {
                 unknown (1),
                 x21 (2),
                 rs449 (3),
                 v35 (4),
                 rs232 (5),
                 t1 (6)
                 }
         ACCESS  read-only
         STATUS  mandatory
         DESCRIPTION
           "This parameter is used to determine the physical port's
            interface type."
         ::= { phySerIfGeneralEntry 3 }

      phySerIfPhysicalPortState  OBJECT-TYPE
         SYNTAX  INTEGER {
                 active (1),
                 inactive (2),
                 test (3)
                 }
         ACCESS  read-only
         STATUS  mandatory
         DESCRIPTION
           "This parameter is used to determine whether the physical port
            may be used to transfer data. The conditions for a physical port
            being reported as in a usable state are specific to the interface
            type and are as follows:
                   X.21   - presence of control/indicate signal
                   RS-449 - presence of RR, DM and CS signals
                   V.35   - presence of RSLD, DSR and CTS signals
                   RS-232 - presence of RSLD, DSR and CTS signals
                   T1     - T1 interface hardware configured and no error
                            reported from T1 line interface or framer."
         ::= { phySerIfGeneralEntry 4 }

      phySerIfPhysicalInterfaceState  OBJECT-TYPE
         SYNTAX  INTEGER
         ACCESS  read-only
         STATUS  mandatory
         DESCRIPTION
           "This parameter is used to obtain the status of the physical
            interface control lines. The format of bit pattern returned
            is physical interface specific."
         ::= { phySerIfGeneralEntry 5 }

      phySerIfOnboardLoopback  OBJECT-TYPE
         SYNTAX  INTEGER {
                 enabled (1),
                 disabled (2)
                 }
         ACCESS  read-write
         STATUS  mandatory
         DESCRIPTION
           "This parameter is used to control the operation of the port hardware
            If the value is disabled(1) the the port hardware is configured to
            operate in normal mode, if the value is enabled(2) then the port
            is configured to operate in (on-board) loopback mode."
         ::= { phySerIfGeneralEntry 6 }


      phySerIfNoOfLinkResets  OBJECT-TYPE
         SYNTAX  Counter
         ACCESS  read-only
         STATUS  mandatory
         DESCRIPTION
           "This object is a count of the number of resets which have
            occurred on this WAN physical link, since the last reinitialization
            of the unit."
         ::= { phySerIfGeneralEntry 7 }

      phySerIfLastLinkResetReason  OBJECT-TYPE
         SYNTAX  INTEGER {
                 noReason    (1),
                 management  (2),
                 deviceReset (3),
                 cableDrop   (4),
                 protocol    (5)
                 }
         ACCESS  read-only
         STATUS  mandatory
         DESCRIPTION
             "This object gives the a reason code for the last reset which
              occurred on this WAN physical link. A value of noReason(1)
              is returned if the link has not reset. A value of management(2)
              is returned when a link reset has been caused by a management
              protocol (either SNMP or by LMS). A value of deviceReset(3)
              is returned if the link reset was caused by a hardware failure.
              A value of cableDrop(4) is returned when the link reset was
              caused by a missing or faulty cable. A value of protocol(5) is
              returned when the link reset is caused by the link protocol which
              is running on this link e.g. a Disconnet Request etc."
         ::= { phySerIfGeneralEntry 8 }

      phySerIfTimeSinceLastLinkReset  OBJECT-TYPE
         SYNTAX  INTEGER
         ACCESS  read-only
         STATUS  mandatory
         DESCRIPTION
             "This is a time (in hundredths of seconds) since the last link
              reset."
         ::= { phySerIfGeneralEntry 9 }

      phySerIfSenseCtrlSgnls  OBJECT-TYPE
         SYNTAX  INTEGER {
            enabled (1),
            disabled (2)
         }
         ACCESS  read-write
         STATUS  mandatory
         DESCRIPTION
           "This allows a port to be configured 'less-sensitive' to
            signal variations on control lines. "
         ::= { phySerIfGeneralEntry 10 }



      phySerIfX21Table  OBJECT-TYPE
         SYNTAX  SEQUENCE OF PhySerIfX21Entry
         ACCESS  not-accessible
         STATUS  mandatory
         DESCRIPTION
           "A table of parameters specific to the X21 type of physical
            interface."
         ::= { physical 2 }

      phySerIfX21Entry  OBJECT-TYPE
         SYNTAX  PhySerIfX21Entry
         ACCESS  not-accessible
         STATUS  mandatory
         DESCRIPTION
           "An entry of X21 specific parameters."
         INDEX  { phySerIfx21Index }
         ::= { phySerIfX21Table 1 }

      PhySerIfX21Entry  ::= SEQUENCE {
            phySerIfx21Index
                  INTEGER,
            phySerIfx21DTEDCESelect
                  INTEGER
            }

      phySerIfx21Index  OBJECT-TYPE
         SYNTAX  INTEGER
         ACCESS  read-only
         STATUS  mandatory
         DESCRIPTION
           "The value of the index which uniquely identifies the physical
            port to which this entry is applicable."
         ::= { phySerIfX21Entry 1 }

      phySerIfx21DTEDCESelect  OBJECT-TYPE
         SYNTAX  INTEGER {
                  x21DTE (1),
                  x21DCE (2)
                  }
         ACCESS  read-write
         STATUS  mandatory
         DESCRIPTION
           "This parameter is used to control whether the port hardware
            provides a DTE or a DCE interface."
         ::= { phySerIfX21Entry 2 }

      phySerIfBertTable  OBJECT-TYPE
         SYNTAX  SEQUENCE OF PhySerIfBertEntry
         ACCESS  not-accessible
         STATUS  mandatory
         DESCRIPTION
           " A table of Bert (Bit Error Rate Testing) specific parameters."
         ::= { physical 3 }

      phySerIfBertEntry  OBJECT-TYPE
         SYNTAX  PhySerIfBertEntry
         ACCESS  not-accessible
         STATUS  mandatory
         DESCRIPTION
           "An entry of Bert specific parameters. An entry exist in this table 
           only if the object, phySerIfGenOperationalMode, has been set to 
           a value of bertMode(2), for this interface."         
         INDEX  { phySerIfBertIndex }
         ::= { phySerIfBertTable 1 }

      PhySerIfBertEntry  ::= SEQUENCE {
            phySerIfBertIndex
                  INTEGER,
            phySerIfBertUnitType
                  INTEGER,
            phySerIfBertPatternType
                  INTEGER,
            phySerIfBertPatternLength
                  INTEGER,
            phySerIfBertPRBSPattern
                  INTEGER,
            phySerIfBertFBSPattern
                  INTEGER,
            phySerIfBertUserFBS
                  INTEGER,
            phySerIfBertPeriod
                  INTEGER,
            phySerIfBertBadLengthFrames
                  Counter,
            phySerIfBertSpurious
                  Counter,
            phySerIfBertLostFrames
                  Counter,
            phySerIfBertAcceptableFrames
                  Counter,
            phySerIfBertErroredFrames
                  Counter,
            phySerIfBertTestTime
                  INTEGER,
            phySerIfBertBitErrors
                  Counter,
            phySerIfBertErroredSecs
                  Counter,
            phySerIfBertFrameSizes
                  Counter,
            phySerIfBertBouncedFrames
                  Counter,
            phySerIfBertTxFrames
                  Counter,
            phySerIfBertRxFrames
                  Counter
            }

      phySerIfBertIndex  OBJECT-TYPE
         SYNTAX  INTEGER
         ACCESS  read-only
         STATUS  mandatory
         DESCRIPTION
           "The value of the index which uniquely identifies the physical port
            for which this entry is applicable."
         ::= { phySerIfBertEntry 1 }

      phySerIfBertUnitType  OBJECT-TYPE
         SYNTAX  INTEGER {
                  testUnit (1),
                  echoUnit (2)
                 }
         ACCESS  read-write
         STATUS  mandatory
         DESCRIPTION
            "If this parameter has a value of testUnit(1) then the unit will
             generate and check test patterns. If the value returned is
             echoUnit (2) the the unit echoes received frames."
         ::= { phySerIfBertEntry 2 }

      phySerIfBertPatternType  OBJECT-TYPE
         SYNTAX  INTEGER {
                 prbs (1),
                 fbs (2)
                 }
         ACCESS  read-write
         STATUS  mandatory
         DESCRIPTION
           "This parameter is used to select between pseudo random (prbs (1))
            and fixed (fbs (2)) bit sequence test patterns."
         ::= { phySerIfBertEntry 3 }

      phySerIfBertPatternLength  OBJECT-TYPE
         SYNTAX  INTEGER (1..4096)
         ACCESS  read-write
         STATUS  mandatory
         DESCRIPTION
           "This parameter is used to control the amount of test pattern which
            is enclosed in a single frame. This parameter is specified in units
            of bytes but will be implemented with a granularity of long words."
         ::= { phySerIfBertEntry 4 }

      phySerIfBertPRBSPattern  OBJECT-TYPE
         SYNTAX  INTEGER {
                 bitPattern511 (1),
                 bitPattern2047 (2),
                 bitPattern32767 (3)
                 }
         ACCESS  read-write
         STATUS  mandatory
         DESCRIPTION
           "This parameter is used to select the size of the pseudo random
            sequence pattern to be used.
            This parameter must be set when the phySerIfBertPatternType
            object has a value of prbs (1)."
         ::= { phySerIfBertEntry 5 }

      phySerIfBertFBSPattern  OBJECT-TYPE
         SYNTAX  INTEGER {
                 allOnesPattern (1),
                 allZerosPattern (2),
                 alternatePattern (3),
                 userPattern (4)
                 }
         ACCESS  read-write
         STATUS  mandatory
         DESCRIPTION
           "This parameter is used to select the fixed bit sequence pattern to
            be used.
            This parameter must be set when the physSerIfBertPatternType object
            has a value of fbs(2)."
         ::= { phySerIfBertEntry 6 }

      phySerIfBertUserFBS  OBJECT-TYPE
         SYNTAX  INTEGER
         ACCESS  read-write
         STATUS  mandatory
         DESCRIPTION
           "This parameter allows the user to define a fixed bit sequence test
            pattern to be used in Bert.
            This parameter need only be set when the phySerIfBertPatternType
            object has a value of fbs(2) and the phySerIfFBSPatternTye object
            has a value of userPattern(4)."
         ::= { phySerIfBertEntry 7 }

      phySerIfBertPeriod  OBJECT-TYPE
         SYNTAX  INTEGER (0..1000000)
         ACCESS  read-write
         STATUS  mandatory
         DESCRIPTION
           "This parameter is used to control the length of time over which the
            two units will perform the BER tests. This parameter is specified in
            units of seconds. A value of 0 is used to indicate an indefinite
            test period. This parameter may be configured at both the Test Unit
            and Echo Unit."
         ::= { phySerIfBertEntry 8 }

      phySerIfBertBadLengthFrames  OBJECT-TYPE
         SYNTAX  Counter
         ACCESS  read-only
         STATUS  mandatory
         DESCRIPTION
           "This parameter is used to obtain the number of frames received with
            an incorrect length during the BER test. This parameter is only
            applicable to a unit configured to act as BER Test Unit."
         ::= { phySerIfBertEntry 9 }

      phySerIfBertSpurious  OBJECT-TYPE
         SYNTAX  Counter
         ACCESS  read-only
         STATUS  mandatory
         DESCRIPTION
           "This parameter is used to obtain the number of frames received with
            an invalid sequence number during the BER test. This parameter is
            applicable to a unit configured to act as BER Test Unit."
         ::= { phySerIfBertEntry 10 }

      phySerIfBertLostFrames  OBJECT-TYPE
         SYNTAX  Counter
         ACCESS  read-only
         STATUS  mandatory
         DESCRIPTION
           "The Bert lost frames request parameter is used to obtain the number
            of frames which were not received during the BER test. This
            parameter is only applicable to a unit configured to act as a BER
            Test unit."
         ::= { phySerIfBertEntry 11 }

      phySerIfBertAcceptableFrames  OBJECT-TYPE
         SYNTAX  Counter
         ACCESS  read-only
         STATUS  mandatory
         DESCRIPTION
           "This parameter is used to obtain the number of frames which were
            received and processed during the BER test. This parameter is only
            applicable to a unit configured to act as BER Test Unit."
         ::= { phySerIfBertEntry 12 }

      phySerIfBertErroredFrames  OBJECT-TYPE
         SYNTAX  Counter
         ACCESS  read-only
         STATUS  mandatory
         DESCRIPTION
           "This parameter is used to obtain the number of processed frames
            which were found to contain at least one bit error during the BER
            test. This parameter is only applicable to a unit configured to act
            as BER Test Unit."
         ::= { phySerIfBertEntry 13 }

      phySerIfBertTestTime  OBJECT-TYPE
         SYNTAX  INTEGER
         ACCESS  read-only
         STATUS  mandatory
         DESCRIPTION
           "The BERT test time request parameter is used to obtain the duration
            (in seconds) of the BER test. This parameter is only applicable to
            a unit configured to act as BER Test Unit."
         ::= { phySerIfBertEntry 14 }

      phySerIfBertBitErrors  OBJECT-TYPE
         SYNTAX  Counter
         ACCESS  read-only
         STATUS  mandatory
         DESCRIPTION
           "This parameter is used to obtain the total number of bit errors seen
            in the BER test. This parameter is applicable to a unit configured
            to act as a BER Test Unit."
         ::= { phySerIfBertEntry 15 }

      phySerIfBertErroredSecs  OBJECT-TYPE
         SYNTAX  Counter
         ACCESS  read-only
         STATUS  mandatory
         DESCRIPTION
           "This parameter is used to obtain the number of seconds of the BERT
            Test in which a bit error was detected. This parameter is only
            applicable to a unit configured to act as BER Test Unit."
         ::= { phySerIfBertEntry 16 }

      phySerIfBertFrameSizes  OBJECT-TYPE
         SYNTAX  Counter
         ACCESS  read-only
         STATUS  mandatory
         DESCRIPTION
           "This is used to obtain the size of the test frames used in the BER
            test. (This parameter in conjunction with the number of acceptable
            frames is used to obtain the total number of bits received during
            the BER test). This parameter is only applicable to a unit
            configured to act as BER Test Unit."
         ::= { phySerIfBertEntry 17 }

      phySerIfBertBouncedFrames  OBJECT-TYPE
         SYNTAX  Counter
         ACCESS  read-only
         STATUS  mandatory
         DESCRIPTION
           "This parameter is used to obtain the number of frames which the BERT
            Echo Unit has received and sent back to the sender. This parameter
            is only applicable to a unit configured to act as BER Test Echo
            Unit."
         ::= { phySerIfBertEntry 18 }

      phySerIfBertTxFrames  OBJECT-TYPE
         SYNTAX  Counter
         ACCESS  read-only
         STATUS  mandatory
         DESCRIPTION
           "This parameter is used to obtain the number of frames that were
            transmitted."
         ::= { phySerIfBertEntry 19 }

      phySerIfBertRxFrames  OBJECT-TYPE
         SYNTAX  Counter
         ACCESS  read-only
         STATUS  mandatory
         DESCRIPTION
           "This parameter is used to obtain the number of frames received."
         ::= { phySerIfBertEntry 20 }


      phySerIfRS449Table  OBJECT-TYPE
         SYNTAX  SEQUENCE OF PhySerIfRS449Entry
         ACCESS  not-accessible
         STATUS  mandatory
         DESCRIPTION
           "A table of RS449 specific parameters."
         ::= { physical 4 }

      phySerIfRS449Entry  OBJECT-TYPE
         SYNTAX  PhySerIfRS449Entry
         ACCESS  not-accessible
         STATUS  mandatory
         DESCRIPTION
           "An entry of RS449 specific parameters."
         INDEX  { phySerIfRS449Index }
         ::= { phySerIfRS449Table 1 }

      PhySerIfRS449Entry ::= SEQUENCE {
            phySerIfRS449Index
                INTEGER,
            phySerIfRS449Clock
                INTEGER,
            phySerIfRS449LocalLoopback
                INTEGER,
            phySerIfRS449RemoteLoopback
                INTEGER,
            phySerIfRS449BackToBack
                INTEGER
            }

      phySerIfRS449Index  OBJECT-TYPE
         SYNTAX  INTEGER
         ACCESS  read-only
         STATUS  mandatory
         DESCRIPTION
           "The value of the index uniquely identifies the physical port to
            which this entry is applicable."
         ::= { phySerIfRS449Entry 1 }


      phySerIfRS449Clock  OBJECT-TYPE
          SYNTAX  INTEGER {
                  clk9100    (9100),
                  clk64000   (64000),
                  clk128000  (128000),
                  clk2048000 (2048000)
                  }
          ACCESS  read-write
          STATUS  mandatory
          DESCRIPTION
            "This parameter determines the rate for the internal clock."
          ::= { phySerIfRS449Entry 2 }

      phySerIfRS449LocalLoopback  OBJECT-TYPE
          SYNTAX  INTEGER {
                  enable (1),
                  disable (2)
                  }
          ACCESS  read-write
          STATUS  mandatory
          DESCRIPTION
            "If this object is set to a value of enable(1) then this port will
            request the local modem port to perform a loopback function.
            If the value returned is disabled(2) this indicated that the
            local modem port has not been requested to perform any loopback
            function."
          ::= { phySerIfRS449Entry 3 }

      phySerIfRS449RemoteLoopback  OBJECT-TYPE
          SYNTAX  INTEGER {
                  enable (1),
                  disable (2)
                  }
          ACCESS  read-write
          STATUS  mandatory
          DESCRIPTION
            "If this object is set to a value of enable(1) then this port will
             request the remote modem port to perform a loopback function.
             If the value returned is disabled(2) this indicated that the
             remote modem port has not been requested to perform any loopback
             function."
          ::= { phySerIfRS449Entry 4 }

      phySerIfRS449BackToBack  OBJECT-TYPE
          SYNTAX  INTEGER {
                  enable (1),
                  disable (2)
                  }
          ACCESS  read-write
          STATUS  mandatory
          DESCRIPTION
            "This parameter is used to enable or disable the onboard clock to
             allow the back to back working of two units."
          ::= { phySerIfRS449Entry 5 }

      phySerIfv35Table  OBJECT-TYPE
         SYNTAX  SEQUENCE OF PhySerIfv35Entry
         ACCESS  not-accessible
         STATUS  mandatory
         DESCRIPTION
           "A table of V.35 specific parameters."
         ::= { physical 5 }

      phySerIfv35Entry  OBJECT-TYPE
         SYNTAX  PhySerIfv35Entry
         ACCESS  not-accessible
         STATUS  mandatory
         DESCRIPTION
           "An entry of V.35 specific parameters."
         INDEX  { phySerIfv35Index }
         ::= { phySerIfv35Table 1 }

      PhySerIfv35Entry ::= SEQUENCE {
            phySerIfv35Index
                INTEGER,
            phySerIfv35BackToBack
                INTEGER,
            phySerIfv35Clock
                INTEGER,
            phySerIfv35LocalLoopback
                INTEGER,
            phySerIfv35RemoteLoopback
                INTEGER
            }

      phySerIfv35Index  OBJECT-TYPE
         SYNTAX  INTEGER
         ACCESS  read-only
         STATUS  mandatory
         DESCRIPTION
            "The value of the index uniquely identifies the physical port
             to which this entry is applicable."
         ::= { phySerIfv35Entry 1 }


      phySerIfv35BackToBack  OBJECT-TYPE
          SYNTAX  INTEGER {
                  enable (1),
                  disable (2)
                  }
          ACCESS  read-write
          STATUS  mandatory
          DESCRIPTION
            "This parameter is used to enable or disable the onboard clock to
             allow the back to back working of two units."
          ::= { phySerIfv35Entry 2 }

      phySerIfv35Clock  OBJECT-TYPE
          SYNTAX  INTEGER {
                  clk9100    (9100),
                  clk64000   (64000),
                  clk128000  (128000),
                  clk2048000 (2048000)
                  }
          ACCESS  read-write
          STATUS  mandatory
          DESCRIPTION
            "This parameter determines the rate for the internal clock."
          ::= { phySerIfv35Entry 3 }

      phySerIfv35LocalLoopback  OBJECT-TYPE
          SYNTAX  INTEGER {
                  enabled (1),
                  disabled (2)
                  }
          ACCESS  read-write
          STATUS  mandatory
          DESCRIPTION
            "If this object is set to a value of enable(1) then this port will
              request the local modem port to perform a loopback function.
              If the value returned is disabled(2) this indicated that the
              local modem port has not been requested to perform any loopback
              function."
          ::= {  phySerIfv35Entry 4 }

      phySerIfv35RemoteLoopback  OBJECT-TYPE
          SYNTAX  INTEGER {
                  enabled (1),
                  disabled (2)
                  }
          ACCESS  read-write
          STATUS  mandatory
          DESCRIPTION
            "If this object is set to a value of enable(1) then this port will
              request the remote modem port to perform a loopback function.
              If the value returned is disabled(2) this indicated that the
              remote modem port has not been requested to perform any loopback
              function."
          ::= { phySerIfv35Entry 5 }


      phySerIfRS232Table  OBJECT-TYPE
         SYNTAX  SEQUENCE OF PhySerIfRS232Entry
         ACCESS  not-accessible
         STATUS  mandatory
         DESCRIPTION
           "A table of RS232 specific parameters."
         ::= { physical 6 }

      phySerIfRS232Entry  OBJECT-TYPE
         SYNTAX  PhySerIfRS232Entry
         ACCESS  not-accessible
         STATUS  mandatory
         DESCRIPTION
           "An entry of RS232 specific parameters."
         INDEX  { phySerIfRS232Index }
         ::= { phySerIfRS232Table 1 }

      PhySerIfRS232Entry ::= SEQUENCE {
            phySerIfRS232Index
                INTEGER,
            phySerIfRS232BackToBack
                INTEGER,
            phySerIfRS232Clock
                INTEGER,
            phySerIfRS232LocalLoopback
                INTEGER,
            phySerIfRS232RemoteLoopback
                INTEGER
            }

      phySerIfRS232Index  OBJECT-TYPE
         SYNTAX  INTEGER
         ACCESS  read-only
         STATUS  mandatory
         DESCRIPTION
           "The value of the index uniquely identifies the physical port to
            which this entry is appliacble."
         ::= { phySerIfRS232Entry 1 }

      phySerIfRS232BackToBack  OBJECT-TYPE
          SYNTAX  INTEGER {
                  enable (1),
                  disable (2)
                  }
          ACCESS  read-write
          STATUS  mandatory
          DESCRIPTION
            "This parameter is used to enable or disable the onboard clock to
             allow the back to back working of two units."
          ::= { phySerIfRS232Entry 2 }


      phySerIfRS232Clock  OBJECT-TYPE
          SYNTAX  INTEGER {
                  clk1200  (1200),
                  clk9600  (9600),
                  clk19200 (19200)
                  }
          ACCESS  read-write
          STATUS  mandatory
          DESCRIPTION
            "This parameter determines the rate for the internal clock."
          ::= { phySerIfRS232Entry 3 }

      phySerIfRS232LocalLoopback  OBJECT-TYPE
          SYNTAX  INTEGER {
                  enable (1),
                  disable (2)
                  }
          ACCESS  read-write
          STATUS  mandatory
          DESCRIPTION
            "If this object is set to a value of enable(1) then this port will
            request the local modem port to perform a loopback function.
            If the value returned is disabled(2) this indicated that the
            local modem port has not been requested to perform any loopback
            function."
          ::= { phySerIfRS232Entry 4 }

      phySerIfRS232RemoteLoopback  OBJECT-TYPE
          SYNTAX  INTEGER {
                  enable (1),
                  disable (2)
                  }
          ACCESS  read-write
          STATUS  mandatory
          DESCRIPTION
            "If this object is set to a value of enable(1) then this port will
             request the remote modem port to perform a loopback function.
             If the value returned is disabled(2) this indicated that the
             remote modem port has not been requested to perform any loopback
             function."
          ::= { phySerIfRS232Entry 5 }

      phySerIfG703Table  OBJECT-TYPE
         SYNTAX  SEQUENCE OF PhySerIfG703Entry
         ACCESS  not-accessible
         STATUS  mandatory
         DESCRIPTION
           "A table of G703 specific parameters."
         ::= { physical 7 }

      phySerIfG703Entry  OBJECT-TYPE
         SYNTAX  PhySerIfG703Entry
         ACCESS  not-accessible
         STATUS  mandatory
         DESCRIPTION
           "An entry of G703 specific parameters."
         INDEX  { phySerIfG703Index }
         ::= { phySerIfG703Table 1 }

      PhySerIfG703Entry ::= SEQUENCE {
            phySerIfG703Index
                INTEGER,
            phySerIfG703LocalLoopback
                INTEGER,
            phySerIfG703RemoteLoopback
                INTEGER
            }

      phySerIfG703Index  OBJECT-TYPE
         SYNTAX  INTEGER
         ACCESS  read-only
         STATUS  mandatory
         DESCRIPTION
           "The value of the index uniquely identifies the physical port to
            which this entry is appliacble."
         ::= { phySerIfG703Entry 1 }


      phySerIfG703LocalLoopback  OBJECT-TYPE
          SYNTAX  INTEGER {
                  enable (1),
                  disable (2)
                  }
          ACCESS  read-write
          STATUS  mandatory
          DESCRIPTION
            "If this object is set to a value of enable(1) then this port will
            request the local modem port to perform a loopback function.
            If the value returned is disabled(2) this indicated that the
            local modem port has not been requested to perform any loopback
            function."
          ::= { phySerIfG703Entry 2 }

      phySerIfG703RemoteLoopback  OBJECT-TYPE
          SYNTAX  INTEGER {
                  enable (1),
                  disable (2)
                  }
          ACCESS  read-write
          STATUS  mandatory
          DESCRIPTION
            "If this object is set to a value of enable(1) then this port will
             request the remote modem port to perform a loopback function.
             If the value returned is disabled(2) this indicated that the
             remote modem port has not been requested to perform any loopback
             function."
          ::= { phySerIfG703Entry 3 }

      phySerIf10base5Table  OBJECT-TYPE
         SYNTAX  SEQUENCE OF PhySerIf10base5Entry
         ACCESS  not-accessible
         STATUS  mandatory
         DESCRIPTION
           "A table of 10base5 specific parameters."
         ::= { physical 8 }

      phySerIf10base5Entry  OBJECT-TYPE
         SYNTAX  PhySerIf10base5Entry
         ACCESS  not-accessible
         STATUS  mandatory
         DESCRIPTION
           "An entry of 10base5 specific parameters."
         INDEX  { phySerIf10base5Index }
         ::= { phySerIf10base5Table 1 }

      PhySerIf10base5Entry ::= SEQUENCE {
            phySerIf10base5Index
                INTEGER,
            phySerIf10base5SenseSQEs
                INTEGER
            }

      phySerIf10base5Index  OBJECT-TYPE
         SYNTAX  INTEGER
         ACCESS  read-only
         STATUS  mandatory
         DESCRIPTION
           "The value of the index uniquely identifies the physical port to
            which this entry is applicable."
         ::= { phySerIf10base5Entry 1 }


      phySerIf10base5SenseSQEs  OBJECT-TYPE
          SYNTAX  INTEGER {
                  enable    (1),
                  disable   (2)
                  }
          ACCESS  read-write
          STATUS  mandatory
          DESCRIPTION
            "Enables or disables the SQE counter."
          ::= { phySerIf10base5Entry 2 }

    --
    -- The Multilink Group
    --

          mlinkTable  OBJECT-TYPE
              SYNTAX  SEQUENCE OF MlinkTableEntry
              ACCESS  not-accessible
              STATUS  mandatory
              DESCRIPTION
                 "The multilink Table  containing all the multilink objects."
              ::= { multilink 1 }

          mlinkTableEntry  OBJECT-TYPE
              SYNTAX  MlinkTableEntry
              ACCESS  not-accessible
              STATUS  mandatory
              DESCRIPTION
                  "Each entry contains configurables for each logical port 
                  on the unit that supports multilink."
              INDEX   { mlinkPortIndex }
              ::= { mlinkTable 1 }

          MlinkTableEntry ::= SEQUENCE {
                mlinkPortIndex
                    INTEGER,
                mlinkOperation
                    INTEGER,
                mlinkStandbyThreshold
                    INTEGER,
                mlinkLostFrameTimer
                    INTEGER,
                mlinkWindow
                    INTEGER,
                mlinkState
                    INTEGER,
                mlinkTotalThroughput
                    INTEGER,
                mlinkActiveThroughput
                    INTEGER,
                mlinkMinTransitDelay
                    INTEGER,
                mlinkMaxTransitDelay
                    INTEGER,
                mlinkActiveChannels
                    INTEGER,
                mlinkStandbyChannels
                    INTEGER,
                mlinkRxInvalidFrames
                    Counter,
                mlinkTxInvalidFrames
                    Counter,
                mlinkRxDiscBadSeqNumFrames
                    Counter,
                mlinkLostFrames
                    Counter,
                mlinkProtocolResets
                    Counter
                }


          mlinkPortIndex  OBJECT-TYPE
              SYNTAX  INTEGER
              ACCESS  read-only
              STATUS  mandatory
              DESCRIPTION
                "This is the logical port number which supports
                multilink. An entry for this port will only exist if
                the logical port is attached to a physical port which is
                using the Retixwan link protocol."
              ::= { mlinkTableEntry 1 }

          mlinkOperation  OBJECT-TYPE
              SYNTAX  INTEGER {
                      enable(1),
                      disable(2)
                      }
              ACCESS  read-write
              STATUS  mandatory
              DESCRIPTION
                "This object enables/disables multilink on this port."
              ::= { mlinkTableEntry 2 }

          mlinkStandbyThreshold  OBJECT-TYPE
              SYNTAX  INTEGER ( 1200..2048000 )
              ACCESS  read-write
              STATUS  mandatory
              DESCRIPTION
                "This is used to determine the line speed level
                at which the multilink module will check to see if
                channels can be made standby. If any channels have
                a line speed greater than this threshold value, then
                the multilink module picks out the best channels and
                makes them active, making any others standby. If no
                channels have line speeds greater than this, then all
                channels are used and there are none in standby mode."
              ::= { mlinkTableEntry 3 }

          mlinkLostFrameTimer  OBJECT-TYPE
              SYNTAX  INTEGER ( 50..5000 )
              ACCESS  read-write
              STATUS  mandatory
              DESCRIPTION
                "This is the Lost Frame Timer.  It starts when an
                out of sequence frame is received, and is not reset
                until the next expected frame is received. If it
                expires then the frames between the last received,
                and the current out-of-sequence frame, are considered
                to be lost. This timer is in millisecs, but the
                granularity of the operating value is 50ms, so the
                value set, is rounded up to the nearest 50ms."
              ::= { mlinkTableEntry 4 }

          mlinkWindow  OBJECT-TYPE
              SYNTAX  INTEGER ( 1..200 )
              ACCESS  read-write
              STATUS  mandatory
              DESCRIPTION
                "This is the multilink window size."
              ::= { mlinkTableEntry 5 }

          mlinkState  OBJECT-TYPE
              SYNTAX  INTEGER {
                      active (1),
                      inactive (2)
                      }
              ACCESS  read-only
              STATUS  mandatory
              DESCRIPTION
                "This indicates whether the multilink protocol has
                been established between the remote partners."
              ::= { mlinkTableEntry 6 }

          mlinkTotalThroughput  OBJECT-TYPE
              SYNTAX  INTEGER
              ACCESS  read-only
              STATUS  mandatory
              DESCRIPTION
                " This is the sum of the line speeds for all the
                active channels( both standby and active ) supporting
                multilink on this logical port."
              ::= { mlinkTableEntry 7 }

          mlinkActiveThroughput  OBJECT-TYPE
              SYNTAX  INTEGER
              ACCESS  read-only
              STATUS  mandatory
              DESCRIPTION
                " This is the sum of the line speeds for all the
                active channels supporting multilink on this logical
                port."
              ::= { mlinkTableEntry 8 }

          mlinkMinTransitDelay  OBJECT-TYPE
              SYNTAX  INTEGER
              ACCESS  read-only
              STATUS  mandatory
              DESCRIPTION
                "This is the minimum transit delay( in millisecs)
                for the active channels supporting multilink. If this
                is not known, then this will return -1."
              ::= { mlinkTableEntry 9 }

          mlinkMaxTransitDelay  OBJECT-TYPE
              SYNTAX  INTEGER
              ACCESS  read-only
              STATUS  mandatory
              DESCRIPTION
                "This is the maximum transit delay( in millisecs ) for
                the active channels supporting multilink. If this is
                not known, then this will return -1."
              ::= { mlinkTableEntry 10 }

          mlinkActiveChannels  OBJECT-TYPE
              SYNTAX  INTEGER
              ACCESS  read-only
              STATUS  mandatory
              DESCRIPTION
                "This is the number of active channels supporting
                multilink for this port."
              ::= { mlinkTableEntry 11 }

          mlinkStandbyChannels  OBJECT-TYPE
              SYNTAX  INTEGER
              ACCESS  read-only
              STATUS  mandatory
              DESCRIPTION
                "This is the number of channels which are in standby
                which support multilink for this port."
              ::= { mlinkTableEntry 12 }

          mlinkRxInvalidFrames  OBJECT-TYPE
              SYNTAX  Counter
              ACCESS  read-only
              STATUS  mandatory
              DESCRIPTION
                "This is the number of frames received but discarded
                due to being too big, or having invalid seq. Numbers,
                etc."
              ::= { mlinkTableEntry 13 }

          mlinkTxInvalidFrames  OBJECT-TYPE
              SYNTAX  Counter
              ACCESS  read-only
              STATUS  mandatory
              DESCRIPTION
                "This is the number of frames to be transmitted but
                discarded due to being too big, or having invalid seq.
                Numbers, etc."
              ::= { mlinkTableEntry 14 }

          mlinkRxDiscBadSeqNumFrames  OBJECT-TYPE
              SYNTAX  Counter
              ACCESS  read-only
              STATUS  mandatory
              DESCRIPTION
                "This is the number of frames discarded due to the
                multilink sequence number being out of range."
              ::= { mlinkTableEntry 15 }

          mlinkLostFrames  OBJECT-TYPE
              SYNTAX  Counter
              ACCESS  read-only
              STATUS  mandatory
              DESCRIPTION
                "This is the number of frames for which the Lost Frame
                Timer has expired."
              ::= { mlinkTableEntry 16 }

          mlinkProtocolResets  OBJECT-TYPE
              SYNTAX  Counter
              ACCESS  read-only
              STATUS  mandatory
              DESCRIPTION
                "This is the number of multilink protocol resets that
                have occurred since the creation of this logical port."
              ::= { mlinkTableEntry 17 }


    --
    -- The LAPB Group
    --

          lapbPortConfigTable  OBJECT-TYPE
              SYNTAX  SEQUENCE OF LapbPortConfigEntry
              ACCESS  not-accessible
              STATUS  mandatory
              DESCRIPTION
                " This table contains the LAPB Port Information."
              ::=  { lapb 1 }

          lapbPortConfigEntry  OBJECT-TYPE
              SYNTAX  LapbPortConfigEntry
              ACCESS  not-accessible 
              STATUS  mandatory
              DESCRIPTION
                "An Entry in this table contains information
                about each physical port in the system that is configured
                with lapb as its physical port protocol."
               INDEX    { lapbPCIndex }
              ::=  { lapbPortConfigTable 1 }

           LapbPortConfigEntry ::= SEQUENCE {
             lapbPCIndex
                   INTEGER,
             lapbPCT1AckTimer
                   INTEGER,
             lapbPCT3DiscTimer
                 INTEGER,
             lapbPCN2ReTxCount
                 INTEGER,
             lapbPCN1FrameSize
                 INTEGER,
             lapbPCLocalAddress
                 INTEGER,
             lapbPCSeqNumbering
                 INTEGER,
             lapbPCKWindowSize
                 INTEGER,
             lapbPCMaxRxQueueLength
                 INTEGER,
             lapbPCMaxTxQueueLength
                 INTEGER
             }

          lapbPCIndex  OBJECT-TYPE
              SYNTAX  INTEGER
              ACCESS  read-only
               STATUS  mandatory
              DESCRIPTION
                "This object is the Physical Port to which this
                table entry refers."
              ::=  { lapbPortConfigEntry 1 }

          lapbPCT1AckTimer  OBJECT-TYPE
              SYNTAX  INTEGER (10..5000)
              ACCESS  read-write
              STATUS  mandatory
              DESCRIPTION 
                "The default T1 timer for this interface.
                This specifies the maximum time in
                Milliseconds to wait for acknowledgement of a
                PDU."
              REFERENCE
               "ISO 8885 Table 3, Name: Acknowledgement timer"
              DEFVAL { 3000 }
              ::=  { lapbPortConfigEntry 2 }

          lapbPCT3DiscTimer  OBJECT-TYPE
              SYNTAX  INTEGER( 1..4294967295 ) 
              ACCESS  read-write
              STATUS  mandatory
              DESCRIPTION 
                "The T3 timer for this interface.  This
                specifies the time in Milliseconds to wait
                before considering the link disconnected.  A
                value of zero indicates the link will be
                considered disconnected upon completion of
                the frame exchange to disconnect the link.
                This value should be set larger than T1 * N2"
              REFERENCE 
                "ISO 7776 section 5.7.1.3"
              DEFVAL { 60000 }
              ::=  { lapbPortConfigEntry 3 }

          lapbPCN2ReTxCount  OBJECT-TYPE
              SYNTAX  INTEGER (1..255)
              ACCESS  read-write
              STATUS  mandatory
              DESCRIPTION 
                "The default N2 retry counter for this
                interface.  This specifies the number of
                times a PDU will be resent after the T1
                timer expires without an acknowledgement for
                the PDU."
              REFERENCE
               "ISO 8885 Table 3, Name: Retransmission Attempts"
              DEFVAL { 20 }
              ::=  { lapbPortConfigEntry 4 }

          lapbPCN1FrameSize  OBJECT-TYPE
              SYNTAX  INTEGER ( 128..1033 )
              ACCESS  read-write
              STATUS  mandatory
              DESCRIPTION
                "The default maximum N1 frame size desired
                in number of bits for a frame the DCE/remote
                DTE transmits to this DTE.  This excludes
                flags and 0 bits inserted for transparency.
                The frame size is assumed to be the same size 
                for both directions of data transfer."
              DEFVAL { 1080  } -- (128+7) * 8
              ::=  { lapbPortConfigEntry 5 }

          lapbPCLocalAddress  OBJECT-TYPE
              SYNTAX  INTEGER {
                      dce (1),
                      dte (3)
                      }
              ACCESS  read-write
              STATUS  mandatory
              DESCRIPTION
                "This is the Local LAPB Address of this port.
                 This determines the station type of the 
                 interface. The remote address will be the 
                 complement of the setting of the local address."
              REFERENCE 
               "ISO 7776 section 3.1"
              DEFVAL { dte }
              ::=  { lapbPortConfigEntry 6 }

          lapbPCSeqNumbering  OBJECT-TYPE
              SYNTAX  INTEGER {
                      mod8 (1),
                      mod128 (2)
                      }
              ACCESS  read-write
              STATUS  mandatory
              DESCRIPTION
               "This object tells us the sequence numbering
                method in use on this port. It is either modulo8,
                i.e. frames are numbered between 0 and 7, or 
                modulo128, where frames are numbered between 0 
                and 128. This object will limit the value which
                can be set for lapbKWindowSize."
              REFERENCE 
                "ISO 8885 Table 3, Name: HDLC Option - 10"
              DEFVAL { 7 }
              ::=  { lapbPortConfigEntry 7 }

          lapbPCKWindowSize  OBJECT-TYPE
              SYNTAX  INTEGER(1..127)
              ACCESS  read-write
              STATUS  mandatory
              DESCRIPTION 
                "The window size used for both directions of data transfer 
                on this Interface.  This is the maximum number of
                unacknowledged sequenced PDUs that may be
                outstanding from this unit at any one time.
                This object can take values 1..7 when SeqNumbering has
                a value of mod8, and values 1,3,7,15,31,63,127 when 
                SeqNumbering has a value mod128."
               REFERENCE 
                "ISO 8885 Table 3, Name: Window size"
              DEFVAL { 7 }
              ::=  { lapbPortConfigEntry 8 }


          lapbPCMaxRxQueueLength  OBJECT-TYPE
              SYNTAX  INTEGER(1..128)
              ACCESS  read-write
              STATUS  mandatory
              DESCRIPTION
                "This is the Maximum No. of frames that can be queued
                up on the receive queue of the LAPB controller. Values
                allowed are 1,2,4,8,16,32,64,128.- what the chip supports."
              ::=  { lapbPortConfigEntry 9 }

          lapbPCMaxTxQueueLength  OBJECT-TYPE
              SYNTAX  INTEGER(1..128)
              ACCESS  read-write
              STATUS  mandatory
              DESCRIPTION
               "This is the Maximum No. of frames that can be queued
                up for transmission on the transmit queue of the 
                LAPB controller. Values allowed are 1,2,4,8,16,32,64,128.
                - what the chip supports."
              ::=  { lapbPortConfigEntry 10 }




          lapbPortStatsTable  OBJECT-TYPE
              SYNTAX  SEQUENCE OF LapbPortStatsEntry
              ACCESS  not-accessible 
              STATUS  mandatory
              DESCRIPTION
                " This table contains the LAPB Port Statistics Information."
              ::=  { lapb 2 }

          lapbPortStatsEntry  OBJECT-TYPE
              SYNTAX  LapbPortStatsEntry
              ACCESS  not-accessible 
              STATUS  mandatory
              DESCRIPTION
               "An Entry in this table contains information
                about each physical port in the system that uses
                lapb."
              INDEX    { lapbPSIndex }
              ::=  { lapbPortStatsTable 1 }

          LapbPortStatsEntry ::= SEQUENCE {
              lapbPSIndex
                  INTEGER,
              lapbPSChannelState
                  INTEGER,
              lapbPST1Timeouts
                  Counter,
              lapbPSTxFrames
                  Counter,
              lapbPSTxRejects
                  Counter,
              lapbPSRxFrames
                  Counter,
              lapbPSRxRejects
                  Counter,
              lapbPSRxFrameRejects
                  Counter,
              lapbPSRxRunts
                  Counter,
              lapbPSRxBadFrames
                  Counter
              }

          lapbPSIndex  OBJECT-TYPE
              SYNTAX  INTEGER
              ACCESS  read-only
              STATUS  mandatory
              DESCRIPTION
               "This object is the Physical Port to which this
                table entry refers."
              ::=  { lapbPortStatsEntry 1 }

          lapbPSChannelState  OBJECT-TYPE
              SYNTAX  INTEGER {
                      disconnected (1),
                                  -- initial state or DISC received

                      linkSetup (2),
                                  -- SABM sent

                      frameReject (3),
                                  -- Invalid frame received and
                                  -- FRMR sent

                      disconnectRequest (4),
                                  -- DISC sent

                      informationTransfer (5),
                                  -- normal information transfer state
                                  -- SABM(E) sent and UA received, or
                                  -- SABM(E) received and UA sent
  
                      rejFrameSent (6),
                                  -- invalid NS received and REJ sent
  
                      waitingAcknowledgement (7),
                                  -- T1 expired and RR sent

                      stationBusy (8),
                                  -- RNR sent

                      remoteStationBusy (9),
                                  -- RNR received

                      bothStationsBusy (10),
                                  -- RNR received and RNR sent

                      waitingAckStationBusy (11),
                                  -- T1 expired, RNR sent

                      waitingAckRemoteBusy (12),
                                  -- T1 expired, RNR received

                      waitingAckBothBusy (13),
                                  -- T1 expired, RNR sent,
                                  -- and RNR received

                      rejFrameSentRemoteBusy (14)
                                 -- REJ sent and RNR received

                      }
              ACCESS  read-only
              STATUS  mandatory
              DESCRIPTION
               "This is the current state of the Lapb 
                 connection"
              ::=  { lapbPortStatsEntry 2 }

          lapbPST1Timeouts  OBJECT-TYPE
              SYNTAX  Counter
              ACCESS  read-only
              STATUS  mandatory
              DESCRIPTION 
               "The Count of T1 timer timeouts since the last link reset."
              ::=  { lapbPortStatsEntry 3 }

          lapbPSTxFrames  OBJECT-TYPE
              SYNTAX  Counter
              ACCESS  read-only
              STATUS  mandatory
              DESCRIPTION 
               "The No. of LAPB frames Transmitted since the last link reset"
              ::=  { lapbPortStatsEntry 4 }

          lapbPSTxRejects  OBJECT-TYPE
              SYNTAX  Counter
              ACCESS  read-only
              STATUS  mandatory
              DESCRIPTION 
               "The No. of reject frames transmitted."
              ::=  { lapbPortStatsEntry 5 }

          lapbPSRxFrames  OBJECT-TYPE
              SYNTAX  Counter
              ACCESS  read-only
              STATUS  mandatory
              DESCRIPTION 
               "The No. of LAPB frames Received since the last link reset"
              ::=  { lapbPortStatsEntry 6 }

          lapbPSRxRejects  OBJECT-TYPE
              SYNTAX  Counter
              ACCESS  read-only
              STATUS  mandatory
              DESCRIPTION 
               "The No. of reject frames received."
              ::=  { lapbPortStatsEntry 7 }

          lapbPSRxFrameRejects  OBJECT-TYPE
              SYNTAX  Counter
              ACCESS  read-only
              STATUS  mandatory
              DESCRIPTION 
               "The No. of frame-reject frames received."
              ::=  { lapbPortStatsEntry 8 }

          lapbPSRxRunts  OBJECT-TYPE
              SYNTAX  Counter
              ACCESS  read-only
              STATUS  mandatory
              DESCRIPTION 
               "The No of Runt frames, that is frames of length shorter than
               the minimum length, received."
              ::=  { lapbPortStatsEntry 9 }

          lapbPSRxBadFrames  OBJECT-TYPE
              SYNTAX  Counter
              ACCESS  read-only
              STATUS  mandatory
              DESCRIPTION 
               "The No. of Bad frames received."
              ::=  { lapbPortStatsEntry 10 }

    --
    -- The Retixwan Group
    --

          rtxWanTable  OBJECT-TYPE
              SYNTAX   SEQUENCE OF RtxWanEntry
              ACCESS   not-accessible
              STATUS   mandatory
              DESCRIPTION
                "The Parameters for the Retix Wan Interface. There will be an 
                entry in this table for each physical port which is configured
                with a physical port protocol - Retixwan "
              ::= { retixwan 1 }

          rtxWanEntry  OBJECT-TYPE
              SYNTAX   RtxWanEntry
              ACCESS   not-accessible
              STATUS   mandatory
              DESCRIPTION
                "The Parameters for the Retix Wan Interface."
              INDEX { rtxWanIfIndex }
              ::= { rtxWanTable 1 }

          RtxWanEntry ::= SEQUENCE {
               rtxWanIfIndex
                    INTEGER,
               rtxWanT1Mode
                  INTEGER,
               rtxWanT1Value
                   INTEGER,
               rtxWanRetry
                   INTEGER,
               rtxWanBlockSize
                   INTEGER,
               rtxWanNegBlockSize
                   INTEGER,
               rtxWanMeasuredDelay
                   INTEGER,
               rtxWanMeasuredLineSpeed
                   INTEGER
               }

          rtxWanIfIndex  OBJECT-TYPE
              SYNTAX  INTEGER
              ACCESS  read-only
              STATUS  mandatory
              DESCRIPTION
                "The value of the index uniquely specifies the physical port
                 for which this entry is applicable."
              ::= { rtxWanEntry 1 }

          rtxWanT1Mode  OBJECT-TYPE
              SYNTAX  INTEGER {
                      enable(1),
                      disable(2)
                      } 
              ACCESS  read-write
              STATUS  mandatory
              DESCRIPTION
                "LAPB T1 Calculation.  This parameter is used to enable
                 the calculation of the value for the LAPB T1 Timer by
                 the WAN Protocol Handler.  When disabled, a pre-configured
                 value is used.  By default, the WAN Protocol Handler
                 calculates the value for the LAPB T1 Timer."
              ::= { rtxWanEntry 2 }

          rtxWanT1Value  OBJECT-TYPE
              SYNTAX  INTEGER (10..5000)
              ACCESS  read-write
              STATUS  mandatory
              DESCRIPTION
                "LAPB T1 Timer Value.  This parameter is used to
                 pre-configure the LAPB T1 Timer when it is to not
                 to be calculated by the WAN Protocol Handler.
                 This parameter is specified in units of milliseconds."
              ::= { rtxWanEntry 3 }

          rtxWanRetry  OBJECT-TYPE
              SYNTAX  INTEGER (1..255)
              ACCESS  read-write
              STATUS  mandatory
              DESCRIPTION
                "LAPB Retry Limit.  This parameter indicates the
                 maximum number of attempts to be made to complete
                 the successful transmission of a frame.  The default
                 value for this parameter is 4."
              ::= { rtxWanEntry 4 }

          rtxWanBlockSize  OBJECT-TYPE
              SYNTAX  INTEGER (200..1528)
              ACCESS  read-write
              STATUS  mandatory
              DESCRIPTION
                "Block Size.  The value of this parameter indicates
                 the block size, in bytes, to be indicated to the
                 remote partner in the link negotiate packets sent.
                 This however cannot be assumed to be the value of
                 the actual block size to be used on the link, as it
                 will be the smaller of this value and that indicated
                 by the remote unix.  The default value for the block
                 size is 552 bytes."
              ::= { rtxWanEntry 5 }

          rtxWanNegBlockSize  OBJECT-TYPE
              SYNTAX  INTEGER (200..1528)
              ACCESS  read-only
              STATUS  mandatory
              DESCRIPTION
                "Negotiated Block Size.  The value returned for this
                 parameter is the negotiated physical block size in
                 bytes.  When the block size has not been negotiated,
                 the configured block size is returned.  This parameter
                 is specified in units of bytes."
              ::= { rtxWanEntry 6 }

          rtxWanMeasuredDelay  OBJECT-TYPE
              SYNTAX  INTEGER (-1..10000)
              ACCESS  read-only
              STATUS  mandatory
              DESCRIPTION
                "Measured Network Transit Delay.  The value returned
                 for this parameter will be the result of the measured
                 transit delay in milliseconds for the link. A value of
                 -1 indicates that the delay has not been measured."
              ::= { rtxWanEntry 7 }


          rtxWanMeasuredLineSpeed  OBJECT-TYPE
              SYNTAX  INTEGER
              ACCESS  read-only
              STATUS  mandatory
              DESCRIPTION
                "This parameter is a measure of the links speed in
                 bits per second."
              ::= { rtxWanEntry 8 }
   
 
    -- 
    --    Token Ring Private Objects
    --
    --    This group augments the draft standard dot5 MIB
    --

      tkrPortTable  OBJECT-TYPE
          SYNTAX  SEQUENCE OF TkrPortEntry 
          ACCESS  not-accessible
          STATUS  mandatory
          DESCRIPTION
             "Table of Token Ring per Port parameters. "
          ::= { tokenring 1 }
           
      tkrPortEntry  OBJECT-TYPE
          SYNTAX  TkrPortEntry 
          ACCESS  not-accessible
          STATUS  mandatory
          DESCRIPTION
            " Entries of Table of Source Routing per port parameters. "
          INDEX  { tkrPortIndex }
          ::= { tkrPortTable 1 }

      TkrPortEntry  ::= SEQUENCE {
          tkrPortIndex
              INTEGER,
          tkrNoOfLinkResets
              INTEGER,
          tkrLastLinkResetReason
              INTEGER,
          tkrTimeSinceLastLinkReset
              INTEGER
          }


      tkrPortIndex  OBJECT-TYPE
          SYNTAX  INTEGER
          ACCESS  read-only
          STATUS  mandatory
          DESCRIPTION
             "The physical port for which this entry applies."
          ::= { tkrPortEntry 1 }


      tkrNoOfLinkResets  OBJECT-TYPE
         SYNTAX  INTEGER
         ACCESS  read-only
         STATUS  mandatory
         DESCRIPTION
           "This object is a count of the number of resets which have
            occurred on this Token Ring link, since the last reinitialization
            of the unit."
         ::= { tkrPortEntry 2 }

      tkrLastLinkResetReason  OBJECT-TYPE
         SYNTAX  INTEGER {
                 noReason    (1),
                 management  (2),
                 deviceError (3),
                 cableDrop   (4),
                 protocol    (5)
                 }
         ACCESS  read-only
         STATUS  mandatory
         DESCRIPTION
             "This object gives the a reason code for the last reset which
              occurred on this Token ring port."
         ::= { tkrPortEntry 3 }

      tkrTimeSinceLastLinkReset  OBJECT-TYPE
         SYNTAX  INTEGER
         ACCESS  read-only
         STATUS  mandatory
         DESCRIPTION
            "This is a time (in hundredths of seconds) since the last link
             reset, eg. the time since the link last went down. The value
             of this object is zero if no link resets have occurred since
             the last reinitialization of the unit."
         ::= { tkrPortEntry 4 }

    --
    -- The IPX Group
    --

          ipxRouting  OBJECT-TYPE
              SYNTAX  INTEGER{
                      enabled (1),
                      disabled (2)
                      }
              ACCESS  read-write
              STATUS  mandatory
              DESCRIPTION
                "This object is used to enable or disable IPX routing. It 
                indicates whether the unit is functioning as an IPX router.
                A value of 1 is used to enable IPX routing while a value of
                2 is used to disable it. The default value is Disable(2). "
              ::= { ipx 1 }

          ipxSecurity  OBJECT-TYPE
              SYNTAX  INTEGER{
                      enabled (1),
                      disabled (2)
                      }
              ACCESS  read-write
              STATUS  mandatory
              DESCRIPTION
                "This parameter is used to enable or disable the security 
                features for the IPX protocol."
              ::= { ipx 2 }

          ipxInternetBcastProcessing  OBJECT-TYPE
              SYNTAX  INTEGER{
                      enabled (1),
                      disabled (2)
                      }
              ACCESS  read-write
              STATUS  mandatory
              DESCRIPTION
                "This parameter is used to enable or disable the Internet 
                broadcast processing feature. If the value is enabled(1), 
                then IPX internet broadcast packets are processed 
                otherwise they are discarded."
              ::= { ipx 3 }

          ipxTotalInHdrErrors  OBJECT-TYPE
              SYNTAX  Counter
              ACCESS  read-only
              STATUS  mandatory
              DESCRIPTION
                "The total number of IPX datagrams received by the unit and
                 discarded due to having a bad checksum, incorrect length or
                 a hop count expiry (i.e. a hop count value of 0)."
              ::= { ipx 4 }

          ipxTotalAccessViolations  OBJECT-TYPE
              SYNTAX  Counter
              ACCESS  read-only
              STATUS  mandatory
              DESCRIPTION
                "This is the total number of IPX datagrams received by 
                the unit and discarded because they were not permitted 
                access to the network."
              ::= { ipx 5 }

          ipxTotalInDiscards  OBJECT-TYPE
              SYNTAX  Counter
              ACCESS  read-only
              STATUS  mandatory
              DESCRIPTION
                "This is the total number of IPX datagrams received by 
                the unit and discarded because the internal queues are full."
              ::= { ipx 6 }

          ipxTotalOutDiscards  OBJECT-TYPE
              SYNTAX  Counter
              ACCESS  read-only
              STATUS  mandatory
              DESCRIPTION
                "This is the total number of IPX datagrams received by 
                the unit and discarded because the transmit queues are full."
              ::= { ipx 7 }
      
          ipxTotalOtherDiscards  OBJECT-TYPE
              SYNTAX  Counter
              ACCESS  read-only
              STATUS  mandatory
              DESCRIPTION
                "This is the total number of IPX datagrams received by 
                the unit and discarded for other reasons, such as an 
                incorrectly configured WAN port. "
              ::= { ipx 8 }

          ipxTotalTransmittedDgms  OBJECT-TYPE
              SYNTAX  Counter
              ACCESS  read-only
              STATUS  mandatory
              DESCRIPTION
                "This is total number of IPX datagrams which have been 
                transmitted by the unit."
              ::= { ipx 9 }

          ipxTotalReceivedDgms  OBJECT-TYPE
              SYNTAX  Counter
              ACCESS  read-only
              STATUS  mandatory
              DESCRIPTION
                "This is the total number of IPX datagrams which have 
                been received by the unit."
              ::= { ipx 10 }

          ipxTotalForwardedDgms  OBJECT-TYPE
              SYNTAX  Counter
              ACCESS  read-only
              STATUS  mandatory
              DESCRIPTION
                "The number of IPX datagrams for which this entry was not 
                their final destination, as a result of which an attempt 
                was made to find a route to forward them to that final 
                destination."
              ::= { ipx 11 }

          ipxTotalRxNotRoutedDgms  OBJECT-TYPE
              SYNTAX  Counter
              ACCESS  read-only
              STATUS  mandatory
              DESCRIPTION
                "This is the total number of IPX datagrams received and then
                discarded by the unit because no route is available. "
              ::= { ipx 12 }

          ipxTotalInDelivers  OBJECT-TYPE
              SYNTAX  Counter
              ACCESS  read-only
              STATUS  mandatory
              DESCRIPTION
                "This is the total number of IPX datagrams received and then
                passed to the upper layers."
              ::= { ipx 13 }


          ipxTotalInAddrErrors  OBJECT-TYPE
              SYNTAX  Counter
              ACCESS  read-only
              STATUS  mandatory
              DESCRIPTION
                "This is a count of the total number of IPX frames which were
                 received and then discarded due to having a bad IPX address
                 value."
              ::= { ipx 14 }

    -- The IPX Routing Information Table

          ipxRoutingInformationTable  OBJECT-TYPE
              SYNTAX  SEQUENCE OF IpxRITEntry
              ACCESS  not-accessible
              STATUS  mandatory
              DESCRIPTION
                "This is a list of the entries in the IPX Routing Information
                 Table."
              ::= { ipx 15 }
       

          ipxRITEntry  OBJECT-TYPE
              SYNTAX  IpxRITEntry
              ACCESS  not-accessible
              STATUS  mandatory
              DESCRIPTION
                "This is an entry in the IPX Routing Information Table."
              INDEX { ipxRITDestNwkNumber }
              ::= { ipxRoutingInformationTable 1 }

          IpxRITEntry ::= SEQUENCE {
                  ipxRITDestNwkNumber
                      OCTET STRING,
                  ipxRITGwyHostAddress
                      OCTET STRING,
                  ipxRITHopCount
                      INTEGER,
                  ipxRITDelay
                      INTEGER,
                  ipxRITInterface
                      INTEGER,
                  ipxRITDirectConnect
                      INTEGER,
                  ipxRITAge
                      INTEGER
                  }

          ipxRITDestNwkNumber  OBJECT-TYPE
              SYNTAX  OCTET STRING (SIZE(4))
              ACCESS  read-only
              STATUS  mandatory
              DESCRIPTION
                "This string contains the IPX Network Number. The 
                address contained in the returned string is in hexadecimal 
                form. If the network number is not a full 4 bytes long, then 
                it is zero-filled, e.g. a network number, 0x234fd will 
                appear as 0x000234fd."
              ::= { ipxRITEntry 1 }
      
          ipxRITGwyHostAddress  OBJECT-TYPE
              SYNTAX  OCTET STRING (SIZE(6))
              ACCESS  read-only
              STATUS  mandatory
              DESCRIPTION
                "This is the Host Address or the gateway to the network 
                specified by the corresponding ipxRITNwkNumber."
              ::= { ipxRITEntry 2 }

          ipxRITHopCount  OBJECT-TYPE
              SYNTAX  INTEGER
              ACCESS  read-only
              STATUS  mandatory
              DESCRIPTION
                "This is the hop count to reach the specified network. It has
                 a range of values from 0 to 15."
              ::= { ipxRITEntry 3 }

          ipxRITDelay  OBJECT-TYPE
              SYNTAX  INTEGER
              ACCESS  read-only
              STATUS  mandatory
              DESCRIPTION
                "This is the estimated delay to reach the specified network."
              ::= { ipxRITEntry 4 }
      
          ipxRITInterface  OBJECT-TYPE
              SYNTAX  INTEGER
              ACCESS  read-only
              STATUS  mandatory
              DESCRIPTION
                "This is the interface through which the IPX datagram is routed
                to the gateway identified by the corresponding entry for
                ipxRITGwyHostAddress. "
              ::= { ipxRITEntry 5 }

          ipxRITDirectConnect  OBJECT-TYPE
              SYNTAX  INTEGER {
                      direct (1),
                      indirect (2)
                      }
              ACCESS  read-only
              STATUS  mandatory
              DESCRIPTION
                "This object is used to indicate whether the gateway is 
                directly connected or not. If the value of this object 
                is direct(1), this indicates a directly connected gateway, 
                if the value is indirect(2) then the gateway is not 
                directly connected."
              ::= { ipxRITEntry 6 }

          ipxRITAge  OBJECT-TYPE
              SYNTAX  INTEGER
              ACCESS  read-only
              STATUS  mandatory
              DESCRIPTION
                "This is the age of this entry."
              ::= { ipxRITEntry 7 }


    -- The IPX SAP Bindery Table

          ipxSAPBinderyTable  OBJECT-TYPE
              SYNTAX  SEQUENCE OF IpxSAPBinderyEntry
              ACCESS  not-accessible
              STATUS  mandatory
              DESCRIPTION
            "This is the Service Advertising Protocol Table which holds
             information about the different servers visible to the device."
              ::= { ipx 16 }

          ipxSAPBinderyEntry  OBJECT-TYPE
              SYNTAX  IpxSAPBinderyEntry
              ACCESS  not-accessible
              STATUS  mandatory
              DESCRIPTION
            "This is an entry in the SAP Bindery Table."
              INDEX  { ipxSAPBinderyType, ipxSAPBinderyServerIPXAddress }
              ::= { ipxSAPBinderyTable 1 }

     IpxSAPBinderyEntry ::= SEQUENCE {
            ipxSAPBinderyType
                INTEGER,
            ipxSAPBinderyServerIPXAddress
                OCTET STRING,
            ipxSAPBinderyServerName
                DisplayString,
            ipxSAPBinderyHopCount
                INTEGER,
            ipxSAPBinderySocket
                INTEGER
            }

    ipxSAPBinderyType  OBJECT-TYPE
        SYNTAX  INTEGER {
     --               unknown       (0),   
                    user          (1),
                    userGroup     (2),
                    printQueue    (3),
                    fileServer    (4),
                    jobServer     (5),
                    gateway       (6),
                    printServer   (7),
                    archiveQueue  (8),
                    archiveServer (9),
                    jobQueue      (10),
                    administration (11),
                    remoteBridgeServer (36),
                    advertisingPrintServer (71),
                    wild          (65535)
                }
        ACCESS  read-only
        STATUS  mandatory
        DESCRIPTION
            "This is the type of the server whose IPX address is given by
             ipxSAPBinderyServerIPXAddress."
        ::= { ipxSAPBinderyEntry 1 }

    ipxSAPBinderyServerIPXAddress  OBJECT-TYPE
        SYNTAX  OCTET STRING (SIZE(10))
        ACCESS  read-only
        STATUS  mandatory
        DESCRIPTION
            "This string contains the network number and host address, i.e. the
             IPX address of an IPX Server."
        ::= { ipxSAPBinderyEntry 2 }

    ipxSAPBinderyServerName  OBJECT-TYPE
        SYNTAX  DisplayString (SIZE(48))
        ACCESS  read-only
        STATUS  mandatory
        DESCRIPTION
            "This is the name of the server. It is a textual string up to
             48 characters long."
        ::= { ipxSAPBinderyEntry 3 }

    ipxSAPBinderyHopCount  OBJECT-TYPE
        SYNTAX  INTEGER
        ACCESS  read-only
        STATUS  mandatory
        DESCRIPTION
            "This is the hop count to reach the specified server. This object
             can take any value in the range 0 to 15."
        ::= { ipxSAPBinderyEntry 4 }

    ipxSAPBinderySocket  OBJECT-TYPE
        SYNTAX  INTEGER
        ACCESS  read-only
        STATUS  mandatory
        DESCRIPTION
            "This is the number of the socket at which the server provides the
             service."
        ::= { ipxSAPBinderyEntry 5 }


    -- The IPX Interface Configuration Table

    ipxIfConfigTable  OBJECT-TYPE
        SYNTAX  SEQUENCE OF IpxIfCfgEntry
        ACCESS  not-accessible
        STATUS  mandatory
        DESCRIPTION
            "This table contains a list of objects which are used to configure
             an IPX logical port."
        ::= { ipx 17 }


    ipxIfCfgEntry  OBJECT-TYPE
        SYNTAX  IpxIfCfgEntry
        ACCESS  not-accessible
        STATUS  mandatory
        DESCRIPTION
            "This is an entry in the IPX interfaces table."
        INDEX { ipxIfCfgIndex }
        ::= { ipxIfConfigTable 1 }

    IpxIfCfgEntry ::= SEQUENCE {
            ipxIfCfgIndex
                INTEGER,
            ipxIfRoutingFlag
                INTEGER,
            ipxIfNwkNumber
                OCTET STRING,
            ipxIfHostAddress
                OCTET STRING,
            ipxIfLANEncapsulation
                INTEGER,
            ipxIfDisposition
                INTEGER,
            ipxIfDelay
                INTEGER,
            ipxIfAccessList1
                INTEGER,
            ipxIfAccessList2
                INTEGER,
            ipxIfRIPTimer
                INTEGER,
            ipxIfSAPTimer
                INTEGER,
            ipxIfSAPFilteringOutFlag
                INTEGER,
            ipxIfSAPFilteringInFlag
                INTEGER,
            ipxIfSAPFilteringActionNoMatch
                INTEGER
            }

    ipxIfCfgIndex  OBJECT-TYPE
        SYNTAX  INTEGER
        ACCESS  read-only
        STATUS  mandatory
        DESCRIPTION
            "The index value which uniquely identifies the logical port
             to which this entry is applicable. "
        ::= { ipxIfCfgEntry 1 }

    ipxIfRoutingFlag  OBJECT-TYPE
        SYNTAX  INTEGER{
                enabled (1),
                disabled (2)
                }
        ACCESS  read-write
        STATUS  mandatory
        DESCRIPTION
            "The value of this object indicates the current state of IPX
             routing on the logical port."
        ::= { ipxIfCfgEntry 2 }

    ipxIfNwkNumber  OBJECT-TYPE
        SYNTAX  OCTET STRING (SIZE(4))
        ACCESS  read-write
        STATUS  mandatory
        DESCRIPTION
            "This string contains this interface`s IPX Network Number.
             The address contained in the returned string is in hexadecimal
             form. If the network number is not a full 4 bytes long, then it
             is zero-filled, e.g.  a network number, 0x234fd will appear
             as 0x000234fd."
        ::= { ipxIfCfgEntry 3 }

    ipxIfHostAddress  OBJECT-TYPE
        SYNTAX  OCTET STRING (SIZE(6))
        ACCESS  read-only
        STATUS  mandatory
        DESCRIPTION
            "This is the host address for the LP. The combination of the
             ipxIfNwkNumber and this object gives the full IPX address for the
             LP. If the LP is attached to a LAN PP then this object
             will have the same value as the MAC address of the PP.
             For a WAN PP, the host address takes the value of
             the unit host address, i.e. the lowest MAC Address on the system"
        ::= { ipxIfCfgEntry 4 }

    ipxIfLANEncapsulation  OBJECT-TYPE
        SYNTAX  INTEGER{
                ieee802-3 (1),
                ethernet (2),
                ieee802-2 (3),
                snap (4)
                }
        ACCESS  read-write
        STATUS  mandatory
        DESCRIPTION
            "This is the datagram encapsulation which applies to the
             interface. The default value is IEEE802.3(1). A Token Ring
	         logical port will only support iee802-2(3) encapsulation."
        ::= { ipxIfCfgEntry 5 }

    ipxIfDisposition  OBJECT-TYPE
        SYNTAX  INTEGER{
                bridge (1),
                discard (2)
                }
        ACCESS  read-write
        STATUS  mandatory
        DESCRIPTION
            "This parameter determines the action taken on a received IPX
             datagram if routing is disabled for this port, and the
             global routing flag is set to enabled (1). If routing is
             disabled for this port and this object has a value of
             discard (2), than all IPX datagrams received on this interface
             and not addressed to the unit,will be discarded."
        ::= { ipxIfCfgEntry 6 }

    ipxIfDelay  OBJECT-TYPE
        SYNTAX  INTEGER
        ACCESS  read-write
        STATUS  mandatory
        DESCRIPTION
            "This is the delay associated with a specific path."
        ::= { ipxIfCfgEntry 7 }

    ipxIfAccessList1  OBJECT-TYPE
        SYNTAX  INTEGER (0..31)
        ACCESS  read-write
        STATUS  mandatory
        DESCRIPTION
          "The first entry in the AccessList Table which will be used by 
           this port. This entry also associates a table of entries from 
           the Security Table with this LP.  A value of zero indicates 
           that the default entry is used i.e. there is no access checking 
           done at all."
        ::= { ipxIfCfgEntry 8 }

    ipxIfAccessList2  OBJECT-TYPE
        SYNTAX  INTEGER (0..31)
        ACCESS  read-write
        STATUS  mandatory
        DESCRIPTION
          "The second entry in the AccessList Table which will be used by 
       this port. This entry also associates a table of entries from 
           the Security Table with this LP.  A value of zero indicates 
           that the default entry is used i.e. there is no access checking 
           done at all."
        ::= { ipxIfCfgEntry 9 }

    ipxIfRIPTimer  OBJECT-TYPE
        SYNTAX  INTEGER (10..65536)
        ACCESS  read-write
        STATUS  mandatory
        DESCRIPTION
          "This timer controls the rate of generation of RIP messages
           and their transmission on this logical port."
        ::= { ipxIfCfgEntry 10 }

    ipxIfSAPTimer  OBJECT-TYPE
        SYNTAX  INTEGER (30..65535)
        ACCESS  read-write
        STATUS  mandatory
        DESCRIPTION
          "This timer controls the rate of generation of SAP messages
           and their transmission on this logical port."
        ::= { ipxIfCfgEntry 11 }

    ipxIfSAPFilteringOutFlag  OBJECT-TYPE
        SYNTAX  INTEGER{
                enabled (1),
                disabled (2)
                }
        ACCESS  read-write
        STATUS  mandatory
        DESCRIPTION
            "The value of this object indicates the current state of IPX
             Sap Filtering for outgoing Saps on the logical port."
        ::= { ipxIfCfgEntry 12 }

    ipxIfSAPFilteringInFlag  OBJECT-TYPE
        SYNTAX  INTEGER{
                enabled (1),
                disabled (2)
                }
        ACCESS  read-write
        STATUS  mandatory
        DESCRIPTION
            "The value of this object indicates the current state of IPX
             Sap Filtering for incoming Saps on the logical port."
        ::= { ipxIfCfgEntry 13 }

    ipxIfSAPFilteringActionNoMatch  OBJECT-TYPE
        SYNTAX  INTEGER{
                pass (1),
                discard (2)
                }
        ACCESS  read-write
        STATUS  mandatory
        DESCRIPTION
            "This object indicates the action to be taken for an 
             incoming/outgoing Sap which does not match any entry in the
         Sap Filtering Table."
        ::= { ipxIfCfgEntry 14 }

    -- IPX Access List Table

        ipxAccessListTable  OBJECT-TYPE
           SYNTAX  SEQUENCE OF IpxAccessListEntry
           ACCESS  not-accessible
           STATUS  mandatory
           DESCRIPTION
             "This is a table of the Access list parameters, these parameters
              are used to define particular security characteristics for
              an LP."
           ::= { ipx 18 }

        ipxAccessListEntry  OBJECT-TYPE
           SYNTAX  IpxAccessListEntry
           ACCESS  not-accessible
           STATUS  mandatory
           DESCRIPTION
             " An entry in the access list table. To set an entry in this 
               table, ALL the objects must be present in a single SET PDU."
           INDEX  { ipxAccessListIndex }
           ::= { ipxAccessListTable 1 }

        IpxAccessListEntry  ::= SEQUENCE {
               ipxAccessListIndex
                   INTEGER,
               ipxTxCheck
                   INTEGER,
               ipxNoMatchTxAction
                   INTEGER,
               ipxRxCheck
                   INTEGER,
               ipxNoMatchRxAction
                   INTEGER
            }

      ipxAccessListIndex  OBJECT-TYPE
          SYNTAX  INTEGER (1..31)
          ACCESS  read-only
          STATUS  mandatory
          DESCRIPTION
             "This index uniquely identifies an entry in the access list
              table. Each LP can reference any two of these entries."
          ::= { ipxAccessListEntry 1 }

       ipxTxCheck  OBJECT-TYPE
          SYNTAX  INTEGER {
                  enabled (1),
                  disabled (2)
                  }
          ACCESS  read-write
          STATUS  mandatory
          DESCRIPTION
             "Indicates whether checking of IPX packets to be transmitted, is
              enabled or not."
          ::= { ipxAccessListEntry 2 }

        ipxNoMatchTxAction  OBJECT-TYPE
           SYNTAX  INTEGER {
                   pass (1),
                   block (2)
                   }
           ACCESS  read-write
           STATUS  mandatory
           DESCRIPTION
              " When an IPX datagram is to be transmitted, the addressing
                information in the packet is compared against the filters in 
                the security table. If there is a no match then the frame is
                either accepted (queued for transmission) or it is denied,
                depending on the value of this object."
           ::= { ipxAccessListEntry 3 }

        ipxRxCheck  OBJECT-TYPE
            SYNTAX  INTEGER {
                    enabled (1),
                    disabled (2)
                    }
            ACCESS  read-write
            STATUS  mandatory
            DESCRIPTION
               " Indicates whether received IPX packets are checked or not."
            ::= { ipxAccessListEntry 4 }

        ipxNoMatchRxAction  OBJECT-TYPE
           SYNTAX  INTEGER {
                   pass (1),
                   block (2)
                   }
           ACCESS  read-write
           STATUS  mandatory
           DESCRIPTION
              " When an IPX datagram is to be received, the addressing
                information in the packet is compared against the filters in 
                the security table. If there is a no match then the frame is
                either accepted or it is denied, depending on the value 
                of this object."
           ::= { ipxAccessListEntry 5 }

        ipxIfSecurityTable  OBJECT-TYPE
            SYNTAX  SEQUENCE OF IpxIfSecurityEntry
            ACCESS  not-accessible
            STATUS  mandatory
            DESCRIPTION
                "A table of the interface security parameters."
            ::= { ipx 19 }

        ipxIfSecurityEntry  OBJECT-TYPE
            SYNTAX  IpxIfSecurityEntry
            ACCESS  not-accessible
            STATUS  mandatory
            DESCRIPTION
                "An entry in the security table. For each entry in the 
                Access List Table, there is a list(table) of Security 
                entries. Therefore, as each port has 2 access List 
                entries associated with it, then the port has access to
                two separate lists of security entries within this table.
                To set an entry in this table, ALL the objects must be
                supplied in a single SET PDU."
            INDEX  { ipxIfSecurityAccessListNum,
                    ipxIfSecurityIndex  }
            ::= { ipxIfSecurityTable 1 }

        IpxIfSecurityEntry  ::= SEQUENCE {
           ipxIfSecurityAccessListNum
               INTEGER,
           ipxIfSecurityIndex
               INTEGER,
           ipxIfSecuritySrcNwkNum
               OCTET STRING,
           ipxIfSecuritySrcHost
               OCTET STRING,
           ipxIfSecurityDestNwkNum
               OCTET STRING,
           ipxIfSecurityDestHost
               OCTET STRING,
           ipxIfSecurityDestSocket
               INTEGER,
           ipxIfSecurityAction
               INTEGER,
           ipxIfSecurityOperator
               INTEGER,
           ipxIfSecurityEntryType
               INTEGER
           }

        ipxIfSecurityAccessListNum  OBJECT-TYPE
            SYNTAX  INTEGER (1..31)
            ACCESS  read-write
            STATUS  mandatory
            DESCRIPTION
              "The access list entry number with which this security entry is
               attached."
            ::= { ipxIfSecurityEntry 1 }

        ipxIfSecurityIndex  OBJECT-TYPE
            SYNTAX  INTEGER
            ACCESS  read-write
            STATUS  mandatory
            DESCRIPTION
              "An index into the security table."
            ::= { ipxIfSecurityEntry 2 }

        ipxIfSecuritySrcNwkNum  OBJECT-TYPE
           SYNTAX  OCTET STRING (SIZE(4))
           ACCESS  read-write
           STATUS  mandatory
           DESCRIPTION
             "The network number of the source. A value of zero means the
             entry applies to all networks."
           ::= { ipxIfSecurityEntry 3 }

        ipxIfSecuritySrcHost  OBJECT-TYPE
           SYNTAX  OCTET STRING (SIZE(6))
           ACCESS  read-write
           STATUS  mandatory
           DESCRIPTION
              "The source host address. If this is set to the Broadcast Address
              ( all f's ), then the entry applies to all hosts. The combination
              of this parameter and the ipxIfSecuritySrcNwkNum gives the 
              full IPX address of the source."
           ::= { ipxIfSecurityEntry 4 }

        ipxIfSecurityDestNwkNum  OBJECT-TYPE
           SYNTAX  OCTET STRING (SIZE(4))
           ACCESS  read-write
           STATUS  mandatory
           DESCRIPTION
              "The network number of the destination. A value of zero means the
              entry applies to all networks."
           ::= { ipxIfSecurityEntry 5 }

        ipxIfSecurityDestHost  OBJECT-TYPE
           SYNTAX  OCTET STRING (SIZE(6))
           ACCESS  read-write
           STATUS  mandatory
           DESCRIPTION
              "The destination host address. If this is set to the Broadcast
              Address ( all f's ), then the entry applies to all hosts. The 
              combination of this parameter and the ipxIfSecurityDestNwkNum
              gives the full IPX address of the destination."
           ::= { ipxIfSecurityEntry 6 }

        ipxIfSecurityDestSocket  OBJECT-TYPE
           SYNTAX  INTEGER
           ACCESS  read-write
           STATUS  mandatory
           DESCRIPTION
              "This parameter identifies the destination socket."
           ::= { ipxIfSecurityEntry 7 }

        ipxIfSecurityAction  OBJECT-TYPE
           SYNTAX  INTEGER {
                   pass (1),
                   block (2)
                   }
           ACCESS  read-write
           STATUS  mandatory
           DESCRIPTION
             "Indicates the action in case of a match occurring between the
              this filter and the addressing information in the IPX Packet."
           ::= { ipxIfSecurityEntry 8 }

        ipxIfSecurityOperator  OBJECT-TYPE
           SYNTAX  INTEGER {
                   lt (1),
                   gt (2),
                   eq (3),
                   neq (4)
                   }
           ACCESS  read-write
           STATUS  mandatory
           DESCRIPTION
              "The operator used in comparison."
           ::= { ipxIfSecurityEntry 9 }


        ipxIfSecurityEntryType  OBJECT-TYPE
           SYNTAX  INTEGER {
                   valid   (1),
                   invalid (2)
                   }
           ACCESS  read-write
           STATUS  mandatory
           DESCRIPTION
               "This parameter is used to indicate whether the entry is to
                be added or removed from the ipxIfSecurityTable. If the value
                is valid(1) then this indicates that this is a request to
                add this entry to the table. A value of valid(1) is always
                returned to a GetRequest in the case where the entry exists."
           ::= { ipxIfSecurityEntry 10 }

    -- IPX Interface Statistics Table

        ipxIfStatsTable  OBJECT-TYPE
           SYNTAX  SEQUENCE OF IpxIfStatsEntry
           ACCESS  not-accessible
           STATUS  mandatory
           DESCRIPTION
               "This table contains a list of all the statistics objects for
                an IPX logical port."
           ::= { ipx 20 }

        ipxIfStatsEntry  OBJECT-TYPE
           SYNTAX  IpxIfStatsEntry
           ACCESS  not-accessible
           STATUS  mandatory
           DESCRIPTION
               "This is an entry in the IPX interface statistics table."
           INDEX { ipxIfStatsIndex }
           ::= { ipxIfStatsTable 1 }

        IpxIfStatsEntry ::= SEQUENCE {
            ipxIfStatsIndex
                INTEGER,
            ipxIfReceivedDgms
                Counter,
            ipxIfTransmittedDgms
                Counter,
            ipxIfNoRouteDgms
                Counter,
            ipxIfDgmsInDelivers
                Counter,
            ipxIfInHdrErrors
                Counter,
            ipxIfInAddrErrors
                Counter,
            ipxIfInDiscards
                Counter,
            ipxIfInForwardedFrames
                Counter,
            ipxIfOtherDiscards
                Counter
            }

        ipxIfStatsIndex  OBJECT-TYPE
           SYNTAX  INTEGER
           ACCESS  read-only
           STATUS  mandatory
           DESCRIPTION
               "The index value which uniquely identifies the logical port
                to which this entry is applicable. "
           ::= { ipxIfStatsEntry 1 }

        ipxIfReceivedDgms  OBJECT-TYPE
           SYNTAX  Counter
           ACCESS  read-only
           STATUS  mandatory
           DESCRIPTION
               "The number of IPX datagrams which have been received on this
                interface."
           ::= { ipxIfStatsEntry 2 }


       ipxIfTransmittedDgms  OBJECT-TYPE
           SYNTAX  Counter
           ACCESS  read-only
           STATUS  mandatory
           DESCRIPTION
               "The number of IPX datagrams which have been transmitted on this
                interface."
           ::= { ipxIfStatsEntry 3 }
   
       ipxIfNoRouteDgms  OBJECT-TYPE
           SYNTAX  Counter
           ACCESS  read-only
           STATUS  mandatory
           DESCRIPTION
               "This is the number of IPX datagrams which have been received on
                this interface and then discarded due to no route being 
                found for them."
           ::= { ipxIfStatsEntry 4 }

       ipxIfDgmsInDelivers  OBJECT-TYPE
           SYNTAX  Counter
           ACCESS  read-only
           STATUS  mandatory
           DESCRIPTION
               "This is the total number of IPX datagrams received on this
                interface and routed inwards to either SAP or RIP."
           ::= { ipxIfStatsEntry 5 }

   
       ipxIfInHdrErrors  OBJECT-TYPE
           SYNTAX  Counter
           ACCESS  read-only
           STATUS  mandatory
           DESCRIPTION
               "This is a count of the number of IPX datagrams which have been
                received but discarded due to having an invalid checksum, 
                incorrect length field or hop count expiry."
           ::= { ipxIfStatsEntry 6 }

       ipxIfInAddrErrors  OBJECT-TYPE
           SYNTAX  Counter
           ACCESS  read-only
           STATUS  mandatory
           DESCRIPTION
               "This is a count of the number of IPX datagrams which have been
                received but discarded due to having an invalid IPX address."
           ::= { ipxIfStatsEntry 7 }

       ipxIfInDiscards  OBJECT-TYPE
           SYNTAX  Counter
           ACCESS  read-only
           STATUS  mandatory
           DESCRIPTION
               "This is a count of the number of IPX datagrams which have been
                received on this port but discarded because the internal queue
                is full."
           ::= { ipxIfStatsEntry 8 }

       ipxIfInForwardedFrames  OBJECT-TYPE
           SYNTAX  Counter
           ACCESS  read-only
           STATUS  mandatory
           DESCRIPTION
               "This is a count of the number of IPX datagrams which have been
                received and forwarded."
           ::= { ipxIfStatsEntry 9 }

       ipxIfOtherDiscards  OBJECT-TYPE
           SYNTAX  Counter
           ACCESS  read-only
           STATUS  mandatory
           DESCRIPTION
               "This is a count of the number pf IPX datagrams which have been
               received on this port but discarded due to other reasons, 
               such as an incorrectly configured WAN port."
           ::= { ipxIfStatsEntry 10 }

    --
    -- IPX PPP private objects
    --


    ipxPPPConfigTable  OBJECT-TYPE
        SYNTAX  SEQUENCE OF IpxPPPConfigEntry
        ACCESS  not-accessible
        STATUS  mandatory
        DESCRIPTION
            "This table contains objects which contain config information
            about the use of IPX over a logical port which is attached to 
            a physical port which is running PPP."
           ::= { ipx 21 }
           

    ipxPPPConfigEntry  OBJECT-TYPE
        SYNTAX  IpxPPPConfigEntry
        ACCESS  not-accessible
        STATUS  mandatory
        DESCRIPTION
            "This is and entry in the IPX PPP status table.
             A SNMP error or noSuchName is returned to a request for an
             object in this table if the IPX port identified by the
             value of ipxIfIndex for this entry, is attached to a
             physical port which is not a PPP physical port."
        INDEX  { ipxPPPConfigIfIndex }
        ::= { ipxPPPConfigTable 1 }

    IpxPPPConfigEntry ::= SEQUENCE {
        ipxPPPConfigIfIndex
            INTEGER,
        ipxPPPAdminStatus
            INTEGER
        }

    ipxPPPConfigIfIndex  OBJECT-TYPE
        SYNTAX  INTEGER
        ACCESS  read-only
        STATUS  mandatory
        DESCRIPTION
            "The value of the index uniquley specifies the logical port
             for which this entry is applicable."
         ::= { ipxPPPConfigEntry 1 }

    ipxPPPAdminStatus  OBJECT-TYPE
        SYNTAX  INTEGER {
                open  (1),
                close (2)
                }
        ACCESS  read-write
        STATUS  mandatory
        DESCRIPTION
            "This is the immediate desired state of the IPX network
             protocol. Setting this object to open(1) will inject an
             administrative open event into the IPX network protocol's
             finite state machine. Setting this object to close(2) will
             inject an administrative close event into the IPX network
             protocol's finite state machine."
        ::= { ipxPPPConfigEntry 2 }

    ipxPPPStatusTable  OBJECT-TYPE
        SYNTAX  SEQUENCE OF IpxPPPStatusEntry
        ACCESS  not-accessible
        STATUS  mandatory
        DESCRIPTION
            "This table contains object which hold status information about
             PPP on a IPX port."
        ::= { ipx 22 }
           
    ipxPPPStatusEntry  OBJECT-TYPE
        SYNTAX  IpxPPPStatusEntry
        ACCESS  not-accessible
        STATUS  mandatory
        DESCRIPTION
            "This is and entry in the IPX PPP status table.
             A SNMP error or noSuchName is returned to a request for an
             object in this table if the IPX port identified by the
             value of ipxIfIndex for this entry, is attached to a
             physical port which is not a PPP physical port."
        INDEX { ipxPPPStatusIfIndex }
        ::= { ipxPPPStatusTable 1 }

    IpxPPPStatusEntry ::= SEQUENCE {
        ipxPPPStatusIfIndex
            INTEGER,
        ipxPPPOperStatus
            INTEGER,
        ipxPPPNegotiatedNetworkNumber
            OCTET STRING
        }

    ipxPPPStatusIfIndex  OBJECT-TYPE
        SYNTAX  INTEGER
        ACCESS  read-only
        STATUS  mandatory
        DESCRIPTION
            "The value of the index uniquley specifies the logical port
             for which this entry is applicable."
         ::= { ipxPPPStatusEntry 1 }

    ipxPPPOperStatus  OBJECT-TYPE
        SYNTAX  INTEGER {
                opened (1),
                not-opened (2)
                }
        ACCESS  read-only
        STATUS  mandatory
        DESCRIPTION
            "This is the current operational status of the IPX network
             protocol. If the value of this object is opened(1) then the
             finite state machine for the IPX protocol has reached the
             Opened state."
        ::= { ipxPPPStatusEntry 2 }

    ipxPPPNegotiatedNetworkNumber  OBJECT-TYPE
        SYNTAX  OCTET STRING(SIZE(4))
        ACCESS  read-only
        STATUS  mandatory
        DESCRIPTION
            "This is the IPX Network Number which has been negotiated by
             a local and remote IPXCP for use on this PPP port."
        ::= { ipxPPPStatusEntry 3 }

       ipxSAPFiltering  OBJECT-TYPE
          SYNTAX  INTEGER{
                      enabled (1),
                      disabled (2)
                      }
          ACCESS  read-write
          STATUS  mandatory
          DESCRIPTION
            "This parameter is used to enable or disable the SAP
             filtering feature. If the value is enabled(1),
             then IPX SAP packets are filtered on the ports which
             have outgoing and/or incoming SAP filtering enabled."
          ::= { ipx 23 }

    --
    -- The IPX SAP Filter Test Table
    --

      ipxSAPFilterTestTable  OBJECT-TYPE
         SYNTAX  SEQUENCE OF IpxSAPFilterTestEntry
         ACCESS  not-accessible
         STATUS  mandatory
         DESCRIPTION
            "The SAP Filter Test Table "
         ::= { ipx 24 }


      ipxSAPFilterTestEntry  OBJECT-TYPE
         SYNTAX  IpxSAPFilterTestEntry
         ACCESS  not-accessible
         STATUS  mandatory
         DESCRIPTION
            "Each entry is a Test to be applied to SAP frames on any
             particular port. There can be up to 30 entries in the
             table. Each test is carried out in the following manner:-"
         INDEX  { ipxSAPFilterTestIndex }
         ::= { ipxSAPFilterTestTable 1 }

      IpxSAPFilterTestEntry ::= SEQUENCE {
         ipxSAPFilterTestIndex
            INTEGER,
         ipxSAPFilterTestName
            DisplayString,
         ipxSAPFilterTestType
            INTEGER,
         ipxSAPFilterTestIPXAddr
            OCTET STRING,
         ipxSAPFilterTestSrvName
            DisplayString,
         ipxSAPFilterTestHopCount
            INTEGER,
         ipxSAPFilterTestSocket
            INTEGER
         }        


      ipxSAPFilterTestIndex  OBJECT-TYPE
         SYNTAX  INTEGER(1..31)
         ACCESS  read-only
         STATUS  mandatory
         DESCRIPTION
           "This is the entry index number."
              ::= { ipxSAPFilterTestEntry 1 }


      ipxSAPFilterTestName  OBJECT-TYPE
         SYNTAX  DisplayString (SIZE(0..20))
         ACCESS  read-write
         STATUS  mandatory
         DESCRIPTION
           "This is the test name."
              ::= { ipxSAPFilterTestEntry 2 }

      ipxSAPFilterTestType  OBJECT-TYPE
         SYNTAX  INTEGER {
 --                 unknown       (0),   
                    user          (1),
                    userGroup     (2),
                    printQueue    (3),
                    fileServer    (4),
                    jobServer     (5),
                    gateway       (6),
                    printServer   (7),
                    archiveQueue  (8),
                    archiveServer (9),
                    jobQueue      (10),
                    administration (11),
                    remoteBridgeServer (36),
                    advertisingPrintServer (71),
                    wild          (65535)
                     }
          ACCESS  read-write
          STATUS  mandatory
          DESCRIPTION
            "This is the type of the server whose IPX address is given by
             ipxSAPFilterTestServerIPXAddr."
              ::= { ipxSAPFilterTestEntry 3 }

      ipxSAPFilterTestIPXAddr  OBJECT-TYPE
         SYNTAX  OCTET STRING (SIZE(10))
         ACCESS  read-write
         STATUS  mandatory
         DESCRIPTION
            "This string contains the network number and host
             address, i.e the IPX address of an IPX Server."
         ::= { ipxSAPFilterTestEntry 4 }

      ipxSAPFilterTestSrvName  OBJECT-TYPE
         SYNTAX  DisplayString (SIZE(48))
         ACCESS  read-write
         STATUS  mandatory
         DESCRIPTION
             "This is the name of the server. It is a textual string
              up to 48 characters long."
         ::= { ipxSAPFilterTestEntry 5 }

      ipxSAPFilterTestHopCount  OBJECT-TYPE
         SYNTAX  INTEGER
         ACCESS  read-write
         STATUS  mandatory
         DESCRIPTION
             "This is the hop count to reach the specified server.
              This object can take any value in the range 0 to 15."
         ::= { ipxSAPFilterTestEntry 6 }

      ipxSAPFilterTestSocket  OBJECT-TYPE
         SYNTAX  INTEGER
         ACCESS  read-write
         STATUS  mandatory
         DESCRIPTION
             "This is the number of the socket at which the server
              provides the service."
         ::= { ipxSAPFilterTestEntry 7 }


    --
    -- The IPX SAP Filter Statement Table
    --

      ipxSAPFilterStmtTable  OBJECT-TYPE
          SYNTAX  SEQUENCE OF IpxSAPFilterStmtEntry
          ACCESS  not-accessible
          STATUS  mandatory
          DESCRIPTION
              "The SAP Filter Statement Table "
          ::= { ipx 25 }

      ipxSAPFilterStmtEntry  OBJECT-TYPE
         SYNTAX  IpxSAPFilterStmtEntry
         ACCESS  not-accessible
         STATUS  mandatory
         DESCRIPTION
           "Each entry is a Test statement. There are up to 30
            entries per port. Each entry links a Test with the
            actions to be carried out depending on the test's
            success or failure. To set an entry in the table,
            all the objects must be present in the SET PDU."
         INDEX   { ipxSFStmtPortNumber, ipxSFStmtIndex }
         ::= { ipxSAPFilterStmtTable 1 }

      IpxSAPFilterStmtEntry ::= SEQUENCE {
         ipxSFStmtPortNumber
            INTEGER,
         ipxSFStmtIndex
            INTEGER,
         ipxSFStmtTestName
            DisplayString,
         ipxSFStmtActionOnSuccess
            INTEGER
         }    


      ipxSFStmtPortNumber  OBJECT-TYPE
          SYNTAX  INTEGER (1..253)
          ACCESS  read-only
          STATUS  mandatory
          DESCRIPTION
            "This is the Logical Port No. for which the table exists."
          ::= { ipxSAPFilterStmtEntry 1 }

      ipxSFStmtIndex  OBJECT-TYPE
          SYNTAX  INTEGER (1..30)
          ACCESS  read-only
          STATUS  mandatory
          DESCRIPTION
              " This is the table index number"
          ::= { ipxSAPFilterStmtEntry 2 }

      ipxSFStmtTestName  OBJECT-TYPE
         SYNTAX  DisplayString (SIZE(1..20))
         ACCESS  read-write
         STATUS  mandatory
         DESCRIPTION
           "This is the name of the Test to apply for this
            statement. It should match a Test name in the ipx SAP
            Filter Test Table. It is an ascii string, of up to
            20 characters."
          ::= { ipxSAPFilterStmtEntry 3 }

      ipxSFStmtActionOnSuccess  OBJECT-TYPE
          SYNTAX  INTEGER {
                            pass(1),
                            discard(2)
                           }
          ACCESS  read-write
          STATUS  mandatory
          DESCRIPTION
            "If an incoming/outgoing SAP matches the filter
             test indexed in this table, then the SAP is either
             allowed into the SAP Bindery table (incoming filtering),
             or send out on this port (outgoing filtering)."
          ::= { ipxSAPFilterStmtEntry 4 }


    --
    -- The DECnet Group
    --

    dcntRouting  OBJECT-TYPE
        SYNTAX  INTEGER{
                enable (1),
                disable (2)
                }
        ACCESS  read-write
        STATUS  mandatory
        DESCRIPTION
            "This object defines whether DECnet Routing has been enabled or not.
             DECnet routing may only be enabled if a valid DECnet address has
             been configured for the device. If a valid address has not been
             configured then a SetRequest to enable dcntRouting will cause a
             badValue error to be generated. "
        ::= { decnet 1 }

    dcntRoutingLevel  OBJECT-TYPE
        SYNTAX  INTEGER
        ACCESS  read-only
        STATUS  mandatory
        DESCRIPTION
            "This object will always return a value of level1(1)."
        ::= { decnet 2 }


    dcntAreaAddress  OBJECT-TYPE
        SYNTAX  INTEGER(1..63)
        ACCESS  read-write
        STATUS  mandatory
        DESCRIPTION
            "This is the DECnet area identification number. It can take on
             any value between 1 and 63. If this object's value is set to zero
             then the DECnet address is deleted. This operation can only be
             performed if decnetRouting {decnet 1} had been disabled. If an
             attempt is made to set this object to a value of zero while
             dcntRouting is enabled, a badValue error will be generated."
        ::= { decnet 3 }

    dcntNodeAddress  OBJECT-TYPE
        SYNTAX  INTEGER(1..1023)
        ACCESS  read-write
        STATUS  mandatory
        DESCRIPTION
            "This is the node address of the device. It can take on any value
             in the range 1 to 1023. If the dcntAreaAddress is zero i.e. the
             decnetAddress has been cleared, then the value returned to a
             GetRequest on this object will also be zero. "
        ::= { decnet 4 }

     dcntInterAreaMaxCost  OBJECT-TYPE
        SYNTAX  INTEGER (1..1022)
        ACCESS  read-write
        STATUS  mandatory
        DESCRIPTION
            "This is the maximum cost possible in a path to a reachable area
             in which his device is situated."
        ::= { decnet 5 }

    dcntInterAreaMaxHops  OBJECT-TYPE
        SYNTAX  INTEGER (1..30)
        ACCESS  read-write
        STATUS  mandatory
        DESCRIPTION
            "This is the maximum number of hops allowed in a path to another
             reachable area."
        ::= { decnet 6 }

     dcntIntraAreaMaxCost  OBJECT-TYPE
        SYNTAX  INTEGER (1..1022)
        ACCESS  read-write
        STATUS  mandatory
        DESCRIPTION
            "The maximum cost possible in a path from the device to a reachable
             node within the same area."
        ::= { decnet 7 }

     dcntIntraAreaMaxHops  OBJECT-TYPE
        SYNTAX  INTEGER (1..30)
        ACCESS  read-write
        STATUS  mandatory
        DESCRIPTION
            "This is the maximum number of hops allowed from this device to
             a reachable node within the same area."
        ::= { decnet 8 }

     dcntMaxVisits  OBJECT-TYPE
        SYNTAX  INTEGER (1..63)
        ACCESS  read-write
        STATUS  mandatory
        DESCRIPTION
            "This is the maximum number of nodes which a data packet can
             traverse before being discarded."
        ::= { decnet 9 }

     dcntRtngMsgTimerBCT1  OBJECT-TYPE
        SYNTAX  INTEGER (5..60)
        ACCESS  read-write
        STATUS  mandatory
        DESCRIPTION
            "This is the maximum time period between broadcasted routing
             messages on the Ethernet."
        ::= { decnet 10 }

     dcntRateControlFreqTimerT2  OBJECT-TYPE
        SYNTAX  INTEGER (1..5)
        ACCESS  read-write
        STATUS  mandatory
        DESCRIPTION
            "This is the rate control frequency timer."
        ::= { decnet 11 }

      dcntSecurity  OBJECT-TYPE
        SYNTAX  INTEGER{
                enabled (1),
                disabled (2)
                }
        ACCESS  read-write
        STATUS  mandatory
        DESCRIPTION
            "This parameter is used to enable or disable the security features
             for the DECnet protocol."
        ::= { decnet 12 }

    dcntSplitPathRouting  OBJECT-TYPE
        SYNTAX  INTEGER {
                enabled (1),
                disabled (2)
                }
        ACCESS  read-write
        STATUS  mandatory
        DESCRIPTION
            "This object is used to enable or disable split path routing for
            the DECnet protocol. If this object has a value of enabled(1) then
            the router will try several path to reach a destination."
        ::= { decnet 13 }

    -- DECnet system wide statistics

    dcntTotalReceivedDgms  OBJECT-TYPE
        SYNTAX  Counter
        ACCESS  read-only
        STATUS  mandatory
        DESCRIPTION
            "This is the total count of all DECnet datagrams received by the
             device on all interfaces. This count includes data packets, hello
             messages and routing messages."
        ::= { decnet 14 }

    dcntTotalTransmittedDgms  OBJECT-TYPE
        SYNTAX  Counter
        ACCESS  read-only
        STATUS  mandatory
        DESCRIPTION
            "This is the total count of all DECnet datagrams transmitted by the
             device on all interfaces."
        ::= { decnet 15 }

    dcntTotalForwardedDgms  OBJECT-TYPE
        SYNTAX  Counter
        ACCESS  read-only
        STATUS  mandatory
        DESCRIPTION
            "This is a count of the total number of data packets which have
             been forwarded by the device on all interfaces."
        ::= { decnet 16 }

     dcntTotalOutRequestedDgms  OBJECT-TYPE
        SYNTAX  Counter
        ACCESS  read-only
        STATUS  mandatory
        DESCRIPTION
            "This is a count of the total number of DECnet hello messages and
             DECnet routing messages which have been transmitted by the device."
        ::= { decnet 17 }

     dcntTotalInDiscards  OBJECT-TYPE
        SYNTAX  Counter
        ACCESS  read-only
        STATUS  mandatory
        DESCRIPTION
            "This is a count of the total number of DECnet packets which have
             been received, but discarded. These packets are discarded by the
             DECnet protocol level."
        ::= { decnet 18 }

     dcntTotalOutDiscards  OBJECT-TYPE
        SYNTAX  Counter
        ACCESS  read-only
        STATUS  mandatory
        DESCRIPTION
            "This is a  count of the total number of DECnet packets which have
             been discarded due to a lack of internal resources. These packets
             are discarded by the DECnet protocol layer."
        ::= { decnet 19 }

     dcntTotalNoRoutes  OBJECT-TYPE
        SYNTAX  Counter
        ACCESS  read-only
        STATUS  mandatory
        DESCRIPTION
            "This is the total number of DECnet packets for which no route
             could be found."
        ::= { decnet 20 }

     dcntTotalInHdrErrors  OBJECT-TYPE
        SYNTAX  Counter
        ACCESS  read-only
        STATUS  mandatory
        DESCRIPTION
            "This is a count of the total number of DECnet packets found with
             an invalid header in the data packet."
        ::= { decnet 21 }

     dcntTotalInAddrErrors  OBJECT-TYPE
        SYNTAX  Counter
        ACCESS  read-only
        STATUS  mandatory
        DESCRIPTION
            "This is a count of the total number of DECnet packets received but
             discarded because the destination address was not a valid address
             for this entity."
        ::= { decnet 22 }

     dcntTotalInDelivers  OBJECT-TYPE
        SYNTAX  Counter
        ACCESS  read-only
        STATUS  mandatory
        DESCRIPTION
            "This is a count of the total number of DECnet packets which have
             been successfully delivered to DECnet Routing Protocols."
        ::= { decnet 23 }

     dcntTotalOtherDiscards  OBJECT-TYPE
        SYNTAX  Counter
        ACCESS  read-only
        STATUS  mandatory
        DESCRIPTION
            "This is a count of the total number of DECnet packets which
             which have been received on this port but discarded due to
             other reasons, such as an incorrectly configured WAN port."
        ::= { decnet 24 }

    dcntTotalAccessViolations  OBJECT-TYPE
        SYNTAX  Counter
        ACCESS  read-only
        STATUS  mandatory
        DESCRIPTION
            "This is a count of the total number of access violations which
             have occurred."
        ::= { decnet 25 }

    -- The DECnet interface configuration table

    dcntIfCfgTable  OBJECT-TYPE
        SYNTAX  SEQUENCE OF DcntIfCfgTableEntry
        ACCESS  not-accessible
        STATUS  mandatory
        DESCRIPTION
            "This is a table of configuration parameters for a DECnet circuit."
        ::= { decnet 26 }

    dcntIfCfgTableEntry  OBJECT-TYPE
        SYNTAX  DcntIfCfgTableEntry
        ACCESS  not-accessible
        STATUS  mandatory
        DESCRIPTION
            "This is an entry in the configuration table."
        INDEX  { dcntIfCfgIndex }
        ::= { dcntIfCfgTable 1 }

    DcntIfCfgTableEntry ::= SEQUENCE {
        dcntIfCfgIndex
            INTEGER,
        dcntIfCfgRouting
            INTEGER,
        dcntIfCfgDisposition
            INTEGER,
        dcntIfCfgRtrPriority
            INTEGER,
        dcntIfCfgHelloTimerBCT3
            INTEGER,
        dcntIfCfgCost
            INTEGER,
        dcntIfCfgAccessList1
            INTEGER,
        dcntIfCfgAccessList2
            INTEGER
        }

    dcntIfCfgIndex  OBJECT-TYPE
        SYNTAX  INTEGER
        ACCESS  read-only
        STATUS  mandatory
        DESCRIPTION
            "This index uniquely identifies the logical port to which this
             entry is applicable."
        ::= { dcntIfCfgTableEntry 1 }

    dcntIfCfgRouting  OBJECT-TYPE
        SYNTAX  INTEGER {
                enable (1),
                disable (2)
                }
        ACCESS  read-write
        STATUS  mandatory
        DESCRIPTION
            "The value of this object indicates the current state of DECnet
             routing on the interface. If the global Routing flag is not 
             enabled, then this has no effect."
        ::= { dcntIfCfgTableEntry 2 }

    dcntIfCfgDisposition  OBJECT-TYPE
        SYNTAX  INTEGER {
                bridge (1),
                discard (2)
                } 
        ACCESS  read-write
        STATUS  mandatory
        DESCRIPTION
            "This parameter determines the action taken on a received DECnet
            datagram if routing is disabled for this port, and the
            global routing flag is set to enabled (1). If routing is
            disabled for this port and this object has a value of
            discard (2), than all DECnet datagrams received on this interface
            and not addressed to the unit,will be discarded."
        ::= { dcntIfCfgTableEntry 3 }

    dcntIfCfgRtrPriority  OBJECT-TYPE
        SYNTAX  INTEGER (1..127)
        ACCESS  read-write
        STATUS  mandatory
        DESCRIPTION
            "This is the priority associated with this interface, it is used to
             determine the designated route. The interface with the highest
             priority is the designated route."
        ::= { dcntIfCfgTableEntry 4 }

    dcntIfCfgHelloTimerBCT3  OBJECT-TYPE
        SYNTAX  INTEGER (1..8191)
        ACCESS  read-write
        STATUS  mandatory
        DESCRIPTION
            "This is the maximum time period between two hello messages,
             transmitted consecutively."
        ::= { dcntIfCfgTableEntry 5 }

    dcntIfCfgCost  OBJECT-TYPE
        SYNTAX  INTEGER (1..25)
        ACCESS  read-write
        STATUS  mandatory
        DESCRIPTION
            "This is the the cost which will be added to the path cost for this
             interface. There is one cost for each logical port."
        ::= { dcntIfCfgTableEntry 6 }

    dcntIfCfgAccessList1  OBJECT-TYPE
        SYNTAX  INTEGER (0..31)
        ACCESS  read-write
        STATUS  mandatory
        DESCRIPTION
            "The first entry in the AccessList Table which will be used by 
            this port. This entry also associates a table of entries from 
            the Security Table with this LP.  A value of zero indicates 
            that the default entry is used i.e. there is no access checking 
            done at all."
        ::= { dcntIfCfgTableEntry 7 }

    dcntIfCfgAccessList2  OBJECT-TYPE
        SYNTAX  INTEGER (0..31)
        ACCESS  read-write
        STATUS  mandatory
        DESCRIPTION
            "The second entry in the AccessList Table which will be used by 
            this port. This entry also associates a table of entries from 
            the Security Table with this LP.  A value of zero indicates 
            that the default entry is used i.e. there is no access checking 
            done at all."
        ::= { dcntIfCfgTableEntry 8 }

    -- The DECnet interface statistics and status table.

    dcntIfStatsTable  OBJECT-TYPE
        SYNTAX  SEQUENCE OF DcntIfStatsTableEntry
        ACCESS  not-accessible
        STATUS  mandatory
        DESCRIPTION
            "This is a table of statistics and status information for a
             DECnet logical port."
        ::= { decnet 27 }

    dcntIfStatsTableEntry  OBJECT-TYPE
        SYNTAX  DcntIfStatsTableEntry
        ACCESS  not-accessible
        STATUS  mandatory
        DESCRIPTION
            "This is an entry in the status and statistics table."
        INDEX  { dcntIfStatsIndex }
        ::= { dcntIfStatsTable 1 }

    DcntIfStatsTableEntry ::= SEQUENCE {
        dcntIfStatsIndex
            INTEGER,
        dcntIfDesignatedRouter
            INTEGER,
        dcntIfReceivedDgms
            Counter,
        dcntIfTransmittedDgms
            Counter,
        dcntIfNoRouteDgms
            Counter,
        dcntIfDgmsInDiscards
            Counter,
        dcntIfInHdrErrors
            Counter,
        dcntIfFrowardedFrames
            Counter,
        dcntIfInAddrErrors
            Counter,
        dcntIfInDelivers
            Counter,
        dcntIfOtherDiscards
            Counter
            }

    dcntIfStatsIndex  OBJECT-TYPE
        SYNTAX  INTEGER
        ACCESS  read-only
        STATUS  mandatory
        DESCRIPTION
            "The index value which uniquely identifies the logical port
             to which this entry is applicable. "
        ::= { dcntIfStatsTableEntry 1 }

    dcntIfDesignatedRouter  OBJECT-TYPE
        SYNTAX  INTEGER {
                 designated (1),
                 notDesignated (2)
                 }
        ACCESS  read-only
        STATUS  mandatory
        DESCRIPTION
            "This parameter indicates if the router is the designated router
             on this interface. There is one designated router on each circuit.
             A value of designated (1) is returned to a Get request if the 
             router is the designated router for this circuit, otherwise a
             value of notDesignated (2) is returned."
        ::= { dcntIfStatsTableEntry 2 }

    dcntIfReceivedDgms  OBJECT-TYPE
        SYNTAX  Counter
        ACCESS  read-only
        STATUS  mandatory
        DESCRIPTION
            "This is a count of the number of DECnet datagrams which have been
             received on this logical port."
        ::= { dcntIfStatsTableEntry 3 }

    dcntIfTransmittedDgms  OBJECT-TYPE
        SYNTAX  Counter
        ACCESS  read-only
        STATUS  mandatory
        DESCRIPTION
            "This is a count of the number of DECnet datagrams which have been
             transmitted on this logical port."
        ::= { dcntIfStatsTableEntry 4 }

    dcntIfNoRouteDgms  OBJECT-TYPE
        SYNTAX  Counter
        ACCESS  read-only
        STATUS  mandatory
        DESCRIPTION
            "This is a count of the number of DECnet datagrams which have been
             received on this logical port and then discarded due to no route
             being found for them."
        ::= { dcntIfStatsTableEntry 5 }

    dcntIfDgmsInDiscards  OBJECT-TYPE
        SYNTAX  Counter
        ACCESS  read-only
        STATUS  mandatory
        DESCRIPTION
            "This is a count of the number of DECnet datagrams which have been
             received on this logical port and then discarded due to the 
             receive queue being full."
        ::= { dcntIfStatsTableEntry 6 }

    dcntIfInHdrErrors  OBJECT-TYPE
        SYNTAX  Counter
        ACCESS  read-only
        STATUS  mandatory
        DESCRIPTION
            "This is a count of the number of DECnet datagrams which have been
             received but discarded due to having an invalid checksum, incorrect
             length field or hop count expiry."
        ::= { dcntIfStatsTableEntry 7 }
    
    dcntIfFrowardedFrames  OBJECT-TYPE
        SYNTAX  Counter
        ACCESS  read-only
        STATUS  mandatory
        DESCRIPTION
            "This is a count of the number of DECnet datagrams which have been
             forwarded by this unit."
        ::= { dcntIfStatsTableEntry 8 }

    dcntIfInAddrErrors  OBJECT-TYPE
        SYNTAX  Counter
        ACCESS  read-only
        STATUS  mandatory
        DESCRIPTION
            "This is a count of the number of DECnet datagrams which have been
             received but discarded due to having an invalid address, for this
             unit."
        ::= { dcntIfStatsTableEntry 9 }

    dcntIfInDelivers  OBJECT-TYPE
        SYNTAX  Counter
        ACCESS  read-only
        STATUS  mandatory
        DESCRIPTION
            "This is a count of the number of DECnet datagrams which have been
             received and delivered user protocols."
        ::= { dcntIfStatsTableEntry 10 }

    dcntIfOtherDiscards  OBJECT-TYPE
        SYNTAX  Counter
        ACCESS  read-only
        STATUS  mandatory
        DESCRIPTION
            "This is a count of the number of DECnet datagrams which have been
             discarded on this logical port due an error e.g. incorrect WAN
             configuration."
        ::= { dcntIfStatsTableEntry 11 }

-- DecNet Routing Information Table

    dcntRoutingTable  OBJECT-TYPE
        SYNTAX  SEQUENCE OF DcntRITEntry
        ACCESS  not-accessible
        STATUS  mandatory
        DESCRIPTION
            "This is the DECnet routing information table. "
        ::= { decnet 28 }

     dcntRITEntry  OBJECT-TYPE
        SYNTAX  DcntRITEntry
        ACCESS  not-accessible
        STATUS  mandatory
        DESCRIPTION
            "This is an entry in the routing information table, each entry
             specifies a particular node's routing information."
        INDEX  { dcntRITDestNode }
        ::= { dcntRoutingTable 1 }

    DcntRITEntry ::= SEQUENCE {
        dcntRITDestNode
            INTEGER,
        dcntRITNextHop
            OCTET STRING,
        dcntRITCost
            INTEGER,
        dcntRITHops
            INTEGER,
        dcntRITInterface
            INTEGER
        }

     dcntRITDestNode  OBJECT-TYPE
        SYNTAX  INTEGER
        ACCESS  read-only
        STATUS  mandatory
        DESCRIPTION
            "This is the address id of the node which uniquely identifies the
             node within a given area."
        ::= { dcntRITEntry 1 }

     dcntRITNextHop  OBJECT-TYPE
        SYNTAX  OCTET STRING
        ACCESS  read-only
        STATUS  mandatory
        DESCRIPTION
            "This is the address of the next hop in the path."
        ::= { dcntRITEntry 2 }

     dcntRITCost  OBJECT-TYPE
        SYNTAX  INTEGER
        ACCESS  read-only
        STATUS  mandatory
        DESCRIPTION
            "This is the path cost of this route."
        ::= { dcntRITEntry 3 }

     dcntRITHops  OBJECT-TYPE
        SYNTAX  INTEGER
        ACCESS  read-only
        STATUS  mandatory
        DESCRIPTION
            "This is the number of hops that have to be traversed to get to the
             destination."
        ::= { dcntRITEntry 4 }

     dcntRITInterface  OBJECT-TYPE
        SYNTAX  INTEGER
        ACCESS  read-only
        STATUS  mandatory
        DESCRIPTION
            "This is the logical port through which the DECnet datagram 
            is routed to the gateway identified by the corresponding entry 
            for dcntRITNextHop. "
        ::= { dcntRITEntry 5 }

-- DecNet Area Routing Table

     dcntAreaRoutingTable  OBJECT-TYPE
        SYNTAX  SEQUENCE OF DcntAreaRITEntry
        ACCESS  not-accessible
        STATUS  mandatory
        DESCRIPTION
            "This is the DECnet area routing table. Its entries are used to
             route packets from the area in which this device resides to other
             areas in the network. This table has a maximum of 63 entries. "
        ::= { decnet 29 }

     dcntAreaRITEntry  OBJECT-TYPE
        SYNTAX  DcntAreaRITEntry
        ACCESS  not-accessible
        STATUS  mandatory
        DESCRIPTION
            "An entry specifies a particular node's routing information."
        INDEX  { dcntAreaRITDestArea }
        ::= { dcntAreaRoutingTable 1 }

    DcntAreaRITEntry ::= SEQUENCE {
        dcntAreaRITDestArea
            INTEGER ,
        dcntAreaRITNextHop
            OCTET STRING,
        dcntAreaRITCost
            INTEGER,
        dcntAreaRITHops
            INTEGER,
        dcntAreaRITInterface
            INTEGER
        }

     dcntAreaRITDestArea  OBJECT-TYPE
        SYNTAX  INTEGER
        ACCESS  read-only
        STATUS  mandatory
        DESCRIPTION
            "This is the area id of the node which uniquely identifies the
             node."
        ::= { dcntAreaRITEntry 1 }

     dcntAreaRITNextHop  OBJECT-TYPE
        SYNTAX  OCTET STRING
        ACCESS  read-only
        STATUS  mandatory
        DESCRIPTION
            "This is the address of the next hop in the path."
        ::= { dcntAreaRITEntry 2 }

     dcntAreaRITCost  OBJECT-TYPE
        SYNTAX  INTEGER
        ACCESS  read-only
        STATUS  mandatory
        DESCRIPTION
            "This is the path cost of this route."
        ::= { dcntAreaRITEntry 3 }

     dcntAreaRITHops  OBJECT-TYPE
        SYNTAX  INTEGER
        ACCESS  read-only
        STATUS  mandatory
        DESCRIPTION
            "This is the number of hops  between here and the destination."
        ::= { dcntAreaRITEntry 4 }

     dcntAreaRITInterface  OBJECT-TYPE
        SYNTAX  INTEGER
        ACCESS  read-only
        STATUS  mandatory
        DESCRIPTION
            "This is the logical port through which the DECnet datagram 
            is routed to the gateway identified by the corresponding entry 
            for dcntAreaRITNextHop. "
        ::= { dcntAreaRITEntry 5 }

    -- DECnet Access List Table

        dcntAccessListTable  OBJECT-TYPE
           SYNTAX  SEQUENCE OF DcntAccessListEntry
           ACCESS  not-accessible
           STATUS  mandatory
           DESCRIPTION
             "This is a table of the Access list parameters, these parameters
              are used to define the particular security characteristic for
              a logical port."
           ::= { decnet 30 }

        dcntAccessListEntry  OBJECT-TYPE
           SYNTAX  DcntAccessListEntry
           ACCESS  not-accessible
           STATUS  mandatory
           DESCRIPTION
             " An entry in the access table. To set an entry in this table
             all the objects must be present in a SET PDU."
           INDEX  { dcntAccessListIndex }
           ::= { dcntAccessListTable 1 }

        DcntAccessListEntry  ::= SEQUENCE {
               dcntAccessListIndex
                   INTEGER,
               dcntTxCheck
                   INTEGER,
               dcntNoMatchTxAction
                   INTEGER,
               dcntRxCheck
                   INTEGER,
               dcntNoMatchRxAction
                   INTEGER
            }

       dcntAccessListIndex  OBJECT-TYPE
          SYNTAX  INTEGER (0..31)
          ACCESS  read-only
          STATUS  mandatory
          DESCRIPTION
             "The index value which uniquely identifies the entry in this
              table. "
          ::= { dcntAccessListEntry 1 }

       dcntTxCheck  OBJECT-TYPE
          SYNTAX  INTEGER {
                  enabled (1),
                  disabled (2)
                  }
          ACCESS  read-write
          STATUS  mandatory
          DESCRIPTION
             "Indicates whether checking of DECnet packets to be transmitted,
             is enabled or not."
          ::= { dcntAccessListEntry 2 }

        dcntNoMatchTxAction  OBJECT-TYPE
           SYNTAX  INTEGER {
                   pass (1),
                   block (2)
                   }
           ACCESS  read-write
           STATUS  mandatory
           DESCRIPTION
              " When a DECnet datagram is to be transmitted, the source and
                destination addresses are ANDed with their masks and compared
                with those in the security entry. This object indicates the
                action to be taken if these two don't match."
           ::= { dcntAccessListEntry 3 }

        dcntRxCheck  OBJECT-TYPE
            SYNTAX  INTEGER {
                    enabled (1),
                    disabled (2)
                    }
            ACCESS  read-write
            STATUS  mandatory
            DESCRIPTION
               " Indicates whether received DECnet packets are checked or not."
            ::= { dcntAccessListEntry 4 }

        dcntNoMatchRxAction  OBJECT-TYPE
           SYNTAX  INTEGER {
                   pass (1),
                   block (2)
                   }
           ACCESS  read-write
           STATUS  mandatory
           DESCRIPTION
              " When a DECnet datagram is to be received, the source and
                destination addresses are ANDed with their masks and compared
                with those in the security entry. This object indicates the
                action to be taken if these two don't match."
           ::= { dcntAccessListEntry 5 }

    -- DECnet Security Table

     dcntIfSecurityTable  OBJECT-TYPE
           SYNTAX  SEQUENCE OF DcntIfSecurityEntry
           ACCESS  not-accessible
           STATUS  mandatory
           DESCRIPTION
              "A table of security parameters."
           ::= { decnet 31 }

        dcntIfSecurityEntry  OBJECT-TYPE
           SYNTAX  DcntIfSecurityEntry
           ACCESS  not-accessible
           STATUS  mandatory
           DESCRIPTION
              "An entry in the security table. For each entry in the Access 
              List Table, there is a list(table) of Security entries. 
              Therefore, as each port has 2 access List entries associated 
              with it, then the port has access to two separate lists 
              of security entries within this table. To set an entry in 
              this table, ALL the objects must be supplied in a single SET 
              PDU."
           INDEX  { dcntIfSecurityAccessListNum,
                    dcntIfSecurityIndex  }
           ::= { dcntIfSecurityTable 1 }

        DcntIfSecurityEntry  ::= SEQUENCE {
           dcntIfSecurityAccessListNum
               INTEGER,
           dcntIfSecurityIndex
               INTEGER,
           dcntIfSecurityAction
               INTEGER,
           dcntIfSecuritySrcArea
               INTEGER,
           dcntIfSecuritySrcNode
               INTEGER,
           dcntIfSecurityDestArea
               INTEGER,
           dcntIfSecurityDestNode
               INTEGER,
           dcntIfSecurityEntryType
               INTEGER
           }

        dcntIfSecurityAccessListNum  OBJECT-TYPE
            SYNTAX  INTEGER (1..31)
            ACCESS  read-write
            STATUS  mandatory
            DESCRIPTION
              "The access list entry number with which this security entry is
               associated."
            ::= { dcntIfSecurityEntry 1 }

        dcntIfSecurityIndex  OBJECT-TYPE
            SYNTAX  INTEGER
            ACCESS  read-write
            STATUS  mandatory
            DESCRIPTION
              "An index into the security table."
            ::= { dcntIfSecurityEntry 2 }

        dcntIfSecurityAction  OBJECT-TYPE
           SYNTAX  INTEGER {
                   pass (1),
                   block (2)
                   }
           ACCESS  read-write
           STATUS  mandatory
           DESCRIPTION
             "Indicates the action in case of a match occurring between the
              src/dest addr in the DECnet packet rxd/txd and the
              src/dest addr in the security entry."
           ::= { dcntIfSecurityEntry 3 }

        dcntIfSecuritySrcArea  OBJECT-TYPE
           SYNTAX  INTEGER
           ACCESS  read-write
           STATUS  mandatory
           DESCRIPTION
              "The area number of the source. A value of 0 means that the entry
              refers to all areas"
           ::= { dcntIfSecurityEntry 4 }

        dcntIfSecuritySrcNode  OBJECT-TYPE
           SYNTAX  INTEGER
           ACCESS  read-write
           STATUS  mandatory
           DESCRIPTION
              "The source node number. A value of 0 means that the entry
              refers to all nodes"
           ::= { dcntIfSecurityEntry 5 }

        dcntIfSecurityDestArea  OBJECT-TYPE
           SYNTAX  INTEGER
           ACCESS  read-write
           STATUS  mandatory
           DESCRIPTION
              "The area number of the destination. A value of 0 means
              that the entry refers to all areas"
           ::= { dcntIfSecurityEntry 6 }

        dcntIfSecurityDestNode  OBJECT-TYPE
           SYNTAX  INTEGER
           ACCESS  read-write
           STATUS  mandatory
           DESCRIPTION
              "The destination node number. A value of 0 means that the entry
               refers to all nodes"
           ::= { dcntIfSecurityEntry 7 }

        dcntIfSecurityEntryType  OBJECT-TYPE
            SYNTAX  INTEGER {
                    valid   (1),
                    invalid (2)
                    }
            ACCESS  read-write
            STATUS  mandatory
            DESCRIPTION
                "This parameter is used to indicate whether the entry is to
                 be added or removed from the dcntIfSecurityTable. If the value
                 is valid(1) then this indicates that this is a request to
                 add this entry to the table. A value of valid(1) is always
                 returned to a GetRequest in the case where the entry exists."
            ::= { dcntIfSecurityEntry 8 }

    -- The DECnet PPP private objects

    dcntPPPConfigTable  OBJECT-TYPE
        SYNTAX  SEQUENCE OF DcntPPPConfigEntry
        ACCESS  not-accessible
        STATUS  mandatory
        DESCRIPTION
            "This table contains objects which hold information about the
            operation of a DECnet logical port, over a PPP physical port."
        ::= { decnet 32 }

    dcntPPPConfigEntry  OBJECT-TYPE
        SYNTAX  DcntPPPConfigEntry
        ACCESS  not-accessible
        STATUS  mandatory
        DESCRIPTION
            "This is and entry in the DECnet PPP status table.
             A SNMP error or noSuchName is returned to a request for an
             object in this table if the DECnet port identified by the
             value of dcntIfIndex for this entry, is attached to a
             physical port which is not a PPP physical port."
        INDEX  { dcntPPPConfigIfIndex }
        ::= { dcntPPPConfigTable 1 }

    DcntPPPConfigEntry ::= SEQUENCE {
        dcntPPPConfigIfIndex
            INTEGER,
        dcntPPPAdminStatus
            INTEGER
        }

    dcntPPPConfigIfIndex  OBJECT-TYPE
        SYNTAX  INTEGER
        ACCESS  read-only
        STATUS  mandatory
        DESCRIPTION
            "The value of the index uniquley specifies the logical port
             for which this entry is applicable."
         ::= { dcntPPPConfigEntry 1 }

    dcntPPPAdminStatus  OBJECT-TYPE
        SYNTAX  INTEGER {
                open  (1),
                close (2)
                }
        ACCESS  read-write
        STATUS  mandatory
        DESCRIPTION
            "This is the immediate desired state of the DECnet network
             protocol. Setting this object to open(1) will inject an
             administrative open event into the DECnet network protocol's
             finite state machine. Setting this object to close(2) will
             inject an administrative close event into the DECnet network
             protocol's finite state machine."
        ::= { dcntPPPConfigEntry 2 }


    dcntPPPStatusTable  OBJECT-TYPE
        SYNTAX  SEQUENCE OF DcntPPPStatusEntry
        ACCESS  not-accessible
        STATUS  mandatory
        DESCRIPTION
            "This table contains object which hold status information about
             PPP on a DECnet port."
        ::= { decnet 33 }

    dcntPPPStatusEntry  OBJECT-TYPE
        SYNTAX  DcntPPPStatusEntry
        ACCESS  not-accessible
        STATUS  mandatory
        DESCRIPTION
            "This is and entry in the DECnet PPP status table.
             A SNMP error or noSuchName is returned to a request for an
             object in this table if the IPX port identified by the
             value of ipxIfIndex for this entry, is attached to a
             physical port which is not a PPP physical port."
        INDEX  { dcntPPPStatusIfIndex }
        ::= { dcntPPPStatusTable 1 }

    DcntPPPStatusEntry ::= SEQUENCE {
        dcntPPPStatusIfIndex
            INTEGER,
        dcntPPPOperStatus
            INTEGER
        }

    dcntPPPStatusIfIndex  OBJECT-TYPE
        SYNTAX  INTEGER
        ACCESS  read-only
        STATUS  mandatory
        DESCRIPTION
            "The value of the index uniquley specifies the logical port
             for which this entry is applicable."
        ::= { dcntPPPStatusEntry 1 }

    dcntPPPOperStatus  OBJECT-TYPE
        SYNTAX  INTEGER {
                opened (1),
                not-opened (2)
                }
        ACCESS  read-only
        STATUS  mandatory
        DESCRIPTION
            "This is the current operational status of the DECnet network
             protocol. If the value of this object is opened(1) then the
             finite state machine for the DECnet protocol has reached the
             Opened state."
        ::= { dcntPPPStatusEntry 2 }

    -- 
    -- The X.25 Group
    --
    -- X.25 Operational Table
    --

    x25OperTable  OBJECT-TYPE
        SYNTAX  SEQUENCE OF X25OperEntry
        ACCESS  not-accessible
        STATUS  mandatory
        DESCRIPTION
            "The common operation parameters in use by the X.25
             Packet Level Entity (PLE) on a physical interface.."
        ::= { x25 1 }

    x25OperEntry  OBJECT-TYPE
        SYNTAX  X25OperEntry
        ACCESS  not-accessible
        STATUS  mandatory
        DESCRIPTION
            "Entries of x25OperTable."
        INDEX { x25OperPort }
        ::= { x25OperTable 1 }

    X25OperEntry ::= SEQUENCE {
        x25OperPort
            INTEGER,
        x25OperComments
            DisplayString,
        x25OperEnable
            INTEGER,
        x25OperProtocolVersionSupported
            INTEGER,
        x25OperPacketSequencing
            INTEGER,
        x25OperDefPktSize
            INTEGER,
        x25OperDefReqPktSize
            INTEGER,
        x25OperDefWinSize
            INTEGER,
        x25OperDefReqWinSize
            INTEGER,
        x25OperFlowCntrlNegEnab
            INTEGER,
        x25OperCUGSub
            INTEGER,
        x25OperRvrsChrgReq
            INTEGER,
        x25OperRvrsChrgAcc
            INTEGER,
        x25OperLow2WayChan
            INTEGER,
        x25OperNumSVCs
            INTEGER,
        x25OperLocalAddress
            X121Address,
        x25OperImmDataAck
            INTEGER,
        x25OperAccUnknownAdd
            INTEGER,
        x25OperLnkReset
            INTEGER,
        x25OperT20RestartTimer
            INTEGER,
        x25OperT21CallTimer
            INTEGER,
        x25OperT22ResetTimer
            INTEGER,
        x25OperT23ClearTimer
            INTEGER,
        x25OperR20RestartCount
            INTEGER,
        x25OperR22ResetCount
            INTEGER,
        x25OperR23ClearCount
            INTEGER,
        x25OperInterfaceMode
            INTEGER,
        x25OperSubAddress
            INTEGER,
        x25OperAddrInCallAcc
            INTEGER
        }

    x25OperPort  OBJECT-TYPE
        SYNTAX  INTEGER (1..16)
        ACCESS  read-only
        STATUS  mandatory
        DESCRIPTION
            "A value that uniquely identifies the
            X.25 PLE subnetwork (physical interface
            on the fp) and matches its physical port value."
        ::= { x25OperEntry 1 }

    x25OperComments  OBJECT-TYPE
        SYNTAX  DisplayString (SIZE (0..21))
        ACCESS  read-write
        STATUS  mandatory
        DESCRIPTION
            "An ASCII comment string which describes
            the interface. This defaults to a NULL string"
        ::= { x25OperEntry 2 }

    x25OperEnable  OBJECT-TYPE
        SYNTAX  INTEGER {
                enable (1),
                disable (2)
                }
        ACCESS  read-write
        STATUS  mandatory
        DESCRIPTION
            "This object is an operation switch, it enables
             or disables the operation of x25 on the interface.
             Setting this parameter to enable from a disable
             condition will result in the transmission of a RESTART
             packet."
        DEFVAL { disable }
        ::= { x25OperEntry 3 }

    x25OperProtocolVersionSupported  OBJECT-TYPE
        SYNTAX  INTEGER {
                v1980 (1),
                v1984 (5)
                }
        ACCESS  read-write
        STATUS  mandatory
        DESCRIPTION
            "This object is an operation switch, allowing the
            user to change the operating mode of x25 on this
            interface. A value of 1 sets the operating mode
            to 1980 operating mode, whereas a value of 5 sets
            it to 1984."
        DEFVAL { v1984 }
        ::= { x25OperEntry 4 }

    x25OperPacketSequencing  OBJECT-TYPE
        SYNTAX  INTEGER {
                mod8 (16),
                mod128 (32)
                }
        ACCESS  read-write
        STATUS  mandatory
        DESCRIPTION
            "The modulus of the packet sequence number
            space. This object determines the maximum
            value for x25OperDefWinSize and x25OperDefReqWinSIze.
            A mod8 setting limits the maximum value to 7, A mod128
            setting limits the maximum value to 127. Default value
            mod8. If this object is set to mod8, all packet window
            size objects: x25OperDefWinSize, x25OperDefReqWinSize,
            and x25RAFTNegWindowSize must be less than 8"
        REFERENCE
            "10733 extendedPacketSequencing; See ISO 8208
            Section 7.1.1"
        DEFVAL { mod8 }
        ::= { x25OperEntry 5 }

    x25OperDefPktSize  OBJECT-TYPE
        SYNTAX  INTEGER {
                size128 (128),
                size256 (256),
                size512 (512),
                size1024 (1024)
                }
        ACCESS  read-write
        STATUS  mandatory
        DESCRIPTION
            "The default send/receive packet size in
             octets for a circuit. Default value is 128."
        DEFVAL { size128 }
        ::= { x25OperEntry 6 }

    x25OperDefReqPktSize  OBJECT-TYPE
        SYNTAX  INTEGER {
                size0   (1),
                size128 (128),
                size256 (256),
                size512 (512),
                size1024 (1024)
                }
        ACCESS  read-write
        STATUS  mandatory
        DESCRIPTION
             "The default request packet size in octets
             for a circuit. Used if flow control is enabled.
             Ignored if flow control is not enabled. The setting
             of x25RAFTNegPacketSize will over-ride the setting
             of this object. Setting this object to a size0(1) 
             value allows flow control negotiation to be configured 
             but  disables the packet size portion of flow control
             negotiation. Default value is 128."
        DEFVAL { size128 }
        ::= { x25OperEntry 7 }

    x25OperDefWinSize  OBJECT-TYPE
        SYNTAX  INTEGER (1..127)
        ACCESS  read-write
        STATUS  mandatory
        DESCRIPTION
            "The default window size for a circuit.
            The value of this object is limited by the
            setting of x25OperPacketSequencing This value
            must be less than 8 if sequencing is mod8.
            Default value is 2."
        DEFVAL { 2 }
        ::= { x25OperEntry 8 }

     x25OperDefReqWinSize  OBJECT-TYPE
        SYNTAX  INTEGER (1..127)
        ACCESS  read-write
        STATUS  mandatory
        DESCRIPTION
            "The default request window size for a circuit. Used
            if flow control is enabled. The value of this object
            is limited by the setting of x25OperPacketSequencing.
            This value must be less than 8 if sequencing is mod8.
            The setting of the x25RAFTNegWindowSize object will
            over-ride the setting of this object. Default value
            is 2."
        DEFVAL { 2 }
        ::= { x25OperEntry 9 }

     x25OperFlowCntrlNegEnab  OBJECT-TYPE
        SYNTAX  INTEGER {
                enable (1),
                disable (2)
                }
        ACCESS  read-write
        STATUS  mandatory
        DESCRIPTION
            "Enable/disable flow control negotiation.
            The setting of this parameter determines
            if x25OperDefReqWinSize or x25OperDefReqPktSize
            will be used in establishing the call. This parameter
            will be over-ridden by the setting of the
            x25RAFTNegWindowSize or the x25RAFTNegPacketSize
            object."
        DEFVAL { disable }
        ::= { x25OperEntry 10 }

     x25OperCUGSub  OBJECT-TYPE
        SYNTAX  INTEGER {
                enable(1),
                disable(2)
                }
        ACCESS  read-write
        STATUS  mandatory
        DESCRIPTION
            "Enable/disable the basic form of closed
            user group. This parameter determines if CUG
            facility can be used on this interface. The
            x25RAFTCUGValue will override this parameter.
            If this object is set to enabled then CUG
            values in received call request packets will
            be validated against entries in the x25CUGTable.
            Call requests containing CUG facility will be
            refused"
        DEFVAL { disable }
        ::= { x25OperEntry 11 }

     x25OperRvrsChrgReq  OBJECT-TYPE
        SYNTAX  INTEGER {
                enable(1),
                disable(2)
                }
        ACCESS  read-write
        STATUS  mandatory
        DESCRIPTION
            "Enable/disable reverse charge request.
            If this parameter if set to enabled, the
            reverse charge request facility will be
            placed in all call request packets. The
            x25RAFTProposeReverseCharging object will
            override the setting of this object."
        DEFVAL { disable }
        ::= { x25OperEntry 12 }

     x25OperRvrsChrgAcc  OBJECT-TYPE
        SYNTAX  INTEGER {
                enable(1),
                disable(2)
                }
        ACCESS  read-write
        STATUS  mandatory
        DESCRIPTION
            "Enable/disable reverse charge accept.
            If this object is set to disabled then all
            received calls containing reverse charging
            will be refused. The x25RAFTAcceptReverseCharging
            object will over-ride the setting of this object"
        DEFVAL { disable }
        ::= { x25OperEntry 13 }


     x25OperLow2WayChan  OBJECT-TYPE
        SYNTAX  INTEGER (1..4032)
        ACCESS  read-write
        STATUS  mandatory
        DESCRIPTION
            "The starting value of two way logical channels.
            The number of usable logical channels on the interface
            will be (x25OperLow2WayChan + x25OperNumSVCs -1 )."
        DEFVAL { 32 }
        ::= { x25OperEntry 14 }

    x25OperNumSVCs  OBJECT-TYPE
        SYNTAX  INTEGER (1..64)
        ACCESS  read-write
        STATUS  mandatory
        DESCRIPTION
            "This is the number of SVCs on a physical port."
        ::= { x25OperEntry 15 }

    x25OperLocalAddress  OBJECT-TYPE
        SYNTAX  X121Address
        ACCESS  read-write
        STATUS  mandatory
        DESCRIPTION
            "The local address for this PLE subnetwork.
            This object will provide the source DTE address
            provided in call request packets. If this object
            is set to a NULL string or to 00000000000000000
            then the source DTE address in the call request
            packets will be absent."
        REFERENCE
            "10733 5.9 localDTEAddress"
        ::= { x25OperEntry 16 }

    x25OperImmDataAck  OBJECT-TYPE
        SYNTAX  INTEGER {
                enable(1),
                disable(2)
                }
        ACCESS  read-write
        STATUS  mandatory
        DESCRIPTION
            "Enable/disable immediate data ack. This parameter
            is used when connected to a network which requires
            immediate acknowledgement of a data packet regardless of
            whether the window is full. Example Accunet. Setting this
            parameter to enabled will result in a RR packet sent for
            every data packet received."
        DEFVAL { disable }
        ::= { x25OperEntry 17 }

    x25OperAccUnknownAdd  OBJECT-TYPE
        SYNTAX  INTEGER {
                enable(1),
                disable(2)
                }
        ACCESS  read-write
        STATUS  mandatory
        DESCRIPTION
            "Enable/disable unknown address acceptance.
            This parameter will allow call packets
            to be received for which a RAFT entry does
            not exist. If a RAFT entry does not exist
            for an incoming call request source address,
            then the default parameters on the physical
            port will determine acceptability of the call."
        DEFVAL { enable }
        ::= { x25OperEntry 18 }

    x25OperLnkReset  OBJECT-TYPE
        SYNTAX  INTEGER {
                execute(1),
                noAction(2)
                }
        ACCESS  read-write
        STATUS  mandatory
        DESCRIPTION
            "Operational parameter to reset link level,
            This parameter will cause the link level to
            be reset. The packet will restart if the X25
            protocol is enabled for that port (see
            x25OperEnable)"
        DEFVAL { noAction }
        ::= { x25OperEntry 19 }

    x25OperT20RestartTimer  OBJECT-TYPE
        SYNTAX  INTEGER (1..1024)
        ACCESS  read-write
        STATUS  mandatory
        DESCRIPTION
            "The T20 restart timer in seconds.
            This determines the amount of time
            allowed for a restart confirm to be
            received for a restart request.
            See restart count."
        REFERENCE
            "10733 5.9 restartTime;
            See ISO 8208    Section 4.1, table 26"
        DEFVAL { 180 }
        ::= { x25OperEntry 20 }

          x25OperT21CallTimer  OBJECT-TYPE
        SYNTAX  INTEGER (1..1024)
        ACCESS  read-write
        STATUS  mandatory
        DESCRIPTION
                "The T21 call timer in seconds. Maximum
              time allowed to receive acceptance response
              to call attempt. There is no call count."
        DEFVAL { 200 }
        ::= { x25OperEntry 21 }

    x25OperT22ResetTimer  OBJECT-TYPE
        SYNTAX  INTEGER (1..1024)
        ACCESS  read-write
        STATUS  mandatory
        DESCRIPTION
            "The T22 Reset timer in seconds. The maximum time allowed to
            receive reset confirm to a reset request. See reset count."
        REFERENCE
            "10733 resetTime;
            See ISO 8208    Section 8.1, table 26"
        DEFVAL { 180 }
        ::= { x25OperEntry 22 }

    x25OperT23ClearTimer  OBJECT-TYPE
        SYNTAX  INTEGER (1..1024)
        ACCESS  read-write
        STATUS  mandatory
        DESCRIPTION
            "The T23 Clear timer in seconds.
            The maximum time allowed to receive
            a clear confirm in response to a
            clear request. See clear count."
        REFERENCE
            "10733 clearTime;
            See ISO 8208 Section 5.5.1, table 26"
        DEFVAL { 180 }
        ::= { x25OperEntry 23 }

    x25OperR20RestartCount  OBJECT-TYPE
        SYNTAX  INTEGER (1..255)
        ACCESS  read-write
        STATUS  mandatory
        DESCRIPTION
            "The R20 restart retransmission count.
            The maximum number of times which a restart
            request packet will be retransmitted on
            expiration of the restart timer."
        REFERENCE
            "10733 5.9 restartCount
            See ISO 8208    Section 4.1, table 27"
        DEFVAL { 2 }
        ::= { x25OperEntry 24 }

    x25OperR22ResetCount  OBJECT-TYPE
        SYNTAX  INTEGER (1..255)
        ACCESS  read-write
        STATUS  mandatory
        DESCRIPTION
            "The r22 Reset retransmission count.
            The maximum number of times which a reset
            request packet will be retransmitted on
            expiration of the reset timer."
        REFERENCE
            "10733 resetCount;
            See section ISO 8208 8.1, table 27"
        DEFVAL { 1 }
        ::= { x25OperEntry 25 }

    x25OperR23ClearCount  OBJECT-TYPE
        SYNTAX  INTEGER (1..255)
        ACCESS  read-write
        STATUS  mandatory
        DESCRIPTION
            "The r23 Clear retransmission count.
            The maximum number of times which a clear
            request packet will be retransmitted on
            expiration of the clear timer."
        REFERENCE
            "10733 clearCount;
            See ISO 8208 Section 5.5.1, table 27"
        DEFVAL { 1 }
        ::= { x25OperEntry 26 }

    x25OperInterfaceMode  OBJECT-TYPE
        SYNTAX  INTEGER {
                dce (1),
                dte (3),
                lapb (4),
                certifyDte (5)
                }
        ACCESS  read-write
        STATUS  mandatory
        DESCRIPTION
            "Identifies DCE/DTE mode in which the
            interface operates.  A value of lapb
            indicates the mode will be determined by
            the address at the Link Layer, otherwise the
            interface will operate as specified DTE or
            DCE."
        REFERENCE
           "10733 5.9 interfaceMode"
        DEFVAL { lapb }
        ::= { x25OperEntry 27 }

    x25OperSubAddress  OBJECT-TYPE
        SYNTAX  INTEGER {
                enable (1),
                disable (2)
                }
        ACCESS  read-write
        STATUS  mandatory
        DESCRIPTION
            "This object is an operation switch, it enables
             or disables the use of sub-addressing in x25 DTE
         addresses. If enabled the last 2 digits of the x25
         address is the sub-address identifying the channel
         number."
        DEFVAL { disable }
        ::= { x25OperEntry 28 }

    x25OperAddrInCallAcc  OBJECT-TYPE
        SYNTAX  INTEGER {
                enable (1),
                disable (2)
                }
        ACCESS  read-write
        STATUS  mandatory
        DESCRIPTION
            "This object is an operation switch, it enables
             or disables the placement of the calling/called 
         x25 addresses in the call accept packet. If this
         parameter is set to disabled and the call request 
         contains calling/called addresses the addresses will not
         be placed into the call accept packet."
        DEFVAL { enable }
        ::= { x25OperEntry 29 }

    -- 
    --            X.25 Closed User Group Table
    --

          x25CUGTable  OBJECT-TYPE
                  SYNTAX  SEQUENCE OF X25CUGEntry
                  ACCESS  not-accessible
                  STATUS  mandatory
                  DESCRIPTION
                      "The table of CUG values which can be
                       received in call request packets,
                       by this X.25 Packet Level Entity (PLE)."
                  ::= { x25 2 }

          x25CUGEntry  OBJECT-TYPE
                  SYNTAX  X25CUGEntry
                  ACCESS  not-accessible
                  STATUS  mandatory
                  DESCRIPTION
                      "Entries of x25CUGTable."
                  INDEX { x25CUGPort, x25CUGTableIndex }
                  ::= { x25CUGTable 1 }

          X25CUGEntry ::= SEQUENCE {
                  x25CUGPort
                      INTEGER,
                  x25CUGTableIndex
                      INTEGER,
                  x25CUGValue
                      INTEGER,
                  x25CUGStatus
                      INTEGER
                  }

          x25CUGPort  OBJECT-TYPE
                  SYNTAX  INTEGER (1..16)
                  ACCESS  read-only
                  STATUS  mandatory
                  DESCRIPTION
                      "A value that uniquely identifies the
                      X.25 PLE subnetwork (physical interface
                      on the fp) and matches its physical port value."
                  ::= { x25CUGEntry 1 }

          x25CUGTableIndex  OBJECT-TYPE
                  SYNTAX  INTEGER (1..10)
                  ACCESS  read-only
                  STATUS  mandatory
                  DESCRIPTION
                      "A value that uniquely identifies the entry
                      in the CUG table for the PLE."
                  ::= { x25CUGEntry 2 }

          x25CUGValue  OBJECT-TYPE
                  SYNTAX  INTEGER (0..99)
                  ACCESS  read-write
                  STATUS  mandatory
                  DESCRIPTION
                          "A closed User Group value for the PLE."
                  ::= { x25CUGEntry 3 }

          x25CUGStatus  OBJECT-TYPE
                  SYNTAX  INTEGER {
                          enable (1),
                          disable (2)
                          }
                  ACCESS  read-write
                  STATUS  mandatory
                  DESCRIPTION
                      "Enable or disable this CUG value.
                      Disabling the value is the equivalent
                      of deleting it."
                  DEFVAL { disable }
                  ::= { x25CUGEntry 4 }

          --
          --            X.25 Interface Statistics Table
          --

          x25StatTable  OBJECT-TYPE
                  SYNTAX  SEQUENCE OF X25StatEntry
                  ACCESS  not-accessible
                  STATUS  mandatory
                  DESCRIPTION
                      "Statistics information about this X.25
                      PLE. These statistics describe the general
                      operation of X.25 on the physical interface."
                  ::= { x25 3 }

          x25StatEntry  OBJECT-TYPE
                  SYNTAX  X25StatEntry
                  ACCESS  not-accessible
                  STATUS  mandatory
                  DESCRIPTION
                      "Entries of the x25StatTable."
                  INDEX { x25StatPort }
                  ::= { x25StatTable 1 }

          X25StatEntry ::= SEQUENCE {
                  x25StatPort
                          INTEGER,
                  x25StatComments
                          DisplayString,
                  x25StatPktStatus
                          INTEGER,
                  x25StatTotalCircuits
                          INTEGER,
                  x25StatActiveCircuits
                          Gauge,
                  x25StatInClearCauseDiag
                          DisplayString,
                  x25StatInClearAddr
                          X121Address,
                  x25StatOutClearCauseDiag
                          DisplayString,
                  x25StatOutClearAddr
                          X121Address,
                  x25StatInDataPackets
                          Counter,
                  x25StatOutDataPackets
                          Counter,
                  x25StatInCalls
                          Counter,
                  x25StatOutCallAttempts
                          Counter,
                  x25StatInClears
                          Counter,
                  x25StatOutClears
                          Counter,
                  x25StatInResets
                          Counter,
                  x25StatOutResets
                          Counter,
                  x25StatInRestarts
                          Counter,
                  x25StatOutRestarts
                          Counter,
                  x25StatDiscards
                          Counter
                  }

          x25StatPort  OBJECT-TYPE
                  SYNTAX  INTEGER
                  ACCESS  read-only
                  STATUS  mandatory
                  DESCRIPTION
                      "A value that uniquely identifies the
                      X.25 PLE subnetwork (physical interface
                      on the fp) and matches its physical port value."
                  ::= { x25StatEntry 1 }

          x25StatComments  OBJECT-TYPE
                  SYNTAX  DisplayString (SIZE (0..21))
                  ACCESS  read-only
                  STATUS  mandatory
                  DESCRIPTION
                      "An ASCII comment string which describes
                      the interface."
                  ::= { x25StatEntry 2 }

          x25StatPktStatus  OBJECT-TYPE
                  SYNTAX  INTEGER {
                          inactive (1),       -- (r0)
                          ready (2),          -- (r1)
                          restart (3),        -- (r2,r3)
                          disabled (4)        -- (r4)
                          }
                  ACCESS  read-only
                  STATUS  mandatory
                  DESCRIPTION
                      "This object reports the current status of
                      the packet level, and indicates if the packet
                      level is ready for use. The r4 state places the
                      interface in the disabled state, ignoring all
                      packets."
                  ::= { x25StatEntry 3 }

          x25StatTotalCircuits  OBJECT-TYPE
                  SYNTAX  INTEGER
                  ACCESS  read-only
                  STATUS  mandatory
                  DESCRIPTION
                      "This object quantifies the total number of
                      virtual circuits (logical channels) available
                      for connection"
                  ::= { x25StatEntry 4 }

          x25StatActiveCircuits  OBJECT-TYPE
                  SYNTAX  Gauge
                  ACCESS  read-only
                  STATUS  mandatory
                  DESCRIPTION
                      "This object quantifies the total number of
                      virtual circuits currently connected (states p4, d2, d3)"
                  ::= { x25StatEntry 5 }

          x25StatInClearCauseDiag  OBJECT-TYPE
                  SYNTAX  DisplayString (SIZE (7))
                  ACCESS  read-only
                  STATUS  mandatory
                  DESCRIPTION
                      "This object defines the cause/diag code
                      in the last received clear packet. The form of this is
                      'nnn nnn' where the first 3 digits give the cause code
                       and the second 3 the diagnostic code."
                  ::= { x25StatEntry 6 }

          x25StatInClearAddr  OBJECT-TYPE
                  SYNTAX  X121Address
                  ACCESS  read-only
                  STATUS  mandatory
                  DESCRIPTION
                      "The X25 address which originated the
                      last received clear"
                  ::= { x25StatEntry 7 }

          x25StatOutClearCauseDiag  OBJECT-TYPE
                  SYNTAX  DisplayString (SIZE (7))
                  ACCESS  read-only
                  STATUS  mandatory
                  DESCRIPTION
                      "This object defines the cause/diag code
                      in the last received clear packet. The form of this is
                      'nnn nnn' where the first 3 digits give the cause code
                      and the second 3 the diagnostic code."
                  ::= { x25StatEntry 8 }

          x25StatOutClearAddr  OBJECT-TYPE
                  SYNTAX  X121Address
                  ACCESS  read-only
                  STATUS  mandatory
                  DESCRIPTION
                      "The X25 address to which the last
                      locally originated clear packet was sent"
                  ::= { x25StatEntry 9 }

          x25StatInDataPackets  OBJECT-TYPE
                  SYNTAX  Counter
                  ACCESS  read-only
                  STATUS  mandatory
                  DESCRIPTION
                      "The number of data pkts received on the interface (PLE)."
                  REFERENCE
                      "10733 5.9 dataPacketsReceived."
                  ::= { x25StatEntry 10 }

          x25StatOutDataPackets  OBJECT-TYPE
                  SYNTAX  Counter
                  ACCESS  read-only
                  STATUS  mandatory
                  DESCRIPTION
                      "The number of data packets sent on the interface (PLE)."
                  REFERENCE
                      "10733 dataPacketSent"
                  ::= { x25StatEntry 11 }

          x25StatInCalls  OBJECT-TYPE
                  SYNTAX  Counter
                  ACCESS  read-only
                  STATUS  mandatory
                  DESCRIPTION
                      "The number of incoming call packets received
                      on the interface (PLE)."
                  ::= { x25StatEntry 12 }

          x25StatOutCallAttempts  OBJECT-TYPE
                  SYNTAX  Counter
                  ACCESS  read-only
                  STATUS  mandatory
                  DESCRIPTION
                      "The number of call packets sent on the interface (PLE)."
                  REFERENCE
                      "10733 5.9 callAttempts"
                  ::= { x25StatEntry 13 }

          x25StatInClears  OBJECT-TYPE
                  SYNTAX  Counter
                  ACCESS  read-only
                  STATUS  mandatory
                  DESCRIPTION
                      "The number of clear packets received on the 
                      interface (PLE)."
                  REFERENCE
                      "10733 providerInitiatedDisconnect"
                  ::= { x25StatEntry 14 }

          x25StatOutClears  OBJECT-TYPE
                  SYNTAX  Counter
                  ACCESS  read-only
                  STATUS  mandatory
                  DESCRIPTION
                      "The number of clear packets transmitted on the
                      interface (PLE)"
                  ::= { x25StatEntry 15 }

          x25StatInResets  OBJECT-TYPE
                  SYNTAX  Counter
                  ACCESS  read-only
                  STATUS  mandatory
                  DESCRIPTION
                      "The number of reset packets received on the
                      interface (PLE)"
                  ::= { x25StatEntry 16 }

          x25StatOutResets  OBJECT-TYPE
                  SYNTAX  Counter
                  ACCESS  read-only
                  STATUS  mandatory
                  DESCRIPTION
                      "The number of reset packets transmitted on the
                      interface (PLE)"
                  ::= { x25StatEntry 17 }

          x25StatInRestarts  OBJECT-TYPE
                  SYNTAX  Counter
                  ACCESS  read-only
                  STATUS  mandatory
                  DESCRIPTION
                      "The number of restart packets received on the
                      interface (PLE)"
                  ::= { x25StatEntry 18 }

          x25StatOutRestarts  OBJECT-TYPE
                  SYNTAX  Counter
                  ACCESS  read-only
                  STATUS  mandatory
                  DESCRIPTION
                      "The number of restart packets sent on the
                      interface (PLE)"
                  ::= { x25StatEntry 19 }

          x25StatDiscards  OBJECT-TYPE
                  SYNTAX  Counter
                  ACCESS  read-only
                  STATUS  mandatory
                  DESCRIPTION
                      "The total number of transmit frames, before segmentation, 
              discarded due to lack of buffers"
                  ::= { x25StatEntry 20 }


          --
          --          X25 SVC Statistics
          --

          x25CircuitTable  OBJECT-TYPE
                  SYNTAX  SEQUENCE OF X25CircuitEntry
                  ACCESS  not-accessible
                  STATUS  mandatory
                  DESCRIPTION
                      "This table contains statistics information
                      about a specific logical channel channel on
                      a physical interface (X.25 PLE)."
                  ::= { x25 4 }

          x25CircuitEntry  OBJECT-TYPE
                  SYNTAX  X25CircuitEntry
                  ACCESS  not-accessible
                  STATUS  mandatory
                  DESCRIPTION
                      "Entries of x25CircuitTable."
                  INDEX { x25CircuitPort,
                          x25CircuitNumber }
                  ::= { x25CircuitTable 1 }

          X25CircuitEntry ::= SEQUENCE {
                  x25CircuitPort
                          INTEGER,
                  x25CircuitNumber
                          INTEGER,
                  x25CircuitStatus
                          INTEGER,
                  x25CircuitRemoteDteAddress
                          X121Address,
                  x25CircuitType
                          INTEGER,
                  x25CircuitComments
                          DisplayString,
                  x25CircuitEstablishTime
                          INTEGER,
                  x25CircuitClearCauseDiag
                          DisplayString,
                  x25CircuitWinSize
                          INTEGER,
                  x25CircuitPktSize
                          INTEGER,
                  x25CircuitInOctets
                          Counter,
                  x25CircuitInPdus
                          Counter,
                  x25CircuitOutOctets
                          Counter,
                  x25CircuitOutPdus
                          Counter,
                  x25CircuitInResets
                          Counter,
                  x25CircuitOutResets
                          Counter
                  }

          x25CircuitPort  OBJECT-TYPE
                  SYNTAX  INTEGER
                  ACCESS  read-only
                  STATUS  mandatory
                  DESCRIPTION
                      "A value that uniquely identifies the
                      X.25 PLE subnetwork (physical interface
                      on the fp) and matches its physical port value."
                  ::= { x25CircuitEntry 1 }

          x25CircuitNumber  OBJECT-TYPE
                  SYNTAX  INTEGER
                  ACCESS  read-only
                  STATUS  mandatory
                  DESCRIPTION
                      "The logical channel number for this switched 
                      virtual circuit (SVC)."
                  ::= { x25CircuitEntry 2 }

          x25CircuitStatus  OBJECT-TYPE
                  SYNTAX  INTEGER {
                          inactive (1),       -- (p0)
                          ready (2),          -- (p1)
                          calling (3),        -- (p2,p3,p5)
                          dataTransfer (4),   -- (p4, d2, d3)
                          clearing (5)        -- (p6,p7)
                          }
                  ACCESS  read-only
                  STATUS  mandatory
                  DESCRIPTION
                      "This object reports the current
                      packet level state of the switched
                      virtual circuit. See annex B of CCITT
                      X.25 specification for more information."
                  REFERENCE
                      "See ISO 8208, table 33 for (p<n>) state table"
                  ::= { x25CircuitEntry 3 }

          x25CircuitRemoteDteAddress  OBJECT-TYPE
                  SYNTAX  X121Address
                  ACCESS  read-only
                  STATUS  mandatory
                  DESCRIPTION
                      "The remote X.25 DTE address associated with
                      this switched virtual circuit"
                  ::= { x25CircuitEntry 4 }

          x25CircuitType  OBJECT-TYPE
                  SYNTAX  INTEGER {
                          rx7000 (1),
                          b4800 (2),
                          isis (3),
                          rfc877 (4),
                          test (5)
                          }
                  ACCESS  read-only
                  STATUS  mandatory
                  DESCRIPTION
                      "The type of user of this circuit. This parameter 
                      identifies the encapsulation and/or the type of 
                      router at the remote destination. rx7000 indicates
                      a RX7000 type router is at the remote end of
                      the SVC, b4800 indicates that there is a 4800/4900
                      router at the remote end of the SVC, isis indicates
                      that the SVC is solely used by the ISIS protocol to
                      communicate to another ISIS router, rfc877 indicates that
                      the SVC is solely used by the IP protocol to communicate
                      to another IP router, test indicates that this is a test
                      SVC."
                  ::= { x25CircuitEntry 5 }

          x25CircuitComments  OBJECT-TYPE
                  SYNTAX  DisplayString (SIZE (0..21))
                  ACCESS  read-only
                  STATUS  mandatory
                  DESCRIPTION
                      "An ASCII comment string which describes
                      this entry. This parameter is a NULL
                      string if the x25CircuitType object is
                      ISIS or IP. This parameter will contain the
                      string defined in x25ChanComments if the x25CircuitType
                      object is RX7000 or 4800."
                  ::= { x25CircuitEntry 6 }

          x25CircuitEstablishTime  OBJECT-TYPE
                  SYNTAX  INTEGER
                  ACCESS  read-only
                  STATUS  mandatory
                  DESCRIPTION
                      "The amount of time in seconds that
                      the switched virtual circuit has been established."
                  ::= { x25CircuitEntry 7 }

          x25CircuitClearCauseDiag  OBJECT-TYPE
                  SYNTAX  DisplayString (SIZE (7))
                  ACCESS  read-only
                  STATUS  mandatory
                  DESCRIPTION
                      "This object defines the cause/diag code
                      in the last received clear packet. The form of this is
                      'nnn nnn' where the first 3 digits give the cause code
                      and the second 3 the diagnostic code.
                      This object indicates the clear cause/diag
                      code in the last clear packet sent or received.
                      The first byte is cause code, the second byte
                      is diagnostic code."
                  ::= { x25CircuitEntry 8 }

          x25CircuitWinSize  OBJECT-TYPE
                  SYNTAX  INTEGER
                  ACCESS  read-only
                  STATUS  mandatory
                  DESCRIPTION
                      "The packet level window size currently
                      in use on the switched virtual circuit."
                  ::= { x25CircuitEntry 9 }

          x25CircuitPktSize  OBJECT-TYPE
                  SYNTAX  INTEGER
                  ACCESS  read-only
                  STATUS  mandatory
                  DESCRIPTION
                      "The x25 packet size currently in use on the
                      switched virtual circuit."
                  ::= { x25CircuitEntry 10 }

    -- X25 Circuit data flow statistics

          x25CircuitInOctets  OBJECT-TYPE
                  SYNTAX  Counter
                  ACCESS  read-only
                  STATUS  mandatory
                  DESCRIPTION
                      "The number of data octets received
                      on this x25 switched virtual circuit ."
                  REFERENCE
                      "5.11 octetsReceivedCounter"
                  ::= { x25CircuitEntry 11 }

          x25CircuitInPdus  OBJECT-TYPE
                  SYNTAX  Counter
                  ACCESS  read-only
                  STATUS  mandatory
                  DESCRIPTION
                      "The number of data PDUs received on this
                      switched virtual circuit."
                  REFERENCE
                      "10733 5.11 dataPacketsReceived"
                  ::= { x25CircuitEntry 12 }

          x25CircuitOutOctets  OBJECT-TYPE
                  SYNTAX  Counter
                  ACCESS  read-only
                  STATUS  mandatory
                  DESCRIPTION
                      "The number of data octets sent on this switched 
                      virtual circuit."
                  REFERENCE
                      "10733 5.11 octetsSentCounter"
                  ::= { x25CircuitEntry 13 }

          x25CircuitOutPdus  OBJECT-TYPE
                  SYNTAX  Counter
                  ACCESS  read-only
                  STATUS  mandatory
                  DESCRIPTION
                      "The number of data PDUs sent on this switched
                      virtual circuit."
                  REFERENCE
                     "10733 5.11 dataPacketsSent"
                  ::= { x25CircuitEntry 14 }

          x25CircuitInResets  OBJECT-TYPE
                  SYNTAX  Counter
                  ACCESS  read-only
                  STATUS  mandatory
                  DESCRIPTION
                      "The number of Reset packets received on this 
                      switched virtual circuit"
                  REFERENCE
                      "10733 remotelyInitiatedResets"
                  ::= { x25CircuitEntry 15 }

          x25CircuitOutResets  OBJECT-TYPE
                  SYNTAX  Counter
                  ACCESS  read-only
                  STATUS  mandatory
                  DESCRIPTION
                      "The number of Reset packets sent on this
                      switched virtual circuit"
                  ::= { x25CircuitEntry 16 }

          --
          --                The Remote Address Facilities Table
          --

          x25RAFTable  OBJECT-TYPE
                  SYNTAX  SEQUENCE OF X25RAFTEntry
                  ACCESS  not-accessible
                  STATUS  mandatory
                  DESCRIPTION
                      "These objects contain the parameters that
                      can be varied between X.25 calls.  There
                      is one table for each interface (PLE).
                      The use of entries in this table is based
                      on the x25RAFTAddr object. When a switched
                      virtual circuit is being established this table
                      is searched for a match between the x25RAFTAddr
                      object and the x25 address of the remote DTE.
                      If a match is found then the x25 parameters configured
                      in the x25RAFTable for the x25RAFTAddr will be used
                      to establish the x25 virtual circuit.
                      Entries in this table will over-ride the
                      default values in the Operational table
                      (x25OperTable)."
                  ::= { x25 5 }

          x25RAFTEntry  OBJECT-TYPE
                  SYNTAX  X25RAFTEntry
                  ACCESS  not-accessible
                  STATUS  mandatory
                  DESCRIPTION
                      "Entries of x25RAFTable."
                  INDEX { x25RAFTPort, x25RAFTIndex }
                  ::= { x25RAFTable 1 }

          X25RAFTEntry ::= SEQUENCE {
                  x25RAFTPort
                          INTEGER,
                  x25RAFTIndex
                          INTEGER,
                  x25RAFTAddr
                          X121Address,
                  x25RAFTComments
                          DisplayString,
                  x25RAFTNegWindowSize
                          INTEGER,
                  x25RAFTNegPacketSize
                          INTEGER,
                  x25RAFTAcceptReverseCharging
                          INTEGER,
                  x25RAFTProposeReverseCharging
                          INTEGER,
                  x25RAFTCUGStatus
                          INTEGER,
                  x25RAFTCUGValue
                          INTEGER,
                  x25RAFTEnable
                          INTEGER
                  }

          x25RAFTPort  OBJECT-TYPE
                  SYNTAX  INTEGER (1..16)
                  ACCESS  read-only
                  STATUS  mandatory
                  DESCRIPTION
                      "A value that uniquely identifies the
                      X.25 PLE subnetwork (physical interface
                      on the fp) and matches its physical port value."
                  ::= { x25RAFTEntry 1 }

          x25RAFTIndex  OBJECT-TYPE
                  SYNTAX  INTEGER (1..64)
                  ACCESS  read-only
                  STATUS  mandatory
                  DESCRIPTION
                      "A value that uniquely identifies the entry
                      in the RAFT table. The maximum No. of entries is 64
                      per Port."
                  ::= { x25RAFTEntry 2 }

          x25RAFTAddr  OBJECT-TYPE
                  SYNTAX  X121Address
                  ACCESS  read-write
                  STATUS  mandatory
                  DESCRIPTION
                      "The address string which identifies this entry.
                      A x25 address which matches this string will result
                      in the facilities being applied to the virtual circuit
                      being established. This string must contain BCD digits
                      0 to 9.
                      This string can contain two wild card characters
                      which are * or ?. * will match any string or portion
                      of a string. ? will match any character.
                      Example 1* will match 12 123 1234 12345 etc,
                      1? will match 12 13 14 15 etc.
                      Any other character is not allowed. In reality a NULL
                      string is not allowed"
                  ::= { x25RAFTEntry 3 }

          x25RAFTComments  OBJECT-TYPE
                  SYNTAX  DisplayString (SIZE (0..21))
                  ACCESS  read-write
                  STATUS  mandatory
                  DESCRIPTION
                      "An ASCII comment string which describes this RAFT entry."
                  ::= { x25RAFTEntry 4 }

          x25RAFTNegWindowSize  OBJECT-TYPE
                  SYNTAX  INTEGER (0..127)
                  ACCESS  read-write
                  STATUS  mandatory
                  DESCRIPTION
                      "The window size which will be negotiated for a
                      circuit. A size of zero for a circuit means no
                      negotiation, If non-zero then call request and call
                      accept packets will contain negotiated window size.
                      The value of this object is limited by the setting of
                      x25OperPacketSequencing. This value must be less than 8
                      if sequencing is mod8.  If this parameter is non-zero then
                      flow control negotiation for window size is enabled."
                  REFERENCE
                      "10733 proposedWindowSize;
                          See ISO 8208 Section 15.2.2.1.2"
                  DEFVAL { 0 }
                  ::= { x25RAFTEntry 5 }

          x25RAFTNegPacketSize  OBJECT-TYPE
                  SYNTAX  INTEGER {
                          size0 (1),
                          size128 (128),
                          size256 (256),
                          size512 (512),
                          size1024 (1024)
                          }
                  ACCESS  read-write
                  STATUS  mandatory
                  DESCRIPTION
                      "The packet size in octets negotiated for a
                      circuit. A size of zero for a circuit
                      means no negotiation. If set then call
                      request and call accept packets will contain
                      negotiated window size.
                      If this parameter is non-zero then flow control
                      negotiation for packet size is enabled."
                  REFERENCE
                      "10733 proposedPacketSize;
                      See ISO 8208 Section 15.2.2.1.1"
                  DEFVAL { size0 }
                  ::= { x25RAFTEntry 6 }

          x25RAFTProposeReverseCharging  OBJECT-TYPE
                  SYNTAX  INTEGER {
                          enable (1),
                          disable (2)
                          }
                  ACCESS  read-write
                  STATUS  mandatory
                  DESCRIPTION
                      "Identify if the PLE should propose reverse charging.
                      If this parameter is set, then the originated call packet
                      will contain the reverse charge request facility."
                  REFERENCE
                      "10733 proposedPacketSize;
                          See ISO 8208 Section 15.2.2.6"
                  DEFVAL { disable }
                  ::= { x25RAFTEntry 7 }

          x25RAFTAcceptReverseCharging  OBJECT-TYPE
                  SYNTAX  INTEGER {
                          enable (1),
                          disable (2)
                          }
                  ACCESS  read-write
                  STATUS  mandatory
                  DESCRIPTION
                      "Identify if the PLE will accept or refuse charges.
                      If this paramter is set, then a received call packet
                      which contains reverse charge request facility will be
                      allowed."
                  REFERENCE
                      "10733 acceptReverseCharging"
                  DEFVAL { disable }
                  ::= { x25RAFTEntry 8 }

          x25RAFTCUGStatus  OBJECT-TYPE
                  SYNTAX  INTEGER {
                          enable(1),
                          disable(2)
                          }
                  ACCESS  read-write
                  STATUS  mandatory
                  DESCRIPTION
                      "Enable/disable the basic form of closed
                      user group. This parameter determines if CUG
                      facility can be used on this interface. Setting
                      this value to enable will override the x25OperCUGSub
                      parameter."
                  DEFVAL { disable }
                  ::= { x25RAFTEntry 9 }

          x25RAFTCUGValue  OBJECT-TYPE
                  SYNTAX  INTEGER (0..99)
                  ACCESS  read-write
                  STATUS  mandatory
                  DESCRIPTION
                      "The Closed User Group to be used on the call." 
                  REFERENCE
                      "See ISO 8208 Section 15.2.2.3. This implementation
                      supports only the basic CUG facility"
                  DEFVAL { 0 }
                  ::= { x25RAFTEntry 10 }

          x25RAFTEnable  OBJECT-TYPE
                  SYNTAX  INTEGER {
                          enable (1),
                          disable (2),
                          delete (3)
                          }
                  ACCESS  read-write
                  STATUS  mandatory
                  DESCRIPTION
                      "Determines the status of the entry in the RAFT table.
                      When set to disabled, the entry in the table is ignored.
                      When set to delete, the entry is deleted from the table.
                      When an entry is first created it is disabled. The 
                      remaining parameters are filled in. The last operation 
                      should be to set this object to enable, which then 
                      makes the table entry an active entry, to be searched."
                  DEFVAL { disable }
                  ::= { x25RAFTEntry 11 }


          --
          --                The Channel Configuration Table
          --

          x25ChanTable  OBJECT-TYPE
                  SYNTAX  SEQUENCE OF X25ChanEntry
                  ACCESS  not-accessible
                  STATUS  mandatory
                  DESCRIPTION
                      "This table contains parameters which are
                      configured for channels. A channel is an entity
                      internal to the RX7000. It is a place holder
                      for x25 parameters and control options which
                      will apply to a switched virtual circuit
                      established for a logical port in the RX7000
                      system."
                  ::= { x25 6 }

          x25ChanEntry  OBJECT-TYPE
                  SYNTAX  X25ChanEntry
                  ACCESS  not-accessible
                  STATUS  mandatory
                  DESCRIPTION
                      "Entries of x25ChanTable. A set to any object within
                      this table results in a channel being created, if it did
                      not already exist."
                  INDEX { x25ChanPort, x25ChanNumber }
                  ::= { x25ChanTable 1 }

          X25ChanEntry ::= SEQUENCE {
                  x25ChanPort
                      INTEGER,
                  x25ChanNumber
                      INTEGER,
                  x25ChanState
                      INTEGER,
                  x25ChanRmtAddr
                      X121Address,
                  x25ChanComments
                      DisplayString,
                  x25ChanConnect
                      INTEGER,
                  x25ChanDisconnect
                      INTEGER,
                  x25ChanAutoConnect
                      INTEGER,
                  x25ChanAutoConnectCount
                      INTEGER,
                  x25ChanDataInactivity
                      INTEGER,
                  x25ChanTimeOfDay
                      INTEGER,
                  x25ChanDataTimeOn
                      DisplayString,
                  x25ChanDataTimeOff
                      DisplayString,
                  x25ChanDirection
                      INTEGER,
                  x25ChanEnable
                      INTEGER
                  }

          x25ChanPort  OBJECT-TYPE
                  SYNTAX  INTEGER (1..16)
                  ACCESS  read-only
                  STATUS  mandatory
                  DESCRIPTION
                      "A value that uniquely identifies the
                      X.25 PLE subnetwork (physical interface
                      on the fp) and matches its physical port value."
                  ::= { x25ChanEntry 1 }

          x25ChanNumber  OBJECT-TYPE
                  SYNTAX  INTEGER (1..64)
                  ACCESS  read-only
                  STATUS  mandatory
                  DESCRIPTION
                      "A value that uniquely identifies the entry
                      in the x25ChanTable. There is a maximum of 64
                      channels per port."
                  ::= { x25ChanEntry 2 }

          x25ChanState  OBJECT-TYPE
                  SYNTAX  INTEGER {
                          inactive (1),      -- (p0)
                          ready (2),         -- (p1)
                          calling (3),       -- (p2,p3,p5)
                          dataTransfer (4),  -- (p4)
                          clearing (5)       -- (p6,p7)
                          }
                  ACCESS  read-only
                  STATUS  mandatory
                  DESCRIPTION
                      "This gives the state of the configured channel.
                      The values of this state are the same as those of
                      the SVC. This object has meaning only if a logical
                      port is attached to the channel. The ready state
                      indicates that the channel is ready to accept
                      or originate an x25 switched virtual circuit
                      connection."
                  ::= { x25ChanEntry 3 }

          x25ChanRmtAddr  OBJECT-TYPE
                  SYNTAX  X121Address
                  ACCESS  read-write
                  STATUS  mandatory
                  DESCRIPTION
                      "The remote x25 DTE address for the channel.
                      This address will be used to provide the
                      called address in the x25 call request
                      packet."
                  ::= { x25ChanEntry 4 }

          x25ChanComments  OBJECT-TYPE
                  SYNTAX  DisplayString (SIZE (0..21))
                  ACCESS  read-write
                  STATUS  mandatory
                  DESCRIPTION
                      "An ASCII comment string which describes
                      the entry in the channel table."
                  ::= { x25ChanEntry 5 }

          x25ChanConnect  OBJECT-TYPE
                  SYNTAX  INTEGER {
                          execute (1),
                          noAction (2)
                          }
                  ACCESS  read-write
                  STATUS  mandatory
                  DESCRIPTION
                      "This is a runtime parameter to instruct
                      the system to activate the virtual circuit.
                      This command can only be executed if a logical
                      port is attached to the channel. If a logical
                      port is not attached to the channel then the
                      command is ignored."
                  DEFVAL { noAction }
                  ::= { x25ChanEntry 6 }

          x25ChanDisconnect  OBJECT-TYPE
                  SYNTAX  INTEGER {
                          execute (1),
                          noAction (2)
                          }
                  ACCESS  read-write
                  STATUS  mandatory
                  DESCRIPTION
                      "This is a runtime parameter to instruct
                      the system to de-activate the virtual circuit.
                      This command can only be executed if a logical
                      port is attached to the channel. If a logical
                      port is not attached to the channel then the
                      command is ignored."
                  DEFVAL { noAction }
                  ::= { x25ChanEntry 7 }

          x25ChanAutoConnect  OBJECT-TYPE
                  SYNTAX  INTEGER (0..3600)
                  ACCESS  read-write
                  STATUS  mandatory
                  DESCRIPTION
                      "This is a configurable parameter to instruct
                      the system to automatically attempt to
                      establish a virtual circuit, when the packet
                      layer is ready, a logical port is attached
                      to the channel, and  the direction object
                      x25ChanDirection for the channel is set to
                      originate or both. The parameter is ignored
                      if any of these conditions are not met.
                      When set to zero the autoconnect function is
                      disabled. When set to non zero this parameter
                      will determine the frequency in seconds which
                      the system will retry the attempt to
                      establish the switched virtual circuit,
                      if the previous attempt failed. This timer can be
                      ineffective if the interface is not responding to
                      call request or clear request packets."
                  DEFVAL { 0 }
                  ::= { x25ChanEntry 9 }

          x25ChanAutoConnectCount  OBJECT-TYPE
                  SYNTAX  INTEGER (0..255)
                  ACCESS  read-write
                  STATUS  mandatory
                  DESCRIPTION
                      "This is a configurable parameter to determine
                      the number of attempts which the system will
                      make to establish the circuit. The
                      x25ChanAutoConnect object must be set
                      to non-zero for this parameter to be
                      effective. A value of 0, will try forever.
                      Manual connect request will restart the
                      process if the previous attempts exhausted
                      the retry count."
                  DEFVAL { 10 }
                  ::= { x25ChanEntry 10 }

          x25ChanDataInactivity  OBJECT-TYPE
                  SYNTAX  INTEGER (0..3600)
                  ACCESS  read-write
                  STATUS  mandatory
                  DESCRIPTION
                      "This is a configurable parameter which enables
                      control of the virtual circuit through data activity,
                      this parameter also sets the amount of time which must
                      elapse without data activity in order for the virtual
                      circuit to be disconnected. If the value is set to 0,
                      then data inactivity operation is disabled. Recommended
                      value for enabled is 90 seconds. A virtual circuit
                      used for bridging may make this mode of operation
                      ineffective. This parameter cannot be set to
                      enabled at the same time that x25ChanTimeOfDay
                      is set to enabled. The object
                      x25ChanDirection must be set to originate
                      or both for data inactivity control to
                      function."
                  DEFVAL { 0 }
                  ::= { x25ChanEntry 11 }

          x25ChanTimeOfDay  OBJECT-TYPE
                  SYNTAX  INTEGER {
                          enable (1),
                          disable (2)
                          }
                  ACCESS  read-write
                  STATUS  mandatory
                  DESCRIPTION
                      "This is a configurable parameter which enables
                      time of day control of the virtual circuit. If
                      this parameter is set to enabled then
                      x25ChanDataTimeON and x25ChanDataTimeOFF will
                      determine when the switched virtual is
                      established and disconnected. This parameter
                      cannot be set to enabled at the same time that
                      x25ChanDataInactivity is set to enabled. The
                      object x25ChanDirection must be set to
                      originate or both for time of day control to
                      function.  "
                  DEFVAL { disable }
                  ::= { x25ChanEntry 12 }

          x25ChanDataTimeOn  OBJECT-TYPE
                  SYNTAX  DisplayString (SIZE (5))
                  ACCESS  read-write
                  STATUS  mandatory
                  DESCRIPTION
                      "This is a configurable parameter which sets
                      the time of day to activate the SVC, Format
                      of string is hh:mm. First 2 bytes are hours,
                      second 2 bytes are minutes The parameter
                      x25ChanTimeOfDay must be set to enabled for
                      this to function. This defaults to '00:00' or midnight."
                  ::= { x25ChanEntry 13 }

          x25ChanDataTimeOff  OBJECT-TYPE
                  SYNTAX  DisplayString (SIZE (5))
                  ACCESS  read-write
                  STATUS  mandatory
                  DESCRIPTION
                      "This is a configurable parameter which sets
                      the time of day to de-activate the SVC, Format
                      of string is hh:mm. First 2 bytes are hours,
                      second 2 bytes are minutes The parameter
                      x25ChanTimeOfDay must be set to enabled for
                      this to function. This defaults to '00:00' or midnight."
                  ::= { x25ChanEntry 14 }

          x25ChanDirection  OBJECT-TYPE
                  SYNTAX  INTEGER {
                          receive (1),
                          originate (2),
                          both (3)
                          }
                  ACCESS  read-write
                  STATUS  mandatory
                  DESCRIPTION
                      "This parameter will determine the direction 
                      call can take on the SVC. When set to originate, 
                       a call request packet can be originated on the
                      interface. When set to receive, a call request
                      packet can only be received on the interface.
                      When set to both then a call request packet
                      can be both originated or received on the
                      interface. This parameter must be set to
                      originate or both for the objects
                      x25ChanTimeOfDay x25ChanDataInactivity
                      x25ChanAutoConnectTime to be effective."
                  DEFVAL { both }
                  ::= { x25ChanEntry 15 }

          x25ChanEnable  OBJECT-TYPE
                  SYNTAX  INTEGER {
                          enable (1),
                          delete (2)
                          }
                  ACCESS  read-write
                  STATUS  mandatory
                  DESCRIPTION
                      " When set to enabled, the entry
                      in the x25ChanTable will be created. When set
                      to delete the entry will be deleted."
                  DEFVAL { disable }
                  ::= { x25ChanEntry 16 }

          -- 
          --              X25 SVC Test
          --

          x25CircuitTestTable  OBJECT-TYPE
                  SYNTAX  SEQUENCE OF      X25CircuitTestEntry
                  ACCESS  not-accessible
                  STATUS  mandatory
                  DESCRIPTION
                      "This table has one entry per port. It allows a user
                      to request a test connection to a remote unit.
                      The table entry will show the status of a test call
                      made to this unit or from this unit. Only
                      one circuit is allowed at a time. A call can
                      be requested or received but not both
                      simultaneously."
                  ::= { x25 7 }

          x25CircuitTestEntry  OBJECT-TYPE
                  SYNTAX  X25CircuitTestEntry
                  ACCESS  not-accessible
                  STATUS  mandatory
                  DESCRIPTION
                          "Test circuit."
                  INDEX { x25CircuitTestPort }
                  ::= { x25CircuitTestTable 1 }

          X25CircuitTestEntry ::= SEQUENCE {
                  x25CircuitTestPort
                          INTEGER,
                  x25CircuitTestRemoteAddress
                          X121Address,
                  x25CircuitTestInRemoteAddress
                          X121Address,
                  x25CircuitTestComments
                          DisplayString,
                  x25CircuitTestInComments
                          DisplayString,
                  x25CircuitTestStatus
                          INTEGER,
                  x25CircuitTestClearCauseDiag
                          DisplayString,
                  x25CircuitTestWinSize
                          INTEGER,
                  x25CircuitTestPktSize
                          INTEGER,
                  x25CircuitTestReverseCharging
                          INTEGER,
                  x25CircuitTestCUGValue 
                          OCTET STRING,
                  x25CircuitTestCmd
                          INTEGER,
                  x25CircuitTestConnResponse
                          INTEGER
                  }

          x25CircuitTestPort  OBJECT-TYPE
                  SYNTAX  INTEGER
                  ACCESS  read-only
                  STATUS  mandatory
                  DESCRIPTION
                      "A value that uniquely identifies the
                      X.25 PLE subnetwork (physical interface
                      on the fp) and matches its physical port value."
                  ::= { x25CircuitTestEntry 1 }

          x25CircuitTestRemoteAddress  OBJECT-TYPE
                  SYNTAX  X121Address
                  ACCESS  read-write
                  STATUS  mandatory
                  DESCRIPTION
                      "The x25 DTE address to be used as the
                      called address, when a call packet is
                      originated from this RX7000 unit."
                  ::= { x25CircuitTestEntry 2 }

          x25CircuitTestInRemoteAddress  OBJECT-TYPE
                  SYNTAX  X121Address
                  ACCESS  read-only
                  STATUS  mandatory
                  DESCRIPTION
                      "The x25 DTE address in the calling address field of
                      a received call packet."
                  ::= { x25CircuitTestEntry 3 }

          x25CircuitTestComments  OBJECT-TYPE
                  SYNTAX  DisplayString (SIZE (0..21))
                  ACCESS  read-write
                  STATUS  mandatory
                  DESCRIPTION
                      "An ASCII comment string which describes
                      this test. This string is sent to the remote
                      site as a data packet when the circuit is
                      established. This defaults to a NULL string."
                  ::= { x25CircuitTestEntry 4 }

          x25CircuitTestInComments  OBJECT-TYPE
                  SYNTAX  DisplayString (SIZE (0..21))
                  ACCESS  read-only
                  STATUS  mandatory
                  DESCRIPTION
                      "The ASCII comment string configured at the
                      remote site. This only has meaning if the test
                      call was received. The contents of this object
                      are meaningless if the test call was originated
                      from this RX7000 unit."
                  ::= { x25CircuitTestEntry 5 }

          x25CircuitTestStatus  OBJECT-TYPE
                  SYNTAX  INTEGER {
                          inactive (1),      -- (p0)
                          ready (2),         -- (p1)
                          calling (3),       -- (p2,p3,p5)
                          dataTransfer (4),  -- (p4)
                          clearing (5)       -- (p6,p7)
                          }
                  ACCESS  read-only
                  STATUS  mandatory
                  DESCRIPTION
                      "This object reports the current packet level
                      status of the switch virtual circuit."
                  ::= { x25CircuitTestEntry 6 }

          x25CircuitTestClearCauseDiag  OBJECT-TYPE
                  SYNTAX  DisplayString (SIZE (7))
                  ACCESS  read-only
                  STATUS  mandatory
                  DESCRIPTION
                      "This object defines the cause/diag code
                      in the last received clear packet. The form of this is
                      'nnn nnn' where the first 3 digits give the cause code
                      and the second 3 the diagnostic code."
                  ::= { x25CircuitTestEntry 7 }

          x25CircuitTestWinSize  OBJECT-TYPE
                  SYNTAX  INTEGER
                  ACCESS  read-only
                  STATUS  mandatory
                  DESCRIPTION
                      "The window size currently in use on the switched
                      virtual circuit."
                  ::= { x25CircuitTestEntry 8 }

          x25CircuitTestPktSize  OBJECT-TYPE
                  SYNTAX  INTEGER
                  ACCESS  read-only
                  STATUS  mandatory
                  DESCRIPTION
                      "The packet size currently in use on the switched
                      virtual circuit."
                  ::= { x25CircuitTestEntry 9 }

          x25CircuitTestReverseCharging  OBJECT-TYPE
                  SYNTAX  INTEGER {
                          enable (1),
                          disable (2)
                          }
                  ACCESS  read-only
                  STATUS  mandatory
                  DESCRIPTION
                      "Identify if the test circuit used reverse charging
                      when establishing the call. Use of this facility is 
                      determined by the RAFT or the interface default"
                  ::= { x25CircuitTestEntry 10 }

          x25CircuitTestCUGValue  OBJECT-TYPE
                  SYNTAX  DisplayString (SIZE(0..2))
                  ACCESS  read-only
                  STATUS  mandatory
                  DESCRIPTION
                      "Indicates  if the Closed User Group facility
                      was used on the circuit.  The object consists of
                      two octets containing the characters 0 through 9.
                      A zero length string indicates no CUG facility was
                      used on the test circuit. Use of this facility is
                      determined by the RAFT or the interface default"
                  ::= { x25CircuitTestEntry 11 }

          x25CircuitTestCmd  OBJECT-TYPE
                  SYNTAX  INTEGER {
                          connect (1),
                          clear (2),
                          clearConnect (3),
                          ready (4)
                          }
                  ACCESS  read-write
                  STATUS  mandatory
                  DESCRIPTION
                      "The command which requests an action on the test
                      circuit. connect - this command will attempt to
                      originate a test connection provided a test connection is
                      not already established.  clear- this command
                      will clear the test connection if it is established.
                      clearConnect - this command will clear the test
                      connection if it is established and then attempt 
                      to originate a test connection."
                  DEFVAL { clearConnect }
                  ::= { x25CircuitTestEntry 12 }

          x25CircuitTestConnResponse  OBJECT-TYPE
                  SYNTAX  INTEGER {
                          incomingConnected (1),
                          outgoingConnected (2),
                          rcvCleared (3),
                          sentCleared (4)
                          } 
                  ACCESS  read-only
                  STATUS  mandatory
                  DESCRIPTION
                      "This indicates the action which last occurred on the
                      circuit. incoming_connected indicates that the switched
                      virtual circuit was connected as a result of an 
                      incoming call, outgoing_connected indicates that the 
                      circuit was connected as a result of an outgoing 
                      call, rcv_cleared indicates that the switched virtual 
                      circuit is disconnected as a result of receiving a 
                      clear packet from the remote end, sent_cleared 
                      indicates that the switched virtual circuit is
                      disconnected as a result of sending a clear packet to 
                      the remote end"
                  ::= { x25CircuitTestEntry 13 }

    --
    -- The Ethernet Group
    --

      ethernetPortParameterTable  OBJECT-TYPE
          SYNTAX  SEQUENCE OF EthernetPortEntry
          ACCESS  not-accessible
          STATUS  mandatory
          DESCRIPTION
             "A table of ethernet physical port parameters."
          ::= { ethernet 1 }

      ethernetPortEntry  OBJECT-TYPE
          SYNTAX  EthernetPortEntry
          ACCESS  not-accessible
          STATUS  mandatory
          DESCRIPTION
             "An entry in the ethernet port table."
          INDEX  { ethernetPortNumber }

          ::= { ethernetPortParameterTable 1 }

      EthernetPortEntry ::= SEQUENCE {
          ethernetPortNumber
               INTEGER,
          ethernetSQEErrors
               Counter,
          ethernetRxMissedFrames
               Counter,
          ethernetRetries
               Counter,
          ethernetCollisions
               Counter,
          ethernetRunts
               Counter,
          ethernetFRAMorCRCErrors
               Counter,
          ethernetTxDeferrals
               Counter,
          ethernetLateCollisions
               Counter,
          ethernetLossofCarrierErrors
               Counter,
          ethernetRetryErrors
               Counter,
          ethernetRetryErrors
               Counter,
          ethernetTDRUnits
               Counter,
          ethernetTxUnicastFrames
               Counter,
          ethernetRxUnicastFrames
               Counter,
          ethernetTxMulticastFrames
               Counter,
          ethernetRxMulticastFrames
               Counter,
          ethernetTxBroadcastFrames
               Counter,
          ethernetRxBroadcastFrames
               Counter,
          ethernetNoOfLinkResets
               Counter,
          ethernetLastLinkResetReason
               INTEGER,
          ethernetTimeSinceLastLinkReset
               INTEGER
       }

      ethernetPortNumber  OBJECT-TYPE
          SYNTAX  INTEGER
          ACCESS  read-only
          STATUS  mandatory
          DESCRIPTION
             "The value of the index uniquley specifies the physical port
              number to which this entry is applicable."
          ::= { ethernetPortEntry 1 }

      ethernetSQEErrors  OBJECT-TYPE
          SYNTAX  Counter
          ACCESS  read-only
          STATUS  mandatory
          DESCRIPTION
             "The number of SQE/Heartbeat errors detected."
          ::= { ethernetPortEntry 2 }

      ethernetRxMissedFrames  OBJECT-TYPE
          SYNTAX  Counter
          ACCESS  read-only
          STATUS  mandatory
          DESCRIPTION
             "The number of receive frames missed because no buffers
              were available to accept the incoming data."
          ::= { ethernetPortEntry 3 }

      ethernetRetries  OBJECT-TYPE
          SYNTAX  Counter
          ACCESS  read-only
          STATUS  mandatory
          DESCRIPTION
             "Total number of transmission retries by this station on the
              attached LAN."
          ::= { ethernetPortEntry 4 }

      ethernetCollisions  OBJECT-TYPE
          SYNTAX  Counter
          ACCESS  read-only
          STATUS  mandatory
          DESCRIPTION
             "Total collisions detected on the attached LAN."
          ::= { ethernetPortEntry 5 }

      ethernetRunts  OBJECT-TYPE
          SYNTAX  Counter
          ACCESS  read-only
          STATUS  mandatory
          DESCRIPTION
             "Total number of runts detected on the attached LAN."
          ::= { ethernetPortEntry 6 }

      ethernetFRAMorCRCErrors  OBJECT-TYPE
          SYNTAX  Counter
          ACCESS  read-only
          STATUS  mandatory
          DESCRIPTION
             "Total number of Framing or CRC errors detected on LAN."
          ::= { ethernetPortEntry 7 }

      ethernetTxDeferrals  OBJECT-TYPE
          SYNTAX  Counter
          ACCESS  read-only
          STATUS  mandatory
          DESCRIPTION
             "The total number of TX deferrals required on the LAN segment."
          ::= { ethernetPortEntry 8 }

      ethernetLateCollisions  OBJECT-TYPE
          SYNTAX  Counter
          ACCESS  read-only
          STATUS  mandatory
          DESCRIPTION
             "Total number of late collisions encountered during transmission
              by this port."
          ::= { ethernetPortEntry 9 }

      ethernetLossofCarrierErrors  OBJECT-TYPE
          SYNTAX  Counter
          ACCESS  read-only
          STATUS  mandatory
          DESCRIPTION
             "Total number of loss of carrier errors encountered by this port"
          ::= { ethernetPortEntry 10 }

      ethernetRetryErrors  OBJECT-TYPE
          SYNTAX  Counter
          ACCESS  read-only
          STATUS  mandatory
          DESCRIPTION
             "Total number of TX retry limit errors encountered during
              transmission by this port."
          ::= { ethernetPortEntry 11 }

      ethernetTDRUnits  OBJECT-TYPE
          SYNTAX  Counter
          ACCESS  read-only
          STATUS  mandatory
          DESCRIPTION
             "Most recently detected TDR figure detected by this port. This
              is the time from the start of transmission to the occurrence of
              of a collision or loss of carrier, and is updated only when a
              retry error is detected on transmission."
          ::= { ethernetPortEntry 12 }

      ethernetTxUnicastFrames  OBJECT-TYPE
          SYNTAX  Counter
          ACCESS  read-only
          STATUS  mandatory
          DESCRIPTION
             "Total number of unicast frames transmitted."
          ::= { ethernetPortEntry 13 }

      ethernetRxUnicastFrames  OBJECT-TYPE
          SYNTAX  Counter
          ACCESS  read-only
          STATUS  mandatory
          DESCRIPTION
             "Total number of unicast frames received."
          ::= { ethernetPortEntry 14 }

      ethernetTxMulticastFrames  OBJECT-TYPE
          SYNTAX  Counter
          ACCESS  read-only
          STATUS  mandatory
          DESCRIPTION
             "Total number of Multicast frames transmitted."
          ::= { ethernetPortEntry 15 }

      ethernetRxMulticastFrames  OBJECT-TYPE
          SYNTAX  Counter
          ACCESS  read-only
          STATUS  mandatory
          DESCRIPTION
             "Total number of Multicast frames received."
          ::= { ethernetPortEntry 16 }

      ethernetTxBroadcastFrames  OBJECT-TYPE
          SYNTAX  Counter
          ACCESS  read-only
          STATUS  mandatory
          DESCRIPTION
             "Total number of Broadcast frames transmitted."
          ::= { ethernetPortEntry 17 }

      ethernetRxBroadcastFrames  OBJECT-TYPE
          SYNTAX  Counter
          ACCESS  read-only
          STATUS  mandatory
          DESCRIPTION
             "Total number of Broadcast frames received."
          ::= { ethernetPortEntry 18 }

      ethernetNoOfLinkResets  OBJECT-TYPE
          SYNTAX  Counter
          ACCESS  read-only
          STATUS  mandatory
          DESCRIPTION
             "This is the number of link resets which have occurred since the
              last reinitialization of the unit."
          ::= { ethernetPortEntry 19 }

      ethernetLastLinkResetReason  OBJECT-TYPE
          SYNTAX  INTEGER {
                  noReason (1),
                  management (2),
                  deviceReset (3),
                  cableDrop (4)
                  }
          ACCESS  read-only
          STATUS  mandatory
          DESCRIPTION
             "This object gives the reason code for the last reset which
              occurred on this LAN physical link. A value of noReason(1)
              is returned if the link has not reset. A value of management(2)
              is returned when a link reset has been caused by a management
              protocol (either SNMP or by LMS). A value of deviceReset(3)
              is returned if the link reset was caused by a hardware failure.
              A value of cableDrop(4) is returned when the link reset was
              caused by a missing or faulty cable."
          ::= { ethernetPortEntry 20 }

    ethernetTimeSinceLastLinkReset  OBJECT-TYPE
        SYNTAX  INTEGER
        ACCESS  read-only
        STATUS  mandatory
        DESCRIPTION
            "This is the time (in hundredths of seconds) since the last link
             reset."
        ::= { ethernetPortEntry 21 }

    --
    --    Private Extensions to the frame relay group.
    --    This group augments the Frame Relay RFC1315.
    --
     --  Private Frame Relay Port Table

     -- The table describing errors encountered on each Frame
     -- Relay Interface.

     frmRelPortTable  OBJECT-TYPE
         SYNTAX   SEQUENCE OF FrmRelPortEntry
         ACCESS   not-accessible
         STATUS   mandatory
         DESCRIPTION
            "A table containing per port information for Frame Relay interfaces."
         ::= { frmrelay 1 }

         frmRelPortEntry  OBJECT-TYPE
             SYNTAX   FrmRelPortEntry
             ACCESS   not-accessible
             STATUS   mandatory
             DESCRIPTION
                "The error information for a single frame relay
                interface."
            INDEX { frmRelPortIndex }
            ::= { frmRelPortTable 1 }

         FrmRelPortEntry ::= SEQUENCE {
                 frmRelPortIndex
                     INTEGER,
                 frmRelPortMaxFrameSize
                     INTEGER,
                 frmRelPortDlcmiErrors
                     Counter,
                 frmRelPortDlcmiRxedStatus
                     Counter,
                 frmRelPortDlcmiTxedStatus
                     Counter,
                 frmRelPortCircuits
                    INTEGER
                 }

         frmRelPortIndex  OBJECT-TYPE
             SYNTAX   INTEGER
             ACCESS   read-only
             STATUS   mandatory
             DESCRIPTION
                "The value of this index uniquely identifies the physical port
                 to which this entry is applicable."
            ::= { frmRelPortEntry 1 }

         frmRelPortMaxFrameSize  OBJECT-TYPE
             SYNTAX   INTEGER (200..1528)
             ACCESS   read-write
             STATUS   mandatory
             DESCRIPTION
                "This is the frame size used between this port (DTE) and the
        network (DCE)."
            ::= { frmRelPortEntry 2 }

         frmRelPortDlcmiErrors  OBJECT-TYPE
             SYNTAX   Counter
             ACCESS   read-only
             STATUS   mandatory
             DESCRIPTION
                "This is the number of Error frames that have occurred on the
        management channel, i.e. the Dlcmi"
            ::= { frmRelPortEntry 3 }

         frmRelPortDlcmiRxedStatus  OBJECT-TYPE
             SYNTAX   Counter
             ACCESS   read-only
             STATUS   mandatory
             DESCRIPTION
                "This is the number of Status messages received from the
        network, on the Dlcmi."
            ::= { frmRelPortEntry 4 }

         frmRelPortDlcmiTxedStatus  OBJECT-TYPE
             SYNTAX   Counter
             ACCESS   read-only
             STATUS   mandatory
             DESCRIPTION
                "This is the number of Status messages transmitted to the
        network, via this port, on the Dlcmi."
            ::= { frmRelPortEntry 5 }

        frmRelPortCircuits  OBJECT-TYPE
             SYNTAX   INTEGER
             ACCESS   read-only
             STATUS   mandatory
             DESCRIPTION
                "This is the number of circuits which are currently configured
        for this port."
            ::= { frmRelPortEntry 6 }

    --
    -- The BootP Group
    --

         bootpServerIpAddress  OBJECT-TYPE
            SYNTAX  IpAddress
            ACCESS  read-write
            STATUS  mandatory
            DESCRIPTION
               " The IP Address of the BootP server"
            ::= { bootp 1 }

         bootpFileName  OBJECT-TYPE
            SYNTAX  DisplayString (SIZE (0..256))
            ACCESS  read-write
            STATUS  mandatory
            DESCRIPTION
                " The path name and name of the file to be downloaded."
            ::= { bootp 2 }

         bootpAction  OBJECT-TYPE
            SYNTAX  INTEGER {
                    start (1),
                    stop  (2),
            noAction (3)
                    }
            ACCESS  read-write
            STATUS  mandatory
            DESCRIPTION
                 " Indicates whether to stop or start bootp/tftp download. This
                 always returns the value no_action to a get request"
            ::= { bootp 3 }

         bootpStatus  OBJECT-TYPE
            SYNTAX  INTEGER {
                    idle (1),
                    attempting (2),
                    downloading (3),
                    failBootpNoServer (4),
                    failTFTPNoFile (5),
                    failTFTPInvalidFile (6),
                    failNetworkError (7),
                    failFlashProgError (8),
                    failFlashChksumError (9),
                    downloadSuccess (10)
                    }
            ACCESS  read-only
            STATUS  mandatory
            DESCRIPTION
                 " Status of the bootp/tftp process."
            ::= { bootp 4 }

    --
    -- The Product group, listed are the objects which identify the
    -- various products in the RX7000 family.
    --
    --
    -- C Chassis.
    --
    productRX7700 OBJECT IDENTIFIER ::= { product 1 }

    --
    -- B Chassis.
    --
    productRX7500 OBJECT IDENTIFIER ::= { product 2 }

    --
    -- B Chassis with power plus.
    --
    productRX7550 OBJECT IDENTIFIER ::= { product 3 }

    --
    -- B Minus Chassis.
    --
    productRX7250 OBJECT IDENTIFIER ::= { product 4 }

    --
    -- A Chassis.
    --
    productRX7260 OBJECT IDENTIFIER ::= { product 5 }

    --
    -- LC Chassis.
    --
    productRX7100 OBJECT IDENTIFIER ::= { product 6 }

    --
    -- A Chassis
    --
    productRX7240   OBJECT IDENTIFIER ::= { product 7 }

    --
    -- 7220 Chassis.
    --
    product7220 OBJECT IDENTIFIER ::= { product 8 }
 
    --
    -- ENS
    --
    productENS OBJECT IDENTIFIER ::= { product 9 }
 
    --
    -- 7221 Chassis.
    --
    product7221 OBJECT IDENTIFIER ::= { product 10 }
 

    --
    -- The Private OSPF Group
    --
    -- This group augments the OSPF MIB, RFC1253
    --

     ospfImportRipRoutes  OBJECT-TYPE
         SYNTAX  Status
         ACCESS  read-write
         STATUS  mandatory
         DESCRIPTION
            "This flag indicates if OSPF can import routes learned
             through RIP locally and insert into OSPF routing."
         ::= { rtxospf 1 }

     ospfRipFilterDefaultAction  OBJECT-TYPE
         SYNTAX  INTEGER {
                 import (1),
                 dontImport (2)
                 }
         ACCESS  read-write
         STATUS  mandatory
         DESCRIPTION
            "This object indicates the action-on-no-match for RIP routes."
         ::= { rtxospf 2 }

     ospfImportStaticRoutes  OBJECT-TYPE
         SYNTAX  Status
         ACCESS  read-write
         STATUS  mandatory
         DESCRIPTION
            "If enabled, OSPF can import static routes."
         ::= { rtxospf 3 }

     ospfStaticFilterDefaultAction  OBJECT-TYPE
         SYNTAX  INTEGER {
                 import (1),
                 dontImport (2)
                 }
         ACCESS  read-write
         STATUS  mandatory
         DESCRIPTION
            "This object indicates the action-on-no-match for Static routes."
         ::= { rtxospf 4 }

     ospfRipFilterTable  OBJECT-TYPE
         SYNTAX  SEQUENCE OF OspfRipFilterEntry
         ACCESS  not-accessible
         STATUS  mandatory
         DESCRIPTION
            "This table contains filter information for RIP routes importation."
         ::= { rtxospf 5 }

     ospfRipFilterEntry  OBJECT-TYPE
         SYNTAX  OspfRipFilterEntry
         ACCESS  not-accessible
         STATUS  mandatory
         DESCRIPTION
            "An entry in the OSPF Rip Filter Table. To set an entry, 
            all the objects in this entry must be supplied within a 
            single SET PDU"
         INDEX { ospfRipFilterIpAddress }
         ::= { ospfRipFilterTable 1 }

     OspfRipFilterEntry ::= SEQUENCE {
         ospfRipFilterIpAddress
             IpAddress,
         ospfRipFilterIpMask
             IpAddress,
         ospfRipFilterAction
             INTEGER,
         ospfRipFilterStatus
             Validation
         }

     ospfRipFilterIpAddress  OBJECT-TYPE
         SYNTAX  IpAddress
         ACCESS  read-write
         STATUS  mandatory
         DESCRIPTION
            "Destination IP address found by RIP to which the filter
             should be applied."
         ::= { ospfRipFilterEntry 1 }

     ospfRipFilterIpMask  OBJECT-TYPE
         SYNTAX  IpAddress
         ACCESS  read-write
         STATUS  mandatory
         DESCRIPTION
            "The mask associated with the IpAddress."
         ::= { ospfRipFilterEntry 2 }

     ospfRipFilterAction  OBJECT-TYPE
         SYNTAX  INTEGER {
                 import (1),
                 dontImport (2)
                 }
         ACCESS  read-write
         STATUS  mandatory
         DESCRIPTION
            "This object indicates whether to import or not import a
             route in case of a match."
         ::= { ospfRipFilterEntry 3 }

     ospfRipFilterStatus  OBJECT-TYPE
         SYNTAX  Validation
         ACCESS  read-write
         STATUS  mandatory
         DESCRIPTION
            "This object indicates if the entry is valid or invalid."
         ::= { ospfRipFilterEntry 4 }

     ospfRipConvertTable  OBJECT-TYPE
         SYNTAX  SEQUENCE OF OspfRipConvertEntry
         ACCESS  not-accessible
         STATUS  mandatory
         DESCRIPTION
            "This table contains information for converting RIP's hop
             count to OSPF's metric for each pair of configured destination
             IP address and its mask."
         ::= { rtxospf 6 }

     ospfRipConvertEntry  OBJECT-TYPE
         SYNTAX  OspfRipConvertEntry
         ACCESS  not-accessible
         STATUS  mandatory
         DESCRIPTION
            "An entry in the OSPF RIP Convert Table.  To set an entry,
            all the objects in this entry must be supplied within a
            single SET PDU"
         INDEX { ospfRipConvertIpAddress,
                 ospfRipConvertHop }
         ::= { ospfRipConvertTable 1 }

     OspfRipConvertEntry ::= SEQUENCE {
         ospfRipConvertIpAddress
             IpAddress,
         ospfRipConvertIpMask
             IpAddress,
         ospfRipConvertHop
             INTEGER,
         ospfRipConvertMetric
             BigMetric,
         ospfRipConvertStatus
             Validation
         }

     ospfRipConvertIpAddress  OBJECT-TYPE
         SYNTAX  IpAddress
         ACCESS  read-write
         STATUS  mandatory
         DESCRIPTION
            "Destination IP address found by RIP."
         ::= { ospfRipConvertEntry 1 }

     ospfRipConvertIpMask  OBJECT-TYPE
         SYNTAX  IpAddress
         ACCESS  read-write
         STATUS  mandatory
         DESCRIPTION
            "Destination IP address mask."
         ::= { ospfRipConvertEntry 2 }

     ospfRipConvertHop  OBJECT-TYPE
         SYNTAX  INTEGER ( 0..16 )
         ACCESS  read-write
         STATUS  mandatory
         DESCRIPTION
            "The hop count measured in RIP."
         ::= { ospfRipConvertEntry 3 }

     ospfRipConvertMetric  OBJECT-TYPE
         SYNTAX  BigMetric
         ACCESS  read-write
         STATUS  mandatory
         DESCRIPTION
            "The metric in OSPF converted from RIP."
         ::= { ospfRipConvertEntry 4 }

     ospfRipConvertStatus  OBJECT-TYPE
         SYNTAX  Validation
         ACCESS  read-write
         STATUS  mandatory
         DESCRIPTION
            "This object tells us if this entry in the table is valid or 
            invalid."
         ::= { ospfRipConvertEntry 5 }

     ospfRipDefaultConvertTable  OBJECT-TYPE
         SYNTAX  SEQUENCE OF OspfRipDefaultConvertEntry
         ACCESS  not-accessible
         STATUS  mandatory
         DESCRIPTION
            "This table contains the default conversion from hop counts
             measured in RIP to metrics measured in OSPF." 


         ::= { rtxospf 7 }

     ospfRipDefaultConvertEntry  OBJECT-TYPE
         SYNTAX  OspfRipDefaultConvertEntry
         ACCESS  not-accessible
         STATUS  mandatory
         DESCRIPTION
            "An entry in the OSPF RIP DefaultConvert Table.  To set an entry,
             all the objects in this entry must be supplied within a
            single SET PDU"
         INDEX  { ospfRipDefaultConvertHop }
         ::= { ospfRipDefaultConvertTable 1 }

     OspfRipDefaultConvertEntry ::= SEQUENCE {
         ospfRipDefaultConvertHop
             INTEGER,
         ospfRipDefaultConvertMetric
             BigMetric,
         ospfRipDefaultConvertStatus
             Validation
         }

     ospfRipDefaultConvertHop  OBJECT-TYPE
         SYNTAX  INTEGER ( 0..16 )
         ACCESS  read-write
         STATUS  mandatory
         DESCRIPTION
            "The hop count measured in RIP."
         ::= { ospfRipDefaultConvertEntry 1 }

     ospfRipDefaultConvertMetric  OBJECT-TYPE
         SYNTAX  BigMetric
         ACCESS  read-write
         STATUS  mandatory
         DESCRIPTION
            "The metric in OSPF converted from RIP."
         ::= { ospfRipDefaultConvertEntry 2 }

     ospfRipDefaultConvertStatus  OBJECT-TYPE
         SYNTAX  Validation
         ACCESS  read-write
         STATUS  mandatory
         DESCRIPTION
            "The object indicates if this entry is valid or invalid."
         ::= { ospfRipDefaultConvertEntry 3 }

     ospfStaticFilterTable  OBJECT-TYPE
         SYNTAX  SEQUENCE OF OspfStaticFilterEntry
         ACCESS  not-accessible
         STATUS  mandatory
         DESCRIPTION
            "This table contains filter information for static routes
             importation."
         ::= { rtxospf 8 }

     ospfStaticFilterEntry  OBJECT-TYPE
         SYNTAX  OspfStaticFilterEntry
         ACCESS  not-accessible
         STATUS  mandatory
         DESCRIPTION
            "An entry in the OSPF Static Filter Table   To set an entry,
            all the objects in this entry must be supplied within a
            single SET PDU"
         INDEX { ospfStaticFilterIpAddress,
                 ospfStaticFilterTOS }
         ::= { ospfStaticFilterTable 1 }

     OspfStaticFilterEntry  ::= SEQUENCE {
         ospfStaticFilterIpAddress
             IpAddress,
         ospfStaticFilterIpMask
             IpAddress,
         ospfStaticFilterTOS
             TOSType,
         ospfStaticFilterAction
             INTEGER,
         ospfStaticFilterStatus
             Validation
         }

     ospfStaticFilterIpAddress  OBJECT-TYPE
         SYNTAX  IpAddress
         ACCESS  read-write
         STATUS  mandatory
         DESCRIPTION
            "Destination IP Address."
         ::= { ospfStaticFilterEntry 1 }

     ospfStaticFilterIpMask  OBJECT-TYPE
         SYNTAX  IpAddress
         ACCESS  read-write
         STATUS  mandatory
         DESCRIPTION
            "Destination network address mask."
         ::= { ospfStaticFilterEntry 2 }

     ospfStaticFilterTOS  OBJECT-TYPE
         SYNTAX  TOSType
         ACCESS  read-write
         STATUS  mandatory
         DESCRIPTION
            "Type Of Service for this route."
         ::= { ospfStaticFilterEntry 3 }

     ospfStaticFilterAction  OBJECT-TYPE
         SYNTAX  INTEGER {
                 import (1),
                 dontImport (2)
                 }
         ACCESS  read-write
         STATUS  mandatory
         DESCRIPTION
            "Action to be taken in case of a match."
         ::= { ospfStaticFilterEntry 4 }

     ospfStaticFilterStatus  OBJECT-TYPE
         SYNTAX  Validation
         ACCESS  read-write
         STATUS  mandatory
         DESCRIPTION
            "The object indicates if this entry is valid or invalid."
         ::= { ospfStaticFilterEntry 5 }

     ospfStaticConvertTable  OBJECT-TYPE
         SYNTAX  SEQUENCE OF OspfStaticConvertEntry
         ACCESS  not-accessible
         STATUS  mandatory
         DESCRIPTION
            "This table contains information for converting hop count
             of static routes to OSPF's metric for each configured pair
             of IP Address and its mask."
         ::= { rtxospf 9 }

     ospfStaticConvertEntry  OBJECT-TYPE
         SYNTAX  OspfStaticConvertEntry
         ACCESS  not-accessible
         STATUS  mandatory
         DESCRIPTION
            "An entry in the OSPF Static Convert Table.   To set an entry,
            all the objects in this entry must be supplied within a
            single SET PDU"
         INDEX { ospfStaticConvertIpAddress,
                 ospfStaticConvertTOS,
                 ospfStaticConvertHop }
         ::= { ospfStaticConvertTable 1 }

     OspfStaticConvertEntry ::= SEQUENCE {
         ospfStaticConvertIpAddress
             IpAddress,
         ospfStaticConvertIpMask
             IpAddress,
         ospfStaticConvertTOS
             TOSType,
         ospfStaticConvertHop
             INTEGER,
         ospfStaticConvertMetric
             BigMetric,
         ospfStaticConvertStatus
             Validation
         }

     ospfStaticConvertIpAddress  OBJECT-TYPE
         SYNTAX  IpAddress
         ACCESS  read-write
         STATUS  mandatory
         DESCRIPTION
            "Destination IP Address."
         ::= { ospfStaticConvertEntry 1 }

     ospfStaticConvertIpMask  OBJECT-TYPE
         SYNTAX  IpAddress
         ACCESS  read-write
         STATUS  mandatory
         DESCRIPTION
            "Destination IP Address."
         ::= { ospfStaticConvertEntry 2 }
        
     ospfStaticConvertTOS  OBJECT-TYPE
         SYNTAX  TOSType
         ACCESS  read-write
         STATUS  mandatory
         DESCRIPTION
            "Type of Service for this route."
         ::= { ospfStaticConvertEntry 3 }

     ospfStaticConvertHop  OBJECT-TYPE
         SYNTAX  INTEGER ( 0..16 )
         ACCESS  read-write
         STATUS  mandatory
         DESCRIPTION
            "The hop count for static route."
         ::= { ospfStaticConvertEntry 4 }

     ospfStaticConvertMetric  OBJECT-TYPE
         SYNTAX  BigMetric
         ACCESS  read-write
         STATUS  mandatory
         DESCRIPTION
            "The metric in OSPF, converted from RIP."
         ::= { ospfStaticConvertEntry 5 }

     ospfStaticConvertStatus  OBJECT-TYPE
         SYNTAX  Validation
         ACCESS  read-write
         STATUS  mandatory
         DESCRIPTION
            "This object indicates if the entry is valid or invalid."
         ::= { ospfStaticConvertEntry 6 }

     ospfStaticDefaultConvertTable  OBJECT-TYPE
         SYNTAX  SEQUENCE OF OspfStaticDefaultConvertEntry
         ACCESS  not-accessible
         STATUS  mandatory
         DESCRIPTION
            "This table contains default conversion from hop counts
             measured for static routes to metrics measured in OSPF."
         ::= { rtxospf 10 }

     ospfStaticDefaultConvertEntry  OBJECT-TYPE
         SYNTAX  OspfStaticDefaultConvertEntry
         ACCESS  not-accessible
         STATUS  mandatory
         DESCRIPTION
            "An entry in the OSPF Static Default Convert Table. To set 
            an entry, all the objects in this entry must be supplied within 
            a single SET PDU"
         INDEX { ospfStaticDefaultConvertTOS,
                 ospfStaticDefaultConvertHop }
         ::= { ospfStaticDefaultConvertTable 1 }

     OspfStaticDefaultConvertEntry ::= SEQUENCE {
         ospfStaticDefaultConvertTOS
             TOSType,
         ospfStaticDefaultConvertHop
             INTEGER,
         ospfStaticDefaultConvertMetric
             BigMetric,
         ospfStaticDefaultConvertStatus
             Validation
         }

     ospfStaticDefaultConvertTOS  OBJECT-TYPE
         SYNTAX  TOSType
         ACCESS  read-write
         STATUS  mandatory
         DESCRIPTION
            "Type Of Service for this route."
         ::= { ospfStaticDefaultConvertEntry 1 }

     ospfStaticDefaultConvertHop  OBJECT-TYPE
         SYNTAX  INTEGER ( 0..16 )
         ACCESS  read-write
         STATUS  mandatory
         DESCRIPTION
            "The hop count measured for static routes."
         ::= { ospfStaticDefaultConvertEntry 2 }

     ospfStaticDefaultConvertMetric  OBJECT-TYPE
         SYNTAX  BigMetric
         ACCESS  read-write
         STATUS  mandatory
         DESCRIPTION
            "The metric in OSPF converted from static routes."
         ::= { ospfStaticDefaultConvertEntry 3 }

     ospfStaticDefaultConvertStatus  OBJECT-TYPE
         SYNTAX  Validation
         ACCESS  read-write
         STATUS  mandatory
         DESCRIPTION
            "This object indicates if the entry is valid or invalid."
         ::= { ospfStaticDefaultConvertEntry 4 }



     --  Retix OSPF Host Table

     --      The Host/Metric Table indicates what hosts are directly
     --      attached to the Router, and what metrics and types of
     --      service should be advertised for them.
	 --      Similar to the Host Table of OSPF V.2 MIB + Logical Port

     rtxospfHostTable  OBJECT-TYPE
         SYNTAX   SEQUENCE OF RtxospfHostEntry
         ACCESS   not-accessible
         STATUS   mandatory
         DESCRIPTION
            "The list of Hosts, and their metrics, that the router
            will advertise as host routes."
         REFERENCE
            "OSPF Version 2, Appendix C.6  Host route parameters."
         ::= { rtxospf 11 }

     rtxospfHostEntry  OBJECT-TYPE
         SYNTAX   RtxospfHostEntry
         ACCESS   not-accessible
         STATUS   mandatory
         DESCRIPTION
            "A metric to be advertised, for a given type of service,
            when a given host is reachable."
         INDEX { rtxospfHostIpAddress,
                 rtxospfHostTOS }
         ::= { rtxospfHostTable 1 }

     RtxospfHostEntry ::= SEQUENCE {
             rtxospfHostIpAddress
                 IpAddress,
             rtxospfHostTOS
                 TOSType,
             rtxospfHostMetric
                 Metric,
             rtxospfHostIf
                 INTEGER,
             rtxospfHostStatus
                 Validation
         }

     rtxospfHostIpAddress  OBJECT-TYPE
         SYNTAX   IpAddress
         ACCESS   read-write
         STATUS   mandatory
         DESCRIPTION
            "The IP Address of the Host."
         REFERENCE
            "OSPF Version 2, Appendix C.6 Host route parameters."
         ::= { rtxospfHostEntry 1 }

     rtxospfHostTOS  OBJECT-TYPE
         SYNTAX   TOSType
         ACCESS   read-write
         STATUS   mandatory
         DESCRIPTION
            "The Type of Service of the route being configured."
         REFERENCE
            "OSPF Version 2, Appendix C.6 Host route parameters."
         ::= { rtxospfHostEntry 2 }

     rtxospfHostMetric  OBJECT-TYPE
         SYNTAX   Metric
         ACCESS   read-write
         STATUS   mandatory
         DESCRIPTION
            "The Metric to be advertised."
         REFERENCE
            "OSPF Version 2, Appendix C.6 Host route parameters."
         ::= { rtxospfHostEntry 3 }

     rtxospfHostIf  OBJECT-TYPE
         SYNTAX   INTEGER
         ACCESS   read-write
         STATUS   mandatory
         DESCRIPTION
            "This variable contains the logical port 
            on which the IPAdress(Host) is reachable."
         ::= { rtxospfHostEntry 4 }

     rtxospfHostStatus  OBJECT-TYPE
         SYNTAX   Validation
         ACCESS   read-write
         STATUS   mandatory
         DESCRIPTION
            "This variable contains the validity or invalidity of
            the entry.  Setting it to 'invalid' has the effect of
            rendering it inoperative.  The internal effect (row
            removal) is implementation dependent."
         DEFVAL   { valid }
         ::= { rtxospfHostEntry 5 }


    --
    -- The Private FDDI  Group
    --

    rtxFddiStatusTable  OBJECT-TYPE
       SYNTAX  SEQUENCE OF RtxFddiStatusEntry
       ACCESS  not-accessible
       STATUS  mandatory
       DESCRIPTION
          "This table contains status and configuration information for
           a FDDI physical port."
       ::= { rtxfddi 1 }

    rtxFddiStatusEntry  OBJECT-TYPE
       SYNTAX  RtxFddiStatusEntry
       ACCESS  not-accessible
       STATUS  mandatory
       DESCRIPTION
          "An entry in the rtxFddiStatusTable."
       INDEX  { rtxFddiStatusIndex }
       ::= { rtxFddiStatusTable 1 }

    RtxFddiStatusEntry ::= SEQUENCE {
        rtxFddiStatusIndex
           INTEGER,
        rtxFddiNoOfLinkResets
           INTEGER,
        rtxFddiLastLinkResetReason
           INTEGER,
        rtxFddiTimeSinceLastLinkReset
           INTEGER,
        rtxFddiRFC1188Support
           INTEGER,
        rtxFddiPromiscuousMode
           INTEGER
        }

    rtxFddiStatusIndex  OBJECT-TYPE
       SYNTAX  INTEGER
       ACCESS  read-only
       STATUS  mandatory
       DESCRIPTION
          "This object identifies the phycial port which is a FDDI
           physical port."
       ::= { rtxFddiStatusEntry 1 }
    
    rtxFddiNoOfLinkResets  OBJECT-TYPE
       SYNTAX  INTEGER
       ACCESS  read-only
       STATUS  mandatory
       DESCRIPTION
          "This object is a count of the number of times this link has reset
           has occurred on the FDDI link, since the last reinitialisation of
           the unit."
       ::= { rtxFddiStatusEntry 2 }
    
    rtxFddiLastLinkResetReason  OBJECT-TYPE
       SYNTAX  INTEGER {
                        noReason    (1),
                        management  (2),
                        deviceReset (3),
                        cableDrop   (4),
                        protocol    (5)
                       }
       ACCESS  read-only
       STATUS  mandatory
       DESCRIPTION
          "This object gives the a reason code for the last reset which
           occurred on this FDDI physical link.  A value of noReason(1)
           is returned if the link has not reset. A value of management(2)
           is returned when a link reset has been caused by a management
           protocol (either SNMP or by LMS). A value of deviceReset(3)
           is returned if the link reset was caused by a hardware failure.
           A value of cableDrop(4) is returned when the link reset was
           caused by a missing or faulty cable. A value of protocol(5) is
           returned when the link reset is caues by the link protocol which
           is running on this link e.g. a Disconnet Request etc."
       ::= { rtxFddiStatusEntry 3 }
    
    rtxFddiTimeSinceLastLinkReset  OBJECT-TYPE
       SYNTAX  INTEGER
       ACCESS  read-only
       STATUS  mandatory
       DESCRIPTION
          "This is a time (in hundredths of seconds) since the last link
            reset"
       ::= { rtxFddiStatusEntry 4 }
    
    rtxFddiRFC1188Support  OBJECT-TYPE
       SYNTAX  INTEGER {
                        supported (1),
                        notSupported (2)
                       }
       ACCESS  read-write
       STATUS  mandatory
       DESCRIPTION
          "This object is used to indicate if this instance of the FDDI
           protocol supports RFC1188 compliance. If this support is not
           required then the object is set to a value of notSupported(2)."
       DEFVAL { supported }
       ::= { rtxFddiStatusEntry 5 }
    
    rtxFddiPromiscuousMode  OBJECT-TYPE
       SYNTAX  INTEGER {
                        enabled (1),
                        disabled (2)
                       }
       ACCESS  read-write
       STATUS  mandatory
       DESCRIPTION
          ""
       DEFVAL { enabled }
       ::= { rtxFddiStatusEntry 6 }

    --
    -- The Retix Private PPP objects
    --

          rtxPPPConfigTable  OBJECT-TYPE
               SYNTAX  SEQUENCE OF RtxPPPConfigEntry
               ACCESS  not-accessible
               STATUS  mandatory
               DESCRIPTION
                  "This is a table of the configuration objects which are
                   the Retix Extensions to the standard PPP mib."
               ::= { rtxppp 1 }

          rtxPPPConfigEntry  OBJECT-TYPE
               SYNTAX  RtxPPPConfigEntry
               ACCESS  not-accessible
               STATUS  mandatory
               DESCRIPTION
                   "An entry in the table."
               INDEX  { pppConfigIfIndex }
               ::= { rtxPPPConfigTable 1 }

          RtxPPPConfigEntry ::= SEQUENCE {
               pppConfigIfIndex
                  INTEGER,
               pppRestartTimer
                  INTEGER,
               pppMaxTerminate
                  INTEGER,
               pppMaxConfigure
                  INTEGER, 
               pppMaxFailure
                  INTEGER, 
               pppEchoTest
                  INTEGER 
               }

          pppConfigIfIndex  OBJECT-TYPE
               SYNTAX  INTEGER
               ACCESS  read-only
               STATUS  mandatory
               DESCRIPTION
                  "The interface number. This number is numerically equal
                   to the physical port ID (portPhysPortID)."
               ::= { rtxPPPConfigEntry 1 }

          pppRestartTimer  OBJECT-TYPE
               SYNTAX  INTEGER
               ACCESS  read-write
               STATUS  mandatory
               DESCRIPTION
                  "This object shows the current value of the Restart
                   Timer. This is the timer which is used in retransmission
                   Configure Request or Terminate Request packets."
               ::= { rtxPPPConfigEntry 2 }

          pppMaxTerminate  OBJECT-TYPE
               SYNTAX  INTEGER
               ACCESS  read-write
               STATUS  mandatory
               DESCRIPTION
                  "This object shows the maximum retry count for sending a
                   Terminate Request packet without receiving a Terminate Ack."
               ::= { rtxPPPConfigEntry 3 }

          pppMaxConfigure  OBJECT-TYPE
               SYNTAX  INTEGER
               ACCESS  read-write
               STATUS  mandatory
               DESCRIPTION
                  "This object shows the maximum retry count for sending a
                   Configure Request packet without receiving a Configure Ack,
                   or Configure Nak, or Configure Reject Packet. If set to 
                   zero, then the protocol will keep retrying forever." 
               ::= { rtxPPPConfigEntry 4 }

          pppMaxFailure  OBJECT-TYPE
               SYNTAX  INTEGER
               ACCESS  read-write
               STATUS  mandatory
               DESCRIPTION
                  "This object shows the maximum retry count for sending a
                   Configure Nak without sending a Configure Ack packet."
               ::= { rtxPPPConfigEntry 5 }

          pppEchoTest  OBJECT-TYPE
               SYNTAX  INTEGER {
                       enable (1),
                       disable (2)
                       }
               ACCESS  read-write
               STATUS  mandatory
               DESCRIPTION
                  "By setting this object, a test pattern will be
                   generated and sent to the peer. An echo reply
                   will be expected from the peer. To begin the
                   test,  a SET will enable the process; otherwise
                   a disable is returned. Currently, the test pattern
                   is configured internally, and is fixed. The length
                   of the test packet is equal to the negotiated packet
                   length between the peers."
               ::= { rtxPPPConfigEntry 6 }


         rtxPPPStatsTable  OBJECT-TYPE
               SYNTAX  SEQUENCE OF RtxPPPStatsEntry
               ACCESS  not-accessible
               STATUS  mandatory
               DESCRIPTION
                  "This is a table of the statistics objects which are
                   the Retix Extensions to the standard PPP mib."
               ::= { rtxppp 2 }

          rtxPPPStatsEntry  OBJECT-TYPE
               SYNTAX  RtxPPPStatsEntry
               ACCESS  not-accessible
               STATUS  mandatory
               DESCRIPTION
                   "An entry in the table."
               INDEX  { pppStatsIfIndex }
               ::= { rtxPPPStatsTable 1 }

          RtxPPPStatsEntry ::= SEQUENCE {
               pppStatsIfIndex
                  INTEGER,
               pppInvalidTransmitFrames
                  INTEGER,
               pppInvalidReceivedFrames
                  INTEGER,
               pppTotalTransmitFrames
                  INTEGER,
               pppTotalReceivedFrames
                  INTEGER,
               pppTotalTransmitOctets
                  INTEGER,
               pppTotalReceivedOctets
                  INTEGER,
               pppTotalTransmitEchoPackets
                  INTEGER,
               pppTotalReceivedEchoPackets
                  INTEGER,
               pppTotalReceivedGoodEchoPackets
                  INTEGER
               }

         pppStatsIfIndex  OBJECT-TYPE
               SYNTAX  INTEGER
               ACCESS  read-only
               STATUS  mandatory
               DESCRIPTION
                  "The interface number which corresponds to the physical
                  port number."
               ::= { rtxPPPStatsEntry 1 }

          pppInvalidTransmitFrames  OBJECT-TYPE
               SYNTAX  INTEGER
               ACCESS  read-only
               STATUS  mandatory
               DESCRIPTION
                  "This object is a count of the number of frames which were
                   not transmitted successfull."
               ::= { rtxPPPStatsEntry 2 }

          pppInvalidReceivedFrames  OBJECT-TYPE
               SYNTAX  INTEGER
               ACCESS  read-only
               STATUS  mandatory
               DESCRIPTION
                  "This object is a count of the number of frames which were
                   received in error."
               ::= { rtxPPPStatsEntry 3 }

         pppTotalTransmitFrames  OBJECT-TYPE
               SYNTAX  INTEGER
               ACCESS  read-only
               STATUS  mandatory
               DESCRIPTION
                  "This object is a count of the number of frames which have
                   been transmitted successfully, or unsuccessfully."
               ::= { rtxPPPStatsEntry 4 }

          pppTotalReceivedFrames  OBJECT-TYPE
               SYNTAX  INTEGER
               ACCESS  read-only
               STATUS  mandatory
               DESCRIPTION
                  "This object is a count of the number of frames which were
                   received successfully, or unsuccessfully."
               ::= { rtxPPPStatsEntry 5 }

          pppTotalTransmitOctets  OBJECT-TYPE
               SYNTAX  INTEGER
               ACCESS  read-only
               STATUS  mandatory
               DESCRIPTION
                  "This object is a count of the number of octets which were
                   transmitted successfully, or unsuccessfully."
               ::= { rtxPPPStatsEntry 6 }

          pppTotalReceivedOctets  OBJECT-TYPE
               SYNTAX  INTEGER
               ACCESS  read-only
               STATUS  mandatory
               DESCRIPTION
                  "This object is a count of the number of octets which were
                   received successfully, or unsuccessfully."
               ::= { rtxPPPStatsEntry 7 }

         pppTotalTransmitEchoPackets  OBJECT-TYPE
               SYNTAX  INTEGER
               ACCESS  read-only
               STATUS  mandatory
               DESCRIPTION
                  "This object is a count of the number of echo packets which
                   were transmitted successfully, or unsuccessfully."
               ::= { rtxPPPStatsEntry 8 }

          pppTotalReceivedEchoPackets  OBJECT-TYPE
               SYNTAX  INTEGER
               ACCESS  read-only
               STATUS  mandatory
               DESCRIPTION
                  "This object is a count of the number of echo packets which
                   were received with a positive or negative results"
               ::= { rtxPPPStatsEntry 9 }

          pppTotalReceivedGoodEchoPackets  OBJECT-TYPE
               SYNTAX  INTEGER
               ACCESS  read-only
               STATUS  mandatory
               DESCRIPTION
                  "This object is a count of the number of echo packets which
                   were received with a positive result"
               ::= { rtxPPPStatsEntry 10 }


    --
    --  Retix Private ATM MIB
    --
      
      atmRtxAtmLayerTable  OBJECT-TYPE
          SYNTAX  SEQUENCE OF AtmRtxAtmLayerEntry
          ACCESS  not-accessible
          STATUS  mandatory
          DESCRIPTION
              "A table of ATM layer status and parameter information for
              the UNI's physical interface"
          ::= { atmRtxAtmLayerGroup 1 }
                                               
       atmRtxAtmLayerEntry  OBJECT-TYPE
           SYNTAX  AtmRtxAtmLayerEntry
           ACCESS  not-accessible
           STATUS  mandatory
           DESCRIPTION
               "A entry in the table"
           INDEX  { atmRtxAtmLayerIndex }
           ::= { atmRtxAtmLayerTable 1 }
                
    AtmRtxAtmLayerEntry ::= SEQUENCE {
        atmRtxAtmLayerIndex
            INTEGER,
        atmRtxAtmLayerMaxLANs -- pcif.pc_num_lans
            INTEGER,
        atmRtxAtmLayerConfiguredLANs
            INTEGER,
        atmRtxAtmLayerActiveLANs
            INTEGER,
        atmRtxAtmLayerMaxVCs -- pcif->pc_net_max_vcs
             INTEGER,
        atmRtxAtmLayerActiveVCs
            INTEGER,
        atmRtxAtmLayerLinkOutPeakRate -- pcif.pc_opeak_rate
            INTEGER,
        atmRtxAtmLayerLinkInPeakRate -- pcif.pc_ipeak_rate
            INTEGER,
        atmRtxAtmLayerLastResetReason
            INTEGER
        }
                         
      atmRtxAtmLayerIndex  OBJECT-TYPE
         SYNTAX  INTEGER (0..2147483647)
         ACCESS  read-only
         STATUS  mandatory
         DESCRIPTION
             "A unique value which identifies this port.  The value of 0 has
             the special meaning of identifying the local UNI"
         ::= { atmRtxAtmLayerEntry 1 }
    
    atmRtxAtmLayerMaxLANs  OBJECT-TYPE
         SYNTAX  INTEGER (0..16)
         ACCESS  read-only
         STATUS  mandatory
         DESCRIPTION
            "Mamimum number of ATM LANs."
         ::= { atmRtxAtmLayerEntry 2 }
    
     atmRtxAtmLayerConfiguredLANs  OBJECT-TYPE
         SYNTAX  INTEGER (1..16)
         ACCESS  read-write
        STATUS  mandatory
        DESCRIPTION
            "Number of configured ATM LANs."
        ::= { atmRtxAtmLayerEntry 3 }

    atmRtxAtmLayerActiveLANs  OBJECT-TYPE
        SYNTAX  INTEGER (0..16)
        ACCESS  read-only
        STATUS  mandatory
        DESCRIPTION
            "Number of active ATM LANs."
        ::= { atmRtxAtmLayerEntry 4 }

    atmRtxAtmLayerMaxVCs  OBJECT-TYPE
        SYNTAX  INTEGER (0..200000)
        ACCESS  read-only
        STATUS  mandatory
        DESCRIPTION
            "Mamimum number of vitual circuits allowed."
        ::= { atmRtxAtmLayerEntry 5 }

    atmRtxAtmLayerActiveVCs  OBJECT-TYPE
        SYNTAX  INTEGER (0..200000)
        ACCESS  read-only
        STATUS  mandatory
        DESCRIPTION
            "Number of active vitual circuits."
        ::= { atmRtxAtmLayerEntry 6 }

    atmRtxAtmLayerLinkOutPeakRate   OBJECT-TYPE
        SYNTAX  INTEGER (0..2147483647)
        ACCESS  read-only
        STATUS  mandatory
        DESCRIPTION
            "Link output peak rate."
        ::= { atmRtxAtmLayerEntry 7 }

    atmRtxAtmLayerLinkInPeakRate   OBJECT-TYPE
        SYNTAX  INTEGER (0..2147483647)
        ACCESS  read-only
        STATUS  mandatory
        DESCRIPTION
            "Link input peak rate."
        ::= { atmRtxAtmLayerEntry 8 }
    
    atmRtxAtmLayerLastResetReason   OBJECT-TYPE
        SYNTAX  INTEGER (0..100)
        ACCESS  read-only
        STATUS  mandatory
        DESCRIPTION
            "The reason the ATM signaling VC goes down last time."
        ::= { atmRtxAtmLayerEntry 9 }
    
    atmRtxAtmStatsTable  OBJECT-TYPE
        SYNTAX  SEQUENCE OF AtmRtxAtmStatsEntry
        ACCESS  not-accessible
        STATUS  mandatory
        DESCRIPTION
            "A table of ATM layer statistics information for
            the UNI's physical interface."
        ::= { atmRtxAtmStatsGroup 1 }
    
    atmRtxAtmStatsEntry  OBJECT-TYPE
        SYNTAX  AtmRtxAtmStatsEntry
        ACCESS  not-accessible
        STATUS  mandatory
        DESCRIPTION
            "A entry in the table, containing statistics for the 
            ATM layer of a UNI interface"
        INDEX { atmRtxAtmStatsIndex }
        ::= { atmRtxAtmStatsTable 1 }
    
    AtmRtxAtmStatsEntry ::= SEQUENCE {
        atmRtxAtmStatsIndex
            INTEGER,
        atmRtxAtmStatsTxUnicastFrames
            Counter,
        atmRtxAtmStatsRxUnicastFrames
            Counter,
        atmRtxAtmStatsTxMulticastFrames
            Counter,
        atmRtxAtmStatsRxMulticastFrames
            Counter,
        atmRtxAtmStatsTxBroadcastFrames
            Counter,
        atmRtxAtmStatsRxBroadcastFrames
            Counter,
        atmRtxAtmStatsDroppedTxFrames
            Counter,
        atmRtxAtmStatsDroppedRxFrames
            Counter,
        atmRtxAtmStatsRxErrorFrames
            Counter,
        atmRtxAtmStatsRxBETagFrames
            Counter,
        atmRtxAtmStatsChipDroppedRxFrames
            Counter,
        atmRtxAtmStatsTxCells
            Counter,
        atmRtxAtmStatsRxCells
            Counter,
        atmRtxAtmStatsRxErrorCells
            Counter,
        atmRtxAtmStatsRxOosCells
            Counter,
        atmRtxAtmStatsRxXoffCells
            Counter,
        atmRtxAtmStatsFifoFullRxFrames
            Counter
        }
    
    atmRtxAtmStatsIndex  OBJECT-TYPE
        SYNTAX  INTEGER (0..2147483647)
        ACCESS  read-only
        STATUS  mandatory
        DESCRIPTION
        "A unique value which identifies this port.  The value of 0 has
        the special meaning of identifying the local UNI"
        ::= { atmRtxAtmStatsEntry 1 }

    atmRtxAtmStatsTxUnicastFrames  OBJECT-TYPE
        SYNTAX  Counter
        ACCESS  read-only
        STATUS  mandatory
        DESCRIPTION
            "Number of transmitted unicast frames."
        ::= { atmRtxAtmStatsEntry 2 }

    atmRtxAtmStatsRxUnicastFrames  OBJECT-TYPE
        SYNTAX  Counter
        ACCESS  read-only
        STATUS  mandatory
        DESCRIPTION
            "Number of received unicast frames."
        ::= { atmRtxAtmStatsEntry 3 }

    atmRtxAtmStatsTxMulticastFrames  OBJECT-TYPE
        SYNTAX  Counter
        ACCESS  read-only
        STATUS  mandatory
        DESCRIPTION
            "Number of transmitted multicast frames."
        ::= { atmRtxAtmStatsEntry 4 }

    atmRtxAtmStatsRxMulticastFrames  OBJECT-TYPE
        SYNTAX  Counter
        ACCESS  read-only
        STATUS  mandatory
        DESCRIPTION
            "Number of received multicast frames."
        ::= { atmRtxAtmStatsEntry 5 }

    atmRtxAtmStatsTxBroadcastFrames  OBJECT-TYPE
        SYNTAX  Counter
        ACCESS  read-only
        STATUS  mandatory
        DESCRIPTION
            "Number of transmitted broadcast frames."
        ::= { atmRtxAtmStatsEntry 6 }

    atmRtxAtmStatsRxBroadcastFrames  OBJECT-TYPE
        SYNTAX  Counter
        ACCESS  read-only
        STATUS  mandatory
        DESCRIPTION
            "Number of received broadcast frames."
        ::= { atmRtxAtmStatsEntry 7 }

    atmRtxAtmStatsDroppedTxFrames  OBJECT-TYPE
        SYNTAX  Counter
        ACCESS  read-only
        STATUS  mandatory
        DESCRIPTION
            "Number of transmitted frames dropped by software."
        ::= { atmRtxAtmStatsEntry 8 }

    atmRtxAtmStatsDroppedRxFrames  OBJECT-TYPE
        SYNTAX  Counter
        ACCESS  read-only
        STATUS  mandatory
        DESCRIPTION
            "Number of received frames dropped by software."
        ::= { atmRtxAtmStatsEntry 9 }

    atmRtxAtmStatsRxErrorFrames  OBJECT-TYPE
        SYNTAX  Counter
        ACCESS  read-only
        STATUS  mandatory
        DESCRIPTION
         "Number of received frames with error (other than mismatched BE Tags)."
        ::= { atmRtxAtmStatsEntry 10 }

    atmRtxAtmStatsRxBETagFrames  OBJECT-TYPE
        SYNTAX  Counter
        ACCESS  read-only
        STATUS  mandatory
        DESCRIPTION
            "Number of received frames with mismatched BE Tags."
        ::= { atmRtxAtmStatsEntry 11 }

    atmRtxAtmStatsChipDroppedRxFrames  OBJECT-TYPE
        SYNTAX  Counter
        ACCESS  read-only
        STATUS  mandatory
        DESCRIPTION
            "Number of received frames dropped by chip(hardware)."
        ::= { atmRtxAtmStatsEntry 12 }

    atmRtxAtmStatsTxCells  OBJECT-TYPE
        SYNTAX  Counter
        ACCESS  read-only
        STATUS  mandatory
        DESCRIPTION
            "Number of transmitted cells."
        ::= { atmRtxAtmStatsEntry 13 }

    atmRtxAtmStatsRxCells  OBJECT-TYPE
        SYNTAX  Counter
        ACCESS  read-only
        STATUS  mandatory
        DESCRIPTION
            "Number of received cells."
        ::= { atmRtxAtmStatsEntry 14 }

    atmRtxAtmStatsRxErrorCells  OBJECT-TYPE
        SYNTAX  Counter
        ACCESS  read-only
        STATUS  mandatory
        DESCRIPTION
            "Number of received cells with error."
        ::= { atmRtxAtmStatsEntry 15 }

    atmRtxAtmStatsRxOosCells  OBJECT-TYPE
        SYNTAX  Counter
        ACCESS  read-only
        STATUS  mandatory
        DESCRIPTION
            "Number of out-of-sequence cells received."
        ::= { atmRtxAtmStatsEntry 16 }

    atmRtxAtmStatsRxXoffCells  OBJECT-TYPE
        SYNTAX  Counter
        ACCESS  read-only
        STATUS  mandatory
        DESCRIPTION
            "Number of received XOFF cells."
        ::= { atmRtxAtmStatsEntry 17 }

    atmRtxAtmStatsFifoFullRxFrames  OBJECT-TYPE
        SYNTAX  Counter
        ACCESS  read-only
        STATUS  mandatory
        DESCRIPTION
            "Number of received FIFO is full."
        ::= { atmRtxAtmStatsEntry 18 }
    
    --
    --   Virtual Circuits
    --
    
    atmRtxVcTable  OBJECT-TYPE
        SYNTAX  SEQUENCE OF AtmRtxVcEntry
        ACCESS  not-accessible
        STATUS  mandatory
        DESCRIPTION
            "A table of status and parameter information on the virtual
            connections which are visible at this UNI."
        ::= { atmRtxVcGroup 1 }
    
    atmRtxVcEntry  OBJECT-TYPE
        SYNTAX  AtmRtxVcEntry
        ACCESS  not-accessible
        STATUS  mandatory
        DESCRIPTION
            "A entry in the table, containing information about a
            particular virtual connection."
        INDEX  { atmRtxVcPortIndex, atmRtxVcInVpci }
        ::= { atmRtxVcTable 1 }
    
    AtmRtxVcEntry ::= SEQUENCE {
        atmRtxVcPortIndex
            INTEGER,
        atmRtxVcInVpci
            INTEGER,
        atmRtxVcOutVpci
            INTEGER,
        atmRtxVcLgclPortIndex
            INTEGER,
        atmRtxVcLocalPortAddress
            AtmAddress,
        atmRtxVcPeerPortAddress
            AtmAddress,
        atmRtxVcOutPeakRate
            INTEGER,
        atmRtxVcOperStatus   -- vcte.vcte_state == VCS_ESTAB ? e2eup : e2edown
            INTEGER
        }
    
    atmRtxVcPortIndex  OBJECT-TYPE
        SYNTAX  INTEGER (0..2147483647)
        ACCESS  read-only
        STATUS  mandatory
        DESCRIPTION
            "A unique value which identifies this port.  The value of 0 has
            the special meaning of identifying the local UNI"
        ::= { atmRtxVcEntry 1 }
    
    atmRtxVcInVpci  OBJECT-TYPE
        SYNTAX  INTEGER (0..16777215)
        ACCESS  read-only
        STATUS  mandatory
        DESCRIPTION
            "The VPCI value of this Virtual Connection at the local UNI."
        ::= { atmRtxVcEntry 2 }
    
    atmRtxVcOutVpci  OBJECT-TYPE
        SYNTAX  INTEGER (0..16777215)
        ACCESS  read-only
        STATUS  mandatory
        DESCRIPTION
            "The VPCI used for transmission."
        ::= { atmRtxVcEntry 3 }
    
    atmRtxVcLgclPortIndex  OBJECT-TYPE
        SYNTAX  INTEGER (0..2147483647)
        ACCESS  read-only
        STATUS  mandatory
        DESCRIPTION
            "A unique value which identifies the logical port to which
            this vc belong"
        ::= { atmRtxVcEntry 4 }
    
    atmRtxVcLocalPortAddress  OBJECT-TYPE
        SYNTAX  AtmAddress
        ACCESS  read-only
        STATUS  mandatory
        DESCRIPTION
            "Local ATM Port address."
        ::= { atmRtxVcEntry 5 }
    
    atmRtxVcPeerPortAddress  OBJECT-TYPE
        SYNTAX  AtmAddress
        ACCESS  read-only
        STATUS  mandatory
        DESCRIPTION
            "Peer ATM Port address."
        ::= { atmRtxVcEntry 6 }
    
    atmRtxVcOutPeakRate   OBJECT-TYPE
        SYNTAX  INTEGER (0..2147483647)
        ACCESS  read-only
        STATUS  mandatory
        DESCRIPTION
            "Output peak rate."
        ::= { atmRtxVcEntry 7 }
        
    atmRtxVcOperStatus  OBJECT-TYPE
        SYNTAX  INTEGER {
                closed(1),
                wsr(2),
                wc(3),
                wcact(4),
                estab(5),
                wrc(6),
                inactive(7),
                wgrc(8),
                war(9),
                active(10)
                }
        ACCESS  read-only
        STATUS  mandatory
        DESCRIPTION
            "The present actual operational status of the VC."
        ::= { atmRtxVcEntry 8 }
    
    --
    --   Virtual Circuits Statistics
    --
    
    atmRtxVcStatsTable  OBJECT-TYPE
        SYNTAX  SEQUENCE OF AtmRtxVcStatsEntry
        ACCESS  not-accessible
        STATUS  mandatory
        DESCRIPTION
            "A table of statistics on the virtual
            connections which are visible at this UNI."
        ::= { atmRtxVcStatsGroup 1 }
    
    atmRtxVcStatsEntry  OBJECT-TYPE
        SYNTAX  AtmRtxVcStatsEntry
        ACCESS  not-accessible
        STATUS  mandatory
        DESCRIPTION
            "A entry in the table, containing statistics about a
            particular virtual connection."
        INDEX  { atmRtxVcStatsPortIndex, atmRtxVcStatsInVpci }
        ::= { atmRtxVcStatsTable 1 }
    
    AtmRtxVcStatsEntry ::= SEQUENCE {
        atmRtxVcStatsPortIndex
            INTEGER,
        atmRtxVcStatsInVpci
            INTEGER,
        atmRtxVcStatsLgclPortIndex
            INTEGER,
        atmRtxVcStatsReceivedPkts
            Counter,
        atmRtxVcStatsTransmittedPkts
            Counter,
        atmRtxVcStatsTimeouts -- vcte.vcte_timeouts
            Counter
        }
    
    atmRtxVcStatsPortIndex  OBJECT-TYPE
        SYNTAX  INTEGER (0..2147483647)
        ACCESS  read-only
        STATUS  mandatory
        DESCRIPTION
            "A unique value which identifies this port.  The value of 0 has
            the special meaning of identifying the local UNI"
        ::= { atmRtxVcStatsEntry 1 }
    
    atmRtxVcStatsInVpci  OBJECT-TYPE
        SYNTAX  INTEGER (0..16777215)
        ACCESS  read-only
        STATUS  mandatory
        DESCRIPTION
            "The VCI value of this Virtual Connection at the local UNI."
        ::= { atmRtxVcStatsEntry 2 }
    
    atmRtxVcStatsLgclPortIndex  OBJECT-TYPE
        SYNTAX  INTEGER (0..2147483647)
        ACCESS  read-only
        STATUS  mandatory
        DESCRIPTION
            "A unique value which identifies the logical port to which
            this vc belong"
        ::= { atmRtxVcStatsEntry 3 }
    
    atmRtxVcStatsReceivedPkts  OBJECT-TYPE
        SYNTAX  Counter
        ACCESS  read-only
        STATUS  mandatory
        DESCRIPTION
            "Number of received packtets on this virtual circuit."
        ::= { atmRtxVcStatsEntry 4 }
    
    atmRtxVcStatsTransmittedPkts  OBJECT-TYPE
        SYNTAX  Counter
        ACCESS  read-only
        STATUS  mandatory
        DESCRIPTION
            "Number of transmitted packtets on this virtual circuit."
        ::= { atmRtxVcStatsEntry 5 }
    
    atmRtxVcStatsTimeouts  OBJECT-TYPE
        SYNTAX  Counter
        ACCESS  read-only
        STATUS  mandatory
        DESCRIPTION
            "Number of timeouts of this virtual circuit."
        ::= { atmRtxVcStatsEntry 6 }

   
    atmRtxPVCLayerTable OBJECT-TYPE
        SYNTAX  SEQUENCE OF AtmRtxPVCLayerEntry
        ACCESS  not-accessible
        STATUS  mandatory
        DESCRIPTION
            "A table of ATM/PVC layer status and parameter information for
            the UNI's physical interface"
        ::= { atmRtxPVCLayerGroup 1 }
    
    atmRtxPVCLayerEntry OBJECT-TYPE
        SYNTAX  AtmRtxPVCLayerEntry
        ACCESS  not-accessible
        STATUS  mandatory
        DESCRIPTION
            "A entry in the table"
        INDEX  { atmRtxPVCLayerIndex }
        ::= { atmRtxPVCLayerTable 1 }
    
    AtmRtxPVCLayerEntry ::= SEQUENCE {
        atmRtxPVCLayerIndex
            INTEGER,
        atmRtxPVCLayerPVCcount
            INTEGER,
        atmRtxPVCLayerMaxPVCs
            INTEGER,
        atmRtxPVCLayerLinkOutPeakRate -- pcif.pc_opeak_rate
            INTEGER,
        atmRtxPVCLayerLinkInPeakRate -- pcif.pc_ipeak_rate
            INTEGER,
        atmRtxPVCLayerLastResetReason
            INTEGER,
        atmRtxPVCLayerVirtualPathId
            INTEGER
        }
    
    atmRtxPVCLayerIndex  OBJECT-TYPE
        SYNTAX  INTEGER (0..2147483647)
        ACCESS  read-only
        STATUS  mandatory
        DESCRIPTION
            "A unique value which identifies this port.  The value of 0 has
            the special meaning of identifying the local UNI"
        ::= { atmRtxPVCLayerEntry 1 }
    
    atmRtxPVCLayerPVCcount  OBJECT-TYPE
        SYNTAX  INTEGER
        ACCESS  read-only
        STATUS  mandatory
        DESCRIPTION
        " Number Of Permanent Virtual Circuits"
        ::= { atmRtxPVCLayerEntry 2 }
    
    atmRtxPVCLayerMaxPVCs  OBJECT-TYPE
        SYNTAX  INTEGER (0..16)
        ACCESS  read-only
        STATUS  mandatory
        DESCRIPTION
            "Maximum number of permanent vitual circuits."
        ::= { atmRtxPVCLayerEntry 3 }
    
    atmRtxPVCLayerLinkOutPeakRate   OBJECT-TYPE
        SYNTAX  INTEGER (0..2147483647)
        ACCESS  read-only
        STATUS  mandatory
        DESCRIPTION
            "Link output peak rate."
        ::= { atmRtxPVCLayerEntry 4 }
    
    atmRtxPVCLayerLinkInPeakRate   OBJECT-TYPE
        SYNTAX  INTEGER (0..2147483647)
        ACCESS  read-only
        STATUS  mandatory
        DESCRIPTION
            "Link input peak rate."
        ::= { atmRtxPVCLayerEntry 5 }
    
    atmRtxPVCLayerLastResetReason   OBJECT-TYPE
        SYNTAX  INTEGER (0..100)
        ACCESS  read-only
        STATUS  mandatory
        DESCRIPTION
            "The reason the ATM signaling VC goes down last time."
        ::= { atmRtxPVCLayerEntry 6 }

     atmRtxPVCLayerVirtualPathId   OBJECT-TYPE
          SYNTAX  INTEGER (0..255)
          ACCESS  read-write
          STATUS  mandatory
          DESCRIPTION
              "Indicates the number of Virtual Path Identifier configured
               for each logical port on this interface."
          ::= { atmRtxPVCLayerEntry 7 }

  
    
    --
    -- Token Ring (Source Routing) Private Objects
    --
    
      srtBridgeNumber  OBJECT-TYPE
          SYNTAX  INTEGER 
          ACCESS  read-write
          STATUS  mandatory
          DESCRIPTION
             "A bridge number uniquely identifies a bridge when more than
              one bridge is used to span the same segments. This object
              can have values between 0..15 inclusive and also a value 65535.
              When set to 65535, source routing on the unit is DISABLED."
          DEFVAL  { 65535 }
          ::= { rtxsrt 1 }

      srtPortTable  OBJECT-TYPE
          SYNTAX  SEQUENCE OF SrtPortEntry 
          ACCESS  not-accessible
          STATUS  mandatory
          DESCRIPTION
             "Table of Source Routing per Port parameters. "
          ::= { rtxsrt 2 }
           
      srtPortEntry  OBJECT-TYPE
          SYNTAX  SrtPortEntry 
          ACCESS  not-accessible
          STATUS  mandatory
          DESCRIPTION
             "Entries of Table of Source Routing per logical port parameters. "
          INDEX  { srtPortIfIndex }
          ::= { srtPortTable 1 }

      SrtPortEntry  ::= SEQUENCE {
          srtPortIfIndex
              INTEGER,
          srtPortSecurityMode
              INTEGER,
          srtPortSrcAddrFiltering
              INTEGER,
          srtPortCustomFiltering
              INTEGER,
          srtProcessForRIFInsertion
              INTEGER,
          srtProcessForSourceRoute
              INTEGER
          }

      srtPortIfIndex  OBJECT-TYPE
          SYNTAX  INTEGER 
          ACCESS  read-only
          STATUS  mandatory
          DESCRIPTION
             "The logical port number corresponding to the value of ifIndex."
          ::= { srtPortEntry 1 }

      srtPortSecurityMode  OBJECT-TYPE
          SYNTAX  INTEGER  {
                  enable (1),
                  disable (2)
                  }
          ACCESS  read-write
          STATUS  mandatory
          DESCRIPTION
             "Disable/Enable filtering on frame destination address for
          source routed frames."
          DEFVAL  { disable }
          ::= { srtPortEntry 2 }


      srtPortSrcAddrFiltering  OBJECT-TYPE
          SYNTAX  INTEGER {
                enable (1),
                disable (2)
              }
          ACCESS  read-write
          STATUS  mandatory
          DESCRIPTION
             "Disable/Enable source address filtering for source routed frames."
          DEFVAL  { disable }
          ::= { srtPortEntry 3 }


      srtPortCustomFiltering  OBJECT-TYPE
          SYNTAX  INTEGER  {
                  enable (1),
                  disable (2)
                  }
          ACCESS  read-write
          STATUS  mandatory
          DESCRIPTION
             "Disable/Enable custom filtering for source routed frames. Note
             that both Source Routing and Transparent Bridging use the same
             Custom Filter Tables, but are enabled to use Custom Filtering 
             separately"
          DEFVAL  { disable }
          ::= { srtPortEntry 4 }

     srtProcessForRIFInsertion  OBJECT-TYPE
        SYNTAX  INTEGER  {
                 enable (1),
                 disable (2)
                 }
        ACCESS  read-write
        STATUS  mandatory
        DESCRIPTION
            "If this object has the value enable(1), then the ring driver
             for the token ring port to which this logical port is attached
             will, in appropriate cases, insert a Routing Information Field
             into the frame to be transmitted."
        ::= { srtPortEntry 5 } 
 
     srtProcessForSourceRoute  OBJECT-TYPE
        SYNTAX  INTEGER  {
                 enable (1),
                 disable (2)
                 }
        ACCESS  read-write
        STATUS  mandatory
        DESCRIPTION
            "If this object has the value enable(1), token ring frames
             originated by the RX7000 or bridged via translational bridging
             will be sebt according to th rule set used by the Source Route
             Manager. If this object has a value of disable(2), token ring
             frames originated by the RX7000 will always be sent as
             transparent frames."
        ::= { srtPortEntry 6 }

    -- the Source Route Manager objects

    rtxSourceRouteVirtRingNum  OBJECT-TYPE
        SYNTAX  INTEGER (0..4095)
        ACCESS  read-write
        STATUS  mandatory
        DESCRIPTION
            "This parameter defines the Virtual ring number for this unit.
             This number is used by the  Source Route Manager. This number 
             is added to the RIF of frames processed by the Source Route
             Manager."
        DEFVAL { 0 }
        ::= { rtxsrt 3 }

    rtxSourceRouteAgingTime  OBJECT-TYPE
        SYNTAX  INTEGER (10..3600)
        ACCESS  read-write
        STATUS  mandatory
        DESCRIPTION
            "If no frames from a source are received for this time, 
             any associated routing information in the Source Route Table 
             is purged. The granularity is seconds."
        DEFVAL { 300 }
        ::= { rtxsrt 4 }

    rtxSourceRouteTable  OBJECT-TYPE
        SYNTAX  SEQUENCE OF RtxSourceRouteEntry
        ACCESS  not-accessible
        STATUS  mandatory
        DESCRIPTION
            "This table contains a list of stored destination address and 
             the routing information fields which will be inserted in 
             frames sent to those destinations."
        ::= { rtxsrt 5 }

    rtxSourceRouteEntry  OBJECT-TYPE
        SYNTAX  RtxSourceRouteEntry
        ACCESS  not-accessible
        STATUS  mandatory
        DESCRIPTION
            "An source route entry."
        INDEX  { rtxSourceRouteSlotID, rtxSourceRouteAddress }
        ::= { rtxSourceRouteTable 1 }
                                     
    RtxSourceRouteEntry  ::= SEQUENCE {
        rtxSourceRouteSlotID
            INTEGER,
        rtxSourceRouteAddress
            OCTET STRING,
        rtxSourceRouteRIF
            OCTET STRING,
        rtxSourceRouteType
            INTEGER,
        rtxSourceRouteDirection
            INTEGER
        }

    rtxSourceRouteSlotID  OBJECT-TYPE
        SYNTAX  INTEGER
        ACCESS  read-only
        STATUS  mandatory
        DESCRIPTION
            "This identifies the FP from which this entry originated."
        ::= { rtxSourceRouteEntry 1 }

    rtxSourceRouteAddress  OBJECT-TYPE
        SYNTAX  OCTET STRING (SIZE(6))
        ACCESS  read-only
        STATUS  mandatory
        DESCRIPTION
            "This is the source address which was stored when the
             Source Routing frame which contained it was processed by the
             Source Route Manager. The address is in the form it was 
             received from the ring network."
        ::= { rtxSourceRouteEntry 2 }

    rtxSourceRouteRIF  OBJECT-TYPE
        SYNTAX  OCTET STRING (SIZE(0..18))
        ACCESS  read-only
        STATUS  mandatory
        DESCRIPTION
            "This object contains all the routing information which was
             extracted from the received Source Routed frame. The data
             is in the form it was received from the ring network"
        ::= { rtxSourceRouteEntry 3 }

    rtxSourceRouteType  OBJECT-TYPE
        SYNTAX  INTEGER {
                          clear (1),
                          sameRing (2),
                          locked   (3),
                          provisional (4),
                          respondWithARE (5),
                          other (6)
                         } 
        ACCESS  read-only
        STATUS  mandatory
        DESCRIPTION
            "This object represents the type of the entry. If the value
             returned is sameRing (1), then this indicates that the
             frame from which this entry was taken originated on our
             local ring. A value of locked (2) is used for entries which
             have been learned from ARE type frames. The value provisional(3)
             is used for frames which have been learned from STE frames and
             the responsWithARE (4) values is used to indicate that when a
             response is sent to this entry's address is should be sent as 
             an ARE frame."
        ::= { rtxSourceRouteEntry 4 }

    rtxSourceRouteDirection  OBJECT-TYPE
        SYNTAX  INTEGER {
                          inOrder(1),
                          reverseOrder(2)
                         }
        ACCESS  read-only
        STATUS  mandatory
        DESCRIPTION
            "If this object returns a value of inOrder(0), then this means 
             that the D bit is zero and that the frame traverses the LANs 
             in the order in which they are specified in the routing 
             information field.
             Conversely, if the D bit is set to 1 the frame will traverse 
             the LANs in the reverse order. The D bit is meaningful only for
             source routed frames (SRF). For STE and ARE frames the D bit 
             is ignored and is not altered by the unit."
       ::= { rtxSourceRouteEntry 5 }

    --   
    -- The 10BaseT objects. The Basic group.
    -- 
    -- This is based on the standard MIB for repeaters, however, that MIB
    -- was lacking in its ability to support more that one repeater module
    -- per device. Therefore a level of instancing was added, to just about
    -- every object, and made this private MIB.


    rtxRptrBasicTable  OBJECT-TYPE
       SYNTAX  SEQUENCE OF RtxRptrBasicEntry
       ACCESS  not-accessible
       STATUS  mandatory
       DESCRIPTION
          "This table contains the status information and control
           parameters for a particular 10 Base-T I/O card in the
           RX7000 chassis."
        ::= { rtxRptrBasicGroup 1 }

    rtxRptrBasicEntry  OBJECT-TYPE
       SYNTAX  RtxRptrBasicEntry
       ACCESS  not-accessible
       STATUS  mandatory
       DESCRIPTION
          "This is an entry in the rtxRptrBasicTable."
       INDEX  { rtxRptrBasicId }
       ::= { rtxRptrBasicTable 1 }


    RtxRptrBasicEntry ::= SEQUENCE {
        rtxRptrBasicId
           INTEGER,
        rtxRptrBasicGroupCapacity
           INTEGER,
        rtxRptrBasicOperStatus
           INTEGER,
        rtxRptrBasicHealthText
           DisplayString,
        rtxRptrBasicReset
           INTEGER,
        rtxRptrBasicGroupDescr
           INTEGER,
        rtxRptrBasicGroupObjectId
           OBJECT IDENTIFIER,
        rtxRptrBasicGroupOperState
           INTEGER,
        rtxRptrBasicGroupLastOperStatusChange
           INTEGER,
        rtxRptrBasicGroupPortCapacity
           INTEGER
       }

     rtxRptrBasicId  OBJECT-TYPE
       SYNTAX  INTEGER
       ACCESS  read-only
       STATUS  mandatory
       DESCRIPTION
          "This object uniquely identifies the 10 Base-T I/O card to
           which the entries in this table apply. It takes a value
           numerically equal to the portPhysPortID for the I/O card.
           This means that the indexing of hub cards is sparse."
       ::= { rtxRptrBasicEntry 1 }

     rtxRptrBasicGroupCapacity  OBJECT-TYPE
       SYNTAX  INTEGER (1..1024)
       ACCESS  read-only
       STATUS  mandatory
       DESCRIPTION
          "The rtxRptrGroupCapacity is the number of groups
           that can be contained within the repeater.  Within
           each managed repeater, the groups are uniquely
           numbered in the range from 1 to rtxRptrGroupCapacity.

           In the RX7000 system this object will only take the
           fixed value 1."
       ::= { rtxRptrBasicEntry 2 }

     rtxRptrBasicOperStatus  OBJECT-TYPE
       SYNTAX  INTEGER {
              other(1),            -- undefined or unknown status
              ok(2),               -- no known failures
              rtxRptrFailure(3),   -- repeater-related failure
              groupFailure(4),     -- group-related failure
              portFailure(5),      -- port-related failure
              generalFailure(6)    -- failure, unspecified type
              }
       ACCESS  read-only
       STATUS  mandatory
       DESCRIPTION
          "The rtxRptrOperStatus object indicates the
           operational state of the repeater.  The
           rtxRptrHealthText object may be consulted for more
           specific information about the state of the
           repeater's health.

           In the case of multiple kinds of failures (e.g.,
           repeater failure and port failure), the value of
           this attribute shall reflect the highest priority
           failure in the following order:

                rtxRptrFailure(3)
                groupFailure(4)
                portFailure(5)
                generalFailure(6).
          
           For the RX7000 a groupFailure(4) is indistinguishable from
           a rtxRptrFailure(3), which will be reported by preference."
       ::= { rtxRptrBasicEntry 3 }

     rtxRptrBasicHealthText  OBJECT-TYPE
       SYNTAX  DisplayString (SIZE (0..255))
       ACCESS  read-only
       STATUS  mandatory
       DESCRIPTION
          "The health text object is a text string that
           provides information relevant to the operational
           state of the repeater. Agents may use this string
           to provide detailed information on current
           failures, including how they were detected, and/or
           instructions for problem resolution. The contents
           are agent-specific."
       ::= { rtxRptrBasicEntry 4 }

    rtxRptrBasicReset  OBJECT-TYPE
       SYNTAX  INTEGER {
               noReset(1),
               reset(2)
               }
       ACCESS  read-write
       STATUS  mandatory
       DESCRIPTION
          "Setting this object to reset(2) causes a
           transition to the START state of Fig 9-2 in
           section 9 [IEEE 802.3 Std].

           Setting this object to noReset(1) has no effect.
           The agent will always return the value noReset(1)
           when this object is read.

           This action does not reset the management counters
           defined in this document nor does it affect the
           portAdminStatus parameters.  Included in this
           action is the execution of a disruptive Self-Test.
           As a result of the action of this test a rtxRptrResetEvent
           Trap may be sent.

           Note: This action may result in the loss of packets.
           For the RX7000, the 'disruptive self-test' involves a
           RIC loopback and collision test."
       ::= { rtxRptrBasicEntry 5 }


    -- The non-disruptive test object which is defined in the IETF
    -- MIB is not supported since the RX7000 series hardware allows
    -- no meaningful non-disruptive test to be performed.
    -- See xxxx for the disruptive self-test which can be performed.

     rtxRptrBasicGroupDescr  OBJECT-TYPE
       SYNTAX  DisplayString (SIZE (0..255))
       ACCESS  read-only
       STATUS  mandatory
       DESCRIPTION
         "This object contains a textual description of the group. This
          string should contain the full name and version identification
          of the group's hardware type and indicate how the group is
          differentiated from other groups in the repeater. 'Wilma
          Flintstone 6-Port FOIRL Plug-In module, Rev A' or 'Barney
          Rubble 10Base-T 4-port SIMM socket V, 2.1' are examples of
          valid group descriptions.
          It is mandatory that this only contain printable ASCII
          characters."
       ::= { rtxRptrBasicEntry 6 }

     rtxRptrBasicGroupObjectId  OBJECT-TYPE
       SYNTAX  OBJECT IDENTIFIER
       ACCESS  read-only
       STATUS  mandatory
       DESCRIPTION
          "The vendor's authoritative identification of the group. This
           is the value allocated within the SMI enterprises subtree
           (1.3.6.1.4.1) and provides a straight-forward and unambiguous
           means for determining the type of group being managed.

           For Example, this variable could take the value :
           1.3.6.1.4.1.4242.1.2.14 if vendor 'Flintstone Inc.'
           was assigned subtree 1.3.6.1.4.1.4242, and had assigned
           1.3.6.1.4.1.4242.1.2.14 to its 'Wilma Flintstone
           6-Port FOIRL Plug-In module, Rev A'.
           
           The definition of the value assigned for the RX7000 
           10 Base-T cards follow the definition of the rtxRtpr traps." 
        ::= { rtxRptrBasicEntry 7 }

    rtxRptrBasicGroupOperState  OBJECT-TYPE
       SYNTAX  INTEGER {
               other       (1),
               operational (2),
               malFunctioning (3),
               notPresent (4),
               undertest  (5),
               resetInProgress (6)
               }
       ACCESS  read-only
       STATUS  mandatory
       DESCRIPTION
          "This object indicates the operational status of the group.

           A state of notPresent(4) indicates that the group has been
           physically removed from the repeater. A status of operational(2)
           indicates that the group is functioning, and a status of
           malFunctioning(3) indicates that the group is malfunctioning
           in some way."
       ::= { rtxRptrBasicEntry 8 }

     rtxRptrBasicGroupLastOperStatusChange  OBJECT-TYPE
       SYNTAX  TimeTicks
       ACCESS  read-only
       STATUS  mandatory
       DESCRIPTION
          "This object contains the value of sysUpTime at the time
           that the value of the rtxRptrOprtStatus object was last
           changed.
          
           A value of zero indicates that the oper status has not
           been changed since the agent last reset."
       ::= { rtxRptrBasicEntry 9 }

     rtxRptrBasicGroupPortCapacity  OBJECT-TYPE
       SYNTAX  INTEGER (1..1024)
       ACCESS  read-only
       STATUS  mandatory
       DESCRIPTION
          "The rtxRptrBasicGroupPortCapacity is the number of ports
           that can be contained within the group. Valid range is
           1 to 1024. Within each group, the ports are uniquley numbered
           in the range 1 to rtxRptrBasicGroupPortCapacity.

           Note : In practice, this will generally be the number
           of ports on a module, card, or board, and the port numbers
           will correspond to numbers marked on the physical
           embodiment."
       ::= { rtxRptrBasicEntry 10 }

   --
   -- The Basic Port Table
   --
   -- To avoid confusion, note that the term 'port' tout court in this MIB
   -- bears the meaning assigned to it in the 802.3 repeater spec., and does
   -- not mean a RX7000 logical or physical port, except in the case of
   -- certain indices. Where a RX7000 physical port is intended, this is
   -- always stated explicitly.
   --

   --
   -- The Basic Port Table
   --

    rtxRptrPortTable  OBJECT-TYPE
       SYNTAX  SEQUENCE OF RtxRptrPortEntry
       ACCESS  not-accessible
       STATUS  mandatory
       DESCRIPTION
         "Table of descriptive and status information about the ports."
       ::= { rtxRptrBasicGroup 2 }

    rtxRptrPortEntry  OBJECT-TYPE
       SYNTAX  RtxRptrPortEntry
       ACCESS  not-accessible
       STATUS  mandatory
       DESCRIPTION
          "An entry in the table, containing information
           about a single port."
       INDEX    { rtxRptrPortRptrIndex, rtxRptrPortIndex }
       ::= { rtxRptrPortTable 1 }

    RtxRptrPortEntry ::= SEQUENCE {
       rtxRptrPortRptrIndex
          INTEGER,
       rtxRptrPortIndex
          INTEGER,
       rtxRptrPortAdminStatus
          INTEGER,
       rtxRptrPortAutoPartitionState
          INTEGER,
       rtxRptrPortOperStatus
          INTEGER
       }

    rtxRptrPortRptrIndex  OBJECT-TYPE
       SYNTAX  INTEGER (1..1024)
       ACCESS  read-only
       STATUS  mandatory
       DESCRIPTION
          "This index uniquley identifies a single 10 Base-T card. It
           takes a value numerically equal to the physical port index
           (portPhysPortID) of the I/O card. Note that this means that
           indexing of hub cards is sparse."
       ::= { rtxRptrPortEntry 1 }

    rtxRptrPortIndex  OBJECT-TYPE
       SYNTAX  INTEGER (1..1024)
       ACCESS  read-only
       STATUS  mandatory
       DESCRIPTION
          "This variable identifies the port within the group within
           the repeater for which this entry contains management
           information. This value can never be greater that
           rtrRptrGroupPortCapacity."
       ::= { rtxRptrPortEntry 2 }

    rtxRptrPortAdminStatus  OBJECT-TYPE
       SYNTAX  INTEGER {
               enable (1),
               disable (2)
               }
       ACCESS  read-write
       STATUS  mandatory
       DESCRIPTION
           "Setting this object to disable(2) disables the
           port.  A disabled port neither transmits nor
           receives.  Once disabled, a port must be
           explicitly enabled to restore operation.  A port
           which is disabled when power is lost or when a
           reset is exerted shall remain disabled when normal
           operation resumes.

           The admin state takes precedence over auto-
           partition and functionally operates between the
           auto-partition mechanism and the AUI/PMA.

           Setting this object to enable(1) enables the port
           and exerts a BEGIN on the port's auto-partition
           state machine.
           (In effect, when a port is disabled, the value of
            rtxRptrPortAutoPartitionState for that port is frozen
           until the port is next enabled.  When the port
           becomes enabled, the rtxRptrPortAutoPartitionState
           becomes notAutoPartitioned(1), regardless of its
           pre-disabling state.)"
       ::= { rtxRptrPortEntry 3 }

    rtxRptrPortAutoPartitionState  OBJECT-TYPE
       SYNTAX  INTEGER {
               notAutoPartitioned (1),
               autoPartitioned    (2)
               }
       ACCESS  read-only
       STATUS  mandatory
       DESCRIPTION
          "The autoPartitionState flag indicates whether the
           port is currently partitioned by the repeater's
           auto-partition protection.

           The conditions that cause port partitioning are
           specified in partition state machine in Section 9
           [IEEE 802.3 Std].  They are not differentiated
           here."
       ::= { rtxRptrPortEntry 4 }

    rtxRptrPortOperStatus  OBJECT-TYPE
       SYNTAX  INTEGER {
               operational    (1),
               notOperational (2),
               notPresent     (3)
               }
       ACCESS  read-only
       STATUS  mandatory
       DESCRIPTION
          "This object indicates the port's operational
           status.  The notPresent(3) status indicates the
           port is physically removed (note this may or may
           not be possible depending on the type of port.)

           The operational(1) status indicates that the port
           is enabled (see rtxRptrPortAdminStatus) and working,
           even though it might be auto-partitioned (see
            rtxRptrPortAutoPartitionState).

           For the RX7000, the value notPresent(3) can never be
           returned notOperational(2) is returned if either the
           port is disabled via rtxRptrPortAdminState, or if Link
           Pulses are not being received."
       ::= { rtxRptrPortEntry 5 }

   --
   --                    The MONITOR GROUP
   --
   -- Implementation of this group is optional, but within the
   -- group all elements are mandatory.  If a managed repeater
   -- implements any part of this group, the entire group shall
   -- be implemented.

   --
   -- Repeater Monitor Information
   --
   -- Performance monitoring statistics for the repeater
   --


    rtxRptrMonitorTable  OBJECT-TYPE
       SYNTAX  SEQUENCE OF RtxRptrMonitorEntry
       ACCESS  not-accessible
       STATUS  mandatory
       DESCRIPTION
          "This table contains statistics information for  a collection
          of repeaters in a given system."
      ::= { rtxRptrMonitorGroup 1 }

    rtxRptrMonitorEntry  OBJECT-TYPE
       SYNTAX  RtxRptrMonitorEntry
       ACCESS  not-accessible
       STATUS  mandatory
       DESCRIPTION
          "This is an entry in the table containing statistics for
           single repeater."
       INDEX  { rtxRptrMonitorIndex }
       ::= { rtxRptrMonitorTable 1 }

    RtxRptrMonitorEntry ::= SEQUENCE {
       rtxRptrMonitorIndex
          INTEGER,
       rtxRptrMonitorTransmitCollisions
          Counter,
       rtxRptrMonitorMJLPs
          Counter
       }

    rtxRptrMonitorIndex  OBJECT-TYPE
       SYNTAX  INTEGER
       ACCESS  read-only
       STATUS  mandatory
       DESCRIPTION
          "This index uniquley identifies a single 10 Base-T I/O card.
           It takes the value numerically equal to the physical port ID
           (portPhysPortID) of the I/O card. Note that this means
           that indexing of hub cards is sparse."
       ::= { rtxRptrMonitorEntry 1 }

    rtxRptrMonitorTransmitCollisions  OBJECT-TYPE
       SYNTAX  Counter
       ACCESS  read-only
       STATUS  mandatory
       DESCRIPTION
           "This counter is incremented every time the
           repeater state machine enters the TRANSMIT
           COLLISION state from any state other than ONE PORT
           LEFT (Ref: Fig 9-2, IEEE 802.3 Std).

           The approximate minimum time for rollover of this
           counter is 16 hours."
       ::= { rtxRptrMonitorEntry 2 }

    rtxRptrMonitorMJLPs  OBJECT-TYPE
       SYNTAX  Counter
       ACCESS  read-only
       STATUS  mandatory
       DESCRIPTION
           "The repeater MJLPs object counts the number of times
           the repeater enters a DISABLE OUTPUT state in the MAU
           Jabber Lockup Protection state diagram."
       ::= { rtxRptrMonitorEntry 3 }

   --
   -- The Port Monitor Table
   --

    rtxRptrMonitorPortTable  OBJECT-TYPE
       SYNTAX  SEQUENCE OF RtxRptrMonitorPortEntry
       ACCESS  not-accessible
       STATUS  mandatory
       DESCRIPTION
          "Table of performance and error statistics for the ports."
       ::= { rtxRptrMonitorGroup 2 }

    rtxRptrMonitorPortEntry  OBJECT-TYPE
       SYNTAX  RtxRptrMonitorPortEntry
       ACCESS  not-accessible
       STATUS  mandatory
       DESCRIPTION
           "An entry in the table, containing performance and
           error statistics for a single port."
       INDEX    { rtxRptrMonitorPortGroupIndex, rtxRptrMonitorPortIndex }
       ::= { rtxRptrMonitorPortTable 1 }

    RtxRptrMonitorPortEntry ::= SEQUENCE {
       rtxRptrMonitorPortGroupIndex
          INTEGER,
       rtxRptrMonitorPortIndex
          INTEGER,
       rtxRptrMonitorPortReadableFrames
          Counter,
       rtxRptrMonitorPortReadableOctets
          Counter,
       rtxRptrMonitorPortFCSErrors
          Counter,
       rtxRptrMonitorPortAlignmentErrors
          Counter,
       rtxRptrMonitorPortFrameTooLongs
          Counter,
       rtxRptrMonitorPortShortEvents
          Counter,
       rtxRptrMonitorPortRunts
          Counter,
       rtxRptrMonitorPortCollisions
          Counter,
       rtxRptrMonitorPortLateCollisions
          Counter,
       rtxRptrMonitorPortVeryLongEvents
          Counter,
       rtxRptrMonitorPortDataRateMismatches
          Counter,
       rtxRptrMonitorPortAutoPartitions
          Counter,
       rtxRptrMonitorPortTotalErrors
          Counter
       }

    rtxRptrMonitorPortGroupIndex  OBJECT-TYPE
       SYNTAX  INTEGER
       ACCESS  read-only
       STATUS  mandatory
       DESCRIPTION
          "This index uniquley identifies a single 10 Base-T I/O card.
           It takes a value numerically equal to the physical port id
           (portPhysPortID) for the I/O card. Note that this means that
           indexing of hub cards is sparse."
       ::= { rtxRptrMonitorPortEntry 1 }

    rtxRptrMonitorPortIndex  OBJECT-TYPE
       SYNTAX  INTEGER (1..1024)
       ACCESS  read-only
       STATUS  mandatory
       DESCRIPTION
          "This object identifies the 10-BaseT port."
       ::= { rtxRptrMonitorPortEntry 2 }

    rtxRptrMonitorPortReadableFrames  OBJECT-TYPE
       SYNTAX  Counter
       ACCESS  read-only
       STATUS  mandatory
       DESCRIPTION
          "This object's value is a representation of the total number
           of frames of valid length. This counter is incremented by
           one for each frame whose Octet count is greater that or equal
           to the minFrameSize and less that or equal to the maxFrameSize
           (Ref : 4.4.2.1 [11]) and for which FCSError is not asserted."
       ::= { rtxRptrMonitorPortEntry 3 }

    rtxRptrMonitorPortReadableOctets  OBJECT-TYPE
       SYNTAX  Counter
       ACCESS  read-only
       STATUS  mandatory
       DESCRIPTION
          "This value of this object is incremented by OctetCount for
           each readable frame which has been determined to be a
           readable frame.

           Note : The approximate minimum time between counter
           rollovers is 58 minutes."
       ::= { rtxRptrMonitorPortEntry 4 }

    rtxRptrMonitorPortFCSErrors  OBJECT-TYPE
       SYNTAX  Counter
       ACCESS  read-only
       STATUS  mandatory
       DESCRIPTION
          "This counter is incremented by one for each frame
           received on this port with the FCSError signal
           asserted and the FramingError and CollisionEvent
           signals deasserted and whose OctetCount is greater
           than or equal to minFrameSize and less than or
           equal to maxFrameSize (Ref: 4.4.2.1, IEEE 802.3 Std).

           The approximate minimum time for rollover of this
           counter is 81 hours."
       ::= { rtxRptrMonitorPortEntry 5 }

    rtxRptrMonitorPortAlignmentErrors  OBJECT-TYPE
       SYNTAX  Counter
       ACCESS  read-only
       STATUS  mandatory
       DESCRIPTION
          "This counter is incremented by one for each frame
           received on this port with the FCSError and
           FramingError signals asserted and CollisionEvent
           signal deasserted and whose OctetCount is greater
           than or equal to minFrameSize and less than or
           equal to maxFrameSize (Ref: IEEE 802.3 Std,
           4.4.2.1).  If rtxRptrMonitorPortAlignmentErrors is
           incremented then the rtxRptrMonitorPortFCSErrors
           Counter shall not be incremented for the same
           frame.

           The approximate minimum time for rollover of this
           counter is 81 hours."
       ::= { rtxRptrMonitorPortEntry 6 }

    rtxRptrMonitorPortFrameTooLongs  OBJECT-TYPE
       SYNTAX  Counter
       ACCESS  read-only
       STATUS  mandatory
       DESCRIPTION
          "This counter is incremented by one for each frame
           received on this port whose OctetCount is greater
           than maxFrameSize (Ref: 4.4.2.1, IEEE 802.3 Std).
           If rtxRptrMonitorPortFrameTooLongs is incremented
           then neither the rtxRptrMonitorPortAlignmentErrors
           nor the rtxRptrMonitorPortFCSErrors counter shall be
           incremented for the frame.

           The approximate minimum time for rollover of this
           counter is 61 days."
       ::= { rtxRptrMonitorPortEntry 7 }

    rtxRptrMonitorPortShortEvents  OBJECT-TYPE
       SYNTAX  Counter
       ACCESS  read-only
       STATUS  mandatory
       DESCRIPTION
          "This counter is incremented by one for each
           CarrierEvent on this port with ActivityDuration
           less than ShortEventMaxTime.  ShortEventMaxTime is
           greater than 7.4 us and less than 8.2 us.
           ShortEventMaxTime has tolerances included
           to provide for circuit losses between a
           conformance test point at the AUI and the
           measurement point within the state machine.

           Note:  shortEvents may indicate an externally
           generated noise hit which will cause the repeater
           to transmit Runts to its other ports, or propagate
           a collision (which may be late) back to the
           transmitting DTE and damaged frames to the rest of
           the network. Such shortEvents are not a feature
           of normal network activity. Also it should be noted
           that a MAU that is attached to a coax segment may
           have several carrier droupouts on the DI circuit
           before the CI circuit is active and stable. Such
           droupouts will increment the shortEvent counter
           but are considered normal for a coax segment."
       ::= { rtxRptrMonitorPortEntry 8 }

    rtxRptrMonitorPortRunts  OBJECT-TYPE
       SYNTAX  Counter
       ACCESS  read-only
       STATUS  mandatory
       DESCRIPTION
          "This counter is incremented by one for each
           CarrierEvent hose ActiveDuration is greater that
           ShortEventsMaxtime and less than RuntMaxTime.
           RuntMaxTime is greater than 53.2us and less than
           56.0us.

           An event whose length is greater than 7.4us
           but less than 8.2us shall increment either
           the shortEvents counter or the runts counter but
           not both.

           A non-collision event greater that 53.2us but less
           than 56.0us may or may not be counted as a runt.
           A non-collision event greater than or equal to
           56.0us shall not be counted as a Runt.
           RuntMaxTime has tolerances included to provide for
           circuit losses between a conformance test point at
           the AUI and a measurement point within the state
           machine.

           Note : Runts do not indicate a problem in the network.
           The approximate minimum time for rollover of this
           counter is 16 hours."
       ::= { rtxRptrMonitorPortEntry 9 }

    rtxRptrMonitorPortCollisions  OBJECT-TYPE
       SYNTAX  Counter
       ACCESS  read-only
       STATUS  mandatory
       DESCRIPTION
          "This counter is incremented by one for any
           carrier event for which the CIPresent(X)
           variable has the value SQE.

           The approximate minimum time for rollover of this
           counter is 16 hours."
       ::= { rtxRptrMonitorPortEntry 10 }

    rtxRptrMonitorPortLateCollisions  OBJECT-TYPE
       SYNTAX  Counter
       ACCESS  read-only
       STATUS  mandatory
       DESCRIPTION
          "This counter is incremented by one for each
           carrier event in which the CIPresent(X)
           variable has the value SQE (Ref: 9.6.6.2,
           IEEE 802.3 Std) at any time when the
           ActivityDuration is greater than the
           RuntMaxTime.

           A late collision is counted twice, as both a
           collision and as a late collision.
           LateCollisionThreshold has tolerances included
           to provide for circuit losses between a conformance
           test point at the AUI and the measurement point
           within the state machine.

           Note : The approximate minimum time for rollover of
           this counter is 81 hours."
       ::= { rtxRptrMonitorPortEntry 11 }
    
    rtxRptrMonitorPortVeryLongEvents  OBJECT-TYPE
        SYNTAX  Counter
        ACCESS  read-only
        STATUS  mandatory
        DESCRIPTION
           "This counter is incremented by one for each
            CarrierEvent on this port whose ActivityDuration
            is greater than the MAU Jabber Lockup Protection
            timer TW3 (Ref: 9.6.1 & 9.6.5, IEEE 802.3 Std).
            Other counters may be incremented as appropriate."
       ::= { rtxRptrMonitorPortEntry 12 }

    rtxRptrMonitorPortDataRateMismatches  OBJECT-TYPE
       SYNTAX  Counter
       ACCESS  read-only
       STATUS  mandatory
       DESCRIPTION
          "This object counts the number of times that a packet
           has been received by this port with the transmission
           frequency (data rate) detectably mismatched from the
           local transmit frequency. The exact degree is
           implementation specific and is to be defined by
           the implementor for conformance testing.

           Note : Whether or not the repeater was able to maintain
           data integrity is beyond the scope of this standard."
       ::= { rtxRptrMonitorPortEntry 13 }

    rtxRptrMonitorPortAutoPartitions  OBJECT-TYPE
       SYNTAX  Counter
       ACCESS  read-only
       STATUS  mandatory
       DESCRIPTION
          "This counter is incremented by one for each time
           the repeater has automatically partitioned this
           port.  The conditions that cause port partitioning
           are specified in the partition state machine in
           Section 9 [IEEE 802.3 Std].  They are not
           differentiated here.

           Note : the approximate minimum time between
           counter rollovers is 20 days."
       ::= { rtxRptrMonitorPortEntry 14 }

    rtxRptrMonitorPortTotalErrors  OBJECT-TYPE
       SYNTAX  Counter
       ACCESS  read-only
       STATUS  mandatory
       DESCRIPTION
          "The total number of errors which have occurred on
           this port.  This counter is the summation of the
           values of other error counters (for the same port),
           namely:

                  rtxRptrMonitorPortFCSErrors,
                  rtxRptrMonitorPortAlignmentFrames,
                  rtxRptrMonitorPortFrameTooLongs,
                  rtxRptrMonitorPortShortEvents,
                  rtxRptrMonitorPortLateEvents,
                  rtxRptrMonitorPortVeryLongEvents and
                  rtxRptrMonitorPortDataRateMismatches.

           This counter is redundant in the sense that it is
           the summation of information already available
           through other objects.  However, it is included
           specifically because the regular retrieval of this
           object as a means of tracking the health of a port
           provides a considerable optimization of network
           management traffic over the otherwise necessary
           retrieval of the summed counters."
       ::= { rtxRptrMonitorPortEntry 15 }


   --
   -- The ADDRESS TRACKING GROUP
   --
   -- Implementation of this group is optional; it is appropriate
   -- for all systems which have the necessary metering.  If a
   -- managed repeater implements any part of this group, the entire
   -- group shall be implemented.

   --
   -- The Port Address Tracking Table
   --

    rtxRptrAddrTrackTable  OBJECT-TYPE
       SYNTAX  SEQUENCE OF RtxRptrAddrTrackEntry
       ACCESS  not-accessible
       STATUS  mandatory
       DESCRIPTION
          "Table of address mapping information about the ports."
       ::= { rtxRptrAddrTrackGroup  1 }

    rtxRptrAddrTrackEntry  OBJECT-TYPE
       SYNTAX  RtxRptrAddrTrackEntry
       ACCESS  not-accessible
       STATUS  mandatory
       DESCRIPTION
          "An entry in the table, containing address mapping
           information about a single port."
       INDEX    { rtxRptrAddrTrackGroupIndex, rtxRptrAddrTrackPortIndex }
       ::= { rtxRptrAddrTrackTable 1 }

    RtxRptrAddrTrackEntry ::= SEQUENCE {
       rtxRptrAddrTrackGroupIndex
          INTEGER,
       rtxRptrAddrTrackPortIndex
          INTEGER,
       rtxRptrAddrTrackLastSourceAddress
          MacAddress,
       rtxRptrAddrTrackSourceAddrChanges
          Counter
       }

    rtxRptrAddrTrackGroupIndex  OBJECT-TYPE
       SYNTAX  INTEGER
       ACCESS  read-only
       STATUS  mandatory
       DESCRIPTION
          "This index uniquley identifies a single 10 Base-T I/O card
           It takes a value numerically equal to the physical port
           ID (portPhysPortID) of the I/O card. Note that this means
           the indexing of hub cards is sparse."
       ::= { rtxRptrAddrTrackEntry 1 }

    rtxRptrAddrTrackPortIndex  OBJECT-TYPE
       SYNTAX  INTEGER (1..1024)
       ACCESS  read-only
       STATUS  mandatory
       DESCRIPTION
          "This object identifies the 10-baseT port."
       ::= { rtxRptrAddrTrackEntry 2 }

    rtxRptrAddrTrackLastSourceAddress  OBJECT-TYPE
       SYNTAX  MacAddress
       ACCESS  read-only
       STATUS  mandatory
       DESCRIPTION
          "This object is the SourceAddress of the last
           readable frame (i.e., counted by
           rtxRptrMonitorPortReadableFrames) received by this
           port."
       ::= { rtxRptrAddrTrackEntry 3 }

    rtxRptrAddrTrackSourceAddrChanges  OBJECT-TYPE
       SYNTAX  Counter
       ACCESS  read-only
       STATUS  mandatory
       DESCRIPTION
          "This counter is incremented by one for each time
           that the rtxRptrAddrTrackLastSourceAddress attribute
           for this port has changed.

           Note : This may indicate whether a link is connected to a
           single DTE or another multi-user segment.

           The approximate minimum time for rollover of this
           counter is 81 hours."
       ::= { rtxRptrAddrTrackEntry 4 }


   -- Traps for use by Repeaters

   -- Traps are defined using the conventions in RFC 1215 [8].

--  rtxRptrHealth TRAP-TYPE
--     ENTERPRISE  rtxrptr
--     VARIABLES   { rtxRptrOperStatus }
--     DESCRIPTION
--             "The rtxRptrHealth trap conveys information related
--             to the operational status of the repeater.  This
--             trap is sent only when the oper status of the
--             repeater changes.
--
--             The rtxRptrHealth trap must contain the
--              rtxRptrOperStatus object.  The agent may optionally
--             include the rtxRptrHealthText object in the varBind
--             list.  See the rtxRptrOperStatus and rtxRptrHealthText
--             objects for descriptions of the information that
--             is sent.
--
--             The agent must throttle the generation of
--             consecutive rtxRptrHealth traps so that there is at
--             least a five-second gap between them."
--     ::= 1
--
--  rtxRptrGroupChange TRAP-TYPE
--     ENTERPRISE  rtxrptr
--     VARIABLES   { rtxRptrGroupIndex }
--     DESCRIPTION
--             "This trap is sent when a change occurs in the
--             group structure of a repeater.  This occurs only
--             when a group is logically or physically removed
--             from or added to a repeater.  The varBind list
--             contains the identifier of the group that was
--             removed or added.
--
--             The agent must throttle the generation of
--             consecutive rtxRptrGroupChange traps for the same
--             group so that there is at least a five-second gap
--             between them."
--     ::= 2
--
--  rtxRptrResetEvent TRAP-TYPE
--     ENTERPRISE  rtxrptr
--     VARIABLES   { rtxRptrOperStatus }
--     DESCRIPTION
--             "The rtxRptrResetEvent trap conveys information
--             related to the operational status of the repeater.
--             This trap is sent on completion of a repeater
--             reset action.  A repeater reset action is defined
--             as an a transition to the START state of Fig 9-2
--             in section 9 [IEEE 802.3 Std], when triggered by a
--             management command (e.g., an SNMP Set on the
--              rtxRptrReset object).
--
--             The agent must throttle the generation of
--             consecutive rtxRptrResetEvent traps so that there is
--             at least a five-second gap between them.
--
--             The rtxRptrResetEvent trap is not sent when the agent
--             restarts and sends an SNMP coldStart or warmStart
--             trap.  However, it is recommended that a repeater
--             agent send the rtxRptrOperStatus object as an
--             optional object with its coldStart and warmStart
--             trap PDUs.
--
--             The rtxRptrOperStatus object must be included in the
--             VarBind list sent with this trap.  The agent may
--             optionally include the rtxRptrHealthText object as
--             well."
--     ::= 3

    rtxRptrOnePortRepeater        OBJECT IDENTIFIER ::= { rtxRptrIOCard 1}
    rtxRptrTwelvePortRepeater     OBJECT IDENTIFIER ::= { rtxRptrIOCard 2}
    rtxRptrTwentyFourPortRepeater OBJECT IDENTIFIER ::= { rtxRptrIOCard 3}

    --
    -- Retix Compression Group
    --

    cmprsnPortTable  OBJECT-TYPE
        SYNTAX  SEQUENCE OF CmprsnPortEntry
        ACCESS  not-accessible
        STATUS  mandatory
        DESCRIPTION
               " This table contains the Compression Port Information."
        ::=  { cmprsn 1 }

    cmprsnPortEntry  OBJECT-TYPE
        SYNTAX  CmprsnPortEntry
        ACCESS  not-accessible
        STATUS  mandatory
        DESCRIPTION
           "An Entry in this table contains information
            about each logical port in the system that uses
            compression. Compression can only be used on Logical
            Ports which have underlying physical ports which
            are running Retixwan or x25 as the Link Protocol."
        INDEX   { cmprsnPortIfIndex  }
        ::=  { cmprsnPortTable 1 }

    CmprsnPortEntry ::= SEQUENCE {
        cmprsnPortIfIndex
            INTEGER,
        cmprsnPortEnable
            INTEGER,
        cmprsnPortRatio
            OCTET STRING
        }

    cmprsnPortIfIndex  OBJECT-TYPE
        SYNTAX  INTEGER
        ACCESS  read-only
        STATUS  mandatory
        DESCRIPTION
            "This object is the Logical Port to which this
            table entry refers. The Port must be of type Retixwan or 
            X.25 to run compression."
        ::=  { cmprsnPortEntry 1 }

    cmprsnPortEnable  OBJECT-TYPE
        SYNTAX  INTEGER{
                enable (1),
                disable (2)
                }
        ACCESS  read-write
        STATUS  mandatory
        DESCRIPTION
            "This enables or disables Compression on this port."
        ::=  { cmprsnPortEntry 2 }

    cmprsnPortRatio  OBJECT-TYPE
        SYNTAX  OCTET STRING(SIZE(5))
        ACCESS  read-only
        STATUS  mandatory
        DESCRIPTION
            "This is the compression Ratio for this port. It is calculated
            as follows :- 
                    Total Bytes into Compression Algorithm
                    --------------------------------------    
                    Total Bytes out of Compression Algorithm
                    
            It is expressed as a percentage, the OCTET STRING allowing
            us to return the floating point calculation in the form
            xx.yy "
        ::=  { cmprsnPortEntry 3 }

    --
    -- This section defines a single table with all objects
    -- needed for ISDN Phase 1.
    --

      isdnTable  OBJECT-TYPE
         SYNTAX  SEQUENCE OF IsdnEntry
         ACCESS  not-accessible
         STATUS  mandatory
         DESCRIPTION
           "A table of parameters specifying whether and how
        ISDN TA support is provided on a serial interface 
        physical port."
         ::= { rtxisdn 1 }

      isdnEntry  OBJECT-TYPE
         SYNTAX  IsdnEntry
         ACCESS  not-accessible
         STATUS  mandatory
         DESCRIPTION
           "An entry in the ISDN table."
         INDEX { isdnIndex }
      ::= { isdnTable 1 }

      IsdnEntry  ::= SEQUENCE {
            isdnIndex
                  INTEGER,
            isdnEnabled
                  INTEGER,
            isdnMode
                  INTEGER,
            isdnInitialRetryInterval
                  INTEGER,
            isdnRetryThresh
                  INTEGER,
            isdnBackupRetryInterval
                  INTEGER,
            isdnCallExpirationTime
                  INTEGER,
            isdnTimeOn
                  DisplayString,
            isdnTimeOff
                  DisplayString,
            isdnControl
                    INTEGER,
            isdnStatus
                  INTEGER,
            isdnInactivityTime
                  INTEGER
            }

      isdnIndex  OBJECT-TYPE
         SYNTAX  INTEGER
         ACCESS  read-only
         STATUS  mandatory
         DESCRIPTION
           "The index value which uniquely identifies the physical port
            to which this entry is applicable."
         ::= { isdnEntry 1 }

      isdnEnabled  OBJECT-TYPE
        SYNTAX  INTEGER {
             enabled (1),
             disabled (2)
         }
        ACCESS  read-write
         STATUS  mandatory
         DESCRIPTION
               "This parameter determines whether ISDN TA support procedures
               are invoked for this port.  When set to disabled, no TA support
               is provided and the values of the remaining parameters in the
               isdnEntry are ignored.  The parameter can only be set
               to enabled if the physical port is of type V35 or X21."
         ::= { isdnEntry 2 }

      isdnMode  OBJECT-TYPE
         SYNTAX  INTEGER {
            manualCall (1),
            autoCall (2),
             timedCall (3),
             answerOnly (4),
             standby (5),
             onDemand (6)
            }
         ACCESS  read-write
         STATUS  mandatory
         DESCRIPTION
           "This parameter selects the call setup and answer algorithms
               desired." 
         ::= { isdnEntry 3 }

     isdnInitialRetryInterval  OBJECT-TYPE
        SYNTAX  INTEGER (10..600)
        ACCESS  read-write
        STATUS  mandatory
        DESCRIPTION
              "The interval in seconds initially in force between successive 
              call attempts, until the isdnRetryThresh is reached"
        ::= { isdnEntry 4 }

     isdnRetryThresh  OBJECT-TYPE
        SYNTAX  INTEGER (0..10000)
        ACCESS  read-write
        STATUS  mandatory
        DESCRIPTION
          "The first isdnRetryThresh call attempts are made at
          the isdnInitialRetryInterval, all subsequent attempts
          are made at the isdnBackupInterval."
        ::= { isdnEntry 5 }

     isdnBackupRetryInterval  OBJECT-TYPE
        SYNTAX  INTEGER (0..3600)
        ACCESS  read-write
        STATUS  mandatory
        DESCRIPTION
              "The interval in seconds at which call attempts are made, once 
              isdRetryThresh is passed.  A value of 0 means no
              further call attempts will be made."
        ::= { isdnEntry 6 }

     isdnCallExpirationTime  OBJECT-TYPE
        SYNTAX  INTEGER (2..20)
        ACCESS  read-write
        STATUS  mandatory
        DESCRIPTION
              "The time in seconds to wait for an answer after a call has 
              been issued."
        ::= { isdnEntry 7 }

     isdnTimeOn  OBJECT-TYPE
        SYNTAX  DisplayString (SIZE (5))
        ACCESS  read-write
        STATUS  mandatory
        DESCRIPTION
          "This is a configurable parameter which sets
          the time of day to make the call. Format
          of string is hh:mm. First 2 bytes are hours,
          second 2 bytes are minutes The parameter
          isdnMode  must be set to timedCall for
          this to function.This defaults to '00:00' or midnight."
    ::= { isdnEntry 8 }

     isdnTimeOff  OBJECT-TYPE
        SYNTAX  DisplayString (SIZE (5))
        ACCESS  read-write
        STATUS  mandatory
        DESCRIPTION
          "This is a configurable parameter which sets
          the time of day to clear the call. Format
          of string is hh:mm. First 2 bytes are hours,
          second 2 bytes are minutes The parameter
          isdnMode  must be set to timedCall for
          this to function.This defaults to '00:00' or midnight."
    ::= { isdnEntry 9 }

     isdnControl  OBJECT-TYPE
        SYNTAX  INTEGER {
            noAction (1),
            makeCall (2),
            clearCall (3)
        }
        ACCESS  read-write
        STATUS  mandatory
        DESCRIPTION
              "This parameter allows a network manager to make or clear an
              ISDN call.  When read, the value noAction will always be returned.
              When set to makeCall, the port will initiate an ISDN call if this
              is allowed by the current setting of isdnMode.  When
              set to clearCall, the call will be cleared if this is allowed
              by the current setting of isdnMode."
        ::= { isdnEntry 10 }

     isdnStatus  OBJECT-TYPE
        SYNTAX  INTEGER {
            disabled (1),  -- isdn support disabled
            idle (2),      -- isdn enabled but no call in progress
            calling (3),   -- call attempt in progress
            waiting (4),   -- between call attempts
            connected (5), -- call connected
            inactive (6)   -- temporarily disconnected due to lack of data
        }
        ACCESS  read-only
        STATUS  mandatory
        DESCRIPTION
              "Returns the current status of the ISDN call."
        ::= { isdnEntry 11 }

     isdnInactivityTime  OBJECT-TYPE
        SYNTAX  INTEGER (10..3600)
        ACCESS  read-write
        STATUS  mandatory
        DESCRIPTION
              "The time in seconds to wait, while not receiving or transmitting
              data, before a call is cleared when in On Demand mode."
        ::= { isdnEntry 12 }


    --
    --  The Token Ring Group 
    --
    --
    -- The Interface Table
 
    -- This table contains state and parameter information which
    -- is specific to 802.5 interfaces.  It is mandatory that
    -- systems having 802.5 interfaces implement this table in
    -- addition to the generic interfaces table [4,6] and its
    -- generic extensions [11].
 
      dot5Table  OBJECT-TYPE
             SYNTAX  SEQUENCE OF Dot5Entry
             ACCESS  not-accessible
             STATUS  mandatory
             DESCRIPTION
                 "This table contains Token Ring interface
                 parameters and state variables, one entry
                 per 802.5 interface."
             ::= { dot5 1 }
 
      dot5Entry  OBJECT-TYPE
             SYNTAX  Dot5Entry
             ACCESS  not-accessible
             STATUS  mandatory
             DESCRIPTION
                 "A list of Token Ring status and parameter
                  values for an 802.5 interface."
             INDEX { dot5IfIndex }
             ::= { dot5Table 1 }
 
      Dot5Entry ::= SEQUENCE {
          dot5IfIndex
              INTEGER,
          dot5Commands
              INTEGER,
          dot5RingStatus
              INTEGER,
          dot5RingState
              INTEGER,
          dot5RingOpenStatus
              INTEGER,
          dot5RingSpeed
              INTEGER,
          dot5UpStream
              MacAddress,
          dot5ActMonParticipate
              INTEGER,
          dot5Functional
              MacAddress
          }
 
      dot5IfIndex  OBJECT-TYPE
             SYNTAX  INTEGER
             ACCESS  read-only
             STATUS  mandatory
             DESCRIPTION
                 "The value of this object identifies the
                  802.5 interface for which this entry
                  contains management information.  The
                  value of this object for a particular
                  interface has the same value as the
                  ifIndex object, defined in [4,6],
                  for the same interface."
             ::= { dot5Entry 1 }
 
      dot5Commands  OBJECT-TYPE
             SYNTAX  INTEGER {
                     no-op (1),
                     open (2),
                     reset (3),
                     close (4)
                     }
             ACCESS  read-write
             STATUS  mandatory
             DESCRIPTION
                 "When this object is set to the value of
                  open(2), the station should go into the
                  open state.  The progress and success of
                  the open is given by the values of the
                  objects dot5RingState and
                  dot5RingOpenStatus.
                  When this object is set to the value
                  of reset(3), then the station should do
                  a reset.  On a reset, all MIB counters
                  should retain their values, if possible.
                  Other side affects are dependent on the
                  hardware chip set.
                  When this object is set to the value
                  of close(4), the station should go into
                  the stopped state by removing itself
                  from the ring.
                  Setting this object to a value of
                  no-op(1) has no effect.
                  When read, this object always has a
                  value of no-op(1)."
             ::= { dot5Entry 2 }
 
      dot5RingStatus  OBJECT-TYPE
             SYNTAX  INTEGER
             ACCESS  read-only
             STATUS  mandatory
             DESCRIPTION
                 "The current interface status which can
                 be used to diagnose fluctuating problems
                 that can occur on token rings, after a
                 station has successfully been added to
                 the ring.
                 Before an open is completed, this
                 object has the value for the 'no status'
                 condition.  The dot5RingState and
                 dot5RingOpenStatus objects provide for
                 debugging problems when the station
                 can not even enter the ring.
                 The object's value is a sum of
                 values, one for each currently applicable
                 condition.  The following values are
                 defined for various conditions:
 
                     0 = No Problems detected
                    32 = Ring Recovery
                    64 = Single Station
                   256 = Remove Received
                   512 = reserved
                  1024 = Auto-Removal Error
                  2048 = Lobe Wire Fault
                  4096 = Transmit Beacon
                  8192 = Soft Error
                 16384 = Hard Error
                 32768 = Signal Loss
                131072 = no status, open not completed."
             ::= { dot5Entry 3 }
 
      dot5RingState  OBJECT-TYPE
             SYNTAX  INTEGER {
                     opened (1),
                     closed (2),
                     opening (3),
                     closing (4),
                     openFailure (5),
                     ringFailure (6)
                     }
             ACCESS  read-only
             STATUS  mandatory
             DESCRIPTION
                 "The current interface state with respect
                 to entering or leaving the ring."
             ::= { dot5Entry 4 }
 
      dot5RingOpenStatus  OBJECT-TYPE
             SYNTAX  INTEGER {
                     noOpen (1),     -- no open attempted
                     badParam (2),
                     lobeFailed (3),
                     signalLoss (4),
                     insertionTimeout (5),
                     ringFailed (6),
                     beaconing (7),
                     duplicateMAC (8),
                     requestFailed (9),
                     removeReceived (10),
                     open (11)      -- last open successful
                     }
             ACCESS  read-only
             STATUS  mandatory
             DESCRIPTION
                 "This object indicates the success, or the
                 reason for failure, of the station's most
                 recent attempt to enter the ring."
             ::= { dot5Entry 5 }
 
      dot5RingSpeed  OBJECT-TYPE
             SYNTAX  INTEGER {
                     unknown (1),
                     oneMegabit (2),
                     fourMegabit (3),
                     sixteenMegabit (4)
                     }
             ACCESS  read-write
             STATUS  mandatory
             DESCRIPTION
                 "The ring's bandwidth."
             ::= { dot5Entry 6 }
 
      dot5UpStream  OBJECT-TYPE
             SYNTAX  MacAddress
             ACCESS  read-only
             STATUS  mandatory
             DESCRIPTION
                 "The MAC-address of the up stream neighbor
                  station in the ring."
             ::= { dot5Entry 7 }
 
      dot5ActMonParticipate  OBJECT-TYPE
             SYNTAX  INTEGER {
                     true (1),
                     false (2)
                     }
             ACCESS  read-write
             STATUS  mandatory
             DESCRIPTION
                 "If this object has a value of true(1) then
                 this interface will participate in the
                 active monitor selection process.  If the
                 value is false(2) then it will not.
                 Setting this object might not have an
                 effect until the next time the interface
                 is opened."
             ::= { dot5Entry 8 }
 
      dot5Functional  OBJECT-TYPE
             SYNTAX  MacAddress
             ACCESS  read-write
             STATUS  mandatory
             DESCRIPTION
                 "The bit mask of all Token Ring functional
                 addresses for which this interface will
                 accept frames."
             ::= { dot5Entry 9 }
 
 
 
      --   The Statistics Table
 
      -- This table contains statistics and error counter which are
      -- specific to 802.5 interfaces.  It is mandatory that systems
      -- having 802.5 interfaces implement this table.
 
      dot5StatsTable  OBJECT-TYPE
             SYNTAX  SEQUENCE OF Dot5StatsEntry
             ACCESS  not-accessible
             STATUS  mandatory
             DESCRIPTION
                 "A table containing Token Ring statistics,
                 one entry per 802.5 interface.
                 All the statistics are defined using
                 the SYNTAX  Counter as 32-bit wrap around
                 counters.  Thus, if an interface's
                 hardware maintains these statistics in
                 16-bit counters, then the agent must read
                 the hardware's counters frequently enough
                 to prevent loss of significance, in order
                 to maintain 32-bit counters in software."
             ::= { dot5 2 }
 
      dot5StatsEntry  OBJECT-TYPE
             SYNTAX  Dot5StatsEntry
             ACCESS  not-accessible
             STATUS  mandatory
             DESCRIPTION
                 "An entry contains the 802.5 statistics
                  for a particular interface."
             INDEX { dot5StatsIfIndex }
             ::= { dot5StatsTable 1 }
 
      Dot5StatsEntry ::= SEQUENCE {
              dot5StatsIfIndex
                  INTEGER,
              dot5StatsLineErrors
                  Counter,
              dot5StatsBurstErrors
                  Counter,
              dot5StatsACErrors
                  Counter,
              dot5StatsAbortTransErrors
                  Counter,
              dot5StatsInternalErrors
                  Counter,
              dot5StatsLostFrameErrors
                  Counter,
              dot5StatsReceiveCongestions
                  Counter,
              dot5StatsFrameCopiedErrors
                  Counter,
              dot5StatsTokenErrors
                  Counter,
              dot5StatsSoftErrors
                  Counter,
              dot5StatsHardErrors
                  Counter,
              dot5StatsSignalLoss
                  Counter,
              dot5StatsTransmitBeacons
                  Counter,
              dot5StatsRecoverys
                  Counter,
              dot5StatsLobeWires
                  Counter,
              dot5StatsRemoves
                  Counter,
              dot5StatsSingles
                  Counter,
              dot5StatsFreqErrors
                  Counter
              }
 
 
      dot5StatsIfIndex  OBJECT-TYPE
             SYNTAX  INTEGER
             ACCESS  read-only
             STATUS  mandatory
             DESCRIPTION
                 "The value of this object identifies the
                 802.5 interface for which this entry
                 contains management information.  The
                 value of this object for a particular
                 interface has the same value as the
                 ifIndex object, defined in [4,6], for
                 the same interface."
             ::= { dot5StatsEntry 1 }
 
      dot5StatsLineErrors  OBJECT-TYPE
             SYNTAX  Counter
             ACCESS  read-only
             STATUS  mandatory
             DESCRIPTION
                 "This counter is incremented when a frame
                 or token is copied or repeated by a
                 station, the E bit is zero in the frame
                 or token and one of the following
                 conditions exists: 1) there is a
                 non-data bit (J or K bit) between the SD
                 and the ED of the frame or token, or
                 2) there is an FCS error in the frame."
             ::= { dot5StatsEntry 2 }
 
      dot5StatsBurstErrors  OBJECT-TYPE
             SYNTAX  Counter
             ACCESS  read-only
             STATUS  mandatory
             DESCRIPTION
                 "This counter is incremented when a station
                 detects the absence of transitions for five
                 half-bit timers (burst-five error)."
             ::= { dot5StatsEntry 3 }
 
      dot5StatsACErrors  OBJECT-TYPE
             SYNTAX  Counter
             ACCESS  read-only
             STATUS  mandatory
             DESCRIPTION
                 "This counter is incremented when a station
                 receives an AMP or SMP frame in which A is
                 equal to C is equal to 0, and then receives
                 another SMP frame with A is equal to C is
                 equal to 0 without first receiving an AMP
                 frame. It denotes a station that cannot set
                 the AC bits properly."
             ::= { dot5StatsEntry 4 }
 
      dot5StatsAbortTransErrors  OBJECT-TYPE
             SYNTAX  Counter
             ACCESS  read-only
             STATUS  mandatory
             DESCRIPTION
                 "This counter is incremented when a station
                 transmits an abort delimiter while
                 transmitting."
             ::= { dot5StatsEntry 5 }
 
      dot5StatsInternalErrors  OBJECT-TYPE
             SYNTAX  Counter
             ACCESS  read-only
             STATUS  mandatory
             DESCRIPTION
                 "This counter is incremented when a station
                 recognizes an internal error."
             ::= { dot5StatsEntry 6 }
 
      dot5StatsLostFrameErrors  OBJECT-TYPE
             SYNTAX  Counter
             ACCESS  read-only
             STATUS  mandatory
             DESCRIPTION
                 "This counter is incremented when a station
                 is transmitting and its TRR timer expires.
                 This condition denotes a condition where a
                 transmitting station in strip mode does not
                 receive the trailer of the frame before the
                 TRR timer goes off."
             ::= { dot5StatsEntry 7 }
 
      dot5StatsReceiveCongestions  OBJECT-TYPE
             SYNTAX  Counter
             ACCESS  read-only
             STATUS  mandatory
             DESCRIPTION
                 "This counter is incremented when a station
                 recognizes a frame addressed to its
                 specific address, but has no available
                 buffer space indicating that the station
                 is congested."
             ::= { dot5StatsEntry 8 }
 
      dot5StatsFrameCopiedErrors  OBJECT-TYPE
             SYNTAX  Counter
             ACCESS  read-only
             STATUS  mandatory
             DESCRIPTION
                 "This counter is incremented when a station
                 recognizes a frame addressed to its
                 specific address and detects that the FS
                 field A bits are set to 1 indicating a
                 possible line hit or duplicate address."
             ::= { dot5StatsEntry 9 }
 
      dot5StatsTokenErrors  OBJECT-TYPE
             SYNTAX  Counter
             ACCESS  read-only
             STATUS  mandatory
             DESCRIPTION
                 "This counter is incremented when a station
                 acting as the active monitor recognizes an
                 error condition that needs a token
                 transmitted."
             ::= { dot5StatsEntry 10 }
 
      dot5StatsSoftErrors  OBJECT-TYPE
             SYNTAX  Counter
             ACCESS  read-only
             STATUS  mandatory
             DESCRIPTION
                 "The number of Soft Errors the interface
                 has detected. It directly corresponds to
                 the number of Report Error MAC frames
                 that this interface has transmitted.
                 Soft Errors are those which are
                 recoverable by the MAC layer protocols."
             ::= { dot5StatsEntry 11 }
 
      dot5StatsHardErrors  OBJECT-TYPE
             SYNTAX  Counter
             ACCESS  read-only
             STATUS  mandatory
             DESCRIPTION
                 "The number of times this interface has
                 detected an immediately recoverable
                 fatal error.  It denotes the number of
                 times this interface is either
                 transmitting or receiving beacon MAC
                 frames."
             ::= { dot5StatsEntry 12 }
 
      dot5StatsSignalLoss  OBJECT-TYPE
             SYNTAX  Counter
             ACCESS  read-only
             STATUS  mandatory
             DESCRIPTION
                 "The number of times this interface has
                 detected the loss of signal condition from
                 the ring."
             ::= { dot5StatsEntry 13 }
 
      dot5StatsTransmitBeacons  OBJECT-TYPE
             SYNTAX  Counter
             ACCESS  read-only
             STATUS  mandatory
             DESCRIPTION
                 "The number of times this interface has
                 transmitted a beacon frame."
             ::= { dot5StatsEntry 14 }
 
      dot5StatsRecoverys  OBJECT-TYPE
             SYNTAX  Counter
             ACCESS  read-only
             STATUS  mandatory
             DESCRIPTION
                 "The number of Claim Token MAC frames
                 received or transmitted after the interface
                 has received a Ring Purge MAC frame.  This
                 counter signifies the number of times the
                 ring has been purged and is being recovered
                 back into a normal operating state."
             ::= { dot5StatsEntry 15 }
 
      dot5StatsLobeWires  OBJECT-TYPE
             SYNTAX  Counter
             ACCESS  read-only
             STATUS  mandatory
             DESCRIPTION
                 "The number of times the interface has
                 detected an open or short circuit in the
                 lobe data path.  The adapter will be closed
                 and dot5RingState will signify this
                 condition."
             ::= { dot5StatsEntry 16 }
 
      dot5StatsRemoves  OBJECT-TYPE
             SYNTAX  Counter
             ACCESS  read-only
             STATUS  mandatory
             DESCRIPTION
                 "The number of times the interface has
                 received a Remove Ring Station MAC frame
                 request.  When this frame is received
                 the interface will enter the close state
                 and dot5RingState will signify this
                 condition."
             ::= { dot5StatsEntry 17 }
 
      dot5StatsSingles  OBJECT-TYPE
             SYNTAX  Counter
             ACCESS  read-only
             STATUS  mandatory
             DESCRIPTION
                 "The number of times the interface has
                 sensed that it is the only station on the
                 ring.  This will happen if the interface
                 is the first one up on a ring, or if
                 there is a hardware problem."
             ::= { dot5StatsEntry 18 }
 
      dot5StatsFreqErrors  OBJECT-TYPE
             SYNTAX  Counter
             ACCESS  read-only
             STATUS  optional
             DESCRIPTION
                 "The number of times the interface has
                 detected that the frequency of the
                 incoming signal differs from the expected
                 frequency by more than that specified by
                 the IEEE 802.5 standard, see chapter 7
                 in [10]."
             ::= { dot5StatsEntry 19 }
 
 
      -- The Timer Table
 
      -- This group contains the values of the timers defined in
      -- [10] for 802.5 interfaces.  It is optional that systems
      -- having 802.5 interfaces implement this group.
 
      dot5TimerTable  OBJECT-TYPE
             SYNTAX  SEQUENCE OF Dot5TimerEntry
             ACCESS  not-accessible
             STATUS  mandatory
             DESCRIPTION
                 "This table contains Token Ring interface
                 timer values, one entry per 802.5
                 interface."
             ::= { dot5 5 }
 
      dot5TimerEntry  OBJECT-TYPE
             SYNTAX  Dot5TimerEntry
             ACCESS  not-accessible
             STATUS  mandatory
             DESCRIPTION
                 "A list of Token Ring timer values for an
                 802.5 interface."
             INDEX { dot5TimerIfIndex }
             ::= { dot5TimerTable 1 }
 
      Dot5TimerEntry ::= SEQUENCE {
             dot5TimerIfIndex
                 INTEGER,
             dot5TimerReturnRepeat
                 INTEGER,
             dot5TimerHolding
                 INTEGER,
             dot5TimerQueuePDU
                 INTEGER,
             dot5TimerValidTransmit
                 INTEGER,
             dot5TimerNoToken
                 INTEGER,
             dot5TimerActiveMon
                 INTEGER,
             dot5TimerStandbyMon
                 INTEGER,
             dot5TimerErrorReport
                 INTEGER,
             dot5TimerBeaconTransmit
                 INTEGER,
             dot5TimerBeaconReceive
                 INTEGER
             }
 
      dot5TimerIfIndex  OBJECT-TYPE
             SYNTAX  INTEGER
             ACCESS  read-only
             STATUS  mandatory
             DESCRIPTION
                 "The value of this object identifies the
                  802.5 interface for which this entry
                  contains timer values.  The value of
                  this object for a particular interface
                  has the same value as the ifIndex
                  object, defined in [4,6], for the same
                  interface."
             ::= { dot5TimerEntry 1 }
 
      dot5TimerReturnRepeat  OBJECT-TYPE
             SYNTAX  INTEGER
             ACCESS  read-only
             STATUS  mandatory
             DESCRIPTION
                 "The time-out value used to ensure the
                 interface will return to Repeat State, in
                 units of 100 micro-seconds.  The value
                 should be greater than the maximum ring
                 latency.
                 Implementors are encouraged to provide
                 read-write access to this object if that is
                 possible/useful in their system, but giving
                 due consideration to the dangers of
                 write-able timers."
             ::= { dot5TimerEntry 2 }
 
      dot5TimerHolding  OBJECT-TYPE
             SYNTAX  INTEGER
             ACCESS  read-only
             STATUS  mandatory
             DESCRIPTION
                 "Maximum period of time a station is
                 permitted to transmit frames after capturing
                 a token, in units of 100 micro-seconds.
                 Implementors are encouraged to provide
                 read-write access to this object if that is
                 possible/useful in their system, but giving
                 due consideration to the dangers of
                 write-able timers."
             ::= { dot5TimerEntry 3 }
 
      dot5TimerQueuePDU  OBJECT-TYPE
             SYNTAX  INTEGER
             ACCESS  read-only
             STATUS  mandatory
             DESCRIPTION
                 "The time-out value for enqueuing of an SMP
                 PDU after reception of an AMP or SMP
                 frame in which the A and C bits were
                 equal to 0, in units of 100
                 micro-seconds.
                 Implementors are encouraged to provide
                 read-write access to this object if that is
                 possible/useful in their system, but giving
                 due consideration to the dangers of
                 write-able timers."
             ::= { dot5TimerEntry 4 }
 
      dot5TimerValidTransmit  OBJECT-TYPE
             SYNTAX  INTEGER
             ACCESS  read-only
             STATUS  mandatory
             DESCRIPTION
                 "The time-out value used by the active
                 monitor to detect the absence of valid
                 transmissions, in units of 100
                 micro-seconds.
                 Implementors are encouraged to provide
                 read-write access to this object if that is
                 possible/useful in their system, but giving
                 due consideration to the dangers of
                 write-able timers."
             ::= { dot5TimerEntry 5 }
 
      dot5TimerNoToken  OBJECT-TYPE
             SYNTAX  INTEGER
             ACCESS  read-only
             STATUS  mandatory
             DESCRIPTION
                 "The time-out value used to recover from
                 various-related error situations [9].
                 If N is the maximum number of stations on
                 the ring, the value of this timer is
                 normally:
                 dot5TimerReturnRepeat + N*dot5TimerHolding.
                 Implementors are encouraged to provide
                 read-write access to this object if that is
                 possible/useful in their system, but giving
                 due consideration to the dangers of
                 write-able timers."
             ::= { dot5TimerEntry 6 }
 
      dot5TimerActiveMon  OBJECT-TYPE
             SYNTAX  INTEGER
             ACCESS  read-only
             STATUS  mandatory
             DESCRIPTION
                 "The time-out value used by the active
                 monitor to stimulate the enqueuing of an
                 AMP PDU for transmission, in units of
                 100 micro-seconds.
                 Implementors are encouraged to provide
                 read-write access to this object if that is
                 possible/useful in their system, but giving
                 due consideration to the dangers of
                 write-able timers."
             ::= { dot5TimerEntry 7 }
 
      dot5TimerStandbyMon  OBJECT-TYPE
             SYNTAX  INTEGER
             ACCESS  read-only
             STATUS  mandatory
             DESCRIPTION
                 "The time-out value used by the stand-by
                 monitors to ensure that there is an active
                 monitor on the ring and to detect a
                 continuous stream of tokens, in units of
                 100 micro-seconds.
                 Implementors are encouraged to provide
                 read-write access to this object if that is
                 possible/useful in their system, but giving
                 due consideration to the dangers of
                 write-able timers."
             ::= { dot5TimerEntry 8 }
 
      dot5TimerErrorReport  OBJECT-TYPE
             SYNTAX  INTEGER
             ACCESS  read-only
             STATUS  mandatory
             DESCRIPTION
                 "The time-out value which determines how
                 often a station shall send a Report Error
                 MAC frame to report its error counters,
                 in units of 100 micro-seconds.
                 Implementors are encouraged to provide
                 read-write access to this object if that is
                 possible/useful in their system, but giving
                 due consideration to the dangers of
                 write-able timers."
             ::= { dot5TimerEntry 9 }
 
      dot5TimerBeaconTransmit  OBJECT-TYPE
             SYNTAX  INTEGER
             ACCESS  read-only
             STATUS  mandatory
             DESCRIPTION
                 "The time-out value which determines how
                 long a station shall remain in the state
                 of transmitting Beacon frames before
                 entering the Bypass state, in units of
                 100 micro-seconds.
                 Implementors are encouraged to provide
                 read-write access to this object if that is
                 possible/useful in their system, but giving
                 due consideration to the dangers of
                 write-able timers."
             ::= { dot5TimerEntry 10 }
 
      dot5TimerBeaconReceive  OBJECT-TYPE
             SYNTAX  INTEGER
             ACCESS  read-only
             STATUS  mandatory
             DESCRIPTION
                 "The time-out value which determines how
                 long a station shall receive Beacon
                 frames from its downstream neighbor
                 before entering the Bypass state, in
                 units of 100 micro-seconds.
                 Implementors are encouraged to provide
                 read-write access to this object if that is
                 possible/useful in their system, but giving
                 due consideration to the dangers of
                 write-able timers."
             ::= { dot5TimerEntry 11 }
 
 
      --              802.5 Interface Tests
 
      dot5Tests     OBJECT IDENTIFIER ::= { dot5 3 }
 
      -- The extensions to the interfaces table proposed in [11]
      -- define a table object, ifExtnsTestTable, through which a
      -- network manager can instruct an agent to test an interface
      -- for various faults.  A test to be performed is identified
      -- (as the value of ifExtnsTestType) via an OBJECT IDENTIFIER.
      --
      -- The Full-Duplex Loop Back Test is a common test, defined
      -- in [11] as:
      --
      --    testFullDuplexLoopBack
      --
      -- Invoking this test on a 802.5 interface causes the
      -- interface to check the path from memory through the
      -- chip set's internal logic and back to memory, thus
      -- checking the proper functioning of the system's
      -- interface to the chip set.
 
      -- The Insert Function test is defined by:
 
      testInsertFunc    OBJECT IDENTIFIER ::= { dot5Tests 1 }
 
      -- Invoking this test causes the station to test the insert
      -- ring logic of the hardware if the station's lobe media
      -- cable is connected to a wiring concentrator.  Note that
      -- this command inserts the station into the network, and
      -- thus, could cause problems if the station is connected
      -- to a operational network.
 
      --         802.5 Hardware Chip Sets
 
      dot5ChipSets   OBJECT IDENTIFIER ::= { dot5 4 }
 
      -- The extensions to the interfaces table proposed in [11]
      -- define an object, ifExtnsChipSet, with the SYNTAX  of
      -- OBJECT IDENTIFIER, to identify the hardware chip set in
      -- use by an interface.  That definition specifies just
      -- one applicable object identifier:
      --
      --    unknownChipSet
      --
      -- for use as the value of ifExtnsChipSet when the specific
      -- chip set is unknown.
      --
      -- This MIB defines the following for use as values of
      -- ifExtnsChipSet:
 
         -- IBM 16/4 Mb/s
      chipSetIBM16       OBJECT IDENTIFIER ::= { dot5ChipSets 1 }
 
         -- TI 4Mb/s
      chipSetTItms380    OBJECT IDENTIFIER ::= { dot5ChipSets 2 }
 
         -- TI 16/4 Mb/s
      chipSetTItms380c16 OBJECT IDENTIFIER ::= { dot5ChipSets 3 }

    --
    -- The PPP Group
    --
    -- This is the draft standard MIB, which is defined as a private MIB
    -- until it becomes a full standard.
    --
    --
    -- The PPP Link Group. Implementation of this
    -- group is mandatory for all PPP entities.
    --

          pppLinkStatusTable  OBJECT-TYPE
               SYNTAX  SEQUENCE OF PppLinkStatusEntry
               ACCESS  not-accessible
               STATUS  mandatory
               DESCRIPTION
                   "A table containing PPP-link specific variables
                   for this PPP implementation."
               ::= { pppLink 1 }


          pppLinkStatusEntry  OBJECT-TYPE
               SYNTAX  PppLinkStatusEntry
               ACCESS  not-accessible
               STATUS  mandatory
               DESCRIPTION
                   "Management information about a particular PPP Link."
               INDEX     { pppLinkStatusIfIndex }
               ::= { pppLinkStatusTable 1 }


          PppLinkStatusEntry ::= SEQUENCE {
               pppLinkStatusIfIndex
                    INTEGER,
               pppLinkStatusPhysicalIndex
                    INTEGER,
               pppLinkStatusBadAddresses
                    Counter,
               pppLinkStatusBadControls
                    Counter,
               pppLinkStatusPacketTooLongs
                    Counter,
               pppLinkStatusBadFCSs
                    Counter,
               pppLinkStatusLocalMRU
                    INTEGER,
               pppLinkStatusRemoteMRU
                    INTEGER,
               pppLinkStatusLocalToPeerACCMap
                    OCTET STRING,
               pppLinkStatusPeerToLocalACCMap
                    OCTET STRING,
               pppLinkStatusLocalToRemoteProtocolCompression
                    INTEGER,
               pppLinkStatusRemoteToLocalProtocolCompression
                    INTEGER,
               pppLinkStatusLocalToRemoteACCompression
                    INTEGER,
               pppLinkStatusRemoteToLocalACCompression
                    INTEGER,
               pppLinkStatusTransmitFcsSize
                    INTEGER,
               pppLinkStatusReceiveFcsSize
                    INTEGER
               }

          pppLinkStatusIfIndex  OBJECT-TYPE
               SYNTAX  INTEGER
               ACCESS  read-only
               STATUS  mandatory
               DESCRIPTION
                   "A unique value for each PPP link. Its value
                   ranges between 1 and the value of ifNumber. The
                   interface identified by a particular value of
                   this index is that identified by the same value
                   of an ifIndex object instance. The value for
                   each link must remain constant at least from
                   one re-initialization of the entity's network
                   management system to the next re-initialization."
               ::= { pppLinkStatusEntry 1 }


          pppLinkStatusPhysicalIndex  OBJECT-TYPE
               SYNTAX  INTEGER
               ACCESS  read-only
               STATUS  mandatory
               DESCRIPTION
                   "The value of ifIndex that identifies the
                   interface over which this PPP Link is
                   operating. This interface would usually be an
                   HDLC or RS-232 type of interface. If there is
                   no lower-layer interface element, or there is
                   no ifEntry for the element, or the element can
                   not be identified, then the value of this
                   object is 0."
               ::= { pppLinkStatusEntry 2 }


          pppLinkStatusBadAddresses  OBJECT-TYPE
               SYNTAX  Counter
               ACCESS  read-only
               STATUS  mandatory
               DESCRIPTION
                   "The number of packets received with an
                   incorrect Address Field. This counter is a
                   component of the ifInErrors variable that is
                   associated with the interface that represents
                   this PPP Link."
               REFERENCE
                   "Section 3.1, Address Field, of RFC1331."
               ::= { pppLinkStatusEntry 3 }


          pppLinkStatusBadControls  OBJECT-TYPE
               SYNTAX  Counter
               ACCESS  read-only
               STATUS  mandatory
               DESCRIPTION
                   "The number of packets received on this link
                   with an incorrect Control Field. This counter
                   is a component of the ifInErrors variable that
                   is associated with the interface that
                   represents this PPP Link."
               REFERENCE
                   "Section 3.1, Control Field, of RFC1331."
               ::= { pppLinkStatusEntry 4 }


          pppLinkStatusPacketTooLongs  OBJECT-TYPE
               SYNTAX  Counter
               ACCESS  read-only
               STATUS  mandatory
               DESCRIPTION
                   "The number of received packets that have been
                   discarded because their length exceeded the
                   MRU. This counter is a component of the
                   ifInErrors variable that is associated with the
                   interface that represents this PPP Link. NOTE,
                   packets which are longer than the MRU but which
                   are successfully received and processed are NOT
                   included in this count."
               ::= { pppLinkStatusEntry 5 }


          pppLinkStatusBadFCSs  OBJECT-TYPE
               SYNTAX  Counter
               ACCESS  read-only
               STATUS  mandatory
               DESCRIPTION
                   "The number of received packets that have been
                   discarded due to having an incorrect FCS. This
                   counter is a component of the ifInErrors
                   variable that is associated with the interface
                   that represents this PPP Link."
               ::= { pppLinkStatusEntry 6 }


          pppLinkStatusLocalMRU  OBJECT-TYPE
               SYNTAX  INTEGER (1..2147483648)
               ACCESS  read-only
               STATUS  mandatory
               DESCRIPTION
                   "The current value of the MRU for the local PPP
                   Entity. This value is the MRU that the remote
                   entity is using when sending packets to the
                   local PPP entity."
               ::= { pppLinkStatusEntry 7 }


          pppLinkStatusRemoteMRU  OBJECT-TYPE
               SYNTAX  INTEGER (1..2147483648)
               ACCESS  read-only
               STATUS  mandatory
               DESCRIPTION
                   "The current value of the MRU for the remote
                   PPP Entity. This value is the MRU that the
                   local entity is using when sending packets to
                   the remote PPP entity."
               ::= { pppLinkStatusEntry 8 }


          pppLinkStatusLocalToPeerACCMap  OBJECT-TYPE
               SYNTAX  OCTET STRING (SIZE (4))
               ACCESS  read-only
               STATUS  mandatory
               DESCRIPTION
                   "The current value of the ACC Map used for
                   sending packets from the local PPP entity to
                   the remote PPP entity."
               ::= { pppLinkStatusEntry 9 }


          pppLinkStatusPeerToLocalACCMap  OBJECT-TYPE
               SYNTAX  OCTET STRING (SIZE (4))
               ACCESS  read-only
               STATUS  mandatory
               DESCRIPTION
                   "The ACC Map used by the remote PPP entity when
                   transmitting packets to the local PPP entity."
               ::= { pppLinkStatusEntry 10 }


          pppLinkStatusLocalToRemoteProtocolCompression  OBJECT-TYPE
               SYNTAX  INTEGER {
                         enabled(1),
                         disabled(2)
                         }
               ACCESS  read-only
               STATUS  mandatory
               DESCRIPTION
                   "Indicates whether the local PPP entity will
                   use Protocol Compression when transmitting
                   packets to the remote PPP entity."
               ::= { pppLinkStatusEntry 11 }


          pppLinkStatusRemoteToLocalProtocolCompression  OBJECT-TYPE
               SYNTAX  INTEGER {
                         enabled(1),
                         disabled(2)
                         }
               ACCESS  read-only
               STATUS  mandatory
               DESCRIPTION
                   "Indicates whether the remote PPP entity will
                   use Protocol Compression when transmitting
                   packets to the local PPP entity."
               ::= { pppLinkStatusEntry 12 }


          pppLinkStatusLocalToRemoteACCompression  OBJECT-TYPE
               SYNTAX  INTEGER {
                         enabled(1),
                         disabled(2)
                         }
               ACCESS  read-only
               STATUS  mandatory
               DESCRIPTION
                   "Indicates whether the local PPP entity will
                   use Address and Control Compression when
                   transmitting packets to the remote PPP entity."
               ::= { pppLinkStatusEntry 13 }


          pppLinkStatusRemoteToLocalACCompression  OBJECT-TYPE
               SYNTAX  INTEGER {
                         enabled(1),
                         disabled(2)
                         }
               ACCESS  read-only
               STATUS  mandatory
               DESCRIPTION
                   "Indicates whether the remote PPP entity will
                   use Address and Control Compression when
                   transmitting packets to the local PPP entity."
               ::= { pppLinkStatusEntry 14 }


          pppLinkStatusTransmitFcsSize  OBJECT-TYPE
               SYNTAX  INTEGER (0..128)
               ACCESS  read-only
               STATUS  mandatory
               DESCRIPTION
                   "The size of the Frame Check Sequence (FCS) in
                   bits that the local node will generate when
                   sending packets to the remote node."
               ::= { pppLinkStatusEntry 15 }


          pppLinkStatusReceiveFcsSize  OBJECT-TYPE
               SYNTAX  INTEGER (0..128)
               ACCESS  read-only
               STATUS  mandatory
               DESCRIPTION
                   "The size of the Frame Check Sequence (FCS) in
                   bits that the remote node will generate when
                   sending packets to the local node."
               ::= { pppLinkStatusEntry 16 }



          pppLinkConfigTable  OBJECT-TYPE
               SYNTAX  SEQUENCE OF PppLinkConfigEntry
               ACCESS  not-accessible
               STATUS  mandatory
               DESCRIPTION
                   "A table containing the LCP configuration
                   parameters for this PPP Link. These variables
                   represent the initial configuration of the PPP
                   Link. The actual values of the parameters may
                   be changed when the link is brought up via the
                   LCP options negotiation mechanism."
               ::= { pppLink 2 }


          pppLinkConfigEntry  OBJECT-TYPE
               SYNTAX  PppLinkConfigEntry
               ACCESS  not-accessible
               STATUS  mandatory
               DESCRIPTION
                   "Configuration information about a particular
                   PPP Link."
               INDEX     { pppLinkConfigIfIndex }
               ::= { pppLinkConfigTable 1 }


          PppLinkConfigEntry ::= SEQUENCE {
               pppLinkConfigIfIndex
                    INTEGER,
               pppLinkConfigInitialMRU
                    INTEGER,
               pppLinkConfigReceiveACCMap
                    OCTET STRING,
               pppLinkConfigTransmitACCMap
                    OCTET STRING,
               pppLinkConfigMagicNumber
                    INTEGER,
               pppLinkConfigFcsSize
                    INTEGER
               }

          pppLinkConfigIfIndex  OBJECT-TYPE
               SYNTAX  INTEGER
               ACCESS  read-only
               STATUS  mandatory
               DESCRIPTION
                   "A unique value for each PPP link. Its value
                   ranges between 1 and the value of ifNumber. The
                   interface identified by a particular value of
                   this index is that identified by the same value
                   of an ifIndex object instance. The value for
                   each link must remain constant at least from
                   one re-initialization of the entity's network
                   management system to the next re-initialization."
               ::= { pppLinkConfigEntry 1 }

    -- 
    -- The standard MIB says this can have a value up to 2**31 -1
    -- however, the protocol field only allows two bytes i.e Uint16.
    -- RX7000 limits the range for this object to 5 - 1530.
    --

          pppLinkConfigInitialMRU  OBJECT-TYPE
               SYNTAX  INTEGER (0..65535)
               ACCESS  read-write
               STATUS  mandatory
               DESCRIPTION
                   "The initial Maximum Receive Unit (MRU) that
                   the local PPP entity will advertise to the
                   remote entity. If the value of this variable is
                   0 then the local PPP entity will not advertise
                   any MRU to the remote entity and the default
                   MRU will be assumed. Changing this object will
                   have effect when the link is next restarted."
               REFERENCE
                   "Section 7.2, Maximum Receive Unit of RFC1331."
               DEFVAL    { 1500 }
               ::= { pppLinkConfigEntry 2 }


          pppLinkConfigReceiveACCMap  OBJECT-TYPE
               SYNTAX  OCTET STRING (SIZE (4))
               ACCESS  read-write
               STATUS  mandatory
               DESCRIPTION
                   "The Asynchronous-Control-Character-Map (ACC)
                   that the local PPP entity requires for use on
                   its receive side. In effect, this is the ACC
                   Map that is required in order to ensure that
                   the local modem will successfully receive all
                   characters. The actual ACC map used on the
                   receive side of the link will be a combination
                   of the local node's pppLinkConfigReceiveACCMap
                   and the remote node's
                   pppLinkConfigTransmitACCMap. Changing this
                   object will have effect when the link is next
                   restarted."
               REFERENCE
                   "Section 7.3, page 4, Async-Control-Character-
                   Map of RFC1331."
               DEFVAL    { 'ffffffff'h }
               ::= { pppLinkConfigEntry 3 }


          pppLinkConfigTransmitACCMap  OBJECT-TYPE
               SYNTAX  OCTET STRING (SIZE (4))
               ACCESS  read-write
               STATUS  mandatory
               DESCRIPTION
                   "The Asynchronous-Control-Character-Map (ACC)
                   that the local PPP entity requires for use on
                   its transmit side. In effect, this is the ACC
                   Map that is required in order to ensure that
                   all characters can be successfully transmitted
                   through the local modem.  The actual ACC map
                   used on the transmit side of the link will be a
                   combination of the local node's
                   pppLinkConfigTransmitACCMap and the remote
                   node's pppLinkConfigReceiveACCMap. Changing
                   this object will have effect when the link is
                   next restarted."
               REFERENCE
                   "Section 7.3, page 4, Async-Control-Character-
                   Map of RFC1331."
               DEFVAL    { 'ffffffff'h }
               ::= { pppLinkConfigEntry 4 }


          pppLinkConfigMagicNumber  OBJECT-TYPE
               SYNTAX  INTEGER {
                         false (1),
                         true (2)
                         }
               ACCESS  read-write
               STATUS  mandatory
               DESCRIPTION
                   "If true(2) then the local node will attempt to
                   perform Magic Number negotiation with the
                   remote node. If false(1) then this negotiation
                   is not performed. In any event, the local node
                   will comply with any magic number negotiations
                   attempted by the remote node, per the PPP
                   specification. Changing this object will have
                   effect when the link is next restarted."
               REFERENCE
                   "Section 7.6, Magic Number, of RFC1331."
               DEFVAL    { false }
               ::= { pppLinkConfigEntry 5 }


          pppLinkConfigFcsSize  OBJECT-TYPE
               SYNTAX  INTEGER (0..128)
               ACCESS  read-write
               STATUS  mandatory
               DESCRIPTION
                   "The size of the FCS, in bits, the local node
                   will attempt to negotiate for use with the
                   remote node. Regardless of the value of this
                   object, the local node will comply with any FCS
                   size negotiations initiated by the remote node,
                   per the PPP specification. Changing this object
                   will have effect when the link is next
                   restarted."
               DEFVAL    { 16 }
               ::= { pppLinkConfigEntry 6 }

    
    --
    -- The PPP IP Group.
    -- Implementation of this group is mandatory for all
    -- PPP implementations that support operating IP over PPP.
    --

          pppIpTable  OBJECT-TYPE
               SYNTAX  SEQUENCE OF PppIpEntry
               ACCESS  not-accessible
               STATUS  mandatory
               DESCRIPTION
                   "Table containing the IP parameters and
                   statistics for the local PPP entity."
               ::= { pppIp 1 }


          pppIpEntry  OBJECT-TYPE
               SYNTAX  PppIpEntry
               ACCESS  not-accessible
               STATUS  mandatory
               DESCRIPTION
                  "IPCP status information for a particular PPP
                   link.
                   A SNMP error of noSuchName is returned to a request
                   for an object in this table for which the index identifies
                   an IP port which is attached to a physical port which
                   is not a PPP physical port."
               INDEX     { pppIpIndex }
               ::= { pppIpTable 1 }

          PppIpEntry ::= SEQUENCE {
               pppIpIndex
                    INTEGER,
               pppIpOperStatus
                    INTEGER,
               pppIpLocalToRemoteCompressionProtocol
                    INTEGER,
               pppIpRemoteToLocalCompressionProtocol
                    INTEGER,
               pppIpRemoteMaxSlotId
                    INTEGER,
               pppIpLocalMaxSlotId
                    INTEGER
                 }

          pppIpIndex  OBJECT-TYPE
               SYNTAX  INTEGER
               ACCESS  read-only
               STATUS  mandatory
               DESCRIPTION
                   "The value of ifIndex that identifies the entry
                    in the ifTable that is associated with the PPP
                    Link over which this instance of the IP network
                    and control protocol are operating."
               ::= { pppIpEntry 1 }


          pppIpOperStatus  OBJECT-TYPE
               SYNTAX  INTEGER {
                         opened(1), 
                         not-opened(2)
                         }
               ACCESS  read-only
               STATUS  mandatory
               DESCRIPTION
                   "The operational status of the IP network
                    protocol. If the value of this object is opened(1)
                    then the finite state machine for the IP
                    network protocol has reached the Opened state."
               ::= { pppIpEntry 2 }


          pppIpLocalToRemoteCompressionProtocol  OBJECT-TYPE
               SYNTAX  INTEGER {
                         none(1),
                         vj-tcp(2)
                    }
               ACCESS  read-only
               STATUS  mandatory
               DESCRIPTION
                   "The IP compression protocol that the local
                   PPP-IP entity uses when sending packets to the
                   remote PPP-IP entity."
               ::= { pppIpEntry 3 }


          pppIpRemoteToLocalCompressionProtocol  OBJECT-TYPE
               SYNTAX  INTEGER {
                         none(1),
                         vj-tcp(2)
                    }
               ACCESS  read-only
               STATUS  mandatory
               DESCRIPTION
                   "The IP compression protocol that the remote
                   PPP-IP entity uses when sending packets to the
                   local PPP-IP entity."
               ::= { pppIpEntry 4 }


          pppIpRemoteMaxSlotId  OBJECT-TYPE
               SYNTAX  INTEGER(0..255)
               ACCESS  read-only
               STATUS  mandatory
               DESCRIPTION
                   "The Max-Slot-Id parameter that the remote node
                   has advertised and that is in use on the link.
                   If vj-tcp header compression is not in use on
                   the link then the value of this object shall be
                   0."
               ::= { pppIpEntry 5 }


          pppIpLocalMaxSlotId  OBJECT-TYPE
               SYNTAX  INTEGER(0..255)
               ACCESS  read-only
               STATUS  mandatory
               DESCRIPTION
                   "The Max-Slot-Id parameter that the local node
                    has advertised and that is in use on the link.
                    If vj-tcp header compression is not in use on
                    the link then the value of this object shall be
                    0."
               ::= { pppIpEntry 6 }


          --
          -- The PPP IP Configuration table.
          -- This is a separate table in order to facilitate
          -- placing these variables in a separate MIB view.
          --

          pppIpConfigTable  OBJECT-TYPE
               SYNTAX  SEQUENCE OF PppIpConfigEntry
               ACCESS  not-accessible
               STATUS  mandatory
               DESCRIPTION
                   "Table containing configuration variables for
                   the IPCP for the local PPP entity."
               ::= { pppIp 2 }


          pppIpConfigEntry  OBJECT-TYPE
               SYNTAX  PppIpConfigEntry
               ACCESS  not-accessible
               STATUS  mandatory
               DESCRIPTION
                  "IPCP information for a particular PPP link.
                   A SNMP error of noSuchName is returned to a request
                   for an object in this table for which the index identifies
                   an IP port which is attached to a physical port which
                   is not a PPP physical port."
               INDEX     { pppIpConfigIndex }
               ::= { pppIpConfigTable 1 }



          PppIpConfigEntry ::= SEQUENCE {
               pppIpConfigIndex
                    INTEGER,
               pppIpConfigAdminStatus
                    INTEGER,
               pppIpConfigCompression
                    INTEGER
          }

          pppIpConfigIndex  OBJECT-TYPE
               SYNTAX  INTEGER
               ACCESS  read-only
               STATUS  mandatory
               DESCRIPTION
                   "The value of ifIndex that identifies the entry
                   in the ifTable that is associated with the
                   local IPCP entity."
               ::= { pppIpConfigEntry 1 }


          pppIpConfigAdminStatus  OBJECT-TYPE
               SYNTAX  INTEGER {open(1), close(2)}
               ACCESS  read-write
               STATUS  mandatory
               DESCRIPTION
                   "The immediate desired status of the IP network
                   protocol. Setting this object to open will
                   inject an administrative open event into the IP
                   network protocol's finite state machine.
                   Setting this object to close will inject an
                   administrative close event into the IP network
                   protocol's finite state machine."
               ::= { pppIpConfigEntry 2 }


          pppIpConfigCompression  OBJECT-TYPE
               SYNTAX  INTEGER {
                         none(1),
                         vj-tcp(2)
                    }
               ACCESS  read-write
               STATUS  mandatory
               DESCRIPTION
                   "If none(1) then the local node will not
                   attempt to negotiate any IP Compression option.
                   Otherwise, the local node will attempt to
                   negotiate compression mode indicated by the
                   enumerated value. Changing this object will
                   have effect when the link is next restarted."
               REFERENCE
                   "Section 4.0, Van Jacobson TCP/IP Header
                   Compression of RFC1332."
               DEFVAL    { none }
               ::= { pppIpConfigEntry 3 }

    --
    -- Definition of the enterprise specific traps for the RX7000
    --
 
--   logicalPortUp  TRAP-TYPE
--     ENTERPRISE  { retix }
--     VARIABLES  { portLgclPortID }
--     DESCRIPTION
--        "This trap signifies that a logical port identified by
--         portLgclPortID has come on-line, i.e. the value of
--         the ifAdminStatus object for this port is now up(1)."
--     ::= { 10 }
 
--   logicalPortDown  TRAP-TYPE
--     ENTERPRISE  { retix }
--     VARIABLES  { portLgclPortID }
--     DESCRIPTION
--        "This trap signifies that a logical port identified by
--         portLgclPortID has gone off-line, i.e. the value of
--         the ifAdminStatus object for this port is now down(2)."
--     ::= { 11 }
 
--    forwardingProcessorUp    TRAP-TYPE
--     ENTERPRISE  { retix }
--     VARIABLES  { stnSlotIndex }
--     DESCRIPTION
--       "This trap signifies that the forwarding processor identified
--        by stnSlotIndex has passed its diagnostic checks, has been
--        downloaded with the appropriate code and may have ports
--        available for data transfer."
--     ::= { 12 }
 
--   forwardingProcessorDown  TRAP-TYPE
--     ENTERPRISE  { retix }
--     VARIABLES  { stnSlotIndex }
--     DESCRIPTION
--       "This trap signifies that the forwarding processor identified
--        by stnSlotIndex has been partitioned (action by the manager)
--        or has experienced some malfunction."
--     ::= { 13 }
 
--   hardwareFailure  TRAP-TYPE
--     ENTERPRISE  { retix }
--     DESCRIPTION
--       "This trap signifies that a hardware failure has occurred in
--        the unit."
--     ::= { 14 }
 
--   temperatureOverheat TRAP-TYPE
--     ENTERPRISE  { retix }
--     DESCRIPTION
--       "This trap signifies that a processor or processors are over-
--        heating."
--     ::= { 15 }
 
--  powerSupplyFailure  TRAP-TYPE
--    ENTERPRISE  { retix }
--    DESCRIPTION
--      "This trap signifies that a power supply has failed on the
--       sending entity."
--    ::= { 16 }

    END
.encl
