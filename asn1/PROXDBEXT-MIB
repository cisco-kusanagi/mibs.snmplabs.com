PROXDBEXT-MIB 

   --FORCE-INCLUDE <mib.h>
   --FORCE-INCLUDE <snmpdefs.h>
   --FORCE-INCLUDE <snmpstat.h>
   --FORCE-INCLUDE "mibproto.h"
 
	DEFINITIONS ::= BEGIN

	IMPORTS
		MODULE-IDENTITY, OBJECT-TYPE, IpAddress, Integer32, Counter64
			FROM SNMPv2-SMI
		proxDbExt
			FROM APENT-MIB;

--PROXDBEXT MIB

    apProxDbExtMib MODULE-IDENTITY
	   LAST-UPDATED "9707202000Z" -- Wed July 20 20:00:00 EST 1997
	   ORGANIZATION "ArrowPoint Communications Inc."
	   CONTACT-INFO
	   "                Customer Support
	   Postal:          ArrowPoint Communications, Inc.
				  		50 Nagog Park
				  		Acton, Massachusetts 01720
	   Tel:             +1 978 206 3000
	   E-Mail:          mibsupport@arrowpoint.com"
       DESCRIPTION
	  "The MIB module used to describe the ArrowPoint Communications Tiered
	  Proximity Database functionality.  This MIB contains all configuration,
	  statistic, and metric objects. "
      ::= { proxDbExt 1}

--Proximity Database Scalars

apProxDbTTLProbed OBJECT-TYPE
	SYNTAX			Integer32 (0..255)
	MAX-ACCESS		read-write
	STATUS			current
	DESCRIPTION
		"This object controls the response TTL associated with probed blocks"
	DEFVAL { 0 }
	::= {proxDbExt 2}

apProxDbTTLAssigned OBJECT-TYPE
	SYNTAX			Integer32 (0..255)
	MAX-ACCESS		read-write
	STATUS			current
	DESCRIPTION
		"This object controls the response TTL associated with assigned blocks"
	DEFVAL { 0 }
	::= {proxDbExt 3}
		  
--Proximity Database /8 Stats
apProxDb8StatTable OBJECT-TYPE
	SYNTAX          SEQUENCE OF APProxDb8StatEntry
	MAX-ACCESS      not-accessible
	STATUS          current
	DESCRIPTION
		"This table is used to expose the /8 database statistics"
	::= { proxDbExt 6}

apProxDb8StatEntry OBJECT-TYPE
	SYNTAX          APProxDb8StatEntry
	MAX-ACCESS      not-accessible
	STATUS          current
	DESCRIPTION
		""
	INDEX   { apProx8StatIpAddress }
	::= { apProxDb8StatTable 1 }

APProxDb8StatEntry ::= SEQUENCE {
		apProx8StatIpAddress     IpAddress,
		apProx8StatHitCount		 Counter64,
		apProx8StatAdvMask       Integer32
}

apProx8StatIpAddress OBJECT-TYPE
	SYNTAX          IpAddress
    MAX-ACCESS      read-only
	STATUS          current
	DESCRIPTION     
			"The IP address associated with this /8 database entry"
	::= { apProxDb8StatEntry 1}

apProx8StatHitCount OBJECT-TYPE
	SYNTAX			Counter64
	MAX-ACCESS		read-only
	STATUS			current
	DESCRIPTION
			"The number of hits on this /8 database entry.  This is an
			 aggregation of all hits occuring within the address space
			 encompassed by this /8 entry."
	::= {apProxDb8StatEntry 2}

apProx8StatAdvMask OBJECT-TYPE
	SYNTAX			Integer32
	MAX-ACCESS		read-only
	STATUS			current
	DESCRIPTION
			"The state of advertisement of entries contained under this
			/8.  Each bit corresponds to a zone index, bit 0 - zone 0, 
			bit 1 - zone 1.  When the bit is CLR all entries contained 
			under this /8 are synchronized.  When the bit is SET entries
			exist under this /8 that are NOT synchronized."
	::= {apProxDb8StatEntry 3}

--Proximity Database /16 Stats
apProxDb16StatTable OBJECT-TYPE
	SYNTAX          SEQUENCE OF APProxDb16StatEntry
	MAX-ACCESS      not-accessible
	STATUS          current
	DESCRIPTION
		"This table is used to expose the /16 database statistics"
	::= { proxDbExt 7}

apProxDb16StatEntry OBJECT-TYPE
	SYNTAX          APProxDb16StatEntry
	MAX-ACCESS      not-accessible
	STATUS          current
	DESCRIPTION
		""
	INDEX   { apProx16StatIpAddress }
	::= { apProxDb16StatTable 1 }

APProxDb16StatEntry ::= SEQUENCE {
		apProx16StatIpAddress     IpAddress,
		apProx16StatHitCount	  Integer32,
		apProx16StatAdvMask		  Integer32
}

apProx16StatIpAddress OBJECT-TYPE
	SYNTAX          IpAddress
    MAX-ACCESS      read-only
	STATUS          current
	DESCRIPTION     
			"The IP address associated with this /16 database entry"
	::= { apProxDb16StatEntry 1}

apProx16StatHitCount OBJECT-TYPE
	SYNTAX			Integer32
	MAX-ACCESS		read-only
	STATUS			current
	DESCRIPTION
			"The number of hits on this /16 database entry.  This is an
			 aggregation of all hits occuring within the address space
			 encompassed by this /16 entry."
	::= {apProxDb16StatEntry 2}

apProx16StatAdvMask OBJECT-TYPE
	SYNTAX			Integer32
	MAX-ACCESS		read-only
	STATUS			current
	DESCRIPTION
			"The state of advertisement of entries contained under this
			/16.  Each bit corresponds to a zone index, bit 0 - zone 0, 
			bit 1 - zone 1.  When the bit is CLR all entries contained 
			under this /16 are synchronized.  When the bit is SET entries
			exist under this /16 that are NOT synchronized."
	::= {apProxDb16StatEntry 3}

--Proximity Database /24 Stats
apProxDb24StatTable OBJECT-TYPE
	SYNTAX          SEQUENCE OF APProxDb24StatEntry
	MAX-ACCESS      not-accessible
	STATUS          current
	DESCRIPTION
		"This table is used to expose the /24 database statistics"
	::= { proxDbExt 8}

apProxDb24StatEntry OBJECT-TYPE
	SYNTAX          APProxDb24StatEntry
	MAX-ACCESS      not-accessible
	STATUS          current
	DESCRIPTION
		""
	INDEX   { apProx24StatIpAddress }
	::= { apProxDb24StatTable 1 }

APProxDb24StatEntry ::= SEQUENCE {
		apProx24StatIpAddress     IpAddress,
		apProx24StatHitCount	  Integer32,
		apProx24StatAdvMask		  Integer32
}

apProx24StatIpAddress OBJECT-TYPE
	SYNTAX          IpAddress
    MAX-ACCESS      read-only
	STATUS          current
	DESCRIPTION     
			"The IP address associated with this /24 database entry"
	::= { apProxDb24StatEntry 1}

apProx24StatHitCount OBJECT-TYPE
	SYNTAX			Integer32
	MAX-ACCESS		read-only
	STATUS			current
	DESCRIPTION
			"The number of hits on this /24 database entry.  This is an
			 aggregation of all hits occuring within the address space
			 encompassed by this /24 entry."
	::= {apProxDb24StatEntry 2}

apProx24StatAdvMask OBJECT-TYPE
	SYNTAX			Integer32
	MAX-ACCESS		read-only
	STATUS			current
	DESCRIPTION
			"The state of advertisement of entries contained under this
			/24.  Each bit corresponds to a zone index, bit 0 - zone 0, 
			bit 1 - zone 1.  When the bit is SET all entries contained 
			under this /24 are synchronized.  When the bit is CLEAR entries
			exist under this /24 that are NOT synchronized."
	::= {apProxDb24StatEntry 3}


--Proximity Database /Vpl Stats
apProxDbVplStatTable OBJECT-TYPE
	SYNTAX          SEQUENCE OF APProxDbVplStatEntry
	MAX-ACCESS      not-accessible
	STATUS          current
	DESCRIPTION
		"This table is used to expose the /Vpl database statistics"
	::= { proxDbExt 9}

apProxDbVplStatEntry OBJECT-TYPE
	SYNTAX          APProxDbVplStatEntry
	MAX-ACCESS      not-accessible
	STATUS          current
	DESCRIPTION
		""
	INDEX   { apProxVplStatIpAddress, apProxVplStatIpPrefix}
	::= { apProxDbVplStatTable 1 }

APProxDbVplStatEntry ::= SEQUENCE {
		apProxVplStatIpAddress     IpAddress,
		apProxVplStatIpPrefix      Integer32,
		apProxVplStatHitCount	   Integer32,
		apProxVplStatAdvMask	   Integer32
}

apProxVplStatIpAddress OBJECT-TYPE
	SYNTAX          IpAddress
    MAX-ACCESS      read-only
	STATUS          current
	DESCRIPTION     
			"The IP address associated with this /Vpl database entry"
	::= { apProxDbVplStatEntry 1}

apProxVplStatIpPrefix OBJECT-TYPE
	SYNTAX          Integer32
    MAX-ACCESS      read-only
	STATUS          current
	DESCRIPTION     
			"The IP prefix associated with this /Vpl database entry"
	::= { apProxDbVplStatEntry 2}

apProxVplStatHitCount OBJECT-TYPE
	SYNTAX			Integer32
	MAX-ACCESS		read-only
	STATUS			current
	DESCRIPTION
			"The number of hits on this /Vpl database entry.  This is an
			 aggregation of all hits occuring within the address space
			 encompassed by this /Vpl entry."
	::= {apProxDbVplStatEntry 3}

apProxVplStatAdvMask OBJECT-TYPE
	SYNTAX			Integer32
	MAX-ACCESS		read-only
	STATUS			current
	DESCRIPTION
			"The state of advertisement of entries contained under this
			/Vpl.  Each bit corresponds to a zone index, bit 0 - zone 0, 
			bit 1 - zone 1.  When the bit is SET all entries contained 
			under this /Vpl are synchronized.  When the bit is CLEAR entries
			exist under this /Vpl that are NOT synchronized."
	::= {apProxDbVplStatEntry 4}




--Proximity Database /8 Metrics
apProxDb8MetricTable OBJECT-TYPE
	SYNTAX          SEQUENCE OF APProxDb8MetricEntry
	MAX-ACCESS      not-accessible
	STATUS          current
	DESCRIPTION
		"This database is used to expose the /8 database metrics"
	::= { proxDbExt 10}

apProxDb8MetricEntry OBJECT-TYPE
	SYNTAX          APProxDb8MetricEntry
	MAX-ACCESS      not-accessible
	STATUS          current
	DESCRIPTION
		""
	INDEX   { apProx8MetricIpAddress, apProx8MetricZoneIndex }
	::= { apProxDb8MetricTable 1 }

APProxDb8MetricEntry ::= SEQUENCE {
		apProx8MetricIpAddress      IpAddress,
		apProx8MetricZoneIndex		Integer32,
		apProx8MetricValue			Integer32
}

apProx8MetricIpAddress OBJECT-TYPE
	SYNTAX          IpAddress
    MAX-ACCESS      read-only
	STATUS          current
	DESCRIPTION     
			"The IP address associated with this /8 database entry"
	::= { apProxDb8MetricEntry 1}

apProx8MetricZoneIndex OBJECT-TYPE
	SYNTAX			Integer32 (0 .. 16)
	MAX-ACCESS		read-only
	STATUS			current
	DESCRIPTION
		"The zone index associated with this /8 database entry"
	::= {apProxDb8MetricEntry 2}

apProx8MetricValue OBJECT-TYPE
	SYNTAX			Integer32 (0 .. 256)
	MAX-ACCESS		read-only
	STATUS			current
	DESCRIPTION
		"The metric associated with this /8 database entry"
	::= {apProxDb8MetricEntry 3}


--Proximity Database /16 Metrics
apProxDb16MetricTable OBJECT-TYPE
	SYNTAX          SEQUENCE OF APProxDb16MetricEntry
	MAX-ACCESS      not-accessible
	STATUS          current
	DESCRIPTION
		"This database is used to expose the /16 database metrics"
	::= { proxDbExt 11}

apProxDb16MetricEntry OBJECT-TYPE
	SYNTAX          APProxDb16MetricEntry
	MAX-ACCESS      not-accessible
	STATUS          current
	DESCRIPTION
		""
	INDEX   { apProx16MetricIpAddress, apProx16MetricZoneIndex }
	::= { apProxDb16MetricTable 1 }

APProxDb16MetricEntry ::= SEQUENCE {
		apProx16MetricIpAddress      IpAddress,
		apProx16MetricZoneIndex		Integer32,
		apProx16MetricValue			Integer32
}

apProx16MetricIpAddress OBJECT-TYPE
	SYNTAX          IpAddress
    MAX-ACCESS      read-only
	STATUS          current
	DESCRIPTION     
			"The IP address associated with this /16 database entry"
	::= { apProxDb16MetricEntry 1}

apProx16MetricZoneIndex OBJECT-TYPE
	SYNTAX			Integer32 (0 .. 15)
	MAX-ACCESS		read-only
	STATUS			current
	DESCRIPTION
		"The zone index associated with this /16 database entry"
	::= {apProxDb16MetricEntry 2}

apProx16MetricValue OBJECT-TYPE
	SYNTAX			Integer32 (0 .. 256)
	MAX-ACCESS		read-only
	STATUS			current
	DESCRIPTION
		"The metric associated with this /16 database entry"
	::= {apProxDb16MetricEntry 3}


--Proximity Database /24 Metrics
apProxDb24MetricTable OBJECT-TYPE
	SYNTAX          SEQUENCE OF APProxDb24MetricEntry
	MAX-ACCESS      not-accessible
	STATUS          current
	DESCRIPTION
		"This table is used to expose the /24 database metrics"
	::= { proxDbExt 12}

apProxDb24MetricEntry OBJECT-TYPE
	SYNTAX          APProxDb24MetricEntry
	MAX-ACCESS      not-accessible
	STATUS          current
	DESCRIPTION
		""
	INDEX   { apProx24MetricIpAddress, apProx24MetricZoneIndex }
	::= { apProxDb24MetricTable 1 }

APProxDb24MetricEntry ::= SEQUENCE {
		apProx24MetricIpAddress      IpAddress,
		apProx24MetricZoneIndex		Integer32,
		apProx24MetricValue			Integer32
}

apProx24MetricIpAddress OBJECT-TYPE
	SYNTAX          IpAddress
    MAX-ACCESS      read-only
	STATUS          current
	DESCRIPTION     
			"The IP address associated with this /24 database entry"
	::= { apProxDb24MetricEntry 1}

apProx24MetricZoneIndex OBJECT-TYPE
	SYNTAX			Integer32 (0 .. 15)
	MAX-ACCESS		read-only
	STATUS			current
	DESCRIPTION
		"The zone index associated with this /24 database entry"
	::= {apProxDb24MetricEntry 2}

apProx24MetricValue OBJECT-TYPE
	SYNTAX			Integer32 (0 .. 256)
	MAX-ACCESS		read-only
	STATUS			current
	DESCRIPTION
		"The metric associated with this /24 database entry"
	::= {apProxDb24MetricEntry 3}


--Proximity Database /VPL Metrics
apProxDbVplMetricTable OBJECT-TYPE
	SYNTAX          SEQUENCE OF APProxDbVplMetricEntry
	MAX-ACCESS      not-accessible
	STATUS          current
	DESCRIPTION
		"This table is used to expose the /Vpl database metrics"
	::= { proxDbExt 13}

apProxDbVplMetricEntry OBJECT-TYPE
	SYNTAX          APProxDbVplMetricEntry
	MAX-ACCESS      not-accessible
	STATUS          current
	DESCRIPTION
		""
	INDEX   { apProxVplMetricIpAddress, apProxVplMetricIpPrefix, apProxVplMetricZoneIndex }
	::= { apProxDbVplMetricTable 1 }

APProxDbVplMetricEntry ::= SEQUENCE {
		apProxVplMetricIpAddress        IpAddress,
		apProxVplMetricIpPrefix         Integer32,
		apProxVplMetricZoneIndex		Integer32,
		apProxVplMetricValue			Integer32
}

apProxVplMetricIpAddress OBJECT-TYPE
	SYNTAX          IpAddress
    MAX-ACCESS      read-only
	STATUS          current
	DESCRIPTION     
			"The IP address associated with this /Vpl database entry"
	::= { apProxDbVplMetricEntry 1}

apProxVplMetricIpPrefix OBJECT-TYPE
	SYNTAX          Integer32
    MAX-ACCESS      read-only
	STATUS          current
	DESCRIPTION     
			"The IP prefix associated with this /Vpl database entry"
	::= { apProxDbVplMetricEntry 2}

apProxVplMetricZoneIndex OBJECT-TYPE
	SYNTAX			Integer32 (0 .. 15)
	MAX-ACCESS		read-only
	STATUS			current
	DESCRIPTION
		"The zone index associated with this /Vpl database entry"
	::= {apProxDbVplMetricEntry 3}

apProxVplMetricValue OBJECT-TYPE
	SYNTAX			Integer32 (0 .. 256)
	MAX-ACCESS		read-only
	STATUS			current
	DESCRIPTION
		"The metric associated with this /Vpl database entry"
	::= {apProxDbVplMetricEntry 4}

END
