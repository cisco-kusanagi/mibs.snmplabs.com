-- ****************************************************************************
--                             gdc5002.mib
-- ****************************************************************************

-- Copyright 1994 General DataComm Inc., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.



-- ****************************************************************************
--                        Revision History
-- ****************************************************************************

-- Version   Date	Name/Description
--
-- 1.00A     14-Oct-94  M. Cyr 		Initial Revision
--
-- 1.00B     09-Nov-94  M. Cyr          Clean up and changes to the 
--                                      gdcDsx1ResetStats & gdcDsx1TestDuration
--                                      objects,renamed file to gdcdsx1.mib.
--
-- 1.00C     20-Dec-94  M. Cyr          Added alarms and network maintenance.
--                                      Cosmetic changes.
--
-- 1.00D     06-Jan-95  M. Cyr          Added attenuation variable to network
--                                      maintenance table. Added csuMode &
--                                      setTxClkSrc to Maintenace table. More
--                                      cosmetic changes.
--
-- 1.00E     02-Feb-95  M. Cyr          Fixed gdcDsx1ANSICRCerrorEvents enums.
--                                      MR#19 Onesdensity enum to 
--                                      restrict8xn+1.
--
-- 1.00F     27-Feb-95  M. Cyr          Added new variables for phase II.
--                                      Circuit Id's - RFC1406.mib extensions
--                                      Redundancy.
--
--                      J. Deptula      Changed DESCRIPTION of gdcDsx1Transmit
--                                      ClockSource and
--                                      gdcDsx1FallbackClockSource to cross
--			 		 reference gdcdsu.mib if Channel timing
--                                      selected. Added NMS553S branch to alarm
--                                      branch. Added gdcDsx1FarEndCurrentTable
--                                      gdcDsx1FarEndTotalTable and
--                                      gdcDsx1FarEndIntervalTable LOFC exten-
--                                      sions to rfc1406.mib.
--                                      Fixed DESCRIPTION of alarm OID in
--                                      gdcDsx1AlarmConfigIdentifier and
--					gdcDsx1AlarmStatusIdentifier.
--
-- 1.00G     30-Mar-95  J. Deptula      Moved nms553s branch to SNMP553-MIB
--                      M. Cyr          Added shelf(6) enum to gdcDsx1TransmitClockSource
--                                      and   shelf(9) enum to gdcDsx1FallbackClockSource.
--
-- 1.00H     29-Jun-95  J. Deptula      Added none(7) enumeration to 
--                                      gdcdsx1Preequalization variable
--
-- 1.00I     11-Jul-95  J. Deptula      Updated DESCRIPTION field for gdcdsx1NetMaintReceiveLevel
--			R. Strempel	Updated DESCRIPTION field for gdcDsx1AdminRcvRange
--
-- 1.00J     26-Jul-95  J. Deptula      Added	send511PatternWithLT(11),
--	 					send511PatternWithRT(12),
--	 					send2047PatternWithLT(13),
--        					send2047PatternWithRT(14),
--	 					sendQRSPatternWithLT(15),
--	 					sendQRSPatternWithRT(16),
--	 					sendProgPatternWithLT(17),
--         					sendProgPatternWithRT(18),
--	 					send3in24PatternWithRT(19)
--					enumerations to gdcDsx1SendCode variable.
--					Updated DESCRIPTION field for gdcDsx1SendCode.
--
-- 1.00K     01-Jul-96   S. Veillette
--                       1) added dsx1FallbackTimingActive as 
--                          OBJECT IDENTIFIER ::= { dsx1AlarmData 21 } to 
--                          the alarm mask table, to control the reporting of
--                          fallback timing active by shelf timing providers
--
-- 1.00L     14-Jan-96	 D. Baylis	Commented out Far End Performance Objects: 
--						gdcDsx1FarEndCurrentTable,
--				 		gdcDsx1FarEndIntervalTable, 
--						gdcDsx1FarEndTotalTable
--					And other Config Objects:
-- 	 					gdcDsx1FDLdcc, 
--  	 					gdcDsx1InbandLoopFraming, 
--						gdcDsx1MasRemSelect,
--						gdcDsx1ProgPattern, 
--         					gdcDsx1DiagTimingSource 
--
-- 1.00M     01-Aug-97   D. Baylis      Added download support
--
-- 1.00N     09-Sep-97   D. Baylis      Added gdcDsx1CurrenUserStat to gdcDsx1CurrentTable
-- ****************************************************************************




-- ****************************************************************************
--                          mib definitions begin
-- ****************************************************************************


 GDCDSX1-MIB DEFINITIONS ::= BEGIN

 IMPORTS
	 Gauge,enterprises,TimeTicks	FROM RFC1155-SMI
	 OBJECT-TYPE			FROM RFC-1212
	 DisplayString			FROM RFC1213-MIB
	 SCinstance			FROM GDCMACRO-MIB;

 gdc 		OBJECT IDENTIFIER ::= { enterprises 498 }
 dsx1		OBJECT IDENTIFIER ::= { gdc 6 }
 gdcDsx1System	OBJECT IDENTIFIER ::= { dsx1 1 }

 sc5001			OBJECT IDENTIFIER ::= { dsx1 2 }
 gdcDsx1Version		OBJECT IDENTIFIER ::= { gdcDsx1System 1 }
 gdcDsx1Maintenance	OBJECT IDENTIFIER ::= { gdcDsx1System 2 }
 gdcDsx1Configuration	OBJECT IDENTIFIER ::= { gdcDsx1System 3 }
 gdcDsx1Diagnostics	OBJECT IDENTIFIER ::= { gdcDsx1System 4 }
 gdcDsx1Performance 	OBJECT IDENTIFIER ::= { gdcDsx1System 5 }
 gdcDsx1Alarms		OBJECT IDENTIFIER ::= { gdcDsx1System 6 }
 gdcDsx1NetMaintenance	OBJECT IDENTIFIER ::= { gdcDsx1System 7 }

 -- This MIB module uses the extended OBJECT-TYPE macro as
 -- defined in RFC 1212.

 -- The implementation of all groups is mandatory for all products that
 -- support a DS1 interface.

 -- Note:  All rows in all tables defined within this MIB module are
 -- virtual.  They can neither be created or deleted by management
 -- operations.

 -- The Version Group. This group identifies the version information
 -- for the MIB.


 -- *****************************************************************************
 -- The interfaces are as follows:
 -- 	Unit 	  0
 --	Network   1
 -- 	Cascade   2
 -- *****************************************************************************

 gdcDsx1SystemMIBversion OBJECT-TYPE
     SYNTAX DisplayString (SIZE (5))
     ACCESS read-only
     STATUS mandatory
     DESCRIPTION
	 "Identifies the version of the MIB. The format of the version
	 is x.yzT, where 'x' identifies the major revision number, 'y'
	 identifies the minor revision number, 'z' identifies the
	 typographical revision, and T identifies the test revision.
	 Acceptable values for the individual revision components are
	 as follows:

		 x: 1 - 9
		 y: 0 - 9
		 z: 0 - 9
		 T: A - Z

	 Upon formal release, no designation for the test revision will
	 be present."
     ::= { gdcDsx1Version 1 }

gdcDsx1VersionTable OBJECT-TYPE
    SYNTAX SEQUENCE OF GdcDsx1VersionEntry
    ACCESS not-accessible
    STATUS mandatory
    DESCRIPTION " "
    ::= { gdcDsx1Version 2  }

gdcDsx1VersionEntry OBJECT-TYPE
    SYNTAX GdcDsx1VersionEntry
    ACCESS not-accessible
    STATUS mandatory
    DESCRIPTION
        "An entry in the GDC gdcDsx1 Version Table."
    INDEX	{ gdcDsx1VersionIndex }
    ::= { gdcDsx1VersionTable 1 }

GdcDsx1VersionEntry ::=
    SEQUENCE {
	gdcDsx1VersionIndex    		SCinstance,
	gdcDsx1FirmwareRev		DisplayString,
	gdcDsx1ModelNumber		DisplayString,	

	gdcDsx1ActiveFirmwareRev 	DisplayString,
	gdcDsx1StoredFirmwareRev	DisplayString,
	gdcDsx1BootRev			DisplayString,
	gdcDsx1StoredFirmwareStatus	INTEGER,
	gdcDsx1SwitchActiveFirmware	INTEGER,
	gdcDsx1DownloadingMode          INTEGER
			 
    }

gdcDsx1VersionIndex OBJECT-TYPE
    SYNTAX SCinstance
    ACCESS read-only
    STATUS mandatory
    DESCRIPTION
        "Identifies Version parameters associated with the managed object."
    ::= { gdcDsx1VersionEntry 1 }



gdcDsx1FirmwareRev OBJECT-TYPE
    SYNTAX DisplayString (SIZE(2))
    ACCESS read-only
    STATUS mandatory
    DESCRIPTION
        "The version number of the bootstrap firmware. 

    	The version number of the firmware, to allow products to know which
    	revision is installed.  The released version number is sequenced from
    	--, A-, ... AA, ... ZZ.  
	"
    ::= { gdcDsx1VersionEntry 2 }

 gdcDsx1ModelNumber		OBJECT-TYPE
	 SYNTAX	DisplayString (SIZE(0..16))
	 ACCESS	read-only
	 STATUS	mandatory
	 DESCRIPTION
		 "This variable is used to determine the type
		 of card family installed ex. SC5001, SC5002."
	 ::= { gdcDsx1VersionEntry 3 }


gdcDsx1ActiveFirmwareRev OBJECT-TYPE
    SYNTAX DisplayString (SIZE(8))
    ACCESS read-only
    STATUS mandatory
    DESCRIPTION
        "The version number of the firmware currently executing.

	The format is MM.NN.BB where:
	
		MM: Major Revision (0-99)
		NN: Minor Revision (0-99)
		BB: Bug Fix Revision (0-99)

 	 	"
    ::= { gdcDsx1VersionEntry 4 }

gdcDsx1StoredFirmwareRev OBJECT-TYPE
    SYNTAX DisplayString (SIZE(8))
    ACCESS read-only
    STATUS mandatory
    DESCRIPTION
        "The version number of the firmware stored (in a compressed format) 
         but not currently executing.

	
		MM: Major Revision (0-99)
		NN: Minor Revision (0-99)
		BB: Bug Fix Revision (0-99)

	"
    ::= { gdcDsx1VersionEntry 5 }

gdcDsx1BootRev OBJECT-TYPE
    SYNTAX DisplayString (SIZE(2))
    ACCESS read-only
    STATUS mandatory
    DESCRIPTION
        "The version number of the bootstrap firmware. 

    	The version number of the firmware, to allow products to know which
    	revision is installed.  The released version number is sequenced from
    	--, A-, ... AA, ... ZZ.  
	"
    ::= { gdcDsx1VersionEntry 6 }


gdcDsx1StoredFirmwareStatus OBJECT-TYPE
    SYNTAX INTEGER {
        statBlank(1),                       
        statDownLoading(2),
	statOK(3),
	statCheckSumBad(4),    
	statUnZipping(5),
	statBadUnZip(6)                    
    }
    ACCESS read-only
    STATUS mandatory
    DESCRIPTION
        "This object represents the state of the Non-Active or Stored firmware:

        statBlank(1)    	Factory Default                  
        statDownLoading(2)	In process of downloading firmware

	statOK(3)		Zipped version checksum succesful (OK to switch)
				(can set gdcDsx1SwitchActive to switchActive(2))
				
	statCheckSumBad(4)    	Failed checksum after download
	statUnZipping(5)	In process of uncompressing into active area
	statBadUnZip(6)      	Failed last uncompress              


	The object is read only.
	 "
    ::= { gdcDsx1VersionEntry 7 }


gdcDsx1SwitchActiveFirmware OBJECT-TYPE
    SYNTAX INTEGER {
        switchNorm(1),                  -- Read only
        switchActive(2)			-- Write only
    }
    ACCESS read-write
    STATUS mandatory
    DESCRIPTION
        "This object is used to switch the active executing firmware from the version 
	in gdcDsx1ActiveRev to the version in gdcDsx1StoredRev.

	When a  switchActive(2) is set (write only) the element will:
		1) reboot
		2) uncompress stored code into active area
		3) perform checksum on active area
		4) Set gdcDsx1StoredStatus object to indicate results
		5) If succesfull:
			update gdcDsx1ActiveFirmwareRev and gdcDsx1StoredFirmwareRev
			and begin executing
		   If failed: 
			replace active area with previous revision


	The switchNorm(1) enumeration will always be read. 

	Setting switchActive(2) when the gdcDsx1StoredStatus is not statOK(3) will
	result in an error.
	"
    ::= { gdcDsx1VersionEntry 8 }


gdcDsx1DownloadingMode OBJECT-TYPE
    SYNTAX INTEGER {
        disableAll(1),
        enableAndWait(2),
	enableAndSwitch(3)
    }
    ACCESS read-write
    STATUS mandatory
    DESCRIPTION
        "This object is used to configure the download mode:

        disableAll(1)		Prevents any firmware downloading to gdcDsx1

        enableAndWait(2)        Allows downloading zipped code to be stored only!
								
	enableAndSwitch(3)	Allows downloading and then unzips and begins executing
				the new code

	"
    ::= { gdcDsx1VersionEntry 9 }







 -- The GDC DS1 Group.  This group contains objects that support the
 -- specific management requirements for products that support a GDC
 -- DS1 interface.  This group augments the DS1 MIB defined in RFC 1406
 -- with GDC specific extensions.  The group contains tables for DS1
 -- maintenance, DS1 configuration management, DS1 performance
 -- management, and DS1 diagnostics.

 -- If the DS1 interface also supports alarm reporting, then the
 -- GDC Alarm Management MIB should be deployed for managing the alarm
 -- reporting of the DS1 Interface.

 -- ********************************************************************
 -- GDC DS1 Maintenance Table
 -- ********************************************************************

 gdcDsx1MaintenanceTable OBJECT-TYPE
	 SYNTAX	SEQUENCE OF GdcDsx1MaintenanceEntry
	 ACCESS	not-accessible
	 STATUS	mandatory
	 DESCRIPTION
		 "The table describes the maintenance objects for 
		 the unit and references the unit interface (cc = 00)."
	 ::= { gdcDsx1Maintenance 1  }

 gdcDsx1MaintenanceEntry OBJECT-TYPE
	 SYNTAX	GdcDsx1MaintenanceEntry
	 ACCESS	not-accessible
	 STATUS	mandatory
	 DESCRIPTION
		 "An entry in the GDC ltu Maintenance Configuration Table."
	 INDEX	{ gdcDsx1MaintenanceLineIndex }
	 ::= { gdcDsx1MaintenanceTable 1 }

 GdcDsx1MaintenanceEntry ::=
	 SEQUENCE {
		  gdcDsx1MaintenanceLineIndex
			 SCinstance,
		  gdcDsx1SoftReset
			 INTEGER,
		  --gdcDsx1MasRemSelect
		  --	 INTEGER,
		  gdcDsx1ConfigMode
			 INTEGER,
		  gdcDsx1FrontPanel
			 INTEGER,
		  gdcDsx1SysUpTime
			 TimeTicks,
		  gdcDsx1DefaultInit
			 INTEGER,
		  gdcDsx1ResetStats
			 INTEGER,
		  gdcDsx1LedStatus
			 OCTET STRING,
		 gdcDsx1SetTransmitClkSrc
			 INTEGER,
		 gdcDsx1CsuMode
			 INTEGER,
	 	 gdcDsx1CircuitIdentifier1
			 DisplayString,
	 	 gdcDsx1CircuitIdentifier2
			 DisplayString
	 }

 gdcDsx1MaintenanceLineIndex OBJECT-TYPE
	 SYNTAX	SCinstance
	 ACCESS	read-only
	 STATUS	mandatory
	 DESCRIPTION
		 "This object identifies Maintenance parameters associated
		 with the managed object."
	 ::= { gdcDsx1MaintenanceEntry 1 }

 gdcDsx1SoftReset 	OBJECT-TYPE
	 SYNTAX	INTEGER {
			 reset(1),
			 norm(2)
		 }
	 ACCESS	read-write
	 STATUS	mandatory
	 DESCRIPTION
		 "Supports the action of soft resetting the unit.  When this
		 object is set to reset(1), then the unit performs a soft
		 reset, whose meaning is specific to the type of unit being
		 managed. The value of norm(2) will be returned when 
		 the reset is complete.
		  
		 The value of norm(2) can not be set by management."

	 ::= { gdcDsx1MaintenanceEntry 2 }

--gdcDsx1MasRemSelect	OBJECT-TYPE
--	 SYNTAX	INTEGER {
--			 master(1),
--			 remote(2)
--		 }
--	 ACCESS	read-write
--	 STATUS	mandatory
--	 DESCRIPTION
--		 "'master' is selected depending upon the network
--		 topology.  Master is usually the source of timing
--		 for a network link and initiates diagnostic
--		 communications to a remote if there is no local
--		 access for network management.
--
--		  'remote' is selected usually at off-site locations
--		 and recovers timing from the network.  A remote 
--		 unit continually scans for a diagnostic communication
--		 to set up a network management link.
--
--		 Default value: master (1)"
--	 ::= { gdcDsx1MaintenanceEntry 3 }

 gdcDsx1ConfigMode 	OBJECT-TYPE
	 SYNTAX	INTEGER {
			 hardware(1),
			 software(2)
		 }
	 ACCESS	read-only
	 STATUS	mandatory
	 DESCRIPTION
		 "The hardware configuration mode of the unit. A unit may
		 be configured through hardware switches, jumper, straps, etc.
		 The value software(2) indicates that the unit is software
		 configurable.  The value of hardware(1) indicates that some
		 options are hard configured and that software
		 configuration is not permitted of these options.

		 The value of hardware(1) can not be set by management."

	 ::= { gdcDsx1MaintenanceEntry 4 }

 gdcDsx1FrontPanel 	OBJECT-TYPE
	 SYNTAX	INTEGER {
			 inhibit(1),
			 enable(2)
		 }
	 ACCESS	read-write
	 STATUS	mandatory
	 DESCRIPTION
		 "This variable is used to indicate whether the front
		 panel switches are operational or not.

		  'inhibit' refers to when the front panel switches are
		 not operational.

		  'enable' refers to when the front panel switches are
		 operational."

	 ::= { gdcDsx1MaintenanceEntry 5 }

 gdcDsx1SysUpTime 	OBJECT-TYPE
	 SYNTAX	TimeTicks
	 ACCESS	read-only
	 STATUS	mandatory
	 DESCRIPTION
		 "This variable is used to report the elapsed system tick
		 time for conversion to real time at the controller and is
		 not related to the sysUpTime referenced in MIB-II.
		 Upon power-up of the unit, the elapsed time is cleared.
		 The elapsed time counter rolls over upon reaching the
		 maximum count."
	 ::= { gdcDsx1MaintenanceEntry 6 }

 gdcDsx1DefaultInit	OBJECT-TYPE
	 SYNTAX	INTEGER {
			 factoryDefault(1),
			 normal(2)

		 }
	 ACCESS	read-write
	 STATUS	mandatory
	 DESCRIPTION
		 "This is used to allow the NonVolatile Configuration to 
		 be set to a factory default state.  When this value is set to
		 factoryDefault(1) the unit will perform
		 a reset to make the default configuration take affect. 
		 The value of normal(2) will be returned when the initialization
		 is complete.
		 The value of normal(2) can not be set by management."
	 ::= { gdcDsx1MaintenanceEntry 7 }

 gdcDsx1ResetStats 	OBJECT-TYPE
	 SYNTAX  INTEGER	{
			 norm(1),
			 reset(9)
		 }
	 ACCESS  read-write
	 STATUS  mandatory
	 DESCRIPTION
		 "Supports the action of soft resetting the dsx1ValidIntervals
		 object.  When this object is set to reset(9), then the unit
		 will reset the dsx1ValidIntervals object to zero.
		 The value of norm(1) can not be set by management."
	 ::= { gdcDsx1MaintenanceEntry 8 }

 gdcDsx1LedStatus OBJECT-TYPE
	 SYNTAX  OCTET STRING (SIZE(3))
	 ACCESS  read-only
	 STATUS  mandatory
	 DESCRIPTION
		 "Returns a bitwise snapshot of the front panel LED state.
		 Octet 1 bit 7 - not used
			 bit 6 - ON
			 bit 5 - INSV
			 bit 4 - RSP
			 bit 3 - TMG
			 bit 2 - EQ LAD
			 bit 1 - EQ 0'S
			 bit 0 - EQ NS

		 Octet 2 bit 7 - not used
			 bit 6 - EQ OOF
			 bit 5 - NTWK AIS
			 bit 4 - NTWK BPV
			 bit 3 - NTWK NS
			 bit 2 - NTWK OOF
			 bit 1 - ALM
			 bit 0 - TM
	 Octet 3 bit 7 - not used
			 bit 6 - ST
			 bit 5 - LT
			 bit 4 - RL
			 bit 3 - future use
			 bit 2 - future use
			 bit 1 - future use
			 bit 0 - future use"
	 ::= { gdcDsx1MaintenanceEntry 9 }

 gdcDsx1SetTransmitClkSrc 		OBJECT-TYPE
	 SYNTAX	INTEGER {
			 txClkSrc(1),
			 fallBackClkSrc(2)
		 }
	 ACCESS	read-write
	 STATUS	mandatory
	 DESCRIPTION
		 " 'txClkSrc' indicates the unit is using the optioned
		   clock source as indicated by the dsx1TransmitClockSource
		   variable in the RFC1406 mib or the gdcDsx1TransmitClockSource
		   variable in the gdcdsx1 mib.

		   'fallBackClkSrc' indicates the unit is using the optioned
		   clock source as indicated by the gdcDsx1FallbackClockSource
		   variable in the gdcdsx1 mib. "
	 ::= { gdcDsx1MaintenanceEntry 10 }

 gdcDsx1CsuMode 		OBJECT-TYPE
	 SYNTAX	INTEGER {
			 csuMode(1),
			 concentratorMode(2)
		 }
	 ACCESS	read-write
	 STATUS	mandatory
	 DESCRIPTION
		 " 'csuMode' indicates the unit is operating as a T1 channel
		   service unit with the payload from the network interface
		   connected to the payload of the cascade interface.

		   'concentratorMode' indicates the unit is operating as a T1
		    channel service unit with the T1 payloads groomed to 
		    cross connect within the shelf and the network and cascade
		    interfaces. "

	 ::= { gdcDsx1MaintenanceEntry 11 }

 gdcDsx1CircuitIdentifier1 OBJECT-TYPE
	 SYNTAX  DisplayString (SIZE(16))
	 ACCESS  read-write
	 STATUS  mandatory
	 DESCRIPTION
		 "Private data storage area of sixteen bytes."

	 ::= { gdcDsx1MaintenanceEntry 12 }

 gdcDsx1CircuitIdentifier2 OBJECT-TYPE
	 SYNTAX  DisplayString (SIZE(16))
	 ACCESS  read-write
	 STATUS  mandatory
	 DESCRIPTION
		"Private data storage area of sixteen bytes."

	 ::= { gdcDsx1MaintenanceEntry 13 }

 -- ********************************************************************
 -- GDC DS1 Network Maintenance Table
 -- ********************************************************************

 gdcDsx1NetMaintTable OBJECT-TYPE
	 SYNTAX	SEQUENCE OF GdcDsx1NetMaintEntry
	 ACCESS	not-accessible
	 STATUS	mandatory
	 DESCRIPTION
		 "The table describes the maintenance objects for 
		 the network and references the network interface (cc = 01)."
	 ::= { gdcDsx1NetMaintenance 1  }

 gdcDsx1NetMaintEntry OBJECT-TYPE
	 SYNTAX	GdcDsx1NetMaintEntry
	 ACCESS	not-accessible
	 STATUS	mandatory
	 DESCRIPTION
		 "An entry in the GDC ltu Network Maintenance Configuration 
		  Table."
	 INDEX	{ gdcDsx1NetMaintLineIndex }
	 ::= { gdcDsx1NetMaintTable 1 }

 GdcDsx1NetMaintEntry ::=
	 SEQUENCE {
		  gdcDsx1NetMaintLineIndex
			 SCinstance,
		  gdcDsx1NetMaintReceiveLevel
			 INTEGER,
		  gdcDsx1NetMaintAttenSense
			 INTEGER
	 }

 gdcDsx1NetMaintLineIndex OBJECT-TYPE
	 SYNTAX	SCinstance
	 ACCESS	read-only
	 STATUS	mandatory
	 DESCRIPTION
		 "This object identifies Maintenance parameters associated
		 with the managed object."
	 ::= { gdcDsx1NetMaintEntry 1 }

 gdcDsx1NetMaintReceiveLevel 	OBJECT-TYPE
	 SYNTAX	INTEGER (0..43)
	 ACCESS	read-only
	 STATUS	mandatory
	 DESCRIPTION
		 "This variable reports the absolute value of the network relative 
		 receive level of -40dB to +3dB when the gdcDsx1InterfaceType is set 
		 for ds1(1). This object interacts with the gdcDsx1NetMaintAttenSense
		 object in determining the unit's actual Receive Level."

	 ::= { gdcDsx1NetMaintEntry 2 }

 gdcDsx1NetMaintAttenSense 	OBJECT-TYPE
	 SYNTAX	INTEGER {
			 positive(1),
			 negative(2)
			 }
	 ACCESS  read-only
	 STATUS  mandatory
	 DESCRIPTION
		 "This variable identifies ths sense of the 
		  gdcdsx1NetReceiveLevel variable."

	 ::= { gdcDsx1NetMaintEntry 3 }

 -- ********************************************************************
 -- The GDC DS1 Configuration Table
 -- ********************************************************************


 gdcDsx1ConfigTable OBJECT-TYPE
     SYNTAX SEQUENCE OF GdcDsx1ConfigEntry
     ACCESS not-accessible
     STATUS mandatory
     DESCRIPTION
	 "The GDC DS1 Configuration table.  Information in the entries
	 of this table augment the entries in the DS1 Configuration
	 table of the DS1 MIB defined in RFC 1406."
     ::= { gdcDsx1Configuration 1 }

 gdcDsx1ConfigEntry OBJECT-TYPE
     SYNTAX GdcDsx1ConfigEntry
     ACCESS not-accessible
     STATUS mandatory
     DESCRIPTION
	 "The GDC DS1 Configuration table entry.  The information in
	 this entry augments the information for the corresponding
	 entry in the dsx1ConfigEntry of the DS1 MIB defined in RFC
	 1406."
     INDEX { gdcDsx1ConfigIndex }
     ::= { gdcDsx1ConfigTable 1 }

 GdcDsx1ConfigEntry ::= 
     SEQUENCE {
	 gdcDsx1ConfigIndex SCinstance,
	 gdcDsx1LineType INTEGER,
	 gdcDsx1InterfaceType INTEGER,
	 gdcDsx1Preequalization INTEGER,
	 gdcDsx1AdminLineBuildout INTEGER,
	 gdcDsx1OperLineBuildout INTEGER,
	 gdcDsx1AdminRcvRange INTEGER,
	 gdcDsx1OperRcvRange INTEGER,
	 gdcDsx1OnesDensity INTEGER,
	 gdcDsx1TransmitClockSource INTEGER,
	 gdcDsx1FallbackClockSource INTEGER,
-- 	 gdcDsx1FDLdcc INTEGER,
--  	 gdcDsx1InbandLoopFraming INTEGER,
	 gdcDsx1AISLoopdown INTEGER,
	 gdcDsx1InbandLoopCfg INTEGER,
	 gdcDsx1Redundancy     INTEGER

     }

 gdcDsx1ConfigIndex OBJECT-TYPE
     SYNTAX SCinstance
     ACCESS read-only
     STATUS mandatory
     DESCRIPTION
	 "The index value which uniquely identifies the interface to
	 which this entry is applicable.  This has the form of a
	 SCinstance which defines the slot, line, drop, and sub-identifier."
     ::= { gdcDsx1ConfigEntry 1 }

 gdcDsx1LineType OBJECT-TYPE
	 SYNTAX	INTEGER {
			 auto(1),
			 manEsf(2),
			 manD4(3),
			 unframed(4)
		 }
	 ACCESS  read-write
	 STATUS  mandatory
	 DESCRIPTION
		 "This variable indicates  the  variety  of  DS-X Line implementing 
		 this circuit.  The type of circuit affects the number of bits  per  
		 second that the circuit can reasonably carry, as well as the 
		 interpretation of the usage and error statistics.  
		 The values, in sequence, describe:


		  'auto' indicates the unit is still determining
		 framing when gdcDsx1LineType is set for auto (1)
		 dsx1LineType reads other(1).

		  'manEsf' indicates manual selection of extended
		 superframe format

		  'manD4'indicates manual selection of D4 framing 
		 format

		  'unframed' indicates manual selection of unframed
		 format

		 Reference rfc1406
		 
		 dsx1LineType		 gdcDsx1LineType
		  dsx1ESF (2) ============> manESF (2)
		  dsx1D4  (3) ============> manD4  (3)

		 All other values in dsx1LineType are not supported
		 at this time. 

		 Default value: manESF (2)"
	  ::= { gdcDsx1ConfigEntry 2 }

 gdcDsx1InterfaceType OBJECT-TYPE
     SYNTAX INTEGER {
	 other(1),		-- another type of interface
	 ds1(2),			-- DS1 mode
	 dsx1(3)			-- DSX-1 mode
     }
     ACCESS read-write
     STATUS mandatory
     DESCRIPTION 
	 "The operating mode of the interface.  Setting the value of
	 this object to ds1(2) configures the interface as
	 standard DS1.  Setting the value of this object to
	 dsx1(3) configures the interface to operate as a standard
	 cross-connect DSX-1. 

	 The value other(1) identifies another interface mode defined
	 elsewhere.  This value can never be set by management operation.

	 This object interoperates with the gdcDsx1Preequalization
	 object.  When this object is set to ds1(2), then the value of
	 gdcDsx1Preequalization does not apply.

	 This object interoperates with the gdcDsx1AdminLineBuildout object.
	 When this object is set to dsx1(3), then the value of
	 gdcDsx1LineBuildout does not apply.

	 This object interoperates with the gdcDsx1AdminLineBuildout
	 object.  When this object is set to dsx1(3), then the value of
	 gdcDsx1AutoLineBuildout does not apply.

	 This object interoperates with the gdcDsx1AdminReceiveRange object.
	 When this object is set to dsx1(3), then the value of
	 gdcDsx1ReceiveRange does not apply.

	 This object interoperates with the gdcDsx1AdminReceiveRange
	 object.  When this object is set to dsx1(3), then the value of
	 gdcDsx1AutoReceiveRange is set to disabled(2)."
     ::= { gdcDsx1ConfigEntry 3 }

 gdcDsx1Preequalization OBJECT-TYPE
     SYNTAX INTEGER {
	 other(1),		-- another preequalization
	 preeq130(2),		-- preequalization for 0 < 130 feet
	 preeq260(3),		-- preequalization for 130 < 260 feet
	 preeq390(4),		-- preequalization for 260 < 390 feet
	 preeq530(5),		-- preequalization for 390 < 530 feet
	 preeq655(6),		-- preequalization for 530 < 655 feet
         none(7)                -- no preequalization
     }
     ACCESS read-write
     STATUS mandatory
     DESCRIPTION
	 "Is the preequalization of the transmitter of the interface.

	 The value other(1) identifies an other preequalization value
	 which is defined elsewhere.  This value can never be set by
	 management operation.

	 This object interoperates with the object
	 gdcDsx1InterfaceType.  When the value of gdcDsx1InterfaceType
	 is ds1(2) then this value is not applicable."

     ::= { gdcDsx1ConfigEntry 4 }

 gdcDsx1AdminLineBuildout OBJECT-TYPE
	 SYNTAX	INTEGER {
			 auto(1),
			 man00dB(2),
			 man75dB(3),
			 man150dB(4)
		 }
	 ACCESS	read-write
	 STATUS	mandatory
	 DESCRIPTION
		 "This variable is used to set the Transmit Ntwk
		 Build-Out value on the network side and is only
		 valid if the gdcDsx1InterfaceType is set for ds1(1).  
		 The values, in sequence, describe:

		  'auto' indicates auto detection of receive level to
		 determine the appropriate Ntwk build out without
		 controller intervention

		  'man00dB' indicates manual selection of 0.0 dB 
		 transmit Ntwk build out

		  'man75dB' indicates manual selection of -7.5 dB 
		 transmit Ntwk build out

		  'man150dB' indicates manual selection of -15.0 dB 
		 transmit Ntwk build out

		 Set/get of auto requires a reading of gdcDsx1OperLineBuildOut 
		 to determine the selection of 
		 the Ntwk buildout.  Caution must be used when setting
		 auto since only one unit on a link can be in auto at
		 a given time.

		 Default value: man00dB (2)"
	     ::= { gdcDsx1ConfigEntry 5 }

 gdcDsx1OperLineBuildout OBJECT-TYPE
	 SYNTAX	INTEGER {
			 inProcess(1),
			 tx00dB(2),
			 tx75dB(3),
			 tx150dB(4)
		 }
	 ACCESS	read-only
	 STATUS	mandatory
	 DESCRIPTION
		 "This variable is used to report the current Ntwk
		 build-out setting if the gdcDsx1InterfaceType is set for ds1(1).

		  'inProcess' indicates the unit is still determining the
		 Ntwk build out required when the gdcDsx1AdminLineBuildout is
		 set for auto (1)

		  'tx00dB' indicates the unit is set for 0.0 dB of attenuation
		 when the gdcDsx1AdminLineBuildout is set for auto (1) or 
		 man00dB (2)

		  'tx75dB' indicates the unit is set for -7.5 dB of attenuation
		 when the gdcDsx1AdminLineBuildout is set for auto (1) or 
		 man75dB (3)

		  'tx150dB' indicates the unit is set for -15.0 dB of attenuation
		 when the gdcDsx1AdminLineBuildout is set for auto (1) or 
		 man150dB (4)"
     ::= { gdcDsx1ConfigEntry 6 }

 gdcDsx1AdminRcvRange 	OBJECT-TYPE
	 SYNTAX	INTEGER {
			 auto(1),
			 manNorm(2),
			 manExt(3)
		 }
	 ACCESS	read-write
	 STATUS	mandatory
	 DESCRIPTION
		 "This variable is used to set the receiver
		 circuitry for signal recovery ranges when gdcDsx1InterfaceType
		 is set for ds1 (1).  This function is not supported for
		 gdcDsx1InterfaceType set for dsx1 (2). Normal
		 range is considered 0 to -28 dB and extended
		 range is from -20 to -40 dB relative to a DS-1
		 launch pulse.  The values,in sequence, describe:

		  'auto' indicates auto selection of receiver range

		  'manNorm' indicates manual selection of normal range

		  'manExt' indicates manual selection of extended range

		 Set/get of auto requires a reading of 
		 gdcDsx1OperRcvRange to determine the selection of 
		 the receiver range. Caution must be used when setting
		 auto since only one unit on a link can be in auto at
		 a given time.

		 Default value: auto(1)"
	 ::= { gdcDsx1ConfigEntry 7 }

 gdcDsx1OperRcvRange 	OBJECT-TYPE
	 SYNTAX	INTEGER {
			 inProcess(1),
			 norm(2),
			 ext(3)
		 }
	 ACCESS	read-only
	 STATUS	mandatory
	 DESCRIPTION
		 "This variable is used to report the current receiver
		 range setting when gdcDsx1InterfaceType is set for ds1 (1).

		  'inProcess' indicates the unit is still determining
		 the required receiver range when the gdcDsx1AdminRcvRange is
		 set for auto (1)

		  'norm' indicates the receiver is set for normal range 
		 when the gdcDsx1AdminRcvRange is set for auto (1) or manNorm (2)

		  'ext' indicates the receiver is set for extended range
		 when the gdcDsx1AdminRcvRange is set for auto (1) or manExt (3)"

	 ::= { gdcDsx1ConfigEntry 8 }

 gdcDsx1OnesDensity OBJECT-TYPE
     SYNTAX INTEGER {
	 inhibit(1),			-- no minimum ones density
	 max15zeros(2),			-- maximum 15 zeros
	 max39zeros(3),			-- maximum 39 zeros
	 restrict8XNplus1(4),		-- minimum of N ones per 8(N+1) bits
	 min1in8(5)			-- minimum of 1 one per 8 bits
     }
     ACCESS read-write
     STATUS mandatory
     DESCRIPTION
	 "The ones density restriction for the interface.  The values
	 of this object define the ones density restriction that is
	 enforced on the interface.

	 The value inhibit(1) indicates that no ones density restriction
	 is enforced.

	 The value max15zeros(2) indicates that a maximum of 15 zeros
	 are transmitted to the network before a one is inserted.

	 The value max39zeros(3) indicates that a maximum of 39 zeros
	 are transmitted to the network before a one is inserted.

	 The value restrict8nX1(4) indicates a minimum of N ones per
	 8(N+1) bits, where N is in the range 1 to 24.

	 The value min1in8(5) indicates a minimum of 1 one per 8 bits.
	 With this value, pulse density violations are enforced but not
	 recorded."

     ::= { gdcDsx1ConfigEntry 9 }

 gdcDsx1TransmitClockSource OBJECT-TYPE
     SYNTAX INTEGER {
	 other(1),			-- other transmit clock source
	 station(2),			-- station transmit clock source
	 cascade(3),			-- cascade transmit clock source
	 channel(4),			-- channel transmit clock source
	 composite(5),			-- composite transmit clock source
	 shelf(6)			-- shelf transmit clock source
     }
     ACCESS read-write
     STATUS mandatory
     DESCRIPTION
	 "Augments the dsx1TransmitClockSource of the DS1 MIB of RFC
	 1406.  This object defines transmit clock sources that are not
	 defined by RFC 1406, but are supported by GDC DS1
	 interfaces.

	 The value other(1) indicates that the DS1 transmit clock
	 source is defined elsewhere.  The other values identify other
	 timing sources as indicated.

	 The value other(1) can never be set by management operation.

	 This object interoperates with the dsx1TransmitClockSource
	 object.  When the dsx1TransmitClockSource is set to
	 loopTiming(1) or localTiming(2), the value of this object
	 reflects other(1).  When the value of this object has a value
	 other than other(1), then the value of the
	 dsx1TransmitClockSource object reflects throughTiming(3).

         The value channel(4) interoperates with the 
	 gdcDsuChannelTransmitClockSource object.  When this value is
	 selected, gdcDsuChannelTransmitClockSource is set to the 
	 appropriate channel of the clock source for multi-channel 
	 products."

     ::= { gdcDsx1ConfigEntry 10 }

 gdcDsx1FallbackClockSource OBJECT-TYPE
     SYNTAX INTEGER {
	 other(1),			-- an other fallback clock source
	 none(2),			-- no fallback clock source
	 composite(3),			-- composite timing clock source
	 loopTiming(4),			-- loop timing clock source
	 channel(5),			-- channel timing clock source
	 cascade(6),			-- cascade timing clock sourc
	 localTiming(7),		-- local timing clock source
	 station(8),			-- station timing clock source
	 shelf(9)			-- shelf timing clock source
	}
     ACCESS read-write
     STATUS mandatory
     DESCRIPTION
	 "Identifies the fallback transmit clock source.  The value of
	 other(1) identifies another fallback transmit clock source
	 that is defined elsewhere.  The value of none(2) indicates no
	 fallback transmit clock source.

	 The value other(1) can never be set by management operation.

         The value channel(4) interoperates with the 
	 gdcDsuChannelTransmitClockSource object.  When this value is
	 selected, gdcDsuChannelTransmitClockSource is set to the 
	 appropriate channel of the clock source for multi-channel 
	 products."

    ::= { gdcDsx1ConfigEntry 11 }

-- gdcDsx1FDLdcc OBJECT-TYPE
--     SYNTAX INTEGER {
--	 enabled(1),			
--	 disabled(2)			
--     }
--     ACCESS read-write
--     STATUS mandatory
--     DESCRIPTION
--	 "Controls whether or not the DCC uses the FDL as its
--	 transport.  The FDL is only available when the DS1 line type
--	 is ESF, a full DS1 interface is being used, and transportation
--	 of the FDL completely through the network is supported.
--
--	 The value enabled(1) enables the transportation of the DCC
--	 using the FDL.  The value disabled(2) disables the use of the
--	 FDL to transport the DCC, which implies that the DCC is
--	 transported by some other means.
--
--	 This object interoperates with the dsx1LineType object.  The
--	 value of this object can be set to enabled(1) only when the
--	 value of the dsx1LineType is one of the ESF values."
--     ::= { gdcDsx1ConfigEntry 12 }

-- gdcDsx1InbandLoopFraming OBJECT-TYPE
--     SYNTAX INTEGER {
--     	framed(1),			
--     	unframed(2)	
--     }
--     ACCESS read-write
--     STATUS mandatory
--     DESCRIPTION
--     	"The framing mode to use when sending in-band loopcodes.  This
--     	object determines whether or not in-band loopcodes are framed
--     	when sent."
--     ::= { gdcDsx1ConfigEntry 13 }

 gdcDsx1AISLoopdown OBJECT-TYPE
     SYNTAX INTEGER (4..60)		-- 4, 5..60 seconds
     ACCESS read-write
     STATUS mandatory
     DESCRIPTION
	 "The time in seconds when receiving a continuous AIS signal
	 before a remotely initiated loopback is terminated.  When this
	 object has the value 4, then there is no time limit and the
	 loop must be terminated by remotely issued in-band loopdown
	 codes.  When the object has a value between 5 and 60, then
	 this is time in seconds of continuous AIS signal before
	 the loopback is terminated."
     ::= { gdcDsx1ConfigEntry 14 }

 gdcDsx1InbandLoopCfg 		OBJECT-TYPE
	 SYNTAX	INTEGER {
			 inhibit(1),
			 payload(2),
			 lineloop(3)
		 }
	 ACCESS	read-write
	 STATUS	mandatory
	 DESCRIPTION
		 "This variable is used to set the
		 In-Band DS1 Loopback Code Detection.

		  'inhibit' refers to when the in-band
		 loopback codes are ignored.

		  'payload' designates a payload loopback
		 is done upon recognition of the inband loopback
		 code.

		  'lineloop' designates a line loopback is done
		 upon recognition of the inband loopback code."

	::= { gdcDsx1ConfigEntry 15 }

 gdcDsx1Redundancy 		OBJECT-TYPE
	 SYNTAX	INTEGER {
			 onLine(1),
			 backUp(2),
			 keepAlive(3)
		 }
	 ACCESS	read-write
	 STATUS	mandatory
	 DESCRIPTION
		 "This variable identifies which unit is the Primary
		  unit and which unit is the Secondary unit.  When
		  the value is onLine(1), then the unit is identified
		  as the Primary unit.  When the value is backUp(2),
		  then the unit is identified as the Secondary unit.

		  The value keepAlive(3) indicates that a physical strap
		  is enabled on the unit and that the values of onLine(1)
		  and backUp(2) are ignored.
		  The value keepAlive(3) can never be set by network
		  management."

	::= { gdcDsx1ConfigEntry 16 }

 -- ********************************************************************
 -- GDC DS1 Diagnostics
 -- ********************************************************************
 gdcDsx1DiagTable OBJECT-TYPE
     SYNTAX SEQUENCE OF GdcDsx1DiagEntry
     ACCESS not-accessible
     STATUS mandatory
     DESCRIPTION
	 "The GDC DS1 Diagnostics table.  Information in the entries of
	 this table support diagnostics testing, both active testing
	 via patterns, and passive testing via loopbacks.  The
	 information of this table augments the entries in the DS1
	 Configuration table of the DS1 MIB defined in RFC 1406."
     ::= { gdcDsx1Diagnostics 1 }

 gdcDsx1DiagEntry OBJECT-TYPE
     SYNTAX GdcDsx1DiagEntry
     ACCESS not-accessible
     STATUS mandatory
     DESCRIPTION
	 "The GDC DS1 Diagnostics table entry.  The information in this
	 entry augments the information for the corresponding entry in
	 the DS1 Configuration table of the DS1 MIB defined in RFC 1406."
     INDEX { gdcDsx1DiagIndex }
     ::= { gdcDsx1DiagTable 1 }

 GdcDsx1DiagEntry ::= 
     SEQUENCE {
	 gdcDsx1DiagIndex SCinstance,
	 gdcDsx1SendCode INTEGER,
--         gdcDsx1ProgPattern INTEGER,
	 gdcDsx1LoopbackConfig INTEGER,
 	 gdcDsx1DS0Diag INTEGER,
	 gdcDsx1TestDuration INTEGER,
--         gdcDsx1DiagTimingSource INTEGER,
	 gdcDsx1TestExecutionStatus INTEGER,
	 gdcDsx1TestExceptions INTEGER,
	 gdcDsx1TestResults INTEGER
     }

 gdcDsx1DiagIndex OBJECT-TYPE
     SYNTAX SCinstance
     ACCESS read-only
     STATUS mandatory
     DESCRIPTION
	 "The index value which uniquely identifies the interface to
	 which this entry is applicable.  This has the form of a
	 SCinstance which defines the slot, line, drop, and sub-identifier,
	 which in this case is a network interface."
     ::= { gdcDsx1DiagEntry 1 }

 gdcDsx1SendCode OBJECT-TYPE
     SYNTAX INTEGER {
	 other(1),			-- sending other code
	 sendProgPattern(2),		-- sending user programmable bit pattern
	 send2047pattern(3),		-- sending 2047 bit pattern
	 sendInbandCode(6),
	 sendInbandCodeReset(7),
	 sendNetworkInterfaceCode(8),	-- 
	 sendNtworkInterfaceResetcode(9),--
	 sendDS0DelayPattern(10),
 	 send511PatternWithLT(11),	-- sending 511 bit pattern
					--   with local test
	 send511PatternWithRT(12),	-- sending 511 bit pattern
					--   with remote test
	 send2047PatternWithLT(13),	-- sending 2047 bit pattern
					--   with local test
         send2047PatternWithRT(14),	-- sending 2047 bit pattern
					--   with remote test
	 sendQRSPatternWithLT(15),	-- sending QRS bit pattern
					--   with local test
	 sendQRSPatternWithRT(16),	-- sending QRS bit pattern
					--   with remote test
	 sendProgPatternWithLT(17),	-- sending Prog bit pattern
					--   with local test
         sendProgPatternWithRT(18),	-- sending Prog bit pattern
					--   with remote test
	 send3in24PatternWithRT(19)	-- sending 3 in 24 bit pattern
					--   with remote test
       }
     ACCESS read-write
     STATUS mandatory
     DESCRIPTION
	 "Augments the dsx1SendCode object from the DS1 MIB of RFC
	 1406.  This object defines other codes that are not defined by
	 dsx1SendCode.

	 The value of other(1) can never be set by management
	 operation.

	 This object and the dsx1SendCode object interoperate.  When
	 the value of dsx1SendCode is set to something other than
	 dsx1SendOtherTestPattern(8), then the value of this object is
	 set to other(1).  When the value of this object is set to
	 something other than other(1), the the value of dsx1SendCode
	 is set to dsx1SendOtherTestPattern(8).

	 This object and the gdcDsx1ProgPattern object interrelate.
	 When this object is set to the value sendProgPattern(4), the
	 value of the gdcDsx1ProgPattern object is used as the 16
	 bit user programmable pattern.

	 The values send511PatternWithLT(11), send511PatternWithRT(12),
	 send2047PatternWithLT(13), send2047PatternWithRT(14), sendQRSPatternWithLT(15),
	 sendQRSPatternWithRT(16), sendProgPatternWithLT(17), sendProgPatternWithRT(18),
	 send3in24PatternWithRT(19) indicate that the given pattern test is running in
	 conjunction with a local test (LT) or remote test (RT). gdcDsx1LoopbackConfig 
	 is updated to indicate this as well.  When one of these tests are running, and 
	 dsx1SendCode is set to dsx1SendNoCode(1), both the pattern and the loopback 
	 are terminated.  However, if dsx1LoopbackConfig is set to dsx1NoLoop(1),
	 and a pattern with LT is in progres, only the loopback portion is terminated."

     ::= { gdcDsx1DiagEntry 2 }

-- gdcDsx1ProgPattern OBJECT-TYPE
--     SYNTAX INTEGER (0..'ffff'h)
--     ACCESS read-write
--     STATUS mandatory
--     DESCRIPTION
--    	"The 16 bit user programmable test pattern.  This object
--    	interrelates with the gdcDsx1SendCode object in that when the
--     	value of that object is sendProgPattern(4), the the value of
--     	this object is used as the 16 bit user programmable test pattern."
--     ::= { gdcDsx1DiagEntry 3 }

 gdcDsx1LoopbackConfig OBJECT-TYPE
     SYNTAX INTEGER {
	 other(1),			-- another loopback
	 localtest(2),
	 ds0(3),
	 cascade(4)
     }
     ACCESS read-write
     STATUS mandatory
     DESCRIPTION
	 "Augments the dsx1LoopbackConfig object from the DS1 MIB of RFC
	 1406.  This object defines other loopback configurations  that
	 are not defined by dsx1LoopbackConfig.

	 The value of other(1) can never be set by management
	 operation."

     ::= { gdcDsx1DiagEntry 4 }

 gdcDsx1DS0Diag OBJECT-TYPE
     SYNTAX INTEGER (0..32)            -- 0, 1-32		
     ACCESS read-write
     STATUS mandatory
     DESCRIPTION
	"Defines a DS0 level diagnostic.  Setting this object value to 0
	 disables a DS0 level diagnostic.  Setting this object to a value
	 from 1 to 32 enables a DS0 level diagnostic on the DS0 indicated.

	 Enabling a DS0 level diagnostic bysetting this object to a value
	 from 1 to 32 alters the meaning of the diagnostic test to be 
	 specific to the DS0 specified instead of the whole DS1.

	 Note that a DS0 level diagnostic and a DS1 level diagnostic
	 cannot be performed simultaneously."


	::= { gdcDsx1DiagEntry 5 }

 gdcDsx1TestDuration OBJECT-TYPE
     SYNTAX INTEGER	{
				 noLimit(1),
				 testTime1Min(2),
				 testTime2Mins(3),
				 testTime3Mins(4),
				 testTime4Mins(5),
				 testTime5Mins(6),
				 testTime6Mins(7),
				 testTime7Mins(8),
				 testTime8Mins(9),
				 testTime9Mins(10),
				 testTime10Mins(11),
				 testTime15Mins(12),
				 testTime20Mins(13),
				 testTime25Mins(14),
				 testTime30Mins(15),
				 testTime30Secs(16)
	     }			
     ACCESS read-write
     STATUS mandatory
     DESCRIPTION
	 "Selects the duration to run a diagnostic test.  The value(1)
	 noLimit signifies that the test should run indefinitely until
	 explicitly terminated. 

	 Default value: noLimit (1)"

     ::= { gdcDsx1DiagEntry 6 }

--  gdcDsx1DiagTimingSource OBJECT-TYPE
--     SYNTAX INTEGER {
--     	currentSource(1),	
--     	loopTiming(2),		
--     	localTiming(3),		
--     	station(4),		
--     	composite(5)		
--     }
--     ACCESS read-write
--     STATUS mandatory
--     DESCRIPTION
--     	"For diagnostics that do not disrupt the transmit timing
--     	source, the value currentSource(1) should be used. The
--     	remaining timing sources are for use when the diagnostic
--     	disrupts the reception of the transmit clock source.
-- 
--         For example, in applications where a cascade is installed and
--         activated, the transmit timing source is the cascade. When
--         performing a DS1 loopback, the transmit timing cannot be
--         recovered from the cascade; as a result, an alternate timing
--         source must be used for the duration of the diagnostic. In
--         this instance, the timing source should be specified as
--         one of the other defined values."
--     ::= { gdcDsx1DiagEntry 7 }

 gdcDsx1TestExecutionStatus OBJECT-TYPE
     SYNTAX INTEGER {
	 notInTest(1),			-- a test is not running
	 testInProgress(2),		-- the test is running
	 testCompleted(4),		-- the test is complete
	 testCompletedNotInTest(5)      -- a test has completed,nolonger in test
	 

     }
     ACCESS read-only
     STATUS mandatory
     DESCRIPTION
     "This variable reports the status of a test.  notInTest(1) indicates
      a test is not running.  testInProgress(2) indicates that a test is
      currently running.  testCompleted(4) indicates that a test has run
      and is completed. testCompletedNotInTest(5) indicates that a test has
      completed and it is no longer in test."

::= { gdcDsx1DiagEntry 8 }

 gdcDsx1TestExceptions OBJECT-TYPE
     SYNTAX INTEGER (0..7)
     ACCESS read-only
     STATUS mandatory
     DESCRIPTION
	 "Indicates exceptions that have occurred that may affect
	 interpretation of the test results.

	 The value of this object is a sum.  This sum initially take
	 the value zero.  Then, for each exception, the value
	 associated with the exception is added to the sum.

	 The exception values are:

		 value	exception
		     1   a timed test was preempted so the result
			 cannot be viewed in relation to the test
			 duration
		     2   the results overflowed so the result cannot be
			 viewed as an absolute value
		     4   the test was performed while synchronization
			 could not be performed so the result may not
			 be accurate."
     ::= { gdcDsx1DiagEntry 9 }

 gdcDsx1TestResults OBJECT-TYPE
     SYNTAX INTEGER(0..1048576)
     ACCESS read-only
     STATUS mandatory
     DESCRIPTION
	 "The results of the last diagnostic test.  This can be the
	 current test running or the last completed test.

	 Note that the interpretation of these results may be affected
	 by the value of the gdcDsx1TestExceptions object.

	 The units of the value of this object depend on the type of
	 diagnostic test run.  For all cases except a DS0 delay
	 measurement, the units of the value of this object is the
	 number of errors that occurred.  For a DS0 delay measurement,
	 the units of the value of this test are milliseconds."
     ::= { gdcDsx1DiagEntry 10 }

 -- ********************************************************************
 -- ANSI Performance 
 -- ********************************************************************


 gdcDsx1ANSIperfTable OBJECT-TYPE
     SYNTAX SEQUENCE OF GdcDsx1ANSIperfEntry
     ACCESS not-accessible
     STATUS mandatory
     DESCRIPTION
	 "The GDC ANSI Performance table.  Information in the entries
	 of this table support the ANSI Scheduled Performance Reports.
	 Entries supply information for both inbound and outbound
	 reports for the last 4 seconds."
     ::= { gdcDsx1Performance 1 }

 gdcDsx1ANSIperfEntry OBJECT-TYPE
     SYNTAX GdcDsx1ANSIperfEntry
     ACCESS not-accessible
     STATUS mandatory
     DESCRIPTION
	 "The GDC ANSI Performance table entry.  The information in
	 this entry presents one of the 4 second periods performance
	 data in either the inbound or outbound direction."
     INDEX { gdcDsx1ANSIperfIndex, gdcDsx1ANSIdirection,
     gdcDsx1ANSIseconds }
     ::= { gdcDsx1ANSIperfTable 1 }

 GdcDsx1ANSIperfEntry ::= 
     SEQUENCE {
	 gdcDsx1ANSIperfIndex SCinstance,
	 gdcDsx1ANSIdirection INTEGER,
	 gdcDsx1ANSIseconds INTEGER,
	 gdcDsx1ANSICRCerrorEvents INTEGER,
	 gdcDsx1ANSIsevereErrors INTEGER,
	 gdcDsx1ANSIframeErrors INTEGER,
	 gdcDsx1ANSIcodeViolations INTEGER,
	 gdcDsx1ANSIcontrolledSlips INTEGER,
	 gdcDsx1ANSIactivePayloadLoops INTEGER
     }

 gdcDsx1ANSIperfIndex OBJECT-TYPE
     SYNTAX SCinstance
     ACCESS read-only
     STATUS mandatory
     DESCRIPTION
	 "The index value which uniquely identifies the interface to
	 which this entry is applicable.  This has the form of a
	 SCinstance which defines the slot, line, drop, and interface,
	 which in this case is a network interface."
     ::= { gdcDsx1ANSIperfEntry 1 }    

 gdcDsx1ANSIdirection OBJECT-TYPE
     SYNTAX INTEGER {
	 outbound(1),			-- outbound report
	 inbound(2)			-- inbound report
     }
     ACCESS read-only
     STATUS mandatory
     DESCRIPTION
	 "Identifies the direction of the report entry.  This is either
	 an outbound(1) report or an inbound(2) report."
     ::= { gdcDsx1ANSIperfEntry 2 }

 gdcDsx1ANSIseconds OBJECT-TYPE
     SYNTAX INTEGER (1..4)		-- 1 to 4 seconds of statistics
     ACCESS read-only
     STATUS mandatory
     DESCRIPTION
	 "Identifies the reporting interval.  This has the value 1 to 4
	 supporting up to the last 4 seconds of performance data."
     ::= { gdcDsx1ANSIperfEntry 3 }

 gdcDsx1ANSICRCerrorEvents OBJECT-TYPE
     SYNTAX INTEGER {
	 noErrors(1),			-- no errors in the interval
	 errors1(2),			-- 1 error in the interval
	 errors2to5(4),			-- 2 to 5 errors in the interval
	 errors6to10(8),		-- 6 to 10 errors in the interval
	 errors11to100(16),		-- 11 to 100 errors in the interval
	 errors101to320(32),		-- 101 to 320 errors in the interval
	 errors321orMore(64)		-- 321 or more errors in the interval
     }
     ACCESS read-only
     STATUS mandatory
     DESCRIPTION
	 "Identifies the magnitude of the error events in the interval
	 which this entry represents."
     ::= { gdcDsx1ANSIperfEntry 4 }

 gdcDsx1ANSIsevereErrors OBJECT-TYPE
     SYNTAX INTEGER {
	 noEventsDetected(1),		-- no events detected in the interval
	 eventsDetected(2)		-- events detected in the interval
     }
     ACCESS read-only
     STATUS mandatory
     DESCRIPTION
	 "Identifies whether or not any severe errors were detected in
	 the interval which this entry represents."
     ::= { gdcDsx1ANSIperfEntry 5 }

 gdcDsx1ANSIframeErrors OBJECT-TYPE
     SYNTAX INTEGER {
	 noEventsDetected(1),		-- no events detected in the interval
	 eventsDetected(2)		-- events detected in the interval
     }
     ACCESS read-only
     STATUS mandatory
     DESCRIPTION
	 "Identifies whether or not any framing errors were detected in
	 the interval which this entry represents."
     ::= { gdcDsx1ANSIperfEntry 6 }

 gdcDsx1ANSIcodeViolations OBJECT-TYPE
     SYNTAX INTEGER {
	 noEventsDetected(1),		-- no events detected in the interval
	 eventsDetected(2)		-- events detected in the interval
     }
     ACCESS read-only
     STATUS mandatory
     DESCRIPTION
	 "Identifies whether or not any code violations were detected in
	 the interval which this entry represents."
     ::= { gdcDsx1ANSIperfEntry 7 }

 gdcDsx1ANSIcontrolledSlips OBJECT-TYPE
     SYNTAX INTEGER {
	 noEventsDetected(1),		-- no events detected in the interval
	 eventsDetected(2)		-- events detected in the interval
     }
     ACCESS read-only
     STATUS mandatory
     DESCRIPTION
	 "Identifies whether or not any controlled slips were detected in
	 the interval which this entry represents."
     ::= { gdcDsx1ANSIperfEntry 8 }

 gdcDsx1ANSIactivePayloadLoops OBJECT-TYPE
     SYNTAX INTEGER {
	 noEventsDetected(1),		-- no events detected in the interval
	 eventsDetected(2)		-- events detected in the interval
     }
     ACCESS read-only
     STATUS mandatory
     DESCRIPTION
	 "Identifies whether or not any active payload loops were detected in
	 the interval which this entry represents."
     ::= { gdcDsx1ANSIperfEntry 9 }

 -- ********************************************************************
 -- ATT Current Performance Table
 -- ********************************************************************


 gdcDsx1CurrentTable 	OBJECT-TYPE
	 SYNTAX  SEQUENCE OF GdcDsx1CurrentEntry
	 ACCESS  not-accessible
	 STATUS  mandatory
	 DESCRIPTION
		 "The gdcDsx1 Current table.  This table supplements the
		 entries in the DS1 AT&T performance table of the DS1
		 MIB defined in RFC1406."
	 ::= { gdcDsx1Performance 2 }


 gdcDsx1CurrentEntry 	OBJECT-TYPE
	 SYNTAX  GdcDsx1CurrentEntry
	 ACCESS  not-accessible
	 STATUS  mandatory
	 DESCRIPTION
		 "An entry in the gdcDsx1 Current table."
	 INDEX   { gdcDsx1CurrentIndex }
	 ::= { gdcDsx1CurrentTable 1 }

 GdcDsx1CurrentEntry ::=
	 SEQUENCE {
		  gdcDsx1CurrentIndex
			 SCinstance,
		  gdcDsx1CurrentLOFCs
			 Gauge,
		  gdcDsx1CurrenUserStat
			 OCTET STRING
	  }

 gdcDsx1CurrentIndex 	OBJECT-TYPE
	 SYNTAX  SCinstance
	 ACCESS  read-only
	 STATUS  mandatory
	 DESCRIPTION
	 "The index value which uniquely identifies the interface to
	 which this entry is applicable.  This has the form of a
	 SCinstance which defines the slot, line, drop, and interface,
	 which in this case is a network interface."
	    ::= { gdcDsx1CurrentEntry 1 }

 gdcDsx1CurrentLOFCs 	OBJECT-TYPE
	SYNTAX Gauge
	ACCESS read-only
	STATUS mandatory
	DESCRIPTION
		 "The number of Loss of Frame Counts (LOFCs) encountered by a DS1 
		 interface in the current 15 minute interval."
	::= {gdcDsx1CurrentEntry 2 }

gdcDsx1CurrenUserStat OBJECT-TYPE
	 SYNTAX OCTET STRING (SIZE (13))
	 ACCESS read-only
	 STATUS mandatory
	 DESCRIPTION
		"Returns a bitwise snapshot of the  statistics.

		 Octet 1 bit 7 - parity   
			 bit 6 - 2^15	Errored Seconds 
			 bit 5 - 2^14
			 bit 4 - 2^15	Severely Errored Seconds
			 bit 3 - 2^14
			 bit 2 - 2^15	Bursty Errored Seconds
			 bit 1 - 2^14
			 bit 0 - 1: 	New Interval

		 Octet 2 bit 7 - parity   
			 bit 6 - 2^13   Errored Seconds
			 bit 5 - 2^12
			 bit 4 - 2^11
			 bit 3 - 2^10
			 bit 2 - 2^9
			 bit 1 - 2^8
			 bit 0 - 2^7

		 Octet 3 bit 7 - parity   
			 bit 6 - 2^6	Errored Seconds
			 bit 5 - 2^5
			 bit 4 - 2^4
			 bit 3 - 2^3
			 bit 2 - 2^2
			 bit 1 - 2^1
			 bit 0 - 2^0

		 Octet 4 bit 7 - parity   
			 bit 6 - 2^13 	Severely Errored Seconds
			 bit 5 - 2^12
			 bit 4 - 2^11
			 bit 3 - 2^10
			 bit 2 - 2^9
			 bit 1 - 2^8
			 bit 0 - 2^7

		 Octet 5 bit 7 - parity   
			 bit 6 - 2^6 	Severely Errored Seconds	
			 bit 5 - 2^5
			 bit 4 - 2^4
			 bit 3 - 2^3
			 bit 2 - 2^2
			 bit 1 - 2^1
			 bit 0 - 2^0

		 Octet 6 bit 7 - parity   
			 bit 6 - 2^13 	Bursty Errored Seconds	
			 bit 5 - 2^12
			 bit 4 - 2^11
			 bit 3 - 2^10
			 bit 2 - 2^9
			 bit 1 - 2^8
			 bit 0 - 2^7

		 Octet 7 bit 7 - parity   
			 bit 6 - 2^6 	Bursty Errored Seconds
			 bit 5 - 2^5
			 bit 4 - 2^4
			 bit 3 - 2^3
			 bit 2 - 2^2
			 bit 1 - 2^1
			 bit 0 - 2^0

		 Octet 8 bit 7 - parity   
			 bit 6 - f/u
			 bit 5 - f/u
			 bit 4 - 2^15	Unavailable Seconds
			 bit 3 - 2^14
			 bit 2 - f/u
			 bit 1 - 2^7 	Loss of Frame Count
			 bit 0 - 2^7	Controlled Slip Seconds

		 Octet 9 bit 7 - parity   
			 bit 6 - 2^13 	Unavailable Seconds
			 bit 5 - 2^12
			 bit 4 - 2^11
			 bit 3 - 2^10
			 bit 2 - 2^9
			 bit 1 - 2^8
			 bit 0 - 2^7

	        Octet 10 bit 7 - parity   
			 bit 6 - 2^6 	Unavailable Seconds
			 bit 5 - 2^5
			 bit 4 - 2^4
			 bit 3 - 2^3
			 bit 2 - 2^2
			 bit 1 - 2^1
			 bit 0 - 2^0

		Octet 11 bit 7 - parity   
			 bit 6 - 2^6  	Controlled Slip Second
			 bit 5 - 2^5
			 bit 4 - 2^4
			 bit 3 - 2^3
			 bit 2 - 2^2
			 bit 1 - 2^1
			 bit 0 - 2^0

		Octet 12 bit 7 - parity   
			 bit 6 - 2^6 	Loss of Frame Count
			 bit 5 - 2^5
			 bit 4 - 2^4
			 bit 3 - 2^3
			 bit 2 - 2^2
			 bit 1 - 2^1
			 bit 0 - 2^0

		Octet 13 bit 7 - parity   
			 bit 6 - 2^6 	Percent Complete
			 bit 5 - 2^5
			 bit 4 - 2^4
			 bit 3 - 2^3
			 bit 2 - 2^2
			 bit 1 - 2^1
			 bit 0 - 2^0
		"

    ::= { gdcDsx1CurrentEntry 3 }
 




 -- ********************************************************************
 -- ATT Interval Performance Table
 -- ********************************************************************


 gdcDsx1IntervalTable 	OBJECT-TYPE
	 SYNTAX  SEQUENCE OF GdcDsx1IntervalEntry
	 ACCESS  not-accessible
	 STATUS  mandatory
	 DESCRIPTION
		 "The gdcDsx1 Interval table.  This table supplements the
		 entries in the DS1 AT&T performance table of the DS1
		 MIB defined in RFC1406."

	 ::= { gdcDsx1Performance 3 }


 gdcDsx1IntervalEntry 	OBJECT-TYPE
	 SYNTAX  GdcDsx1IntervalEntry
	 ACCESS  not-accessible
	 STATUS  mandatory
	 DESCRIPTION
		 "An entry in the DS1 Interval table."
	 INDEX   { gdcDsx1IntervalIndex, gdcDsx1IntervalNumber }
	 ::= { gdcDsx1IntervalTable 1 }

 GdcDsx1IntervalEntry ::=
	 SEQUENCE {
		  gdcDsx1IntervalIndex
			 SCinstance,
		  gdcDsx1IntervalNumber
			 INTEGER,
		  gdcDsx1IntervalLOFCs
			 Gauge
	  }

 gdcDsx1IntervalIndex 	OBJECT-TYPE
	 SYNTAX  SCinstance
	 ACCESS  read-only
	 STATUS  mandatory
	 DESCRIPTION
	 "The index value which uniquely identifies the interface to
	 which this entry is applicable.  This has the form of a
	 SCinstance which defines the slot, line, drop, and interface,
	 which in this case is a network interface."
	 ::= { gdcDsx1IntervalEntry 1 }

 gdcDsx1IntervalNumber 	OBJECT-TYPE
	 SYNTAX  INTEGER (1..96)
	 ACCESS  read-only
	 STATUS  mandatory
	 DESCRIPTION
		 "A number between 1 and 96, where 1 is the most recently completed 
		 15 minute interval and 96 is the least recently completed 15 minutes  
		 interval   (assuming   that  all  96  intervals  are valid)."
	 ::= { gdcDsx1IntervalEntry 2 }

 gdcDsx1IntervalLOFCs 	OBJECT-TYPE
	 SYNTAX Gauge
	 ACCESS read-only
	 STATUS mandatory
	 DESCRIPTION
		 "The number of Loss of Frame Counts (LOFCs) encountered by a DS1 
		 interface in the current 15 minute interval."
	 ::= {gdcDsx1IntervalEntry 3 }

 -- ********************************************************************
 -- ATT Total Performance Table
 -- ********************************************************************


 gdcDsx1TotalTable 		OBJECT-TYPE
	 SYNTAX  SEQUENCE OF GdcDsx1TotalEntry
	 ACCESS  not-accessible
	 STATUS  mandatory
	 DESCRIPTION
		 "The DS1 Total table.  24 hour interval.
		 This table supplements the entries in the DS1 
		 AT&T performance table of the DS1
		 MIB defined in RFC1406."

	 ::= { gdcDsx1Performance 4}

 gdcDsx1TotalEntry 		OBJECT-TYPE
	 SYNTAX  GdcDsx1TotalEntry
	 ACCESS  not-accessible
	 STATUS  mandatory
	 DESCRIPTION
		 "An entry in the DS1 Total table."
	 INDEX   { gdcDsx1TotalIndex }
	 ::= { gdcDsx1TotalTable 1 }

 GdcDsx1TotalEntry ::=
	 SEQUENCE {
		  gdcDsx1TotalIndex
			 SCinstance,
		  gdcDsx1TotalLOFCs
			 Gauge
	  }

 gdcDsx1TotalIndex 		OBJECT-TYPE
	 SYNTAX  SCinstance
	 ACCESS  read-only
	 STATUS  mandatory
	 DESCRIPTION
	 "The index value which uniquely identifies the interface to
	 which this entry is applicable.  This has the form of a
	 SCinstance which defines the slot, line, drop, and interface,
	 which in this case is a network interface."
	 ::= { gdcDsx1TotalEntry 1 }

 gdcDsx1TotalLOFCs 		OBJECT-TYPE
	 SYNTAX Gauge
	 ACCESS read-only
	 STATUS mandatory
	 DESCRIPTION
		 "The number of Loss of Frame Counts (LOFCs) encountered by a
		 DS1interface in the current 15 minute interval."
	 ::= {gdcDsx1TotalEntry 2 }

 -- ********************************************************************
 -- ATT Far End Current Performance Table
 -- ********************************************************************


-- gdcDsx1FarEndCurrentTable 	OBJECT-TYPE
--	 SYNTAX  SEQUENCE OF GdcDsx1FarEndCurrentEntry
--	 ACCESS  not-accessible
--	 STATUS  mandatory
--	 DESCRIPTION
--		 "The gdcDsx1FarEnd Current table.  This table supplements the
--		 entries in the DS1 AT&T performance table of the DS1
--		 MIB defined in RFC1406."
--	 ::= { gdcDsx1Performance 5 }


-- gdcDsx1FarEndCurrentEntry 	OBJECT-TYPE
--	 SYNTAX  GdcDsx1FarEndCurrentEntry
--	 ACCESS  not-accessible
--	 STATUS  mandatory
--	 DESCRIPTION
--		 "An entry in the gdcDsx1FarEnd Current table."
--	 INDEX   { gdcDsx1FarEndCurrentIndex }
--	 ::= { gdcDsx1FarEndCurrentTable 1 }

-- GdcDsx1FarEndCurrentEntry ::=
--	 SEQUENCE {
--		  gdcDsx1FarEndCurrentIndex
--			 SCinstance,
--		  gdcDsx1FarEndCurrentLOFCs
--			 Gauge
--	  }

-- gdcDsx1FarEndCurrentIndex 	OBJECT-TYPE
--	 SYNTAX  SCinstance
--	 ACCESS  read-only
--	 STATUS  mandatory
--	 DESCRIPTION
--	 "The index value which uniquely identifies the interface to
--	 which this entry is applicable.  This has the form of a
--	 SCinstance which defines the slot, line, drop, and interface,
--	 which in this case is a network interface."
--	    ::= { gdcDsx1FarEndCurrentEntry 1 }

-- gdcDsx1FarEndCurrentLOFCs 	OBJECT-TYPE
--	SYNTAX Gauge
--	ACCESS read-only
--	STATUS mandatory
--	DESCRIPTION
--		 "The number of Loss of Frame Counts (LOFCs) encountered by a DS1 
--		 interface in the current 15 minute interval."
--	::= {gdcDsx1FarEndCurrentEntry 2 }


 -- ********************************************************************
 -- ATT Interval Far End Performance Table
 -- ********************************************************************


-- gdcDsx1FarEndIntervalTable 	OBJECT-TYPE
--	 SYNTAX  SEQUENCE OF GdcDsx1FarEndIntervalEntry
--	 ACCESS  not-accessible
--	 STATUS  mandatory
--	 DESCRIPTION
--		 "The gdcDsx1FarEnd Interval table.  This table supplements the
--		 entries in the DS1 AT&T performance table of the DS1
--		 MIB defined in RFC1406."
--
--	 ::= { gdcDsx1Performance 6 }


-- gdcDsx1FarEndIntervalEntry 	OBJECT-TYPE
--	 SYNTAX  GdcDsx1FarEndIntervalEntry
--	 ACCESS  not-accessible
--	 STATUS  mandatory
--	 DESCRIPTION
--		 "An entry in the DS1 Interval table."
--	 INDEX   { gdcDsx1FarEndIntervalIndex, gdcDsx1FarEndIntervalNumber }
--	 ::= { gdcDsx1FarEndIntervalTable 1 }

-- GdcDsx1FarEndIntervalEntry ::=
--	 SEQUENCE {
--		  gdcDsx1FarEndIntervalIndex
--			 SCinstance,
--		  gdcDsx1FarEndIntervalNumber
--			 INTEGER,
--		  gdcDsx1FarEndIntervalLOFCs
--			 Gauge
--	  }

-- gdcDsx1FarEndIntervalIndex 	OBJECT-TYPE
--	 SYNTAX  SCinstance
--	 ACCESS  read-only
--	 STATUS  mandatory
--	 DESCRIPTION
--	 "The index value which uniquely identifies the interface to
--	 which this entry is applicable.  This has the form of a
--	 SCinstance which defines the slot, line, drop, and interface,
--	 which in this case is a network interface."
--	 ::= { gdcDsx1FarEndIntervalEntry 1 }

-- gdcDsx1FarEndIntervalNumber 	OBJECT-TYPE
--	 SYNTAX  INTEGER (1..96)
--	 ACCESS  read-only
--	 STATUS  mandatory
--	 DESCRIPTION
--		 "A number between 1 and 96, where 1 is the most recently completed 
--		 15 minute interval and 96 is the least recently completed 15 minutes  
--		 interval   (assuming   that  all  96  intervals  are valid)."
--	 ::= { gdcDsx1FarEndIntervalEntry 2 }

-- gdcDsx1FarEndIntervalLOFCs 	OBJECT-TYPE
--	 SYNTAX Gauge
--	 ACCESS read-only
--	 STATUS mandatory
--	 DESCRIPTION
--		 "The number of Loss of Frame Counts (LOFCs) encountered by a DS1 
--		 interface in the current 15 minute interval."
--	 ::= {gdcDsx1FarEndIntervalEntry 3 }

 -- ********************************************************************
 -- ATT Total Far End Performance Table
 -- ********************************************************************


-- gdcDsx1FarEndTotalTable 		OBJECT-TYPE
--	 SYNTAX  SEQUENCE OF GdcDsx1FarEndTotalEntry
--	 ACCESS  not-accessible
--	 STATUS  mandatory
--	 DESCRIPTION
--		 "The DS1 Total table.  24 hour interval.
--		 This table supplements the entries in the DS1 
--		 AT&T performance table of the DS1
--		 MIB defined in RFC1406."
--
--	 ::= { gdcDsx1Performance 7 }

-- gdcDsx1FarEndTotalEntry 		OBJECT-TYPE
--	 SYNTAX  GdcDsx1FarEndTotalEntry
--	 ACCESS  not-accessible
--	 STATUS  mandatory
--	 DESCRIPTION
--		 "An entry in the DS1 Total table."
--	 INDEX   { gdcDsx1FarEndTotalIndex }
--	 ::= { gdcDsx1FarEndTotalTable 1 }

-- GdcDsx1FarEndTotalEntry ::=
--	 SEQUENCE {
--		  gdcDsx1FarEndTotalIndex
--			 SCinstance,
--		  gdcDsx1FarEndTotalLOFCs
--			 Gauge
--	  }

-- gdcDsx1FarEndTotalIndex 		OBJECT-TYPE
--	 SYNTAX  SCinstance
--	 ACCESS  read-only
--	 STATUS  mandatory
--	 DESCRIPTION
--	 "The index value which uniquely identifies the interface to
--	 which this entry is applicable.  This has the form of a
--	 SCinstance which defines the slot, line, drop, and interface,
--	 which in this case is a network interface."
--	 ::= { gdcDsx1FarEndTotalEntry 1 }

-- gdcDsx1FarEndTotalLOFCs 		OBJECT-TYPE
--	 SYNTAX Gauge
--	 ACCESS read-only
--	 STATUS mandatory
--	 DESCRIPTION
--		 "The number of Loss of Frame Counts (LOFCs) encountered by a
--		 DS1interface in the current 15 minute interval."
--	 ::= {gdcDsx1FarEndTotalEntry 2 }







 -- ********************************************************************
 -- GDC Dsx-1 Alarm Object Identifier Definitions
 -- ********************************************************************

 dsx1AlarmData		OBJECT IDENTIFIER ::= { sc5001 1 }

 dsx1NoResponseAlm	   OBJECT IDENTIFIER ::= { dsx1AlarmData 1 }
 dsx1DiagRxErrAlm	   OBJECT IDENTIFIER ::= { dsx1AlarmData 2 }
 dsx1PowerUpAlm		   OBJECT IDENTIFIER ::= { dsx1AlarmData 3 }
 dsx1NvRamCorrupt	   OBJECT IDENTIFIER ::= { dsx1AlarmData 4 }
 dsx1UnitFailure	   OBJECT IDENTIFIER ::= { dsx1AlarmData 5 }
 dsx1MbiLock		   OBJECT IDENTIFIER ::= { dsx1AlarmData 6 }
 dsx1LocalPwrFail	   OBJECT IDENTIFIER ::= { dsx1AlarmData 7 }
 dsx1TimingLoss		   OBJECT IDENTIFIER ::= { dsx1AlarmData 8 }
 dsx1StatusChange	   OBJECT IDENTIFIER ::= { dsx1AlarmData 9 }
 dsx1UnsoTest		   OBJECT IDENTIFIER ::= { dsx1AlarmData 10 }
 dsx1LossOfSignal	   OBJECT IDENTIFIER ::= { dsx1AlarmData 11 }
 dsx1LossOfFrame	   OBJECT IDENTIFIER ::= { dsx1AlarmData 12 }
 dsx1Ais		   OBJECT IDENTIFIER ::= { dsx1AlarmData 13 }
 dsx1ReceivedYellow	   OBJECT IDENTIFIER ::= { dsx1AlarmData 14 }
 dsx1UnavailSignalState	   OBJECT IDENTIFIER ::= { dsx1AlarmData 15 }
 dsx1ExcessiveZeros	   OBJECT IDENTIFIER ::= { dsx1AlarmData 16 }
 dsx1LowAverageDensity	   OBJECT IDENTIFIER ::= { dsx1AlarmData 17 }
 dsx1ControlledSlips  	   OBJECT IDENTIFIER ::= { dsx1AlarmData 18 }
 dsx1BipolarViolations     OBJECT IDENTIFIER ::= { dsx1AlarmData 19 }
 dsx1CrcErrors	           OBJECT IDENTIFIER ::= { dsx1AlarmData 20 }
 dsx1FallbackTimingActive  OBJECT IDENTIFIER ::= { dsx1AlarmData 21 }


 -- ALARM                   Maskable   Valid interfaces   window/thres
 -- ==================================================================
 -- dsx1NoResponseAlm          no         unit               no
 -- dsx1DiagRxErrAlm           no         unit               no
 -- dsx1PowerUpAlm             no         unit               no
 -- dsx1NvRamCorrupt           no         unit               no
 -- dsx1UnitFailure            no         unit               no
 -- dsx1MbiLock                no         unit               no
 -- dsx1LocalPwrFail           no         unit               no
 -- dsx1TimingLoss             yes        unit               no
 -- dsx1StatusChange           yes        unit               no
 -- dsx1UnsoTest               yes        unit               no
 -- dsx1FallbackTimingActive   yes        unit               no
 -- dsx1LossofSignal           yes        net/casc           no
 -- dsx1LossOfFrame            yes        net/casc           no
 -- dsx1Ais                    yes        net/casc           no
 -- dsx1ReceivedYellow         yes        net/casc           no
 -- dsx1UnavailSignalstate     yes        net/casc           no
 -- dsx1ExcessiveZeros         yes        net only           no
 -- dsx1LowAverageDensity      yes        net only           no
 -- dsx1ControlledSlips        yes        net only           no
 -- dsx1BipolarViolations      yes        net/casc           yes
 -- dsx1CrcErrors              yes        net/casc           yes

 -- 
 -- ********************************************************************
 -- GDC DSX-1 Alarm Configuration
 -- ********************************************************************

 gdcDsx1AlarmConfigTable OBJECT-TYPE
     SYNTAX SEQUENCE OF GdcDsx1AlarmConfigEntry
     ACCESS not-accessible
     STATUS mandatory
     DESCRIPTION
	 "The gdcAlarmConfigTable contains entries that configure alarm
	 reporting.  The structure of the table is such that alarm
	 configuration is supported on a unit and interface basis, and
	 then on an alarm type basis within the interface.  For
	 simplicity sake alarms, be they unit or interface
	 related, are represented in one table."
     ::= { gdcDsx1Alarms 1 }

 gdcDsx1AlarmConfigEntry OBJECT-TYPE
     SYNTAX GdcDsx1AlarmConfigEntry
     ACCESS not-accessible
     STATUS mandatory
     DESCRIPTION
	 "An entry in the GDC Alarm Configuration table."
     INDEX { gdcDsx1AlarmConfigIndex, gdcDsx1AlarmConfigIdentifier }
     ::= { gdcDsx1AlarmConfigTable 1 }

 GdcDsx1AlarmConfigEntry ::=
     SEQUENCE {
	 gdcDsx1AlarmConfigIndex
	     SCinstance,
	 gdcDsx1AlarmConfigIdentifier
	     OBJECT IDENTIFIER,
	 gdcDsx1AlarmCountWindow
	     INTEGER,
	 gdcDsx1AlarmCountThreshold
	     INTEGER
     }

 gdcDsx1AlarmConfigIndex OBJECT-TYPE
     SYNTAX SCinstance
     ACCESS read-only
     STATUS mandatory
     DESCRIPTION
	 "The index value which uniquely identifies the interface to
	 which this entry is applicable."
     ::= { gdcDsx1AlarmConfigEntry 1 }

 gdcDsx1AlarmConfigIdentifier OBJECT-TYPE
     SYNTAX OBJECT IDENTIFIER
     ACCESS read-only
     STATUS mandatory
     DESCRIPTION
	 "The unique alarm identifier assigned to this alarm type.
	 The format of this identifier is an OBJECT IDENTIFIER that has
	 the following format: {iso(1) org(3) dod(6) internet(1)
	 private(4) enterprises(1) gdc(498) xxx(x) alarm(z) yyy(y) 
	 where xxx(x) is the administratively assigned family object 
	 identifier (z) is the object identifier for alarms in the family
	 defined MIB and yyy(y) is the administratively assigned alarm 
	 type identifier for this alarm."

     ::= { gdcDsx1AlarmConfigEntry 2 }

 gdcDsx1AlarmCountWindow OBJECT-TYPE
     SYNTAX INTEGER{
			disabled(1),
			last1sec(2),
			last1min(3),
			last1hr(4),
			infinite(5)
		}
	ACCESS  read-write
	STATUS  mandatory
	DESCRIPTION
		"This variable sets/reads the BPV alarm window.

		This window is used with the alarm threshold to determine
		how long the alarm should be active before reporting.

		Default: disabled(1)"
    ::= { gdcDsx1AlarmConfigEntry 3 }

gdcDsx1AlarmCountThreshold OBJECT-TYPE
    SYNTAX INTEGER {
			thresGT10(1),
			thresGT100(2),
			thresGT1000(3),
			thresGT10000(4)
		}
	ACCESS  read-write
	STATUS  mandatory
	DESCRIPTION
		"This function sets/reads the BPV alarm threshold criteria.

		This threshold is used along with the the alarm window to 
		determine the number of instances in a given time frame for
		an alarm to occur before the alarm is considered active.

		Default: thresGT10(1)"
    ::= { gdcDsx1AlarmConfigEntry 4 }

-- ********************************************************************
-- The GDC DSX-1 Alarm Status Table
-- ********************************************************************

gdcDsx1AlarmStatusTable OBJECT-TYPE
    SYNTAX SEQUENCE OF GdcDsx1AlarmStatusEntry
    ACCESS not-accessible
    STATUS mandatory
    DESCRIPTION
    	"The gdcDsx1AlarmStatusTable contains entries that report the
	status of alarms.  The status of an alarm consists of the
	current alarm status, indicating whether or not the alarm
	condition is in effect, the number of times the alarm has
	occurred, the time of the first alarm occurrence, and the time
	of the last alarm occurrence.

        The structure of the table is such that alarm status is
        supported on a unit or interface basis, and then on an alarm
        type basis within the interface.  For simplicity sake and to
        support the reporting of status of all alarms, a unit is
        treated as an interface in this table."
    ::= { gdcDsx1Alarms 2 }

gdcDsx1AlarmStatusEntry OBJECT-TYPE
    SYNTAX GdcDsx1AlarmStatusEntry
    ACCESS not-accessible
    STATUS mandatory
    DESCRIPTION
    	"An entry in the GDC Alarm Status table."
    INDEX { gdcDsx1AlarmStatusIndex, gdcDsx1AlarmStatusIdentifier }
    ::= { gdcDsx1AlarmStatusTable 1 }

GdcDsx1AlarmStatusEntry ::=
    SEQUENCE {
    	gdcDsx1AlarmStatusIndex
    	    SCinstance,
    	gdcDsx1AlarmStatusIdentifier
    	    OBJECT IDENTIFIER,
	gdcDsx1AlarmCount
	    Gauge,
	gdcDsx1AlarmFirstOccurrence
	    TimeTicks,
	gdcDsx1AlarmLastOccurrence
	    TimeTicks
    }

gdcDsx1AlarmStatusIndex OBJECT-TYPE
    SYNTAX SCinstance
    ACCESS read-only
    STATUS mandatory
    DESCRIPTION
    	"The index value which uniquely identifies the interface to
    	which this entry is applicable."
    ::= { gdcDsx1AlarmStatusEntry 1 }

gdcDsx1AlarmStatusIdentifier OBJECT-TYPE
    SYNTAX OBJECT IDENTIFIER
    ACCESS read-only
    STATUS mandatory
    DESCRIPTION
    	"The unique alarm identifier assigned to this alarm type.
    	The format of this identifier is an OBJECT IDENTIFIER that has
    	the following format: {iso(1) org(3) dod(6) internet(1)
    	private(4) enterprises(1) gdc(498) xxx(x) alarm(z) yyy(y) 
	where xxx(x) is the administratively assigned family object 
	identifier (z) is the object identifier for alarms in the family
	defined MIB and yyy(y) is the administratively assigned alarm 
	type identifier for this alarm."

  ::= { gdcDsx1AlarmStatusEntry 2 }

gdcDsx1AlarmCount OBJECT-TYPE
    SYNTAX Gauge
    ACCESS read-only
    STATUS mandatory
    DESCRIPTION
    	"The number of occurrences of this alarm.  This objects value
    	is incremented once for each time that the alarm occurs.  This
    	count is incremented regardless of whether or not the alarm
    	is masked or is not reporteded because of the threshold
    	configuration.
	
	If the network element type does not support this variable, a 
	noSuch will be returned."
    ::= { gdcDsx1AlarmStatusEntry 3 }

gdcDsx1AlarmFirstOccurrence OBJECT-TYPE
    SYNTAX TimeTicks
    ACCESS read-only
    STATUS mandatory
    DESCRIPTION
   	"The time at which the alarm first occurred.  This is reported
    	as the number of TimeTicks after the interface was
    	initialized.  This object along with its companion object,
    	gdcDsx1AlarmLastOccurrence, can be used to provide greater meaning
    	to the value of gdcDsx1AlarmOccurrenceCount by weighing the count
    	over the period of time.

	If the network element type does not support this variable, a 
	noSuch will be returned."
    ::= { gdcDsx1AlarmStatusEntry 4 }

gdcDsx1AlarmLastOccurrence OBJECT-TYPE
    SYNTAX TimeTicks
    ACCESS read-only
    STATUS mandatory
    DESCRIPTION
    	"The time at which the alarm last occurred.  This is reported
    	as the number of TimeTicks after the interface was
    	initialized.  This object along with its companion object,
    	gdcDsx1AlarmFirstOccurrence, can be used to provide greater meaning
    	to the value of gdcDsx1AlarmOccurrenceCount by weighing the count
    	over the period of time.

	If the network element type does not support this variable, a 
	noSuch will be returned."
    ::= { gdcDsx1AlarmStatusEntry 5 }


-- ****************************************************************************
--                       mib definitions end
-- ****************************************************************************


END
