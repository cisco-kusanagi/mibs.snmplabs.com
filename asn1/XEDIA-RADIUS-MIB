XEDIA-RADIUS-MIB DEFINITIONS ::= BEGIN

IMPORTS 
    RowStatus, DisplayString
        FROM SNMPv2-TC

   radiusAccServerEntry
	FROM  RADIUS-ACC-CLIENT-MIB

    radiusAuthServerEntry
	FROM   RADIUS-AUTH-CLIENT-MIB 

    MODULE-IDENTITY, OBJECT-TYPE, IpAddress,  
    Integer32, Counter32, Gauge32, TimeTicks
        FROM SNMPv2-SMI

    MODULE-COMPLIANCE, OBJECT-GROUP
        FROM SNMPv2-CONF

    xediaMibs
        FROM XEDIA-REG
    ;    

xediaRadiusMIB MODULE-IDENTITY
    LAST-UPDATED "9804142200Z" -- April 14, 1998   
    ORGANIZATION "Xedia Corp."
    CONTACT-INFO
        "support@xedia.com"
    DESCRIPTION
        "This module defines additional objects for management of Radius
        in Xedia devices, above and beyond what is defined in the
        proposed drafts."
    ::= { xediaMibs 16 }

-- Top-level organization of the MIB

xRadiusObjects          OBJECT IDENTIFIER ::= { xediaRadiusMIB 1 }
xRadiusConformance      OBJECT IDENTIFIER ::= { xediaRadiusMIB 2 }

-- Radius Client objects

xRadiuscObjects         OBJECT IDENTIFIER ::= { xRadiusObjects 1 } 

xRadiuscGlobal          OBJECT IDENTIFIER ::= { xRadiuscObjects 1 }
xRadiuscAuthentication  OBJECT IDENTIFIER ::= { xRadiuscObjects 2 }
xRadiuscAccounting      OBJECT IDENTIFIER ::= { xRadiuscObjects 3 }

xRadiuscGlobalCfg       OBJECT IDENTIFIER ::= { xRadiuscGlobal 1 }
xRadiuscGlobalStat      OBJECT IDENTIFIER ::= { xRadiuscGlobal 2 }

--
-- Radius Client Global Config
--
xradiuscAdminAuthStatus OBJECT-TYPE
    SYNTAX      INTEGER {
                    enabled(1),
                    disabled(2)
                }
    MAX-ACCESS  read-write
    STATUS      current
    DESCRIPTION
        "The administrative status of Radius Authentication in the router. 
	 Changing this parameter may require a node boot to take affect."
    DEFVAL      { enabled }
    ::= { xRadiuscGlobalCfg 1 }

xradiuscAdminActgStatus OBJECT-TYPE
    SYNTAX      INTEGER {
                    enabled(1),
                    disabled(2)
                }
    MAX-ACCESS  read-write
    STATUS      current
    DESCRIPTION
        "The administrative status of Radius Accounting in the router. 
	 Changing this parameter may require a node boot to take affect."
    DEFVAL      { enabled }
    ::= { xRadiuscGlobalCfg 2 }

xradiuscDebugCmd OBJECT-TYPE
    SYNTAX      DisplayString 
    MAX-ACCESS  read-write
    STATUS      current
    DESCRIPTION
        "The control for dumping in/out radius packets, and error/trace
         messages to the console.  Although the summary of commands is
	 displayed when read, command modifications must be done one 
	 at a time."
    DEFVAL { "rx-pkt-dump:off; tx-pkt-dump:off; error-print:off; trace-print:off" }
    ::= { xRadiuscGlobalCfg 3 }

xradiuscNasId OBJECT-TYPE
    SYNTAX      DisplayString (SIZE(0..32))
    MAX-ACCESS  read-write
    STATUS      current
    DESCRIPTION
        "The NAS ID assigned to this node."
    DEFVAL { "" }
    ::= { xRadiuscGlobalCfg 4 }

xradiuscNasIP OBJECT-TYPE
    SYNTAX      IpAddress
    MAX-ACCESS  read-write
    STATUS      current
    DESCRIPTION
        "The NAS IP Address assigned to this node."
    DEFVAL { 0 }
    ::= { xRadiuscGlobalCfg 5 }

xradiuscBackgroundTimer OBJECT-TYPE
    SYNTAX      INTEGER(90..86400)
    MAX-ACCESS  read-write
    STATUS      current
    DESCRIPTION
        "The number of seconds inwhich the background task will
	 perform cleanup."
    DEFVAL      { 100 }
    ::= { xRadiuscGlobalCfg 6 }

xradiuscMaxOutstanding OBJECT-TYPE
    SYNTAX      INTEGER(1..100)
    MAX-ACCESS  read-write
    STATUS      current
    DESCRIPTION
        "The maximum number of outstanding resquests."
    DEFVAL { 20 }
    ::= { xRadiuscGlobalCfg 7 }

--
-- Radius Client Global Stats
--
xradiuscOperAuthStatus OBJECT-TYPE
    SYNTAX      INTEGER {
                    up(1),
                    down(2),
		    stalled(3)
                }
    MAX-ACCESS  read-only
    STATUS      current
    DESCRIPTION
        "The ccurrent operational state of Radius Authentication on the router."
    ::= { xRadiuscGlobalStat 1 }

xradiuscOperActgStatus OBJECT-TYPE
    SYNTAX      INTEGER {
                    up(1),
                    down(2),
		    stalled(3)
                }
    MAX-ACCESS  read-only
    STATUS      current
    DESCRIPTION
        "The ccurrent operational state of Radius Accounting on the router."
    ::= { xRadiuscGlobalStat 2 }

xradiuscOperNasId OBJECT-TYPE
    SYNTAX      DisplayString
    MAX-ACCESS  read-only
    STATUS      current
    DESCRIPTION
        "The NAS ID assigned to this node."
    ::= { xRadiuscGlobalStat 3 }

xradiuscOperNasIP OBJECT-TYPE
    SYNTAX      IpAddress
    MAX-ACCESS  read-only
    STATUS      current
    DESCRIPTION
        "The NAS IP Address currently being used."
    ::= { xRadiuscGlobalStat 4 }

xradiuscOperGenErrors OBJECT-TYPE
    SYNTAX      Counter32
    MAX-ACCESS  read-only
    STATUS      current
    DESCRIPTION
        "The number of general errors encounted by the Radius Client
	 Task."
    ::= { xRadiuscGlobalStat 5}

xradiuscOperAuthQCurr OBJECT-TYPE
    SYNTAX      Integer32
    MAX-ACCESS  read-only
    STATUS      current
    DESCRIPTION
        "The current number of elements in the Authentication queue."
    ::= { xRadiuscGlobalStat 6}

xradiuscOperAuthQMax OBJECT-TYPE
    SYNTAX      Gauge32
    MAX-ACCESS  read-only
    STATUS      current
    DESCRIPTION
        "The maximum number of elements in the Authentication queue
	 at one time."
    ::= { xRadiuscGlobalStat 7 }

xradiuscOperAuthExpected OBJECT-TYPE
    SYNTAX      Integer32
    MAX-ACCESS  read-only
    STATUS      current
    DESCRIPTION
        "The expected number of elements in the Authentication queue by
	 monitoring the enqueue/dequeue operations."
    ::= { xRadiuscGlobalStat 8 }

xradiuscOperAuthEnqueued OBJECT-TYPE
    SYNTAX      Counter32
    MAX-ACCESS  read-only
    STATUS      current
    DESCRIPTION
        "The number of requested posted to the Authentication queue."
    ::= { xRadiuscGlobalStat 9 }

xradiuscOperAuthDequeued OBJECT-TYPE
    SYNTAX      Counter32
    MAX-ACCESS  read-only
    STATUS      current
    DESCRIPTION
        "The number of requested removed from the Authentication queue."
    ::= { xRadiuscGlobalStat 10 }

xradiuscOperActgQCurr OBJECT-TYPE
    SYNTAX      Integer32
    MAX-ACCESS  read-only
    STATUS      current
    DESCRIPTION
        "The current number of elements in the Accounting queue."
    ::= { xRadiuscGlobalStat 11 }

xradiuscOperActgQMax OBJECT-TYPE
    SYNTAX      Gauge32
    MAX-ACCESS  read-only
    STATUS      current
    DESCRIPTION
        "The maximum number of elements in the Accounting queue
	 at one time."
    ::= { xRadiuscGlobalStat 12 }

xradiuscOperActgExpected OBJECT-TYPE
    SYNTAX      Integer32
    MAX-ACCESS  read-only
    STATUS      current
    DESCRIPTION
        "The expected number of elements in the Accounting queue by
	 monitoring the enqueue/dequeue operations."
    ::= { xRadiuscGlobalStat 13 }

xradiuscOperActgEnqueued OBJECT-TYPE
    SYNTAX      Counter32
    MAX-ACCESS  read-only
    STATUS      current
    DESCRIPTION
        "The number of requested posted to the Accounting queue."
    ::= { xRadiuscGlobalStat 14 }

xradiuscOperActgDequeued OBJECT-TYPE
    SYNTAX      Counter32
    MAX-ACCESS  read-only
    STATUS      current
    DESCRIPTION
        "The number of requested removed from the Accounting queue."
    ::= { xRadiuscGlobalStat 15 }

xradiuscOperPendingListCurr OBJECT-TYPE
    SYNTAX      Integer32
    MAX-ACCESS  read-only
    STATUS      current
    DESCRIPTION
        "The current number of Authentication and Accounting requests Pending."
    ::= { xRadiuscGlobalStat 16 }

xradiuscOperPendingListMax  OBJECT-TYPE
    SYNTAX      Gauge32
    MAX-ACCESS  read-only
    STATUS      current
    DESCRIPTION
        "The maximum number of Authentication and Accounting requests Pending
	 at one time."
    ::= { xRadiuscGlobalStat 17 }

xradiuscOperPendingExpected OBJECT-TYPE
    SYNTAX      Integer32
    MAX-ACCESS  read-only
    STATUS      current
    DESCRIPTION
        "The expected number of elements in the Pending list by
	 monitoring the enqueue/dequeue operations."
    ::= { xRadiuscGlobalStat 18 }

xradiuscOperPendingEnqueued OBJECT-TYPE
    SYNTAX      Counter32
    MAX-ACCESS  read-only
    STATUS      current
    DESCRIPTION
        "The number of requested posted to the Pending list."
    ::= { xRadiuscGlobalStat 19 }

xradiuscOperPendingDequeued OBJECT-TYPE
    SYNTAX      Counter32
    MAX-ACCESS  read-only
    STATUS      current
    DESCRIPTION
        "The number of requested removed from the Pending list."
    ::= { xRadiuscGlobalStat 20 }

xradiuscOperLastPktID OBJECT-TYPE
    SYNTAX      Integer32
    MAX-ACCESS  read-only
    STATUS      current
    DESCRIPTION
        "The last Packet ID that was used."
    ::= { xRadiuscGlobalStat 21 }

xradiuscOperNextPktID OBJECT-TYPE
    SYNTAX      Integer32
    MAX-ACCESS  read-only
    STATUS      current
    DESCRIPTION
        "The next Packet ID that will most likely be used."
    ::= { xRadiuscGlobalStat 22 }

xradiuscOperLastAuthIndex OBJECT-TYPE
    SYNTAX      Integer32
    MAX-ACCESS  read-only
    STATUS      current
    DESCRIPTION
        "The index of the last authentication server used."
    ::= { xRadiuscGlobalStat 23 }

xradiuscOperLastActgIndex OBJECT-TYPE
    SYNTAX      Integer32
    MAX-ACCESS  read-only
    STATUS      current
    DESCRIPTION
        "The index of the last accounting server used."
    ::= { xRadiuscGlobalStat 24 }

-- ************************************************************
-- Additions to the Radius Client Authentication Server TAble
-- ************************************************************
xRadiuscAuthSvrTable        OBJECT-TYPE
    SYNTAX      SEQUENCE OF XRadiuscAuthSvrEntry
    MAX-ACCESS  not-accessible
    STATUS      current
    DESCRIPTION
            "A list of Radius Client Authentication Server entries."
    ::= { xRadiuscAuthentication 1 }
 
xRadiuscAuthSvrEntry     OBJECT-TYPE
    SYNTAX      XRadiuscAuthSvrEntry
    MAX-ACCESS  not-accessible
    STATUS      current
    DESCRIPTION
            "An entry containing additional management information
            applicable to a particular Radius Client Authentication Server."
    AUGMENTS    { radiusAuthServerEntry }
    ::= { xRadiuscAuthSvrTable 1 }

XRadiuscAuthSvrEntry ::=
    SEQUENCE {
      -- 
      -- Configuration
      --
      xradiuscAuthSvrIpAddress       IpAddress,
      xradiuscAuthSvrName            DisplayString,
      xradiuscAuthSvrPort            INTEGER,
      xradiuscAuthSvrTimeout         INTEGER,
      xradiuscAuthSvrRetries         INTEGER,
      xradiuscAuthSvrPriority        INTEGER,
      xradiuscAuthSvrSecretKey       DisplayString,
      xradiuscAuthSvrVendorOffset    INTEGER,
      -- 
      -- Stats
      -- 
      xradiuscAuthSvrOperIpAddress   IpAddress,
      xradiuscAuthSvrOperState       INTEGER,
      xradiuscAuthSvrOperStateChange TimeTicks,
      xradiuscAuthSvrOperBadPktIds   Counter32,
      xradiuscAuthSvrOperRxErrors    Counter32,
      xradiuscAuthSvrOperTxErrors    Counter32,

      xradiuscAuthSvrRowStatus       RowStatus
    }

xradiuscAuthSvrIpAddress OBJECT-TYPE
    SYNTAX      IpAddress
    MAX-ACCESS  read-create
    STATUS      current
    DESCRIPTION
        "The IP Address of the specified Authentication Server.
	 If this address is configured, it is used exclusively
	 to communicate with this server."
    DEFVAL { 0 }
    ::= { xRadiuscAuthSvrEntry 1 }

xradiuscAuthSvrName OBJECT-TYPE
    SYNTAX      DisplayString
    MAX-ACCESS  read-create
    STATUS      current
    DESCRIPTION
        "The name identifying the specified Authentication Server.
	 If no IP Address is configured, then this name MAY be used
	 during a DNS lookup."
    DEFVAL { "" }
    ::= { xRadiuscAuthSvrEntry 2 }

xradiuscAuthSvrPort OBJECT-TYPE
    SYNTAX      INTEGER(1025..65535)
    MAX-ACCESS  read-create
    STATUS      current
    DESCRIPTION
        "The udp port number that the specified Authentication
	 Server is listening for requests."
    DEFVAL { 1812 }
    ::= { xRadiuscAuthSvrEntry 3 }

xradiuscAuthSvrTimeout OBJECT-TYPE
    SYNTAX      INTEGER(1..10)
    MAX-ACCESS  read-create
    STATUS      current
    DESCRIPTION
        "The number of seconds to wait for a response to a resquests."
    DEFVAL { 2 }
    ::= { xRadiuscAuthSvrEntry 4 }

xradiuscAuthSvrRetries OBJECT-TYPE
    SYNTAX      INTEGER(0..5)
    MAX-ACCESS  read-create
    STATUS      current
    DESCRIPTION
        "The number of times to resend the server a requests when
	 no response has been received."
    DEFVAL { 2 }
    ::= { xRadiuscAuthSvrEntry 5 }

xradiuscAuthSvrPriority OBJECT-TYPE
    SYNTAX      INTEGER(1..10)
    MAX-ACCESS  read-create
    STATUS      current
    DESCRIPTION
        "The priority assigned to this server.  Lowest priority
	 servers are used first.  In the case of multiple servers
	 having the same priority, they will be used in a round-
	 robin fashion when their priority is the highest of the
	 available servers."
    DEFVAL { 1 }
    ::= { xRadiuscAuthSvrEntry 6 }

xradiuscAuthSvrSecretKey OBJECT-TYPE
    SYNTAX      DisplayString
    MAX-ACCESS  read-create
    STATUS      current
    DESCRIPTION
        "The shared secret key associated with the specified
	 server.  It is used to 'hide' user passwords and
	 authenticate requests and responses.  When this
	 object is read from a non-superuser, '--------' is
	 returned in order to maintain security."
    DEFVAL { "" }
    ::= { xRadiuscAuthSvrEntry 7 }

xradiuscAuthSvrVendorOffset OBJECT-TYPE
    SYNTAX      INTEGER(0..255)
    MAX-ACCESS  read-create
    STATUS      current
    DESCRIPTION
        "The offset used to assign Vendor Specific attribute IDs to 
	 the standard attribute number space.  Setting this value to
	 0, forces the encoding of Vendor Specific attributes within
	 the Vendor's number space, using the standard 
	 'Vendor-Specific' attribute.  Setting this to a non-zero
	 value uses standard attribute encoding, with the Vendor
	 Specific Base for the attributes beginning with this offset."
    DEFVAL { 0 }
    ::= { xRadiuscAuthSvrEntry 8 }

xradiuscAuthSvrOperIpAddress OBJECT-TYPE
    SYNTAX      IpAddress
    MAX-ACCESS  read-only
    STATUS      current
    DESCRIPTION
        "The IP Address currently being used to communicate 
	 the specified Authentication server."
    ::= { xRadiuscAuthSvrEntry 9 }

xradiuscAuthSvrOperState OBJECT-TYPE 
    SYNTAX      INTEGER {
                    unknown       (1),  
                    responding    (2),
                    notResponding (3),
                    notAvailable  (4)
                }
    MAX-ACCESS  read-only
    STATUS      current
    DESCRIPTION
        "The operational state of the specified Authentication server.
	 The 'unknown' state will be set periodically to allow 'notResponding'
	 servers to be retried after a period of time."
    ::= { xRadiuscAuthSvrEntry 10 }

xradiuscAuthSvrOperStateChange OBJECT-TYPE
    SYNTAX      TimeTicks
    MAX-ACCESS  read-only
    STATUS      current
    DESCRIPTION
        "The value of sysUpTime when the Authentication server
	 last changed state."
    ::= { xRadiuscAuthSvrEntry 11 }

xradiuscAuthSvrOperBadPktIds OBJECT-TYPE
    SYNTAX      Counter32
    MAX-ACCESS  read-only
    STATUS      current
    DESCRIPTION
        "The count of unexpected Packet IDs received on this port."
    ::= { xRadiuscAuthSvrEntry 12 }

xradiuscAuthSvrOperRxErrors OBJECT-TYPE
    SYNTAX      Counter32
    MAX-ACCESS  read-only
    STATUS      current
    DESCRIPTION
        "The count of general Receive errors encountered by this server"
    ::= { xRadiuscAuthSvrEntry 13 }

xradiuscAuthSvrOperTxErrors OBJECT-TYPE
    SYNTAX      Counter32
    MAX-ACCESS  read-only
    STATUS      current
    DESCRIPTION
        "The count of general Transmit errors encountered by this server"
    ::= { xRadiuscAuthSvrEntry 14 }

xradiuscAuthSvrRowStatus OBJECT-TYPE
    SYNTAX       RowStatus
    MAX-ACCESS   read-create
    STATUS       current
    DESCRIPTION
    "This variable displays the status of  the  entry.  Setting it to 
     'destroy' marks the entry as removed.  Eventually, when no other
     applications depend on that particular resource, it will be completely
     removed from the table.  Setting it to  either 'create', or 'active' will
     add a row to the table."
    ::= { xRadiuscAuthSvrEntry 15 }
 
-- ************************************************************
-- Additions to the Radius Client Accounting Server TAble
-- ************************************************************
xRadiuscActgSvrTable        OBJECT-TYPE
    SYNTAX      SEQUENCE OF XRadiuscActgSvrEntry
    MAX-ACCESS  not-accessible
    STATUS      current
    DESCRIPTION
            "A list of Radius Client Accounting Server entries."
    ::= { xRadiuscAccounting 1 }
 
xRadiuscActgSvrEntry     OBJECT-TYPE
    SYNTAX      XRadiuscActgSvrEntry
    MAX-ACCESS  not-accessible
    STATUS      current
    DESCRIPTION
            "An entry containing additional management information
            applicable to a particular Radius Client Accounting Server."
    AUGMENTS    { radiusAccServerEntry }
    ::= { xRadiuscActgSvrTable 1 }

XRadiuscActgSvrEntry ::=
    SEQUENCE {
      -- 
      -- Configuration
      --
      xradiuscActgSvrIpAddress       IpAddress,
      xradiuscActgSvrName            DisplayString,
      xradiuscActgSvrPort            INTEGER,
      xradiuscActgSvrTimeout         INTEGER,
      xradiuscActgSvrRetries         INTEGER,
      xradiuscActgSvrPriority        INTEGER,
      xradiuscActgSvrSecretKey       DisplayString,
      xradiuscActgSvrVendorOffset    INTEGER,
      -- 
      -- Stats
      -- 
      xradiuscActgSvrOperIpAddress   IpAddress,
      xradiuscActgSvrOperState       INTEGER,
      xradiuscActgSvrOperStateChange TimeTicks,
      xradiuscActgSvrOperBadPktIds   Counter32,
      xradiuscActgSvrOperRxErrors    Counter32,
      xradiuscActgSvrOperTxErrors    Counter32,

      xradiuscActgSvrRowStatus       RowStatus
    }

xradiuscActgSvrIpAddress OBJECT-TYPE
    SYNTAX      IpAddress
    MAX-ACCESS  read-create
    STATUS      current
    DESCRIPTION
        "The IP Address of the specified Accounting Server.
	 If this address is configured, it is used exclusively
	 to communicate with this server."
    DEFVAL { 0 }
    ::= { xRadiuscActgSvrEntry 1 }

xradiuscActgSvrName OBJECT-TYPE
    SYNTAX      DisplayString
    MAX-ACCESS  read-create
    STATUS      current
    DESCRIPTION
        "The name identifying the specified Accounting Server.
	 If no IP Address is configured, then this name MAY be used
	 during a DNS lookup."
    DEFVAL { "" }
    ::= { xRadiuscActgSvrEntry 2 }

xradiuscActgSvrPort OBJECT-TYPE
    SYNTAX      INTEGER(1025..65535)
    MAX-ACCESS  read-create
    STATUS      current
    DESCRIPTION
        "The udp port number that the specified Accounting
	 Server is listening for requests."
    DEFVAL { 1813 }
    ::= { xRadiuscActgSvrEntry 3 }

xradiuscActgSvrTimeout OBJECT-TYPE
    SYNTAX      INTEGER(1..10)
    MAX-ACCESS  read-create
    STATUS      current
    DESCRIPTION
        "The number of seconds to wait for a response to a resquests."
    DEFVAL { 2 }
    ::= { xRadiuscActgSvrEntry 4 }

xradiuscActgSvrRetries OBJECT-TYPE
    SYNTAX      INTEGER(0..5)
    MAX-ACCESS  read-create
    STATUS      current
    DESCRIPTION
        "The number of times to resend the server a requests when
	 no response has been received."
    DEFVAL { 2 }
    ::= { xRadiuscActgSvrEntry 5 }

xradiuscActgSvrPriority OBJECT-TYPE
    SYNTAX      INTEGER(1..10)
    MAX-ACCESS  read-create
    STATUS      current
    DESCRIPTION
        "The priority assigned to this server.  Lowest priority
	 servers are used first.  In the case of multiple servers
	 having the same priority, they will be used in a round-
	 robin fashion when their priority is the highest of the
	 available servers."
    DEFVAL { 1 }
    ::= { xRadiuscActgSvrEntry 6 }

xradiuscActgSvrSecretKey OBJECT-TYPE
    SYNTAX      DisplayString
    MAX-ACCESS  read-create
    STATUS      current
    DESCRIPTION
        "The shared secret key associated with the specified
	 server.  It is used to authenticate requests and 
	 responses.  When this object is read from a non-superuser, 
	 '--------' is returned in order to maintain security."
    DEFVAL { "" }
    ::= { xRadiuscActgSvrEntry 7 }

xradiuscActgSvrVendorOffset OBJECT-TYPE
    SYNTAX      INTEGER(0..255)
    MAX-ACCESS  read-create
    STATUS      current
    DESCRIPTION
        "The offset used to assign Vendor Specific attribute IDs to 
	 the standard attribute number space.  Setting this value to
	 0, forces the encoding of Vendor Specific attributes within
	 the Vendor's number space, using the standard 
	 'Vendor-Specific' attribute.  Setting this to a non-zero
	 value uses standard attribute encoding, with the Vendor
	 Specific Base for the attributes beginning with this offset."
    DEFVAL { 0 }
    ::= { xRadiuscActgSvrEntry 8 }

xradiuscActgSvrOperIpAddress OBJECT-TYPE
    SYNTAX      IpAddress
    MAX-ACCESS  read-only
    STATUS      current
    DESCRIPTION
        "The IP Address currently being used to communicate 
	 the specified Accounting server."
    ::= { xRadiuscActgSvrEntry 9 }

xradiuscActgSvrOperState OBJECT-TYPE 
    SYNTAX      INTEGER {
                    unknown       (1),  
                    responding    (2),
                    notResponding (3),
                    notAvailable  (4)
                }
    MAX-ACCESS  read-only
    STATUS      current
    DESCRIPTION
        "The operational state of the specified Accounting server.
	 The 'unknown' state will be set periodically to allow 'notResponding'
	 servers to be retried after a period of time."
    ::= { xRadiuscActgSvrEntry 10 }

xradiuscActgSvrOperStateChange OBJECT-TYPE
    SYNTAX      TimeTicks
    MAX-ACCESS  read-only
    STATUS      current
    DESCRIPTION
        "The value of sysUpTime when the Accounting server
	 last changed state."
    ::= { xRadiuscActgSvrEntry 11 }

xradiuscActgSvrOperBadPktIds OBJECT-TYPE
    SYNTAX      Counter32
    MAX-ACCESS  read-only
    STATUS      current
    DESCRIPTION
        "The count of unexpected Packet IDs received on this port."
    ::= { xRadiuscActgSvrEntry 12 }

xradiuscActgSvrOperRxErrors OBJECT-TYPE
    SYNTAX      Counter32
    MAX-ACCESS  read-only
    STATUS      current
    DESCRIPTION
        "The count of general Receive errors encountered by this server"
    ::= { xRadiuscActgSvrEntry 13 }

xradiuscActgSvrOperTxErrors OBJECT-TYPE
    SYNTAX      Counter32
    MAX-ACCESS  read-only
    STATUS      current
    DESCRIPTION
        "The count of general Transmit errors encountered by this server"
    ::= { xRadiuscActgSvrEntry 14 }

xradiuscActgSvrRowStatus OBJECT-TYPE
    SYNTAX       RowStatus
    MAX-ACCESS   read-create
    STATUS       current
    DESCRIPTION
    "This variable displays the status of  the  entry.  Setting it to 
     'destroy' marks the entry as removed.  Eventually, when no other
     applications depend on that particular resource, it will be completely
     removed from the table.  Setting it to  either 'create', or 'active' will
     add a row to the table."
    ::= { xRadiuscActgSvrEntry 15 }
 
-- ****************************************************************
-- Conformance Information
-- ****************************************************************

xradiusCompliances OBJECT IDENTIFIER ::= { xRadiusConformance 1 }
xradiusGroups      OBJECT IDENTIFIER ::= { xRadiusConformance 2 }

--
-- Compliance Statements
--

xradiusCompliance MODULE-COMPLIANCE
    STATUS      current
    DESCRIPTION
        "The compliance statement for all agents that support this
        MIB. A compliant agent implements all objects defined in this
        MIB."
    MODULE  -- this module
    MANDATORY-GROUPS {
        xradiusAllGroup
    }
    ::= { xradiusCompliances 1 }

--
-- All Object Groups
--
xradiusAllGroup OBJECT-GROUP
    OBJECTS {
       -- ******************************
       -- Global Configuration
       -- ******************************
       xradiuscAdminAuthStatus,
       xradiuscAdminActgStatus,
       xradiuscDebugCmd,
       xradiuscNasId,
       xradiuscNasIP,
       xradiuscBackgroundTimer,
       xradiuscMaxOutstanding,
       --
       -- Global Stats
       --
       xradiuscOperAuthStatus,
       xradiuscOperActgStatus,
       xradiuscOperNasId,
       xradiuscOperNasIP,
       xradiuscOperGenErrors,
       xradiuscOperAuthQCurr,
       xradiuscOperAuthQMax,
       xradiuscOperAuthExpected,
       xradiuscOperAuthEnqueued,
       xradiuscOperAuthDequeued,
       xradiuscOperActgQCurr,
       xradiuscOperActgQMax,
       xradiuscOperActgExpected,
       xradiuscOperActgEnqueued,
       xradiuscOperActgDequeued,
       xradiuscOperLastPktID,
       xradiuscOperNextPktID,
       xradiuscOperLastAuthIndex,
       xradiuscOperLastActgIndex,
       xradiuscOperPendingListCurr,
       xradiuscOperPendingListMax,
       xradiuscOperPendingExpected,
       xradiuscOperPendingEnqueued,
       xradiuscOperPendingDequeued,

       -- ******************************
       -- Authentication Server Config
       -- ******************************
       xradiuscAuthSvrIpAddress,
       xradiuscAuthSvrName,
       xradiuscAuthSvrPort,
       xradiuscAuthSvrTimeout,
       xradiuscAuthSvrRetries,
       xradiuscAuthSvrPriority,
       xradiuscAuthSvrSecretKey,
       xradiuscAuthSvrVendorOffset,

       xradiuscAuthSvrRowStatus,

       -- 
       -- Auththentication Server Stats
       -- 
       xradiuscAuthSvrOperIpAddress,
       xradiuscAuthSvrOperState,
       xradiuscAuthSvrOperStateChange,
       xradiuscAuthSvrOperBadPktIds,
       xradiuscAuthSvrOperRxErrors,
       xradiuscAuthSvrOperTxErrors,

       -- ******************************
       -- Accounting Server Config
       -- ******************************
       xradiuscActgSvrIpAddress,
       xradiuscActgSvrName,
       xradiuscActgSvrPort,
       xradiuscActgSvrTimeout,
       xradiuscActgSvrRetries,
       xradiuscActgSvrPriority,
       xradiuscActgSvrSecretKey,
       xradiuscActgSvrVendorOffset,
       -- 
       -- Accounting Server Stats
       -- 
       xradiuscActgSvrOperIpAddress,
       xradiuscActgSvrOperState,
       xradiuscActgSvrOperStateChange,
       xradiuscActgSvrOperBadPktIds,
       xradiuscActgSvrOperRxErrors,
       xradiuscActgSvrOperTxErrors,

       xradiuscActgSvrRowStatus
    }
    STATUS      current
    DESCRIPTION
        "The set of all accessible objects in this MIB."
    ::= { xradiusGroups 1 }

END
