--MibName=caiNtOs
--
-- NT System Agent MIB
-- v1.0.2
-- 
--
-- CA-UK Development
--
--

CA-NTOS-MIB DEFINITIONS ::= BEGIN                          -- defined by IETF
IMPORTS
	TRAP-TYPE FROM RFC-1215
              OBJECT-TYPE, Counter, Gauge, enterprises    FROM RFC1155-SMI
				  DisplayString FROM RFC1213-MIB;

cai			OBJECT IDENTIFIER ::= { enterprises 791 }
caiSysMgr		OBJECT IDENTIFIER ::= { cai 2 }
agentWorks		OBJECT IDENTIFIER ::= { caiSysMgr 9 }
nt			OBJECT IDENTIFIER ::= { agentWorks 2 }

caiNtOs		OBJECT IDENTIFIER ::= { nt 2 }

ntConfigGroup		OBJECT IDENTIFIER 
--	DESCRIPTION
--     		"Contains all configuration groups for NT System Agent."
						::= { caiNtOs 2 }
ntStatusGroup		OBJECT IDENTIFIER 
--	DESCRIPTION
--     		"Contains all status groups and tables for NT System Agent."
						::= { caiNtOs 3 }
ntPollGroup		OBJECT IDENTIFIER 
--	DESCRIPTION
--     		"Contains all polling tables for NT System Agent."
						::= { caiNtOs 4 }

ntAvailableGroup	OBJECT IDENTIFIER 
--	DESCRIPTION
--     		"Contains availablility tables for NT System Agent."
						::= { caiNtOs 5 }
	
--
--			Configuration
--
--
--	General Configuration Entry
--
ntGeneralConfig	OBJECT IDENTIFIER 
--	DESCRIPTION
--     	"Maintains the agent version and timestamps of polling."
	::= { ntConfigGroup 2 }

ntAgentVersion OBJECT-TYPE
	SYNTAX  DisplayString
	ACCESS  read-only
	STATUS  mandatory
	DESCRIPTION
		"&<caiNtOs.100>The currently installed version of NT System Agent." 
			::= { ntGeneralConfig 2 }

ntAgentColdStartTimestamp OBJECT-TYPE
	SYNTAX  DisplayString
	ACCESS  read-only
	STATUS  mandatory
	DESCRIPTION
		"&<caiNtOs.101>The date and time that NT System Agent was last initiated." 
			::= { ntGeneralConfig  3 }

ntAgentWarmStartTimestamp OBJECT-TYPE
	SYNTAX  DisplayString
	ACCESS  read-only
	STATUS  mandatory
	DESCRIPTION 
		"&<caiNtOs.102>The date and time that NT System Agent was last reset." 
			::= { ntGeneralConfig  4 }

ntFilesystemPollTimestamp OBJECT-TYPE
	SYNTAX  DisplayString
	ACCESS  read-only
	STATUS  mandatory
	DESCRIPTION
		"&<caiNtOs.103>The date and time that NT System Agent last polled for filesystem information." 
			::= { ntGeneralConfig  5 }

ntFilePollTimestamp OBJECT-TYPE
	SYNTAX  DisplayString
	ACCESS  read-only
	STATUS  mandatory
	DESCRIPTION
		"&<caiNtOs.104>The date and time that NT System Agent last polled for file information."
			::= { ntGeneralConfig  6 }
ntProcessPollTimestamp OBJECT-TYPE
	SYNTAX  DisplayString
	ACCESS  read-only
	STATUS  mandatory
	DESCRIPTION
		"&<caiNtOs.105>The date and time that NT System Agent last polled for process information." 
			::= { ntGeneralConfig  7 }

ntServicePollTimestamp OBJECT-TYPE
	SYNTAX  DisplayString
	ACCESS  read-only
	STATUS  mandatory
	DESCRIPTION
		"&<caiNtOs.106>The date and time that NT System Agent last polled for service information." 
			::= { ntGeneralConfig  8 }

ntPrinterPollTimestamp OBJECT-TYPE
	SYNTAX  DisplayString
	ACCESS  read-only
	STATUS  mandatory
	DESCRIPTION
		"&<caiNtOs.107>The date and time that NT System Agent last polled for printer information."
			::= { ntGeneralConfig  9 }

ntMemoryPollTimestamp OBJECT-TYPE
	SYNTAX  DisplayString
	ACCESS  read-only
	STATUS  mandatory
	DESCRIPTION
		"&<caiNtOs.108>The date and time that NT System Agent last polled for memory information."
			::= { ntGeneralConfig  10 }

ntProcessorPollTimestamp OBJECT-TYPE
	SYNTAX  DisplayString
	ACCESS  read-only
	STATUS  mandatory
	DESCRIPTION
		"&<caiNtOs.109>The date and time that NT System Agent last polled for % CPU utilization information."
			::= { ntGeneralConfig  11 }

ntRegistryPollTimestamp OBJECT-TYPE
	SYNTAX  DisplayString
	ACCESS  read-only
	STATUS  mandatory
	DESCRIPTION
		"&<caiNtOs.110>The date and time that NT System Agent last polled for registry information."
			::= { ntGeneralConfig  12 }

ntLogPollTimestamp OBJECT-TYPE
	SYNTAX  DisplayString
	ACCESS  read-only
	STATUS  mandatory
	DESCRIPTION
		"&<caiNtOs.111>The date and time that NT System Agent last polled for event log information."
			::= { ntGeneralConfig  13 }

--
--	FileSystem Configuration Entry
--

ntFileSystemConfig	OBJECT IDENTIFIER
--              DESCRIPTION
--	"Specifies the polling interval and default filesystem utilization
--	 thresholds for each filesystem to be monitored.  Users also enter
--	 here details of filesystems to be added or removed."
			::= { ntConfigGroup 3 }

ntFSPollInterval OBJECT-TYPE
	SYNTAX  INTEGER
	ACCESS  read-write
	STATUS  mandatory
	DESCRIPTION
		"&<caiNtOs.112>Filesystem Poll Interval."
			::= { ntFileSystemConfig 2 }
ntDefFSWarnThresh OBJECT-TYPE
	SYNTAX  INTEGER
	ACCESS  read-write
	STATUS  mandatory
	DESCRIPTION
		"&<caiNtOs.113>Default utilization warning threshold defined in terms of percentage of
		 filesystem total capacity."
			::= { ntFileSystemConfig 3 }

ntDefFSCriticalThresh OBJECT-TYPE
	SYNTAX  INTEGER
	ACCESS  read-write
	STATUS  mandatory
	DESCRIPTION
		"&<caiNtOs.114>Default utilization critical threshold defined in terms of percentage of
		 filesystem total capacity."
			::= { ntFileSystemConfig 4 }

ntDefFSDelta OBJECT-TYPE
	SYNTAX  INTEGER
	ACCESS  read-write
	STATUS  mandatory
	DESCRIPTION
		"&<caiNtOs.115>Default delta threshold defined in terms of percentage of total capacity."
			::= { ntFileSystemConfig 5 }

ntFSMonitored OBJECT-TYPE
	SYNTAX  INTEGER
	ACCESS  read-only
	STATUS  mandatory
	DESCRIPTION
		"&<caiNtOs.116>Number of Filesystems currently being monitored."
			::= { ntFileSystemConfig 6 }

ntFSAdd OBJECT-TYPE
	SYNTAX DisplayString
	ACCESS  read-write
	STATUS  mandatory
	DESCRIPTION
		"&<caiNtOs.117>User enters new filesystems for monitoring here, referencing by drive letter.  e.g. c:\"
			::= { ntFileSystemConfig 7 }

ntFSRemove OBJECT-TYPE
	SYNTAX DisplayString
	ACCESS  read-write
	STATUS  mandatory
	DESCRIPTION
		"&<caiNtOs.118>User removes filesystems from the monitoring list, referencing by drive letter.  e.g. c:\"
			::= { ntFileSystemConfig 8 }

--
--	File Configuration Entry
--

ntFileConfig	OBJECT IDENTIFIER
--              DESCRIPTION
--	"Defines the default monitoring of a file.  Files may be
--	 monitored for size using Warning and Critical thresholds
--	 and timestamp of the file may also be monitored for change.
--	 Finally, the size change rate of the file may be monitored,
--	 with the user defining a size and time delta to monitor
--	 against, the time delta being a multiple of monitoring periods."
			::= { ntConfigGroup 4 } 

ntFilePollInterval OBJECT-TYPE
	SYNTAX  INTEGER
	ACCESS  read-write
	STATUS  mandatory
	DESCRIPTION
		"&<caiNtOs.119>File Poll Interval."
			::= { ntFileConfig 2 }


ntDefFileSizeWarning OBJECT-TYPE
	SYNTAX  INTEGER
	ACCESS  read-write
	STATUS  mandatory
	DESCRIPTION
		"&<caiNtOs.120>Initial Warning threshold, defined in terms of percentage of current size
		 (when the file was added for monitoring)."
			 ::= { ntFileConfig 3 }

ntDefFileSizeCritical OBJECT-TYPE
	SYNTAX  INTEGER
	ACCESS  read-write
	STATUS  mandatory
	DESCRIPTION
		"&<caiNtOs.121>Initial Critical threshold, defined in terms of percentage of current size
		 (when the file was added for monitoring)."
			 ::= { ntFileConfig 4 }

ntDefFileSizeChangeFlag OBJECT-TYPE
	SYNTAX INTEGER {
		do-not-monitor(1),
		warning(2),
		critical(3)
		}
	ACCESS  read-write
	STATUS  mandatory
	DESCRIPTION
		"&<caiNtOs.122>Flag indicating whether, by default, files should be monitored for size change."
			::= { ntFileConfig 5 }

ntDefFileSizeChange OBJECT-TYPE
	SYNTAX  INTEGER
	ACCESS  read-write
	STATUS  mandatory
	DESCRIPTION
		"&<caiNtOs.123>Percentage file size change over ntFileSizeChangePolls required to raise an alert."
			::= { ntFileConfig 6 }

ntDefFileTimestampFlag OBJECT-TYPE
	SYNTAX  INTEGER {
		do-not-monitor(1),
		warning(2),
		critical(3)
		}
	ACCESS  read-write
	STATUS  mandatory
	DESCRIPTION
		"&<caiNtOs.124>Flag indicating at what alert level the file should be monitored for a timestamp change."
			::= { ntFileConfig 7 }

ntFilesMonitored OBJECT-TYPE
	SYNTAX  INTEGER
	ACCESS  read-only
	STATUS  mandatory
	DESCRIPTION
		"&<caiNtOs.125>Number of Files currently being monitored"
			::= { ntFileConfig 8 }

ntFileAdd OBJECT-TYPE
	SYNTAX DisplayString
	ACCESS  read-write
	STATUS  mandatory	
	DESCRIPTION
		"&<caiNtOs.126>Full pathname of a file to add to the monitoring list."
			::= { ntFileConfig 9 }

ntFileRemove OBJECT-TYPE
	SYNTAX DisplayString
	ACCESS  read-write
	STATUS  mandatory
	DESCRIPTION
		"&<caiNtOs.127>Full pathname of a file to remove from the monitoring list."
			::= { ntFileConfig 10 }

--
--	Process Configuration Entry
--

ntProcessConfig OBJECT IDENTIFIER
--              DESCRIPTION
--			"Defines the default monitoring of a processes.
--			 Processes may be monitored for existance or 
--			 non-existance with the additional ability to
--			 monitor for thread and instance counts on the
--			 system."
	::= { ntConfigGroup 5 } 

ntProcPollInterval OBJECT-TYPE
	SYNTAX  INTEGER
	ACCESS  read-write
	STATUS  mandatory
	DESCRIPTION
		"&<caiNtOs.128>Process Poll Interval."
			::= { ntProcessConfig 2 }

ntDefProcAlertLevel OBJECT-TYPE
	SYNTAX  INTEGER {
		not-monitored(1),
		warning(2),
		critical(3)
		}
	ACCESS  read-write
	STATUS  mandatory
	DESCRIPTION
		"&<caiNtOs.129>Default level of alert to be signalled."
			::= { ntProcessConfig 3 }

ntDefProcExist OBJECT-TYPE
	SYNTAX  INTEGER {
		alert-if-exist(1),
		alert-if-not-exist(2)
		}
	ACCESS  read-write
	STATUS  mandatory
	DESCRIPTION
		"&<caiNtOs.130>Flag indicating whether, by default, an alert is raised if the process
		exists or doesn't exist."
			::= { ntProcessConfig 4 }

ntDefProcInstanceAlert OBJECT-TYPE
	SYNTAX  INTEGER {
		true(1),
		false(2)
		}
	ACCESS  read-write
	STATUS  mandatory
	DESCRIPTION
		"&<caiNtOs.131>Flag indicating whether, by default, the instances of the process should be monitored."
			::= { ntProcessConfig 5 }

ntDefProcThreadAlert OBJECT-TYPE
	SYNTAX  INTEGER {
		do-not-monitor(1),
		above(2),
		below(3)
		}
	ACCESS  read-write
	STATUS  mandatory
	DESCRIPTION
		"&<caiNtOs.132>Value indicating whether, by default, the thread count of the process should be monitored."
			::= { ntProcessConfig 6 }

ntProcessesMonitored OBJECT-TYPE
	SYNTAX  INTEGER
	ACCESS  read-only
	STATUS  mandatory
	DESCRIPTION
		"&<caiNtOs.133>Number of Processes currently being monitored"
			::= { ntProcessConfig 7 }

ntProcAdd OBJECT-TYPE
	SYNTAX  DisplayString
	ACCESS  read-write
	STATUS  mandatory
	DESCRIPTION
		"&<caiNtOs.134>Process to add to the monitoring list."
			::= { ntProcessConfig 8}

ntProcRemove OBJECT-TYPE
	SYNTAX  DisplayString
	ACCESS  read-write
	STATUS  mandatory
	DESCRIPTION
		"&<caiNtOs.135>Process to the remove from the monitoring list."
			::= { ntProcessConfig 9 }

--
--	Service Configuration Entry
--

ntServiceConfig OBJECT IDENTIFIER
--              DESCRIPTION
--	"Defines the default monitoring of services.  Services may be
--	 monitored for existance or non-existance and configured to send
--	 traps on a change in operational status."
			::= { ntConfigGroup 6 } 

ntServPollInterval OBJECT-TYPE
	SYNTAX  INTEGER
	ACCESS  read-write
	STATUS  mandatory
	DESCRIPTION
		"&<caiNtOs.136>Service Poll Interval."
			::= { ntServiceConfig 2 }

ntDefServAlertOn OBJECT-TYPE
	SYNTAX  INTEGER {
		do-not-monitor(1),
		active(2),
		inactive(3)
		}
	ACCESS  read-write
	STATUS  mandatory
	DESCRIPTION
		"&<caiNtOs.137>Default configuration indicating when to raise an event, either never,
		 when the service is active or when it is inactive."
			::= { ntServiceConfig 3 }

ntServicesMonitored OBJECT-TYPE
	SYNTAX  INTEGER
	ACCESS  read-only
	STATUS  mandatory
	DESCRIPTION
		"&<caiNtOs.138>Number of Services currently being monitored."
			::= { ntServiceConfig 4 }

ntServiceAdd OBJECT-TYPE
	SYNTAX DisplayString
	ACCESS  read-write
	STATUS  mandatory
	DESCRIPTION
		"&<caiNtOs.139>Service to add to the monitoring list, this is the Service Name,
		not the description provided by the vendor."
			::= { ntServiceConfig 5 }

ntServiceRemove OBJECT-TYPE
	SYNTAX  DisplayString
	ACCESS  read-write
	STATUS  mandatory
	DESCRIPTION
		"&<caiNtOs.140>Process to remove from the monitoring list, this is the Service Name,
		 not the description provided by the vendor."
			::= { ntServiceConfig 6 }

--
--	Printer Configuration Entry
--

ntPrinterConfig OBJECT IDENTIFIER
--              DESCRIPTION
--	"Defines the default monitoring of printers.  Printers may be
--	 monitored for the number of jobs on the print queue and on
--	 printer events."
			::= { ntConfigGroup 7 } 

ntPrinterPollInterval OBJECT-TYPE
	SYNTAX  INTEGER
	ACCESS  read-write
	STATUS  mandatory
	DESCRIPTION
		"&<caiNtOs.141>Printer Poll Interval."
			::= { ntPrinterConfig 2 }

ntDefPrintEventMonitor OBJECT-TYPE
	SYNTAX  INTEGER {
		do-not-monitor(1),
		warning(2),
		critical(3)
		}	
	ACCESS  read-write
	STATUS  mandatory
	DESCRIPTION
		"&<caiNtOs.142>Flag indicating whether, by default. alerts should be raised on printer
		 events, and if so, the level of alert to raise."
			::= { ntPrinterConfig 3 }

ntDefPrinterQFlag OBJECT-TYPE
	SYNTAX  INTEGER {
		true(1),
		false(2)
		}
	ACCESS  read-write
	STATUS  mandatory
	DESCRIPTION
		"&<caiNtOs.143>Flag indicating whether, by default. the printer's job queue should be monitored."
			::= { ntPrinterConfig 4 }

ntDefPrinterQWarning OBJECT-TYPE
	SYNTAX  INTEGER
	ACCESS  read-write
	STATUS  mandatory
	DESCRIPTION
		"&<caiNtOs.144>Default Warning threshold for the number of jobs in the printer'squeue."
			::= { ntPrinterConfig 5 }

ntDefPrinterQCritical OBJECT-TYPE
	SYNTAX  INTEGER
	ACCESS  read-write
	STATUS  mandatory
	DESCRIPTION
		"&<caiNtOs.145>Default Critical threshold for the number of jobs in the printer's queue." 
			::= { ntPrinterConfig 6 }

ntPrintersMonitored OBJECT-TYPE
	SYNTAX  INTEGER
	ACCESS  read-only
	STATUS  mandatory
	DESCRIPTION
		"&<caiNtOs.146>Number of Printers currently being monitored."
			::= { ntPrinterConfig 7 }

ntPrinterAdd OBJECT-TYPE
	SYNTAX  DisplayString
	ACCESS  read-write
	STATUS  mandatory
	DESCRIPTION
		"&<caiNtOs.147>Printer to add to the monitoring list."
			::= { ntPrinterConfig 8 }

ntPrinterRemove OBJECT-TYPE
	SYNTAX  DisplayString
	ACCESS  read-write
	STATUS  mandatory
	DESCRIPTION
		"&<caiNtOs.148>Printer to remove from the monitoring list."
			::= { ntPrinterConfig 9 }

--
--	Memory Configuration Entry
--

ntMemoryConfig OBJECT IDENTIFIER
--	DESCRIPTION
--		"Defines the monitoring of memory.  Three aspects of
--		 memory are recorded, Memory Load (as a percentage),
--		 Physical Memory Available and Paging Memory available
--		 (available swapspace).  Against each of the three aspects
--		 are defined the number of monitoring cycles for which the
--		 attribute should remain in a new state until an alert is
--		 signalled."
		::= { ntConfigGroup 8 } 

ntMemPollInterval OBJECT-TYPE
	SYNTAX  INTEGER
	ACCESS  read-write
	STATUS  mandatory
	DESCRIPTION
		"&<caiNtOs.149>Memory Monitoring Poll Interval."
			::= { ntMemoryConfig 2 }

ntDefMemLoadWarning OBJECT-TYPE
	SYNTAX  INTEGER
	ACCESS  read-write
	STATUS  mandatory
	DESCRIPTION
		"&<caiNtOs.150>Current Memory Load Warning Threshold, in terms of percentage.
		  This threshold should be lower, or equal to the Critical Threshold."
			::= { ntMemoryConfig 3 }

ntDefMemLoadCritical OBJECT-TYPE
	SYNTAX  INTEGER
	ACCESS  read-write
	STATUS  mandatory
	DESCRIPTION
		"&<caiNtOs.151>Current Memory Load Critical Threshold, in terms of percentage.
		 This threshold should be higher, or equal to the Warning Threshold."
			::= { ntMemoryConfig 4 }

ntDefMemLoadCount OBJECT-TYPE
	SYNTAX  INTEGER
	ACCESS  read-write
	STATUS  mandatory
	DESCRIPTION
		"&<caiNtOs.152>The number of successive polling periods that Memory Load must exceed
		cross a threshold before a status change is signalled."
			::= { ntMemoryConfig 5 }

ntDefMemPhysWarning OBJECT-TYPE
	SYNTAX  INTEGER
	ACCESS  read-write
	STATUS  mandatory
	DESCRIPTION
		"&<caiNtOs.153>Available Physical Memory Warning Threshold, in terms of percentage of
		 total Physical Memory on the system.  This threshold should be higher,
		  or equal, to the Critical Threshold."
			::= { ntMemoryConfig 6 }

ntDefMemPhysCritical OBJECT-TYPE
	SYNTAX  INTEGER
	ACCESS  read-write
	STATUS  mandatory
	DESCRIPTION
		"&<caiNtOs.154>Available Physical Memory Critical Threshold, in terms of percentage of
		 total Physical Memory on the system.  This threshold should be lower, or
		  equal, to the Warning Threshold."
			::= { ntMemoryConfig 7 }

ntDefMemPhysCount OBJECT-TYPE
	SYNTAX  INTEGER
	ACCESS  read-write
	STATUS  mandatory
	DESCRIPTION
		"&<caiNtOs.155>The number of successive polling periods that Physical Memory must exceed
		 cross a threshold before a status change is signalled."
			::= { ntMemoryConfig 8 }

ntDefMemSwapWarning OBJECT-TYPE
	SYNTAX  INTEGER
	ACCESS  read-write
	STATUS  mandatory
	DESCRIPTION
		"&<caiNtOs.156>Available Swapspace Warning Threshold, in terms of percentage of total
		 Swapspace (Page File Memory) available on the system.  This threshold
		  should be higher, or equal, to the Critical Threshold."
			::= { ntMemoryConfig 9 }

ntDefMemSwapCritical OBJECT-TYPE
	SYNTAX  INTEGER
	ACCESS  read-write
	STATUS  mandatory
	DESCRIPTION
		"&<caiNtOs.157>Available Swapspace Critical Threshold, in terms of percentage of total
		 Swapspace (Page File Memory) available on the system.  This threshold
		  should be lower, or equal, to the Warning Threshold"
			::= { ntMemoryConfig 10 }

ntDefMemSwapCount OBJECT-TYPE
	SYNTAX  INTEGER
	ACCESS  read-write
	STATUS  mandatory
	DESCRIPTION
		"&<caiNtOs.158>The number of successive polling periods that available Swapspace must exceed
		 cross a threshold before a status change is signalled."
			::= { ntMemoryConfig 11 }

--
--	Processor Configuration Entry
--

ntProcessorConfig OBJECT IDENTIFIER
--	DESCRIPTION
--		"Defines the default thresholds set against total CPU
--		 utilization on a per-processor basis. Utilizations are
--		 defined the number of monitoring cycles for which the
--		 attribute should remain in a potentially new state until
--		 an alert is signalled.  All processors are monitored on
--		 a system."
			::= { ntConfigGroup 9 } 

ntCPUPollInterval OBJECT-TYPE
	SYNTAX  INTEGER
	ACCESS  read-write
	STATUS  mandatory
	DESCRIPTION
		"&<caiNtOs.159>Processor Monitoring Poll Interval."
			::= { ntProcessorConfig 2 }

ntDefCPUWarning OBJECT-TYPE
	SYNTAX  INTEGER
	ACCESS  read-write
	STATUS  mandatory
	DESCRIPTION
		"&<caiNtOs.160>Default CPU Warning Threshold, defined in terms of %Total CPU.  This should
		 be lower, or equal to, the Critical Threshold."
			::= { ntProcessorConfig 3 }

ntDefCPUCritical OBJECT-TYPE
	SYNTAX  INTEGER
	ACCESS  read-write
	STATUS  mandatory
	DESCRIPTION
		"&<caiNtOs.161>Default CPU Critical Threshold, defined in terms of %Total CPU.  This should
		 be greater than, or equal to, the Warning Threshold."
			::= { ntProcessorConfig 4 }

ntDefCPUCount OBJECT-TYPE
	SYNTAX  INTEGER
	ACCESS  read-write
	STATUS  mandatory
	DESCRIPTION
		"&<caiNtOs.162>The number of successive polling periods that %Total CPU must exceed cross
		 a threshold before a status change is signalled."
			::= { ntProcessorConfig 5 }

ntCPUsMonitored OBJECT-TYPE
	SYNTAX  INTEGER
	ACCESS  read-only
	STATUS  mandatory
	DESCRIPTION
		"&<caiNtOs.163>Number of CPUs currently being monitored."
			::= { ntProcessorConfig 6 }

--
--	Registry Configuration Entry
--

ntRegistryConfig OBJECT IDENTIFIER
--      DESCRIPTION
--		"Defines default thresholds, monitoring policy and
--		 enables users to add and remove registry leaves for
--		 monitoring."
			::= { ntConfigGroup 10 } 

ntRegPollInterval OBJECT-TYPE
	SYNTAX  INTEGER
	ACCESS  read-write
	STATUS  mandatory
	DESCRIPTION
		"&<caiNtOs.164>Registry Monitoring Poll Interval."
			::= { ntRegistryConfig 2 } 

ntDefRegMonitorLevel OBJECT-TYPE
	SYNTAX  INTEGER {
		do-not-monitor(1),
		change(2),
		thresholds(3)
		}
	ACCESS  read-write
	STATUS  mandatory
	DESCRIPTION
		"&<caiNtOs.165>Defines the default type of value monitoring to be performed, this may be
		 not to monitor, monitor for a change or to monitor against thresholds.  
		 For leaves of string type requests to monitor against thresholds are ignored."
			::= { ntRegistryConfig 3 }

ntDefRegWarning OBJECT-TYPE
	SYNTAX  INTEGER
	ACCESS  read-write
	STATUS  mandatory
	DESCRIPTION
		"&<caiNtOs.166>Default Warning Threshold for integer type leaves, defined as a percentage of
		 the original leaf value at initiation.  (This value is ignored if the leaf is
		  of string type)."
			::= { ntRegistryConfig 4 }

ntDefRegCritical OBJECT-TYPE
	SYNTAX  INTEGER
	ACCESS  read-write
	STATUS  mandatory
	DESCRIPTION
		"&<caiNtOs.167>Default Critical Threshold for integer type leaves, defined as a percentage of
		 the original leaf value at initiation.  (This value is ignored if the leaf is
		  of string type)."
			::= { ntRegistryConfig 5 }

ntRegLeavesMonitored OBJECT-TYPE
	SYNTAX  INTEGER
	ACCESS  read-only
	STATUS  mandatory
	DESCRIPTION
		"&<caiNtOs.168>Number of Registry Leaves currently being monitored."
			::= { ntRegistryConfig 6 }

ntRegistryLeafAdd OBJECT-TYPE
	SYNTAX  DisplayString
	ACCESS  read-write
	STATUS  mandatory
	DESCRIPTION
		"&<caiNtOs.169>Registry leaf to add to the monitoring list.  This should be explicit and in
		 the form Table\Leaf (for example 'HKEY-LOCAL-MACHINE\SOFTWARE\MyApp\Version')."
			::= { ntRegistryConfig 7 }

ntRegistryLeafRemove OBJECT-TYPE
	SYNTAX  DisplayString
	ACCESS  read-write
	STATUS  mandatory
	DESCRIPTION
		"&<caiNtOs.170>Registry leaf to remove from the monitoring list."
			::= { ntRegistryConfig 8 }

--
--	Event Log Configuration Entry
--

ntEventLogConfig OBJECT IDENTIFIER
--      DESCRIPTION
--		"Defines the poll interval for event log monitoring.
--		It also stores the starting timestamp and enables event
--		watches to be added or removed."
			::= { ntConfigGroup 11 } 

ntLogPollInterval OBJECT-TYPE
	SYNTAX  INTEGER
	ACCESS  read-write
	STATUS  mandatory
	DESCRIPTION
		"&<caiNtOs.171>The interval at which the agent checks the event logs."
			::= { ntEventLogConfig 1 }

ntLogApplicationCount OBJECT-TYPE
	SYNTAX  INTEGER
	ACCESS  read-only
	STATUS  mandatory
	DESCRIPTION
		"&<caiNtOs.172>The number of events currently in the application event log."
			::= { ntEventLogConfig 2 }

ntLogSecurityCount OBJECT-TYPE
	SYNTAX  INTEGER
	ACCESS  read-only
	STATUS  mandatory
	DESCRIPTION
		"&<caiNtOs.173>The number of events currently in the security event log."
			::= { ntEventLogConfig 3 }

ntLogSystemCount OBJECT-TYPE
	SYNTAX  INTEGER
	ACCESS  read-only
	STATUS  mandatory
	DESCRIPTION
		"&<caiNtOs.174>The number of events currently in the system event log."
			::= { ntEventLogConfig 4 }

ntDefLogMonitorLevel OBJECT-TYPE
	SYNTAX  INTEGER {
		do-not-monitor(1),
		warning(2),
		critical(3)
		}
	ACCESS  read-write
	STATUS  mandatory
	DESCRIPTION
		"&<caiNtOs.175>Defines the default type of value monitoring to be performed, this may be not
		 to raise traps or raise warning or critical level traps."
			::= { ntEventLogConfig 5 }

ntLogsMonitored OBJECT-TYPE
	SYNTAX  INTEGER
	ACCESS  read-only
	STATUS  mandatory
	DESCRIPTION
		"&<caiNtOs.176>Number of Event Log Watches"
			::= { ntEventLogConfig 6 }

ntLogAdd OBJECT-TYPE
	SYNTAX  DisplayString
	ACCESS  read-write
	STATUS  mandatory
	DESCRIPTION
		"&<caiNtOs.177>Comma-separated description of the event watcher to be configured.  
		The format is:LOG/S,SOURCE,SEVERITY/s,EVENTID,USER,COMPUTER"		
	::= { ntEventLogConfig 7 }

--
--			Status
--

--
--	Status Summary Entry
--

ntStatusSummary OBJECT IDENTIFIER
--	DESCRIPTION
--		"Provides an overall status of NT System Agent."
			::= { ntStatusGroup 2 } 

ntStatus OBJECT-TYPE
	SYNTAX INTEGER {
		ok(1),
		warning(2),
		critical(3)
		}
	ACCESS  read-only
	STATUS  mandatory
	DESCRIPTION
		"&<caiNtOs.178>The overall status of the NT System Agent, aggregated from it's component managed objects.  This is a 'worst case' aggregation."
			::= { ntStatusSummary 2 }

ntTotalWarning OBJECT-TYPE
	SYNTAX  INTEGER
	ACCESS  read-only
	STATUS  mandatory
	DESCRIPTION
		"&<caiNtOs.179>The total number of managed objects with a Warning Status."
			::= { ntStatusSummary 3 }

ntTotalCritical OBJECT-TYPE
	SYNTAX  INTEGER
	ACCESS  read-only
	STATUS  mandatory
	DESCRIPTION
		"&<caiNtOs.180>The total number of managed objects with a Critical Status."
			::= { ntStatusSummary 4 }

ntFSWarnStatus OBJECT-TYPE
	SYNTAX  INTEGER
	ACCESS  read-only
	STATUS  mandatory
	DESCRIPTION
		"&<caiNtOs.181>The total number of filesystems with a Warning state."
			::= { ntStatusSummary 5 }

ntFSCriticalStatus OBJECT-TYPE
	SYNTAX  INTEGER
	ACCESS  read-only
	STATUS  mandatory
	DESCRIPTION
		"&<caiNtOs.182>The total number of filesystems with a Critical state."
			::= { ntStatusSummary 6 }

ntFileWarnStatus OBJECT-TYPE
	SYNTAX  INTEGER
	ACCESS  read-only
	STATUS  mandatory
	DESCRIPTION
		"&<caiNtOs.183>The total number of monitored files with a Warning state."
			::= { ntStatusSummary 7 }

ntFileCriticalStatus OBJECT-TYPE
	SYNTAX  INTEGER
	ACCESS  read-only
	STATUS  mandatory
	DESCRIPTION
		"&<caiNtOs.184>The total number of monitored files with a Critical state."
			::= { ntStatusSummary 8 }

ntProcessWarnStatus OBJECT-TYPE
	SYNTAX  INTEGER
	ACCESS  read-only
	STATUS  mandatory
	DESCRIPTION
		"&<caiNtOs.185>The total number of processes with a Warning state."
			::= { ntStatusSummary 9 }

ntProcessCriticalStatus OBJECT-TYPE
	SYNTAX  INTEGER
	ACCESS  read-only
	STATUS  mandatory
	DESCRIPTION
		"&<caiNtOs.186>The total number of processes with a Critical state."
			::= { ntStatusSummary 10 }

ntServicesWarnStatus OBJECT-TYPE
	SYNTAX  INTEGER
	ACCESS  read-only
	STATUS  mandatory
	DESCRIPTION
		"&<caiNtOs.187>The total number of services with a Warning state."
			::= { ntStatusSummary 11 }

ntServicesCriticalStatus OBJECT-TYPE
	SYNTAX  INTEGER
	ACCESS  read-only
	STATUS  mandatory
	DESCRIPTION
		"&<caiNtOs.188>The total number of services with a Critical state."
			::= { ntStatusSummary 12 }

ntPrintWarnStatus OBJECT-TYPE
	SYNTAX  INTEGER
	ACCESS  read-only
	STATUS  mandatory
	DESCRIPTION
		"&<caiNtOs.189>The total number of monitored printers with a Warning state."
			::= { ntStatusSummary 13 }

ntPrintCriticalStatus OBJECT-TYPE
	SYNTAX  INTEGER
	ACCESS  read-only
	STATUS  mandatory
	DESCRIPTION
		"&<caiNtOs.190>The total number of monitored printers with a Critical state."
			::= { ntStatusSummary 14 }

ntMemoryWarnStatus OBJECT-TYPE
	SYNTAX  INTEGER
	ACCESS  read-only
	STATUS  mandatory
	DESCRIPTION
		"&<caiNtOs.191>The total number of monitored memory attributes with a Warning state."
			::= { ntStatusSummary 15 }

ntMemoryCriticalStatus OBJECT-TYPE
	SYNTAX  INTEGER
	ACCESS  read-only
	STATUS  mandatory
	DESCRIPTION
		"&<caiNtOs.192>The total number of monitored memory attributes with a Critical state."
			::= { ntStatusSummary 16 }

ntProcessorWarnStatus OBJECT-TYPE
	SYNTAX  INTEGER
	ACCESS  read-only
	STATUS  mandatory
	DESCRIPTION
		"&<caiNtOs.193>The total number of processors with a Warning state."
			::= { ntStatusSummary 17 }

ntProcessorCriticalStatus OBJECT-TYPE
	SYNTAX  INTEGER
	ACCESS  read-only
	STATUS  mandatory
	DESCRIPTION
		"&<caiNtOs.194>The total number of processors with a Critical state."
			::= { ntStatusSummary 18 }

ntRegistryWarnStatus OBJECT-TYPE
	SYNTAX  INTEGER
	ACCESS  read-only
	STATUS  mandatory
	DESCRIPTION
		"&<caiNtOs.195>The total number of 'registry watches' with a Warning state."
			::= { ntStatusSummary 19 }

ntRegistryCriticalStatus OBJECT-TYPE
	SYNTAX  INTEGER
	ACCESS  read-only
	STATUS  mandatory
	DESCRIPTION
		"&<caiNtOs.196>The total number of 'registry watches' with a Critical state."
			::= { ntStatusSummary 20 }

ntEventLogWarnStatus OBJECT-TYPE
	SYNTAX  INTEGER
	ACCESS  read-only
	STATUS  mandatory
	DESCRIPTION
		"&<caiNtOs.197>The total number of 'event log watches' with a Warning state."
			::= { ntStatusSummary 21 }

ntEventLogCriticalStatus OBJECT-TYPE
	SYNTAX  INTEGER
	ACCESS  read-only
	STATUS  mandatory
	DESCRIPTION
		"&<caiNtOs.198>The total number of 'event log watches' with a Critical state."
			::= { ntStatusSummary 22 }

--
--	Filesystem Status Table
--

ntFilesystemStTable 	OBJECT-TYPE
	SYNTAX  SEQUENCE OF NtFilesystemStTableEntry
	ACCESS  not-accessible
	STATUS  mandatory
	DESCRIPTION
		"&<caiNtOs.199>List of information about monitored filesystems."
		::= { ntStatusGroup 3 }

ntFilesystemStTableEntry OBJECT-TYPE
        SYNTAX NtFilesystemStTableEntry
        ACCESS  not-accessible
        STATUS  mandatory
        DESCRIPTION
                "&<caiNtOs.200>A table entry containing information about a monitored filesystem."
	INDEX { ntStatusFSDriveLetter }
		::= { ntFilesystemStTable 2 }

NtFilesystemStTableEntry::=
        SEQUENCE {
		ntStatusFSDriveLetter	DisplayString,		
		ntStatusFSDriveLabel	DisplayString, 
		ntStatusFSDriveType 	DisplayString, 
		ntStatusFSDriveFormat 	DisplayString,
		ntStatusFSTotalCapacity INTEGER,
		ntStatusFSUtilization 	INTEGER,
		ntStatusFSFree 		INTEGER,
		ntStatusFSStatus 	INTEGER,
		ntStatusFSPcntWarn 	INTEGER,
		ntStatusFSPcntCritical 	INTEGER,
		ntStatusFSKByteWarn	INTEGER,
		ntStatusFSKByteCritical INTEGER,
		ntStatusFSAvgUtil 	INTEGER,
		ntStatusFSMinUtil 	INTEGER,
		ntStatusFSMaxUtil 	INTEGER,
		ntStatusFSUtilDelta 	INTEGER,
		ntStatusFSDeltaLevel 	INTEGER,
		ntStatusFSDeltaThreshold INTEGER,
		ntStatusFSDescription	DisplayString
		      }

ntStatusFSDriveLetter OBJECT-TYPE
	SYNTAX DisplayString
	ACCESS  read-only
	STATUS  mandatory
	DESCRIPTION
		"&<caiNtOs.201>The drive letter of the filesystem as recognised by the operating system."
			::= { ntFilesystemStTableEntry 2 }

ntStatusFSDriveLabel OBJECT-TYPE
	SYNTAX DisplayString
	ACCESS  read-only
	STATUS  mandatory
	DESCRIPTION
		"&<caiNtOs.202>The drive label of the filesystem."
			::= { ntFilesystemStTableEntry 3 }

ntStatusFSDriveType OBJECT-TYPE
	SYNTAX DisplayString
	ACCESS  read-only
	STATUS  mandatory
	DESCRIPTION
		"&<caiNtOs.203>Drive type as determined by the operating system (removeable, fixed, CDROM etc.)."
			::= { ntFilesystemStTableEntry 4 }

ntStatusFSDriveFormat OBJECT-TYPE
	SYNTAX DisplayString
	ACCESS  read-only
	STATUS  mandatory
	DESCRIPTION
		"&<caiNtOs.204>Format type as determined by the operating system (FAT, NTFS, CDFS etc)."
			::= { ntFilesystemStTableEntry 5 }

ntStatusFSTotalCapacity OBJECT-TYPE
	SYNTAX INTEGER
	ACCESS  read-only
	STATUS  mandatory
	DESCRIPTION
		"&<caiNtOs.205>Total Filesystem Capacity in Kbytes."
			::= { ntFilesystemStTableEntry 6 }

ntStatusFSUtilization OBJECT-TYPE
	SYNTAX INTEGER
	ACCESS  read-only
	STATUS  mandatory
	DESCRIPTION
		"&<caiNtOs.206>Current Utilization of the Filesystem in Kbytes."
			::= { ntFilesystemStTableEntry 7 }

ntStatusFSFree OBJECT-TYPE
	SYNTAX INTEGER
	ACCESS  read-only
	STATUS  mandatory
	DESCRIPTION
		"&<caiNtOs.207>Current Free Space on the Filesystem in Kbytes."
			::= { ntFilesystemStTableEntry 8 }

ntStatusFSStatus OBJECT-TYPE
	SYNTAX INTEGER {
		ok(1),
		warning(2),
		critical(3),
		down(4),
		unknown(5)
		}
	ACCESS  read-only
	STATUS  mandatory
	DESCRIPTION
		"&<caiNtOs.208>Current status of the filesystem."
			::= { ntFilesystemStTableEntry 9 }

ntStatusFSPcntWarn OBJECT-TYPE
	SYNTAX INTEGER
	ACCESS  read-write
	STATUS  mandatory
	DESCRIPTION
		"&<caiNtOs.209>Filesystem Utilization Warning Threshold defined in terms of percentage of total capacity.  
		This value must be less than, or equal to, the Critical threshold.  
		Changes to this value are automatically reflected in ntStatusKFSByteWarn."
			::= { ntFilesystemStTableEntry 10 }

ntStatusFSPcntCritical OBJECT-TYPE
	SYNTAX INTEGER
	ACCESS  read-write
	STATUS  mandatory
	DESCRIPTION
		"&<caiNtOs.210>Filesystem Utilization Critical Threshold defined in terms of percentage of total capacity.  
		This value must be greater than, or equal to, the Warning threshold.  
		Changes to this value are automatically reflected in ntStatusFSKByteCritical."
			::= { ntFilesystemStTableEntry 11 }

ntStatusFSKByteWarn OBJECT-TYPE
	SYNTAX INTEGER
	ACCESS  read-write
	STATUS  mandatory
	DESCRIPTION
		"&<caiNtOs.211>Filesystem Utilization Warning Threshold defined in terms of Kbytes utilized.  
		This value must be less than, or equal to, the Critical threshold.  
		Changes to this value are automatically reflected in ntStatusFSPcntWarn."
			::= { ntFilesystemStTableEntry 12 }

ntStatusFSKByteCritical OBJECT-TYPE
	SYNTAX INTEGER
	ACCESS  read-write
	STATUS  mandatory
	DESCRIPTION
		"&<caiNtOs.212>Filesystem Utilization Critical Threshold defined in terms of Kbytes utilized.  
		This value must be greater than, or equal to, the Warning threshold.  
		Changes to this value are automatically reflected in ntStatusFSPcntCritical."
			::= { ntFilesystemStTableEntry 13 }

ntStatusFSAvgUtil OBJECT-TYPE
	SYNTAX INTEGER
	ACCESS  read-only
	STATUS  mandatory
	DESCRIPTION
		"&<caiNtOs.213>Average filesystem utilization over the up-time of the agent, expressed in Kbytes."
			::= { ntFilesystemStTableEntry 14 }

ntStatusFSMinUtil OBJECT-TYPE
	SYNTAX INTEGER
	ACCESS  read-only
	STATUS  mandatory
	DESCRIPTION
		"&<caiNtOs.214>Minimum filesystem utilization over the up-time of the agent, expressed in Kbytes."
			::= { ntFilesystemStTableEntry 15 }

ntStatusFSMaxUtil OBJECT-TYPE
	SYNTAX INTEGER
	ACCESS  read-only
	STATUS  mandatory
	DESCRIPTION
		"&<caiNtOs.215>Maximum filesystem utilization over the up-time of the agent, expressed in Kbytes."
			::= { ntFilesystemStTableEntry 16 }

ntStatusFSUtilDelta OBJECT-TYPE
	SYNTAX INTEGER
	ACCESS  read-only
	STATUS  mandatory
	DESCRIPTION
		"&<caiNtOs.216>Difference in filesystem utilization between the current and previous polls, in 
		terms of percentage of total capacity."
			::= { ntFilesystemStTableEntry 17 }

ntStatusFSDeltaLevel OBJECT-TYPE
	SYNTAX INTEGER {
		do-not-monitor(1),
		warning(2),
		critical(3)
		}	
	ACCESS  read-write
	STATUS  mandatory
	DESCRIPTION
		"&<caiNtOs.217>Level of alert to be raised on delta monitoring."
			::= { ntFilesystemStTableEntry 18 }

ntStatusFSDeltaThreshold OBJECT-TYPE
	SYNTAX INTEGER
	ACCESS  read-write
	STATUS  mandatory
	DESCRIPTION
		"&<caiNtOs.218>Filesystem Delta Threshold defines, in terms of percentage of total filesystem capacity, 
		the delta value at which to raise an alert at the level defined in ntStatusFSDeltaLevel."
			::= { ntFilesystemStTableEntry 19 }

ntStatusFSDescription OBJECT-TYPE
	SYNTAX DisplayString
	ACCESS  read-write
	STATUS  mandatory
	DESCRIPTION
		"&<caiNtOs.219>Description of the filesystem to be amended by the user, primary use, manufacturer etc.."
			::= { ntFilesystemStTableEntry 20 }

--
--	File Status Table
--

ntFileStTable	OBJECT-TYPE
	SYNTAX  SEQUENCE OF NtFileStTableEntry
	ACCESS  not-accessible
	STATUS  mandatory
	DESCRIPTION
		"&<caiNtOs.220>List of information about monitored files."
			::= { ntStatusGroup 4 }

ntFileStTableEntry OBJECT-TYPE
        SYNTAX NtFileStTableEntry
        ACCESS  not-accessible
        STATUS  mandatory
        DESCRIPTION
                "&<caiNtOs.221>A table entry containing information about a monitored file."
	INDEX { ntStatusFileName }
			::= { ntFileStTable 2 }

NtFileStTableEntry::=
	SEQUENCE {
		ntStatusFileName	DisplayString,		
		ntStatusFileStatus	INTEGER, 
		ntStatusFileSize	INTEGER,
		ntStatusFileSizeStatus	INTEGER,
		ntStatusFileSizeWarning	INTEGER,
		ntStatusFileSizeCritical INTEGER,
		ntStatusFileTimestamp	DisplayString,
		ntStatusFileTimestampFlag	INTEGER,
		ntStatusFileTimestampStatus	INTEGER,
		ntStatusFileSizeChFlag	INTEGER,
		ntStatusFileSizeCh	INTEGER,
		ntStatusFileSizeChState	INTEGER,
		ntStatusFileSizeChBytes	INTEGER,
		ntStatusFileMinSize	INTEGER,
		ntStatusFileMaxSize	INTEGER,
		ntStatusFileAvgSize	INTEGER,
		ntStatusFileDescription	DisplayString,
		ntStatusFileSizeBase	INTEGER
	      }


ntStatusFileName OBJECT-TYPE
	SYNTAX DisplayString
	ACCESS  read-only
	STATUS  mandatory
	DESCRIPTION
		"&<caiNtOs.222>The complete pathname of the file on the managed system."
			::= { ntFileStTableEntry 2 }

ntStatusFileStatus OBJECT-TYPE
	SYNTAX INTEGER {
		ok(1),
		warning(2),
		critical(3),
		unknown(4)
		}
	ACCESS  read-only
	STATUS  mandatory
	DESCRIPTION
		"&<caiNtOs.223>Current status of the file, which is an aggregation of the file size status, 
		file size change and timestamp status."
			::= { ntFileStTableEntry 3 }

ntStatusFileSize OBJECT-TYPE
	SYNTAX INTEGER
	ACCESS  read-only
	STATUS  mandatory
	DESCRIPTION
		"&<caiNtOs.224>Current file size in bytes."
			::= { ntFileStTableEntry 4 }

ntStatusFileSizeStatus OBJECT-TYPE
	SYNTAX INTEGER {
		ok(1),
		warning(2),
		critical(3)
		}
	ACCESS  read-only
	STATUS  mandatory
	DESCRIPTION
		"&<caiNtOs.225>File Size Status, determined according to the File Size thresholds."
			::= { ntFileStTableEntry 5 }

ntStatusFileSizeWarning OBJECT-TYPE
	SYNTAX INTEGER
	ACCESS  read-write
	STATUS  mandatory
	DESCRIPTION
		"&<caiNtOs.226>File Size Warning threshold defined as a percentage of ntStatusFileSizeBase, this value should be less 
		than, or equal to, the Critical Threshold."
			::= { ntFileStTableEntry 6 }

ntStatusFileSizeCritical OBJECT-TYPE
	SYNTAX INTEGER
	ACCESS  read-write
	STATUS  mandatory
	DESCRIPTION
		"&<caiNtOs.227>File Size Critical threshold defined as a of percentage of ntStatusFileSizeBase, this value should be greater 
		than, or equal to, the Warning Threshold."
			::= { ntFileStTableEntry 7 }

ntStatusFileTimestamp OBJECT-TYPE
	SYNTAX DisplayString
	ACCESS  read-only
	STATUS  mandatory
	DESCRIPTION
		"&<caiNtOs.228>File timestamp."
			::= { ntFileStTableEntry 8 }

ntStatusFileTimestampFlag OBJECT-TYPE
	SYNTAX INTEGER {
		do-not-monitor(1),
		warning(2),
		critical(3)
		}
	ACCESS  read-write
	STATUS  mandatory
	DESCRIPTION
		"&<caiNtOs.229>Monitoring configuration for timestamp monitoring"
			::= { ntFileStTableEntry 9 }

ntStatusFileTimestampStatus OBJECT-TYPE
	SYNTAX INTEGER {
		ok(1),
		warning(2),
		critical(3),
		not-monitored(4),
		reset(5)
		}
	ACCESS  read-write
	STATUS  mandatory
	DESCRIPTION
		"&<caiNtOs.230>Timestamp Monitoring status - set to 'Reset' to reset timestamp"
			::= { ntFileStTableEntry 10 }


ntStatusFileSizeChFlag OBJECT-TYPE
	SYNTAX INTEGER {
		do-not-monitor(1),
		warning(2),
		critical(3)
		}
	ACCESS  read-write
	STATUS  mandatory
	DESCRIPTION
		"&<caiNtOs.231>Flag indicating whether the file should be monitored for size change."
			::= { ntFileStTableEntry 11 }

ntStatusFileSizeCh OBJECT-TYPE
	SYNTAX INTEGER
	ACCESS  read-only
	STATUS  mandatory
	DESCRIPTION
		"&<caiNtOs.232>File size change calculated over number of periods defined in ntFileConfig.  
		If this has not been possible to calculate yet -1 is stored."
			::= { ntFileStTableEntry 12 }

ntStatusFileSizeChState OBJECT-TYPE
	SYNTAX INTEGER {
		ok(1),
		warning(2),
		critical(3),
		not-monitored(4),
		reset(5)
		}
	ACCESS  read-write
	STATUS  mandatory
	DESCRIPTION
		"&<caiNtOs.233>File Size Change status according to the File Size Change threshold values."
			::= { ntFileStTableEntry 13 }

ntStatusFileSizeChBytes OBJECT-TYPE
	SYNTAX INTEGER
	ACCESS  read-write
	STATUS  mandatory
	DESCRIPTION
		"&<caiNtOs.234>Number of bytes of size growth."
			::= { ntFileStTableEntry 14 }

ntStatusFileMinSize OBJECT-TYPE
	SYNTAX INTEGER
	ACCESS  read-only
	STATUS  mandatory
	DESCRIPTION
		"&<caiNtOs.235>Minimum file size recorded over the up-time of the agent, in bytes."
			::= { ntFileStTableEntry 15 }

ntStatusFileMaxSize OBJECT-TYPE
	SYNTAX INTEGER
	ACCESS  read-only
	STATUS  mandatory
	DESCRIPTION
		"&<caiNtOs.236>Maximum file size recorded over the up-time of the agent, in bytes."
			::= { ntFileStTableEntry 16 }

ntStatusFileAvgSize OBJECT-TYPE
	SYNTAX INTEGER
	ACCESS  read-only
	STATUS  mandatory
	DESCRIPTION
		"&<caiNtOs.237>Average file size recorded over the up-time of the agent, in bytes."
			::= { ntFileStTableEntry 17 }

ntStatusFileDescription OBJECT-TYPE
	SYNTAX DisplayString
	ACCESS  read-write
	STATUS  mandatory
	DESCRIPTION
		"&<caiNtOs.238>Description of the file, defined by the user."
			::= { ntFileStTableEntry 18 }

ntStatusFileSizeBase OBJECT-TYPE
	SYNTAX INTEGER
	ACCESS  read-only
	STATUS  mandatory
	DESCRIPTION
		"&<caiNtOs.239>Original file size in bytes used as base size in calculations of File Size thresholds."
			::= { ntFileStTableEntry 19 }

--
--	Process Status Table
--

ntProcessStTable	OBJECT-TYPE
	SYNTAX  SEQUENCE OF NtProcessStTableEntry
	ACCESS  not-accessible
	STATUS  mandatory
	DESCRIPTION
		"&<caiNtOs.240>List of information about monitored processes."
			::= { ntStatusGroup 5 }

ntProcessStTableEntry OBJECT-TYPE
	SYNTAX NtProcessStTableEntry
        ACCESS  not-accessible
        STATUS  mandatory
        DESCRIPTION
        	"&<caiNtOs.241>A table entry containing information about a monitored process."
	INDEX { ntStatusProcName }
			::= { ntProcessStTable 2 }

NtProcessStTableEntry::=
	SEQUENCE {
		ntStatusProcName	DisplayString,		
		ntStatusProcStatus	INTEGER, 
		ntStatusProcAlertLevel	INTEGER,
		ntStatusProcExist	INTEGER,
		ntStatusProcInst 	INTEGER,
		ntStatusProcInstMonitor INTEGER,
		ntStatusProcInstWarning INTEGER,
		ntStatusProcInstCritical INTEGER,
		ntStatusProcThd 	INTEGER,
		ntStatusProcThdMonitor 	INTEGER,
		ntStatusProcThdRef 	INTEGER,
		ntStatusProcThdMax 	INTEGER,
		ntStatusProcThdMin 	INTEGER,
		ntStatusProcDescription DisplayString
	      }

ntStatusProcName OBJECT-TYPE
	SYNTAX DisplayString
	ACCESS  read-only
	STATUS  mandatory
	DESCRIPTION
		"&<caiNtOs.242>The name of the process, as returned from the NT Registry."
			::= { ntProcessStTableEntry 2 }

ntStatusProcStatus OBJECT-TYPE
	SYNTAX INTEGER {
		ok(1),
		warning(2),
		critical(3)
		}
	ACCESS  read-only
	STATUS  mandatory
	DESCRIPTION
		"&<caiNtOs.243>Current status of the process, which is an aggregation of the status of the 
		existance, thread and instance monitoring."
			::= { ntProcessStTableEntry 3 }

ntStatusProcAlertLevel OBJECT-TYPE
	SYNTAX INTEGER {
		do-not-monitor(1),
		warning(2),
		critical(3)
		}
	ACCESS  read-write
	STATUS  mandatory
	DESCRIPTION
		"&<caiNtOs.244>Level of alert to be signalled for an existance check."
			::= { ntProcessStTableEntry 4 }


ntStatusProcExist OBJECT-TYPE
	SYNTAX  INTEGER {
		alert-if-exist(1),
		alert-if-not-exist(2)
		}
	ACCESS  read-write
	STATUS  mandatory
	DESCRIPTION
		"&<caiNtOs.245>Flag indicating whether, by default, an alert is raised if the process 
		exists or doesn't exist."
			::= { ntProcessStTableEntry 5 }

ntStatusProcInst OBJECT-TYPE
	SYNTAX INTEGER
	ACCESS  read-only
	STATUS  mandatory
	DESCRIPTION
		"&<caiNtOs.246>Number of instances of the process."
			::= { ntProcessStTableEntry 6 }


ntStatusProcInstMonitor OBJECT-TYPE
	SYNTAX INTEGER {
		true(1),
		false(2)
		}
	ACCESS  read-write
	STATUS  mandatory
	DESCRIPTION
		"&<caiNtOs.247>Flag indicating whether the process should be monitored for instance count."
			::= { ntProcessStTableEntry 7 }

ntStatusProcInstWarning OBJECT-TYPE
	SYNTAX INTEGER
	ACCESS  read-write
	STATUS  mandatory
	DESCRIPTION
		"&<caiNtOs.248>Instance Warning threshold, in terms of a count of instances.  This should be less 
		than, or equal to, the Critical Threshold."
			::= { ntProcessStTableEntry 8}

ntStatusProcInstCritical OBJECT-TYPE
	SYNTAX INTEGER
	ACCESS  read-write
	STATUS  mandatory
	DESCRIPTION
		"&<caiNtOs.249>Instance Critical threshold, in terms of a count of instances.  This should be 
		greater than, or equal to, the Warning Threshold."
			::= { ntProcessStTableEntry 9}

ntStatusProcThd OBJECT-TYPE
	SYNTAX INTEGER 
	ACCESS  read-only
	STATUS  mandatory
	DESCRIPTION
		"&<caiNtOs.250>Current thread count, for more than one instance, the maximum is shown."
			::= { ntProcessStTableEntry 10}

ntStatusProcThdMonitor OBJECT-TYPE
	SYNTAX INTEGER {
		do-not-monitor(1),
		above(2),
		below(3)
		}
	ACCESS  read-write
	STATUS  mandatory
	DESCRIPTION
		"&<caiNtOs.251>Flag indicating whether the process is monitored for thread count, and if so 
		whether to alert on exceeding or dropping below the reference value."
			::= { ntProcessStTableEntry 11}

ntStatusProcThdRef OBJECT-TYPE
	SYNTAX INTEGER
	ACCESS  read-write
	STATUS  mandatory
	DESCRIPTION
		"&<caiNtOs.252>Reference number of threads to measure state against."
			::= { ntProcessStTableEntry 12}

ntStatusProcThdMax OBJECT-TYPE
	SYNTAX INTEGER
	ACCESS  read-only
	STATUS  mandatory
	DESCRIPTION
		"&<caiNtOs.253>Current maximum number of threads of any instance of the process."
		::= { ntProcessStTableEntry 13}

ntStatusProcThdMin OBJECT-TYPE
	SYNTAX INTEGER
	ACCESS  read-only
	STATUS  mandatory
	DESCRIPTION
		"&<caiNtOs.254>Current minimum number of threads of any instance of the process."
			::= { ntProcessStTableEntry 14}

ntStatusProcDescription OBJECT-TYPE
	SYNTAX DisplayString
	ACCESS  read-write
	STATUS  mandatory
	DESCRIPTION
		"&<caiNtOs.255>Description of the process, supplied by the user."
			::= { ntProcessStTableEntry 17}


--
--	Service Status Table
--

ntServiceStTable	OBJECT-TYPE
	SYNTAX  SEQUENCE OF NtServiceStTableEntry
	ACCESS  not-accessible
	STATUS  mandatory
	DESCRIPTION
		"&<caiNtOs.256>List of information about monitored services."
			::= { ntStatusGroup 6 }

ntServiceStTableEntry OBJECT-TYPE
        SYNTAX NtServiceStTableEntry
        ACCESS  not-accessible
        STATUS  mandatory
        DESCRIPTION
        	"&<caiNtOs.257>A table entry containing information about a monitored service."
	INDEX { ntStatusServName }
			::= { ntServiceStTable 2 }

NtServiceStTableEntry::=
        SEQUENCE {
		ntStatusServName	DisplayString,		
		ntStatusServDescription	DisplayString, 
		ntStatusServState	INTEGER,
		ntStatusServStatus 	INTEGER,
		ntStatusServAlertOn	INTEGER
	      }

ntStatusServName OBJECT-TYPE
	SYNTAX DisplayString
	ACCESS  read-only
	STATUS  mandatory
	DESCRIPTION
		"&<caiNtOs.258>The shortname of the service, as defined to the NT Service Manager."
			::= { ntServiceStTableEntry 2 }

ntStatusServDescription OBJECT-TYPE
	SYNTAX DisplayString
	ACCESS  read-only
	STATUS  mandatory
	DESCRIPTION
		"&<caiNtOs.259>The description of the service, as defined to the NT Service Manager."
			::= { ntServiceStTableEntry 3 }

ntStatusServState OBJECT-TYPE
	SYNTAX INTEGER {
		stopped(1),
		start-pending(2),
		stop-pending(3),
		running(4),
		continue-pending(5),
		pause-pending(6),
		paused(7),
		unknown(8)
		}
	ACCESS  read-only
	STATUS  mandatory
	DESCRIPTION
		"&<caiNtOs.260>Operational state of the service returned by the NT Service Manager."
			::= { ntServiceStTableEntry 4 }

ntStatusServStatus OBJECT-TYPE
	SYNTAX INTEGER {
		ok(1),
		warning(2),
		critical(3),
		down(4),
		unknown(5)
		}
	ACCESS  read-only
	STATUS  mandatory
	DESCRIPTION
		"&<caiNtOs.261>Status of the service according to monitoring rules."
			::= { ntServiceStTableEntry 5 }

ntStatusServAlertOn OBJECT-TYPE
	SYNTAX INTEGER {
		do-not-monitor(1),
		active(2),
		inactive(3)
		}
	ACCESS  read-write
	STATUS  mandatory
	DESCRIPTION
		"&<caiNtOs.262>Flag indicating when to raise an event."
			::= { ntServiceStTableEntry 6 }

--
--	Printer Status Table
--

--	Naming conventions are different for this table
ntPrinterStTable OBJECT-TYPE
	SYNTAX  SEQUENCE OF NtStatusPrintTableEntry
	ACCESS  not-accessible
	STATUS  mandatory
	DESCRIPTION
		"&<caiNtOs.263>List of information about monitored printers."
			::= { ntStatusGroup 7 }

ntStatusPrintTableEntry OBJECT-TYPE
	SYNTAX NtStatusPrintTableEntry
        ACCESS  not-accessible
        STATUS  mandatory
        DESCRIPTION
        	"&<caiNtOs.264>A table entry containing information about a monitored printer."
	INDEX { ntStatusPrintName }
			::= { ntPrinterStTable 2 }

NtStatusPrintTableEntry::=
	SEQUENCE {
		ntStatusPrintName	DisplayString,		
		ntStatusPrintStatus	INTEGER,
		ntStatusPrintEventMonitor INTEGER,
 		ntStatusPrintEventStatus INTEGER,
		ntStatusPrintEventDescription DisplayString,
		ntStatusPrintQFlag	INTEGER,
		ntStatusPrintQueue	INTEGER,
		ntStatusPrintQStatus	INTEGER,
		ntStatusPrintQWarning	INTEGER,
		ntStatusPrintQCritical	INTEGER,
		ntStatusPrintQMax	INTEGER,
		ntStatusPrintDescription DisplayString
		}

ntStatusPrintName OBJECT-TYPE
	SYNTAX DisplayString
	ACCESS  read-only
	STATUS  mandatory
	DESCRIPTION
		"&<caiNtOs.265>The printer name as known to the operating system."
			::= { ntStatusPrintTableEntry 2 }

ntStatusPrintStatus OBJECT-TYPE
	SYNTAX INTEGER {
		ok(1),
		warning(2),
		critical(3)
		}
	ACCESS  read-only
	STATUS  mandatory
	DESCRIPTION
		"&<caiNtOs.266>Current status of the printer, which is an aggregation of the status of the 
		job queue monitoring and event monitoring."
			::= { ntStatusPrintTableEntry 3 }

ntStatusPrintEventMonitor OBJECT-TYPE
	SYNTAX INTEGER {
 	       do-not-monitor(1),
   	       warning(2),
   	       critical(3)
   	       }    
	ACCESS  read-write
	STATUS  mandatory
	DESCRIPTION
		"&<caiNtOs.267>Flag indicating whether alerts should be raised on printer events signalled 
		by Windows NT, and if so, the level of alert to raise."
			::= { ntStatusPrintTableEntry 4 }

ntStatusPrintEventStatus OBJECT-TYPE
	SYNTAX INTEGER {
		ok(1),
		warning(2),
		critical(3)
		}
	ACCESS  read-only
	STATUS  mandatory
	DESCRIPTION
		"&<caiNtOs.268>Current event status."
			::= { ntStatusPrintTableEntry 5 }

ntStatusPrintEventDescription OBJECT-TYPE
	SYNTAX DisplayString
	ACCESS  read-only
	STATUS  mandatory
	DESCRIPTION
		"&<caiNtOs.269>Textual description of any flagged events on the printer."
			::= { ntStatusPrintTableEntry 6 }

ntStatusPrintQFlag OBJECT-TYPE
	SYNTAX INTEGER {
		true(1),
		false(2)
		}
	ACCESS  read-write
	STATUS  mandatory
	DESCRIPTION
		"&<caiNtOs.270>Flag indicating whether the printer's job queue should be monitored."
			::= { ntStatusPrintTableEntry 7 }

ntStatusPrintQueue OBJECT-TYPE
	SYNTAX INTEGER
	ACCESS  read-only
	STATUS  mandatory
	DESCRIPTION
		"&<caiNtOs.271>Number of jobs currently on the printer's queue."
			::= { ntStatusPrintTableEntry 8 }

ntStatusPrintQStatus OBJECT-TYPE
	SYNTAX INTEGER {
		ok(1),
		warning(2),
		critical(3)
		}
	ACCESS  read-only
	STATUS  mandatory
	DESCRIPTION
		"&<caiNtOs.272>Current event status."
			::= { ntStatusPrintTableEntry 9 }


ntStatusPrintQWarning OBJECT-TYPE
	SYNTAX INTEGER
	ACCESS  read-write
	STATUS  mandatory
	DESCRIPTION
		"&<caiNtOs.273>Warning threshold defined in terms of the number of jobs in the queue."
			::= { ntStatusPrintTableEntry 10 }

ntStatusPrintQCritical OBJECT-TYPE
	SYNTAX INTEGER
	ACCESS  read-write
	STATUS  mandatory
	DESCRIPTION
		"&<caiNtOs.274>Critical threshold defined in terms of the number of jobs in the queue."
			::= { ntStatusPrintTableEntry 11 }

ntStatusPrintQMax OBJECT-TYPE
	SYNTAX INTEGER
	ACCESS  read-only
	STATUS  mandatory
	DESCRIPTION
		"&<caiNtOs.275>Maximum number of jobs recorded on the queue since agent up-time."
			::= { ntStatusPrintTableEntry 12 }

ntStatusPrintDescription OBJECT-TYPE
	SYNTAX DisplayString
	ACCESS  read-write
	STATUS  mandatory
	DESCRIPTION
		"&<caiNtOs.276>Description of the Printer, defaulting to that described to NT"
			::= { ntStatusPrintTableEntry 13 }


--
--	Memory Status
--

ntMemorySt OBJECT IDENTIFIER
--	DESCRIPTION
--		"Details of monitored memory attributes."
		::= { ntStatusGroup 8 }

ntStatusMemLoad OBJECT-TYPE
	SYNTAX  INTEGER
	ACCESS  read-only
	STATUS  mandatory
	DESCRIPTION
		"&<caiNtOs.277>Current Memory Load, defined as a percentage."
			::= { ntMemorySt 2 }

ntStatusMemLoadStatus OBJECT-TYPE
	SYNTAX INTEGER {
		ok(1),
		warning(2),
		critical(3)
		}
	ACCESS  read-only
	STATUS  mandatory
	DESCRIPTION
		"&<caiNtOs.278>Current Memory Load status, as determined by the thresholds defined in ntMemoryConfig."
			::= { ntMemorySt 3 }

ntStatusMemLoadAvg OBJECT-TYPE
	SYNTAX  INTEGER
	ACCESS  read-only
	STATUS  mandatory
	DESCRIPTION
		"&<caiNtOs.279>Average Memory Load recorded over the agent up-time, as a percentage."
			::= { ntMemorySt 4 }

ntStatusMemLoadMax OBJECT-TYPE
	SYNTAX  INTEGER
	ACCESS  read-only
	STATUS  mandatory
	DESCRIPTION
		"&<caiNtOs.280>Maximum Memory Load recorded over the agent up-time, as a percentage."
			::= { ntMemorySt 5 }

ntStatusMemLoadMin OBJECT-TYPE
	SYNTAX  INTEGER
	ACCESS  read-only
	STATUS  mandatory
	DESCRIPTION
		"&<caiNtOs.281>Minimum Memory Load recorded over the agent up-time, as a percentage."
			::= { ntMemorySt 6 }

ntStatusMemPhysTotal OBJECT-TYPE
	SYNTAX  INTEGER
	ACCESS  read-only
	STATUS  mandatory
	DESCRIPTION
		"&<caiNtOs.282>Total Physical Memory available on the system, expressed in bytes."
			::= { ntMemorySt 7 }

ntStatusMemPhys OBJECT-TYPE
	SYNTAX  INTEGER
	ACCESS  read-only
	STATUS  mandatory
	DESCRIPTION
		"&<caiNtOs.283>Current Physical Memory available, expressed in bytes."
			::= { ntMemorySt 8 }

ntStatusMemPhysStatus OBJECT-TYPE
	SYNTAX INTEGER {
		ok(1),
		warning(2),
		critical(3)
		}
	ACCESS  read-only
	STATUS  mandatory
	DESCRIPTION
		"&<caiNtOs.284>Current Physical Memory status, as determined by the thresholds defined in ntMemoryConfig."
			::= { ntMemorySt 9 }

ntStatusMemPhysAvg OBJECT-TYPE
	SYNTAX  INTEGER
	ACCESS  read-only
	STATUS  mandatory
	DESCRIPTION
		"&<caiNtOs.285>Average available Physical Memory recorded over the agent up-time, expressed in bytes."
			::= { ntMemorySt 10 }

ntStatusMemPhysMax OBJECT-TYPE
	SYNTAX  INTEGER
	ACCESS  read-only
	STATUS  mandatory
	DESCRIPTION
		"&<caiNtOs.286>Maximum available Physical Memory recorded over the agent up-time, expressed in bytes."
			::= { ntMemorySt 11 }

ntStatusMemPhysMin OBJECT-TYPE
	SYNTAX  INTEGER
	ACCESS  read-only
	STATUS  mandatory
	DESCRIPTION
		"&<caiNtOs.287>Minimum available Physical Memory recorded over the agent up-time, expressed in bytes."
			::= { ntMemorySt 12 }

ntStatusMemSwapTotal OBJECT-TYPE
	SYNTAX INTEGER
	ACCESS	read-only
	STATUS	mandatory
	DESCRIPTION
		"&<caiNtOs.288>Total Swapspace (Paging Memory) available on the system, expressed in bytes."
			::= { ntMemorySt 13 }

ntStatusMemSwap OBJECT-TYPE
	SYNTAX  INTEGER
	ACCESS  read-only
	STATUS  mandatory
	DESCRIPTION
		"&<caiNtOs.289>Current Swapspace (Paging Memory) available over the agent up-time, expressed in bytes."
			::= { ntMemorySt 14 }

ntStatusMemSwapStatus OBJECT-TYPE
	SYNTAX INTEGER {
		ok(1),
		warning(2),
		critical(3)
		}
	ACCESS  read-only
	STATUS  mandatory
	DESCRIPTION
		"&<caiNtOs.290>Current Swapspace (Paging Memory) status, as determined by the thresholds defined 
		in ntMemoryConfig."
			::= { ntMemorySt 15 }

ntStatusMemSwapAvg OBJECT-TYPE
	SYNTAX  INTEGER
	ACCESS  read-only
	STATUS  mandatory
	DESCRIPTION
		"&<caiNtOs.291>Average available Swapspace (Paging Memory) recorded over the agent up-time, 
		expressed in bytes."
			::= { ntMemorySt 16 }

ntStatusMemSwapMax OBJECT-TYPE
	SYNTAX  INTEGER
	ACCESS  read-only
	STATUS  mandatory
	DESCRIPTION
		"&<caiNtOs.292>Maximum available Swapspace (Paging Memory) recorded over the agent up-time, 
		expressed in bytes."
			::= { ntMemorySt 17 }

ntStatusMemSwapMin OBJECT-TYPE
	SYNTAX  INTEGER
	ACCESS  read-only
	STATUS  mandatory
	DESCRIPTION
		"&<caiNtOs.293>Minimum available Swapspace (Paging Memory) recorded over the agent up-time, 
		expressed in bytes."
			::= { ntMemorySt 18 }


--
--	Processor Status Table
--

ntProcessorStTable OBJECT-TYPE
	SYNTAX  SEQUENCE OF NtProcessorStTableEntry
	ACCESS  not-accessible
	STATUS  mandatory
	DESCRIPTION
		"&<caiNtOs.294>List of information about processors."
			::= { ntStatusGroup 9 }

ntProcessorStTableEntry OBJECT-TYPE
    SYNTAX NtProcessorStTableEntry
    ACCESS  not-accessible
    STATUS  mandatory
    DESCRIPTION
    	"&<caiNtOs.295>A table entry containing information about the status of a processor."
	INDEX { ntStatusCPUNumber }
			::= { ntProcessorStTable 2 }

NtProcessorStTableEntry ::=
        SEQUENCE {
		ntStatusCPUNumber	DisplayString, 
		ntStatusCPUStatus	INTEGER,
		ntStatusCPUTotal	INTEGER,
		ntStatusCPUWarning	INTEGER,
		ntStatusCPUCritical	INTEGER,
		ntStatusCPUCount	INTEGER,
		ntStatusCPUAvg		INTEGER,
		ntStatusCPUMax		INTEGER,
		ntStatusCPUMin		INTEGER,
		ntStatusCPUDelta	INTEGER,
		ntStatusCPUDescription	DisplayString
		}

ntStatusCPUNumber OBJECT-TYPE
	SYNTAX DisplayString
	ACCESS  read-only
	STATUS  mandatory
	DESCRIPTION
		"&<caiNtOs.296>Processor identification number."
			::= { ntProcessorStTableEntry 2 }

ntStatusCPUStatus OBJECT-TYPE
	SYNTAX INTEGER {
		ok(1),
		warning(2),
		critical(3)
		}
	ACCESS  read-only
	STATUS  mandatory
	DESCRIPTION
		"&<caiNtOs.297>Status of of processor, determined by the thresholds."
			::= { ntProcessorStTableEntry  3 }

ntStatusCPUTotal OBJECT-TYPE
	SYNTAX INTEGER
	ACCESS  read-only
	STATUS  mandatory
	DESCRIPTION
		"&<caiNtOs.298>Current %Total utilization on the processor."
			::= { ntProcessorStTableEntry  4 }

ntStatusCPUWarning OBJECT-TYPE
	SYNTAX INTEGER
	ACCESS  read-write
	STATUS  mandatory
	DESCRIPTION
		"&<caiNtOs.299>Default %Total utilization Warning threshold level."
			::= { ntProcessorStTableEntry  5 }

ntStatusCPUCritical OBJECT-TYPE
	SYNTAX INTEGER
	ACCESS  read-write
	STATUS  mandatory
	DESCRIPTION
		"&<caiNtOs.300>Default %utilization Critical threshold level."
			::= { ntProcessorStTableEntry  6 }

ntStatusCPUCount OBJECT-TYPE
	SYNTAX INTEGER
	ACCESS  read-write
	STATUS  mandatory
	DESCRIPTION
		"&<caiNtOs.301>The number of successive polling periods over which %Total CPU must cross a 
		threshold before a status change is signalled."
			::= { ntProcessorStTableEntry  7 }

ntStatusCPUAvg OBJECT-TYPE
	SYNTAX INTEGER
	ACCESS  read-only
	STATUS  mandatory
	DESCRIPTION
		"&<caiNtOs.302>Average %Total utilization calculated since the agent was started."
			::= { ntProcessorStTableEntry  8 }

ntStatusCPUMax OBJECT-TYPE
	SYNTAX INTEGER
	ACCESS  read-only
	STATUS  mandatory
	DESCRIPTION
		"&<caiNtOs.303>%Total utilization 'high water mark' over the agent up-time."
			::= { ntProcessorStTableEntry  9 }

ntStatusCPUMin OBJECT-TYPE
	SYNTAX INTEGER
	ACCESS  read-only
	STATUS  mandatory
	DESCRIPTION
		"&<caiNtOs.304>Minimum %Total utilization over the agent up-time."
			::= { ntProcessorStTableEntry  10 }

ntStatusCPUDelta OBJECT-TYPE
	SYNTAX INTEGER
	ACCESS  read-only
	STATUS  mandatory
	DESCRIPTION
		"&<caiNtOs.305>The difference of %Total utilization between this and the last poll."
			::= { ntProcessorStTableEntry  11 }

ntStatusCPUDescription OBJECT-TYPE
	SYNTAX DisplayString
	ACCESS  read-write
	STATUS  mandatory
	DESCRIPTION
		"&<caiNtOs.306>Description of the Processor."
			::= { ntProcessorStTableEntry 12 }


--
--	Registry Status Table
--

ntRegistryStTable OBJECT-TYPE
	SYNTAX  SEQUENCE OF NtRegistryStTableEntry
	ACCESS  not-accessible
	STATUS  mandatory
	DESCRIPTION
		"&<caiNtOs.307>List of information about the status of configured Registry Leaf monitors."
			::= { ntStatusGroup 10 }

ntRegistryStTableEntry OBJECT-TYPE
	SYNTAX NtRegistryStTableEntry
	ACCESS  not-accessible
	STATUS  mandatory
	DESCRIPTION
		"&<caiNtOs.308>A table entry containing information about the status of a configured Registry Leaf monitor."
	INDEX { ntStatusRegHandle, ntStatusRegKey, ntStatusRegLeaf }
			::= { ntRegistryStTable 2 }

NtRegistryStTableEntry::=
	SEQUENCE {
		ntStatusRegHandle	INTEGER,
		ntStatusRegKey		DisplayString,
		ntStatusRegLeaf		DisplayString,
		ntStatusRegDataType 	INTEGER, 
		ntStatusRegValue 	DisplayString,
		ntStatusRegPrevValue 	DisplayString,
		ntStatusRegStatus 	INTEGER,
		ntStatusRegAvgTicks	INTEGER,
		ntStatusRegAvg 		INTEGER,
		ntStatusRegMax 		INTEGER,
		ntStatusRegMin 		INTEGER,
		ntStatusRegMonitorLevel	INTEGER,
		ntRegWarning		INTEGER,
		ntRegCritical 		INTEGER
		}

ntStatusRegHandle OBJECT-TYPE
	SYNTAX INTEGER {
		hkey-local-machine(1),
		hkey-current-user(2),
		hkey-users(3),
		hkey-classes-root(4)
		}
	ACCESS  read-only
	STATUS  mandatory
	DESCRIPTION
		"&<caiNtOs.309>Handle for the leaf."
			::= { ntRegistryStTableEntry 1 }

ntStatusRegKey OBJECT-TYPE
	SYNTAX DisplayString
	ACCESS  read-only
	STATUS  mandatory
	DESCRIPTION
		"&<caiNtOs.310>leaf location in the registry."
			::= { ntRegistryStTableEntry 2 }

ntStatusRegLeaf OBJECT-TYPE
	SYNTAX DisplayString
	ACCESS  read-only
	STATUS  mandatory
	DESCRIPTION
		"&<caiNtOs.311>The leaf itself."
			::= { ntRegistryStTableEntry 3 }

ntStatusRegDataType OBJECT-TYPE
	SYNTAX INTEGER {
		integer(1),
		string(2)
		}
	ACCESS  read-only
	STATUS  mandatory
	DESCRIPTION
		"&<caiNtOs.312>Type of data contained at the location."
			::= { ntRegistryStTableEntry 4 }

ntStatusRegValue OBJECT-TYPE
	SYNTAX DisplayString
	ACCESS  read-only
	STATUS  mandatory
	DESCRIPTION
		"&<caiNtOs.313>Value stored in the Registry."
			::= { ntRegistryStTableEntry 5 }

ntStatusRegPrevValue OBJECT-TYPE
	SYNTAX DisplayString
	ACCESS  read-only
	STATUS  mandatory
	DESCRIPTION
		"&<caiNtOs.314>Previous value stored at the location."
			::= { ntRegistryStTableEntry 6 }

ntStatusRegStatus OBJECT-TYPE
	SYNTAX INTEGER {
		ok(1),
		warning(2),
		critical(3),
		reset(4)
		}
	ACCESS  read-write
	STATUS  mandatory
	DESCRIPTION
		"&<caiNtOs.315>Registry watch status."
			::= { ntRegistryStTableEntry 7 }

ntStatusRegAvgTicks OBJECT-TYPE
	SYNTAX INTEGER
	ACCESS  read-only
	STATUS  optional
	DESCRIPTION
		"&<caiNtOs.316>(For integer values) Poll count used in the calculation of the average value."
			::= { ntRegistryStTableEntry 8 }

ntStatusRegAvg OBJECT-TYPE
	SYNTAX INTEGER
	ACCESS  read-only
	STATUS  optional
	DESCRIPTION
		"&<caiNtOs.317>(For integer values) Average value recorded at the location."
			::= { ntRegistryStTableEntry 9 }

ntStatusRegMax OBJECT-TYPE
	SYNTAX INTEGER
	ACCESS  read-only
	STATUS  optional
	DESCRIPTION
		"&<caiNtOs.318>(For integer values) Maximum value recorded at the location."
			::= { ntRegistryStTableEntry 10}

ntStatusRegMin OBJECT-TYPE
	SYNTAX INTEGER
	ACCESS  read-only
	STATUS  optional
	DESCRIPTION
		"&<caiNtOs.319>(For integer values) Minimum value recorded at the location. If this is 
		prefixed with a '-' then the threshold is set if the value at the leaf drops 
		below ntStatusRegMax."
			::= { ntRegistryStTableEntry 11 }

ntStatusRegMonitorLevel OBJECT-TYPE
	SYNTAX INTEGER {
		do-not-monitor(1),
		change(2),
		thresholds(3)
		}
	ACCESS  read-write
	STATUS  mandatory
	DESCRIPTION
		"&<caiNtOs.320>Defines the type of value monitoring to be performed.  For leaves of string 
		type value of 3 is ignored."
			::= { ntRegistryStTableEntry 12 }

ntStatusRegWarning OBJECT-TYPE
	SYNTAX INTEGER
	ACCESS  read-write
	STATUS mandatory
	DESCRIPTION
		"&<caiNtOs.321>warning threshold for integer type leaves."
			::= { ntRegistryStTableEntry 13 }

ntStatusRegCritical OBJECT-TYPE
	SYNTAX INTEGER
	ACCESS  read-write
	STATUS  mandatory
	DESCRIPTION
		"&<caiNtOs.322>Critical threshold for integer type leaves."
			::= { ntRegistryStTableEntry 14 }

--
--	Event Log Status Table
--

ntEventLogStTable OBJECT-TYPE
	SYNTAX  SEQUENCE OF NtEventLogStTableEntry
	ACCESS  not-accessible
	STATUS  mandatory
	DESCRIPTION
		"&<caiNtOs.323>List of information about the status of Event Log Watchers, the attributes 
		defining a logical AND on matching."
			::= { ntStatusGroup 11 }

ntEventLogStTableEntry OBJECT-TYPE
	SYNTAX NtEventLogStTableEntry
        ACCESS  not-accessible
        STATUS  mandatory
        DESCRIPTION
		"&<caiNtOs.324>A table entry containing information about the status of an Event Log Watcher, 
		the attributes defining a logical AND on matching."
		::= { ntEventLogStTable 2 }


NtEventLogStTableEntry::=
	SEQUENCE {
		ntStatusLogLogs		DisplayString,
		ntStatusLogSeverity	DisplayString,
		ntStatusLogSource	DisplayString,
		ntStatusLogEventID	DisplayString,
		ntStatusLogUser		DisplayString,
		ntStatusLogComputer	DisplayString,
		ntStatusLogStatus	INTEGER,
		ntStatusLogAlertOn	INTEGER,
		ntStatusLogStartTime	INTEGER,
		ntStatusLogStartTimeInText  DisplayString,
		ntStatusLogAppLogMatches INTEGER,
		ntStatusLogAppLogLastMatch  DisplayString,
		ntStatusLogSecLogMatches INTEGER,
		ntStatusLogSecLogLastMatch  DisplayString,
		ntStatusLogSysLogMatches INTEGER,
		ntStatusLogSysLogLastMatch  DisplayString,
		ntStatusLogWatcherIndex	INTEGER,
		ntStatusLogDescription	DisplayString
		}

ntStatusLogLogs OBJECT-TYPE
	SYNTAX DisplayString
	ACCESS read-write
	STATUS mandatory
	DESCRIPTION
		"&<caiNtOs.325>Event Log/s to watch.  May be a combination of these numbers; 
		( 1=Application, 2=Security, 3=System )."
			::= { ntEventLogStTableEntry 1 }

ntStatusLogSeverity OBJECT-TYPE
	SYNTAX DisplayString
	ACCESS  read-write
	STATUS  mandatory
	DESCRIPTION
		"&<caiNtOs.326>Severity level to record at, as defined by NT. May be a combination of 
		these numbers; ( 1 = Information, 2=warning,3=Error, 4=Success, 5=Failure Audit)."
			::= { ntEventLogStTableEntry 2 }

ntStatusLogSource OBJECT-TYPE
	SYNTAX DisplayString
	ACCESS  read-write
	STATUS  mandatory
	DESCRIPTION
		"&<caiNtOs.327>Source string to match against.  '*' wildcard is permitted."
			::= { ntEventLogStTableEntry 3 }

ntStatusLogEventID OBJECT-TYPE
	SYNTAX DisplayString
	ACCESS  read-write
	STATUS  mandatory
	DESCRIPTION
		"&<caiNtOs.328>Event ID to match against.  '*' wildcard is permitted."
			::= { ntEventLogStTableEntry 4 }

ntStatusLogUser OBJECT-TYPE
	SYNTAX DisplayString
	ACCESS  read-write
	STATUS  mandatory
	DESCRIPTION
		"&<caiNtOs.329>User name to match against.  '*' wildcard is permitted."
			::= { ntEventLogStTableEntry 5 }

ntStatusLogComputer OBJECT-TYPE
	SYNTAX DisplayString
	ACCESS  read-write
	STATUS  mandatory
	DESCRIPTION
		"&<caiNtOs.330>Computer name to match against. '*' wildcard is permitted."
			::= { ntEventLogStTableEntry 6 }

ntStatusLogStatus OBJECT-TYPE
	SYNTAX INTEGER {
		ok(1),
		warning(2),
		critical(3),
		reset(4)
		}
	ACCESS  read-write
	STATUS  mandatory
	DESCRIPTION
		"&<caiNtOs.331>Event log watch status.  Setting 'reset' will reset status to 'ok', alerts 
		will the be raised with respect to current levels."
			::= { ntEventLogStTableEntry 7 }

ntStatusLogAlertOn OBJECT-TYPE
	SYNTAX INTEGER {
		do-not-monitor(1),
		warning(2),
		critical(3),
		remove-watcher(4) 
		}
	ACCESS	read-write
	STATUS  mandatory
	DESCRIPTION
		"&<caiNtOs.332>How the watcher is to raise alerts.  Either not raising alerts 
		(i.e. informational monitoring only) or raising a warning or critical 
		level trap when the number of matching events changes.  
		Selecting remove-watcher will delete the current watc
her from the table."
			::= { ntEventLogStTableEntry 8 }

ntStatusLogStartTime OBJECT-TYPE
	SYNTAX INTEGER
	ACCESS  read-write
	STATUS  mandatory
	DESCRIPTION
		"&<caiNtOs.333>The time at which the watcher should start looking for events in the log.  
		Initially this will be set to the earliest event time recorded in any of the three logs.  
		Number represents number of seconds elapsed since 0:00.00 on 1 January 1970."
			::= { ntEventLogStTableEntry 9 }

ntStatusLogStartTimeInText OBJECT-TYPE
	SYNTAX DisplayString
	ACCESS  read-only
	STATUS  mandatory
	DESCRIPTION
		"&<caiNtOs.334>The time at which the watcher should start looking for events in the log displayed 
		in textual form."
			::= { ntEventLogStTableEntry 10 }

ntStatusLogAppLogMatches OBJECT-TYPE
	SYNTAX INTEGER
	ACCESS  read-only
	STATUS  mandatory
	DESCRIPTION
		"&<caiNtOs.335>Number of matches recorded in the Application log."
			::= { ntEventLogStTableEntry 11 }

ntStatusLogAppLogLastMatch OBJECT-TYPE
	SYNTAX DisplayString
	ACCESS  read-only
	STATUS  mandatory
	DESCRIPTION
		"&<caiNtOs.336>The time of the last matching event in the Application Log."
			::= { ntEventLogStTableEntry 12 }

ntStatusLogSecLogMatches OBJECT-TYPE
	SYNTAX INTEGER
	ACCESS  read-only
	STATUS  mandatory
	DESCRIPTION
		"&<caiNtOs.337>Number of matches recorded in the Security log."
			::= { ntEventLogStTableEntry 13 }

ntStatusLogSecLogLastMatch OBJECT-TYPE
	SYNTAX DisplayString
	ACCESS  read-only
	STATUS  mandatory
	DESCRIPTION
		"&<caiNtOs.338>The time of the last matching event in the Security Log."
			::= { ntEventLogStTableEntry 14 }

ntStatusLogSysLogMatches OBJECT-TYPE
	SYNTAX DisplayString
	ACCESS  read-only
	STATUS  mandatory
	DESCRIPTION
		"&<caiNtOs.339>Number of matches recorded in the System log."
			::= { ntEventLogStTableEntry 15 }

ntStatusLogSysLogLastMatch OBJECT-TYPE
	SYNTAX DisplayString
	ACCESS  read-only
	STATUS  mandatory
	DESCRIPTION
		"&<caiNtOs.340>The time of the last matching event in the System Log."
			::= { ntEventLogStTableEntry 16 }

ntStatusLogWatcherIndex OBJECT-TYPE
	SYNTAX INTEGER
	ACCESS read-only
	STATUS mandatory
	DESCRIPTION
		"&<caiNtOs.341>This is the index number for this watcher within the Event Log watcher table."
			::= { ntEventLogStTableEntry 17 }

ntStatusLogDescription OBJECT-TYPE
	SYNTAX DisplayString
	ACCESS  read-write
	STATUS  mandatory
	DESCRIPTION
		"&<caiNtOs.342>Description of what the event watcher defined is looking for 
		e.g. 'SQL Server event watcher' - for information only."
			::= { ntEventLogStTableEntry 18 }

--
--			Polled Values
--

--
--	Filesystem Poll Table
--

ntFilesystemPollTable 	OBJECT-TYPE
	SYNTAX  SEQUENCE OF NtFilesystemPollTableEntry
	ACCESS  not-accessible
	STATUS  mandatory
	DESCRIPTION
		"&<caiNtOs.343>List of information about filesystems."
			::= { ntPollGroup 2 }

ntFilesystemPollTableEntry OBJECT-TYPE
	SYNTAX NtFilesystemPollTableEntry
        ACCESS  not-accessible
        STATUS  mandatory
        DESCRIPTION
        	"&<caiNtOs.344>A table entry containing information about a filesystem."
	INDEX { ntFsysDriveLetter }
				::= { ntFilesystemPollTable 2 }

NtFilesystemPollTableEntry::=
	SEQUENCE {
		ntFsysDriveLetter	DisplayString,		
		ntFsysTotalCapacity 	INTEGER,
		ntFsysFree 		INTEGER,
		ntFsysUtilization 	INTEGER,
		ntFsysLastUtilization	INTEGER,
		ntFsysAverage		INTEGER,
		ntFsysAvgTicks		INTEGER
		}

ntFsysDriveLetter OBJECT-TYPE
	SYNTAX DisplayString
	ACCESS  read-only
	STATUS  mandatory
	DESCRIPTION
		"&<caiNtOs.345>The drive letter of the filesystem as recognised by the operating system."
			::= { ntFilesystemPollTableEntry 2 }

ntFsysTotalCapacity OBJECT-TYPE
	SYNTAX INTEGER
	ACCESS  read-only
	STATUS  mandatory
	DESCRIPTION
		"&<caiNtOs.346>Total disk capacity in bytes."
			::= { ntFilesystemPollTableEntry 3 }


ntFsysFree OBJECT-TYPE
	SYNTAX INTEGER
	ACCESS  read-only
	STATUS  mandatory
	DESCRIPTION
		"&<caiNtOs.347>Number of free bytes on the filesystem."
			::= { ntFilesystemPollTableEntry 4 }

ntFsysUtilization OBJECT-TYPE
	SYNTAX INTEGER
	ACCESS  read-only
	STATUS  mandatory
	DESCRIPTION
		"&<caiNtOs.348>Number of bytes of the filesystem utilized."
			::= { ntFilesystemPollTableEntry 5 }

ntFsysLastUtilization OBJECT-TYPE
	SYNTAX INTEGER
	ACCESS  read-only
	STATUS  mandatory
	DESCRIPTION
		"&<caiNtOs.349>Number of bytes utilized at the last polling interval."
			::= { ntFilesystemPollTableEntry 6 }

ntFsysAverage OBJECT-TYPE
	SYNTAX INTEGER
	ACCESS  read-only
	STATUS  mandatory
	DESCRIPTION
		"&<caiNtOs.350>Current average calculation value."
			::= { ntFilesystemPollTableEntry 7 }

ntFsysAvgTicks OBJECT-TYPE
	SYNTAX INTEGER
	ACCESS  read-only
	STATUS  mandatory
	DESCRIPTION
		"&<caiNtOs.351>Number of polling intervals since last average calculation."
			::= { ntFilesystemPollTableEntry 8 }

--
--	File Poll Table
--

ntFilePollTable	OBJECT-TYPE
	SYNTAX  SEQUENCE OF NtFilePollTableEntry
	ACCESS  not-accessible
	STATUS  mandatory
	DESCRIPTION
		"&<caiNtOs.352>List of information about monitored files."
			::= { ntPollGroup 3 }

ntFilePollTableEntry OBJECT-TYPE
        SYNTAX NtFilePollTableEntry
        ACCESS  not-accessible
        STATUS  mandatory
        DESCRIPTION
        	"&<caiNtOs.353>A table entry containing information about a monitored file."
	INDEX { ntFileName }
			::= { ntFilePollTable 2 }

NtFilePollTableEntry::=
        SEQUENCE {
		ntFileName			DisplayString,		
		ntFileTimestamp			DisplayString,
		ntFileRefTimestamp		DisplayString, 
		ntFileSize			INTEGER,
		ntFileSizeChangeReference	INTEGER,
		ntFileSizeChangeCount		INTEGER,
		ntFileSizeAvgTicks		INTEGER
		}

ntFileName OBJECT-TYPE
	SYNTAX DisplayString
	ACCESS  read-only
	STATUS  mandatory
	DESCRIPTION
		"&<caiNtOs.354>The full pathname of the file on the managed system."
			::= { ntFilePollTableEntry 2 }

ntFileTimestamp OBJECT-TYPE
	SYNTAX DisplayString
	ACCESS  read-only
	STATUS  mandatory
	DESCRIPTION
		"&<caiNtOs.355>File timestamp."
			::= { ntFilePollTableEntry 3 }

ntFileRefTimestamp OBJECT-TYPE
	SYNTAX DisplayString
	ACCESS  read-only
	STATUS  mandatory
	DESCRIPTION
		"&<caiNtOs.356>File timestamp."
			::= { ntFilePollTableEntry 4 }

ntFileSize OBJECT-TYPE
	SYNTAX INTEGER
	ACCESS  read-only
	STATUS  mandatory
	DESCRIPTION
		"&<caiNtOs.357>Current file size in bytes."
			::= { ntFilePollTableEntry 5 }

ntFileSizeChangeReference OBJECT-TYPE
	SYNTAX INTEGER
	ACCESS  read-only
	STATUS  mandatory
	DESCRIPTION
		"&<caiNtOs.358>Reference file size for change calculation."
			::= { ntFilePollTableEntry 6 }

ntFileSizeChangeCount OBJECT-TYPE
	SYNTAX INTEGER
	ACCESS  read-only
	STATUS  mandatory
	DESCRIPTION
		"&<caiNtOs.359>Number of polls since last file size change calculation."
			::= { ntFilePollTableEntry 7 }

ntFileSizeAvgTicks OBJECT-TYPE
	SYNTAX INTEGER
	ACCESS  read-only
	STATUS  mandatory
	DESCRIPTION
		"&<caiNtOs.360>Number of polling intervals since last average calculation."
			::= { ntFilePollTableEntry 8 }

--
--	Process Poll Table
--

ntProcessPollTable	OBJECT-TYPE
	SYNTAX  SEQUENCE OF NtProcessPollTableEntry
	ACCESS  not-accessible
	STATUS  mandatory
	DESCRIPTION
		"&<caiNtOs.361>List of information about processes."
			::= { ntPollGroup 4 }

ntProcessPollTableEntry OBJECT-TYPE
    SYNTAX NtProcessPollTableEntry
    ACCESS  not-accessible
    STATUS  mandatory
    DESCRIPTION
    	"&<caiNtOs.362>A table entry containing information about a monitored process."
	INDEX { ntProcessName }
			::= { ntProcessPollTable 2 }

NtProcessPollTableEntry::=
	SEQUENCE {
		ntProcessName		DisplayString,		
		ntProcessInstCount	INTEGER,
		ntProcessMaxThread	INTEGER,
		ntProcessMinThread	INTEGER
		}

ntProcessName OBJECT-TYPE
	SYNTAX DisplayString
	ACCESS  read-only
	STATUS  mandatory
	DESCRIPTION
		"&<caiNtOs.363>The name of the process, as returned from the NT Registry."
			::= { ntProcessPollTableEntry 2 }

ntProcessInstCount OBJECT-TYPE
	SYNTAX INTEGER
	ACCESS  read-only
	STATUS  mandatory
	DESCRIPTION
		"&<caiNtOs.364>Current number of instances of the process running on the system."
			::= { ntProcessPollTableEntry 3 }

ntProcessMaxThread OBJECT-TYPE
	SYNTAX INTEGER
	ACCESS  read-only
	STATUS  mandatory
	DESCRIPTION
		"&<caiNtOs.365>Maximum number of threads of any instance of the process."
			::= { ntProcessPollTableEntry 4 }

ntProcessMinThread OBJECT-TYPE
	SYNTAX INTEGER
	ACCESS  read-only
	STATUS  mandatory
	DESCRIPTION
		"&<caiNtOs.366>Minimum number of threads of any instance of the process."
			::= { ntProcessPollTableEntry 5 }


--
--	Processor Poll Table
--
ntProcessorPollTable OBJECT-TYPE
	SYNTAX  SEQUENCE OF NtProcessorPollTableEntry
	ACCESS  not-accessible
	STATUS  mandatory
	DESCRIPTION
		"&<caiNtOs.367>List of information about printers."
			::= { ntPollGroup 5 }

ntProcessorPollTableEntry OBJECT-TYPE
	SYNTAX NtProcessorPollTableEntry
        ACCESS  not-accessible
        STATUS  mandatory
        DESCRIPTION
		"&<caiNtOs.368>A table entry containing information about a printer."
	INDEX { ntCPUNumber }
			::= { ntProcessorPollTable 2 }

NtProcessorPollTableEntry::=
	SEQUENCE {
		ntCPUNumber	DisplayString, 
		ntCPUDPCTime	INTEGER, 
		ntCPUInterruptTime	INTEGER,
		ntCPUPrivilegedTime	INTEGER,
		ntCPUProcessorTime	INTEGER,
		ntCPUUserTime		INTEGER,
		ntCPUTicks		INTEGER,
		ntCPUCountsSoFar	INTEGER
		}

ntCPUNumber OBJECT-TYPE
	SYNTAX DisplayString
	ACCESS  read-only
	STATUS  mandatory
	DESCRIPTION
		"&<caiNtOs.369>Processor identification number."
			::= { ntProcessorPollTableEntry 3 }

ntCPUDPCTime OBJECT-TYPE
	SYNTAX INTEGER
	ACCESS  read-only
	STATUS  mandatory
	DESCRIPTION
		"&<caiNtOs.370>%DPC (Deferred Procedure Call) time for the processor."
			::= { ntProcessorPollTableEntry 4 }

ntCPUInterruptTime OBJECT-TYPE
	SYNTAX INTEGER
	ACCESS  read-only
	STATUS  mandatory
	DESCRIPTION
		"&<caiNtOs.371>%Interrupt time (handling hardware interrupts) for the processor."
			::= { ntProcessorPollTableEntry 5 }

ntCPUPrivilegedTime OBJECT-TYPE
	SYNTAX INTEGER
	ACCESS  read-only
	STATUS  mandatory
	DESCRIPTION
		"&<caiNtOs.372>%Privileged time (time spent in privileged mode in non-idle threads) for the processor."
			::= { ntProcessorPollTableEntry 6 }

ntCPUProcessorTime OBJECT-TYPE
	SYNTAX INTEGER
	ACCESS  read-only
	STATUS  mandatory
	DESCRIPTION
		"&<caiNtOs.373>%Processor time (time spent executing non-idle threads) for the processor."
			::= { ntProcessorPollTableEntry 7 }

ntCPUUserTime OBJECT-TYPE
	SYNTAX INTEGER
	ACCESS  read-only
	STATUS  mandatory
	DESCRIPTION
		"&<caiNtOs.374>%User time (time spent in user mode executing non-idle threads) for the processor."
			::= { ntProcessorPollTableEntry 8 }

ntCPUTicks OBJECT-TYPE
	SYNTAX INTEGER
	ACCESS  read-only
	STATUS  mandatory
	DESCRIPTION
		"&<caiNtOs.375>Counter for Average CPU calculation."
			::= { ntProcessorPollTableEntry 9 }

ntCPUCountsSoFar OBJECT-TYPE
	SYNTAX INTEGER
	ACCESS  read-only
	STATUS  mandatory
	DESCRIPTION
		"&<caiNtOs.376>Number of counts on a potential state change."
			::= { ntProcessorPollTableEntry 10 }


--
--  Log Poll Table
--

ntLogPollTable	OBJECT-TYPE
	SYNTAX  SEQUENCE OF NtLogPollTableEntry
	ACCESS  not-accessible
	STATUS  mandatory
	DESCRIPTION
		"&<caiNtOs.377>List of information about configured Log watchers."
			::= { ntPollGroup 6 }

ntLogPollTableEntry OBJECT-TYPE
        SYNTAX NtLogPollTableEntry
        ACCESS  not-accessible
        STATUS  mandatory
        DESCRIPTION
        	"&<caiNtOs.378>A table entry containing information about a configured Log watcher."
			::= { ntLogPollTable 1}

NtLogPollTableEntry::=
        SEQUENCE {
		ntLogAppStart			INTEGER,
		ntLogSecStart			INTEGER,
		ntLogSysStart			INTEGER,
		ntLogAppLast			INTEGER,
		ntLogSecLast			INTEGER,
		ntLogSysLast			INTEGER
		}

ntLogAppStart OBJECT-TYPE
	SYNTAX INTEGER
	ACCESS  read-only
	STATUS  mandatory
	DESCRIPTION
		"&<caiNtOs.379>Starting Event for Application Log."
			::= { ntLogPollTableEntry 1 }

ntLogSecStart OBJECT-TYPE
	SYNTAX INTEGER
	ACCESS  read-only
	STATUS  mandatory
	DESCRIPTION
		"&<caiNtOs.380>Starting Event for Security Log."
			::= { ntLogPollTableEntry 2 }

ntLogSysStart OBJECT-TYPE
	SYNTAX INTEGER
	ACCESS  read-only
	STATUS  mandatory
	DESCRIPTION
		"&<caiNtOs.381>Starting Event for System Log."
			::= { ntLogPollTableEntry 3 }

ntLogAppLast OBJECT-TYPE
	SYNTAX INTEGER
	ACCESS  read-only
	STATUS  mandatory
	DESCRIPTION
		"&<caiNtOs.382>Last Checked Event in the Application Log."
			::= { ntLogPollTableEntry 4 }

ntLogSecLast OBJECT-TYPE
	SYNTAX INTEGER
	ACCESS  read-only
	STATUS  mandatory
	DESCRIPTION
		"&<caiNtOs.383>Last Checked Event in the Security Log."
			::= { ntLogPollTableEntry 5 }

ntLogSysLast OBJECT-TYPE
	SYNTAX INTEGER
	ACCESS  read-only
	STATUS  mandatory
	DESCRIPTION
		"&<caiNtOs.384>Last Checked Event in the System Log."
			::= { ntLogPollTableEntry 6 }


--
--			Availability Tables
--

ntAvailConfig	OBJECT IDENTIFIER 
--	DESCRIPTION
--     	"Timestamps and periods of polling for availability."
	::= { ntAvailableGroup 1 }

ntAvailFSPeriod OBJECT-TYPE
	SYNTAX  DisplayString
	ACCESS  read-write
	STATUS  mandatory
	DESCRIPTION
		"&<caiNtOs.385>Polling Interval to check for current local Filesystem availability." 
			::= { ntAvailConfig  1 }

ntAvailFSPollTimestamp OBJECT-TYPE
	SYNTAX  DisplayString
	ACCESS  read-only
	STATUS  mandatory
	DESCRIPTION
		"&<caiNtOs.386>The date and time that NT System Agent last polled for current local Filesystem availability." 
			::= { ntAvailConfig  2 }

ntAvailProcPeriod OBJECT-TYPE
	SYNTAX  DisplayString
	ACCESS  read-write
	STATUS  mandatory
	DESCRIPTION
		"&<caiNtOs.387>Polling Interval to update the table of current process activity." 
			::= { ntAvailConfig  3 }

ntAvailProcTimestamp OBJECT-TYPE
	SYNTAX  DisplayString
	ACCESS  read-only
	STATUS  mandatory
	DESCRIPTION
		"&<caiNtOs.388>The date and time that NT System Agent last polled for current process activity." 
			::= { ntAvailConfig  4 }

ntAvailServPeriod OBJECT-TYPE
	SYNTAX  DisplayString
	ACCESS  read-write
	STATUS  mandatory
	DESCRIPTION
		"&<caiNtOs.389>Polling Interval to update the table of current service availability." 
			::= { ntAvailConfig  5 }

ntAvailServPollTimestamp OBJECT-TYPE
	SYNTAX  DisplayString
	ACCESS  read-only
	STATUS  mandatory
	DESCRIPTION
		"&<caiNtOs.390>The date and time that NT System Agent last polled for current service availability." 
			::= { ntAvailConfig  6 }

ntAvailPrinterPeriod OBJECT-TYPE
	SYNTAX  DisplayString
	ACCESS  read-write
	STATUS  mandatory
	DESCRIPTION
		"&<caiNtOs.391>Polling Interval to check for current local printer availability." 
			::= { ntAvailConfig  7 }

ntAvailPrinterPollTimestamp OBJECT-TYPE
	SYNTAX  DisplayString
	ACCESS  read-only
	STATUS  mandatory
	DESCRIPTION
		"&<caiNtOs.392>The date and time that NT System Agent last polled for current local printer availability." 
			::= { ntAvailConfig  8 }


--
--  Logsystem Availability
--
ntAvailFSTable OBJECT-TYPE 
	SYNTAX  SEQUENCE OF NtAvailFSEntry
	ACCESS  not-accessible
	STATUS  mandatory
	DESCRIPTION
		"&<caiNtOs.393>Table containing Filesystems available for monitoring."
				::= { ntAvailableGroup 2 }

ntAvailFSEntry OBJECT-TYPE
        SYNTAX NtAvailFSEntry
        ACCESS  not-accessible
        STATUS  mandatory
        DESCRIPTION
                "&<caiNtOs.394>A table entry containing information Filesystems available for monitoring."
	INDEX { ntAvailFSDriveLetter }
			::= { ntAvailFSTable 1 }

NtAvailFSEntry::=
	SEQUENCE {
		ntAvailFSDriveLetter	DisplayString,		
		ntAvailFSDriveLabel	DisplayString, 
		ntAvailFSDriveType	DisplayString
	      }

ntAvailFSDriveLetter OBJECT-TYPE
	SYNTAX DisplayString
	ACCESS  read-only
	STATUS  mandatory
	DESCRIPTION
		"&<caiNtOs.395>The drive letter of the Filesystem as recognised by the operating system."
			::= { ntAvailFSEntry 1 }

ntAvailFSDriveLabel OBJECT-TYPE
	SYNTAX DisplayString
	ACCESS  read-only
	STATUS  mandatory
	DESCRIPTION
		"&<caiNtOs.396>The drive label of the Filesystem."
			::= { ntAvailFSEntry 2 }

ntAvailFSDriveType OBJECT-TYPE
	SYNTAX DisplayString
	ACCESS  read-only
	STATUS  mandatory
	DESCRIPTION
		"&<caiNtOs.397>Drive type as determined by the operating system (removeable, fixed, CDROM etc.)."
			::= { ntAvailFSEntry 3 }

--
-- Process Availability
--

ntAvailProcTable	OBJECT-TYPE
	SYNTAX  SEQUENCE OF NtAvailProcEntry
	ACCESS  not-accessible
	STATUS  mandatory
	DESCRIPTION
	    	"&<caiNtOs.398>Table containing Processes currently running."
				::= { ntAvailableGroup 3 }

ntAvailProcEntry OBJECT-TYPE
        SYNTAX NtAvailProcEntry
        ACCESS  not-accessible
        STATUS  mandatory
        DESCRIPTION
                "&<caiNtOs.399>A table entry containing information Logsystems available for monitoring."
	INDEX { ntAvailProcessName }
			::= { ntAvailProcTable 1 }

NtAvailProcEntry::=
	SEQUENCE {
		ntAvailProcessName	DisplayString
	      }

ntAvailProcessName OBJECT-TYPE
	SYNTAX DisplayString
	ACCESS  read-only
	STATUS  mandatory
	DESCRIPTION
		"&<caiNtOs.400>The name of a process currently running"
			::= { ntAvailProcEntry 1 }

-- 
-- Service Availability
--

ntAvailServiceTable	OBJECT-TYPE
	SYNTAX  SEQUENCE OF NtAvailServiceEntry
	ACCESS  not-accessible
	STATUS  mandatory
	DESCRIPTION
     		"&<caiNtOs.401>Table containing Services currently registered with the Service Manager."
				::= { ntAvailableGroup 4 }

ntAvailServiceEntry OBJECT-TYPE
        SYNTAX NtAvailServiceEntry
        ACCESS  not-accessible
        STATUS  mandatory
        DESCRIPTION
                "&<caiNtOs.402>A table entry containing information Logsystems available for monitoring."
	INDEX { ntAvailServiceName }
			::= { ntAvailServiceTable 1 }

NtAvailServiceEntry::=
	SEQUENCE {
		ntAvailServiceName	DisplayString,
		ntAvailServiceDescr	DisplayString,
		ntAvailServiceStatus	INTEGER
	      }

ntAvailServiceName OBJECT-TYPE
	SYNTAX DisplayString
	ACCESS  read-only
	STATUS  mandatory
	DESCRIPTION
		"&<caiNtOs.403>The name of a service currently running."
			::= { ntAvailServiceEntry 1 }

ntAvailServiceDescr OBJECT-TYPE
	SYNTAX DisplayString
	ACCESS  read-only
	STATUS  mandatory
	DESCRIPTION
		"&<caiNtOs.404>The decsription of a service currently running."
			::= { ntAvailServiceEntry 2 }

ntAvailServiceStatus OBJECT-TYPE
	SYNTAX INTEGER {
		stopped(1),
		start-pending(2),
		stop-pending(3),
		running(4),
		continue-pending(5),
		pause-pending(6),
		paused(7),
		unknown(8)
		}
	ACCESS  read-only
	STATUS  mandatory
	DESCRIPTION
		"&<caiNtOs.405>The name of a process currently running."
			::= { ntAvailServiceEntry 3 }

-- 
-- Printer Availability
--
ntAvailPrinterTable	OBJECT-TYPE
	SYNTAX  SEQUENCE OF NtAvailPrinterEntry
	ACCESS  not-accessible
	STATUS  mandatory
	DESCRIPTION
     		"&<caiNtOs.406>Table containing Printers available for monitoring."
				::= { ntAvailableGroup 5 }

ntAvailPrinterEntry OBJECT-TYPE
        SYNTAX NtAvailPrinterEntry
        ACCESS  not-accessible
        STATUS  mandatory
        DESCRIPTION
                "&<caiNtOs.407>A table entry containing information Logsystems available for monitoring."
	INDEX { ntAvailPrinterName }
			::= { ntAvailPrinterTable 1 }

NtAvailPrinterEntry::=
	SEQUENCE {
		ntAvailPrinterName	DisplayString,
		ntAvailPrinterDescr	DisplayString,
		ntAvailPrinterType	DisplayString,
		ntAvailPrinterLocation	DisplayString
	      }

ntAvailPrinterName OBJECT-TYPE
	SYNTAX DisplayString
	ACCESS  read-only
	STATUS  mandatory
	DESCRIPTION
		"&<caiNtOs.408>The name of a Printer local to the machine."
			::= { ntAvailPrinterEntry 1 }

ntAvailPrinterDescr OBJECT-TYPE
	SYNTAX DisplayString
	ACCESS  read-only
	STATUS  mandatory
	DESCRIPTION
		"&<caiNtOs.409>Description of the Printer as defined to Print Manager."
			::= { ntAvailPrinterEntry 2 }

ntAvailPrinterType OBJECT-TYPE
	SYNTAX DisplayString
	ACCESS  read-only
	STATUS  mandatory
	DESCRIPTION
		"&<caiNtOs.410>Type of Printer according to driver settings."
			::= { ntAvailPrinterEntry 3 }

ntAvailPrinterLocation OBJECT-TYPE
	SYNTAX DisplayString
	ACCESS  read-only
	STATUS  mandatory
	DESCRIPTION
		"&<caiNtOs.411>Location of the Printer as defined to Print Manager."
			::= { ntAvailPrinterEntry 4 }

--
-- TRAP DEFINITIONS
--

--
-- File Systems
--

ntFSUnknown TRAP-TYPE
	ENTERPRISE caiNtOs
	DESCRIPTION
		"&<caiNtOs.412>A monitored file system is in an unknown state.
		The varbind entry contains the name of the
		file system whose state changed."
	::= 1

ntFSok TRAP-TYPE
	ENTERPRISE caiNtOs
	DESCRIPTION
		"&<caiNtOs.413>A monitored file system is in the ok state.
		The varbind entry contains the name of the
		file system whose state changed."
	::= 2

ntFSwarning TRAP-TYPE
	ENTERPRISE caiNtOs
	DESCRIPTION
		"&<caiNtOs.414>A monitored file system is in the warning state.
		The varbind entry contains the name of the
		file system whose state changed."
	::= 3

ntFScritical TRAP-TYPE
	ENTERPRISE caiNtOs
	DESCRIPTION
		"&<caiNtOs.415>A monitored file system is in the critical state.
		The varbind entry contains the name of the
		file system whose state changed."
	::= 4
--
-- Files
--

ntFileUnknown TRAP-TYPE
	ENTERPRISE caiNtOs
	DESCRIPTION
		"&<caiNtOs.416>A monitored file is in an unknown state.
		The varbind entry contains the name of the
		file whose state changed."
	::= 5

ntFileok TRAP-TYPE
	ENTERPRISE caiNtOs
	DESCRIPTION
		"&<caiNtOs.417>A monitored file is in the ok state.
		The varbind entry contains the name of the
		file whose state changed."
	::= 6

ntFilewarning TRAP-TYPE
	ENTERPRISE caiNtOs
	DESCRIPTION
		"&<caiNtOs.418>A monitored file is in the warning state.
		The varbind entry contains the name of the
		file whose state changed."
	::= 7

ntFilecritical TRAP-TYPE
	ENTERPRISE caiNtOs
	DESCRIPTION
		"&<caiNtOs.419>A monitored file is in the critical state.
		The varbind entry contains the name of the
		file whose state changed."
	::= 8

--
-- Processes
--

ntProcessUnknown TRAP-TYPE
	ENTERPRISE caiNtOs
	DESCRIPTION
		"&<caiNtOs.420>A monitored Process is in an unknown state.
		The varbind entry contains the name of the
		Process whose state changed."
	::= 9

ntProcessok TRAP-TYPE
	ENTERPRISE caiNtOs
	DESCRIPTION
		"&<caiNtOs.421>A monitored Process is in the ok state.
		The varbind entry contains the name of the
		Process whose state changed."
	::= 10

ntProcesswarning TRAP-TYPE
	ENTERPRISE caiNtOs
	DESCRIPTION
		"&<caiNtOs.422>A monitored Process is in the warning state.
		The varbind entry contains the name of the
		Process whose state changed."
	::= 11

ntProcesscritical TRAP-TYPE
	ENTERPRISE caiNtOs
	DESCRIPTION
		"&<caiNtOs.423>A monitored Process is in the critical state.
		The varbind entry contains the name of the
		Process whose state changed."
	::= 12

--
-- Services
--

ntServiceUnknown TRAP-TYPE
	ENTERPRISE caiNtOs
	DESCRIPTION
		"&<caiNtOs.424>A monitored Service is in an unknown state.
		The varbind entry contains the name of the
		Service whose state changed."
	::= 13

ntServiceok TRAP-TYPE
	ENTERPRISE caiNtOs
	DESCRIPTION
		"&<caiNtOs.425>A monitored Service is in the ok state.
		The varbind entry contains the name of the
		Service whose state changed."
	::= 14

ntServicewarning TRAP-TYPE
	ENTERPRISE caiNtOs
	DESCRIPTION
		"&<caiNtOs.426>A monitored Service is in the warning state.
		The varbind entry contains the name of the
		Service whose state changed."
	::= 15

ntServicecritical TRAP-TYPE
	ENTERPRISE caiNtOs
	DESCRIPTION
		"&<caiNtOs.427>A monitored Service is in the critical state.
		The varbind entry contains the name of the
		Service whose state changed."
	::= 16

--
-- Printers
--

ntPrinterUnknown TRAP-TYPE
	ENTERPRISE caiNtOs
	DESCRIPTION
		"&<caiNtOs.428>A monitored Printer is in an unknown state.
		The varbind entry contains the name of the
		Printer whose state changed."
	::= 17

ntPrinterok TRAP-TYPE
	ENTERPRISE caiNtOs
	DESCRIPTION
		"&<caiNtOs.429>A monitored Printer is in the ok state.
		The varbind entry contains the name of the
		Printer whose state changed."
	::= 18

ntPrinterwarning TRAP-TYPE
	ENTERPRISE caiNtOs
	DESCRIPTION
		"&<caiNtOs.430>A monitored Printer is in the warning state.
		The varbind entry contains the name of the
		Printer whose state changed."
	::= 19

ntPrintercritical TRAP-TYPE
	ENTERPRISE caiNtOs
	DESCRIPTION
		"&<caiNtOs.431>A monitored Printer is in the critical state.
		The varbind entry contains the name of the
		Printer whose state changed."
	::= 20

--
-- CPUs
--

ntCPUUnknown TRAP-TYPE
	ENTERPRISE caiNtOs
	DESCRIPTION
		"&<caiNtOs.432>A monitored CPU is in an unknown state.
		The varbind entry contains the name of the
		CPU whose state changed."
	::= 21

ntCPUok TRAP-TYPE
	ENTERPRISE caiNtOs
	DESCRIPTION
		"&<caiNtOs.433>A monitored CPU is in the ok state.
		The varbind entry contains the name of the
		CPU whose state changed."
	::= 22

ntCPUwarning TRAP-TYPE
	ENTERPRISE caiNtOs
	DESCRIPTION
		"&<caiNtOs.434>A monitored CPU is in the warning state.
		The varbind entry contains the name of the
		CPU whose state changed."
	::= 23

ntCPUcritical TRAP-TYPE
	ENTERPRISE caiNtOs
	DESCRIPTION
		"&<caiNtOs.435>A monitored CPU is in the critical state.
		The varbind entry contains the name of the
		CPU whose state changed."
	::= 24

--
-- Memory
--

ntMemLoadok TRAP-TYPE
	ENTERPRISE caiNtOs
	DESCRIPTION
		"&<caiNtOs.436>Memory Load is in the ok state."
	::= 25

ntMemLoadwarning TRAP-TYPE
	ENTERPRISE caiNtOs
	DESCRIPTION
		"&<caiNtOs.437>Memory Load is in the warning state."
	::= 26

ntMemLoadcritical TRAP-TYPE
	ENTERPRISE caiNtOs
	DESCRIPTION
		"&<caiNtOs.438>Memory Load is in the critical state."
	::= 27

ntMemPhysok TRAP-TYPE
	ENTERPRISE caiNtOs
	DESCRIPTION
		"&<caiNtOs.439>Available Physical Memory is in the ok state."
	::= 28

ntMemPhyswarning TRAP-TYPE
	ENTERPRISE caiNtOs
	DESCRIPTION
		"&<caiNtOs.440>Available Physical Memory is in the warning state."
	::= 29

ntMemPhyscritical TRAP-TYPE
	ENTERPRISE caiNtOs
	DESCRIPTION
		"&<caiNtOs.441>Available Physical Memory is in the critical state."
	::= 30

ntMemSwapok TRAP-TYPE
	ENTERPRISE caiNtOs
	DESCRIPTION
		"&<caiNtOs.442>Available Swapspace is in the ok state."
	::= 31

ntMemSwapwarning TRAP-TYPE
	ENTERPRISE caiNtOs
	DESCRIPTION
		"&<caiNtOs.443>Available Swapspace is in the warning state."
	::= 32

ntMemSwapcritical TRAP-TYPE
	ENTERPRISE caiNtOs
	DESCRIPTION
		"&<caiNtOs.444>Available Swapspace is in the critical state."
	::= 33

--
-- Registry
--

ntRegUnknown TRAP-TYPE
	ENTERPRISE caiNtOs
	DESCRIPTION
		"&<caiNtOs.445>A monitored registry leaf is in an unknown state.
		The varbind entry contains details of the
		registry leaf whose state changed."
	::= 34

ntRegOK TRAP-TYPE
	ENTERPRISE caiNtOs
	DESCRIPTION
		"&<caiNtOs.446>A monitored registry leaf is in the ok state.
		The varbind entry contains details of the
		registry leaf whose state changed."
	::= 35

ntRegwarning TRAP-TYPE
	ENTERPRISE caiNtOs
	DESCRIPTION
		"&<caiNtOs.447>A monitored registry leaf is in the warning state.
		The varbind entry contains details of the
		registry leaf whose state changed"
	::= 36

ntRegcritical TRAP-TYPE
	ENTERPRISE caiNtOs
	DESCRIPTION
		"&<caiNtOs.448>A monitored registry leaf is in the critical state.
		The varbind entry contains the details of the
		registry leaf whose state changed"
	::= 37


--
-- Event Log Watchers
--

ntLogOK TRAP-TYPE
	ENTERPRISE caiNtOs
	DESCRIPTION
		"&<caiNtOs.449>A monitored event log watcher is in the ok state."
	::= 38

ntLogwarning TRAP-TYPE
	ENTERPRISE caiNtOs
	DESCRIPTION
		"&<caiNtOs.450>A monitored event log watcher is in the warning state.
		This means one or more event records match the criteria and
		have not been acknowledged."
	::= 39

ntLogcritical TRAP-TYPE
	ENTERPRISE caiNtOs
	DESCRIPTION
		"&<caiNtOs.451>A monitored event log watcher is in the critical state.
		This means one or more event records match the criteria and
		have not been acknowledged."
	::= 40

--
-- General traps
--

ntAdd TRAP-TYPE
	ENTERPRISE caiNtOs
	DESCRIPTION
		"&<caiNtOs.452>An object has been added to the list
		of monitored objects.
		e.g. filesystems, files, processes, etc."
	::= 41

ntRemove TRAP-TYPE
	ENTERPRISE caiNtOs
	DESCRIPTION
		"&<caiNtOs.453>An object has been removed from the list
		of monitored objects.
		e.g. filesystems, files, processes, etc."
	::= 42


END
