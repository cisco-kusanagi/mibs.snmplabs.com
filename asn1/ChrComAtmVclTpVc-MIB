ChrComAtmVclTpVc-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComAtmVcl				FROM  Chromatis-MIB
	TruthValue				FROM  ChrTyp-MIB
	OperStatus				FROM  CISCO-RHINO-MIB;

-- chrComAtmVclTpVc Table

chrComAtmVclTpVcTable		OBJECT-TYPE
	SYNTAX		SEQUENCE OF ChrComAtmVclTpVcEntry
	MAX-ACCESS	not-accessible
	STATUS		current
	DESCRIPTION
	"Private table.  This table does not augment the VCL table, since it contains entries only VCC TP (i.e. APS channels and inband management and control channel, like those of IP)"
	::= { chrComAtmVcl 2}

chrComAtmVclTpVcEntry		OBJECT-TYPE
	SYNTAX		ChrComAtmVclTpVcEntry
	MAX-ACCESS	not-accessible
	STATUS		current
	DESCRIPTION
	""
	INDEX  {  chrComAtmVclifIndex, chrComAtmVclAtmVclVpi, chrComAtmVclAtmVclVci }

--DEFAULT  get-function-async  MNIL_GetRoutine
--DEFAULT  set-function-async  MNIL_SetRoutine
--DEFAULT  next-function-async MNIL_NextRoutine
--DEFAULT  test-function-async MNIL_TestRoutine
--DEFAULT  cookie "TpVc"
	::= { chrComAtmVclTpVcTable  1 }

ChrComAtmVclTpVcEntry  ::=
	SEQUENCE  {
	chrComAtmVclifIndex			Unsigned32	(0..4294967295),
	chrComAtmVclAtmVclVpi		Unsigned32	(0..4294967295),
	chrComAtmVclAtmVclVci		Unsigned32	(0..4294967295),
	chrComAtmVclCCSource		TruthValue,
	chrComAtmVclCCSink			TruthValue,
	chrComAtmVclTPOperStatus		OperStatus,
	chrComAtmVclAlarmVector		Integer32	(0..65535),
	chrComAtmVclAlarmSeverityProfileIndex Unsigned32	(0..4294967295)
}

chrComAtmVclifIndex 	OBJECT-TYPE
	SYNTAX		Unsigned32	(0..4294967295)
	MAX-ACCESS 	read-write
	STATUS 		current
	DESCRIPTION
	"Index of entry in the interface table"
	::= { chrComAtmVclTpVcEntry  1 }

chrComAtmVclAtmVclVpi 	OBJECT-TYPE
	SYNTAX		Unsigned32	(0..4294967295)
	MAX-ACCESS 	read-write
	STATUS 		current
	DESCRIPTION
	"The VPI value of the VCL"
	::= { chrComAtmVclTpVcEntry  2 }

chrComAtmVclAtmVclVci 	OBJECT-TYPE
	SYNTAX		Unsigned32	(0..4294967295)
	MAX-ACCESS 	read-write
	STATUS 		current
	DESCRIPTION
	"The VCI value of the VCL."
	::= { chrComAtmVclTpVcEntry  3 }

chrComAtmVclCCSource 	OBJECT-TYPE
	SYNTAX		TruthValue
	MAX-ACCESS 	read-write
	STATUS 		current
	DESCRIPTION
	"A boolean indication whether this TP implements CC source finctionality."
	::= { chrComAtmVclTpVcEntry  4 }

chrComAtmVclCCSink 	OBJECT-TYPE
	SYNTAX		TruthValue
	MAX-ACCESS 	read-write
	STATUS 		current
	DESCRIPTION
	"A boolean indication whether this TP implements CC sink finctionality"
	::= { chrComAtmVclTpVcEntry  5 }


chrComAtmVclTPOperStatus 	OBJECT-TYPE
	SYNTAX		OperStatus
	MAX-ACCESS 	read-only
	STATUS 		current
	DESCRIPTION
	"This object indicates the current operational status of the TP. The up and down states indicate that the TP is currently operational, or not operational, respectively. The unknown state indicates that the status of this TP cannot be determined. "
	::= { chrComAtmVclTpVcEntry  6 }

chrComAtmVclAlarmVector 	OBJECT-TYPE
	SYNTAX		Integer32	(0..65535)
	MAX-ACCESS 	read-only
	STATUS 		current
	DESCRIPTION
	"16 bit field. The following are bits relative positions (0=LSB), and the trap ID associated to each alarm state. 
0. VCC-AIS  atmfM4VccTpAisAlarm
8. VCC-RDI  atmfM4VccTpRdiAlarm
"
	::= { chrComAtmVclTpVcEntry  7 }

chrComAtmVclAlarmSeverityProfileIndex 	OBJECT-TYPE
	SYNTAX		Unsigned32	(0..4294967295)
	MAX-ACCESS 	read-write
	STATUS 		current
	DESCRIPTION
	""
	::= { chrComAtmVclTpVcEntry  8 }


END
