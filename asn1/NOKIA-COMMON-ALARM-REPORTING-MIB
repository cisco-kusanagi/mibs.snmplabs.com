NOKIA-COMMON-ALARM-REPORTING-MIB 
DEFINITIONS ::= BEGIN

-- 4567890123456789012345678901234567890123456789012345678901234567890123456789
-- This line is 80 characters wide, keep lines in this file shorter than that--
-- ===============================================================
--     Copyright (C) Nokia Telecommunications Oy 1998
-- ===============================================================
-- This MIB Module defines Nokia Common Alarm Reporting MIB. The 
-- alarm traps are defined in other MIB Module. More detailed 
-- description of the variables and tables is provided in other 
-- related documentation.
--
-- Format:   SNMP v1 MIB (Simple network management protocol,
--       version 1, Management Information Base  )
-- version 
-- 0.02         : ObjectName replaced by OBJECT IDENTIFIER
-- 0.03         : Updated according to the review comments.
-- 0.04         : Editorial change to move two first lines of ASN.1 to the
--                very beginning of the MIB file.
-- 1.00         : Final version.
-- 1.01 08.09.98: MIB to be revised according to implementors guide v.0.08
-- 1.02 29.10.98: low boundary of caTrapId corrected to be 0 instead of 1.
-- 1.03 11.11.98: Syntax of time stamp related objects corrected to TimeTicks.
--                RowPointer syntax to be used for caColumnInTbl and other
--                related objects in calCurrentAlarmListTable and
--                alAlarmLogTable.
-- 1.04 18.05.99: Value used for indeterminate in calSeverity and alSeverity
--                aligned with the value used for indeterminate in 
--                caSeverity carried in alarm traps (value 6 shall be used
--                from now on). Value 0 shall be used to mean 
--                <not supported>. 
-- 1.05 07.06.99: Proposal in 1.04 changed so that severities included 
--                as a type (or textual convention) instead of three
--                duplicate identical descriptions. Applied to caSeverity, 
--                calSeverity and alSeverity objects.
--                This version also incorporates the agreed changes in CR13 
--                in implementors guide.
--
-- ===============================================================
-- Author      : Mika Kiikkila
-- Version     : 1.05
-- Last Update : 07-06-99 08:40
--================================================================

IMPORTS
enterprises, NetworkAddress, TimeTicks --, ObjectName
FROM RFC1155-SMI
DisplayString
FROM RFC1213-MIB
OBJECT-TYPE
FROM RFC-1212;

--=============================================================
-- Following variables are copied from nokia.mib
--=============================================================

nokia       OBJECT IDENTIFIER ::= {enterprises 94}
nokiaProducts   OBJECT IDENTIFIER ::= {nokia 1}
ntcCommon   OBJECT IDENTIFIER ::= {nokiaProducts 16}
ntcCommonAlarm  OBJECT IDENTIFIER ::= {ntcCommon 1}


--=============================================================
-- OID registration subtrees for this MIB module
--=============================================================

ca    OBJECT IDENTIFIER ::= {ntcCommonAlarm 1} -- common alarms
caVars    OBJECT IDENTIFIER ::= {ca 1} -- common alarms variables
cal   OBJECT IDENTIFIER ::= {ntcCommonAlarm 2} -- Current Alarm List
calVars   OBJECT IDENTIFIER ::= {cal 1} -- CAL variables
calTables OBJECT IDENTIFIER ::= {cal 2} -- CAL tables
al    OBJECT IDENTIFIER ::= {ntcCommonAlarm 3} -- Alarm Log
alVars    OBJECT IDENTIFIER ::= {al 1} -- alarm log variables
alTables  OBJECT IDENTIFIER ::= {al 2} -- alarm log tables



--=============================================================
-- Types
--=============================================================

-- In case the NE does not support severity in alarm traps,
-- the value 0 in AlarmSeverity shall be used.
-- Otherwise, severities use following values:
-- critical(1), major(2), minor(3), warning(4), cleared(5).
-- indeterminate(6) is used when severity is supported, but
-- it is not possible to assign any of the other values above.

AlarmSeverity ::= INTEGER


EnabledDisabled ::= INTEGER { enabled(1), disabled(2)}


-- behaviour of RowPointer (as defined in RFC1903)
-- "Represents a pointer to a conceptual row.  The value is the
-- name of the instance of the first accessible columnar object
-- in the conceptual row.
-- For example, ifIndex.3 would point to the 3rd row in the
-- ifTable (note that if ifIndex were not-accessible, then
-- ifDescr.3 would be used instead)."

RowPointer ::= OBJECT IDENTIFIER


--=============================================================
-- Variables controlling Nokia Common Alarm Reporting
-- ca == Common Alarm
--=============================================================

caReportNokiaAlarmTraps  OBJECT-TYPE
    SYNTAX  EnabledDisabled
    ACCESS  read-write
    STATUS  mandatory
    DESCRIPTION
    "This NE wide variable is used to control if the NE reports alarms 
    using Nokia Common Alarm syntax. When the value equals to enabled, 
    the NE shall report alarms using Nokia Common Alarm Traps, and when 
    disabled, Nokia Common Alarm Traps shall not be emitted.
    The default value for this variable is enabled."
::= {caVars 1}

caReportLinkUpLinkDownTraps  OBJECT-TYPE
    SYNTAX  EnabledDisabled
    ACCESS  read-write
    STATUS  mandatory
    DESCRIPTION
    "This NE wide variable is used to control if the NE reports standard
    linkUp and linkDown traps. When the value equals to enabled, the 
    NE shall report these standard traps, and when disabled, these 
    standard traps shall not be emitted.
    The default value for this variable is disabled."
::= {caVars 2}

--=============================================================
-- Variables carried in the Nokia Common Alarm Traps
-- ca == Common Alarm
--=============================================================

caAlarmText  OBJECT-TYPE
    SYNTAX  DisplayString (SIZE (0..64))
    ACCESS  read-only
    STATUS  mandatory
    DESCRIPTION
    "Alarm text of the last Nokia enterprise specific alarm 
    trap emitted by the NE. This is textual description shown e.g. on user 
    interface of NMS. The contents of this text shall not be processed in 
    any way by NMS. In case of not supporting this variable, empty string shall 
    be used.

    When this object is accessed using GET operation, this object shall contain
    the value of the corresponding variable in the last regularly sent alarm 
    trap i.e. in cases of re-sending an alarm trap as a result of NMS 
    operation (ie. via alResendTrapId object), this object shall not be 
    updated."
::= {caVars 3}

caTrapId OBJECT-TYPE
    SYNTAX  INTEGER (0..'7fffffff'h)
    ACCESS  read-only
    STATUS  mandatory
    DESCRIPTION
    "caTrapId of the last Nokia enterprise specific alarm trap 
    emitted by the NE. 
    caTrapId shall be incremented by one in each trap sent by NE to a NMS. When
    caTrapId achieves the maximum value, the variable shall wrap back to
    value 1 when sending the next trap. If NE has several trap destinations 
    the same caTrapId shall be used when a trap is sent to them all.
    caTrapId is used by NMS to detect if traps are lost in DCN. In case of not 
    supporting this variable (though this is not recommended), value 0 shall 
    be used.

    When this object is accessed using GET operation, this object shall contain
    the value of the corresponding variable in the last regularly sent alarm 
    trap i.e. in cases of re-sending an alarm trap as a result of NMS 
    operation (ie. via alResendTrapId object), this object shall not be 
    updated."
::= {caVars 4}

caCorrelatedAlarmId OBJECT-TYPE
    SYNTAX  INTEGER
    ACCESS  read-only
    STATUS  mandatory
    DESCRIPTION
    "This variable shall be supported by an NE product if support for 
    real-time current alarm list in NMS is expected. When supported, 
    the value of this variable in alarm clearing trap shall equal to 
    the value of this variable in the corresponding alarm trap. In 
    alarm traps, the value of this variable shall equal to the value of 
    the caAlarmIndex of the corresponding alarm entry in the 
    caCurrentAlarmListTable (both in case of alarm and alarm clearing 
    traps). When this variable has value 0, it means that no alarm 
    correlation is present and that the NMS should not assume alarm 
    correlation support from NE concerning the corresponding alarm. 
    This means that either alarm clearing trap will not be sent by NE or 
    if alarm clearing trap will be sent by NE, it does not support 
    correlation to the corresponding alarm trap.

    When this object is accessed using GET operation, this object shall contain
    the value of the corresponding variable in the last regularly sent alarm 
    trap i.e. in cases of re-sending an alarm trap as a result of NMS 
    operation (ie. via alResendTrapId object), this object shall not be 
    updated."
::= {caVars 5}

caColumnInTbl OBJECT-TYPE
    SYNTAX  RowPointer
    ACCESS  read-only
    STATUS  mandatory
    DESCRIPTION 
    "The value of caColumnInTbl field of the last Nokia 
    enterprise specific alarm trap emitted by the NE. The value is the
    name of the instance of the first accessible columnar object
    in the conceptual row, which represents the failed resource.

    In case of not supporting this variable, value {0 0} shall be used.

    When this object is accessed using GET operation, this object shall contain
    the value of the corresponding variable in the last regularly sent alarm 
    trap i.e. in cases of re-sending an alarm trap as a result of NMS 
    operation (ie. via alResendTrapId object), this object shall not be 
    updated."
::= {caVars 6}

caRowIdx OBJECT-TYPE
    SYNTAX  OBJECT IDENTIFIER --ObjectName
    ACCESS  read-only
    STATUS  mandatory
    DESCRIPTION
    "This variable contains value {0 0} for the time being.

    When this object is accessed using GET operation, this object shall contain
    the value of the corresponding variable in the last regularly sent alarm 
    trap i.e. in cases of re-sending an alarm trap as a result of NMS 
    operation (ie. via alResendTrapId object), this object shall not be 
    updated."
::= {caVars 7}

caSeverity OBJECT-TYPE
    SYNTAX  AlarmSeverity
    ACCESS  read-only
    STATUS  mandatory
    DESCRIPTION
    "Severity of the last Nokia enterprise specific alarm trap 
    emitted by the NE.

    When this object is accessed using GET operation, this object shall contain
    the value of the corresponding variable in the last regularly sent alarm 
    trap i.e. in cases of re-sending an alarm trap as a result of NMS 
    operation (ie. via alResendTrapId object), this object shall not be 
    updated."
::= {caVars 8}

caNESpecificAlarmManualPageNbr OBJECT-TYPE
    SYNTAX  INTEGER
    ACCESS  read-only
    STATUS  mandatory
    DESCRIPTION
    "caNESpecificAlarmManualPageNbr of the last Nokia enterprise 
    specific alarm trap emitted by the NE. The value is the alarm manual page
    number (usually NE type specific alarm code) containing more information 
    for the operator how to recover from the problem. The value of this 
    variable uniquely idenfies an alarm manual page of the given type of NE. 
    In case of not supporting this variable, value 0 shall be used.

    When this object is accessed using GET operation, this object shall contain
    the value of the corresponding variable in the last regularly sent alarm 
    trap i.e. in cases of re-sending an alarm trap as a result of NMS 
    operation (ie. via alResendTrapId object), this object shall not be 
    updated."
::= {caVars 9}

caSupplementaryInfo OBJECT-TYPE
    SYNTAX  OCTET STRING(SIZE (0..64))
    ACCESS  read-only
    STATUS  mandatory
    DESCRIPTION
    "Supplementary information fields of the last Nokia enterprise
    specific alarm trap emitted by the NE. Alarm manual page contains
    the explanation of supplementary information fields. With these
    fields operator may get e.g. more detailed instructions to recover
    from the problem. When no information is carried in this variable,
    the contents is an empty string (i.e. length of the OCTET STRING 
    shall be 0.

    When this object is accessed using GET operation, this object shall contain
    the value of the corresponding variable in the last regularly sent alarm 
    trap i.e. in cases of re-sending an alarm trap as a result of NMS 
    operation (ie. via alResendTrapId object), this object shall not be 
    updated."
::= {caVars 10}

--=============================================================
-- Variables and Tables for Current Alarm List
-- cal == Current Alarm List
--=============================================================

calActiveAlarmCount  OBJECT-TYPE
    SYNTAX  INTEGER
    ACCESS  read-only
    STATUS  mandatory
    DESCRIPTION
    "This variable contains the number of currently active alarms in the NE. 
    When the Current Alarm List is empty, the value of this variable is 0."
::= {calVars 1}

calContentsChangeTime  OBJECT-TYPE
    SYNTAX  TimeTicks
    ACCESS  read-only
    STATUS  mandatory
    DESCRIPTION
    "This variable contains the value of sysUpTime (i.e. time stamp in 
    time ticks) when the contents of CAL was changed last time. In the 
    startup of the NE the initial value of this variable shall be 0."
::= {calVars 2}

calCurrentAlarmListTable OBJECT-TYPE
    SYNTAX  SEQUENCE OF CalCurrentAlarmListEntry
    ACCESS  not-accessible
    STATUS  mandatory
    DESCRIPTION
    "This table contains information on the all currently active alarms in 
    the agent. There shall be one entry in this table for each active alarm."
::= {calTables 1}

calCurrentAlarmListEntry OBJECT-TYPE
    SYNTAX  CalCurrentAlarmListEntry
    ACCESS  not-accessible
    STATUS  mandatory
    DESCRIPTION
    "This contains detailed information concerning each currently active
    alarm in the agent."
    INDEX   {calAlarmIndex}
::= {calCurrentAlarmListTable 1}

CalCurrentAlarmListEntry ::=
    SEQUENCE {
        calAlarmIndex
            INTEGER,
        calSpecificTrap
            INTEGER,
        calTimeStamp
            TimeTicks,
        calAlarmText
            DisplayString,
        calFirstColumnInTbl
            RowPointer,
        calRowIdx
            OBJECT IDENTIFIER,
        calSeverity
            AlarmSeverity,
        calNESpecificAMPNbr
            INTEGER,
        calSupplementaryInfo
            OCTET STRING
         }

calAlarmIndex OBJECT-TYPE
    SYNTAX  INTEGER (1..'7fffffff'h)
    ACCESS  read-only
    STATUS  mandatory
    DESCRIPTION
    "Used as an index of the table. The value of this variable shall be 
    incremented by 1 for each new entry of this table. When alarm correlation 
    capability is supported by the NE, the value of this variable equals to 
    the value of correlatedAlarmId in the corresponding alarm and alarm 
    clearing traps."
::= {calCurrentAlarmListEntry 1}

calSpecificTrap OBJECT-TYPE
    SYNTAX  INTEGER (1..'7fffffff'h)
    ACCESS  read-only
    STATUS  mandatory
    DESCRIPTION
    "The value equals to the value of the specific-trap field in the 
    corresponding Nokia enterprise specific alarm trap."
::= {calCurrentAlarmListEntry 2}

calTimeStamp OBJECT-TYPE
    SYNTAX  TimeTicks
    ACCESS  read-only
    STATUS  mandatory
    DESCRIPTION
    "The value equals to the time stamp as reported in the corresponding 
    Nokia enterprise specific trap. The value of this field shall equal to 
    the value of time-stamp field in the alarm trap which reported this 
    alarm."
::= {calCurrentAlarmListEntry 3}

calAlarmText OBJECT-TYPE
    SYNTAX  DisplayString (SIZE (0..64))
    ACCESS  read-only
    STATUS  mandatory
    DESCRIPTION
    "This variable contains alarm information in human readable format to 
    be shown e.g. in NMS UI. No processing of the contents of this alarm 
    text are assumed within NMS. The maximum length of the alarm text 
    shall be 64 characters."
::= {calCurrentAlarmListEntry 4}

calFirstColumnInTbl OBJECT-TYPE
    SYNTAX  RowPointer
    ACCESS  read-only
    STATUS  mandatory
    DESCRIPTION
    "This variable is used to reference to an conceptual row which represents
    the failed resource (see caColumnInTbl for further details).
    
    In case of not supporting this variable, value {0 0} shall be used."
::= {calCurrentAlarmListEntry 5}

calRowIdx OBJECT-TYPE
    SYNTAX  OBJECT IDENTIFIER
    ACCESS  read-only
    STATUS  mandatory
    DESCRIPTION
    "This variable contains value {0 0} for the time being."
::= {calCurrentAlarmListEntry 6}

calSeverity OBJECT-TYPE
    SYNTAX  AlarmSeverity
    ACCESS  read-only
    STATUS  mandatory
    DESCRIPTION
    "This variable contains the severity of the detected failure as 
    reported by the NE."
::= {calCurrentAlarmListEntry 7}

calNESpecificAMPNbr OBJECT-TYPE
    SYNTAX  INTEGER
    ACCESS  read-only
    STATUS  mandatory
    DESCRIPTION
    "This variable contains the NE type specific value unique within the 
    context of the NE type, and used to identify which alarm manual page 
    shall be shown to the user. Alarm manual page is additional information 
    to be provided to the user to give guidance what are the possible 
    reasons of the alarm, how the user can recover from the problem etc. 
    This information is like one or more pages in the NE products reference 
    manual describing the possible alarm reported by the NE and reasons of 
    the alarms. Each NE product is responsible for keeping these values 
    unique within the context of their product and provide the contents 
    of user manual pages. When supporting this variable, only positive 
    values are allowed. When this variable has value 0, it means that no 
    alarm manual page is associated to the alarm or this field is not 
    supported by the NE."
::= {calCurrentAlarmListEntry 8}

calSupplementaryInfo OBJECT-TYPE
    SYNTAX  OCTET STRING(SIZE (0..64))
    ACCESS  read-only
    STATUS  mandatory
    DESCRIPTION
    "Supplementary information fields of the last Nokia enterprise
    specific alarm trap emitted by the NE. Alarm manual page contains
    the explanation of supplementary information fields. With these
    fields operator may get e.g. more detailed instructions to recover
    from the problem. When no information is carried in this variable,
    the contents is an empty string (i.e. length of the OCTET STRING 
    shall be 0)."
::= {calCurrentAlarmListEntry 9}

--=============================================================
-- Variables and Tables for Alarm Log
-- al == Alarm Log
--=============================================================

alAlarmLogEntryCount  OBJECT-TYPE
    SYNTAX  INTEGER
    ACCESS  read-only
    STATUS  mandatory
    DESCRIPTION 
    "This variable equals to the number of entries in the Alarm Log. 
    When the log is empty, this variable is 0."
::= {alVars 1}

alAlarmLogMaxSize  OBJECT-TYPE
    SYNTAX  INTEGER
    ACCESS  read-write
    STATUS  mandatory
    DESCRIPTION 
    "This variable contains the number of entries the alarm log shall 
    contain. The current number of entries in the Alarm Log 
    (alAlarmLogEntryCount) may be equal of less than the value of this 
    variable. If Alarm Log is not supported, the value of this variable 
    shall be 0."
::= {alVars 2}

alLogFullAction  OBJECT-TYPE
    SYNTAX  INTEGER
    ACCESS  read-write
    STATUS  mandatory
    DESCRIPTION 
    "This variable control the behaviour of the log when the log shall 
    become full. Possible values are wrap (1) and halt (2). The default value 
    shall be wrap.
    Note that this variable does not affect to the behaviour of trap ids used
    in alarm traps. I.e. when log is in halt mode, trap ids are incremented
    by 1 in each trap emitted by the NE."
::= {alVars 3}

alResendTrapDestinationAddr  OBJECT-TYPE
    SYNTAX  NetworkAddress
    ACCESS  read-write
    STATUS  mandatory
    DESCRIPTION 
    "This variable contains the IP address of the destination to which 
    the trap shall be sent, when the manager sets the value of 
    alResendTrapId."
::= {alVars 4}

alResendTrapDestinationPort  OBJECT-TYPE
    SYNTAX  INTEGER (0..65535)
    ACCESS  read-write
    STATUS  mandatory
    DESCRIPTION 
    "This variable contains the port number of the destination to 
    which the trap shall be sent, when the manager sets the value 
    of alResendTrapId. Initially the value of this variable shall be 
    the standard port allocated for SNMP traps i.e. 162."
::= {alVars 5}

alResendTrapId  OBJECT-TYPE
    SYNTAX  INTEGER
    ACCESS  read-write
    STATUS  mandatory
    DESCRIPTION 
    "This variable contains value of the caTrapId of the last successfully 
    resent alarm trap. Initially this variable has value 0. When NMS sets 
    this variable, the NE shall resend the alarm trap whose caTrapId equals 
    to the value provided by NMS, if the corresponding alarm trap is still 
    available in the internal alarm log in NE (e.g. the corresponding log 
    entry has not yet been lost in the alarm log because of wrapping). If 
    this operation fails, the value of this variable is not changed to the 
    value provided by NMS.
    Note that in addition to this variable, NMS has to set the values of 
    alResendTrapDestinationAddr and alResendTrapDestinationPort to the 
    correct value so that the traps shall be sent to the correct 
    destination. It is preferred that the NMS sets these three variables 
    in the single SNMP SET message in order this operation to be atomic. 
    In these cases the NE must guarantee that the 
    alResendTrapDestinationAddr and alResendTrapDestinationPort are 
    logically set to given values before the value of alResendTrapId is 
    set (This is because at the moment of setting the value of 
    alResendTrapId to the value given by NMS the trap shall be issued to 
    the destination address/port found in variables 
    alResendTrapDestinationAddr and alResendTrapDestinationPort).
    The value of community string shall be known by NE based on the 
    contents of trap destination MIB."
::= {alVars 6}

alAlarmLogTable OBJECT-TYPE
    SYNTAX  SEQUENCE OF AlAlarmLogEntry
    ACCESS  not-accessible
    STATUS  mandatory
    DESCRIPTION
    "This table contains information on the all logged alarm or alarm 
    clearing traps in the agent. There shall be one entry in this table 
    for each logged alarm or alarm clearing trap."
::= {alTables 1}

alAlarmLogEntry OBJECT-TYPE
    SYNTAX  AlAlarmLogEntry
    ACCESS  not-accessible
    STATUS  mandatory
    DESCRIPTION
    "This contains detailed information concerning each logged alarm entry
    in the agent."
    INDEX   {alTrapIndex}
::= {alAlarmLogTable 1}

AlAlarmLogEntry ::=
    SEQUENCE {
        alTrapIndex
            INTEGER,
        alSpecificTrap
            INTEGER,
        alTimeStamp
            TimeTicks,
        alAlarmText
            DisplayString,
        alCorrelatedAlarmId
            INTEGER,
        alFirstColumnInTbl
            RowPointer,
        alRowIdx
            OBJECT IDENTIFIER,
        alSeverity
            AlarmSeverity,
        alNESpecificAMPNbr
            INTEGER,
        alSupplementaryInfo
            OCTET STRING
         }

alTrapIndex OBJECT-TYPE
    SYNTAX  INTEGER (1..'7fffffff'h)
    ACCESS  read-only
    STATUS  mandatory
    DESCRIPTION
    "Used as an index of the table. The value of this variable equals to 
    variable caTrapId in the corresponding alarm trap."
::= {alAlarmLogEntry 1}

alSpecificTrap OBJECT-TYPE
    SYNTAX  INTEGER (1..'7fffffff'h)
    ACCESS  read-only
    STATUS  mandatory
    DESCRIPTION
    "The value equals to the value of the specific-trap field in the 
    corresponding Nokia enterprise specific alarm trap."
::= {alAlarmLogEntry 2}

alTimeStamp OBJECT-TYPE
    SYNTAX  TimeTicks
    ACCESS  read-only
    STATUS  mandatory
    DESCRIPTION
    "The value equals to the time stamp as reported in the corresponding 
    Nokia enterprise specific trap. The value of this field shall equal to 
    the value of time-stamp field in the alarm trap which reported this 
    alarm."
::= {alAlarmLogEntry 3}

alAlarmText OBJECT-TYPE
    SYNTAX  DisplayString (SIZE (0..64))
    ACCESS  read-only
    STATUS  mandatory
    DESCRIPTION
    "This variable contains alarm information in human readable format to 
    be shown e.g. in NMS UI. No processing of the contents of this alarm 
    text are assumed within NMS. The maximum length of the alarm text 
    shall be 64 characters."
::= {alAlarmLogEntry 4}

alCorrelatedAlarmId OBJECT-TYPE
    SYNTAX  INTEGER
    ACCESS  read-only
    STATUS  mandatory
    DESCRIPTION
    "The value of this variable equals to the value of corresponding field 
    in alarm and alarm clearing trap (caCorrelatedAlarmId). When this 
    variable has value 0, it means that no alarm correlation is present 
    and that the NMS should not assume alarm correlation support from NE 
    concerning the corresponding alarm. This means that either alarm 
    clearing trap will not be sent by NE or if alarm clearing trap will be 
    sent by NE, it does not support correlation to the corresponding alarm 
    trap."
::= {alAlarmLogEntry 5}

alFirstColumnInTbl OBJECT-TYPE
    SYNTAX  RowPointer
    ACCESS  read-only
    STATUS  mandatory
    DESCRIPTION
    "This variable is used to reference to an conceptual row which represents
    the failed resource (see caColumnInTbl for further details).
    
    In case of not supporting this variable, value {0 0} shall be used."
::= {alAlarmLogEntry 6}

alRowIdx OBJECT-TYPE
    SYNTAX  OBJECT IDENTIFIER
    ACCESS  read-only
    STATUS  mandatory
    DESCRIPTION
    "This variable contains value {0 0} for the time being."
::= {alAlarmLogEntry 7}

alSeverity OBJECT-TYPE
    SYNTAX  AlarmSeverity
    ACCESS  read-only
    STATUS  mandatory
    DESCRIPTION
    "This variable contains the severity of the detected failure as 
    reported by the NE."
::= {alAlarmLogEntry 8}

alNESpecificAMPNbr OBJECT-TYPE
    SYNTAX  INTEGER
    ACCESS  read-only
    STATUS  mandatory
    DESCRIPTION
    "This variable contains the NE type specific value unique within the 
    context of the NE type, and used to identify which alarm manual page 
    shall be shown to the user. Alarm manual page is additional information 
    to be provided to the user to give guidance what are the possible 
    reasons of the alarm, how the user can recover from the problem etc. 
    This information is like one or more pages in the NE products reference 
    manual describing the possible alarm reported by the NE and reasons of 
    the alarms. Each NE product is responsible for keeping these values 
    unique within the context of their product and provide the contents 
    of user manual pages. When supporting this variable, only positive 
    values are allowed. When this variable has value 0, it means that no 
    alarm manual page is associated to the alarm or this field is not 
    supported by the NE."
::= {alAlarmLogEntry 9}

alSupplementaryInfo OBJECT-TYPE
    SYNTAX  OCTET STRING(SIZE (0..64))
    ACCESS  read-only
    STATUS  mandatory
    DESCRIPTION
    "Supplementary information fields of the last Nokia enterprise
    specific alarm trap emitted by the NE. Alarm manual page contains
    the explanation of supplementary information fields. With these
    fields operator may get e.g. more detailed instructions to recover
    from the problem. When no information is carried in this variable,
    the contents is an empty string (i.e. length of the OCTET STRING 
    shall be 0)."
::= {alAlarmLogEntry 10}

END
