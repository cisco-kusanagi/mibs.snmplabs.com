-- 
-- file :fcd_a.pkb
-- 
DACS-MIB

			DEFINITIONS ::= BEGIN

--Title:     DACS   MIB
--
-- Copyright 1993 RAD Data Communications, Ltd.
-- All Rights Reserved.  

-- It is RAD's intent to encourage the widespread use of
-- this Specification in connection with the management of
-- RAD products. RAD grants vendors, end-users,
-- and other interested parties a non-exclusive license to
-- use this Specification in connection with the management
-- of RAD products.

-- This Specification is supplied "as is," and RAD makes
-- no warranty, either express or implied, as to the use,
-- operation, condition, or performance of the Specification.

IMPORTS
      Counter, TimeTicks,enterprises, Gauge,
      NetworkAddress, IpAddress       FROM RFC1155-SMI
      DisplayString                   FROM RFC1213-MIB
      OBJECT-TYPE                     FROM RFC-1212
      TRAP-TYPE                       FROM RFC-1215;


-- Some MIB compilers need those two lines:
-- enterprises OBJECT IDENTIFIER ::=
--		     { iso org(3) dod(6) internet(1) private(4) 1 }

MacAddress ::= OCTET STRING (SIZE(6))

rad           OBJECT IDENTIFIER ::= { enterprises 164 }
radTokenRing  OBJECT IDENTIFIER ::= { rad 1 } -- RAD Token Ring tree
radFddi       OBJECT IDENTIFIER ::= { rad 2 } -- rad FDDI Tree
radWan        OBJECT IDENTIFIER ::= { rad 3 } -- rad WAN Tree
radBridges    OBJECT IDENTIFIER ::= { rad 4 }
radConverters OBJECT IDENTIFIER ::= { rad 5 } -- RAD Converters products' tree
radGen        OBJECT IDENTIFIER ::= { rad 6 } -- General information
radStkHub     OBJECT IDENTIFIER ::= { rad 7 } -- stackable products

--wanGen        OBJECT IDENTIFIER ::= {radWan 1}
--muxHub        OBJECT IDENTIFIER ::= {radWan 2}


--agnWanGen     OBJECT IDENTIFIER ::= {wanGen 2}
--mdlWanGen     OBJECT IDENTIFIER ::= {wanGen 3}
--prtWanGen     OBJECT IDENTIFIER ::= {wanGen 4}

--cnfgAgnGen    OBJECT IDENTIFIER ::= {agnWanGen 2}
--agnSystemTs   OBJECT IDENTIFIER ::= {agnWanGen 11}

--statMdlGen    OBJECT IDENTIFIER ::= {mdlWanGen 1}
--cnfgMdlGen    OBJECT IDENTIFIER ::= {mdlWanGen 2}

--statPrtGen    OBJECT IDENTIFIER ::= {prtWanGen 1}


--prtMux        OBJECT IDENTIFIER ::= {muxHub 3}

--cnfgPrtMux    OBJECT IDENTIFIER ::= {prtMux 2}


-- 
-- file :v:\doc\rdv\mib\ver450\radgen.txt
-- 

--Version:   4.50
--First Version Date:   25.01.99              
--By:        Orly Nicklass
--File:      radgen.txt

--Last Update: 23-09-99 by Liora Gafni


systems OBJECT IDENTIFIER ::= { radGen 1}  --    list of RAD products

radSysTR  OBJECT IDENTIFIER ::= { systems 1 } -- RAD Token Ring 

radRADring    OBJECT IDENTIFIER  ::= { radSysTR  1 }

radTMA  OBJECT IDENTIFIER  ::= { radSysTR  2 }

radRingMonitor    OBJECT IDENTIFIER  ::= { radSysTR  3 }

radSysFddi OBJECT IDENTIFIER ::= { systems 2 } -- RAD Fddi 

radFDX100  OBJECT IDENTIFIER ::= { radSysFddi  1 } -- RAD Fddi
 
radSysWan OBJECT IDENTIFIER ::= { systems 3 }  -- RAD Wan products

radMP2100      OBJECT IDENTIFIER ::= { radSysWan  1 }
radMP2104      OBJECT IDENTIFIER ::= { radSysWan  2 }
radMP2100B     OBJECT IDENTIFIER ::= { radSysWan  3 }
radMP2100F     OBJECT IDENTIFIER ::= { radSysWan  4 }

radMP2100H      OBJECT IDENTIFIER ::= { radSysWan  5 }
radMP2104H      OBJECT IDENTIFIER ::= { radSysWan  6 }
radMP2200B      OBJECT IDENTIFIER ::= { radSysWan  7 }
radMP2200F      OBJECT IDENTIFIER ::= { radSysWan  8 }

radMX3000       OBJECT IDENTIFIER ::= { radSysWan  9 }
radMX3004       OBJECT IDENTIFIER ::= { radSysWan 10 }
radMX30			OBJECT IDENTIFIER ::= { radSysWan 11 }
radMX300		OBJECT IDENTIFIER ::= { radSysWan 12 }

radVOIP         OBJECT IDENTIFIER ::= { radSysWan 13 }

radKM2100	    OBJECT IDENTIFIER ::= { radSysWan 15 }
radKM2104		OBJECT IDENTIFIER ::= { radSysWan 16 }

radDXC30        OBJECT IDENTIFIER ::= { radSysWan 20 }
radDXC10A       OBJECT IDENTIFIER ::= { radSysWan 21 }
radDXC8R        OBJECT IDENTIFIER ::= { radSysWan 22 }
radDXC30E       OBJECT IDENTIFIER ::= { radSysWan 23 }

radFcdT1         OBJECT IDENTIFIER ::= { radSysWan 30 }
radFcdE1         OBJECT IDENTIFIER ::= { radSysWan 31 }
radFcdE1I        OBJECT IDENTIFIER ::= { radSysWan 32 }
radFcdT1M        OBJECT IDENTIFIER ::= { radSysWan 33 }
radFcdE1M        OBJECT IDENTIFIER ::= { radSysWan 34 }
radFcdIP         OBJECT IDENTIFIER ::= { radSysWan 35} 
radFcdT1A        OBJECT IDENTIFIER ::= { radSysWan 36 }
radFcdE1A        OBJECT IDENTIFIER ::= { radSysWan 37 }
radFcdW          OBJECT IDENTIFIER ::= { radSysWan 38 }

radHtuE1Sa      OBJECT IDENTIFIER ::= { radSysWan 40 }
radHtuE1        OBJECT IDENTIFIER ::= { radSysWan 41 }	 --card
radHtu2Sa       OBJECT IDENTIFIER ::= { radSysWan 42 }
radHtu2         OBJECT IDENTIFIER ::= { radSysWan 43 }	 --card
radAsmi450R768Sa OBJECT IDENTIFIER ::= { radSysWan 44 }
radAsmi450R768  OBJECT IDENTIFIER ::= { radSysWan 45 }	 --card
radAsmi450R1152Sa  OBJECT IDENTIFIER ::= { radSysWan 46 }
radAsmi450R1152 OBJECT IDENTIFIER ::= { radSysWan 47 }	 --card

radLrs12F        OBJECT IDENTIFIER ::= { radSysWan 48 }
radLrs12B        OBJECT IDENTIFIER ::= { radSysWan 49 }

radHcdE1Sa       OBJECT IDENTIFIER ::= { radSysWan 51 }
radHcdE1         OBJECT IDENTIFIER ::= { radSysWan 52 }  --card
radHtuT1Sa       OBJECT IDENTIFIER ::= { radSysWan 53 }
radHtuT1         OBJECT IDENTIFIER ::= { radSysWan 54 }	 --card

radOptimux4E1         OBJECT IDENTIFIER ::= { radSysWan 55 }
radOptimux4T1         OBJECT IDENTIFIER ::= { radSysWan 56 }
radOptimuxXLE1         OBJECT IDENTIFIER ::= { radSysWan 57 }
radOptimuxXLT1         OBJECT IDENTIFIER ::= { radSysWan 58 }
radOptimuxXL16E1       OBJECT IDENTIFIER ::= { radSysWan 59 }

radImx64        OBJECT IDENTIFIER ::= { radSysWan 60 }
radImx6L        OBJECT IDENTIFIER ::= { radSysWan 61 }
radImx2         OBJECT IDENTIFIER ::= { radSysWan 62 }
radImx4T1       OBJECT IDENTIFIER ::= { radSysWan 63 }
radImx4E1       OBJECT IDENTIFIER ::= { radSysWan 64 }
radImx2T1E1     OBJECT IDENTIFIER ::= { radSysWan 65 }


radHtuE1SaV2      OBJECT IDENTIFIER ::= { radSysWan 70 }
radHtuE1V2        OBJECT IDENTIFIER ::= { radSysWan 71 }  --card
radFomiE3         OBJECT IDENTIFIER ::= { radSysWan 72 }  --card
radFomiT3         OBJECT IDENTIFIER ::= { radSysWan 73 }  --card
radOpt4E1C        OBJECT IDENTIFIER ::= { radSysWan 74 }  --card
radOpt4T1C        OBJECT IDENTIFIER ::= { radSysWan 75 }  --card
radPrbiE3         OBJECT IDENTIFIER ::= { radSysWan 76 }  --SA
radPrbiT3         OBJECT IDENTIFIER ::= { radSysWan 77 }  --SA
radHcd4Sa         OBJECT IDENTIFIER ::= { radSysWan 78 }  --SA

radFRmon          OBJECT IDENTIFIER ::= { radSysWan 80 } 


radSysBRG OBJECT IDENTIFIER ::= { systems 4 }  -- RAD Bridges products

radTRE1  OBJECT IDENTIFIER ::= { radSysBRG 1 }  -- RAD Bridges products

radTRE1D  OBJECT IDENTIFIER ::= { radSysBRG 2 }  -- RAD Bridges products

radTRE8  OBJECT IDENTIFIER ::= { radSysBRG 3 }  -- RAD Bridges products

radTRE8D  OBJECT IDENTIFIER ::= { radSysBRG 4 }  -- RAD Bridges products

radMBE1  OBJECT IDENTIFIER ::= { radSysBRG 5 }  -- RAD Bridges products

radMBE1D  OBJECT IDENTIFIER ::= { radSysBRG  6 }  -- RAD Bridges products

radMBE8  OBJECT IDENTIFIER ::= { radSysBRG  7 }  -- RAD Bridges products

radMBE8D  OBJECT IDENTIFIER ::= { radSysBRG  8 }  -- RAD Bridges products

radMLBT   OBJECT IDENTIFIER ::= { radSysBRG  9 }  -- RAD Bridges products 

radFEB4DAS    OBJECT IDENTIFIER ::= { radSysBRG  10 }  -- RAD Bridges products

radTrimBrg10  OBJECT IDENTIFIER ::= { radSysBRG 11 }  -- RAD Bridges products

radTrimBrg16  OBJECT IDENTIFIER ::= { radSysBRG 12 }  -- RAD Bridges products

radRRTRE8  OBJECT IDENTIFIER ::= { radSysBRG 13 }  -- RAD Bridges products

radRRTRE8D  OBJECT IDENTIFIER ::= { radSysBRG 14 }  -- RAD Bridges products

radRRMLBT   OBJECT IDENTIFIER ::= { radSysBRG 15 }  -- RAD Bridges products 

radRRMLBTF   OBJECT IDENTIFIER ::= { radSysBRG 16 }  -- RAD Bridges products 

radRRTRE1D  OBJECT IDENTIFIER ::= { radSysBRG 17 }  -- RAD Bridges products

radTRERAS  OBJECT IDENTIFIER ::= { radSysBRG 18 }  -- RAD Bridges products

radTRERASa  OBJECT IDENTIFIER ::= { radSysBRG 19 }  -- RAD Bridges products

radMBERAS  OBJECT IDENTIFIER ::= { radSysBRG 20 }  -- RAD Bridges products

radMBERASa  OBJECT IDENTIFIER ::= { radSysBRG 21 }  -- RAD Bridges products
 
radFEB4FDX   OBJECT IDENTIFIER ::= { radSysBRG 22 }  -- RAD Bridges products

radFEB4SAS  OBJECT IDENTIFIER ::= { radSysBRG 23 }  -- RAD Bridges products

radRRFTBDAS  OBJECT IDENTIFIER ::= { radSysBRG 24 }  -- RAD Bridges products

radRRFTBSAS  OBJECT IDENTIFIER ::= { radSysBRG 25 }  -- RAD Bridges products

radFTBDAS    OBJECT IDENTIFIER ::= { radSysBRG 26 }  -- RAD Bridges products

radFTBSAS    OBJECT IDENTIFIER ::= { radSysBRG 27 }  -- RAD Bridges products

radFastWay100    OBJECT IDENTIFIER ::= { radSysBRG 28 }  -- RAD Bridges products

radSysCnvrtr OBJECT IDENTIFIER ::= { systems 5 }  -- RAD Converters products

radSTC1   OBJECT IDENTIFIER ::= { radSysCnvrtr 1 }  -- RAD Converters products

radSTC2   OBJECT IDENTIFIER ::= { radSysCnvrtr 3 }  -- RAD Converters products

radSTC1UDP  OBJECT IDENTIFIER ::= { radSysCnvrtr 4 }  -- RAD Converters products

radSTC2UDP  OBJECT IDENTIFIER ::= { radSysCnvrtr 6 }  -- RAD Converters products

radFTC1   OBJECT IDENTIFIER ::= { radSysCnvrtr 10 }  -- RAD Converters products

radFTC2   OBJECT IDENTIFIER ::= { radSysCnvrtr 12 }  -- RAD Converters products

radFTC1UDP    OBJECT IDENTIFIER ::= { radSysCnvrtr 13 }  -- RAD Converters products

radFTC2UDP    OBJECT IDENTIFIER ::= { radSysCnvrtr 15 }  -- RAD Converters products

radSEC1   OBJECT IDENTIFIER ::= { radSysCnvrtr 20 }  -- RAD Converters products

radSEC2   OBJECT IDENTIFIER ::= { radSysCnvrtr 22 }  -- RAD Converters products

radSEC1UDP   OBJECT IDENTIFIER ::= { radSysCnvrtr 23 }  -- RAD Converters products

radSEC2UDP   OBJECT IDENTIFIER ::= { radSysCnvrtr 25 }  -- RAD Converters products

radFEC1   OBJECT IDENTIFIER ::= { radSysCnvrtr 30 }  -- RAD Converters products

radFEC2   OBJECT IDENTIFIER ::= { radSysCnvrtr 32 }  -- RAD Converters products

radFEC1UDP   OBJECT IDENTIFIER ::= { radSysCnvrtr 33 }  -- RAD Converters products

radFEC2UDP   OBJECT IDENTIFIER ::= { radSysCnvrtr 35 }  -- RAD Converters products

radSysStkHub  OBJECT IDENTIFIER ::= { systems 7 }  -- RAD Stackable products

radRBHE    OBJECT IDENTIFIER ::= { radSysStkHub 1 }  -- RAD Stackable products

radRBHT    OBJECT IDENTIFIER ::= { radSysStkHub 2 }  -- RAD Stackable products

radETS4fddiDAS   OBJECT IDENTIFIER ::= { radSysStkHub 3 }  -- RAD Stackable products

radETS4fddiSAS   OBJECT IDENTIFIER ::= { radSysStkHub 4 }  -- RAD Stackable products

radSAHEMX  OBJECT IDENTIFIER ::= { radSysStkHub 5 }  -- RAD Stackable products

radSAHTM   OBJECT IDENTIFIER ::= { radSysStkHub 6 }  -- RAD Stackable products

radETS4   OBJECT IDENTIFIER ::= { radSysStkHub 7 }  -- RAD Stackable products

radSAHEMU  OBJECT IDENTIFIER ::= { radSysStkHub 8 }  -- RAD Stackable products


unknown    	OBJECT IDENTIFIER ::= { radSysStkHub 9 }  -- RAD Stackable products

radSAH16Eint   OBJECT IDENTIFIER ::= { radSysStkHub 10 }  -- RAD Stackable products

radSAH16Tint   OBJECT IDENTIFIER ::= { radSysStkHub 11 }  -- RAD Stackable products

radSAH16Eext   OBJECT IDENTIFIER ::= { radSysStkHub 12 }  -- RAD Stackable products

radSAH16Text   OBJECT IDENTIFIER ::= { radSysStkHub 13 }  -- RAD Stackable products



radSysPS OBJECT IDENTIFIER ::=  { systems 8 } -- RAD Packet Switch  (PS) products 

radSPS2  OBJECT IDENTIFIER ::=  { radSysPS 1 } -- RAD Packet Switch  (PS) products 

radSPS3  OBJECT IDENTIFIER ::=  { radSysPS 2 } -- RAD Packet Switch  (PS) products 

radSPS6  OBJECT IDENTIFIER ::=  { radSysPS 3 } -- RAD Packet Switch  (PS) products 

radSPS9  OBJECT IDENTIFIER ::=  { radSysPS 4 } -- RAD Packet Switch  (PS) products 

radSPS12 OBJECT IDENTIFIER ::=  { radSysPS 5 } -- RAD Packet Switch  (PS) products 

radAPD2  OBJECT IDENTIFIER ::=  { radSysPS 6 } -- RAD Packet Switch  (PS) products 

radAPD8  OBJECT IDENTIFIER ::=  { radSysPS 7 } -- RAD Packet Switch  (PS) products 

radAPS8  OBJECT IDENTIFIER ::=  { radSysPS 8 } -- RAD Packet Switch  (PS) products 

radAPS16 OBJECT IDENTIFIER ::=  { radSysPS 9 } -- RAD Packet Switch  (PS) products 

radAPS24 OBJECT IDENTIFIER ::=  { radSysPS 10 } -- RAD Packet Switch  (PS) products 

radSPS3S  OBJECT IDENTIFIER ::=  { radSysPS 11} -- RAD Packet Switch  (PS) products 

radFPS8  OBJECT IDENTIFIER ::=  { radSysPS 12} -- RAD Packet Switch  (PS) products 

radFPS12  OBJECT IDENTIFIER ::=  { radSysPS 13} -- RAD Packet Switch  (PS) products 

radSPS3ScSL  OBJECT IDENTIFIER ::= { radSysPS 14} -- RAD Packet Switch  (PS) products 

radSPS3Sc2S  OBJECT IDENTIFIER ::=  { radSysPS 15} -- RAD Packet Switch  (PS) products 

radFPS8c OBJECT IDENTIFIER ::=  { radSysPS 16} -- RAD Packet Switch  (PS) products

radFPS4 OBJECT IDENTIFIER ::=  { radSysPS 17} -- RAD Packet Switch  (PS) products


radSysEth  OBJECT IDENTIFIER ::= { systems 9 } -- RAD Ethernet products 

radEP8T    OBJECT IDENTIFIER ::= {radSysEth 1} -- RAD Ethernet products

radEP4TAUI   OBJECT IDENTIFIER ::= {radSysEth 2} -- RAD Ethernet products

radEP4T2FL   OBJECT IDENTIFIER ::= {radSysEth 3} -- RAD Ethernet products

radEP4TFL    OBJECT IDENTIFIER ::= {radSysEth 4} -- RAD Ethernet products

radEP4FL     OBJECT IDENTIFIER ::= {radSysEth 5} -- RAD Ethernet products


radEPR8T   OBJECT IDENTIFIER ::= {radSysEth 7} -- RAD Ethernet products

radEPR4TAUI  OBJECT IDENTIFIER ::= {radSysEth 8} -- RAD Ethernet products

radEPR4T2FL  OBJECT IDENTIFIER ::= {radSysEth 9} -- RAD Ethernet products

radEPR4TFL   OBJECT IDENTIFIER ::= {radSysEth 10} -- RAD Ethernet products

radEPR4FL    OBJECT IDENTIFIER ::= {radSysEth 11} -- RAD Ethernet products


radSysRtr  OBJECT IDENTIFIER ::= { systems 11 } -- RAD Router products 

radRTED    OBJECT IDENTIFIER ::= {radSysRtr 1} -- RAD Router products

radRTEM    OBJECT IDENTIFIER ::= {radSysRtr 2} -- RAD Router products

radRTEC    OBJECT IDENTIFIER ::= {radSysRtr 3} -- RAD Router products

radWebRanger    OBJECT IDENTIFIER ::= {radSysRtr 4} -- RAD Router products

radTinyRouter   OBJECT IDENTIFIER ::= {radSysRtr 5} -- RAD Router products

radSysAtm  OBJECT IDENTIFIER ::= { systems 12 } -- RAD ATM products 

radStarSwitch    OBJECT IDENTIFIER ::= {radSysAtm 1} --RAD StartSwitch products

radStarSwitchATM25    OBJECT IDENTIFIER ::= {radStarSwitch 1} --RAD StartSwitch products
radStarSwitchATM25L   OBJECT IDENTIFIER ::= {radStarSwitch 2} --RAD StartSwitch products
radStarSwitchATM155   OBJECT IDENTIFIER ::= {radStarSwitch 3} --RAD StartSwitch products


radAtmCsuDsu  OBJECT IDENTIFIER ::= {radSysAtm 2} --RAD CSU/DSU products 

radAmcdE1  OBJECT IDENTIFIER ::= {radAtmCsuDsu 1} -- RAD CSU/DSU products
radAmcdT1  OBJECT IDENTIFIER ::= {radAtmCsuDsu 2} -- RAD CSU/DSU products
radAce20E  OBJECT IDENTIFIER ::= {radAtmCsuDsu 3} -- RAD CSU/DSU products
radAce20T  OBJECT IDENTIFIER ::= {radAtmCsuDsu 4} -- RAD CSU/DSU products

radAce2005 OBJECT IDENTIFIER ::= { radAtmCsuDsu 5} -- RAD ACE2005
radAce2002 OBJECT IDENTIFIER ::= { radAtmCsuDsu 6} -- RAD ACE2002

radAce2E  OBJECT IDENTIFIER ::= {radAtmCsuDsu 8} -- RAD CSU/DSU products
radAce2T  OBJECT IDENTIFIER ::= {radAtmCsuDsu 9} -- RAD CSU/DSU products

radAce  OBJECT IDENTIFIER ::= {radSysAtm 3} --RAD ACE products 
radAce101  OBJECT IDENTIFIER ::= {radAce 1} -- RAD ACE101
radAce102  OBJECT IDENTIFIER ::= {radAce 2} -- RAD ACE102

agnt OBJECT IDENTIFIER ::= { radGen 2} 
-- agent general tree
-- Agent General  
agnHwVersion OBJECT-TYPE
      SYNTAX  DisplayString
      ACCESS  read-write
      STATUS  mandatory
      DESCRIPTION
      "ASCII string for description and display of the agent hardware version,
      as it is known by the agent software.The user can update the version
       upon request when he changes   components in the agent's module  "
      ::= { agnt 1 }

agnTrapMask OBJECT-TYPE   
      SYNTAX  INTEGER 
      ACCESS  read-write    
      STATUS  mandatory
      DESCRIPTION
      "The value of this attribute determines the type of traps the 
       agent should mask and not send to the management console. The 
       value is differently determined for different products. There are 
       mainly two methods:
       - an integer number, specifying the traps' severity.
       - a sum of 2**n, where n is a bit assigned to a certain 
         masked trap group.
       User should consult the product specification, to find out 
       the method employed."
      ::= { agnt 2 }

agnTrapValue OBJECT-TYPE
	SYNTAX  OCTET STRING
	ACCESS  read-only
	STATUS deprecated
	DESCRIPTION
	"The value of the trap decoded in internal RAD format. Full description is given
	  in the Trap definition file"
	::= {agnt 3}

agnChangeCnt OBJECT-TYPE
	SYNTAX  Counter
	ACCESS  read-only
	STATUS mandatory
	DESCRIPTION
	"The number of changes in system configuration that were  reported to the 
	manager since last cold start"
	::= {agnt 4 }

agnSpecific OBJECT-TYPE
      SYNTAX  OBJECT IDENTIFIER
      ACCESS  read-only
      STATUS  mandatory
      DESCRIPTION
      " Object identifier of entity containing additional information 
      regarding this instance."
      ::= { agnt 5}

agnConfigMsg OBJECT-TYPE   
      SYNTAX  OCTET STRING
      ACCESS  read-only
      STATUS  mandatory
      DESCRIPTION
      "Full configuration message  coded in internal RAD application format.
       This entry describes agent's configuration.

       For MP-2200 R3, this object describes agent's support of the V5.1
       feature: 1 octet ; bit 0 (LSB). 
       '1' - V5.1 feature is supported
       '0' - V5.1 feature is not supported."
      ::= { agnt 6 }

-- Manager table to record all IP addresses

mngTrapIpTable  OBJECT-TYPE
	SYNTAX  SEQUENCE OF MngEntry
	ACCESS  not-accessible
	STATUS mandatory
	DESCRIPTION
	"This table indicates  the destination address of the traps.
	  Internally it will be limited to ten addresses. "
	::= { agnt 7 }

mngEntry OBJECT-TYPE
	SYNTAX  MngEntry
	ACCESS  not-accessible
	STATUS mandatory
 	  		 DESCRIPTION ""
	INDEX {  mngID }
	::= { mngTrapIpTable 1 }


MngEntry  ::=
	    SEQUENCE {
	mngID
	  INTEGER,
	mngIP
	  IpAddress,
	mngIPMask
	  IpAddress,
    mngTrapMask
      INTEGER	
    }

mngID OBJECT-TYPE
	SYNTAX  INTEGER 
	ACCESS  read-only
	STATUS mandatory
	DESCRIPTION
	" This value indicates an index of a specific IP address"
	::= { mngEntry 1 }

mngIP OBJECT-TYPE
	SYNTAX  IpAddress 
	ACCESS  read-write
	STATUS mandatory
	DESCRIPTION
	"This value indicates  the  destination address of the traps. IP 0.0.0.0 removes the entry. "
	::= { mngEntry 2 }

mngIPMask OBJECT-TYPE
	SYNTAX  IpAddress 
	ACCESS  read-write
	STATUS deprecated
	DESCRIPTION
	"This value indicates  the  mask of the destination addresses of the traps. "
	::= { mngEntry 3 }

mngTrapMask OBJECT-TYPE
	SYNTAX  INTEGER 
	ACCESS  read-write
	STATUS mandatory
	DESCRIPTION
      "The value of this attribute determines the type of traps the 
       agent should mask and not send to this NMS. The 
       value is differently determined for different products. There are 
       mainly two methods:
       - an integer number, specifying the traps' severity.
       - a sum of 2**n, where n is a bit assigned to a certain 
         masked trap group.
       User should consult the product specification, to find out 
       the method employed."
	::= { mngEntry 4 }

agnIndication OBJECT-TYPE   
      SYNTAX  INTEGER {
		 faulty (1),		-- critical
		 warning (2),
		 normal(3),			-- off
		 minor(4),
		 major(5),
		 event(6)
		}
      ACCESS  read-only
      STATUS  mandatory
      DESCRIPTION
      "Attribute describing the state of the entity the agent is responsible for.
       In case of a modular entity, the value of this attribute will be according
       to the component which is in the worst state.
       The order of severity (from top to bottom) is:
       faulty (critical)-> major-> minor-> warning-> event-> normal (off)."   
      ::= { agnt 8 }


agnMonitorModeCmd OBJECT-TYPE
	SYNTAX  INTEGER {
	notApplicable(1),
	off(2),
	on(3)
	}
	ACCESS  read-write
	STATUS mandatory
	DESCRIPTION
	"Setting this attribute to ON, will enforce the agent to change its mode of operation to
	 Monitor Mode"
	::= {agnt 9}

agnLed OBJECT-TYPE
	SYNTAX  OCTET STRING
	ACCESS  read-only
	STATUS mandatory
	DESCRIPTION
	"This entry specifies  the LEDs status of the agent module . Each led will be represented by 4 
	 bits  where the first 2 bits (left) will specify  the status :
	 (00=NA, 01=OFF, 10=ON, 11=BLINK),
     and the next two bits (right) will specify the color :
     (00=GREEN, 01=RED, 10=YELLOW, 11=ORANGE)"
	::= {agnt 10}

trapTable  OBJECT-TYPE
	SYNTAX  SEQUENCE OF TrapEntry
	ACCESS  not-accessible
	STATUS mandatory
	DESCRIPTION
	"This table includes the last few traps generated by the agent, for future retrieval. The table
	 has a limited capacity. If traps are not retrieved in proper time, they will be
	 over-written by new traps "
	::= {agnt 11}

trapEntry OBJECT-TYPE
	SYNTAX  TrapEntry
	ACCESS  not-accessible
	STATUS mandatory
 	  		 DESCRIPTION ""
	INDEX {  trapID }
	::= { trapTable 1 }

TrapEntry  ::=
	    SEQUENCE {
	trapID
	  INTEGER,
	trapVal
	  DisplayString,
	 trapTimeSinceOccurrence
	   TimeTicks
	}

trapID OBJECT-TYPE
	SYNTAX  INTEGER 
	ACCESS  read-only
	STATUS mandatory
	DESCRIPTION
	" This value indicates an index of a specific trap "
	::= { trapEntry 1 }

trapVal OBJECT-TYPE
	SYNTAX  DisplayString 
	ACCESS  read-only
	STATUS mandatory
	DESCRIPTION
	"This value is the actual ASCII description  of the trap. "
	::= { trapEntry 2 }

trapTimeSinceOccurrence OBJECT-TYPE
	 SYNTAX    TimeTicks
	ACCESS  read-only
	STATUS mandatory
	DESCRIPTION
	"This value indicates the amount of  time passed since the occurrence of the event that
	   trigger this trap. "
	::= { trapEntry 3 }

fileTransfer  OBJECT IDENTIFIER ::= { agnt 12 }

fileServerIP  OBJECT-TYPE
	SYNTAX  IpAddress
	ACCESS  read-write
	STATUS  mandatory
	DESCRIPTION
	"The IP address of the server from which the file is loaded "
	::= { fileTransfer 1 }

fileName  OBJECT-TYPE
	SYNTAX  DisplayString
	ACCESS  read-write
	STATUS  mandatory
	DESCRIPTION
	"The name of the file to be loaded. For protection, read returns
	 NULL. "
	::= { fileTransfer 2 }

fileTransCmd  OBJECT-TYPE
	SYNTAX  INTEGER {
	                 swDwnLoad       (1),
					 configDwnLoad   (2),
					 configUpLoad    (3),
					 coProcDwnLoad   (4),
					 stateUpLoad     (5),
					 dwnLoadUserFile (6),
					 upLoadUserFile  (7), 
					 noOp           (255)
					}
	ACCESS  read-write
	STATUS  mandatory
	DESCRIPTION
	"The command to be executed on fileName at fileServerIP."
	::= { fileTransfer 3 }
 
-- tftp  group  

tftpRetryTimeOut OBJECT-TYPE
    SYNTAX  INTEGER
    ACCESS  read-write
    STATUS  mandatory
    DESCRIPTION
        " General Retransmission time-out value (seconds) "
    -- DEFVAL  { 15 }
    ::= { fileTransfer 4 }

tftpTotalTimeOut OBJECT-TYPE
    SYNTAX  INTEGER
    ACCESS  read-write
    STATUS  mandatory
    DESCRIPTION
        " Total Retransmission time-out value (seconds) "
    -- DEFVAL  { 60 }
    ::= { fileTransfer 5 }

tftpStatus OBJECT-TYPE
    SYNTAX  INTEGER {
		noOp(2),
		connecting(3),
		transferringData(4),
		endedTimeOut(5),
		endedOk(6),
		error(7)
	}
    ACCESS  read-write
    STATUS  mandatory
    DESCRIPTION
    "Status of tftp session. When a session ended with success,
    the tftpStatus should be endedOk(6). Before restarting a
    tftp session, the NMS should set the tftpStatus to noOp(2).
    That's the reason of ACCESS read-write to this field."
    DEFVAL  { noOp}
    ::= { fileTransfer 6 }

tftpError OBJECT-TYPE
    SYNTAX  OCTET STRING ( SIZE(2) )
    ACCESS  read-only
    STATUS  mandatory
    DESCRIPTION
    " The MSB represents the standard error code.
    The LSB represents the private error code.
    0x0000 is No Error
    0x0100 is File Not Found
    0x0400 is Illegal TFTP operation
    0x0500 is Unknown transfer ID
    0x0001 is Server Overflow
    0x0002 is No empty UDP port
    0x0003 is No empty connection
    0x0004 is Illegal File Mode
    0x0007 is Illegal PDU size "
    DEFVAL  { '0000'h }
    ::= { fileTransfer 7 }

fileTransferToSubSystems OBJECT-TYPE
    SYNTAX  OCTET STRING 
    ACCESS  read-write
    STATUS  mandatory
    DESCRIPTION
    " This object represents the sub-systems the fileTransCmd 
      refers to. It should be used when a system is divided 
      to sub-systems and each sub-system (or part of them) can 
	  have a different SW/Configuration.

	  Each bit of this object will represent one of the sub-systems.
	  Bit='1' - APPLY to respective sub-system
	  Bit='0' - DO NOT APPLY to respective sub-system

	  For the meaning of each bit, see product's specification.
	  User will select the sub-systems envolved by filling-in the bits
      that represent these sub-systems.
      In this case, the file represented by 'fileName' will 
	  include several parts, each representing one of the sub-systems.
	  The agent will refer only to the part/s indicated by this object.

      0 Octet Strings = not applicable  
      DEFVAL = 0h	for  the products that support this object."
    ::= { fileTransfer 8 }


fileNameWithinProduct  OBJECT-TYPE
	SYNTAX  DisplayString
	ACCESS  read-write
	STATUS  mandatory
	DESCRIPTION
	"The file name used by the product within the product file system."
	::= { fileTransfer 9 }


systemReset  OBJECT-TYPE
	SYNTAX  INTEGER	{
	                 off         (2),
					 on          (3), --HW
					 resetConfig (4)  
				    }
	ACCESS  read-write
	STATUS  mandatory
	DESCRIPTION
	"Reset action to be performed on the system."
	::= { agnt 13 }

systemTiming  OBJECT IDENTIFIER ::= { agnt 14 }

systemDate OBJECT-TYPE
        SYNTAX  DisplayString
        ACCESS  read-write
        STATUS  mandatory
        DESCRIPTION
           "System date."
        ::= { systemTiming 1 }
        
systemTime OBJECT-TYPE
        SYNTAX  DisplayString
        ACCESS  read-write
        STATUS  mandatory
        DESCRIPTION
           "System time."
        ::= { systemTiming 2 }


systemPort  OBJECT IDENTIFIER ::= { agnt 15 }

physicalConnectorTable OBJECT-TYPE
	SYNTAX  SEQUENCE OF PhysicalConnectorEntry
	ACCESS  not-accessible
	STATUS mandatory
	DESCRIPTION
	"This table includes the connector type of ports or interfaces."
	::= {systemPort 1}

physicalConnectorEntry OBJECT-TYPE
	SYNTAX  PhysicalConnectorEntry
	ACCESS  not-accessible
	STATUS mandatory
	 	  		 DESCRIPTION ""
INDEX {portIdx}
	::= { physicalConnectorTable 1 }

PhysicalConnectorEntry  ::=
	    SEQUENCE {
	portIdx
	  INTEGER,
	physicalConnector
	  INTEGER,
	portOptWaveLength
	  INTEGER
	}

portIdx OBJECT-TYPE
	SYNTAX  INTEGER 
	ACCESS  read-only
	STATUS mandatory
	DESCRIPTION
	"This object is an index of the specific port or interface.
	 For a port, the index will be as agreed between agent and 
	 application.
	 For an interface, ifIndex may be used."
	::= { physicalConnectorEntry 1 }

physicalConnector OBJECT-TYPE
	SYNTAX  INTEGER 
	        {
			other (1),
			v35   (2),	  --34 pin female
			rs530 (3),	  --DB25
			x21   (4),	  --DB15
			bnc   (5),
			utp   (6),	  --RJ45
			aui   (7),
			rs422 (8),	  --DB25
			crossUtp (9), --RJ45
			rj45    (10),
			v24     (11), --DB25
			g703    (12), --TB5
			termBlock3AndRj45 (13),
			terminalBlock3    (14),
			terminalBlock5    (15),
			terminalBlock7    (16),
			db25              (17),
			db15              (18),
			rj45ethernet      (19),
			termBlock5AndRj45 (20),
			db9               (21),
			g703E1            (22),  --BNC-RJ45-BNC	
			g703E1-LTU        (23),  --BNC-RJ45-BNC
			sc                (24),	 --sc optical 
			st                (25),	 --st optical
			stl               (26),
			fc                (27),	 --fc optical
			tb5w              (28),  --Term-Block-5-Wire (for HCD)
			termBlock6AndRj45 (29),
			ethBnc            (30),
			scsi26            (31),  --SCSI with 26 pins
			eth4381           (32),  --RJ45 with two embeded LEDs
			twoBnc			  (33),  --Two BNC
			scsi50            (34),  --SCSI with 50 pins
			twoMiniBnc        (35),  --Two mini BNC
			sf1               (36),  --sf1=single fiber optical 
			terminalBlock4    (37),
			sf2         	  (38),  --sf2=single fiber optical
			-- 39 is reserved for the next version: ver455
			v36               (40),
			block4W           (41),  --like in WR connector for Modems
			none             (255)    	
			}	 
	ACCESS  read-only
	STATUS mandatory
	DESCRIPTION
	"The connector of the port/interface.
	 other - none of the specified connectors
	 none -  no connector."
	::= { physicalConnectorEntry 2 }

portOptWaveLength OBJECT-TYPE
    SYNTAX  INTEGER {
		notApplicable(1),
		nm850(2),
		nm1300(3),
		nm1300Laser(4),
		nm1550Laser(5)
	}
    ACCESS  read-only
    STATUS  mandatory
    DESCRIPTION
     "Wave Length of an Optical interface/port in [nm] and specification if 
      Laser or not.
      notApplicable - for non-optical ports."
     ::= { physicalConnectorEntry 3 }


prtSupervisory  OBJECT IDENTIFIER ::= { systemPort 2 }


prtSpTable OBJECT-TYPE
      SYNTAX SEQUENCE OF PrtSpEntry
      ACCESS not-accessible
      STATUS  mandatory
      DESCRIPTION "" ::= {prtSupervisory 1}

prtSpEntry OBJECT-TYPE
      SYNTAX PrtSpEntry
      ACCESS not-accessible
      STATUS mandatory
      DESCRIPTION
      "Supervisory port parameter table."
      INDEX {prtSupervisoryIndex }
      ::= { prtSpTable 1}

PrtSpEntry ::=
      SEQUENCE {
      prtSupervisoryIndex       INTEGER,
	  prtSupervisoryRate        INTEGER,
	  prtSupervisoryDataBits    INTEGER,
	  prtSupervisoryParity      INTEGER,
	  prtSupervisoryStopBits    INTEGER,
	  prtSupervisoryUsage       INTEGER,
	  prtSupervisoryInterface   INTEGER,
	  prtSupervisoryCTS		    INTEGER,
	  prtSupervisoryDcdDelay    INTEGER,
	  prtSupervisoryDSR		    INTEGER,
	  prtSupervisoryRoutProtocol   INTEGER
      }				  
 					  

prtSupervisoryIndex OBJECT-TYPE
      SYNTAX  INTEGER
      ACCESS  read-only
      STATUS  mandatory
      DESCRIPTION
      "The SP port index. 
       The LS byte of the integer is the port index 1..255. 
       The MS byte is different than 0 only if the port belongs to 
       a module. In	that case it is the module number."
      ::= { prtSpEntry 1}

prtSupervisoryRate     OBJECT-TYPE
      SYNTAX  INTEGER
	      {
        auto      (1),
        s300bps   (2),
        s1200bps  (3),
        s2400bps  (4),
        s4800bps  (5),
        s9600bps  (6),
        s19200bps (7),
        s38400bps (8),
        s57600bps (9),
        s115200bps (10)
	      }
      ACCESS  read-write
      STATUS  mandatory
      DESCRIPTION
      "This attribute indicates the operation rate (speed) of the 
       port.
       auto - automatic rate selection, by the agent."
      ::= { prtSpEntry 2}

prtSupervisoryDataBits OBJECT-TYPE
      SYNTAX  INTEGER
	      {
        dataBits7 (1),
        dataBits8 (2)
	      }
      ACCESS  read-write
      STATUS  mandatory
      DESCRIPTION
      "This attribute indicates the number of data bits in an async 
       frame"
      ::= { prtSpEntry 3}

prtSupervisoryParity OBJECT-TYPE
      SYNTAX  INTEGER
	      {
        none  (1),
        odd   (2),
        even  (3)
	      }
      ACCESS  read-write
      STATUS  mandatory
      DESCRIPTION
      "This attribute indicates the parity mode in an async frame"
      ::= { prtSpEntry 4}

prtSupervisoryStopBits OBJECT-TYPE
      SYNTAX  INTEGER
	      {
		notApplicable  (1),
        stopBits1      (2),
        stopBits1dot5  (3),
        stopBits2      (4)
	      }
      ACCESS  read-only
      STATUS  mandatory
      DESCRIPTION
      "This attribute indicates the parity mode in an async frame."
      ::= { prtSpEntry 5}

prtSupervisoryUsage OBJECT-TYPE
      SYNTAX  INTEGER
	      {
		unknown (1),
		noUse   (2),
		terminal(3),
		nmsSlip (4),
		nmsPpp  (5),
		muxSlip (6),
		muxPpp  (7),
		dialOut (8)
	      }
      ACCESS  read-write
      STATUS  mandatory
      DESCRIPTION
      "This attribute indicates the usage of the SP port."
      ::= { prtSpEntry 6}

prtSupervisoryInterface OBJECT-TYPE
      SYNTAX  INTEGER
	      {
		  notApplicable(1),
          dce  (2),
          dte  (3)
	      }
      ACCESS  read-write
      STATUS  mandatory
      DESCRIPTION
      "This attribute indicates the supervisory port interface."
      ::= { prtSpEntry 7}

prtSupervisoryCTS OBJECT-TYPE
      SYNTAX  INTEGER
	      {
          	notApplicable   (1),
          	on            	(2),        --Old value for DCE.
			rts           	(3),        --Old value for DCE 
			dteWait         (4),        --DTE will wait for CTS to become active before transmit date.
			dteIgnore       (5)         --DTE will Ignore CTS signal and will transmit date anyway.
	      }
      ACCESS  read-write
      STATUS  mandatory
      DESCRIPTION
	  "CTS line state." 
      ::= { prtSpEntry 8}

prtSupervisoryDcdDelay OBJECT-TYPE
      SYNTAX  INTEGER
	      {
          notApplicable (1),
          d0   (2),
          d10  (3),
		  d50  (4),
		  d100 (5),
		  d200 (6),
		  d300 (7)
	      }
      ACCESS  read-write
      STATUS  mandatory
      DESCRIPTION
	  "DCD delay in msec." 
      ::= { prtSpEntry 9}

prtSupervisoryDSR OBJECT-TYPE
      SYNTAX  INTEGER
	      {
          notApplicable (1),
          on   (2),
          dtr  (3)
	      }
      ACCESS  read-write
      STATUS  mandatory
      DESCRIPTION
	  "DSR line state." 
      ::= { prtSpEntry 10}

prtSupervisoryRoutProtocol OBJECT-TYPE
      SYNTAX  INTEGER
       {
        notApplicable (1),
  		none          (2),
        proprietary   (3),
        rip2          (4)
       }
      ACCESS  read-write
      STATUS  mandatory
      DESCRIPTION
      "This attribute indicates the routing protocol of the port.
       notApplicable - for DP."
      ::= { prtSpEntry 11}

--Port Performance Data

prtPerformance  OBJECT IDENTIFIER ::= { systemPort 3 }

prtPerfTable OBJECT-TYPE
	SYNTAX  SEQUENCE OF PrtPerfEntry
	ACCESS  not-accessible
	STATUS mandatory
	DESCRIPTION
	"This table includes G.826 ports or interfaces."
	::= {prtPerformance 1}

prtPerfEntry OBJECT-TYPE
	SYNTAX  PrtPerfEntry
	ACCESS  not-accessible
	STATUS mandatory
	 	  		 DESCRIPTION ""
INDEX {prtPerfIdx, prtPerfPeriodRef}
	::= { prtPerfTable 1 }

PrtPerfEntry  ::=
	    SEQUENCE {
	prtPerfIdx
	  INTEGER,
	prtPerfPeriodRef
	  INTEGER,
	prtPerfElapsedTime
	  INTEGER,
	prtPerfUAS
	  INTEGER,
	prtPerfES
	  INTEGER,
	prtPerfSES
	  INTEGER,
	prtPerfBBE
	  INTEGER,
	prtPerfBlocksPerSec
	  INTEGER,
	prtPerfTimeTag
	  TimeTicks,
	prtPerfSaveAndResetCmd
	  INTEGER
	  }

prtPerfIdx OBJECT-TYPE
	SYNTAX  INTEGER 
	ACCESS  read-only
	STATUS mandatory
	DESCRIPTION
	"This object is an index of the specific port or interface.
	 For a port, the index will be as agreed between agent and 
	 application.
	 For an interface, ifIndex may be used."
	::= { prtPerfEntry 1 }

prtPerfPeriodRef OBJECT-TYPE
	SYNTAX  INTEGER 
	      {
          currentPeriod (1),
          lastPeriod    (2)
	      }
	ACCESS  read-only
	STATUS  mandatory
	DESCRIPTION
	"This object is an index that specifies which period of time, the next
	 5 objects refer to.
	 currentPeriod - the period since last prtPerfSaveAndResetCmd received or
	           since Start-up (if no prtPerfSaveAndResetCmd was received since
	           Start-up) until now.
	 lastPeriod - the period between last two commands of prtPerfSaveAndResetCmd.
	           - If only one command occured since Start-up: the period between 
	             Start-up and last command.
	           - If no command occured since Start-up: this period will not 
	             actually exist. In this case, he following 5 objects will be 0."
	::= { prtPerfEntry 2 }

prtPerfElapsedTime OBJECT-TYPE
	SYNTAX  INTEGER 
	ACCESS  read-only
	STATUS  mandatory
	DESCRIPTION
	"Elapsed Time in seconds.
	 - for prtPerfPeriodRef=currentPeriod:
	   The period since last prtPerfSaveAndResetCmd received or	since Start-up 
	   (if no prtPerfSaveAndResetCmd was received since	Start-up) until now.
	 - for prtPerfPeriodRef=lastPeriod:
	   The value of prtPerfElapsedTime when last prtPerfSaveAndResetCmd
	   was received."
	::= { prtPerfEntry 3 }

prtPerfUAS OBJECT-TYPE
	SYNTAX  INTEGER 
	ACCESS  read-only
	STATUS  mandatory
	DESCRIPTION
	"Number of Unavailable Seconds for the reference period (prtPerfPeriodRef)."
	::= { prtPerfEntry 4 }

prtPerfES OBJECT-TYPE
	SYNTAX  INTEGER 
	ACCESS  read-only
	STATUS  mandatory
	DESCRIPTION
	"Number of Errored Seconds for the reference period (prtPerfPeriodRef)."
	::= { prtPerfEntry 5 }

prtPerfSES OBJECT-TYPE
	SYNTAX  INTEGER 
	ACCESS  read-only
	STATUS  mandatory
	DESCRIPTION
	"Number of Severely Errored Seconds for the reference period (prtPerfPeriodRef)."
	::= { prtPerfEntry 6 }

prtPerfBBE OBJECT-TYPE
	SYNTAX  INTEGER 
	ACCESS  read-only
	STATUS  mandatory
	DESCRIPTION
	"Number of Background Block (or Frame) Errors for the reference period 
	 (prtPerfPeriodRef)."
	::= { prtPerfEntry 7 }

prtPerfBlocksPerSec OBJECT-TYPE
	SYNTAX  INTEGER 
	ACCESS  read-only
	STATUS  mandatory
	DESCRIPTION
	"Blocks per second (or frames per second) of the port/interface indicated by 
	 portIdx. This object is constant for a certain port/interface.
	 It is not affected by the prtPerfPeriodRef index."
	::= { prtPerfEntry 8 }

prtPerfTimeTag OBJECT-TYPE
	SYNTAX  TimeTicks 
	ACCESS  read-only
	STATUS  mandatory
	DESCRIPTION
	"Time Tag of Last Period: sysUpTime when last prtPerfSaveAndResetCmd was
	 executed.
	 This object is applicable only for prtPerfPeriodRef=lastPeriod.
	 For prtPerfPeriodRef=currentPeriod, the value will always be 0."
	::= { prtPerfEntry 9 }

prtPerfSaveAndResetCmd OBJECT-TYPE
    SYNTAX   INTEGER
	      {
    		off(2),
	    	on (3)
	      }
    ACCESS  read-write
    STATUS  mandatory
    DESCRIPTION
    "A command per port/interface, to Save data of Current Period in Last Period
     data-set and start a new counting period for Current Period.
     This object is applicable only for prtPerfPeriodRef=currentPeriod.
     Setting this object to on(3) for prtPerfPeriodRef=last, will cause the agent
     to return: Bad Value response.
     When setting validly this object to on(3), agent will perform the required 
     command and will reset automatically the value of this object to off(2).
     Setting this object to off(2), will do nothing."
    ::= { prtPerfEntry 10 }

--Port Test Data

prtTest OBJECT IDENTIFIER ::= { systemPort 4 }

prtTestTable OBJECT-TYPE
	SYNTAX  SEQUENCE OF PrtTestEntry
	ACCESS  not-accessible
	STATUS mandatory
	DESCRIPTION
	"This table includes test data for ports or interfaces."
	::= {prtTest 1}

prtTestEntry OBJECT-TYPE
	SYNTAX  PrtTestEntry
	ACCESS  not-accessible
	STATUS mandatory
	 	  		 DESCRIPTION ""
INDEX {prtTestIdx}
	::= { prtTestTable 1 }

PrtTestEntry  ::=
	    SEQUENCE {
     	prtTestIdx
	    INTEGER,
    	prtTestCmdAndStatus
        INTEGER,
    	prtBertCounter
        INTEGER,
		prtTestInitiator
		INTEGER
        } 

prtTestIdx OBJECT-TYPE
	SYNTAX  INTEGER 
	ACCESS  read-only
	STATUS mandatory
	DESCRIPTION
	"This object is an index of the specific port or interface.
	 For a port, the index will be as agreed between agent and 
	 application.
	 For an interface, ifIndex may be used."
	::= { prtTestEntry 1 }

prtTestCmdAndStatus OBJECT-TYPE
      SYNTAX  INTEGER
      ACCESS  read-write
      STATUS  mandatory
      DESCRIPTION
      "Setting this object to a value as detailed furter on 
       (except 0) will initiate a test on the specific port. 
       The test/s requested will be set according to the respective
       bit. The value of this object will be a sum of (2**n), where n is
       the Bit:
         TEST                  BIT	                     VALUE
        -----------            ---						------
        reserved                0						   1
		PayloadLoop=RLB     	1 (=Remote Loopback)	   2
        LineLoop=DIG            2 (=Digital)			   4
        OtherLoop               3						   8
        InwardLoop=LLB          4 (=Local Loopback)       16
        BERT                    5						  32
        LC                      6                         64

        e.g : If the requested value is 20 -> 010100  ->
              Bits 2 & 4 are set -> the requested tests are :
                                    LineLoopback=DIG
                                    InwardLoopback=LLB
                                      
       Not all tests combinations are valid.
	   For valid test combination, see each product's specification.

       The terminology and order of tests (except BERT) is according to 
	   the one used for Test Status of DS1 and DS3 standards.

       Setting this object to stop (value=0 ; all bits are 0), 
       will stop all the user requested tests running on the 
       selected port.

       When no test is running on the port, the Get value (test status)
	   will be 0.

	   PayloadLoop=RLB
	     The received signal at this interface is looped
	     through the device.  Typically the received signal
	     is looped back for retransmission after it has
	     passed through the device's framing function.

	   LineLoop=DIG
	     The received signal at this interface does not
	     go through the device (minimum penetration) but
	     is looped back out.

	   OtherLoop
	     Loopbacks that are not defined here.

	   InwardLoop=LLB
	     The sent signal at this interface is looped back
	     through the device.

	   LC
	     This loop is applicable only for HSSI interface, towards the router ."
   	  ::= { prtTestEntry 2 }

prtBertCounter   OBJECT-TYPE
      SYNTAX  INTEGER
      ACCESS  read-only
      STATUS  mandatory
      DESCRIPTION
      "This object indicates the number of BERT errors encountered
       during the BERT operation.
       It is valid only when BERT (Bit Error Rate Test) is active on the 
       specific port.
       The Counter starts from zero (0) anytime BERT is initiated."
      ::= { prtTestEntry 3}

prtTestInitiator OBJECT-TYPE
    SYNTAX   INTEGER
	      {
    		unknown   (1),
    		user      (2),
	    	remoteUnit(3),
			dteRouter (4)
	      }
    ACCESS  read-only
    STATUS  mandatory
    DESCRIPTION
    "This object indicates who initiated this port's test/s."
    ::= { prtTestEntry 4 }


--Port General Parameters

prtParam OBJECT IDENTIFIER ::= { systemPort 5 }

prtParamTable OBJECT-TYPE
	SYNTAX  SEQUENCE OF PrtParamEntry
	ACCESS  not-accessible
	STATUS mandatory
	DESCRIPTION
	"This table includes the connector type of ports or interfaces."
	::= {prtParam 1}

prtParamEntry OBJECT-TYPE
	SYNTAX  PrtParamEntry
	ACCESS  not-accessible
	STATUS mandatory
	 	  		 DESCRIPTION ""
INDEX {prtParamIdx}
	::= { prtParamTable 1 }

PrtParamEntry  ::=
	    SEQUENCE {
	prtParamIdx
	  INTEGER,
	prtControlCnfg
	  INTEGER
	}

prtParamIdx OBJECT-TYPE
	SYNTAX  INTEGER 
	ACCESS  read-only
	STATUS mandatory
	DESCRIPTION
	"This object is an index of the specific port or interface.
	 For a port, the index will be as agreed between agent and 
	 application.
	 For an interface, ifIndex may be used."
	::= { prtParamEntry 1 }

prtControlCnfg OBJECT-TYPE
	SYNTAX  INTEGER 
	ACCESS  read-write
	STATUS mandatory
	DESCRIPTION
	"This object may be used for port RW general parameter/s.
	 For detailed meaning, see product's spec.
	 Supported by: PRBi-E3/T3."
	::= { prtParamEntry 2 }

systemResetAllStatsCmd OBJECT-TYPE
      SYNTAX   INTEGER
	      {
    		off(2),
	    	on (3)
	      }
      ACCESS  read-write
      STATUS  mandatory
      DESCRIPTION
       "Reset statistics of all ports and connections of the device."
      ::= { agnt 16 }

systemClearTablesCmd OBJECT-TYPE
      SYNTAX   INTEGER
	      {
    		off(2),
	    	tempCnfgTables (3)
	      }
      ACCESS  read-write
      STATUS  mandatory
      DESCRIPTION
       "tempCnfgTables - Set *RowStatus = destroy for all entries of 
                         some tables having *RowStatus object, for 
                         temporary configuration only! (255).
                         For the relevant tables, see product's specification.
                         This object should be used by WAN product applications 
                         before performing the Update operation, in order to clear 
                         old entries of these tables. 
        off - agent will automatically change to this value, after performing the 
              command. "
      ::= { agnt 17 }

systemParameter OBJECT-TYPE
      SYNTAX   INTEGER
      ACCESS  read-write
      STATUS  mandatory
      DESCRIPTION
       "This parameter can be used for different purposes: 
        - TELNET session time-out in seconds.
				- Ace20: when trying to create row in a table that already
								 has row with the same values, if set of values has to be uniqe
								 in table, this attribute is set to the index of the existing row."
       ::= { agnt 18 }
 
agnGlobalAlarmMask OBJECT-TYPE   
      SYNTAX OCTET STRING 
      ACCESS  read-write    
      STATUS  mandatory
      DESCRIPTION
      "The value of this attribute determines the alarm traps the 
       agent should mask and not send to the managers.
       Each bit from a certain octet represents a certain alarm."
      ::= { agnt 19 }

alarmSeverity   OBJECT-TYPE
      	SYNTAX   INTEGER
	      	{
			event		(3),
			minor		(4),
			major		(5),
	    	warning		(6),
			critical	(7)
	  		}
      	ACCESS  read-only
      	STATUS  mandatory
      	DESCRIPTION
       	"This object specifies the severity of the alarms."
      ::= { agnt 20 }

alarmState   OBJECT-TYPE
      	SYNTAX   INTEGER
	      	{
			off (2), 	-- End, 
			on  (3) 	-- Start.
	  		}
      	ACCESS  read-only
      	STATUS  mandatory
      	DESCRIPTION
       "."
      ::= { agnt 21 }


agnTestStatus OBJECT-TYPE
	SYNTAX	INTEGER
		{
		 off			(2),
		 on 			(3)
		}

	ACCESS	read-only
	STATUS	mandatory
	DESCRIPTION
	"Indicates the current test status (for all levels: system,
	   card, port).
       This attribute will be set to: 
         on(3): when there is at least one test	in progress on the
                system/card/port
		 off(2): when there is NO test in progress on the
    	         system/card/port" 
      ::= {agnt 22  }

systemSaveAndResetAllStatsCmd OBJECT-TYPE
      SYNTAX   INTEGER
	      {
    		off(2),
	    	on (3)
	      }
    ACCESS  read-write
    STATUS  mandatory
    DESCRIPTION
    "on  - a command to Save data of Current Period in Last Period
           data-set and start a new counting period for Current Period.
     off - agent will automatically change to this value, after performing the 
           command."
      ::= { agnt 23 }

systemDefaultGateway OBJECT-TYPE
      SYNTAX   IpAddress
    ACCESS  read-write
    STATUS  mandatory
    DESCRIPTION
    "Default Gateway's IP Address."
      ::= { agnt 24 }

-- PS Table
systemPsTable OBJECT-TYPE
	SYNTAX  SEQUENCE OF SystemPsEntry
	ACCESS  not-accessible
	STATUS mandatory
	DESCRIPTION
	"This table describes the PS types of a device.
	Usage of this table is specified in the device's NMS SRS"
	::= { agnt 25 }

systemPsEntry OBJECT-TYPE
	SYNTAX  SystemPsEntry
	ACCESS  not-accessible
	STATUS mandatory
	 	  		 DESCRIPTION ""
INDEX {systemPsIndex1, systemPsIndex2}
	::= { systemPsTable 1 }

SystemPsEntry  ::=
	    SEQUENCE {
	systemPsIndex1
	  INTEGER,
	systemPsIndex2
	  INTEGER,
	systemPsType
	  INTEGER
	}

systemPsIndex1 OBJECT-TYPE
	SYNTAX  INTEGER 
	ACCESS  read-only
	STATUS mandatory
	DESCRIPTION
	"First Index. 
	In HUBs:
	1 = PS-A slot
	2 = PS-B slot.
	In SA units:
	1 = PS1
	2 = PS2
	Default = 1"
	::= { systemPsEntry 1 }

systemPsIndex2 OBJECT-TYPE
	SYNTAX  INTEGER 
	ACCESS  read-only
	STATUS mandatory
	DESCRIPTION
	"Second Index. 
	In HUBs:
	1 always.
    In SA units:
	1 = Local
	2 = Remote
	Default = 1."
	::= { systemPsEntry 2 }

systemPsType OBJECT-TYPE
      SYNTAX  INTEGER
	      {
		  none  (1),
	      ac    (2),
	      dc    (3),
		  acDc  (4)
	      }
      ACCESS  read-only
      STATUS  mandatory
      DESCRIPTION
      "The type of PS, for a stand-alone product.
      acDc - AC with rj45 DC."
      ::= { systemPsEntry 3 }

--TRAPS

tftpStatusChangeTrap  TRAP-TYPE
     ENTERPRISE      systems
     VARIABLES       { tftpStatus}
     DESCRIPTION     
     "This trap is sent whenever the status of tftp changed."
     ::= 1

agnStatusChangeTrap  TRAP-TYPE
	ENTERPRISE		systems
	VARIABLES		{agnIndication}
	DESCRIPTION
	"This trap is sent whenever the state of the entity the agent is
	 responsible for changed.
	 TDM devices will send agnTestStatus variable to indicate the current test status."
	::= 2

prtStatusChangeTrap  TRAP-TYPE
	ENTERPRISE		systems
	DESCRIPTION
	"This trap is sent whenever the state of a port changed.
	 Attached, will be parameter/s that indicate the new port status.
	 The attached variables will be specified in the specifications
	 of the products supporting this trap."
	::= 3
-- 
-- file :v:\doc\rdv\mib\ver450\mpmx.txt
-- 

--Title:     RAD's WAN PRODUCTS MIB
--Version:   1.0
--Date:      31.1.1993
--By:        Yaira Gabay, Orly Nicklass
--Update :   10.11.1994
--By:  Arik Sadovski

--Last Update: 	28-Sep-99 
--By: Smadar Tauber
--File:      v:\doc\rdv\mib\ver450\mpmx.txt

--IMPORTS
--      enterprises                            FROM RFC1155-SMI
--      DisplayString                          FROM RFC1213-MIB
--      IpAddress                              FROM RFC1155-SMI
--      OCTET STRING                           FROM RFC1213-MIB
--      OBJECT-TYPE                            FROM RFC1212;


--Some MIB compilers need those two lines:
-- enterprises OBJECT IDENTIFIER ::=
--                       { iso org(3) dod(6) internet(1) private(4) 1 }

--systems OBJECT IDENTIFIER ::= { radGen 1}
--agnt OBJECT IDENTIFIER ::= { radGen 2}
--radSysWan OBJECT IDENTIFIER ::= { systems 3 }

--  -----------------------------------------------------------------------------

wanGen   OBJECT IDENTIFIER ::= {radWan 1}

muxHub OBJECT IDENTIFIER ::= {radWan 2}

--  ----------------------------------------------------------------------------------------------
chasWanGen  OBJECT IDENTIFIER ::= {wanGen 1}
agnWanGen   OBJECT IDENTIFIER ::= {wanGen 2}
mdlWanGen   OBJECT IDENTIFIER ::= {wanGen 3}
prtWanGen   OBJECT IDENTIFIER ::= {wanGen 4}
mapWanGen   OBJECT IDENTIFIER ::= {wanGen 5}
diverseIfWanGen OBJECT IDENTIFIER ::= {wanGen 6}
--ethIf          OBJECT IDENTIFIER ::= {diverseIfWanGen 1}
--sonetInterface OBJECT IDENTIFIER ::= {diverseIfWanGen 2}
--ds3Interface	 OBJECT IDENTIFIER ::= {diverseIfWanGen 3}
--ds1Interface	 OBJECT IDENTIFIER ::= {diverseIfWanGen 4}
--hdlcMibObjects OBJECT IDENTIFIER ::= {diverseIfWanGen 5}
--v51If          OBJECT IDENTIFIER ::= {diverseIfWanGen 6} (see v51.txt)
--voipWanGen OBJECT IDENTIFIER ::= {wanGen 7} (see voip.txt)


statAgnGen       OBJECT IDENTIFIER ::= {agnWanGen 1}
cnfgAgnGen       OBJECT IDENTIFIER ::= {agnWanGen 2}
cmprAgnGen       OBJECT IDENTIFIER ::= {agnWanGen 3}
alrBuffGen       OBJECT IDENTIFIER ::= {agnWanGen 4}
agnFlipDb        OBJECT IDENTIFIER ::= {agnWanGen 5}
agnSa            OBJECT IDENTIFIER ::= {agnWanGen 6}
agnListDecoding  OBJECT IDENTIFIER ::= {agnWanGen 7}
agnSystemDlci    OBJECT IDENTIFIER ::= {agnWanGen 8}
agnVoiceSwitching    OBJECT IDENTIFIER ::= {agnWanGen 9}
agnSigProfile    OBJECT IDENTIFIER ::= {agnWanGen 10}
agnSystemTs      OBJECT IDENTIFIER ::= {agnWanGen 11}

statMdlGen   OBJECT IDENTIFIER ::= {mdlWanGen 1}
cnfgMdlGen   OBJECT IDENTIFIER ::= {mdlWanGen 2}
cmprMdlGen   OBJECT IDENTIFIER ::= {mdlWanGen 3}


statPrtGen   OBJECT IDENTIFIER ::= {prtWanGen 1}
cnfgPrtGen   OBJECT IDENTIFIER ::= {prtWanGen 2}
cmprPrtGen   OBJECT IDENTIFIER ::= {prtWanGen 3}


agnMux        OBJECT IDENTIFIER ::= {muxHub 1}
mdlMux        OBJECT IDENTIFIER ::= {muxHub 2}
prtMux        OBJECT IDENTIFIER ::= {muxHub 3}


statPrtMux         OBJECT IDENTIFIER ::= {prtMux 1}
cnfgPrtMux         OBJECT IDENTIFIER ::= {prtMux 2}

--

--prtHsfStatTable   OBJECT IDENTIFIER ::= {statPrtMux 6}

--

prtClCnfg       OBJECT IDENTIFIER ::= {cnfgPrtMux 1}
prtPh1MlCnfg    OBJECT IDENTIFIER ::= {cnfgPrtMux 2} --MPH1/e1/t1
prtPhPlCnfg     OBJECT IDENTIFIER ::= {cnfgPrtMux 3} --MPH1,MPH3,MPL6
prtLs2Cnfg      OBJECT IDENTIFIER ::= {cnfgPrtMux 4} --LS2 family
--prtVc2CnfgTable      OBJECT IDENTIFIER ::= {cnfgPrtMux 5}
--prtHsfCnfgTable      OBJECT IDENTIFIER ::= {cnfgPrtMux 6}
prtHs4Cnfg      OBJECT IDENTIFIER ::= {cnfgPrtMux 7}
prtHsiCnfg      OBJECT IDENTIFIER ::= {cnfgPrtMux 8}
prtPVc4Cnfg     OBJECT IDENTIFIER ::= {cnfgPrtMux 9}
prtHsrCnfg      OBJECT IDENTIFIER ::= {cnfgPrtMux 10}
prtMbeCnfg      OBJECT IDENTIFIER ::= {cnfgPrtMux 11}
prtTreCnfg      OBJECT IDENTIFIER ::= {cnfgPrtMux 12}
prtLs6Cnfg      OBJECT IDENTIFIER ::= {cnfgPrtMux 13}
prtVc3Cnfg      OBJECT IDENTIFIER ::= {cnfgPrtMux 14}
prtVcPbxCnfg    OBJECT IDENTIFIER ::= {cnfgPrtMux 15}
prtIsdnCnfg     OBJECT IDENTIFIER ::= {cnfgPrtMux 16}
prtLogicalCnfg  OBJECT IDENTIFIER ::= {cnfgPrtMux 17}
prtFrPlusCnfg   OBJECT IDENTIFIER ::= {cnfgPrtMux 18}
prtMl4Cnfg      OBJECT IDENTIFIER ::= {cnfgPrtMux 19}
prtAcmCnfg      OBJECT IDENTIFIER ::= {cnfgPrtMux 20}

--
-- Wan chassis general information
--

chasVersion OBJECT-TYPE
      SYNTAX  DisplayString (SIZE (0..255))
      ACCESS  read-only
      STATUS  mandatory
      DESCRIPTION
      "An ASCII string for description and display of the agent chassis version."
      ::= { chasWanGen 1 }

chasTotalNoOfSlt  OBJECT-TYPE
      SYNTAX  INTEGER
      ACCESS  read-only
      STATUS  mandatory
      DESCRIPTION
      "This entry indicates the number of physical slots in the
       chassis."
      ::= { chasWanGen 2 }

chasTotalNoOfIoSlt  OBJECT-TYPE
      SYNTAX  INTEGER
      ACCESS  read-only
      STATUS  mandatory
      DESCRIPTION
      "This entry indicates the total number of physical IO slots
       in the chassis, (not all slots hardware should be occupied
       and active) ."
      ::= { chasWanGen 3 }

chasTotalNoOfPsSlt  OBJECT-TYPE
      SYNTAX  INTEGER
      ACCESS  read-only
      STATUS  mandatory
      DESCRIPTION
      "This entry indicates the number of physical Power Supply
       slots in the chassis."
      ::= { chasWanGen 4 }

chasTotalNoOfClSlt  OBJECT-TYPE
      SYNTAX  INTEGER
      ACCESS  read-only
      STATUS  mandatory
      DESCRIPTION
      "This entry indicates the number of physical Common Logic slots in the
       chassis."
      ::= { chasWanGen 5 }

--
-- Wan agent status general information
--
agnSDateFormat  OBJECT-TYPE
      SYNTAX  INTEGER
       {
          ddMMYYYY (1),
          mmDDYYYY (2),
          yyyyDDMM (3),
		  yyyyMMDD (4)
       }
      ACCESS  read-write
      STATUS  mandatory
      DESCRIPTION
      "This entry indicates the date and time format used for the
       agnSDateAndTimeCmd and for the alarm history report.
       MP-2100H, MP-2100 r1-r4 and MAXcess products do not support
       the 'yyyyMMDD' format."
      ::= { statAgnGen 1 }

agnSDateCmd  OBJECT-TYPE
      SYNTAX  DisplayString (SIZE (0..255))
      ACCESS  read-write
      STATUS  mandatory
      DESCRIPTION
      "This entry indicates the current date as it is known by the
       agent using its own real-time clock. The format would be as
       specified by the agnSDateFormat.
       This  parameter can be set for time synchronization between
       the NMS and the Agent."
      ::= { statAgnGen 2 }

agnSTimeCmd  OBJECT-TYPE
      SYNTAX  DisplayString (SIZE (0..255))
      ACCESS  read-write
      STATUS  mandatory
      DESCRIPTION
      "This entry indicates the current time as it is known by the
       agent using its own real-time clock.
       This  parameter can be set for time synchronization between
       the NMS and the Agent."
      ::= { statAgnGen 3 }

agnSActiveCnfg  OBJECT-TYPE
      SYNTAX  INTEGER
      ACCESS  read-only
      STATUS  mandatory
      DESCRIPTION
      "This entry specifies the unique identifier of the  configuration,
       that is currently  active and running."
      ::= { statAgnGen 4 }
-- return 1 (db1) in phase I

agnSEditCnfg OBJECT-TYPE
      SYNTAX  INTEGER
      ACCESS  read-only
      STATUS  mandatory
      DESCRIPTION
      "This entry indicates the  unique identifier of the
       configuration that is currently loaded into the tmp working
       space  for manipulation and update operations. Value of 255
       means no config. is under editing process."
      ::= { statAgnGen 5 }
-- return 1 (db1) in phase I

agnSLastCnfgFlipTime OBJECT-TYPE
      SYNTAX  DisplayString (SIZE (0..255))
      ACCESS  read-only
      STATUS  mandatory
      DESCRIPTION
      "This entry indicates the Date & Time of the last flip to the
       current configuration at the agent."
      ::= { statAgnGen 6 }
-- return sysUpTime in phase I

agnSLastCnfgFlipCause OBJECT-TYPE
      SYNTAX  DisplayString (SIZE (0..255))
      ACCESS  read-only
      STATUS  mandatory
      DESCRIPTION
      "This entry describes the flip's cause."
      ::= { statAgnGen 7 }
-- In phase I return two causes:
--          Power up
--          Update Db

agnSEditBy OBJECT-TYPE
      SYNTAX  INTEGER
       {
           none            (1),
           snmp            (2),
           terCon1         (3),
           terCon2         (4),
           terInbandCon1   (5),
           terInbandCon2   (6),
           lcd             (7)
       }
      ACCESS  read-only
      STATUS  mandatory
      DESCRIPTION
      "This entry indicates which MMI application is working on  the
       edited config.
       The editing phase starts at the first modify operation and
       ends after an update(load) operation."
      ::= { statAgnGen 8 }

agnSClkSrc  OBJECT-TYPE
      SYNTAX  INTEGER
    {
        master  (1),
        fallback(2),
        internal(3)
 }
      ACCESS  read-only
      STATUS  mandatory
      DESCRIPTION
     "This entry indicates the source of the system clock."
      ::= { statAgnGen 9 }

agnSAlrStatus OBJECT-TYPE
      SYNTAX  INTEGER
       {
  off      (2),
  event    (3),
  minor    (4),
  major    (5),
  warning  (6),
  critical (7)
       }
      ACCESS  read-only
      STATUS  mandatory
      DESCRIPTION
      "Indicates the alarm state in the agent level, i.e. lower
       level (card/port) alarms not included.
    critical(7) - when there is at least one active (state ON)
                  critical alarm,
                  otherwise it will be set to
       major(5) - when there is at least one active (state ON)
                  major alarm,
                  otherwise it will be set to
       minor(4) - if there is at least one active (state ON) minor
                  alarm,
                  otherwise it will be set to
       warning(6) - if there is at least one active (state ON)
                  warning alarm,
                  otherwise it will be set to
       event(3) - if there was at least one alarm event (including
                  state on,off events) since the last clear operation."
      ::= { statAgnGen 10 }

agnSAlrStatusAll OBJECT-TYPE
      SYNTAX  INTEGER
       {
  off      (2),
  event    (3),
  minor    (4),
  major    (5),
     warning  (6),
  critical (7)
       }
      ACCESS  read-only
      STATUS  mandatory
      DESCRIPTION
      "Indicates the alarm state of the entire agent, i.e.
       including card and port alarms status.
    critical(7) - when there is at least one active (state ON)
                  critical alarm,
                  otherwise it will be set to
       major(5) - when there is at least one active (state ON)
                  major alarm,
                  otherwise it will be set to
       minor(4) - if there is at least one active (state ON) minor
                  alarm,
                  otherwise it will be set to
       warning(6) - if there is at least one active (state ON)
                  warning alarm,
                  otherwise it will be set to
       event(3) - if there was at least one alarm event (including
                  state on,off events) since the last clear operation."
      ::= { statAgnGen 11 }

agnSMaskedAlrStat OBJECT-TYPE
      SYNTAX  INTEGER
       {
  off      (2),
  event    (3),
  minor    (4),
  major    (5),
     warning  (6),
  critical (7)
       }
      ACCESS  read-only
      STATUS  mandatory
      DESCRIPTION
      "Indicates the alarm state in the agent level,[ i.e. lower
       level (card/port) alarms not included] including Masked
       alarms.
    critical(7) - when there is at least one active (state ON)
                  critical alarm,
                  otherwise it will be set to
       major(5) - when there is at least one active (state ON)
                  major alarm,
                  otherwise it will be set to
       minor(4) - if there is at least one active (state ON) minor
                  alarm,
                  otherwise it will be set to
       warning(6) - if there is at least one active (state ON)
                  warning alarm,
                  otherwise it will be set to
       event(3) - if there was at least one alarm event (including
                  state on,off events) since the last clear operation."
      ::= { statAgnGen 12 }

agnSMaskedAlrStatAll OBJECT-TYPE
      SYNTAX  INTEGER
       {
  off      (2),
  event    (3),
  minor    (4),
  major    (5),
     warning  (6),
  critical (7)
       }
      ACCESS  read-only
      STATUS  mandatory
      DESCRIPTION
      "Indicates the alarm state of the entire agent, i.e.
       including card and port alarms status,including
       Masked alarms.
    critical(7) - when there is at least one active (state ON)
                  critical alarm,
                  otherwise it will be set to
       major(5) - when there is at least one active (state ON)
                  major alarm,
                  otherwise it will be set to
       minor(4) - if there is at least one active (state ON) minor
                  alarm,
                  otherwise it will be set to
       warning(6) - if there is at least one active (state ON)
                  warning alarm,
                  otherwise it will be set to
       event(3) - if there was at least one alarm event (including
                  state on,off events) since the last clear operation."
      ::= { statAgnGen 13 }

agnSTstStatAll OBJECT-TYPE
      SYNTAX  INTEGER
       {
  off(2),
  on (3)
       }
      ACCESS  read-only
      STATUS  mandatory
      DESCRIPTION
      "on(3) - when there is at least one test in progress in one
               of the agent cards,
       otherwise the value will be off(2)."
      ::= { statAgnGen 14 }

agnSAlrTable OBJECT-TYPE
      SYNTAX SEQUENCE OF AgnSAlrEntry
      ACCESS not-accessible
      STATUS mandatory
      DESCRIPTION
      "List of agent related alarms and indications for alarms at
       system level."
      ::= { statAgnGen 15 }

agnSAlrEntry OBJECT-TYPE
      SYNTAX AgnSAlrEntry
      ACCESS not-accessible
      STATUS mandatory
       	  		 DESCRIPTION ""
INDEX { agnSAlrIdx}
      ::= { agnSAlrTable 1}

AgnSAlrEntry ::=
      SEQUENCE {
  agnSAlrIdx              INTEGER,
  agnSAlrCodeDescription  DisplayString (SIZE (0..255)),
  agnSAlrCode             INTEGER,
  agnSAlrSeverity         INTEGER,
  agnSAlrState            INTEGER,
  agnSAlrCounter          INTEGER,
  agnSAlrMask             INTEGER,
  agnSAlrInvert           INTEGER
      }

agnSAlrIdx OBJECT-TYPE
      SYNTAX  INTEGER
      ACCESS  read-only
      STATUS  mandatory
      DESCRIPTION
      "A unique number to identify an entry in the alarm status table
       of the agent."
      ::= { agnSAlrEntry 1 }

agnSAlrCodeDescription OBJECT-TYPE
      SYNTAX  DisplayString (SIZE (0..255))
      ACCESS  read-only
      STATUS  mandatory
      DESCRIPTION
      "This attribute is a full text description of the alarm .
       The alarm description includes the following information:
       alarm code, alarm text, alarm severity, Masked or Inverted
       flag and counter."
     ::= { agnSAlrEntry 2 }

agnSAlrCode OBJECT-TYPE
      SYNTAX  INTEGER
      ACCESS  read-only
      STATUS  mandatory
      DESCRIPTION
      "A code identifying the alarm of an entry in the alarm status
       table at system level."
      ::= { agnSAlrEntry 3 }

agnSAlrSeverity OBJECT-TYPE
      SYNTAX  INTEGER
       {
  event    (3),
  minor    (4),
  major    (5),
     warning  (6),
  critical (7)
       }
      ACCESS  read-only
      STATUS  mandatory
      DESCRIPTION
      "The severity of the alarm."
      ::= { agnSAlrEntry 4 }

agnSAlrState  OBJECT-TYPE
      SYNTAX  INTEGER
       {
  off(2),
  on (3)
       }
      ACCESS  read-only
      STATUS  mandatory
      DESCRIPTION
      "State of the alarm."
      ::= { agnSAlrEntry 5 }

agnSAlrCounter OBJECT-TYPE
      SYNTAX  INTEGER
      ACCESS  read-only
      STATUS  mandatory
      DESCRIPTION
      "A counter - how many times the alarm occured since last
       clear operation.
       ON and OFF Alarm will be counted separately."
      ::= { agnSAlrEntry 6 }

agnSAlrMask  OBJECT-TYPE
      SYNTAX  INTEGER
       {
  off(2),
  on (3)
       }
      ACCESS  read-only
      STATUS  mandatory
      DESCRIPTION
      "Alarm mask : on/off."
      ::= { agnSAlrEntry 7 }

agnSAlrInvert  OBJECT-TYPE
      SYNTAX  INTEGER
       {
  off(2),
  on (3)
       }
      ACCESS  read-only
      STATUS  mandatory
      DESCRIPTION
      "Alarm invert : on/off."
      ::= { agnSAlrEntry 8 }


agnSClearAlrCmd  OBJECT-TYPE
      SYNTAX  INTEGER
       {
  off(2),
  on (3)
       }
      ACCESS  read-write
      STATUS  mandatory
      DESCRIPTION
      "Setting this attribute to ON, enforce a  clear operation on
       all the agent(general) events. General alarms are alarms
       which are not specific to a card or port. The clear
       operation will not be applied for masked/inverted alarms."
      ::= { statAgnGen 16 }

agnSClearAllAlrCmd OBJECT-TYPE
      SYNTAX  INTEGER
       {
  off(2),
  on (3)
       }
      ACCESS  read-write
      STATUS  mandatory
      DESCRIPTION
      "Setting this attribute to ON, enforce a clear operation on
       all MUX alarm events at the levels of agent, slots and ports.
       The clear operation will not be applied for masked/inverted
       alarms."
      ::= { statAgnGen 17 }

agnSSanityCheckStatus OBJECT-TYPE
      SYNTAX  INTEGER
       {
  unknown (1),
  fail    (2),
  warning (3),
  ok      (4)
       }
      ACCESS  read-only
      STATUS  mandatory
      DESCRIPTION
      "Upon completion of the Sanity check process on the TmpCnfg
       this attribute will be set to:
       FAIL(2) - when there is at least one error encountered and
                 possibly some warnings.
       WARNING(3) - when there are only warnings.
       otherwise, the value will be OK(4).
       The value will be UNKNOWN(1) if changes were made in the
       TmpCnfg following the last Sanity check."
      ::= { statAgnGen 18 }

agnSNoOfSanityCheckErr OBJECT-TYPE
      SYNTAX  INTEGER
      ACCESS  read-only
      STATUS  mandatory
      DESCRIPTION
      "This entry indicates the number of errors/warnings discovered
       by the last SanityCheck process."
      ::= { statAgnGen 19 }

agnSErrListTable OBJECT-TYPE
      SYNTAX SEQUENCE OF AgnSErrListEntry
      ACCESS not-accessible
      STATUS mandatory
      DESCRIPTION
      "List of errors and warnings found during Sanity Check
       process."
      ::= { statAgnGen 20 }

agnSErrListEntry OBJECT-TYPE
      SYNTAX AgnSErrListEntry
      ACCESS not-accessible
      STATUS mandatory
       	  		 DESCRIPTION ""
INDEX { agnSErrIdx}
      ::= { agnSErrListTable 1}

AgnSErrListEntry ::=
      SEQUENCE {
  agnSErrIdx          INTEGER,
     agnSErrDescription  DisplayString (SIZE (0..255))
               }

agnSErrIdx OBJECT-TYPE
      SYNTAX  INTEGER
      ACCESS  read-only
      STATUS  mandatory
      DESCRIPTION
      "Unique number to identify an entry in the  error list table.
       The maximum entry  value cannot exceed the value of
       'agnSNoOfSanityCheckErr'. "
    ::= { agnSErrListEntry 1}

agnSErrDescription OBJECT-TYPE
      SYNTAX  DisplayString (SIZE (0..255))
      ACCESS  read-only
      STATUS  mandatory
      DESCRIPTION
      "This attribute is a full text description of the sanity check
       error including error code, slot and port numbers related to
       the code ."
  ::= { agnSErrListEntry 2}

agnSMaxNoOfCnfg OBJECT-TYPE
      SYNTAX  INTEGER
      ACCESS  read-only
      STATUS  mandatory
      DESCRIPTION
      "Maximum number of configurations that can be defined and
       stored in the MUX.
       If the mux has a large capacity, the maximum will be limited
       to  254."
      ::= { statAgnGen 21}
-- return 1 (db1) in phase I

agnSCnfgTable OBJECT-TYPE
      SYNTAX SEQUENCE OF AgnSCnfgEntry
      ACCESS not-accessible
      STATUS  mandatory
      DESCRIPTION
      "This table contains an entry per configuration. It indicates
       if the configuration is valid."
      ::= { statAgnGen 22 }
--  - in phase I only one entry

agnSCnfgEntry OBJECT-TYPE
      SYNTAX AgnSCnfgEntry
      ACCESS not-accessible
      STATUS mandatory
       	  		 DESCRIPTION ""
INDEX { agnSEntryIdx}
      ::= {agnSCnfgTable  1}

AgnSCnfgEntry ::=
      SEQUENCE  {
 agnSEntryIdx         INTEGER,
 agnSEntryIsValid     INTEGER
      }

agnSEntryIdx OBJECT-TYPE
      SYNTAX  INTEGER
      ACCESS  read-only
      STATUS  mandatory
      DESCRIPTION
      "Unique number to identify an entry in the configuration table."
    ::= { agnSCnfgEntry 1}

agnSEntryIsValid OBJECT-TYPE
      SYNTAX  INTEGER
       {
  no  (2),
  yes (3)
       }
      ACCESS  read-only
      STATUS  mandatory
      DESCRIPTION
      "This attribute indicates whether the specific configuration
       is valid in the MUX . Value of NO indicates: no such
       configuration  in the MUX. "
    ::= { agnSCnfgEntry 2}

--
-- Wan agent configuration information
--
agnCSanityCheckCmd OBJECT-TYPE
      SYNTAX  INTEGER
       {
       off(2),
       on (3)
       }
      ACCESS  read-write
      STATUS  mandatory
      DESCRIPTION
      "Setting this attribute to on(3) will initiate the process
       of Sanity check on the TmpCnfg. Upon completion the value
       will automatically be changed to off(2)."
      ::= { cnfgAgnGen 1 }

agnCSaveCnfgIdxCmd OBJECT-TYPE
      SYNTAX  INTEGER   (1..100)
      ACCESS  read-write
      STATUS  mandatory
      DESCRIPTION
      "This attribute specifies the Id of the target RealCnfg to
       which the TmpCnfg should be transferred. Upon set command the
       MUX will initiate the Sanity-Check  process first. If
       successful, the actual transfer will be performed. If warnings
       are detected, the user will have to perform the command again
       to confirm the operation. Setting this object a second time
       to the same value without performing any change in the database,
       will cause the result: agnSSanityCheckStatus = unknown"
      ::= { cnfgAgnGen 2 }
-- In phase I only the value 1 (Cnfg1) is valid.

agnCLoadCnfgIdxCmd OBJECT-TYPE
      SYNTAX  INTEGER  (1..100)
      ACCESS  read-write
      STATUS  mandatory
      DESCRIPTION
      "This attribute specifies the Id of the source Cnfg to be
       loaded into the TmpCnfg. Upon set operation the actual
       transfer will be initiated.
       The operation is valid only on Valid configurations
       (agnSEntryIsValid)"
      ::= { cnfgAgnGen 3 }
-- In phase I only the value 1 (Cnfg1) is valid.


agnCClkSrcTable  OBJECT-TYPE
      SYNTAX SEQUENCE OF AgnCClkSrcEntry
      ACCESS not-accessible
      STATUS  mandatory
      DESCRIPTION
      "All the entries of this table are identical (have the same
       value) for all the configurations (1..100) except the
       TmpCnfg.
       The write operation into the Table Objects is valid only
       for the TmpCnfg entry."
       ::= { cnfgAgnGen 4}

agnCClkSrcEntry OBJECT-TYPE
      SYNTAX AgnCClkSrcEntry
      ACCESS not-accessible
      STATUS mandatory
       	  		 DESCRIPTION ""
INDEX {agnCClkCnfgIdx, agnCClkSrcIdx}
      ::= { agnCClkSrcTable 1}

AgnCClkSrcEntry ::=
      SEQUENCE {
   agnCClkCnfgIdx      INTEGER,
   agnCClkSrcIdx       INTEGER,
   agnCClkSrcMode      INTEGER,
   agnCClkSrcSlt       INTEGER,
   agnCClkSrcPrt       INTEGER
      }

agnCClkCnfgIdx OBJECT-TYPE
      SYNTAX INTEGER (1..255)
      ACCESS read-only
      STATUS mandatory
      DESCRIPTION
      "This attribute indicates the Idx of the Cnfg(1..100) being
       accessed and Idx 255 relates to the TmpCnfg."
      ::= { agnCClkSrcEntry 1}
-- In phase I only the values 1 (Cnfg1) and 255 (temp) are valid.

agnCClkSrcIdx OBJECT-TYPE
      SYNTAX  INTEGER (1..2)
      ACCESS  read-only
      STATUS  mandatory
      DESCRIPTION
      "An index to the table. There are only two entries to this
       table.
       Index 1 points to the Master clock parameters and Index 2
       points to the Fallback clock parameters"
      ::= { agnCClkSrcEntry 2}

agnCClkSrcMode OBJECT-TYPE
      SYNTAX  INTEGER
       {
           internal   (1),
           rxClk      (2)
       }
      ACCESS  read-write
      STATUS  mandatory
      DESCRIPTION
      "The source of the nodal timing."
      ::= { agnCClkSrcEntry 3}

agnCClkSrcSlt OBJECT-TYPE
      SYNTAX  INTEGER
        {
          notApplicable   (1),
       io1   (5),
       io2   (6),
       io3   (7),
       io4   (8),
       io5   (9),
       io6  (10),
       io7  (11),
       io8  (12),
       io9  (13),
       io10 (14),
       io11 (15),
       io12 (16)
     }
      ACCESS  read-write
      STATUS  mandatory
      DESCRIPTION
      "This entry is valid only when we are working in rxClk mode.
       For an invalid entry, the return value will be '7fff'h."
      ::= { agnCClkSrcEntry 4}

agnCClkSrcPrt OBJECT-TYPE
      SYNTAX  INTEGER
      {
     exPrt1    (1) ,
     exPrt2    (2) ,
     exPrt3    (3) ,
     exPrt4    (4) ,
     exPrt5    (5) ,
     exPrt6    (6) ,
     exPrt7    (7) ,
     exPrt8    (8) ,
     exPrt9    (9) ,
     exPrt10  (10) ,
     exPrt11  (11) ,
     exPrt12  (12) ,
     notApplicable   (100)
      }
      ACCESS  read-write
      STATUS  mandatory
      DESCRIPTION
      "This entry is valid only when we are working in rxClk mode.
       For an invalid entry, the return value will be '7fff'h."
      ::= { agnCClkSrcEntry 5}


agnCDeleteCnfgIdxCmd OBJECT-TYPE
  SYNTAX  INTEGER (1..100)
  ACCESS  read-write
  STATUS  mandatory
  DESCRIPTION
  "Setting this attribute will delete the requested DB
   from the NVRAM ."
  ::= { cnfgAgnGen 5 }

agnCDefaultCnfgIdxCmd OBJECT-TYPE
  SYNTAX  INTEGER (1..100)
  ACCESS  read-write
  STATUS  mandatory
  DESCRIPTION
  "Setting this attribute will define the desired working
   configuration when no conditions of the Flip DB Table are
   fulfilled and no Net GO command was issued. This command
   will be accepted only if the Configuration number exists
   (agnSEntryIsValid=yes)."
  ::= { cnfgAgnGen 6 }

agnCnfgDataTable OBJECT-TYPE
      SYNTAX SEQUENCE OF AgnCnfgDataEntry
      ACCESS not-accessible
      STATUS  mandatory
      DESCRIPTION
      "This table contains data about the agent configurations.
       The table will support only data about valid configurations
       of the agent."
       ::= { cnfgAgnGen 7}

agnCnfgDataEntry OBJECT-TYPE
      SYNTAX AgnCnfgDataEntry
      ACCESS not-accessible
      STATUS mandatory
       	  		 DESCRIPTION ""
INDEX {agnCnfgIdx}
      ::= { agnCnfgDataTable 1}

AgnCnfgDataEntry ::=
      SEQUENCE {
   agnCnfgIdx      INTEGER,
   agnCnfgDesc     DisplayString,
   agnCnfgUpdDate  DisplayString,
   agnCnfgUpdTime  DisplayString,
   agnCnfgUpdMnger IpAddress
      }

agnCnfgIdx OBJECT-TYPE
      SYNTAX INTEGER (1..255)
      ACCESS read-only
      STATUS mandatory
      DESCRIPTION
      "This object indicates the Idx of the agent' Cnfg the following 
       objects refer.
       255=Temporary Cnfg (Set is done only to this configuration)."
      ::= { agnCnfgDataEntry 1}
-- Only the values 1..10, 255 are valid.

agnCnfgDesc OBJECT-TYPE
      SYNTAX DisplayString (SIZE (0..30))
      ACCESS read-write
      STATUS mandatory
      DESCRIPTION
      "This object is a description of the Configuration, entered
       by user, to enhance Cnfg recognition."
      ::= { agnCnfgDataEntry 2}

agnCnfgUpdDate  OBJECT-TYPE
      SYNTAX  DisplayString (SIZE (0..255))
      ACCESS  read-only
      STATUS  mandatory
      DESCRIPTION
      "This object indicates the date when last update of this
       configuration was performed, as it is known by the
       agent using its own real-time clock. The format would be as
       specified by the agnSDateFormat.
       When update is performed, the agent should save the date."
      ::= { agnCnfgDataEntry 3 }

agnCnfgUpdTime  OBJECT-TYPE
      SYNTAX  DisplayString (SIZE (0..255))
      ACCESS  read-only
      STATUS  mandatory
      DESCRIPTION
      "This object indicates the time when last update of this
       configuration was performed, as it is known by the
       agent using its own real-time clock.
       When update is performed, the agent should save the time."
      ::= { agnCnfgDataEntry 4 }

agnCnfgUpdMnger  OBJECT-TYPE
      SYNTAX  IpAddress
      ACCESS  read-only
      STATUS  mandatory
      DESCRIPTION
      "This object indicates the IP Address of the Manager who
       performed the last update of this configuration.
       When update is performed, the agent should save the
       IP Address of the Manager who commanded the update.
       That will enable a manager to know if he performed the last
       update, or another manager did."
      ::= { agnCnfgDataEntry 5 }


agnCnfgAlarm   OBJECT IDENTIFIER ::= { cnfgAgnGen 8}

agnCnfgAlrFilterWindow OBJECT-TYPE
      SYNTAX INTEGER (0..30)
      ACCESS read-write
      STATUS mandatory
      DESCRIPTION
      "Window of time, in minutes.
       During this Window, the alarms filter is performed.
       Same Window for all agent alarms that need filtering.
       Upon end of the Window, the state of the alarm is updated
       and a new Window starts.
       If no alarm needs filtering, this object's value will not be
       used."
      ::= { agnCnfgAlarm 1}

agnCnfgAlrTable OBJECT-TYPE
      SYNTAX SEQUENCE OF AgnCnfgAlrEntry
      ACCESS not-accessible
      STATUS  mandatory
      DESCRIPTION
      "This table enables the user to set attributes to each alarm.
       Setting  for a non-existing entry agnCnfgAlrMask,
       agnCnfgAlrInvert or agnCnfgAlrFilter to 'yes'(or yesAndSave
       for Mask) will add this new entry to the table.
       Setting  for an existing entry agnCnfgAlrMask/
       agnCnfgAlrInvert/agnCnfgAlrFilter (one or more) to 'no'
       (noAndSave for Mask)  so that ALL  these objects' values are
       'no' , will delete this entry from the table.
       For agnCnfgAlrMask, only if [(last saved value=noAndSave)
       AND (new value is 'no' or 'noAndSave')] the object's value
       is considered 'no' for deleting the entry."
       ::= { agnCnfgAlarm 2}

agnCnfgAlrEntry OBJECT-TYPE
      SYNTAX AgnCnfgAlrEntry
      ACCESS not-accessible
      STATUS mandatory
       	  		 DESCRIPTION ""
INDEX {agnCnfgAlrCode, agnCnfgAlrSlot, agnCnfgAlrPort}
      ::= { agnCnfgAlrTable 1}

AgnCnfgAlrEntry ::=
      SEQUENCE {
   agnCnfgAlrCode        INTEGER,
   agnCnfgAlrSlot        INTEGER,
   agnCnfgAlrPort        INTEGER,
   agnCnfgAlrMask        INTEGER,
   agnCnfgAlrInvert      INTEGER,
   agnCnfgAlrFilter      INTEGER,
   agnCnfgAlrFilterSet   INTEGER,
   agnCnfgAlrFilterReset INTEGER
      }

agnCnfgAlrCode OBJECT-TYPE
      SYNTAX INTEGER
      ACCESS read-only
      STATUS mandatory
      DESCRIPTION
      "The alarm code. The following attributes refer this code."
      ::= { agnCnfgAlrEntry 1 }

agnCnfgAlrSlot OBJECT-TYPE
      SYNTAX INTEGER
      {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16),
       io13 (17),
       io14 (18),
       io15 (19),
       all           (200),
       notApplicable (255)
   }
      ACCESS read-only
      STATUS mandatory
      DESCRIPTION
      "The alarm slot. The following attributes apply for the alarm
       code and slot selected.
    all = the attributes apply to all slots.
       notApplicable = the selected alarm is for system level."
      ::= { agnCnfgAlrEntry 2 }

agnCnfgAlrPort OBJECT-TYPE
      SYNTAX INTEGER
      ACCESS read-only
      STATUS mandatory
      DESCRIPTION
      "The alarm port. The following attributes apply for the alarm
       code,slot and port selected.
       200 = all = the attributes apply to all ports of the selected slot.
             When selected Slot is 'all', only 'all' or	'notApplicable' are valid  
             Port selections.
       notApplicable = the selected alarm is for system or card
                       level.
					   =255 for MP
					   =100 for DXC
	   - For MP, valid cards' ports are: exPrt1(1)..exPrt12(12)
										 inPrt1(101)..inPrt48 (148)
	   - For DXC, the port index will include the Slot, as for all DXC 
	     tables: [(IO Slot+10)&n]  ; n=odd  for external ports
		                             n=even for internal ports."
      ::= { agnCnfgAlrEntry 3 }

agnCnfgAlrMask OBJECT-TYPE
      SYNTAX INTEGER
      {
       no         (1),
       noAndSave  (2),
       yes        (3),
       yesAndSave (4)
   }
      ACCESS read-write
      STATUS mandatory
      DESCRIPTION
      "An attribute defining the desired Mask state of an alarm .
       no - unmask (this command is not saved in agent's common
            database)
       noAndSave -  unmask ; this command is saved in agent's
             common database
       yes - mask  (this command is not saved in agent's
             common database)
       yesAndSave - mask  ; this command is saved in
             agent's common database.
       Commands that are not saved, will be lost upon power-up or
       selected card removal.      "
      ::= { agnCnfgAlrEntry 4 }

agnCnfgAlrInvert OBJECT-TYPE
      SYNTAX INTEGER
      {
       no            (2),
       yes           (3)
   }
      ACCESS read-write
      STATUS mandatory
      DESCRIPTION
      "An attribute defining the desired Invert state of an alarm .
       no  - not inverted.
       yes - inverted. For MP, it is not applicable for alarms
             that are currently OFF."
      ::= { agnCnfgAlrEntry 5 }

agnCnfgAlrFilter OBJECT-TYPE
      SYNTAX INTEGER
      {
       no            (2),
       yes           (3)
   }
      ACCESS read-write
      STATUS mandatory
      DESCRIPTION
      "An attribute defining if Filter is desired for the alarm .
       no  - no  filter.
       yes - filter activate.

       This filter is activated within a window of time defined by
       agnCnfgAlrFilterWindow.
       Its purpose is to avoid frequent changes of an alarm between
       ON/OFF states."
      ::= { agnCnfgAlrEntry 6 }

agnCnfgAlrFilterSet OBJECT-TYPE
      SYNTAX INTEGER
      ACCESS read-write
      STATUS mandatory
      DESCRIPTION
      "This is a top threshold causing the alarm that passes it,
       to be declared Set (ON) at the end of the respective
       window of time.
       - For alarms defined by default as state alarms (minor,major)
         this value will be in [%].
       - For alarms defined by default as events, this value will be
         an integer meaning how many times this event should appear
         at least, during the window in order to be considered ON.
   The maximum valuewill be 255.
       This value should be greater than the one of
       agnCnfgAlrFilterReset.
       Agents that do not support Alarms Filter, will return 0."
      ::= { agnCnfgAlrEntry 7 }

agnCnfgAlrFilterReset OBJECT-TYPE
      SYNTAX INTEGER
      ACCESS read-write
      STATUS mandatory
      DESCRIPTION
      "This is a bottom threshold causing the alarm that does not
       pass it, to be declared Reset (ON) at the end of the
       respective window of time.
       - For alarms defined by default as state alarms (minor,major)
         this value will be in [%].
       - For alarms defined by default as events, this value will be
         an integer meaning how many times this event should appear
         at most, during the window, in order to be considered OFF.
       This value should be less than the one of
       agnCnfgAlrFilterSet.
       Agents that do not support Alarms Filter, will return 0."
      ::= { agnCnfgAlrEntry 8 }


agnCnfgAlrReportTable OBJECT-TYPE
      SYNTAX SEQUENCE OF AgnCnfgAlrReportEntry
      ACCESS not-accessible
      STATUS  mandatory
      DESCRIPTION
      "This table enables the user to configure the desired Alarm
       Reports according to alarms severity."
       ::= { agnCnfgAlarm 3}

agnCnfgAlrReportEntry OBJECT-TYPE
      SYNTAX AgnCnfgAlrReportEntry
      ACCESS not-accessible
      STATUS mandatory
       	  		 DESCRIPTION ""
INDEX {agnCnfgAlrReportType}
      ::= { agnCnfgAlrReportTable 1}

AgnCnfgAlrReportEntry ::=
      SEQUENCE {
   agnCnfgAlrReportType        INTEGER,
   agnCnfgAlrStartReportOn     INTEGER,
   agnCnfgAlrStartReportOff    INTEGER
      }

agnCnfgAlrReportType OBJECT-TYPE
      SYNTAX INTEGER
         {
          trap        (1),
          buffer      (2),
          relay       (3),	 --Minor Relay
          alrLedOn    (4),	 --Minor LED
          alrLedBlink (5),	 --Major LED
		  relay2      (6)    --Major Relay
         }
      ACCESS read-only
      STATUS mandatory
      DESCRIPTION
      "The alarm report type.
       trap - traps will be sent only for alarms having the
              selected On/Off severity or higher.
       buffer - only alarms having the selected On/Off severity and
                higher, will be reported to the buffer.
       relay -  relay contact will be activated only for alarms
                having the selected On severity or higher.
				For products having 2 relays, this is the Minor Relay.

       alrLedOn/alrLedBlink - user should select a higher severity
                (ReportOn) for alrLedBlink than for alrLedOn
                (Blinking Led means a more severe alarm than steady
                 ON Led).
       alrLedOn - MTCL-1 Alarm Led will be ON only when
                agnSAlrStatusAll equals the selected severity or
                higher, but lower severity than that selected for
                'alrLedBlink'.
				For products having 2 LEDs, this is the Minor LED.
       alrLedBlink - MTCL-1 Alarm Led will Blink only when
                agnSAlrStatusAll equals the selected severity or
                higher.
				For products having 2 LEDs, this is the Major LED.
       relay2 -  relay 2 contact will be activated only for alarms
                having the selected On severity or higher.
				This is the Major Relay."
      ::= { agnCnfgAlrReportEntry 1 }

agnCnfgAlrStartReportOn OBJECT-TYPE
      SYNTAX INTEGER
         {
          noReport (2),
          event    (3),
          minor    (4),
          major    (5),
          warning  (6),
          critical (7)
         }  
      ACCESS read-write
      STATUS mandatory
      DESCRIPTION
      "This object specifies the severity from which alarms will 
       be reported. Alarms having this severity or higher, will be
       reported.
       This object specifies the report severity only for alarms
       that turn to ON state.
       noReport - no Report at all (for any severity)."
      ::= { agnCnfgAlrReportEntry 2 }

agnCnfgAlrStartReportOff OBJECT-TYPE
      SYNTAX INTEGER
         {
        notApplicable (1),
        noReport (2),
        event    (3),
        minor    (4),
        major    (5),
        warning  (6),
        critical (7)
         }  
      ACCESS read-write
      STATUS mandatory
      DESCRIPTION
      "This object specifies the severity from which alarms will 
       be reported. Alarms having this severity or higher, will be
       reported.
       This object specifies the report severity only for alarms
       that turn to OFF state. 
       notApplicable - for 'relay','alrLedOn','alrLedBlink', 'relay2' report 
                       types, in MP.
       noReport - no Report at all (for any severity)."
      ::= { agnCnfgAlrReportEntry 3 }

agnCOffsetCmd OBJECT-TYPE
      SYNTAX INTEGER
      {
       notApplicable (1),
       normal        (2),
       u1            (3)
      }
      ACCESS read-write
      STATUS mandatory
      DESCRIPTION
      "An object defining special user request.
       notApplicable - is RO value for products that do not support this object.
       normal -  nothing special
       u1 - user 1 - for all Voice cards, the DISPLAYED Tx and Rx Levels
            will have the following Offsets:
            - 2 Wires port: Tx Level: the base value (for 0dBm) = 0
                            Rx Level: the base value (for 0dBm) = -2
            - 4 Wires port: Tx Level: the base value (for 0dBm) = -16
                            Rx Level: the base value (for 0dBm) = 7    
            The MIB and application DB will use the values without Offset."
      ::= { cnfgAgnGen 9 }

--
-- Compressed information.
--
-- Specially for RadView management station
--
agnCmprTable  OBJECT-TYPE
      SYNTAX SEQUENCE OF AgnCmprEntry
      ACCESS not-accessible
      STATUS  mandatory
      DESCRIPTION "" ::= { cmprAgnGen 1 }

agnCmprEntry OBJECT-TYPE
      SYNTAX AgnCmprEntry
      ACCESS not-accessible
      STATUS mandatory
       	  		 DESCRIPTION ""
INDEX { agnCmprTypIdx, agnCmprCnfgIdx ,agnCmprVersion}
      ::= {agnCmprTable  1}

AgnCmprEntry ::=
      SEQUENCE {
     agnCmprTypIdx      INTEGER,
     agnCmprCnfgIdx     INTEGER,
     agnCmprVersion     INTEGER,
     agnCmprObj         OCTET STRING
      }

agnCmprTypIdx OBJECT-TYPE
      SYNTAX  INTEGER
      ACCESS  read-only
      STATUS  mandatory
      DESCRIPTION
      "This attribute indicates the Type of the Compressed being
       referred."
      ::= { agnCmprEntry 1}

agnCmprCnfgIdx OBJECT-TYPE
      SYNTAX  INTEGER
      ACCESS  read-only
      STATUS  mandatory
      DESCRIPTION
      "This attribute indicates the configuration to which the
       Compressed information is  related."
      ::= { agnCmprEntry 2}

agnCmprVersion OBJECT-TYPE
      SYNTAX  INTEGER
      ACCESS  read-only
      STATUS  mandatory
      DESCRIPTION
      "This attribute indicates the version of the internal format
       of the Compressed data"
      ::= { agnCmprEntry 3}

agnCmprObj OBJECT-TYPE
      SYNTAX  OCTET STRING
      ACCESS  read-write
      STATUS  mandatory
      DESCRIPTION
      "This attribute is the compressed information itself."
      ::= { agnCmprEntry 4}


-- Compressed Dlci table in the Agent level
-- The only way of reading this table is by the command 'GET NEXT'

agnDlciCmprTable  OBJECT-TYPE
      SYNTAX SEQUENCE OF AgnDlciCmprEntry
      ACCESS not-accessible
      STATUS  mandatory
      DESCRIPTION "" ::= {cmprAgnGen 2}

agnDlciCmprEntry OBJECT-TYPE
      SYNTAX AgnDlciCmprEntry
      ACCESS not-accessible
      STATUS mandatory
       	  		 DESCRIPTION ""
INDEX {agnDlciCmprCnfgIdx,agnDlciCmprVersion,agnDlciCmprDlciIdx}
      ::= {agnDlciCmprTable  1}

AgnDlciCmprEntry ::=
      SEQUENCE {
     agnDlciCmprCnfgIdx       INTEGER,
     agnDlciCmprVersion       INTEGER,
     agnDlciCmprDlciIdx       INTEGER,
     agnDlciCmprObj          OCTET STRING
      }

agnDlciCmprCnfgIdx OBJECT-TYPE
      SYNTAX  INTEGER
      ACCESS  read-only
      STATUS  mandatory
      DESCRIPTION
      "This attribute indicates the configuration to which the
       Compressed information is  related."
      ::= { agnDlciCmprEntry 1}

agnDlciCmprVersion OBJECT-TYPE
      SYNTAX  INTEGER
      ACCESS  read-only
      STATUS  mandatory
      DESCRIPTION
      "This attribute indicates the version of the internal format
       of the Compressed data"
      ::= { agnDlciCmprEntry 2}

agnDlciCmprDlciIdx  OBJECT-TYPE
      SYNTAX  INTEGER
      ACCESS  read-only
      STATUS  mandatory
      DESCRIPTION
      "This attribute indicates a unique identifier of  the Dlci,
       the compressed information relates to.
       The values are between 16 - 991."
      ::= { agnDlciCmprEntry 3}

agnDlciCmprObj OBJECT-TYPE
      SYNTAX  OCTET STRING
      ACCESS  read-write
      STATUS  mandatory
      DESCRIPTION
      "This attribute is the compressed information itself."
      ::= { agnDlciCmprEntry 4}

-- Compressed Status Alarm table at the Agent level
-- The only way of reading this table is by the command 'GET NEXT'

agnAlarmsCmprTable  OBJECT-TYPE
      SYNTAX SEQUENCE OF AgnAlarmsCmprEntry
      ACCESS not-accessible
      STATUS  mandatory
      DESCRIPTION "" ::= {cmprAgnGen 3}

agnAlarmsCmprEntry OBJECT-TYPE
      SYNTAX AgnAlarmsCmprEntry
      ACCESS not-accessible
      STATUS mandatory
       	  		 DESCRIPTION ""
INDEX {agnAlarmsCmprVersion,agnAlarmsCmprAlarmIdx}
      ::= {agnAlarmsCmprTable  1}

AgnAlarmsCmprEntry ::=
      SEQUENCE {
     agnAlarmsCmprVersion      INTEGER,
     agnAlarmsCmprAlarmIdx     INTEGER,
     agnAlarmsCmprObj          OCTET STRING
      }

agnAlarmsCmprVersion OBJECT-TYPE
      SYNTAX  INTEGER
      ACCESS  read-only
      STATUS  mandatory
      DESCRIPTION
      "This attribute indicates the version of the internal
       format of the Compressed data"
      ::= { agnAlarmsCmprEntry 1}

agnAlarmsCmprAlarmIdx  OBJECT-TYPE
      SYNTAX  INTEGER
      ACCESS  read-only
      STATUS  mandatory
      DESCRIPTION
      "A unique number to identify an entry in the alarm status table
       of the agent."
      ::= { agnAlarmsCmprEntry 2}

agnAlarmsCmprObj OBJECT-TYPE
      SYNTAX  OCTET STRING
      ACCESS  read-only
      STATUS  mandatory
      DESCRIPTION
      "This attribute is the compressed information itself."
      ::= { agnAlarmsCmprEntry 3}

-- Compressed History Alarms buffer
-- The only way of reading this table is by the command 'GET NEXT'

agnAlrBufCmprTable  OBJECT-TYPE
      SYNTAX SEQUENCE OF AgnAlrBufCmprEntry
      ACCESS not-accessible
      STATUS  mandatory
      DESCRIPTION "" ::= {cmprAgnGen 4}

agnAlrBufCmprEntry OBJECT-TYPE
      SYNTAX AgnAlrBufCmprEntry
      ACCESS not-accessible
      STATUS mandatory
       	  		 DESCRIPTION ""
INDEX {agnAlrBufCmprVersion,agnAlrBufCmprAlarmIdx}
      ::= {agnAlrBufCmprTable  1}

AgnAlrBufCmprEntry ::=
      SEQUENCE {
     agnAlrBufCmprVersion      INTEGER,
     agnAlrBufCmprAlarmIdx     INTEGER,
     agnAlrBufCmprObj          OCTET STRING
      }

agnAlrBufCmprVersion OBJECT-TYPE
      SYNTAX  INTEGER
      ACCESS  read-only
      STATUS  mandatory
      DESCRIPTION
      "This attribute indicates the version of the internal format of
       the Compressed data"
      ::= { agnAlrBufCmprEntry 1}

agnAlrBufCmprAlarmIdx  OBJECT-TYPE
      SYNTAX  INTEGER
      ACCESS  read-only
      STATUS  mandatory
      DESCRIPTION
      "A unique number to identify an entry in the history alarms
       buffer of the agent."
      ::= { agnAlrBufCmprEntry 2}

agnAlrBufCmprObj OBJECT-TYPE
      SYNTAX  OCTET STRING
      ACCESS  read-only
      STATUS  mandatory
      DESCRIPTION
      "This attribute is the compressed information itself."
      ::= { agnAlrBufCmprEntry 3}


-- Compressed Sanity Errors buffer
-- The only way of reading this table is by the command 'GET NEXT'


agnSCmprErrListTable OBJECT-TYPE
      SYNTAX SEQUENCE OF AgnSCmprErrListEntry
      ACCESS not-accessible
      STATUS mandatory
      DESCRIPTION "" ::= { cmprAgnGen 5 }

agnSCmprErrListEntry OBJECT-TYPE
      SYNTAX AgnSCmprErrListEntry
      ACCESS not-accessible
      STATUS mandatory
       	  		 DESCRIPTION ""
INDEX {agnSCmprErrVersion,agnSCmprErrIdx}
      ::= { agnSCmprErrListTable 1}

AgnSCmprErrListEntry ::=
      SEQUENCE {
     agnSCmprErrVersion      INTEGER,
     agnSCmprErrIdx          INTEGER,
     agnSCmprErrObj          OCTET STRING
      }

agnSCmprErrVersion OBJECT-TYPE
      SYNTAX  INTEGER
      ACCESS  read-only
      STATUS  mandatory
      DESCRIPTION
      "The version of the compressed data "
       ::= { agnSCmprErrListEntry 1}

agnSCmprErrIdx OBJECT-TYPE
      SYNTAX  INTEGER
      ACCESS  read-only
      STATUS  mandatory
      DESCRIPTION
      "Unique number to identify an entry in the errors list table.
       The maximum entry  value  cannot exceed the value of
       'agnSNoOfSanityCheckErr'. "
       ::= { agnSCmprErrListEntry 2}

agnSCmprErrObj OBJECT-TYPE
      SYNTAX  OCTET STRING
      ACCESS  read-only
      STATUS  mandatory
      DESCRIPTION
      "This attribute is a full text description of the error,
       including: error code, slot and port numbers related to the
       code ."
     ::= { agnSCmprErrListEntry 3}


-- New TS Assignment compressed table, per port 01/09/98
-- The only way of reading this table is by the command 'GET NEXT'

agnTsCmprTable  OBJECT-TYPE
      SYNTAX SEQUENCE OF AgnTsCmprEntry
      ACCESS not-accessible
      STATUS  mandatory
      DESCRIPTION "" ::= { cmprAgnGen 6 }

agnTsCmprEntry OBJECT-TYPE
      SYNTAX AgnTsCmprEntry
      ACCESS not-accessible
      STATUS mandatory
       	  		 DESCRIPTION ""
INDEX { agnTsCmprVerIdx,  agnTsCmprCnfgIdx , agnTsCmprSlotIdx,
              agnTsCmprPortIdx, agnTsCmprPduIdx }
      ::= {agnTsCmprTable  1}

AgnTsCmprEntry ::=
      SEQUENCE {
     agnTsCmprVerIdx      INTEGER,
     agnTsCmprCnfgIdx     INTEGER,
     agnTsCmprSlotIdx     INTEGER,
     agnTsCmprPortIdx     INTEGER,
     agnTsCmprPduIdx      INTEGER,
     agnTsCmprData        OCTET STRING
      }

agnTsCmprVerIdx OBJECT-TYPE
      SYNTAX  INTEGER
      ACCESS  read-only
      STATUS  mandatory
      DESCRIPTION
      "This object indicates the version of the internal format
       of the Compressed data."
      ::= { agnTsCmprEntry 1}

agnTsCmprCnfgIdx OBJECT-TYPE
      SYNTAX  INTEGER
      ACCESS  read-only
      STATUS  mandatory
      DESCRIPTION
      "This object indicates the configuration to which the
       Compressed information is related.
       255=temporary configuration.
       Set can be performed only to the temporary configuration."
      ::= { agnTsCmprEntry 2}

agnTsCmprSlotIdx OBJECT-TYPE
      SYNTAX  INTEGER
      ACCESS  read-only
      STATUS  mandatory
      DESCRIPTION
      "This object indicates the Slot to which the
       Compressed information is  related.
       For MP-2100: IO-1..IO-12 = (5).. (16)
       For DXC-30 : IO-1..IO-15 = (5).. (19)."
      ::= { agnTsCmprEntry 3}

agnTsCmprPortIdx OBJECT-TYPE
      SYNTAX  INTEGER
      ACCESS  read-only
      STATUS  mandatory
      DESCRIPTION
      "This object indicates the Port within the Slot, to which the
       Compressed information is  related.
       For Port Index see each product's spec."
      ::= { agnTsCmprEntry 4}

agnTsCmprPduIdx OBJECT-TYPE
      SYNTAX  INTEGER
      ACCESS  read-only
      STATUS  mandatory
      DESCRIPTION
      "This object indicates the PDU index within the same port.
       That provides for the case when one PDU is not sufficient for all TS
       Assignment data of the same port."
      ::= { agnTsCmprEntry 5}

agnTsCmprData OBJECT-TYPE
      SYNTAX  OCTET STRING
      ACCESS  read-write
      STATUS  mandatory
      DESCRIPTION
      "This object is the compressed information itself. It provides
       information about all TSs of a port."
      ::= { agnTsCmprEntry 6}

-- Extended Compress Genearl Table with 7 indexes -  10/02/99
-- Used for: V5.1 Variant, 

agnXCmprTable  OBJECT-TYPE
      SYNTAX SEQUENCE OF AgnXCmprEntry
      ACCESS not-accessible
      STATUS  mandatory
      DESCRIPTION "" ::= { cmprAgnGen 7 }

agnXCmprEntry OBJECT-TYPE
      SYNTAX AgnXCmprEntry
      ACCESS not-accessible
      STATUS mandatory
       	  		 DESCRIPTION ""
INDEX {agnXCmprTypIdx, agnXCmprVersion, agnXCmprIdx3,agnXCmprIdx4,
             agnXCmprIdx5, agnXCmprIdx6, agnXCmprIdx7}
      ::= {agnXCmprTable  1}

AgnXCmprEntry ::=
      SEQUENCE {
     agnXCmprTypIdx       INTEGER,
     agnXCmprVersion      INTEGER,
     agnXCmprIdx3         INTEGER,
     agnXCmprIdx4         INTEGER,
     agnXCmprIdx5         INTEGER,
     agnXCmprIdx6         INTEGER,
     agnXCmprIdx7         INTEGER,
     agnXCmprObj          OCTET STRING
      }

agnXCmprTypIdx OBJECT-TYPE
      SYNTAX  INTEGER
      ACCESS  read-only
      STATUS  mandatory
      DESCRIPTION
      "This attribute indicates the Type of the Compressed being
       referred. 
       One of the types is V5.1 Variant data."
      ::= { agnXCmprEntry 1}

agnXCmprVersion OBJECT-TYPE
      SYNTAX  INTEGER
      ACCESS  read-only
      STATUS  mandatory
      DESCRIPTION
      "This attribute indicates the version of the internal format of
       the Compressed data."
      ::= { agnXCmprEntry 2}

agnXCmprIdx3 OBJECT-TYPE
      SYNTAX  INTEGER
      ACCESS  read-only
      STATUS  mandatory
      DESCRIPTION
      "3rd index - can be used for any purpose according to the 
       agnXCmprTypIdx.
       Example: for V5.1 Variant, this attribute indicates the configuration
       to which the Compressed information is  related.
       255=temporary configuration.
       Set can be performed only to the temporary configuration."
      ::= { agnXCmprEntry 3}

agnXCmprIdx4  OBJECT-TYPE
      SYNTAX  INTEGER
      ACCESS  read-only
      STATUS  mandatory
      DESCRIPTION
      "4th index - can be used for any purpose according to the 
       agnXCmprTypIdx.
       Example: for V5.1 Variant,this attribute indicates a unique number of 
       the slot position where the card is inserted.
	   Valid values: psA(1),psB(2),clA(3),clB(4),io1(5)..io12(16); notApplicable=255."
      ::= { agnXCmprEntry 4}

agnXCmprIdx5   OBJECT-TYPE
      SYNTAX  INTEGER
      ACCESS  read-only
      STATUS  mandatory
      DESCRIPTION
      "5th index - can be used for any purpose according to the 
       agnXCmprTypIdx.
       Example: for V5.1 Variant,this attribute indicates a unique identifier 
       of  the port	the compressed information relates to.
       Valid values: exPrt1    (1) .. exPrt12  (12) ,
                     inPrt1  (101) .. inPrt48 (148)."
      ::= { agnXCmprEntry 5}

agnXCmprIdx6  OBJECT-TYPE
      SYNTAX  INTEGER
      ACCESS  read-only
      STATUS  mandatory
      DESCRIPTION
      "6th index - can be used for any purpose according to the 
       agnXCmprTypIdx.
       Example: for V5.1 Variant,this attribute indicates the Variant index. 
       Valid values are: 0..127, 255 (= temp cnfg).Set can be performed only 
       to the temporary configuration."
      ::= { agnXCmprEntry 6}

agnXCmprIdx7  OBJECT-TYPE
      SYNTAX  INTEGER
      ACCESS  read-only
      STATUS  mandatory
      DESCRIPTION
      "7th index - can be used for any purpose according to the 
       agnXCmprTypIdx.
       Example: for V5.1 Variant,this attribute is not needed. Therefore, its 
       value will be always 255=notApplicable."
      ::= { agnXCmprEntry 7}

agnXCmprObj OBJECT-TYPE
      SYNTAX  OCTET STRING
      ACCESS  read-write
      STATUS  mandatory
      DESCRIPTION
      "This attribute is the compressed information itself."
      ::= { agnXCmprEntry 8}

--
-- Link Mapping Table for internal use
--
agnLinkMapTable OBJECT-TYPE
      SYNTAX SEQUENCE OF AgnLinkMapEntry
      ACCESS not-accessible
      STATUS  mandatory
      DESCRIPTION "" ::= { mapWanGen 1}

agnLinkMapEntry OBJECT-TYPE
      SYNTAX AgnLinkMapEntry
      ACCESS not-accessible
      STATUS mandatory
       	  		 DESCRIPTION ""
INDEX {mapLinkId}
      ::= {agnLinkMapTable 1}

AgnLinkMapEntry ::=
      SEQUENCE {
      mapLinkId               INTEGER,
      mapLinkSltIdx           INTEGER,
      mapLinkPrtIdx           INTEGER,
      mapLinkStatus           INTEGER
      }

mapLinkId     OBJECT-TYPE
      SYNTAX  INTEGER
      ACCESS  read-only
      STATUS  mandatory
      DESCRIPTION
      "A unique identifier of the link"
::=  {agnLinkMapEntry 1}

mapLinkSltIdx    OBJECT-TYPE
      SYNTAX  INTEGER
        {
          noConnect   (2),
       clA   (3),
       io1   (5),
       io2   (6),
       io3   (7),
       io4   (8),
       io5   (9),
       io6  (10),
       io7  (11),
       io8  (12),
       io9  (13),
       io10 (14),
       io11 (15),
       io12 (16),
    notApplicable (255)
     }
      ACCESS  read-write
      STATUS  mandatory
      DESCRIPTION
      "This attribute indicates a unique  slot  position where
       the card is inserted.
       In the ?004 Unit the entries clA(3), io6(10)..io12(16) are
       not valid."
::=  {agnLinkMapEntry 2}

mapLinkPrtIdx  OBJECT-TYPE
      SYNTAX  INTEGER
      {
         exPrt1    (1) ,
         exPrt2    (2) ,
         exPrt3    (3) ,
         exPrt4    (4) ,
         exPrt5    (5) ,
         exPrt6    (6) ,
         exPrt7    (7) ,
         exPrt8    (8) ,
         exPrt9    (9) ,
         exPrt10  (10) ,
         exPrt11  (11) ,
         exPrt12  (12) ,
         noConnect  (100) ,
         inPrt1  (101) ,
         inPrt2  (102) ,
         inPrt3  (103) ,
         inPrt4  (104) ,
         inPrt5  (105) ,
         inPrt6  (106) ,
         inPrt7  (107) ,
         inPrt8  (108) ,
         inPrt9  (109) ,
         inPrt10 (110) ,
         inPrt11 (111) ,
         inPrt12 (112)
      }
      ACCESS  read-write
      STATUS  mandatory
      DESCRIPTION
      "This attribute indicates a unique  port number. "
::=  {agnLinkMapEntry 3}

mapLinkStatus   OBJECT-TYPE
      SYNTAX  INTEGER
 {
 unknown(1),
 down(2),
 up(3)
 }
      ACCESS  read-only
      STATUS  mandatory
      DESCRIPTION
      "This attribute indicates the status of the link between the
       two muxes"
::=  {agnLinkMapEntry 4}


--
-- diverseIfWanGen - diverse NON-DS1 interfaces of WAN products
--


ethIf OBJECT IDENTIFIER ::= {diverseIfWanGen 1}	  --Ethernet Interface

ethIfTable OBJECT-TYPE
      SYNTAX SEQUENCE OF EthIfEntry
      ACCESS not-accessible
      STATUS  mandatory
      DESCRIPTION "" ::= { ethIf 1}

ethIfEntry OBJECT-TYPE
      SYNTAX EthIfEntry
      ACCESS not-accessible
      STATUS mandatory
       	  		 DESCRIPTION ""
INDEX {ethIfIdx}
      ::= {ethIfTable 1}

EthIfEntry ::=
      SEQUENCE {
      ethIfIdx                INTEGER,
      ethMode                 INTEGER,
      ethBridgingMode         INTEGER
      }

ethIfIdx     OBJECT-TYPE
      SYNTAX  INTEGER
      ACCESS  read-only
      STATUS  mandatory
      DESCRIPTION
      "A unique index of the ethernet interface/port."
      ::=  {ethIfEntry 1}

ethMode    OBJECT-TYPE
      SYNTAX  INTEGER
        {
    halfDuplex  (1),
          fullDuplex  (2)
     }
      ACCESS  read-write
      STATUS  mandatory
      DESCRIPTION
      "This object indicates the Ethernet mode of operation."
      ::=  {ethIfEntry 2}

ethBridgingMode  OBJECT-TYPE
      SYNTAX  INTEGER
      {
         filtered    (1),
         transparent (2)
      }
      ACCESS  read-write
      STATUS  mandatory
      DESCRIPTION
      "This object indicates the bridging mode of the Ethernet
       interface. "
      ::=  {ethIfEntry 3}


--
-- Wan alarm buffer (history) information
--
alrBufTable  OBJECT-TYPE
      SYNTAX SEQUENCE OF AlrBufEntry
      ACCESS not-accessible
      STATUS  mandatory
      DESCRIPTION "" ::= { alrBuffGen 1 }

alrBufEntry OBJECT-TYPE
      SYNTAX AlrBufEntry
      ACCESS not-accessible
      STATUS mandatory
       	  		 DESCRIPTION ""
INDEX { alrBufIdx }
      ::= { alrBufTable 1}

AlrBufEntry ::=
      SEQUENCE {
  alrBufIdx          INTEGER,
     alrBufDescription  DisplayString (SIZE (0..255))
      }

alrBufIdx OBJECT-TYPE
      SYNTAX  INTEGER
      ACCESS  read-only
      STATUS  mandatory
      DESCRIPTION
      "This attribute indicates a  unique number to identify this
       entry"
    ::= { alrBufEntry 1}

alrBufDescription  OBJECT-TYPE
      SYNTAX  DisplayString (SIZE (0..255))
      ACCESS  read-only
      STATUS  mandatory
      DESCRIPTION
      "This entry is a unique text description of the alarm in the
       buffer.
       The alarm description includes the following information:
       alarm code, slot id, card type, channel id ,
       alarm text, alarm status, masked flag and event counter"
       ::= { alrBufEntry 2}


--
-- Wan Flip Data-Base parameters
--
--         agnCAgendaTable :
--

agnCAgendaTable OBJECT-TYPE
      SYNTAX SEQUENCE OF AgnCAgendaEntry
      ACCESS not-accessible
      STATUS  mandatory
      DESCRIPTION
      "This table devides the week days into categories needed for
       DB flip consideration."
      ::= {agnFlipDb 1}

agnCAgendaEntry OBJECT-TYPE
      SYNTAX AgnCAgendaEntry
      ACCESS not-accessible
      STATUS mandatory
       	  		 DESCRIPTION ""
INDEX {agnCAgendaCnfgIdx, agnCAgendaDayIdx}
      ::= {agnCAgendaTable 1}

AgnCAgendaEntry ::=
      SEQUENCE {
           agnCAgendaCnfgIdx    INTEGER,
           agnCAgendaDayIdx           INTEGER,
           agnCAgendaDayCategory      INTEGER
               }

agnCAgendaCnfgIdx OBJECT-TYPE
      SYNTAX  INTEGER
              {
                active    (1),
                temporary  (255)
              }
      ACCESS  read-only
      STATUS  mandatory
      DESCRIPTION
      "Active or Temporary Agenda Table.
       Both configurations can be read but only the Temporary can
       be written to."
      ::= {agnCAgendaEntry 1}

agnCAgendaDayIdx OBJECT-TYPE
      SYNTAX  INTEGER
              {
                sunday    (1),
                monday    (2),
                tuesday   (3),
                wednesday (4),
                thursday  (5),
                friday    (6),
                saturday  (7)
              }
      ACCESS  read-only
      STATUS  mandatory
      DESCRIPTION
      "Day of week"
      ::= {agnCAgendaEntry 2}

agnCAgendaDayCategory OBJECT-TYPE
      SYNTAX  INTEGER
              {
                fullWorkday    (1),
                partialWorkday (2),
                weekend        (3)
              }
      ACCESS  read-write
      STATUS  mandatory
      DESCRIPTION
      "The Category of the Day "
      ::= {agnCAgendaEntry 3}


--          agnCFlipNetEventsTable :
--

agnCFlipNetEventsTable OBJECT-TYPE
      SYNTAX SEQUENCE OF AgnCFlipNetEventsEntry
      ACCESS not-accessible
      STATUS  mandatory
      DESCRIPTION
      "This table holds the Net Events the MUX should trace"
      ::= {agnFlipDb 2}

agnCFlipNetEventsEntry OBJECT-TYPE
      SYNTAX AgnCFlipNetEventsEntry
      ACCESS not-accessible
      STATUS mandatory
      DESCRIPTION "" INDEX {agnCFlipNetEventsCnfgIdx, agnCFlipNetEventIdx}
      ::= {agnCFlipNetEventsTable 1}

AgnCFlipNetEventsEntry ::=
      SEQUENCE {
    agnCFlipNetEventsCnfgIdx   INTEGER,
                agnCFlipNetEventIdx        INTEGER,
                agnCFlipNetEventActive     INTEGER,
                agnCFlipNetEventType       INTEGER,
                agnCFlipNetEventNo         INTEGER,
                agnCFlipNetEventSlot       INTEGER,
                agnCFlipNetEventPort       INTEGER,
                agnCFlipNetEventISD        INTEGER,
                agnCFlipNetEventOSD        INTEGER,
                agnCFlipNetEventDayType    INTEGER,
                agnCFlipNetEventStartTime  DisplayString (SIZE (5)),
                agnCFlipNetEventEndTime    DisplayString (SIZE (5))
               }

agnCFlipNetEventsCnfgIdx OBJECT-TYPE
      SYNTAX  INTEGER
              {
                active    (1),
                temporary  (255)
              }
      ACCESS  read-only
      STATUS  mandatory
      DESCRIPTION
      "Active or Temporary Net Events Table.
       Both configurations can be read but only the Temporary can
       be written to."
      ::= {agnCFlipNetEventsEntry 1}

agnCFlipNetEventIdx OBJECT-TYPE
      SYNTAX  INTEGER  (1..10)
      ACCESS  read-only
      STATUS  mandatory
      DESCRIPTION
      "Entry within the table"
      ::= {agnCFlipNetEventsEntry 2}

agnCFlipNetEventActive     OBJECT-TYPE
      SYNTAX  INTEGER
              {
                no  (2),
                yes (3)
              }
      ACCESS  read-write
      STATUS  mandatory
      DESCRIPTION
      "Indicates if the entry is valid.
       In order to Add/Modify parameters of an entry, this object
       should be set to Yes.
       In order to delete an entry, this object should be Set to No."
      ::= {agnCFlipNetEventsEntry 3}


agnCFlipNetEventType OBJECT-TYPE
      SYNTAX  INTEGER
              {
                time       (1),
                linkDown   (2),
                congestion (3)   -- MP3000 Only
              }
      ACCESS  read-write
      STATUS  mandatory
      DESCRIPTION
      "The Net Event type "
      ::= {agnCFlipNetEventsEntry 4}

agnCFlipNetEventNo OBJECT-TYPE
      SYNTAX  INTEGER  (1..512)
      ACCESS  read-write
      STATUS  mandatory
      DESCRIPTION
      "The Net Event No. (Bit Index)"
      ::= {agnCFlipNetEventsEntry 5}

agnCFlipNetEventSlot OBJECT-TYPE
      SYNTAX  INTEGER
              {
                notApplicable   (1),
                io1   (5),
                io2   (6),
                io3   (7),
                io4   (8),
                io5   (9),
                io6  (10),
                io7  (11),
                io8  (12),
                io9  (13),
                io10 (14),
                io11 (15),
                io12 (16)
              }
      ACCESS  read-write
      STATUS  mandatory
      DESCRIPTION
      "The slot to which the net event relates .
       Not applicable for time event"
      ::= {agnCFlipNetEventsEntry 6}

agnCFlipNetEventPort OBJECT-TYPE
      SYNTAX  INTEGER
              {
                exPrt1    (1) ,
                exPrt2    (2) ,
                exPrt3    (3) ,
                exPrt4    (4) ,
                exPrt5    (5) ,
                exPrt6    (6) ,
                exPrt7    (7) ,
                exPrt8    (8) ,
                exPrt9    (9) ,
                exPrt10  (10) ,
                exPrt11  (11) ,
                exPrt12  (12) ,
                notApplicable   (100),
                inPrt1    (101) ,
                inPrt2    (102) ,
                inPrt3    (103) ,
                inPrt4    (104) ,
                inPrt5    (105) ,
                inPrt6    (106) ,
                inPrt7    (107) ,
                inPrt8    (108)
              }
      ACCESS  read-write
      STATUS  mandatory
      DESCRIPTION
      "The port within the relevant slot"
      ::= {agnCFlipNetEventsEntry 7}


agnCFlipNetEventISD OBJECT-TYPE
      SYNTAX  INTEGER  (1..999)
      ACCESS  read-write
      STATUS  mandatory
      DESCRIPTION
      "The time in seconds since the Net Event was reported as ON
       until it is considered as ON.
       Not relevant for time events."
      ::= {agnCFlipNetEventsEntry 8}

agnCFlipNetEventOSD OBJECT-TYPE
      SYNTAX  INTEGER  (1..999)
      ACCESS  read-write
      STATUS  mandatory
      DESCRIPTION
      "The time in seconds since the net event was reported as OFF
       until it is considered as OFF.
       Not relevant for time events."
      ::= {agnCFlipNetEventsEntry 9}

agnCFlipNetEventDayType OBJECT-TYPE
      SYNTAX  INTEGER
              {
                notApplicable  (1),
                fullWorkday    (2),
                partialWorkday (3),
    weekend        (4)
              }
      ACCESS  read-write
      STATUS  mandatory
      DESCRIPTION
      "The time event relates to all days defined in this category in
       the agnCAgendaTable.
       Applicable only for time event"
      ::= {agnCFlipNetEventsEntry 10}

agnCFlipNetEventStartTime    OBJECT-TYPE
      SYNTAX    DisplayString (SIZE (5))
      ACCESS  read-write
      STATUS  mandatory
      DESCRIPTION
      "The time event will be activated at this time.
       The format is hh:mm."
      ::= {agnCFlipNetEventsEntry 11}

agnCFlipNetEventEndTime     OBJECT-TYPE
      SYNTAX    DisplayString (SIZE (5))
      ACCESS  read-write
      STATUS  mandatory
      DESCRIPTION
      "The time event will be deactivated at this time.
       The format is hh:mm."
      ::= {agnCFlipNetEventsEntry 12}


--         agnCFlipTable :
--

agnCFlipTable OBJECT-TYPE
     SYNTAX SEQUENCE OF AgnCFlipEntry
     ACCESS not-accessible
     STATUS  mandatory
     DESCRIPTION
     "The DB Flip Decisions Table"
     ::= {agnFlipDb 3}

agnCFlipEntry OBJECT-TYPE
     SYNTAX AgnCFlipEntry
     ACCESS not-accessible
     STATUS mandatory
     DESCRIPTION "" INDEX {agnCFlipCnfgIdx, agnCFlipIdx}
     ::= {agnCFlipTable 1}

AgnCFlipEntry ::=
     SEQUENCE {
               agnCFlipCnfgIdx    INTEGER,
               agnCFlipIdx         INTEGER,
               agnCFlipActive      INTEGER,
               agnCFlipLogicalExp  DisplayString (SIZE (1..20)),
               agnCFlipDbNo        INTEGER,
               agnCFlipDiscardDe   INTEGER
              }

agnCFlipCnfgIdx OBJECT-TYPE
      SYNTAX  INTEGER
              {
                active     (1),
                temporary  (255)
              }
      ACCESS  read-only
      STATUS  mandatory
      DESCRIPTION
      "Active or Temporary Flip Decisions Table.
       Both configurations can be read but only the Temporary can
       be written to."
      ::= {agnCFlipEntry 1}



agnCFlipIdx OBJECT-TYPE
     SYNTAX  INTEGER  (1..10)
     ACCESS  read-only
     STATUS  mandatory
     DESCRIPTION
     "Entry number within the table"
     ::= {agnCFlipEntry 2}

agnCFlipActive     OBJECT-TYPE
     SYNTAX  INTEGER
             {
               no  (2),
               yes (3)
             }
     ACCESS  read-write
     STATUS  mandatory
     DESCRIPTION
     "Indicates if the entry is valid.
      In order to Add/Modify parameters of an entry this object
      should be Set to Yes.
      In order to delete an entry, this object should be Set to No."
     ::= {agnCFlipEntry 3}

agnCFlipLogicalExp    OBJECT-TYPE
     SYNTAX    DisplayString (SIZE (1..20))
     ACCESS  read-write
     STATUS  mandatory
     DESCRIPTION
     "A logical expression composed of events numbers (which were
      configured in the 'AgnCFlipNetEvantsTable') and logical operators
      ('|', '&', '!', '(', ')') between them.
      e.g - (1 & !2) | (121 & 230)"
     ::= {agnCFlipEntry 4}

agnCFlipDbNo OBJECT-TYPE
     SYNTAX  INTEGER  (1..10)
     ACCESS  read-write
     STATUS  mandatory
     DESCRIPTION
     "The ID of the required DB "
     ::= {agnCFlipEntry 5}

agnCFlipDiscardDe     OBJECT-TYPE
     SYNTAX  INTEGER
             {
               notApplicable (1),
               no            (2),
               yes           (3)
             }
     ACCESS  read-write
     STATUS  mandatory
     DESCRIPTION
     "Indicates whether the Mux should start discarding
      all DE. (MP3000 Only)."
     ::= {agnCFlipEntry 6}

--  Commands concerning the Flip DB

agnFlipDbControls    OBJECT IDENTIFIER ::= {agnFlipDb 4}


agnCFlipDbSanityCheckCmd OBJECT-TYPE
     SYNTAX  INTEGER
             {
               off(2),
               on (3)
             }
     ACCESS  read-write
     STATUS  mandatory
     DESCRIPTION
     "Setting this attribute to on(3) will initiate the process
      of Sanity check on the Temp Flip Db and automatically be
      changed to off(2)."
     ::= { agnFlipDbControls 1 }

agnCSaveFlipDbCmd OBJECT-TYPE
     SYNTAX  INTEGER
             {
               off(2),
               on (3)
             }
     ACCESS  read-write
     STATUS  mandatory
     DESCRIPTION
     "Setting this attribute to on(3) will initiate the process
      of Sanity check on the Temp Flip Db and if it is OK, it will
      save the Flip Db in the NVRAM, activating the new  Flip DB .
      If check detects errors, the save will not be performed.
      Afterwards, the object's value will change automatically to off(2)."
     ::= { agnFlipDbControls 2 }

agnCSaveNetCnfgIdxCmd OBJECT-TYPE
     SYNTAX  INTEGER   (1..10)
     ACCESS  read-write
     STATUS  mandatory
     DESCRIPTION
     "This attribute specifies the Id of the target NVRAM Cnfg to
      which the TmpCnfg should be transferred. Upon set command the
      MUX will initiate the Sanity-Check  process first. If
      successful, the actual transfer will be performed. If warnings
      are detected, the user will have to perform the command again
      to confirm the operation. Setting this object a second time
      to the same value without performing any change in the database,
      will cause the result: agnSSanityCheckStatus = unknown.
      This attribute doesn't cause actual Flip."
     ::= { agnFlipDbControls 3 }

agnCSaveNetFlipDbCmd OBJECT-TYPE
     SYNTAX  INTEGER
             {
               off(2),
               on (3)
             }
     ACCESS  read-write
     STATUS  mandatory
     DESCRIPTION
     "Setting this attribute to on(3) will save the Temp Flip DB
      Into the NVRAM without actual flip."
     ::= { agnFlipDbControls 4 }

agnCNetGoCmd OBJECT-TYPE
     SYNTAX  INTEGER
             {
               off(2),
               on (3)
             }
     ACCESS  read-write
     STATUS  mandatory
     DESCRIPTION
     "Setting this attribute to On will broadcast a 'GO' command
      to the network.  When a Mux receives a 'GO' command it issues
      a delay for 'agnCNetDelay' seconds and then activates
      the DB which was pre-defined by one of the commands :
      'agnCSaveNetCnfgIdxCmd' or 'agnCSaveNetFlipDbCmd'."
     ::= { agnFlipDbControls 5 }

agnCNetDelay OBJECT-TYPE
     SYNTAX  INTEGER (1..999)
     ACCESS  read-write
     STATUS  mandatory
     DESCRIPTION
     "This attribute determines the period of time in seconds that
      takes for a message to be transferred over all the network.
      After a 'GO' command the MUX issues a delay of
      'agnCNetDelay' before activating the appropriate DB.
      The delay will be applied only after performing
      agnCSaveFlipDbCmd."
     ::= { agnFlipDbControls 6 }

agnCNetEventsBcast OBJECT-TYPE
     SYNTAX  INTEGER
             {
               disabled(2),
               enabled (3)
             }
     ACCESS  read-write
     STATUS  mandatory
     DESCRIPTION
     "This object determines if the Net Events will be Broadcasted to
      other Muxes of the Net or not.
      disabled - Net Events will NOT be Broadcasted
      enabled  - Net Events will be Broadcasted.
   Default=disabled.
      The value will be applied only after performing
      agnCSaveFlipDbCmd."
     ::= { agnFlipDbControls 7 }

agnCNetEventsBcastInterval OBJECT-TYPE
     SYNTAX  INTEGER (10..60)
     ACCESS  read-write
     STATUS  mandatory
     DESCRIPTION
     "When agnCNetEventsBcast is enabled, this object determines
      the interval of time in seconds, between two consecutive
      Net Events transferred over the network.
   Default=40 sec.
      The interval will be applied only after performing
      agnCSaveFlipDbCmd."
     ::= { agnFlipDbControls 8 }

--
-- agnSa = agent Stand-Alone (not HUB) specific objects
--
agnSaSwchStatus OBJECT-TYPE
     SYNTAX  INTEGER
     ACCESS  read-only
     STATUS  mandatory
     DESCRIPTION
  "This object indicates the status of the switches on the
   stand-alone unit.
   Each switch is represented by a bit. The status is a sum of
   2**n, according to the bits:
   bit 0   NMS (LSB)
   bit 1   Terminal    '1' = forces the DCE to be terminal with
         Rate=9600bps, Data bits=8,
         Stop bits=1
   bit 2   Xray
   bit 3   SW-Load      '1' = when SW is loaded
   bit 4   DBS
   Default of all bits=0
   When the status of these switches is unknown, the value of
   this object is 255."
     ::= { agnSa 1 }

--Decoding Table: Code vs. Description

agnListDecodingTable  OBJECT-TYPE
      SYNTAX SEQUENCE OF AgnListDecodingEntry
      ACCESS not-accessible
      STATUS  mandatory
   DESCRIPTION
      "A decoding table . For each type of list, a description is
       given for each existing code."
      ::= { agnListDecoding 1 }

agnListDecodingEntry OBJECT-TYPE
      SYNTAX AgnListDecodingEntry
      ACCESS not-accessible
      STATUS mandatory
      DESCRIPTION "" INDEX { agnListDecodingType, agnListDecodingCode }
      ::= { agnListDecodingTable 1}

AgnListDecodingEntry ::=
      SEQUENCE {
     agnListDecodingType        INTEGER,
     agnListDecodingCode  INTEGER,
     agnListDecodingDescription DisplayString (SIZE (0..255)),
     agnListDecodingDefState    INTEGER,
     agnListDecodingSeverity    INTEGER,
     agnListDecodingAcmRelaySlt INTEGER,
     agnListDecodingAcmRelayPrt INTEGER
      }

agnListDecodingType OBJECT-TYPE
      SYNTAX  INTEGER
       {
       alr      (1),
       sanity   (2)
       }
      ACCESS  read-only
      STATUS  mandatory
      DESCRIPTION
      "The type of list the decoding data refers to.
       alr - Alarms list
       sanity - Sanity Check Error list. "
      ::= { agnListDecodingEntry 1}

agnListDecodingCode OBJECT-TYPE
      SYNTAX  INTEGER
      ACCESS  read-only
      STATUS  mandatory
      DESCRIPTION
      "The specific code for which decoding is needed. "
      ::= { agnListDecodingEntry 2}

agnListDecodingDescription OBJECT-TYPE
      SYNTAX  DisplayString (SIZE (0..255))
      ACCESS  read-only
      STATUS  mandatory
      DESCRIPTION
      "The description fitting the specific code and type of list
       required. "
      ::= { agnListDecodingEntry 3}

agnListDecodingDefState OBJECT-TYPE
      SYNTAX  INTEGER
       {
  notApplicable (1),
  event    (3),
  minor    (4),
  major    (5)
       }
      ACCESS  read-only
      STATUS  mandatory
      DESCRIPTION
      "This object is applicable only for agnListDecodingType=alr.
       It reports the default state/severity of each alarm.
       User can change the  severity of the alarms defined by
       this default via the agnListDecodingSeverity object."
      ::= { agnListDecodingEntry 4}

agnListDecodingSeverity OBJECT-TYPE
      SYNTAX  INTEGER
       {
  notApplicable (1),
  event    (3),
  minor    (4),
  major    (5),
  warning  (6),
  critical (7)
       }
      ACCESS  read-write
      STATUS  mandatory
      DESCRIPTION
      "This object is applicable only for agnListDecodingType=alr.
       It enables the user to select a severity for each alarm.
    The severity is set per alarm code (same for all slots/ports
    using this code).
    event - can be set only for an alarm that is defined by
            default as 'event'.
       User can change the  severity of the alarms defined by
       default as minor or major.
       The severity of an event may be set to another severity,
       but the change will actually happen only if the event
       threshold is active and passed the Set/ON condition.
       An event alarm that passed the threshold and changed its
       severity, will return automatically to event severity when
       meeting its Reset/OFF condition."
      ::= { agnListDecodingEntry 5}

agnListDecodingAcmRelaySlt OBJECT-TYPE
      SYNTAX  INTEGER
     { none  (1),
       io1   (5),
       io2   (6),
       io3   (7),
       io4   (8),
       io5   (9),
       io6  (10),
       io7  (11),
       io8  (12),
       io9  (13),
       io10 (14),
       io11 (15),
       io12 (16),
	   notApplicable(255)
	    }
      ACCESS  read-write
      STATUS  mandatory
      DESCRIPTION
      "This object indicates the ACM slot, desired for outbound relay
       (report) for the selected alarm.
       In the ?004 Unit the entries io6(10)..io12(16) are not valid.
	   none - when agnListDecodingType=alr AND the selected
                       alarm should not be reported by an ACM card.
       notApplicable - when agnListDecodingType=sanity OR when
             [agnListDecodingType=alr and there is no ACM card installed in the Mux]."
      ::= { agnListDecodingEntry 6}

agnListDecodingAcmRelayPrt OBJECT-TYPE
      SYNTAX  INTEGER
       {
      exPrt1    (1) ,
      exPrt2    (2) ,
      exPrt3    (3) ,
      exPrt4    (4) ,
      notApplicable(255)
	    }
      ACCESS  read-write
      STATUS  mandatory
      DESCRIPTION
      "This object indicates the ACM port within the slot, desired for outbound relay
       (report) for the selected alarm.
       notApplicable - when agnListDecodingType=sanity OR when
                       agnListDecodingAcmRelaySlt=notApplicable."
      ::= { agnListDecodingEntry 7}


-- Dlci Table from system point of view
agnDlciTable  OBJECT-TYPE
     SYNTAX SEQUENCE OF AgnDlciEntry
     ACCESS not-accessible
     STATUS  mandatory
     DESCRIPTION
      "The write operation into the Table Objects is valid only
       to the TmpCnfg entry."
     ::= { agnSystemDlci 1}

agnDlciEntry OBJECT-TYPE
      SYNTAX AgnDlciEntry
      ACCESS not-accessible
      STATUS mandatory
      DESCRIPTION "" INDEX {agnDlciCnfgIdx, agnDlciLSltIdx, agnDlciLPrtIdx, agnDlciHIdx,
         agnDlciHSltIdx, agnDlciHPrtIdx, agnDlciLIdx }
      ::= { agnDlciTable 1}

AgnDlciEntry ::=
      SEQUENCE {
 	agnDlciCnfgIdx 	 INTEGER,
 	agnDlciLSltIdx 	 INTEGER,
    agnDlciLPrtIdx	 INTEGER,
    agnDlciLIdx		 INTEGER,
	agnDlciHSltIdx	 INTEGER,
    agnDlciHPrtIdx	 INTEGER,
    agnDlciHIdx		 INTEGER,
	agnDlciTxBc	     INTEGER,
    agnDlciTxBe      INTEGER,
    agnDlciRxBc      INTEGER,
    agnDlciRxBe      INTEGER,
	agnDlciPriority  INTEGER,
	agnDlciStatus    INTEGER,
	agnDlciSpoofing  INTEGER,
	agnDlciFunnelEnable INTEGER,
	agnDlciRoutingProtocol INTEGER,
	agnDlciRowStatus INTEGER
      }

agnDlciCnfgIdx OBJECT-TYPE
      SYNTAX  INTEGER (1..255)
      ACCESS  read-only
      STATUS  mandatory
      DESCRIPTION
      "This attribute indicates the Idx of the Cnfg (1..100) being
       accessed.
       Idx 255 relates to the TmpCnfg. "
      ::= { agnDlciEntry 1}
-- In phase I only the values 1 (Cnfg1) and 255 (temp) are valid.

agnDlciLSltIdx OBJECT-TYPE
      SYNTAX  INTEGER
     { cl(3),
       io1   (5),
       io2   (6),
       io3   (7),
       io4   (8),
       io5   (9),
       io6  (10),
       io7  (11),
       io8  (12),
       io9  (13),
       io10 (14),
       io11 (15),
       io12 (16),
	   vs  (254),
	   notApplicable(255)
	    }
      ACCESS  read-only
      STATUS  mandatory
      DESCRIPTION
      "This attribute indicates a unique  slot  position where
       the card is inserted.
	   vs=Voice Switching
       In the ?004 Unit the entries io6(10)..io16) are not valid.
       For ISDN BRI ports of MX300/30 units:
           io1(5) = isdn1(5) and io2(6) = isdn2(6)
       LSlotIdx is defined according one of the following possiblities:
 1. LSlotIdx is < HSlotIdx.
 2. LSlotIdx is = HSlotIdx and LPrtIdx is < HPrtIdx.
 3. LSlotIdx is = HSlotIdx and LPrtIdx is = HPrtIdx but LIdx is < HIdx."
      ::= { agnDlciEntry 2}

agnDlciLPrtIdx OBJECT-TYPE
      SYNTAX  INTEGER
      ACCESS  read-only
      STATUS  mandatory
      DESCRIPTION
      "This attribute indicates a unique external or internal port number,
       including linkSelector or encapsulator.
	   100=noConnect  (for voice switching)
        LPrtIdx is defined according one of the following possiblities:
	1. LSlotIdx is < HSlotIdx.
	2. LSlotIdx is = HSlotIdx and LPrtIdx is < HPrtIdx.
	3. LSlotIdx is = HSlotIdx and LPrtIdx is = HPrtIdx but LIdx is < HIdx."
   ::= { agnDlciEntry 3}

agnDlciLIdx OBJECT-TYPE
      SYNTAX  INTEGER (0..991)
      ACCESS  read-only
      STATUS  mandatory
      DESCRIPTION
      "This attribute indicates a unique index for each possible
       used dlci(16..991).
       0=notApplicable (for voice switching)
       LIdx is defined according one of the following possiblities:
 1. LSlotIdx is < HSlotIdx.
 2. LSlotIdx is = HSlotIdx and LPrtIdx is < HPrtIdx.
 3. LSlotIdx is = HSlotIdx and LPrtIdx is = HPrtIdx but LIdx is < HIdx."
      ::= { agnDlciEntry 4}

agnDlciHSltIdx OBJECT-TYPE
      SYNTAX  INTEGER
 {   cl    (3),
       io1   (5),
       io2   (6),
       io3   (7),
       io4   (8),
       io5   (9),
       io6  (10),
       io7  (11),
       io8  (12),
       io9  (13),
       io10 (14),
       io11 (15),
       io12 (16),
       notApplicable(255)
       }
      ACCESS  read-only
      STATUS  mandatory
      DESCRIPTION
      "This attribute indicates a unique slot position In the Mux
       (Agent) where the dlci is routed to.
       For ISDN BRI ports of MX300/30 units:
           io1(5) = isdn1(5) and io2(6) = isdn2(6)
       In the ?004 Unit the entries io6(10)..io16) are not valid"
      ::= { agnDlciEntry 5}

agnDlciHPrtIdx OBJECT-TYPE
      SYNTAX  INTEGER
      ACCESS  read-only
      STATUS  mandatory
      DESCRIPTION
      "This attribute indicates a unique port id which the dlci is
       routed to."
      ::= { agnDlciEntry 6}

agnDlciHIdx OBJECT-TYPE
      SYNTAX  INTEGER    (1..991)
      ACCESS  read-only
      STATUS  mandatory
      DESCRIPTION
      "This attribute indicates a unique internal connection dlci
       number which the src dlci is routed to."
      ::= { agnDlciEntry 7}

agnDlciTxBc OBJECT-TYPE
      SYNTAX  INTEGER
        {
         full           (1),
         zero           (2),
         txBc5100bps    (3),
         txBc6400bps    (4),
         txBc8300bps    (5),
         txBc9600bps    (6),
        txBc14400bps    (7),
        txBc19200bps    (8),
        txBc28800bps    (9),
        txBc32000bps   (10),
        txBc38400bps   (11),
        txBc48000bps   (12),
        txBc56000bps   (13),
        txBc57600bps   (14),
          txBc64Kbps   (15),
         txBc128Kbps   (16),
         txBc192Kbps   (17),
         txBc256Kbps   (18),
         txBc320Kbps   (19),
         txBc384Kbps   (20),
         txBc448Kbps   (21),
         txBc512Kbps   (22),
         txBc768Kbps   (23),
         txBc896Kbps   (24),
        txBc1024Kbps   (25),
        txBc1152Kbps   (26),
        txBc1280Kbps   (27),
        txBc1344Kbps   (28),
        txBc1472Kbps   (29),
        txBc1600Kbps   (30),
        txBc1728Kbps   (31),
        txBc1856Kbps   (32),
        txBc1920Kbps   (33),
        txBc1984Kbps   (34),
        txBc2048Kbps   (35),
		txBc16000bps   (36), -- Added here: No room between (7) and (8).

		-- For Mx 30/300
		txBc112Kbps    (37),
		txBc168Kbps    (38),
        txBc224Kbps    (39),
		txBc336Kbps    (40),
        txBc672Kbps    (41),
        txBc1536Kbps   (42),
        txBc1792Kbps   (43)
        }
      ACCESS  read-write
      STATUS  mandatory
      DESCRIPTION
      "This attribute indicates a unique Tx committed bandwidth on
       the user transmit line or at the port receive line."
      DEFVAL { full }
      ::= { agnDlciEntry 8}

agnDlciTxBe OBJECT-TYPE
      SYNTAX  INTEGER
        {
         full           (1),
         zero           (2),
         txBe5100bps    (3),
         txBe6400bps    (4),
         txBe8300bps    (5),
         txBe9600bps    (6),
        txBe14400bps    (7),
        txBe19200bps    (8),
        txBe28800bps    (9),
        txBe32000bps   (10),
        txBe38400bps   (11),
        txBe48000bps   (12),
        txBe56000bps   (13),
        txBe57600bps   (14),
          txBe64Kbps   (15),
         txBe128Kbps   (16),
         txBe192Kbps   (17),
         txBe256Kbps   (18),
         txBe320Kbps   (19),
         txBe384Kbps   (20),
         txBe448Kbps   (21),
         txBe512Kbps   (22),
         txBe768Kbps   (23),
         txBe896Kbps   (24),
        txBe1024Kbps   (25),
        txBe1152Kbps   (26),
        txBe1280Kbps   (27),
        txBe1344Kbps   (28),
        txBe1472Kbps   (29),
        txBe1600Kbps   (30),
        txBe1728Kbps   (31),
        txBe1856Kbps   (32),
        txBe1920Kbps   (33),
        txBe1984Kbps   (34),
        txBe2048Kbps   (35),
		txBe16000bps   (36), -- Added here: No room between (7) and (8).

		-- For Mx 30/300
		txBe112Kbps    (37),
		txBe168Kbps    (38),
        txBe224Kbps    (39),
		txBe336Kbps    (40),
        txBe672Kbps    (41),
        txBe1536Kbps   (42),
        txBe1792Kbps   (43)
        }
      ACCESS  read-write
      STATUS  mandatory
      DESCRIPTION
      "This attribute indicates a unique Tx excess bandwidth on the
      user transmit line or at the port receive line."
      DEFVAL { zero }
      ::= { agnDlciEntry 9}

agnDlciRxBc OBJECT-TYPE
      SYNTAX  INTEGER
        {
         full           (1),
         zero           (2),
         rxBc5100bps    (3),
         rxBc6400bps    (4),
         rxBc8300bps    (5),
         rxBc9600bps    (6),
        rxBc14400bps    (7),
        rxBc19200bps    (8),
        rxBc28800bps    (9),
        rxBc32000bps   (10),
        rxBc38400bps   (11),
        rxBc48000bps   (12),
        rxBc56000bps   (13),
        rxBc57600bps   (14),
          rxBc64Kbps   (15),
         rxBc128Kbps   (16),
         rxBc192Kbps   (17),
         rxBc256Kbps   (18),
         rxBc320Kbps   (19),
         rxBc384Kbps   (20),
         rxBc448Kbps   (21),
         rxBc512Kbps   (22),
         rxBc768Kbps   (23),
         rxBc896Kbps   (24),
        rxBc1024Kbps   (25),
        rxBc1152Kbps   (26),
        rxBc1280Kbps   (27),
        rxBc1344Kbps   (28),
        rxBc1472Kbps   (29),
        rxBc1600Kbps   (30),
        rxBc1728Kbps   (31),
        rxBc1856Kbps   (32),
        rxBc1920Kbps   (33),
        rxBc1984Kbps   (34),
        rxBc2048Kbps   (35),
		rxBc16000bps   (36), -- Added here: No room between (7) and (8).

				-- For Mx 30/300
		rxBc112Kbps    (37),
		rxBc168Kbps    (38),
        rxBc224Kbps    (39),
		rxBc336Kbps    (40),
        rxBc672Kbps    (41),
        rxBc1536Kbps   (42),
        rxBc1792Kbps   (43)
        }
      ACCESS  read-write
      STATUS  mandatory
      DESCRIPTION
      "This attribute indicates a unique Rx committed bandwidth on
       the user receive line or at the port transmit line."
      DEFVAL { full }
      ::= { agnDlciEntry 10}

agnDlciRxBe OBJECT-TYPE
      SYNTAX  INTEGER
        {
         full           (1),
         zero           (2),
         rxBe5100bps    (3),
         rxBe6400bps    (4),
         rxBe8300bps    (5),
         rxBe9600bps    (6),
        rxBe14400bps    (7),
        rxBe19200bps    (8),
        rxBe28800bps    (9),
        rxBe32000bps   (10),
        rxBe38400bps   (11),
        rxBe48000bps   (12),
        rxBe56000bps   (13),
        rxBe57600bps   (14),
          rxBe64Kbps   (15),
         rxBe128Kbps   (16),
         rxBe192Kbps   (17),
         rxBe256Kbps   (18),
         rxBe320Kbps   (19),
         rxBe384Kbps   (20),
         rxBe448Kbps   (21),
         rxBe512Kbps   (22),
         rxBe768Kbps   (23),
         rxBe896Kbps   (24),
        rxBe1024Kbps   (25),
        rxBe1152Kbps   (26),
        rxBe1280Kbps   (27),
        rxBe1344Kbps   (28),
        rxBe1472Kbps   (29),
        rxBe1600Kbps   (30),
        rxBe1728Kbps   (31),
        rxBe1856Kbps   (32),
        rxBe1920Kbps   (33),
        rxBe1984Kbps   (34),
        rxBe2048Kbps   (35),
		rxBe16000bps   (36), -- Added here: No room between (7) and (8).

		-- For Mx 30/300
		rxBe112Kbps    (37),
		rxBe168Kbps    (38),
        rxBe224Kbps    (39),
		rxBe336Kbps    (40),
        rxBe672Kbps    (41),
        rxBe1536Kbps   (42),
        rxBe1792Kbps   (43)
		}
      ACCESS  read-write
      STATUS  mandatory
      DESCRIPTION
      "This attribute indicates a unique Rx excess bandwidth on the
      user receive line or at the port transmit line."
      DEFVAL { zero }
      ::= { agnDlciEntry 11}

agnDlciPriority OBJECT-TYPE
      SYNTAX  INTEGER  (1..8)
      ACCESS  read-write
      STATUS  mandatory
      DESCRIPTION
      "This attribute indicates a unique priority of the pcv.
       1 is the lowest priority and 7 is the highest priority."
      ::= { agnDlciEntry 12}

agnDlciStatus OBJECT-TYPE
      SYNTAX  INTEGER
 {
          disconnected (1),
          connected    (2)
       }
      ACCESS  read-only
      STATUS  mandatory
      DESCRIPTION
      "This attribute indicates the status of the pvc. The status is
       disconnected(1) when one of the sides is programmed as
       not connected"
      ::= { agnDlciEntry 13}

agnDlciSpoofing OBJECT-TYPE
      SYNTAX  INTEGER
      {   no     (2),
          yes    (3)
	      }
      ACCESS  read-write
      STATUS  mandatory
      DESCRIPTION
      "This object refers to sending of RIP messages:
       - yes : RIP messages will be sent ONLY if there is a change in the Net.
	   - no  : RIP messages will be always sent.
	   This object is relevant only when one side of the DLCI is a CL-NMS interface.
	   Default=no. "
      ::= { agnDlciEntry 14}

agnDlciFunnelEnable OBJECT-TYPE
      SYNTAX  INTEGER
      {   disabled (2),
          enabled  (3)
	      }
      ACCESS  read-write
      STATUS  mandatory
      DESCRIPTION
      "This object selects Funnel activation enable/disable:
       - disabled: Funnel operation disabled. The agnDlciTxBe and agnDlciTxBc
	               values are not used for funneling.
	   - enabled : Funnel operation enabled. The agnDlciTxBe and agnDlciTxBc
	               values are used for funneling calculations.
	   This object is relevant only for an encapsulating DLCI.

	   In case of a Link Selector DLCI, the agnDlciTxBe and agnDlciTxBc
	               values are used for bandwidth of Link Selector.
	   Default=disabled. "
      ::= { agnDlciEntry 15}

agnDlciRoutingProtocol OBJECT-TYPE
      SYNTAX  INTEGER
      {   notApplicable(1),
          rip (2),
          rip2(3),
          none(4)
	      }
      ACCESS  read-write
      STATUS  mandatory
      DESCRIPTION
      "This object is relevant only when one side of the DLCI is a CL-NMS interface.
	   It defines which Routing Protocol will be used for management via CL-NMS port.
	   notApplicable will be used for all slots but CL.
	   rip is a proprietary rip protocol.

	   Default=rip. "
      ::= { agnDlciEntry 16}

agnDlciRowStatus OBJECT-TYPE
      SYNTAX  INTEGER
	{     active(1),
          destroy(6)
	      }
      ACCESS  read-write
      STATUS  mandatory
      DESCRIPTION
      "This attribute allows to create/delete a row in this table.
       For creating a row, the NMS should set
	   agnRowStatus.255.id2.id3.id4.id5.id6.id7 = active(1).
       For destroying a row, the NMS should set:
	   agnRowStatus.255.id2.id3.id4.id5.id6.id7 = destroy(6).
       Only rows with status active(1) are relevant."
      ::= { agnDlciEntry 17}


-- Voice Switching Configuration Support: agnVoiceSwitching group
agnVoiceSwConfTable  OBJECT-TYPE
      SYNTAX SEQUENCE OF AgnVoiceSwConfEntry
      ACCESS not-accessible
      STATUS  mandatory
      DESCRIPTION
      "MXcess Configuration for Voice Switching."
     ::= { agnVoiceSwitching 1 }

agnVoiceSwConfEntry OBJECT-TYPE
      SYNTAX AgnVoiceSwConfEntry
      ACCESS not-accessible
      STATUS mandatory
      DESCRIPTION "" INDEX { agnVoiceSwConfIdx }
      ::= { agnVoiceSwConfTable 1}

AgnVoiceSwConfEntry ::=
      SEQUENCE {
 agnVoiceSwConfIdx INTEGER,
 agnVoiceSwConfZoneId  DisplayString,
 agnVoiceSwConfNodeId  DisplayString,
 agnVoiceSwConfNoOfHops 	INTEGER
 }

agnVoiceSwConfIdx OBJECT-TYPE
      SYNTAX  INTEGER {    active(1),  temporary(255)  }
      ACCESS  read-only
      STATUS  mandatory
      DESCRIPTION
      "Active or Temporary Table.
       Both configurations can be read but only the Temporary can
       be written to."
      ::= { agnVoiceSwConfEntry 1}

agnVoiceSwConfZoneId OBJECT-TYPE
      SYNTAX  DisplayString(SIZE(1..2))
      ACCESS  read-write
      STATUS  mandatory
      DESCRIPTION
      "1 or 2 digits, (0-9)(1-9)."
      ::= { agnVoiceSwConfEntry 2}

agnVoiceSwConfNodeId OBJECT-TYPE
      SYNTAX  DisplayString(SIZE(1..3))
      ACCESS  read-write
      STATUS  mandatory
      DESCRIPTION
      "1, 2 or 3 digits, (1-9),(0-9),(0-9)."
      ::= { agnVoiceSwConfEntry 3}

agnVoiceSwConfNoOfHops OBJECT-TYPE
      SYNTAX  INTEGER (0..20)
      ACCESS  read-write
      STATUS  mandatory
      DESCRIPTION
      "Number of hops the frame will go through the net before deciding to discard
       the frame (like time-to-live in IP).
       0 = notApplicable
       Default=20 ."
      ::= { agnVoiceSwConfEntry 4}

agnVoiceSwConfRtTable  OBJECT-TYPE
      SYNTAX SEQUENCE OF AgnVoiceSwConfRtEntry
      ACCESS not-accessible
      STATUS  mandatory
      DESCRIPTION
      "Routing Table for Voice Switching."
     ::= { agnVoiceSwitching 2 }

agnVoiceSwConfRtEntry OBJECT-TYPE
      SYNTAX AgnVoiceSwConfRtEntry
      ACCESS not-accessible
      STATUS mandatory
      DESCRIPTION "" INDEX { agnVoiceSwConfRtDbId, agnVoiceSwConfRtIdx }
      ::= { agnVoiceSwConfRtTable 1}

AgnVoiceSwConfRtEntry ::=
      SEQUENCE {
 agnVoiceSwConfRtDbId   INTEGER,
 agnVoiceSwConfRtIdx        INTEGER,
 agnVoiceSwConfRtDigits  DisplayString,
 agnVoiceSwConfRtAction  INTEGER,
 agnVoiceSwConfRtData  DisplayString,
 agnVoiceSwConfRtSlot  INTEGER,
 agnVoiceSwConfRtPort  INTEGER,
 agnVoiceSwConfRtDlci  INTEGER,
 agnVoiceSwConfRtRowStatus        INTEGER
}

agnVoiceSwConfRtDbId OBJECT-TYPE
      SYNTAX  INTEGER {    active(1),  temporary(255)  }
      ACCESS  read-only
      STATUS  mandatory
      DESCRIPTION
      "Active or Temporary Table.
       Both configurations can be read but only the Temporary can
       be written to."
 ::= { agnVoiceSwConfRtEntry 1 }

agnVoiceSwConfRtIdx  OBJECT-TYPE
 SYNTAX  INTEGER
 ACCESS read-only
 STATUS mandatory
 DESCRIPTION
 " The Index of the row."
 ::= { agnVoiceSwConfRtEntry 2 }

agnVoiceSwConfRtDigits OBJECT-TYPE
 SYNTAX  DisplayString ( SIZE(1..7) )
 ACCESS read-write
 STATUS mandatory
 DESCRIPTION
 " Serie of digits or keyword 'ELSE'.."
 ::= { agnVoiceSwConfRtEntry 3 }

agnVoiceSwConfRtAction OBJECT-TYPE
 SYNTAX  INTEGER {
   notApplicable(1),
   zone(2),
   node(3),
   shortDialing(4),
   in(5),
   hgr(6),
   del(7),
   rep(8)
 }
 ACCESS read-write
 STATUS mandatory
 DESCRIPTION
 " Action that the system should perform for this digits:
 agnVoiceSwConfRtDigits."
 DEFVAL { notApplicable }
 ::= { agnVoiceSwConfRtEntry 4 }

agnVoiceSwConfRtData   OBJECT-TYPE
 SYNTAX  DisplayString(SIZE(1..7))
 ACCESS read-write
 STATUS mandatory
 DESCRIPTION
 " This field is relevant for actions hgr(6), del(7) and rep(8)."
-- DEFVAL {"0" }
 ::= { agnVoiceSwConfRtEntry 5 }

agnVoiceSwConfRtSlot OBJECT-TYPE
 SYNTAX  INTEGER{
       noConnect(2),
       cl    (3),
       io1   (5),
       io2   (6),
       io3   (7),
       io4   (8),
       io5   (9),
       io6  (10),
       io7  (11),
       io8  (12),
       io9  (13),
       io10 (14),
       io11 (15),
       io12 (16),
       notApplicable(255)
       }
 ACCESS read-write
 STATUS mandatory
 DESCRIPTION
 " Routing Slot- Relevant for actions zone(2) and node(3)."
 DEFVAL { noConnect }
 ::= { agnVoiceSwConfRtEntry 6 }

agnVoiceSwConfRtPort OBJECT-TYPE
 SYNTAX  INTEGER
 ACCESS read-write
 STATUS mandatory
 DESCRIPTION
	" Routing Port- Relevant for actions zone(2) and node(3).
	  100=noConnect (for non-routing case)."
 DEFVAL { 0 }
 ::= { agnVoiceSwConfRtEntry 7 }

agnVoiceSwConfRtDlci OBJECT-TYPE
	SYNTAX 	INTEGER
	ACCESS	read-write
	STATUS	mandatory
	DESCRIPTION
	" Routing DLCI- Relevant for actions zone(2) and node(3).
	  Valid values:
	  0=notApplicable (for non-routing case).
	  1, 16..991 "
               DEFVAL { 15 }
	::= { agnVoiceSwConfRtEntry 8 }

agnVoiceSwConfRtRowStatus OBJECT-TYPE
 SYNTAX  INTEGER {
       active(1),
             notInService(2),
             notReady(3),
             createAndGo(4),
             createAndWait(5),
             destroy(6)
       }
 ACCESS read-write
 STATUS mandatory
 DESCRIPTION
 " Status of the row for creating/deleting entries in
 the table."
 ::= { agnVoiceSwConfRtEntry 9 }

agnVoiceSwConfHGTable  OBJECT-TYPE
      SYNTAX SEQUENCE OF AgnVoiceSwConfHGEntry
      ACCESS not-accessible
      STATUS  mandatory
      DESCRIPTION
      "Table of Hunt Groups."
     ::= { agnVoiceSwitching 5 }

agnVoiceSwConfHGEntry OBJECT-TYPE
      SYNTAX AgnVoiceSwConfHGEntry
      ACCESS not-accessible
      STATUS mandatory
      DESCRIPTION "" INDEX { agnVoiceSwConfHGdbIdx, agnVoiceSwConfHGIdx }
      ::= { agnVoiceSwConfHGTable 1}

AgnVoiceSwConfHGEntry ::=
      SEQUENCE {
 agnVoiceSwConfHGdbIdx INTEGER,
 agnVoiceSwConfHGIdx  INTEGER,
 agnVoiceSwConfHGConnect INTEGER,
 agnVoiceSwConfHGExt  INTEGER
}

agnVoiceSwConfHGdbIdx OBJECT-TYPE
      SYNTAX  INTEGER {    active(1),  temporary(255)  }
      ACCESS  read-only
      STATUS  mandatory
      DESCRIPTION
      "Active or Temporary Table.
       Both configurations can be read but only the Temporary can
       be written to."
      ::= { agnVoiceSwConfHGEntry 1}

agnVoiceSwConfHGIdx OBJECT-TYPE
      SYNTAX  INTEGER(1..10)
      ACCESS  read-only
      STATUS  mandatory
      DESCRIPTION
      "There may be up to 10 Hunt Groups per MXcess. That's the
       index of the hunt group relevant to this row."
      ::= { agnVoiceSwConfHGEntry 2}

agnVoiceSwConfHGConnect OBJECT-TYPE
      SYNTAX  INTEGER {  no(2),  yes(3)   }
      ACCESS  read-write
      STATUS  mandatory
      DESCRIPTION
      "This attribute indicates whether the  hunt group  should be
       considered in any of the mux algorithms."
      ::= { agnVoiceSwConfHGEntry 3}

agnVoiceSwConfHGExt OBJECT-TYPE
      SYNTAX  INTEGER(0..99)
      ACCESS  read-write
      STATUS  mandatory
      DESCRIPTION
      "This is the extension number of the hunt group.
       0 is for not valid. The allowed range is 10 - 99."
      DEFVAL { 0 }
      ::= { agnVoiceSwConfHGEntry 4}


--
-- Signaling Profiles for MP-2200
--

agnSigProfileTable  OBJECT-TYPE
     SYNTAX SEQUENCE OF AgnSigProfileEntry
     ACCESS not-accessible
     STATUS  mandatory
     DESCRIPTION
      "The write operation into the Table Objects is valid only
       to the TmpCnfg entry."
     ::= { agnSigProfile 1}

agnSigProfileEntry OBJECT-TYPE
      SYNTAX AgnSigProfileEntry
      ACCESS not-accessible
      STATUS mandatory
      DESCRIPTION "" INDEX {agnSigProfileCnfgIdx, agnSigProfileIdx, agnSigProfileRxTx}
      ::= { agnSigProfileTable 1}

AgnSigProfileEntry ::=
      SEQUENCE {
      agnSigProfileCnfgIdx INTEGER,
      agnSigProfileIdx     INTEGER,
      agnSigProfileRxTx    INTEGER,
      agnSigProfileABCD    OCTET STRING
      }


agnSigProfileCnfgIdx OBJECT-TYPE
      SYNTAX  INTEGER (1..255)
      ACCESS  read-only
      STATUS  mandatory
      DESCRIPTION
      "This attribute indicates the Idx of the Cnfg (1..100) being
       accessed.
       Idx 255 relates to the TmpCnfg.
       The write operation is valid only to the TmpCnfg."
      ::= { agnSigProfileEntry 1}

agnSigProfileIdx OBJECT-TYPE
      SYNTAX  INTEGER (1..5)
      ACCESS  read-only
      STATUS  mandatory
      DESCRIPTION
      "This attribute indicates the Signaling Profile (1..5)."
      ::= { agnSigProfileEntry 2}

agnSigProfileRxTx OBJECT-TYPE
      SYNTAX  INTEGER
       {
       rx   (1),
       tx   (2)
       }
      ACCESS  read-only
      STATUS  mandatory
      DESCRIPTION
      "This attribute indicates if the following objects refer to:
       Rx or Tx translation.
       Rx : ML->IO
       Tx : IO->ML  ."
      ::= { agnSigProfileEntry 3}

agnSigProfileABCD OBJECT-TYPE
      SYNTAX  OCTET STRING
      ACCESS  read-write
      STATUS  mandatory
      DESCRIPTION
      "This object represents 6 parameters, by 3 Octets :
    Busy  Code-MSB nibble, - applicable only for Rx translation
    Idle  Code-    nibble, - applicable only for Rx translation
       D Bit Code-    nibble,
       C Bit Code-    nibble,
       B Bit Code-    nibble,
       A Bit Code-LSB nibble.

       Each of Busy and Idle Code nibble will have the valid values:
       0000 .. FFFF.

       Each of A,B,C,D Bit Code nibble represents:
    0 hex = 0000 = 0
    1 hex = 0001 = 1
    2 hex = 0010 = A bit
    3 hex = 0011 = B bit
    4 hex = 0100 = C bit
    5 hex = 0101 = D bit
    6 hex = 0110 = A bit inverse
    7 hex = 0111 = B bit inverse
    8 hex = 1000 = C bit inverse
    9 hex = 1001 = D bit inverse
    A-F hex - not used (invalid values) "
      ::= { agnSigProfileEntry 4}

--
-- TS Assignment Table from system point of view
--
-- agnTsTable  OBJECT-TYPE ::= { agnSystemTs 1}
--
-- For this table see tsa.txt file.

--
-- Wan installed module status general information
--
mdlSInstTable  OBJECT-TYPE
      SYNTAX SEQUENCE OF MdlSInstEntry
      ACCESS not-accessible
      STATUS  mandatory
      DESCRIPTION "" ::= { statMdlGen 1 }

mdlSInstEntry OBJECT-TYPE
      SYNTAX MdlSInstEntry
      ACCESS not-accessible
      STATUS mandatory
      DESCRIPTION "" INDEX { mdlSInstSltIdx }
      ::= { mdlSInstTable 1}

MdlSInstEntry ::=
      SEQUENCE {
     mdlSInstSltIdx        INTEGER,
     mdlSInstCardType      INTEGER,
     mdlSHwVersion         DisplayString (SIZE (0..255)),
     mdlSSwVersion         DisplayString (SIZE (0..255)),
     mdlSAlrStatus         INTEGER,
     mdlSAlrStatusAll      INTEGER,
     mdlSMaskedAlrStat     INTEGER,
     mdlSMaskedAlrStatAll  INTEGER,
     mdlSTstStatusAll      INTEGER,
     mdlSClearAlrCmd       INTEGER,
     mdlSClearAllAlrCmd    INTEGER
      }

mdlSInstSltIdx OBJECT-TYPE
      SYNTAX  INTEGER
       {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16)
       }
      ACCESS  read-only
      STATUS  mandatory
      DESCRIPTION
      "A unique number to identify a slot position in the mux.
       In the ?004 Unit the entries PsB(2),ClB(4),io6(10)..io(16)
       are not valid."
      ::= { mdlSInstEntry 1}


mdlSInstCardType OBJECT-TYPE
      SYNTAX  INTEGER
       {
  --
  -- General types
  --
         unknown        (1),
         empty          (2),

  -- (3)..(7) are reserved ; they appear in the compress structure

		 acm            (9), --alarm module
  --
  -- Power Supply Modules
  --
        ps60W          (10),
        ps100W         (11),

  --
  -- Cl Modules
  --
        cl1            (20),
        clEth          (21),
        cl2            (22),
		cl2Eth         (23),
        cl3            (24),
		cl3Eth         (25),

  --
  -- Packet Cards of Megaplex
  --
        mPh1            (31),
        mPh3            (32),
        mPh1T1DSU       (33),
        mPh1T1CSU       (34),
        mPh1E1DSU       (35),
        mPh1E1LTU       (36),

        mPl6            (60),
        mPl3            (61),
        mPv4            (72),

  --
  -- TDM Cards
  --

      vf3EandM          (80),
      vf3Fxs            (81),
      vf3Fxo            (82),

      vfPbx             (83),
      vfPbxT1           (84),
      vfPbxE1           (85),

      mtMlF2T1          (88),
      mtMlF2E1          (89),
      mtMlT1Fiber       (90),
      mtMlE1Fiber       (91),
      mtMlT1FiberFb     (92),
      mtMlE1FiberFb     (93),
      mtmlHE1           (94),
      mtmlH1E1          (95),
      mtmlHSE1          (96),
      ml20              (97),
      mtMl4T1           (98),
      mtMl4E1           (99),

      mtMl1T1DSU       (100),
      mtMl1T1CSU       (101),
      mtMl1E1DSU       (102),
      mtMl1E1LTU       (103),
      mtMl1T1DSUfb     (104),
      mtMl1T1CSUfb     (105),
      mtMl1E1DSUfb     (106),
      mtMl1E1LTUfb     (107),
      mtMl2T1          (108),
      mtMl2E1          (109),

       ls2CcittX50     (110),
       ls2CcittX58     (111),
       ls2ATandTSdm    (112),
       ls2ACcittX50    (113),
       ls2ACcittX58    (114),
       ls2AATandTSdm   (115),
       ls2A2Ts         (116),
       ls2M            (117),

       hs2             (120),
       hs3             (121),
       hsq             (122),
       hs703           (123),
       hsQM            (124),
       hsqN            (125),
       hs6             (126),
       hs12            (127),

       hs4T1           (130),
       hs4E1           (131),
       hs4             (132),

       vc2EandM        (140),
       vc2Fxs1Plar     (141),
       vc2Fxo1         (142),
       vc2Fxs2         (143),
       vc2Fxo2         (144),
       vc2Fxs3         (145),
       vc2Fxo3         (146),
       vc26EandM       (147),
       mtvc2           (148),
       vc2R2Fxs        (149),

       hsu             (150),

       mbeA            (151),
       mbeB            (152),
       mbeU            (153),
       tre             (154),

       hsuI            (155),
       hsr             (156),
       hss             (157),
       hsu1            (158),

       ls12            (159),
       ls6             (160),
       ls6V1EandM      (161),
       ls6V1Fxo        (162),
       ls6V1Fxs        (163),
       ls6V2EandM      (164),
       ls6V2Fxo        (165),
       ls6V2Fxs        (166),
       ls6VfEandM      (167),
       ls6VfFxo        (168),
       ls6VfFxs        (169),

       vc3EandM        (170),
       vc3Fxo          (171),
       vc3Fxs          (172),

       vcPbx           (173),
       vcPbxT1         (174),
       vcPbxE1         (175),

       vc6EandM        (176),
       vc6Fxo          (177),
       vc6Fxs          (178),

       vcq             (179),

  --
  -- Packet Cards of MAXcess and Hybrid
  --

        -- High speed cards

        mhs1V36          (181),
        mhs1V35          (182),
        mhs1G703         (183),
        mhs1DDS          (184),
        mhs3             (185),
        mhs1X21          (186),
        mhs1V24          (187),
		mhs4             (188),
        mhsE1Hs          (189),
		mhsT1Hs          (190),
		mhsHyE1Hs        (191), -- 2 HS ports + 1 Hybrid E1 port
		mhsHyT1Hs        (192), -- 2 HS ports + 1 Hybrid T1 port
        mlfHybE1Hs       (193), -- Fiber Optic Hybrid: 2 HS + 1 Hybrid E1 port
        mlfHybT1Hs       (194), -- Fiber Optic Hybrid: 2 HS + 1 Hybrid T1 port 


        -- T1/E1 cards

        mhs2e1			 (195),
		mhs2t1           (196),
		mhsHy2e1         (197), -- 2 Hybrid E1 ports
		mhsHy2t1         (198), -- 2 Hybrid T1 ports
        mlfHybE12        (199), -- Fiber Optic Hybrid: 2 E1 ports
        

        -- Low speed cards

        mls6             (200),
        mls3             (201),


        -- More  T1/E1 cards


        mlfHybT12        (204), -- Fiber Optic Hybrid: 2 T1 ports



		-- Voice cards

        mvc4             (210),
        mvc4PbxE1        (211),
        mvc4PbxT1Dsu     (212),
        mvc4PbxT1Csu     (213),
        mvc4PbxE1Slave   (214),
        mvc4PbxT1Slave   (215),

		-- ISDN for Maxcess
        mhsS             (220),
        mhsU             (221),
        mhsPriE1         (222),
        mhsPriT1         (223),

        --Voice cards for MP
        vc12EandM        (230),
        vc12Fxo          (231),
        vc12Fxs          (232),
		vc6aEandM        (233),
        vc6aFxo          (234),
        vc6aFxs          (235),
        vc6AgFxo         (236),
        vc6AgFxs         (237),

        --ISDN cards for MP
		hsu12            (240),
		hsu6             (241),
		hss12            (242),
		hss6             (243),

        -- VOIP cards for MPH & MX
        mvg1Lan          (253),
        mvg2Lan          (254)

          }
      ACCESS  read-only
      STATUS  mandatory
      DESCRIPTION
      "This attribute indicates the type of card installed
       in the specific slot position.
       Only PS cards are possible in the PS slots.
       Only CL cards are possible in the CL slots.
       Only IO cards are possible in the IO slots."
      ::= { mdlSInstEntry 2}

mdlSHwVersion OBJECT-TYPE
      SYNTAX  DisplayString (SIZE (0..255))
      ACCESS  read-only
      STATUS  mandatory
      DESCRIPTION
      "This attribute indicates the Hardware version of the
       installed card in the specific slot position."
      ::= { mdlSInstEntry 3 }

mdlSSwVersion OBJECT-TYPE
      SYNTAX  DisplayString (SIZE (0..255))
      ACCESS  read-only
      STATUS  mandatory
      DESCRIPTION
      "This attribute indicates the Software version of the
       installed card in the specific slot position."
      ::= {mdlSInstEntry 4}


mdlSAlrStatus OBJECT-TYPE
      SYNTAX  INTEGER
       {
  off      (2),
  event    (3),
  minor    (4),
  major    (5),
     warning  (6),
  critical (7)
       }
      ACCESS  read-only
      STATUS  mandatory
      DESCRIPTION
      "Indicates the alarm state at module level, i.e. lower level
      (port alarms) status is not included.
      This attribute will be set to:
    critical(7) - when there is at least one active (state ON)
                  critical alarm,
                  otherwise it will be set to
       major(5) - when there is at least one active (state ON)
                  major alarm,
                  otherwise it will be set to
       minor(4) - if there is at least one active (state ON) minor
                  alarm,
                  otherwise it will be set to
       warning(6) - if there is at least one active (state ON)
                  warning alarm,
                  otherwise it will be set to
       event(3) - if there was at least one alarm event (including
                  state on,off events) since the last clear operation."
       ::= { mdlSInstEntry 5 }

mdlSAlrStatusAll OBJECT-TYPE
      SYNTAX  INTEGER
       {
  off      (2),
  event    (3),
  minor    (4),
  major    (5),
     warning  (6),
  critical (7)
       }
      ACCESS  read-only
      STATUS  mandatory
      DESCRIPTION
      "Indicates the alarm state in the module-all level, i.e. lower level
      (port alarms) included.
      This attribute will be set to:
    critical(7) - when there is at least one active (state ON)
                  critical alarm,
                  otherwise it will be set to
       major(5) - when there is at least one active (state ON)
                  major alarm,
                  otherwise it will be set to
       minor(4) - if there is at least one active (state ON) minor
                  alarm,
                  otherwise it will be set to
       warning(6) - if there is at least one active (state ON)
                  warning alarm,
                  otherwise it will be set to
       event(3) - if there was at least one alarm event (including
                  state on,off events) since the last clear operation."
       ::= { mdlSInstEntry 6 }

mdlSMaskedAlrStat OBJECT-TYPE
      SYNTAX  INTEGER
       {
  off      (2),
  event    (3),
  minor    (4),
  major    (5),
     warning  (6),
  critical (7)
       }
      ACCESS  read-only
      STATUS  mandatory
      DESCRIPTION
      "Indicates the alarm state at module level, [i.e. lower level
      (port alarms) status is not included],including Masked alarms.
      This attribute will be set to:
    critical(7) - when there is at least one active (state ON)
                  critical alarm,
                  otherwise it will be set to
       major(5) - when there is at least one active (state ON)
                  major alarm,
                  otherwise it will be set to
       minor(4) - if there is at least one active (state ON) minor
                  alarm,
                  otherwise it will be set to
       warning(6) - if there is at least one active (state ON)
                  warning alarm,
                  otherwise it will be set to
       event(3) - if there was at least one alarm event (including
                  state on,off events) since the last clear operation."
       ::= { mdlSInstEntry 7 }

mdlSMaskedAlrStatAll OBJECT-TYPE
      SYNTAX  INTEGER
       {
  off      (2),
  event    (3),
  minor    (4),
  major    (5),
     warning  (6),
  critical (7)
       }
      ACCESS  read-only
      STATUS  mandatory
      DESCRIPTION
      "Indicates the alarm state in the module-all level, i.e. lower level
      (port alarms) included, including Masked alarms.
      This attribute will be set to:
    critical(7) - when there is at least one active (state ON)
                  critical alarm,
                  otherwise it will be set to
       major(5) - when there is at least one active (state ON)
                  major alarm,
                  otherwise it will be set to
       minor(4) - if there is at least one active (state ON) minor
                  alarm,
                  otherwise it will be set to
       warning(6) - if there is at least one active (state ON)
                  warning alarm,
                  otherwise it will be set to
       event(3) - if there was at least one alarm event (including
                  state on,off events) since the last clear operation."
       ::= { mdlSInstEntry 8 }

mdlSTstStatusAll OBJECT-TYPE
      SYNTAX  INTEGER
       {
  off(2),
  on (3)
       }
      ACCESS  read-only
      STATUS  mandatory
      DESCRIPTION
      "This attribute will be set to on(3) when there is at least
       one test in progress on a channel of the card, otherwise
       the value will be off(2)."
      ::= { mdlSInstEntry 9 }


mdlSClearAlrCmd  OBJECT-TYPE
      SYNTAX  INTEGER
       {
  off(2),
  on (3)
       }
      ACCESS  read-write
      STATUS  mandatory
      DESCRIPTION
      "Setting this command to ON, enforces a clear of all the
       alarms in the given slot, excluding alarms of port level.
       The clear operation will not be applied for masked/inverted
       alarms."
      ::= { mdlSInstEntry 10 }

mdlSClearAllAlrCmd  OBJECT-TYPE
      SYNTAX  INTEGER
       {
  off(2),
  on (3)
       }
      ACCESS  read-write
      STATUS  mandatory
      DESCRIPTION
      "Setting this command to ON, enforces a  clear of all the
       alarms in the given slot, including all its ports alarms.
       The clear operation will not be applied for masked/inverted
       alarms."
      ::= { mdlSInstEntry 11 }

mdlSAlrTable OBJECT-TYPE
      SYNTAX SEQUENCE OF MdlSAlrEntry
      ACCESS not-accessible
      STATUS mandatory
      DESCRIPTION
      "The list of card agent alarms ; includes also an alarm
       indicating existence of alarms on its ports if there are any."
      ::= { statMdlGen 2 }

mdlSAlrEntry OBJECT-TYPE
      SYNTAX MdlSAlrEntry
      ACCESS not-accessible
      STATUS mandatory
      DESCRIPTION "" INDEX {mdlSAlrSltIdx , mdlSAlrIdx}
      ::= { mdlSAlrTable 1}

MdlSAlrEntry ::=
      SEQUENCE {
     mdlSAlrSltIdx           INTEGER,
  mdlSAlrIdx              INTEGER,
     mdlSAlrCodeDescription  DisplayString (SIZE (0..255)),
  mdlSAlrCode             INTEGER,
  mdlSAlrSeverity         INTEGER,
  mdlSAlrState            INTEGER,
  mdlSAlrCounter          INTEGER,
  mdlSAlrMask             INTEGER,
  mdlSAlrInvert           INTEGER
      }

mdlSAlrIdx OBJECT-TYPE
      SYNTAX  INTEGER
      ACCESS  read-only
      STATUS  mandatory
      DESCRIPTION
      "A unique number to identify an entry in the alarm status table.
       Users should use the get next function to read this table because
       the indexes are not consecutive."
      ::= { mdlSAlrEntry 1}

mdlSAlrSltIdx OBJECT-TYPE
      SYNTAX  INTEGER
       {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16)
       }
      ACCESS  read-only
      STATUS  mandatory
      DESCRIPTION
      "This attribute indicates the  desired slot position.
       In the ?004 Unit the entries PsB(2),ClB(4),io6(10)..io12(16)
       are not valid."
      ::= { mdlSAlrEntry 2}

mdlSAlrCodeDescription OBJECT-TYPE
      SYNTAX  DisplayString (SIZE (0..255))
      ACCESS  read-only
      STATUS  mandatory
      DESCRIPTION
      "This attribute is a full text description of the alarm .
       The alarm description includes the following information:
       alarm code, alarm text, alarm severity, Masked or Inverted
       flag and counter."
      ::= { mdlSAlrEntry 3}

mdlSAlrCode OBJECT-TYPE
      SYNTAX  INTEGER
      ACCESS  read-only
      STATUS  mandatory
      DESCRIPTION
      "A code identifying the alarm of an entry in the alarm status
       table at card level."
      ::= { mdlSAlrEntry 4 }

mdlSAlrSeverity OBJECT-TYPE
      SYNTAX  INTEGER
       {
  event    (3),
  minor    (4),
  major    (5),
     warning  (6),
  critical (7)
       }
      ACCESS  read-only
      STATUS  mandatory
      DESCRIPTION
      "The severity of the alarm."
      ::= { mdlSAlrEntry 5 }

mdlSAlrState  OBJECT-TYPE
      SYNTAX  INTEGER
       {
  off(2),
  on (3)
       }
      ACCESS  read-only
      STATUS  mandatory
      DESCRIPTION
      "State of the alarm."
      ::= { mdlSAlrEntry 6 }

mdlSAlrCounter OBJECT-TYPE
      SYNTAX  INTEGER
      ACCESS  read-only
      STATUS  mandatory
      DESCRIPTION
      "A counter - how many times the alarm occured since last
       clear operation.
       ON and OFF Alarm will be counted separately."
      ::= { mdlSAlrEntry 7 }

mdlSAlrMask  OBJECT-TYPE
      SYNTAX  INTEGER
       {
  off(2),
  on (3)
       }
      ACCESS  read-only
      STATUS  mandatory
      DESCRIPTION
      "Alarm mask : on/off."
      ::= { mdlSAlrEntry 8 }

mdlSAlrInvert  OBJECT-TYPE
      SYNTAX  INTEGER
       {
  off(2),
  on (3)
       }
      ACCESS  read-only
      STATUS  mandatory
      DESCRIPTION
      "Alarm invert : on/off."
      ::= { mdlSAlrEntry 9 }


--
-- Wan module configuration information
--
mdlCPrgTable  OBJECT-TYPE
      SYNTAX SEQUENCE OF MdlCPrgEntry
      ACCESS not-accessible
      STATUS  mandatory
      DESCRIPTION "" ::= { cnfgMdlGen 1 }

mdlCPrgEntry OBJECT-TYPE
      SYNTAX MdlCPrgEntry
      ACCESS not-accessible
      STATUS mandatory
      DESCRIPTION "" INDEX { mdlCCnfgIdx, mdlCSltIdx  }
      ::= { mdlCPrgTable 1}

MdlCPrgEntry ::=
      SEQUENCE {
   		mdlCCnfgIdx           INTEGER,
      	mdlCSltIdx            INTEGER,
   		mdlCPrgCardType       INTEGER,
   		mdlCNoOfExternPrt     INTEGER,   -- RO
   		mdlCNoOfInternPrt     INTEGER    -- RO
      }

mdlCCnfgIdx OBJECT-TYPE
      SYNTAX  INTEGER (1..255)
      ACCESS  read-only
      STATUS  mandatory
      DESCRIPTION
      "This attribute indicates the Idx of the Cnfg(1..100) being
       referred.
       Value  255 specifies the TmpCnfg "
      ::= { mdlCPrgEntry 1}
-- In phase I only the values 1 (Cnfg1) and 255 (temp) are valid.

mdlCSltIdx OBJECT-TYPE
      SYNTAX  INTEGER
       {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16)
       }
      ACCESS  read-only
      STATUS  mandatory
      DESCRIPTION
      "This attribute indicates a unique number of  the slot
       position where the card is inserted.
       In the ?004 Unit the entries psB(2),clB(4),io6(10)..io(16)
       are not valid."
      ::= { mdlCPrgEntry 2}

mdlCPrgCardType OBJECT-TYPE
      SYNTAX  INTEGER
       {
  --
  -- General types
  --
        unknown         (1),
        empty           (2),

  -- (3)..(7) are reserved ; they appear in the compress structure

		 acm            (9), --alarm module

  --
  -- Power Supply Modules
  --
        ps48x60W       (10),
        ps48x100W      (11),
        ps110x60W      (12),
        ps110x100W     (13),
        ps220x60W      (14),
        ps220x100W     (15),
        ps180W         (16),

  --
  -- Cl Modules
  --
        cl1            (20),
        clEth          (21),
        cl2            (22),
		cl2Eth         (23),
        cl3            (24),
		cl3Eth         (25),

  --
  -- Packet Cards of Megaplex
  --
        mPh1            (31),
        mPh3            (32),
        mPh1T1DSU       (33),
        mPh1T1CSU       (34),
        mPh1E1DSU       (35),
        mPh1E1LTU       (36),

        mPl6            (60),
--      mPl3            (61),
--      mPv4            (72),


  --
  -- TDM Cards
  --

      vf3EandM          (80),
      vf3Fxs            (81),
      vf3Fxo            (82),

      vfPbx             (83),
      vfPbxT1           (84),
      vfPbxE1           (85),

      mtMlF2T1          (88),
      mtMlF2E1          (89),
      mtMlT1Fiber       (90),
      mtMlE1Fiber       (91),
      mtMlT1FiberFb     (92),
      mtMlE1FiberFb     (93),
      mtmlHE1           (94),
      mtmlH1E1          (95),
      mtmlHSE1          (96),
      ml20              (97),
      mtMl4T1           (98),
      mtMl4E1           (99),

      mtMl1T1DSU       (100),
      mtMl1T1CSU       (101),
      mtMl1E1DSU       (102),
      mtMl1E1LTU       (103),
      mtMl1T1DSUfb     (104),
      mtMl1T1CSUfb     (105),
      mtMl1E1DSUfb     (106),
      mtMl1E1LTUfb     (107),
      mtMl2T1          (108),
      mtMl2E1          (109),

      ls2CcittX50      (110),
      ls2CcittX58      (111),
      ls2ATandTSdm     (112),
      ls2ACcittX50     (113),
      ls2ACcittX58     (114),
      ls2AATandTSdm    (115),
      ls2A2Ts          (116),
      ls2M             (117),

      hs2              (120),
      hs3              (121),
      hsq              (122),
      hs703            (123),
      hsQM             (124),
      hsqN             (125),
      hs6              (126),
      hs12             (127),

      hs4T1            (130),
      hs4E1            (131),

      vc2EandM         (140),
      vc2Fxs1Plar      (141),
      vc2Fxo1          (142),
      vc2Fxs2          (143),
      vc2Fxo2          (144),
      vc2Fxs3          (145),
      vc2Fxo3          (146),
      vc26EandM        (147),
      mtvc2            (148),
      vc2R2Fxs         (149),

      hsu              (150),

      mbeA             (151),
      mbeB             (152),
      mbeU             (153),
      tre              (154),

      hsuI             (155),
      hsr              (156),
      hss              (157),
      hsu1             (158),

      ls12            (159),
      ls6             (160),
      ls6V1EandM      (161),
      ls6V1Fxo        (162),
      ls6V1Fxs        (163),
      ls6V2EandM      (164),
      ls6V2Fxo        (165),
      ls6V2Fxs        (166),
      ls6VfEandM      (167),
      ls6VfFxo        (168),
      ls6VfFxs        (169),

      vc3EandM        (170),
      vc3Fxo          (171),
      vc3Fxs          (172),

      vcPbx           (173),
      vcPbxT1         (174),
      vcPbxE1         (175),

      vc6EandM        (176),
      vc6Fxo          (177),
      vc6Fxs          (178),

      vcq             (179),

  --
  -- Packet Cards of Maxcess and Hybrid
  --

        -- High speed cards

        mhs1V36          (181),
        mhs1V35          (182),
        mhs1G703         (183),
        mhs1DDS          (184),
        mhs3             (185),
        mhs1X21          (186),
        mhs1V24          (187),
		mhs4             (188),
        mhsE1Hs          (189),
		mhsT1Hs          (190),
		mhsHyE1Hs        (191), -- 2 HS ports + 1 Hybrid E1 port
		mhsHyT1Hs        (192), -- 2 HS ports + 1 Hybrid T1 port
        mlfHybE1Hs       (193), -- Fiber Optic Hybrid: 2 HS + 1 Hybrid E1 port
        mlfHybT1Hs       (194), -- Fiber Optic Hybrid: 2 HS + 1 Hybrid T1 port 

        -- T1/E1 cards

        mhs2e1			 (195),
		mhs2t1           (196),
		mhsHy2e1         (197), -- 2 Hybrid E1 ports
		mhsHy2t1         (198), -- 2 Hybrid T1 ports
        mlfHybE12        (199), -- Fiber Optic Hybrid: 2 E1 ports

        -- Low speed cards

        mls6             (200),
        mls3             (201),


        -- More  T1/E1 cards

        mlfHybT12        (204), -- Fiber Optic Hybrid: 2 T1 ports


		-- Voice cards

        mvc4             (210),
        mvc4PbxE1        (211),
        mvc4PbxT1Dsu     (212),
        mvc4PbxT1Csu     (213),
        mvc4PbxE1Slave   (214),
        mvc4PbxT1Slave   (215),

		-- ISDN for Maxcess
        mhsS             (220),
        mhsU             (221),
        mhsPriE1         (222),
        mhsPriT1         (223),

        --Voice cards for MP
        vc12EandM        (230),
        vc12Fxo          (231),
        vc12Fxs          (232),
		vc6aEandM        (233),
        vc6aFxo          (234),
        vc6aFxs          (235),
        vc6AgFxo         (236),
        vc6AgFxs         (237),

        --ISDN cards for MP
		hsu12            (240),
		hsu6             (241),
		hss12            (242),
		hss6             (243),

        -- VOIP cards for MPH & MX
        mvg1Lan          (253),
        mvg2Lan          (254)
		
        }
      ACCESS  read-write
      STATUS  mandatory
      DESCRIPTION
      "This attribute indicates the type of card assigned to the
       specific slot in the common configuration.
       This object is identical in all the configurations (1..100).
       Only the TmpCnf(255) may have different value.
       The write operation is valid only to the TmpCnfg entry."
      ::= { mdlCPrgEntry 3}

mdlCNoOfExternPrt OBJECT-TYPE
      SYNTAX  INTEGER
      ACCESS  read-only
      STATUS  mandatory
      DESCRIPTION
      "Number of external ports in the programmed card of the
       specific slot position"
      ::= { mdlCPrgEntry 4}

mdlCNoOfInternPrt OBJECT-TYPE
      SYNTAX  INTEGER
      ACCESS  read-only
      STATUS  mandatory
      DESCRIPTION
      "Number of internal ports in the programmed card of the
       specific slot position."
      ::= { mdlCPrgEntry 5}

--
-- Compressed information.
--
-- Specially for RadView management station
--
mdlCmprTable  OBJECT-TYPE
      SYNTAX SEQUENCE OF MdlCmprEntry
      ACCESS not-accessible
      STATUS  mandatory
      DESCRIPTION "" ::= { cmprMdlGen 1 }

mdlCmprEntry OBJECT-TYPE
      SYNTAX MdlCmprEntry
      ACCESS not-accessible
      STATUS mandatory
      DESCRIPTION "" INDEX { mdlCmprTypIdx, mdlCmprCnfgIdx ,mdlCmprVersion,mdlCmprSltIdx }
      ::= {mdlCmprTable  1}

MdlCmprEntry ::=
      SEQUENCE {
  mdlCmprTypIdx       INTEGER,
  mdlCmprCnfgIdx       INTEGER,
  mdlCmprVersion    INTEGER,
     mdlCmprSltIdx    INTEGER,
  mdlCmprObj          OCTET STRING
      }

mdlCmprTypIdx OBJECT-TYPE
      SYNTAX  INTEGER
      ACCESS  read-only
      STATUS  mandatory
      DESCRIPTION
      "This attribute indicates the Type of the Compressed being
       referred."
      ::= { mdlCmprEntry 1}

mdlCmprCnfgIdx OBJECT-TYPE
      SYNTAX  INTEGER
      ACCESS  read-only
      STATUS  mandatory
      DESCRIPTION
      "This attribute indicates the configuration to which the
       Compressed information is  related."
      ::= { mdlCmprEntry 2}

mdlCmprVersion OBJECT-TYPE
      SYNTAX  INTEGER
      ACCESS  read-only
      STATUS  mandatory
      DESCRIPTION
      "This attribute indicates the version of the internal format
       of the Compressed data"
      ::= { mdlCmprEntry 3}

mdlCmprSltIdx  OBJECT-TYPE
      SYNTAX  INTEGER
       {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16)
       }
      ACCESS  read-only
      STATUS  mandatory
      DESCRIPTION
      "This attribute indicates a unique number of  the slot
       position where the card is inserted.
       In the ?004 Unit the entries psB(2),clB(4),io6(10)..io(16)
       are not valid."
      ::= { mdlCmprEntry 4}

mdlCmprObj OBJECT-TYPE
      SYNTAX  OCTET STRING
      ACCESS  read-write
      STATUS  mandatory
      DESCRIPTION
      "This attribute is the compressed information itself."
      ::= { mdlCmprEntry 5}

-- Compressed Alarm table at Card level
-- The only way of reading this table is by the command 'GET NEXT'

mdlAlarmsCmprTable  OBJECT-TYPE
      SYNTAX SEQUENCE OF MdlAlarmsCmprEntry
      ACCESS not-accessible
      STATUS  mandatory
      DESCRIPTION "" ::= {cmprMdlGen 2}

mdlAlarmsCmprEntry OBJECT-TYPE
      SYNTAX MdlAlarmsCmprEntry
      ACCESS not-accessible
      STATUS mandatory
      DESCRIPTION "" INDEX {mdlAlarmsCmprVersion,
             mdlAlarmsCmprAlarmSlot,mdlAlarmsCmprAlarmIdx}
      ::= {mdlAlarmsCmprTable  1}

MdlAlarmsCmprEntry ::=
      SEQUENCE {
     mdlAlarmsCmprVersion      INTEGER,
     mdlAlarmsCmprAlarmSlot    INTEGER,
     mdlAlarmsCmprAlarmIdx     INTEGER,
     mdlAlarmsCmprObj          OCTET STRING
      }

mdlAlarmsCmprVersion OBJECT-TYPE
      SYNTAX  INTEGER
      ACCESS  read-only
      STATUS  mandatory
      DESCRIPTION
      "This attribute indicates the version of the internal format
       of the Compressed data"
      ::= { mdlAlarmsCmprEntry 1}

mdlAlarmsCmprAlarmSlot  OBJECT-TYPE
      SYNTAX  INTEGER
      ACCESS  read-only
      STATUS  mandatory
      DESCRIPTION
      "This attribute indicates the  desired slot position.
       In the ?004 Unit the entries PsB(2),ClB(4),io6(10)..io(16)
       are not valid."
      ::= { mdlAlarmsCmprEntry 2}

mdlAlarmsCmprAlarmIdx  OBJECT-TYPE
      SYNTAX  INTEGER
      ACCESS  read-only
      STATUS  mandatory
      DESCRIPTION
      "A unique number to identify an entry in the alarm status table
       of the agent."
      ::= { mdlAlarmsCmprEntry 3}

mdlAlarmsCmprObj OBJECT-TYPE
      SYNTAX  OCTET STRING
      ACCESS  read-write
      STATUS  mandatory
      DESCRIPTION
      "This attribute is the compressed information itself."
      ::= { mdlAlarmsCmprEntry 4}


--
-- Wan port status general information
--
prtSInstTable  OBJECT-TYPE
      SYNTAX SEQUENCE OF PrtSInstEntry
      ACCESS not-accessible
      STATUS  mandatory
      DESCRIPTION "" ::= { statPrtGen 1 }

prtSInstEntry OBJECT-TYPE
      SYNTAX PrtSInstEntry
      ACCESS not-accessible
      STATUS mandatory
      DESCRIPTION "" INDEX { prtSInstSltIdx, prtSInstPrtIdx }
      ::= { prtSInstTable 1}

PrtSInstEntry ::=
      SEQUENCE {
        prtSInstSltIdx       INTEGER,
        prtSInstPrtIdx       INTEGER,
        prtSInstPrtType      INTEGER,
        prtSInstIfIndex      INTEGER,
        prtSActiveStatus     INTEGER,
        prtSAlrStatus        INTEGER,
        prtSMaskedAlrStat    INTEGER,
        prtSClearAlrCmd      INTEGER,
        prtSTestMask         INTEGER,
--        prtSTstStatus        INTEGER,
        prtSTstCmd           INTEGER,
        prtSTstDuration      INTEGER,
        prtSBertClrCmd       INTEGER,
        prtSBertTstRslt      INTEGER,
        prtSInterfaceType    DisplayString (SIZE (0..255)),
        prtSParamStatus      OCTET STRING
      }

prtSInstSltIdx OBJECT-TYPE
      SYNTAX  INTEGER
       {
       clA   (3),
       clB   (4),
       io1   (5),
       io2   (6),
       io3   (7),
       io4   (8),
       io5   (9),
       io6  (10),
       io7  (11),
       io8  (12),
       io9  (13),
       io10 (14),
       io11 (15),
       io12 (16),
       notApplicable (255)
       }
      ACCESS  read-only
      STATUS  mandatory
      DESCRIPTION
      "This attribute indicates a unique number to identify the
       slot where the card is inserted.
       In the ?004 Unit the entries io6(10)..io(16) are not valid."
      ::= { prtSInstEntry 1}

prtSInstPrtIdx OBJECT-TYPE
      SYNTAX  INTEGER
      ACCESS  read-only
      STATUS  mandatory
      DESCRIPTION
      "This attribute indicates a unique number to identify a port
       in a specific card.
       The valid ports depend on the installed card:
       the valid external ports (interfaces) are (1..mdlCNoOfExternPrt) if any,
       and the valid internal ports are (101..100+mdlCNoOfInternPrt) if any.
       Generally:  exPrt1 (1) .. exPrt12  (12),
					inPrt14 (114) .. inPrt48 (148) "
      ::= { prtSInstEntry 2}

prtSInstPrtType  OBJECT-TYPE
      SYNTAX  INTEGER
       {
  external      (2),
  internal      (3),
  highSpeedV35  (4),
  highSpeedV24  (5),
  highSpeedV36  (6),
  highSpeedX21  (7),
  highSpeedG703 (8),
  highSpeedDDS  (9),
  lowSpeed      (10),
  voice         (11),
  cl            (12),
  isdns         (13),
  isdnu         (14),
  ethernet      (15),
  voiceS0       (16)
       }
      ACCESS  read-only
      STATUS  mandatory
      DESCRIPTION
       "This attribute describes the type of the designated port.
	   In MX 3000 only external & internal options are used.
	   All the other options are only for MX 30/300 which need special handling.
	   In order to support interface types in MX 3000, return an ascii string for
	   prtSInterfaceType in this table or support the general RAD value of
       physicalConnector.

       External port - is a port with  a physical connector.
       Internal port - might be of two types:
         a) A composite port which collects a few external ports
            data into a common bandwidth (usually routed through
            DS1 link)
         b) A port which gets only part of the external ports
            (usually a few DS0's)
    The following types are used when all ports are external/
    internal and the connector/interface type is necessary
    (for example, stand-alone units):
       High Speed port types
       Low  Speed port types
       Voice port types, CL port types."
      ::= { prtSInstEntry 3}

prtSInstIfIndex  OBJECT-TYPE
      SYNTAX  INTEGER
      ACCESS  read-only
      STATUS  mandatory
      DESCRIPTION
      "This attribute indicates the  unique  interface number
       assigned to the port. The specific interface of this
       attribute is the same as the interface identified by the
       value of ifindex  in MIB-II.If there is no interface for
       the specific prtIdx the value will be '7fffffff'h."
      ::= { prtSInstEntry 4}

prtSActiveStatus   OBJECT-TYPE
      SYNTAX  INTEGER
       {
         unknown           (1),
         notUsed           (2),
         offLine           (3),
         onLine            (4),
         offLineRedundancy (5),
         onLineRedundancy  (6)
       }
      ACCESS  read-only
      STATUS  mandatory
      DESCRIPTION
      "This attribute describes the activity status of the port.
       unknown(1) indicates that the information is not supported.
       notUsed(2) indicates that the ch is not connected according
                  to the active config.
       offLine(3) indicates that the ch is down (not working)
                  because of any problem.
       onLine(4)  indicates that the ch is up (working)
       offLineRedundancy(5) indicates that the ch is down, because
                            it is redundant port.
       onLineRedundancy(6)  indicates that the ch is up, and it is
                            the active link"
      ::= { prtSInstEntry 5}

prtSAlrStatus OBJECT-TYPE
      SYNTAX  INTEGER
       {
  off      (2),
  event    (3),
  minor    (4),
  major    (5),
  warning  (6),
  critical (7)
       }
      ACCESS  read-only
      STATUS  mandatory
      DESCRIPTION
      "Indicates the alarm state in the port(ch) agent level.
      This attribute will be set to:
    critical(7) - when there is at least one active (state ON)
                  critical alarm,
                  otherwise it will be set to
       major(5) - when there is at least one active (state ON)
                  major alarm,
                  otherwise it will be set to
       minor(4) - if there is at least one active (state ON) minor
                  alarm,
                  otherwise it will be set to
       warning(6) - if there is at least one active (state ON)
                  warning alarm,
                  otherwise it will be set to
       event(3) - if there was at least one alarm event (including
                  state on,off events) since the last clear operation."
      ::= { prtSInstEntry 6}

prtSMaskedAlrStat OBJECT-TYPE
      SYNTAX  INTEGER
       {
  off      (2),
  event    (3),
  minor    (4),
  major    (5),
  warning  (6),
  critical (7)
       }
      ACCESS  read-only
      STATUS  mandatory
      DESCRIPTION
      "Indicates the alarm state in the port(ch) agent level,
       including Masked alarms.
       This attribute will be set to:
    critical(7) - when there is at least one active (state ON)
                  critical alarm,
                  otherwise it will be set to
       major(5) - when there is at least one active (state ON)
                  major alarm,
                  otherwise it will be set to
       minor(4) - if there is at least one active (state ON) minor
                  alarm,
                  otherwise it will be set to
       warning(6) - if there is at least one active (state ON)
                  warning alarm,
                  otherwise it will be set to
       event(3) - if there was at least one alarm event (including
                  state on,off events) since the last clear operation."
 ::= {prtSInstEntry 7}

prtSClearAlrCmd  OBJECT-TYPE
      SYNTAX  INTEGER
       {
  off(2),
  on (3)
       }
      ACCESS  read-write
      STATUS  mandatory
      DESCRIPTION
      "Setting this attribute to on(3) enforces a clear operation
       of the alarm status events in the given port. The clear
       operation will not be applied for masked/inverted alarms."
      ::= { prtSInstEntry 8}

prtSTestMask OBJECT-TYPE
      SYNTAX  INTEGER
      ACCESS  read-only
      STATUS  mandatory
      DESCRIPTION
      "This is a mask which indicates which tests from the
       'prtSTstCmd' list are allowed for the requested port.
       If a specific test is allowed, its respective bit
       will be SET in the mask :

         TEST                  BIT
        -----------            ---
        local-loop              1
        remote-loop             2
        loc-and-rem-main-loops  3
        remote-analog-loop      4
        remote-digital-loop     5
        rem-loop-on-ext-unit    6
        bert                    7
        tone-injection          8
        dlci local-loop         9
        all dlci local-loop    10
        dlci remote-loop       11
        all dlci remote-loop   12
        bert-and-rem-loop-on-rem-unit 13
        rem-loop-on-rem-unit   14
        block                  15
        backward-tone-inject   16
        llb                    17
        rlb                    18

        ft1Enable              21
		lbbd                   22  --for 2B+D
		lb1                    23  --for B1
		lb2                    24  --for B2

        e.g : If the return value is 3 -> 0000000000000011  ->
              Bits 1 & 2 are set -> the allowed tests are :
                                           local-loop
                                           remote-loop
        "
      ::= { prtSInstEntry 9}

-- prtSTstStatus OBJECT-TYPE
--      SYNTAX  INTEGER
--          {
--        off(2),
--        on (3)
--          }
--      ACCESS  read-only
--      STATUS  mandatory
--      DESCRIPTION
--      "This attribute will be set to on(3) when there is at least
--       one test in progress in the port, otherwise the value
--       will be off(2)."
--      ::= { prtSInstEntry 10}
--


prtSTstCmd OBJECT-TYPE
      SYNTAX  INTEGER
       {
        none                 (1),
        localLoop            (2),
        remoteLoop           (3),
        locAndRemMainLoops   (4),
        remoteAnalogLoop     (5),
        remoteDigitalLoop    (6),
        remLoopOnExtUnit     (7),
        bert                 (8),
        toneInjection        (9),
        dlciLocalLoop        (10),
        allDlciLocalLoop     (11),
        dlciRemoteLoop       (12),
        allDlciRemoteLoop    (13),
        extInitLocalLoop     (14),
        bertAndRemLoopOnRemUnit (15),
        remLoopOnRemUnit     (16),
        block                (17),
        backwardToneInject   (18),
        llb                  (19),
        rlb                  (20),
        ft1Enable            (21),
		lbbd                 (22),	--for 2B+D
		lb1                  (23),	--for B1
		lb2                  (24)	--for B2
       }
      ACCESS  read-write
      STATUS  mandatory
      DESCRIPTION
      "Setting this attribute to any of the above values will
       initiate a test on the specific port if the operation is
       legal. If the operation is not legal, the mux will ignore
       the operation.
       If a test time out is needed, the test will be set with a
       default timeout of 2 minutes until the user will set the
       parameter 'prtSTstDuration' to the required time out.
       If no time out is needed , the test will be set with infinite
       timeout until the user will set the parameter
       'prtSTstDuration' to the required time out."
      ::= { prtSInstEntry 10}

prtSTstDuration OBJECT-TYPE
      SYNTAX  INTEGER
      ACCESS  read-write
      STATUS  mandatory
      DESCRIPTION
      "This attribute indicates the maximum duration of executing
      a test on the specific port. This entry applies to all the
      test operations. The resolution will be a minute, and the
      maximum duration is limited to 30 minutes .
      A zero  value specifies no time limitation.
      When the test isn't active, the agent initiates this object to
      2 when the duration is needed and to 0 if its not required.
      The user should set this parameter after setting the
      'prtSTstCmd' parameter."
      ::= { prtSInstEntry 11}

prtSBertClrCmd  OBJECT-TYPE
      SYNTAX  INTEGER {
      off(2),
      on (3)
      }
      ACCESS  read-write
      STATUS  mandatory
      DESCRIPTION
      "Setting this attribute initiates bert count clear operation.
       It is valid only when bert test is active on the specific
       port."
      ::= { prtSInstEntry 12}

prtSBertTstRslt   OBJECT-TYPE
      SYNTAX  INTEGER
      ACCESS  read-only
      STATUS  mandatory
      DESCRIPTION
      "This attribute indicates the number of Bit Error Rate
       indicated during the BERT operation.
       It is valid only when bert test is active on the specific
       port."
      ::= { prtSInstEntry 13}

prtSInterfaceType OBJECT-TYPE
      SYNTAX  DisplayString (SIZE (0..255))
      ACCESS  read-only
      STATUS  mandatory
      DESCRIPTION
      "This attribute indicates a unique HW interface type of the
       selected port."
      ::= { prtSInstEntry 14}


prtSParamStatus OBJECT-TYPE
      SYNTAX  OCTET STRING
      ACCESS  read-only
      STATUS  mandatory
      DESCRIPTION
      "This object indicates Status of parameters specific to the
       selected port.
       - For a port that has no special status or is supported
         by prtSExHsfStatTable - 1 Octet: 00hex

       - For VC-6, VC-12, VC-12/6 external ports - 1 Octet :
         Bit 7 (MSB)..Bit 2 = 0 (NA)
         Bit 1:       Tx Signaling '1'=On ; '0'=Off
         Bit 0 (LSB): Rx Signaling '1'=On ; '0'=Off

       - For VC-6A and VC-6AG external ports - 1 Octet :
         Bit 7 (MSB)..Bit 3 = 0 (NA)
		 Bit 2:       ADPCM module '1' =Exist ; '0' =Not Exist
         Bit 1:       Tx Signaling '1'=On ; '0'=Off
         Bit 0 (LSB): Rx Signaling '1'=On ; '0'=Off

       - For VC-2/R2(FXS) external ports - 1 Octet :
         Bit  -   7 6 5 4 3 2 1 0
                  |_| |_________|
                  Call  Call State
             Direction

         Bit 7 (MSB) and Bit 6  : Call Direction
         00 - Incoming
         01 - Outgoing
         Bit 5..Bit 0: Call State
         000000 - Idle
         000001 - Seized
         000010 - Both-Way Conflict
         000011 - Seizure Ack
         000100 - Answered
         000101 - Clear Backward
         000110 - Clear Forward
         000111 - Blocked
         001000 - Fault
         001001 - Fault 3
         001010 - Fault 4
         001011 - Fault 5
         001100 - Fault 6
         001101 - Fault 7

       - For ML-20 external port - 3 Octets :
         - 1 MS Octet will represent the Real Rate used:
               Bit    - 7 6 5 4 3 2 1 0
                        |___| |_______|
                  spare  Rate

           Valid values: 0..31, meaning 0..31x64Kbps
           Invalid values: 32..255.
         - 2 LS Octets will represent the Status of 7 Control
           Signals:
           Signal - ---  CTS  DSR  DCD   RJ   TM   DTR  RTS
           Bit   - 7 6  5 4  3 2  1 0    7 6  5 4  3 2  1 0
           Octet  -          2                     3 (LS)
           '---' will always have the value 00
           Rest of the Signals (2 bits each) can have the following
           values:
           00=NA   ;  01=unused ; 10=Off  ; 11=On

       - For ML-H/E1, ML-H/1/E1, ML-H/S/E1 internal port - 1 Octet
         Bit    - 7 6 5 4 3 2 1 0
                  |___________|
                    spare       Mode of Operation

         Mode of Operation: '1'=Central  ; '0'=Remote

       - For ACM external port - 1 Octet
         Bit    - 7 6 5 4 3 2 1 0
                  |_________|
                    spare       Alarm State

         Alarm State: according to bits 1,0:
         00=NA   ;  01=unused ; 10=Off  ; 11=On

       - For HS-U/1 external port - 1 Octet
	     Bit 7  6  5  4  3  2  1  0 LSB
             |________|  |__|  |__|
               spare     modem  sync  
               
         modem: 00 = unknown         sync:  00 = not sync
                01 = ASMi-31                01 = sync
                10 = other                  10 = reserved
                11 = reserved               11 = reserved "
      ::= { prtSInstEntry 15}


prtSAlrTable OBJECT-TYPE
      SYNTAX SEQUENCE OF PrtSAlrEntry
      ACCESS not-accessible
      STATUS mandatory
      DESCRIPTION
      "The list of port agent alarms."
      ::= { statPrtGen 2 }

prtSAlrEntry OBJECT-TYPE
      SYNTAX PrtSAlrEntry
      ACCESS not-accessible
      STATUS mandatory
      DESCRIPTION "" INDEX { prtSAlrSltIdx, prtSAlrPrtIdx, prtSAlrIdx}
      ::= { prtSAlrTable 1}

PrtSAlrEntry ::=
      SEQUENCE {
  prtSAlrSltIdx            INTEGER,
  prtSAlrPrtIdx            INTEGER,
  prtSAlrIdx               INTEGER,
  prtSAlrCodeDescription   DisplayString (SIZE (0..255)),
  prtSAlrCode              INTEGER,
  prtSAlrSeverity          INTEGER,
  prtSAlrState             INTEGER,
  prtSAlrCounter           INTEGER,
  prtSAlrMask              INTEGER,
  prtSAlrInvert            INTEGER
      }

prtSAlrIdx OBJECT-TYPE
      SYNTAX  INTEGER
      ACCESS  read-only
      STATUS  mandatory
      DESCRIPTION
      "A unique number to identify an entry in the alarm status table.
       Users should use the get next function to read this table because
       the indexes are not consecutive"
      ::= { prtSAlrEntry 1}

prtSAlrSltIdx OBJECT-TYPE
      SYNTAX  INTEGER
       {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16),
    notApplicable (255)
       }
      ACCESS  read-only
      STATUS  mandatory
      DESCRIPTION
      "This attribute indicates a unique identifier of  the slot
       where the card is inserted.
       In the ?004 Unit the entries PsB(2),ClB(4),io6(10)..io12(16)
       are not valid."
    ::= { prtSAlrEntry 2}

prtSAlrPrtIdx OBJECT-TYPE
      SYNTAX  INTEGER
      ACCESS  read-only
      STATUS  mandatory
      DESCRIPTION
      "This attribute indicates a unique identifier of  the port
       the alarm applies to.
       All the values are valid. No alarms exist for a port
       which does not physically exist.
       Valid values: exPrt1    (1) .. exPrt12  (12) ,
                     inPrt1  (101) .. inPrt48 (148)."
    ::= { prtSAlrEntry 3}

prtSAlrCodeDescription OBJECT-TYPE
      SYNTAX  DisplayString (SIZE (0..255))
      ACCESS  read-only
      STATUS  mandatory
      DESCRIPTION
      "This attribute is a full text description of the alarm.
       The alarm description includes the following information:
       alarm code, alarm text, alarm severity, Masked  or Inverted
       flag and counter."
       ::= { prtSAlrEntry 4}

prtSAlrCode OBJECT-TYPE
      SYNTAX  INTEGER
      ACCESS  read-only
      STATUS  mandatory
      DESCRIPTION
      "A code identifying the alarm of an entry in the alarm status
       table at port level."
      ::= { prtSAlrEntry 5 }

prtSAlrSeverity OBJECT-TYPE
      SYNTAX  INTEGER
       {
  event    (3),
  minor    (4),
  major    (5),
     warning  (6),
  critical (7)
       }
      ACCESS  read-only
      STATUS  mandatory
      DESCRIPTION
      "The severity of the alarm."
      ::= { prtSAlrEntry 6 }

prtSAlrState  OBJECT-TYPE
      SYNTAX  INTEGER
       {
  off(2),
  on (3)
       }
      ACCESS  read-only
      STATUS  mandatory
      DESCRIPTION
      "State of the alarm."
      ::= { prtSAlrEntry 7 }

prtSAlrCounter OBJECT-TYPE
      SYNTAX  INTEGER
      ACCESS  read-only
      STATUS  mandatory
      DESCRIPTION
      "A counter - how many times the alarm occured since last
       clear operation.
       ON and OFF Alarm will be counted separately."
      ::= { prtSAlrEntry 8 }

prtSAlrMask  OBJECT-TYPE
      SYNTAX  INTEGER
       {
  off(2),
  on (3)
       }
      ACCESS  read-only
      STATUS  mandatory
      DESCRIPTION
      "Alarm mask : on/off."
      ::= { prtSAlrEntry 9 }

prtSAlrInvert  OBJECT-TYPE
      SYNTAX  INTEGER
       {
  off(2),
  on (3)
       }
      ACCESS  read-only
      STATUS  mandatory
      DESCRIPTION
      "Alarm invert : on/off."
      ::= { prtSAlrEntry 10 }

--
-- Statistics of Ports
--

statisPrtGen   OBJECT IDENTIFIER ::= {statPrtGen 3}

prtFrStatis    OBJECT IDENTIFIER ::= {statisPrtGen 1}
prtCrStatis    OBJECT IDENTIFIER ::= {statisPrtGen 2}
prtDlciStatis  OBJECT IDENTIFIER ::= {statisPrtGen 3}
prtT1Statis    OBJECT IDENTIFIER ::= {statisPrtGen 4}

--prtFrStatis - Port Statistics for (FR) Frame Relay protocol

prtFrStatisTable  OBJECT-TYPE
     SYNTAX SEQUENCE OF PrtFrStatisEntry
     ACCESS not-accessible
     STATUS  mandatory
     DESCRIPTION
      "This table is applicable only for an active port running an
       FR protocol ."
  ::= { prtFrStatis 1}

prtFrStatisEntry OBJECT-TYPE
      SYNTAX PrtFrStatisEntry
      ACCESS not-accessible
      STATUS mandatory
      DESCRIPTION "" INDEX {prtFrStatisSltIdx, prtFrStatisPrtIdx, prtFrStatisInvIdx}
      ::= { prtFrStatisTable 1}

PrtFrStatisEntry ::=
      SEQUENCE {
      prtFrStatisSltIdx    INTEGER,
      prtFrStatisPrtIdx    INTEGER,
   prtFrStatisInvIdx    INTEGER,
      prtFrTimeElapsed     INTEGER,
      prtFrRxTotalFrames   Counter,
      prtFrTxTotalFrames   Counter,
      prtFrRxTotalBytes    Counter,
      prtFrTxTotalBytes    Counter,
      prtFrRxMngFrames     Counter,
      prtFrTxMngFrames     Counter,
      prtFrRxDeFrames      Counter,
      prtFrTxDeFrames      Counter,
      prtFrRxDcrdCongDeFr  Counter,
      prtFrTxDcrdCongDeFr  Counter,
      prtFrRxDcrdCongAllFr Counter,
      prtFrTxDcrdCongAllFr Counter,
      prtFrRxFecn     Counter,
      prtFrTxFecn     Counter,
      prtFrRxBecn     Counter,
      prtFrTxBecn     Counter,
      prtFrRxBeViol     Counter,
      prtFrTxBeViol        Counter,
      prtFrRxBcViol     Counter,
      prtFrTxBcViol     Counter
      }

prtFrStatisSltIdx    OBJECT-TYPE
      SYNTAX  INTEGER
       {
       io1   (5),
       io2   (6),
       io3   (7),
       io4   (8),
       io5   (9),
       io6  (10),
       io7  (11),
       io8  (12),
       io9  (13),
       io10 (14),
       io11 (15),
       io12 (16),
       notApplicable (255)
       }
      ACCESS  read-only
      STATUS  mandatory
      DESCRIPTION
      "This attribute indicates a unique  slot  position where
       the module is inserted.
       In the ?004 Unit the entries io6(10)..io12(16) are not valid.
       For stand-alone units this index will be notApplicable (255)."
      ::= { prtFrStatisEntry 1}

prtFrStatisPrtIdx OBJECT-TYPE
      SYNTAX  INTEGER
      {
          exPrt1  (1) ,
          exPrt2  (2) ,
          exPrt3  (3) ,
          exPrt4  (4) ,
          exPrt5  (5) ,
          exPrt6  (6)
       }
      ACCESS  read-only
      STATUS  mandatory
      DESCRIPTION
      "This attribute indicates a unique  port number."
      ::= { prtFrStatisEntry 2}

prtFrStatisInvIdx OBJECT-TYPE
      SYNTAX  INTEGER
       {
          currentInv (1),
    last       (2)
    }
      ACCESS  read-only
      STATUS  mandatory
      DESCRIPTION
   "The Interval of 15 min. for which the following statistics
    counters are applicable."
      ::= { prtFrStatisEntry 3}

prtFrTimeElapsed OBJECT-TYPE
      SYNTAX  INTEGER (0..899)
      ACCESS  read-only
      STATUS  mandatory
      DESCRIPTION
      "The number of seconds that have elapsed  since the
       beginning of the current error-measurement interval.
       This object is applicable mainly for the current interval.
       For other interval:
       - if data is available: value will be 899.
       - if data is not available: value will be 0."
      ::= { prtFrStatisEntry 4 }

prtFrRxTotalFrames OBJECT-TYPE
      SYNTAX   Counter
      ACCESS   read-only
      STATUS   mandatory
      DESCRIPTION
      "The total number of frames received by this port during the
       selected interval."
      ::= { prtFrStatisEntry 5 }

prtFrTxTotalFrames OBJECT-TYPE
      SYNTAX   Counter
      ACCESS   read-only
      STATUS   mandatory
      DESCRIPTION
      "The total number of frames sent by this port during the
       selected interval."
      ::= { prtFrStatisEntry 6 }

prtFrRxTotalBytes OBJECT-TYPE
      SYNTAX   Counter
      ACCESS   read-only
      STATUS   mandatory
      DESCRIPTION
      "The total number of bytes received by this port during the
       selected interval."
      ::= { prtFrStatisEntry 7 }

prtFrTxTotalBytes OBJECT-TYPE
      SYNTAX   Counter
      ACCESS   read-only
      STATUS   mandatory
      DESCRIPTION
      "The total number of bytes sent by this port during the
       selected interval."
      ::= { prtFrStatisEntry 8 }

prtFrRxMngFrames OBJECT-TYPE
      SYNTAX   Counter
      ACCESS   read-only
      STATUS   mandatory
      DESCRIPTION
      "The management number of frames received by this port
       during the selected interval."
      ::= { prtFrStatisEntry 9 }

prtFrTxMngFrames OBJECT-TYPE
      SYNTAX   Counter
      ACCESS   read-only
      STATUS   mandatory
      DESCRIPTION
      "The management number of frames sent by this port during the
       selected interval."
      ::= { prtFrStatisEntry 10 }

prtFrRxDeFrames OBJECT-TYPE
      SYNTAX   Counter
      ACCESS   read-only
      STATUS   mandatory
      DESCRIPTION
      "The number of De frames received by this port during the
       selected interval."
      ::= { prtFrStatisEntry 11 }

prtFrTxDeFrames OBJECT-TYPE
      SYNTAX   Counter
      ACCESS   read-only
      STATUS   mandatory
      DESCRIPTION
      "The number of De frames sent by this port during the
       selected interval."
      ::= { prtFrStatisEntry 12 }

prtFrRxDcrdCongDeFr OBJECT-TYPE
      SYNTAX   Counter
      ACCESS   read-only
      STATUS   mandatory
      DESCRIPTION
      "The number of De frames discarded due to congestion,
       received by this port during the selected interval."
      ::= { prtFrStatisEntry 13 }

prtFrTxDcrdCongDeFr OBJECT-TYPE
      SYNTAX   Counter
      ACCESS   read-only
      STATUS   mandatory
      DESCRIPTION
      "The number of De frames discarded due to congestion,
       sent by this port during the selected interval."
      ::= { prtFrStatisEntry 14 }

prtFrRxDcrdCongAllFr OBJECT-TYPE
      SYNTAX   Counter
      ACCESS   read-only
      STATUS   mandatory
      DESCRIPTION
      "All the frames discarded due to congestion,
       received by this port during the selected interval."
      ::= { prtFrStatisEntry 15 }

prtFrTxDcrdCongAllFr OBJECT-TYPE
      SYNTAX   Counter
      ACCESS   read-only
      STATUS   mandatory
      DESCRIPTION
      "All the frames discarded due to congestion,
       sent by this port during the selected interval."
      ::= { prtFrStatisEntry 16 }

prtFrRxFecn OBJECT-TYPE
      SYNTAX   Counter
      ACCESS   read-only
      STATUS   mandatory
      DESCRIPTION
      "Number of frames received by this port during the
       selected interval, indicating forward congestion."
      ::= { prtFrStatisEntry 17 }

prtFrTxFecn OBJECT-TYPE
      SYNTAX   Counter
      ACCESS   read-only
      STATUS   mandatory
      DESCRIPTION
      "Number of frames sent by this port during the
       selected interval, indicating forward congestion."
      ::= { prtFrStatisEntry 18 }

prtFrRxBecn OBJECT-TYPE
      SYNTAX   Counter
      ACCESS   read-only
      STATUS   mandatory
      DESCRIPTION
      "Number of frames received by this port during the
       selected interval, indicating backward congestion."
      ::= { prtFrStatisEntry 19 }

prtFrTxBecn OBJECT-TYPE
      SYNTAX   Counter
      ACCESS   read-only
      STATUS   mandatory
      DESCRIPTION
      "Number of frames sent by this port during the
       selected interval, indicating backward congestion."
      ::= { prtFrStatisEntry 20 }

prtFrRxBeViol OBJECT-TYPE
      SYNTAX   Counter
      ACCESS   read-only
      STATUS   mandatory
      DESCRIPTION
      "Number of data frames received by this port during the
       selected interval, exceeding the Burst Excess value."
      ::= { prtFrStatisEntry 21 }

prtFrTxBeViol OBJECT-TYPE
      SYNTAX   Counter
      ACCESS   read-only
      STATUS   mandatory
      DESCRIPTION
      "Number of data frames sent by this port during the
       selected interval, exceeding the Burst Excess value."
      ::= { prtFrStatisEntry 22 }

prtFrRxBcViol OBJECT-TYPE
      SYNTAX   Counter
      ACCESS   read-only
      STATUS   mandatory
      DESCRIPTION
      "Number of data frames received by this port during the
       selected interval, exceeding the Burst Committed value."
      ::= { prtFrStatisEntry 23 }

prtFrTxBcViol OBJECT-TYPE
      SYNTAX   Counter
      ACCESS   read-only
      STATUS   mandatory
      DESCRIPTION
      "Number of data frames sent by this port during the
       selected interval, exceeding the Burst Committed value."
      ::= { prtFrStatisEntry 24 }


--prtCrStatis - Port Statistics for (CR) Cell Relay protocol

prtCrStatisTable  OBJECT-TYPE
     SYNTAX SEQUENCE OF PrtCrStatisEntry
     ACCESS not-accessible
     STATUS  mandatory
     DESCRIPTION
      "This table is applicable only for an active port running a
       CR protocol ."
  ::= { prtCrStatis 1}

prtCrStatisEntry OBJECT-TYPE
      SYNTAX PrtCrStatisEntry
      ACCESS not-accessible
      STATUS mandatory
      DESCRIPTION "" INDEX {prtCrStatisSltIdx, prtCrStatisPrtIdx, prtCrStatisInvIdx}
      ::= { prtCrStatisTable 1}

PrtCrStatisEntry ::=
      SEQUENCE {
      prtCrStatisSltIdx    INTEGER,
      prtCrStatisPrtIdx    INTEGER,
   prtCrStatisInvIdx    INTEGER,
      prtCrTimeElapsed     INTEGER,
      prtCrRxTotalCells    Counter,
      prtCrTxTotalCells    Counter,
      prtCrRxDataCells     Counter,
      prtCrTxDataCells     Counter
      }

prtCrStatisSltIdx    OBJECT-TYPE
      SYNTAX  INTEGER
       {
       io1   (5),
       io2   (6),
       io3   (7),
       io4   (8),
       io5   (9),
       io6  (10),
       io7  (11),
       io8  (12),
       io9  (13),
       io10 (14),
       io11 (15),
       io12 (16),
       notApplicable (255)
       }
      ACCESS  read-only
      STATUS  mandatory
      DESCRIPTION
      "This attribute indicates a unique  slot  position where
       the module is inserted.
       In the ?004 Unit the entries io6(10)..io12(16) are not valid.
       For stand-alone units this index will be notApplicable (255)."
      ::= { prtCrStatisEntry 1}

prtCrStatisPrtIdx OBJECT-TYPE
      SYNTAX  INTEGER
      {
          exPrt1  (1) ,
          exPrt2  (2) ,
          exPrt3  (3) ,
          exPrt4  (4) ,
          exPrt5  (5) ,
          exPrt6  (6)
       }
      ACCESS  read-only
      STATUS  mandatory
      DESCRIPTION
      "This attribute indicates a unique  port number."
      ::= { prtCrStatisEntry 2}

prtCrStatisInvIdx OBJECT-TYPE
      SYNTAX  INTEGER
       {
          currentInv (1),
    last       (2)
    }
      ACCESS  read-only
      STATUS  mandatory
      DESCRIPTION
   "The Interval of 15 min. for which the following statistics
    counters are applicable."
      ::= { prtCrStatisEntry 3}

prtCrTimeElapsed OBJECT-TYPE
      SYNTAX  INTEGER (0..899)
      ACCESS  read-only
      STATUS  mandatory
      DESCRIPTION
      "The number of seconds that have elapsed  since the
       beginning of the current error-measurement interval.
       This object is applicable mainly for the current interval.
       For other interval:
       - if data is available: value will be 899.
       - if data is not available: value will be 0."
      ::= { prtCrStatisEntry 4 }

prtCrRxTotalCells OBJECT-TYPE
      SYNTAX   Counter
      ACCESS   read-only
      STATUS   mandatory
      DESCRIPTION
      "The total number of cells received by this port during the
       selected interval."
      ::= { prtCrStatisEntry 5 }

prtCrTxTotalCells OBJECT-TYPE
      SYNTAX   Counter
      ACCESS   read-only
      STATUS   mandatory
      DESCRIPTION
      "The total number of cells sent by this port during the
       selected interval."
      ::= { prtCrStatisEntry 6 }

prtCrRxDataCells OBJECT-TYPE
      SYNTAX   Counter
      ACCESS   read-only
      STATUS   mandatory
      DESCRIPTION
      "The number of Data Cells received by this port during the
       selected interval."
      ::= { prtCrStatisEntry 7 }

prtCrTxDataCells OBJECT-TYPE
      SYNTAX   Counter
      ACCESS   read-only
      STATUS   mandatory
      DESCRIPTION
      "The number of Data Cells sent by this port during the
       selected interval."
      ::= { prtCrStatisEntry 8 }


--prtDlciStatis - Port DLCI Statistics for FR, FR+ and CR protocol

prtDlciStatisTable  OBJECT-TYPE
     SYNTAX SEQUENCE OF PrtDlciStatisEntry
     ACCESS not-accessible
     STATUS  mandatory
     DESCRIPTION
      "This table is applicable only for an active port running an
       FR, FR+ or CR protocol, with valid DLCIs ."
  ::= { prtDlciStatis 1}

prtDlciStatisEntry OBJECT-TYPE
      SYNTAX PrtDlciStatisEntry
      ACCESS not-accessible
      STATUS mandatory
      DESCRIPTION "" INDEX {prtDlciSltIdx, prtDlciPrtIdx, prtDlciIdx}
      ::= { prtDlciStatisTable 1}

PrtDlciStatisEntry ::=
      SEQUENCE {
      prtDlciSltIdx          INTEGER,
      prtDlciPrtIdx          INTEGER,
   prtDlciIdx             INTEGER,
      prtDlciRxDeFrames      Counter,
      prtDlciTxDeFrames      Counter,
      prtDlciRxDcrdCongDeFr  Counter,
      prtDlciTxDcrdCongDeFr  Counter,
      prtDlciRxDcrdCongAllFr Counter,
      prtDlciTxDcrdCongAllFr Counter,
      prtDlciTxFecn       Counter,
      prtDlciTxBecn       Counter,
      prtDlciRxBeViol      Counter,
      prtDlciTxBeViol        Counter,
      prtDlciRxBcViol      Counter,
      prtDlciTxBcViol       Counter
      }

prtDlciSltIdx    OBJECT-TYPE
      SYNTAX  INTEGER
       {
       io1   (5),
       io2   (6),
       io3   (7),
       io4   (8),
       io5   (9),
       io6  (10),
       io7  (11),
       io8  (12),
       io9  (13),
       io10 (14),
       io11 (15),
       io12 (16),
       notApplicable (255)
       }
      ACCESS  read-only
      STATUS  mandatory
      DESCRIPTION
      "This attribute indicates a unique  slot  position where
       the module is inserted.
       In the ?004 Unit the entries io6(10)..io12(16) are not valid.
       For stand-alone units this index will be notApplicable (255)."
      ::= { prtDlciStatisEntry 1}

prtDlciPrtIdx OBJECT-TYPE
      SYNTAX  INTEGER
      {
          exPrt1  (1) ,
          exPrt2  (2) ,
          exPrt3  (3) ,
          exPrt4  (4) ,
          exPrt5  (5) ,
          exPrt6  (6)
       }
      ACCESS  read-only
      STATUS  mandatory
      DESCRIPTION
      "This attribute indicates a unique  port number."
      ::= { prtDlciStatisEntry 2}

prtDlciIdx OBJECT-TYPE
      SYNTAX  INTEGER (1..991)
      ACCESS  read-only
      STATUS  mandatory
      DESCRIPTION
      "This attribute indicates a unique DLCI index for each valid
       DLCI (16..991). "
      ::= { prtDlciStatisEntry 3}

prtDlciRxDeFrames OBJECT-TYPE
      SYNTAX   Counter
      ACCESS   read-only
      STATUS   mandatory
      DESCRIPTION
      "The number of De frames received by this DLCI."
      ::= { prtDlciStatisEntry 4 }

prtDlciTxDeFrames OBJECT-TYPE
      SYNTAX   Counter
      ACCESS   read-only
      STATUS   mandatory
      DESCRIPTION
      "The number of De frames sent by this DLCI."
      ::= { prtDlciStatisEntry 5 }

prtDlciRxDcrdCongDeFr OBJECT-TYPE
      SYNTAX   Counter
      ACCESS   read-only
      STATUS   mandatory
      DESCRIPTION
      "The number of De frames discarded due to congestion,
       received by this DLCI."
      ::= { prtDlciStatisEntry 6 }

prtDlciTxDcrdCongDeFr OBJECT-TYPE
      SYNTAX   Counter
      ACCESS   read-only
      STATUS   mandatory
      DESCRIPTION
      "The number of De frames discarded due to congestion,
       sent by this DLCI."
      ::= { prtDlciStatisEntry 7 }

prtDlciRxDcrdCongAllFr OBJECT-TYPE
      SYNTAX   Counter
      ACCESS   read-only
      STATUS   mandatory
      DESCRIPTION
      "All the frames discarded due to congestion,
       received by this DLCI."
      ::= { prtDlciStatisEntry 8 }

prtDlciTxDcrdCongAllFr OBJECT-TYPE
      SYNTAX   Counter
      ACCESS   read-only
      STATUS   mandatory
      DESCRIPTION
      "All the frames discarded due to congestion,
       sent by this DLCI."
      ::= { prtDlciStatisEntry 9 }

prtDlciTxFecn OBJECT-TYPE
      SYNTAX   Counter
      ACCESS   read-only
      STATUS   mandatory
      DESCRIPTION
      "Number of frames sent by this DLCI, indicating forward
       congestion."
      ::= { prtDlciStatisEntry 10 }

prtDlciTxBecn OBJECT-TYPE
      SYNTAX   Counter
      ACCESS   read-only
      STATUS   mandatory
      DESCRIPTION
      "Number of frames sent by this DLCI, indicating backward
       congestion."
      ::= { prtDlciStatisEntry 11 }

prtDlciRxBeViol OBJECT-TYPE
      SYNTAX   Counter
      ACCESS   read-only
      STATUS   mandatory
      DESCRIPTION
      "Number of data frames received by this DLCI, exceeding the
       Burst Excess value."
      ::= { prtDlciStatisEntry 12 }

prtDlciTxBeViol OBJECT-TYPE
      SYNTAX   Counter
      ACCESS   read-only
      STATUS   mandatory
      DESCRIPTION
      "Number of data frames sent by this DLCI, exceeding the Burst
       Excess value."
      ::= { prtDlciStatisEntry 13 }

prtDlciRxBcViol OBJECT-TYPE
      SYNTAX   Counter
      ACCESS   read-only
      STATUS   mandatory
      DESCRIPTION
      "Number of data frames received by this DLCI, exceeding the
       Burst Committed value."
      ::= { prtDlciStatisEntry 14 }

prtDlciTxBcViol OBJECT-TYPE
      SYNTAX   Counter
      ACCESS   read-only
      STATUS   mandatory
      DESCRIPTION
      "Number of data frames sent by this DLCI, exceeding the Burst
       Committed value."
      ::= { prtDlciStatisEntry 15 }


--prtT1 Last FDL Message Table - Statistics

prtT1FdlMsgTable  OBJECT-TYPE
     SYNTAX SEQUENCE OF PrtT1FdlMsgEntry
     ACCESS not-accessible
     STATUS  mandatory
     DESCRIPTION
      "This table is applicable for a T1 interface with 'esf'
       LineType ."
  ::= { prtT1Statis 1}

prtT1FdlMsgEntry OBJECT-TYPE
      SYNTAX PrtT1FdlMsgEntry
      ACCESS not-accessible
      STATUS mandatory
      DESCRIPTION "" INDEX {prtT1FdlMsgSltIdx, prtT1FdlMsgPrtIdx, prtT1FdlMsgFdlTxRx}
      ::= { prtT1FdlMsgTable 1}

PrtT1FdlMsgEntry ::=
      SEQUENCE {
      prtT1FdlMsgSltIdx    INTEGER,
      prtT1FdlMsgPrtIdx    INTEGER,
   prtT1FdlMsgFdlTxRx   INTEGER,
      prtT1FdlMsg          OCTET STRING
      }

prtT1FdlMsgSltIdx    OBJECT-TYPE
      SYNTAX  INTEGER
       {
       io1   (5),
       io2   (6),
       io3   (7),
       io4   (8),
       io5   (9),
       io6  (10),
       io7  (11),
       io8  (12),
       io9  (13),
       io10 (14),
       io11 (15),
       io12 (16)
       }
      ACCESS  read-only
      STATUS  mandatory
      DESCRIPTION
      "This attribute indicates a unique  slot  position where
       the module is inserted.
       In the ?004 Unit the entries io6(10)..io12(16) are not valid."
      ::= { prtT1FdlMsgEntry 1}

prtT1FdlMsgPrtIdx OBJECT-TYPE
      SYNTAX  INTEGER
       {
       exPrt1    (1)
       }
      ACCESS  read-only
      STATUS  mandatory
      DESCRIPTION
      "This attribute indicates a unique  port number.
       MTML-1/T1 modules have just one external interface."
      ::= { prtT1FdlMsgEntry 2}

prtT1FdlMsgFdlTxRx OBJECT-TYPE
      SYNTAX  INTEGER
       {
          tx    (1),
    rx    (2)
    }
      ACCESS  read-only
      STATUS  mandatory
      DESCRIPTION
   "The Fdl tx/rx reference of the Fdl message."
      ::= { prtT1FdlMsgEntry 3}


prtT1FdlMsg  OBJECT-TYPE
   SYNTAX  OCTET STRING
      ACCESS  read-only
      STATUS  mandatory
      DESCRIPTION
   "FDL message."
      ::= { prtT1FdlMsgEntry 4}


--
-- Extension of the Time Slot Config Table of ML ports
--
-- Time Slot is split to 8 Bits


prtExTsSplitTable OBJECT-TYPE
     SYNTAX SEQUENCE OF PrtExTsSplitEntry
     ACCESS not-accessible
     STATUS  mandatory
     DESCRIPTION
      "The write operation into the Table Objects is valid only
       to the TmpCnfg entry."
     ::= {cnfgPrtGen 1}

prtExTsSplitEntry OBJECT-TYPE
      SYNTAX PrtExTsSplitEntry
      ACCESS not-accessible
      STATUS mandatory
      DESCRIPTION "" INDEX {prtExTsCnfgIdx, prtExTsSltIdx, prtExTsPrtIdx,
             prtExTsIdx, prtExTsBit}
      ::= { prtExTsSplitTable 1}

PrtExTsSplitEntry ::=
      SEQUENCE {
      prtExTsCnfgIdx        INTEGER,
      prtExTsSltIdx         INTEGER,
      prtExTsPrtIdx         INTEGER,
      prtExTsIdx            INTEGER,
      prtExTsBit            INTEGER,
      prtExTsIConSlot       INTEGER,
      prtExTsIConPrt        INTEGER
      }

prtExTsCnfgIdx OBJECT-TYPE
      SYNTAX  INTEGER  (1..255)
      ACCESS  read-only
      STATUS  mandatory
      DESCRIPTION
      "This attribute indicates the Idx of the Cnfg (1..100) being
       accessed.
       Idx 255 relates to the TmpCnfg. "
      ::= { prtExTsSplitEntry 1}

prtExTsSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16),
          notApplicable (255)
        }
      ACCESS  read-only
      STATUS  mandatory
      DESCRIPTION
      "This attribute indicates a unique  slot  position where
       the card is inserted.
       In the ?004 Unit the entries io6(10)..io12(16) are not valid.
       notApplicable - for stand-alone units."
      ::= { prtExTsSplitEntry 2}

prtExTsPrtIdx OBJECT-TYPE
      SYNTAX  INTEGER
--  For MP:
--    {
--      exPrt1    (1),
--     inPrt1  (101)
--     }
      ACCESS  read-only
      STATUS  mandatory
      DESCRIPTION
      "This attribute indicates a unique  port number.
       Most ML cards have only one external interface.
       inPrt1 - for MTML-H/E1 cards.
       For other products' index see their specification."
      ::= { prtExTsSplitEntry 3}

prtExTsIdx OBJECT-TYPE
      SYNTAX  INTEGER
      ACCESS  read-only
      STATUS  mandatory
      DESCRIPTION
      "This attribute indicates a unique time slot  position.
       The valid time slots are:
       1..24 for T1 Card and
       1..31 for E1 interface.
       In G732S-E1 lines, time slot 16 is not valid for data,
       it is dedicated to multiframe synchronization bits
       and voice signaling."
      ::= { prtExTsSplitEntry 4}

prtExTsBit OBJECT-TYPE
      SYNTAX  INTEGER (1..8)
      ACCESS  read-only
      STATUS  mandatory
      DESCRIPTION
      "This attribute indicates a unique Bit within the time slot.
       The valid Bits are: 1..8."
      ::= { prtExTsSplitEntry 5}

prtExTsIConSlot OBJECT-TYPE
      SYNTAX  INTEGER
       {
       noConnect (2),
          io1       (5),
          io2       (6),
          io3       (7),
          io4       (8),
          io5       (9),
          io6      (10),
          io7      (11),
          io8      (12),
          io9      (13),
          io10     (14),
          io11     (15),
          io12     (16),
    notApplicable (255)
       }
      ACCESS  read-write
      STATUS  mandatory
      DESCRIPTION
      "This attribute indicates whether the specified time slot is
       connected/routed internally in the Agent and to which card
       it is connected.
       In the ?004 Unit the entries io6(10)..io12(16) are not valid.
       notApplicable - for stand-alone units."
      ::= {prtExTsSplitEntry 6}

prtExTsIConPrt OBJECT-TYPE
      SYNTAX  INTEGER
--    For MP:
--       {
--       exPrt1    (1) ,
--       exPrt2    (2) ,
--       exPrt3    (3) ,
--       exPrt4    (4) ,
--       exPrt5    (5) ,
--       exPrt6    (6) ,
--       exPrt7    (7) ,
--       exPrt8    (8) ,
--       exPrt9    (9) ,
--       exPrt10  (10) ,
--       exPrt11  (11) ,
--       exPrt12  (12) ,
--
--        noConnect (100),
--
--       inPrt1  (101) ,
--       inPrt2  (102) ,
--       inPrt3  (103) ,
--       inPrt4  (104) ,
--       inPrt5  (105) ,
--       inPrt6  (106) ,
--       inPrt7  (107) ,
--       inPrt8  (108) ,
--       inPrt9  (109) ,
--       inPrt10 (110) ,
--    inPrt11 (111) ,
--    inPrt12 (112)
--       }
      ACCESS  read-write
      STATUS  mandatory
      DESCRIPTION
      "This attribute indicates the internally (In Mux)
       connected/routed port.
       For other products' index see their specification."
      ::= {prtExTsSplitEntry 7}


prtCnfgAgenda OBJECT IDENTIFIER ::= {cnfgPrtGen 2}

prtAgendaBehaviourTable OBJECT-TYPE
     SYNTAX SEQUENCE OF PrtAgendaBehaviourEntry
     ACCESS not-accessible
     STATUS  mandatory
     DESCRIPTION
      "The write operation into the Table Objects is valid only
       to the TmpCnfg entry."
     ::= { prtCnfgAgenda 1}

prtAgendaBehaviourEntry OBJECT-TYPE
      SYNTAX PrtAgendaBehaviourEntry
      ACCESS not-accessible
      STATUS mandatory
      DESCRIPTION "" INDEX {prtAgendaBehaviourCnfgIdx, prtAgendaBehaviourSltIdx,
             prtAgendaBehaviourPrtIdx }
      ::= { prtAgendaBehaviourTable 1}

PrtAgendaBehaviourEntry ::=
      SEQUENCE {
      prtAgendaBehaviourCnfgIdx INTEGER,
      prtAgendaBehaviourSltIdx  INTEGER,
      prtAgendaBehaviourPrtIdx  INTEGER,
      prtAgendaBehaviourOnOff   INTEGER
}

prtAgendaBehaviourCnfgIdx OBJECT-TYPE
      SYNTAX  INTEGER  (1..255)
      ACCESS  read-only
      STATUS  mandatory
      DESCRIPTION
      "This attribute indicates the Idx of the Cnfg (1..100) being
       accessed.
       Idx 255 relates to the TmpCnfg. "
      ::= { prtAgendaBehaviourEntry 1}

prtAgendaBehaviourSltIdx  OBJECT-TYPE
      SYNTAX  INTEGER
      ACCESS  read-only
      STATUS  mandatory
      DESCRIPTION
      "This parameter should be:
 - slot number for MX3000
 - 255 = N/A  for MX300/30. "
      ::= { prtAgendaBehaviourEntry 2 }

prtAgendaBehaviourPrtIdx  OBJECT-TYPE
      SYNTAX  INTEGER
      ACCESS  read-only
      STATUS  mandatory
      DESCRIPTION
      "This parameter should be:
 - port number for MX300/30
 - 100 = N/A  for MX3000. "
      ::= { prtAgendaBehaviourEntry 3 }

prtAgendaBehaviourOnOff   OBJECT-TYPE
      SYNTAX  INTEGER
              {
                notApplicable(1),
                off(2),
                on (3)
              }
      ACCESS  read-write
      STATUS  mandatory
      DESCRIPTION
      "Setting this command to on(3) enables the agenda function
       at module (3000) or port (300/30) level."
      DEFVAL { off }
      ::= { prtAgendaBehaviourEntry 4 }

prtCnfgAgendaTable OBJECT-TYPE
     SYNTAX SEQUENCE OF PrtCnfgAgendaEntry
     ACCESS not-accessible
     STATUS  mandatory
     DESCRIPTION
      "This table allows the user to schedule the time a session
        is active per week basis."
     ::= { prtCnfgAgenda 2}

prtCnfgAgendaEntry OBJECT-TYPE
      SYNTAX PrtCnfgAgendaEntry
      ACCESS not-accessible
      STATUS mandatory
      DESCRIPTION "" INDEX { prtCnfgAgendaCnfgIdx, prtCnfgAgendaSltIdx,
 prtCnfgAgendaPrtIdx, prtCnfgAgendaDayIdx, prtCnfgAgendaSesId }
      ::= { prtCnfgAgendaTable 1}

PrtCnfgAgendaEntry ::=
      SEQUENCE {
      prtCnfgAgendaCnfgIdx        INTEGER,
      prtCnfgAgendaSltIdx         INTEGER,
      prtCnfgAgendaPrtIdx         INTEGER,
      prtCnfgAgendaDayIdx         INTEGER,
      prtCnfgAgendaSesId          INTEGER,
      prtCnfgAgendaFrom           INTEGER,
      prtCnfgAgendaTo             INTEGER
      }

prtCnfgAgendaCnfgIdx OBJECT-TYPE
      SYNTAX  INTEGER  (1..255)
      ACCESS  read-only
      STATUS  mandatory
      DESCRIPTION
      "This attribute indicates the Idx of the Cnfg (1..100) being
       accessed.
       Idx 255 relates to the TmpCnfg. "
      ::= { prtCnfgAgendaEntry 1}

prtCnfgAgendaSltIdx OBJECT-TYPE
      SYNTAX  INTEGER
      ACCESS  read-only
      STATUS  mandatory
      DESCRIPTION
      "This attribute is equal to:
 -slot number for MX3000
 -255 = N/A for MX300/30"
      ::= { prtCnfgAgendaEntry 2}

prtCnfgAgendaPrtIdx OBJECT-TYPE
      SYNTAX  INTEGER
      ACCESS  read-only
      STATUS  mandatory
      DESCRIPTION
      "This attribute is equal to:
 -port number for MX300/30
 -100 = N/A for MX3000"
      ::= { prtCnfgAgendaEntry 3}


prtCnfgAgendaDayIdx OBJECT-TYPE
      SYNTAX  INTEGER {
                monday   (1),
                tuesday  (2),
                wednesday(3),
                thursday (4),
                friday   (5),
                saturday (6),
                sunday   (7)
        }
      ACCESS  read-only
      STATUS  mandatory
      DESCRIPTION
      "This attribute for which day of the week this row applies."
      ::= { prtCnfgAgendaEntry 4 }


prtCnfgAgendaSesId OBJECT-TYPE
      SYNTAX  INTEGER (1..4)
      ACCESS  read-only
      STATUS  mandatory
      DESCRIPTION
      "The user may define 4 different active intervals per day."
      ::= { prtCnfgAgendaEntry  5 }

prtCnfgAgendaFrom OBJECT-TYPE
      SYNTAX  INTEGER (0..86400)
      ACCESS  read-write
      STATUS  mandatory
      DESCRIPTION
      "Start from time interval in seconds."
      DEFVAL {86400}
      ::= { prtCnfgAgendaEntry 6 }

prtCnfgAgendaTo OBJECT-TYPE
      SYNTAX  INTEGER (0..86400)
      ACCESS  read-write
      STATUS  mandatory
      DESCRIPTION
      "To time interval in seconds."
      DEFVAL {86400}
      ::= { prtCnfgAgendaEntry 7 }

-- General Port Configuration parameters

prtGenCnfgTable OBJECT-TYPE
     SYNTAX SEQUENCE OF PrtGenCnfgEntry
     ACCESS not-accessible
     STATUS  mandatory
     DESCRIPTION
      "This table allows the user to configure general
       port parameters."
     ::= {cnfgPrtGen 3}

prtGenCnfgEntry OBJECT-TYPE
      SYNTAX PrtGenCnfgEntry
      ACCESS not-accessible
      STATUS mandatory
      DESCRIPTION "" INDEX { prtGenCnfgIdx, prtGenCnfgSltIdx, prtGenCnfgPrtIdx }
      ::= { prtGenCnfgTable 1}

PrtGenCnfgEntry ::=
      SEQUENCE {
      prtGenCnfgIdx            INTEGER,
      prtGenCnfgSltIdx         INTEGER,
      prtGenCnfgPrtIdx         INTEGER,
      prtGenCnfgLinkToSlot     INTEGER,
      prtGenCnfgLinkToPort     INTEGER,
	  prtGenCnfgPortId         INTEGER
      }

prtGenCnfgIdx OBJECT-TYPE
      SYNTAX  INTEGER  (1..255)
      ACCESS  read-only
      STATUS  mandatory
      DESCRIPTION
      "This attribute indicates the Idx of the Cnfg (1..100) being
       accessed.
       Idx 255 relates to the TmpCnfg.
       The write operation is valid only to the TmpCnfg."
      ::= { prtGenCnfgEntry 1}

prtGenCnfgSltIdx OBJECT-TYPE
      SYNTAX  INTEGER
   {   io1   (5),
       io2   (6),
       io3   (7),
       io4   (8),
       io5   (9),
       io6  (10),
       io7  (11),
       io8  (12),
       io9  (13),
       io10 (14),
       io11 (15),
       io12 (16),
    notApplicable (255)
   }
      ACCESS  read-only
      STATUS  mandatory
      DESCRIPTION
      "This attribute indicates a unique  slot  position where
       the card is inserted."
      ::= { prtGenCnfgEntry 2}

prtGenCnfgPrtIdx OBJECT-TYPE
      SYNTAX  INTEGER
      ACCESS  read-only
      STATUS  mandatory
      DESCRIPTION
      "This attribute indicates a unique external or internal port number.
     For MP:
     exPrt1    (1) .. exPrt12  (12) ,
     notApplicable(100),
     inPrt1  (101) .. inPrt48 (148) "
      ::= { prtGenCnfgEntry 3}

prtGenCnfgLinkToSlot OBJECT-TYPE
      SYNTAX  INTEGER
       {
       io1   (5),
       io2   (6),
       io3   (7),
       io4   (8),
       io5   (9),
       io6  (10),
       io7  (11),
       io8  (12),
       io9  (13),
       io10 (14),
       io11 (15),
       io12 (16),
    notApplicable (255)
       }
      ACCESS  read-write
      STATUS  mandatory
      DESCRIPTION
      "This attribute indicates the slot of the ML card to which
       the IO port is mapped."
      ::= { prtGenCnfgEntry 4}

prtGenCnfgLinkToPort OBJECT-TYPE
      SYNTAX  INTEGER
      ACCESS  read-write
      STATUS  mandatory
      DESCRIPTION
      "This attribute indicates the port in the prtGenCnfgLinkToSlot of
       the ML card to which the IO port is mapped.
    For MP:
     exPrt1    (1) ,
     exPrt2    (2) ,
     exPrt3    (3) ,
     exPrt4    (4) ,
     inPrt1  (101)
     notApplicable (255)"
      ::= { prtGenCnfgEntry 5}

prtGenCnfgPortId OBJECT-TYPE
      SYNTAX  INTEGER (0..16777215)
      ACCESS  read-write
      STATUS  mandatory
      DESCRIPTION
      "IO Port Id for V5.1 use.
       This object is applicable only for part of the PSTN and ISDN IO ports.       
       Generally, 0 is a valid value.
       Nevertheless, for ports that do not support this object, the value
       will be: notApplicable= 0"
      ::= { prtGenCnfgEntry 6}

--
-- Compressed information.
--
-- Specially for RadView management station
--
prtCmprTable  OBJECT-TYPE
      SYNTAX SEQUENCE OF PrtCmprEntry
      ACCESS not-accessible
      STATUS  mandatory
      DESCRIPTION "" ::= { cmprPrtGen 1 }

prtCmprEntry OBJECT-TYPE
      SYNTAX PrtCmprEntry
      ACCESS not-accessible
      STATUS mandatory
      DESCRIPTION "" INDEX {prtCmprTypIdx, prtCmprCnfgIdx,prtCmprVersion,prtCmprSltIdx,prtCmprPrtIdx}
      ::= {prtCmprTable  1}

PrtCmprEntry ::=
      SEQUENCE {
     prtCmprTypIdx       INTEGER,
     prtCmprCnfgIdx      INTEGER,
     prtCmprVersion      INTEGER,
     prtCmprSltIdx       INTEGER,
     prtCmprPrtIdx       INTEGER,
     prtCmprObj          OCTET STRING
      }

prtCmprTypIdx OBJECT-TYPE
      SYNTAX  INTEGER
      ACCESS  read-only
      STATUS  mandatory
      DESCRIPTION
      "This attribute indicates the Type of the Compressed being
       referred."
      ::= { prtCmprEntry 1}

prtCmprCnfgIdx OBJECT-TYPE
      SYNTAX  INTEGER
      ACCESS  read-only
      STATUS  mandatory
      DESCRIPTION
      "This attribute indicates the configuration to which the
       Compressed information is  related."
      ::= { prtCmprEntry 2}

prtCmprVersion OBJECT-TYPE
      SYNTAX  INTEGER
      ACCESS  read-only
      STATUS  mandatory
      DESCRIPTION
      "This attribute indicates the version of the internal format of
       the Compressed data"
      ::= { prtCmprEntry 3}

prtCmprSltIdx  OBJECT-TYPE
      SYNTAX  INTEGER
       {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16),
    notApplicable (255)
       }
      ACCESS  read-only
      STATUS  mandatory
      DESCRIPTION
      "This attribute indicates a unique number of the slot position
       where the card is inserted.
       In the ?004 Unit the entries psB(2),clB(4),io6(10)..io(16)
       are not valid."
      ::= { prtCmprEntry 4}

prtCmprPrtIdx  OBJECT-TYPE
      SYNTAX  INTEGER
      ACCESS  read-only
      STATUS  mandatory
      DESCRIPTION
      "This attribute indicates a unique identifier of  the port
       the compressed information relates to.
       Valid values: exPrt1    (1) .. exPrt12  (12) ,
                     inPrt1  (101) .. inPrt48 (148)."
      ::= { prtCmprEntry 5}

prtCmprObj OBJECT-TYPE
      SYNTAX  OCTET STRING
      ACCESS  read-write
      STATUS  mandatory
      DESCRIPTION
      "This attribute is the compressed information itself."
      ::= { prtCmprEntry 6}


-- Compressed Dlci table in the Port level
-- The only way of reading this table is by the command 'GET NEXT'

prtDlciCmprTable  OBJECT-TYPE
      SYNTAX SEQUENCE OF PrtDlciCmprEntry
      ACCESS not-accessible
      STATUS  mandatory
      DESCRIPTION "" ::= { cmprPrtGen 2 }

prtDlciCmprEntry OBJECT-TYPE
      SYNTAX PrtDlciCmprEntry
      ACCESS not-accessible
      STATUS mandatory
      DESCRIPTION "" INDEX {prtDlciCmprCnfgIdx,prtDlciCmprVersion,
             prtDlciCmprSltIdx,prtDlciCmprPrtIdx,prtDlciCmprDlciIdx}
      ::= {prtDlciCmprTable  1}

PrtDlciCmprEntry ::=
      SEQUENCE {
     prtDlciCmprCnfgIdx       INTEGER,
     prtDlciCmprVersion    INTEGER,
     prtDlciCmprSltIdx    INTEGER,
     prtDlciCmprPrtIdx    INTEGER,
     prtDlciCmprDlciIdx       INTEGER,
     prtDlciCmprObj          OCTET STRING
      }

prtDlciCmprCnfgIdx OBJECT-TYPE
      SYNTAX  INTEGER
      ACCESS  read-only
      STATUS  mandatory
      DESCRIPTION
      "This attribute indicates the configuration to which the
       Compressed information is  related."
      ::= { prtDlciCmprEntry 1}

prtDlciCmprVersion OBJECT-TYPE
      SYNTAX  INTEGER
      ACCESS  read-only
      STATUS  mandatory
      DESCRIPTION
      "This attribute indicates the version of the internal format of
       the Compressed data"
      ::= { prtDlciCmprEntry 2}

prtDlciCmprSltIdx  OBJECT-TYPE
     SYNTAX  INTEGER
         {
         io1   (5),
         io2   (6),
         io3   (7),
         io4   (8),
         io5   (9),
         io6  (10),
         io7  (11),
         io8  (12),
         io9  (13),
         io10 (14),
         io11 (15),
         io12 (16),
      notApplicable (255)
         }
     ACCESS  read-only
     STATUS  mandatory
     DESCRIPTION
     "This attribute indicates a unique number of the slot position
      where the module is inserted.
      In the ?004 Unit the entries psB(2),clB(4),io6(10)..io(16)
      are not valid."
     ::= { prtDlciCmprEntry 3}

prtDlciCmprPrtIdx  OBJECT-TYPE
     SYNTAX  INTEGER
     {
    exPrt1    (1) ,
    exPrt2    (2) ,
    exPrt3    (3) ,
    exPrt4    (4) ,
    exPrt5    (5) ,
    exPrt6    (6) ,
    exPrt7    (7) ,
    exPrt8    (8) ,
    exPrt9    (9) ,
    exPrt10  (10) ,
    inPrt1  (101) ,
    inPrt2  (102) ,
    inPrt3  (103) ,
    inPrt4  (104) ,
    inPrt5  (105) ,
    inPrt6  (106) ,
    inPrt7  (107) ,
    inPrt8  (108) ,
    inPrt9  (109) ,
    inPrt10 (110) ,
 inPrt11 (111) ,
 inPrt12 (112)
     }
     ACCESS  read-only
     STATUS  mandatory
     DESCRIPTION
     "This attribute indicates a unique identifier of  the port
      the compressed information relates to.
      All the values are valid."
     ::= { prtDlciCmprEntry 4}

prtDlciCmprDlciIdx  OBJECT-TYPE
      SYNTAX  INTEGER
      ACCESS  read-only
      STATUS  mandatory
      DESCRIPTION
      "This attribute indicates a unique identifier of  the Dlci
       the compressed information relates to.
       The values are between 16 - 991."
      ::= { prtDlciCmprEntry 5}

prtDlciCmprObj OBJECT-TYPE
      SYNTAX  OCTET STRING
      ACCESS  read-write
      STATUS  mandatory
      DESCRIPTION
      "This attribute is the compressed information itself."
      ::= { prtDlciCmprEntry 6}


-- Compressed Alarm table in the Port level
-- The only way of reading this table is by the command 'GET NEXT'

prtAlarmsCmprTable  OBJECT-TYPE
      SYNTAX SEQUENCE OF PrtAlarmsCmprEntry
      ACCESS not-accessible
      STATUS  mandatory
      DESCRIPTION "" ::= {cmprPrtGen 3}

prtAlarmsCmprEntry OBJECT-TYPE
      SYNTAX PrtAlarmsCmprEntry
      ACCESS not-accessible
      STATUS mandatory
      DESCRIPTION "" INDEX {prtAlarmsCmprVersion,prtAlarmsCmprAlarmSlot,
             prtAlarmsCmprAlarmPort,prtAlarmsCmprAlarmIdx}
      ::= {prtAlarmsCmprTable  1}

PrtAlarmsCmprEntry ::=
      SEQUENCE {
     prtAlarmsCmprVersion      INTEGER,
     prtAlarmsCmprAlarmSlot    INTEGER,
     prtAlarmsCmprAlarmPort    INTEGER,
     prtAlarmsCmprAlarmIdx     INTEGER,
     prtAlarmsCmprObj          OCTET STRING
      }

prtAlarmsCmprVersion OBJECT-TYPE
      SYNTAX  INTEGER
      ACCESS  read-only
      STATUS  mandatory
      DESCRIPTION
      "This attribute indicates the version of the internal format of
       the Compressed data"
      ::= { prtAlarmsCmprEntry 1}

prtAlarmsCmprAlarmSlot  OBJECT-TYPE
      SYNTAX  INTEGER
      ACCESS  read-only
      STATUS  mandatory
      DESCRIPTION
      "This attribute indicates the  desired slot position.
       In the ?004 Unit the entries PsB(2),ClB(4),io6(10)..io(16)
       are not valid.
       For Stand-alone units, notApplicable(255) will appear."
      ::= { prtAlarmsCmprEntry 2}

prtAlarmsCmprAlarmPort  OBJECT-TYPE
      SYNTAX  INTEGER
      ACCESS  read-only
      STATUS  mandatory
      DESCRIPTION
      "This attribute indicates a unique identifier of  the port
       the alarm applies to.
       All the values are valid. No alarms exist for a non-physical
       port"
      ::= { prtAlarmsCmprEntry 3}

prtAlarmsCmprAlarmIdx  OBJECT-TYPE
      SYNTAX  INTEGER
      ACCESS  read-only
      STATUS  mandatory
      DESCRIPTION
      "A unique number to identify an entry in the alarm status table
       of the agent."
      ::= { prtAlarmsCmprEntry 4}

prtAlarmsCmprObj OBJECT-TYPE
      SYNTAX  OCTET STRING
      ACCESS  read-only
      STATUS  mandatory
      DESCRIPTION
      "This attribute is the compressed information itself."
      ::= { prtAlarmsCmprEntry 5}




--
-- Specific port status for each module Type
-- *****************************************
--

-- Megaplex?000/?004 port specific status for HS(TDM) modules
-- HS-2,HS-3,HS-Q, HS-6, HS-12
prtSExHsfStatTable OBJECT-TYPE
      SYNTAX SEQUENCE OF PrtSExHsfStatEntry
      ACCESS not-accessible
      STATUS  mandatory
      DESCRIPTION "" ::= {statPrtMux 6}

prtSExHsfStatEntry OBJECT-TYPE
      SYNTAX PrtSExHsfStatEntry
      ACCESS not-accessible
      STATUS mandatory
      DESCRIPTION "" INDEX {prtSExHsfSltIdx, prtSExHsfPrtIdx }
      ::= {prtSExHsfStatTable 1}

PrtSExHsfStatEntry ::=
      SEQUENCE {
      prtSExHsfSltIdx           INTEGER,
      prtSExHsfPrtIdx           INTEGER,
      prtSExHsfInterfaceTyp     INTEGER,
      prtSExHsfRts              INTEGER
      }


prtSExHsfSltIdx OBJECT-TYPE
      SYNTAX  INTEGER
        {
       io1   (5),
       io2   (6),
       io3   (7),
       io4   (8),
       io5   (9),
       io6  (10),
       io7  (11),
       io8  (12),
       io9  (13),
       io10 (14),
       io11 (15),
       io12 (16)
     }
      ACCESS  read-only
      STATUS  mandatory
      DESCRIPTION
      "This attribute indicates a unique  slot  position where
       the card is inserted.
       In the ?004 Unit the entries io6(10)..io16) are not valid."
      ::= { prtSExHsfStatEntry 1}

prtSExHsfPrtIdx OBJECT-TYPE
      SYNTAX  INTEGER
      {
      exPrt1    (1) ,
      exPrt2    (2) ,
      exPrt3    (3) ,
      exPrt4    (4) ,
      exPrt5    (5) ,
      exPrt6    (6) ,
      exPrt7    (7) ,
      exPrt8    (8) ,
      exPrt9    (9) ,
      exPrt10  (10) ,
      exPrt11  (11) ,
      exPrt12  (12)
      }
      ACCESS  read-only
      STATUS  mandatory
      DESCRIPTION
      "This attribute indicates a unique  port number. "
      ::= { prtSExHsfStatEntry 2}

prtSExHsfInterfaceTyp OBJECT-TYPE
      SYNTAX  INTEGER
        {
         unknown     (1),
         v35         (2),
         rs422       (3)
     }
      ACCESS  read-only
      STATUS  mandatory
      DESCRIPTION
      "This attribute indicates a unique interface type of a
       selected port."
      ::= { prtSExHsfStatEntry 3}

prtSExHsfRts OBJECT-TYPE
      SYNTAX  INTEGER
        {
         unknown     (1),
         notActive   (2),
         active      (3)
     }
      ACCESS  read-only
      STATUS  mandatory
      DESCRIPTION
      "This attribute indicates a unique  RTS control signal state."
      ::= { prtSExHsfStatEntry 4}

cnfgMdlMux         OBJECT IDENTIFIER ::= {mdlMux 1}
mdlPbxFramerCnfg   OBJECT IDENTIFIER ::= {cnfgMdlMux 1}

mdlPbxFramerCnfgTable   OBJECT-TYPE
        SYNTAX SEQUENCE OF MdlPbxFramerCnfgEntry
        ACCESS not-accessible
        STATUS mandatory
        DESCRIPTION
        "This table contains parameters relevant to a module belonging to
         a digital voice system, except mdlPbxFraEnhEcho which is relevant
         also for analog cards."
::= {mdlPbxFramerCnfg 1}

mdlPbxFramerCnfgEntry  OBJECT-TYPE
        SYNTAX MdlPbxFramerCnfgEntry
        ACCESS not-accessible
        STATUS mandatory
        DESCRIPTION "" INDEX  { mdlPbxFraCnfgIdx, mdlPbxFraSltIdx }
        ::=  {mdlPbxFramerCnfgTable 1}

MdlPbxFramerCnfgEntry ::=
        SEQUENCE {
                mdlPbxFraCnfgIdx INTEGER,
                mdlPbxFraSltIdx  INTEGER,
                mdlPbxFraEnhEcho INTEGER,
                mdlPbxFraTSGroupAss INTEGER,
                mdlPbxFraSignalMode INTEGER,
                mdlPbxFraSignalVector OCTET STRING,
                mdlPbxFraSignalMask   OCTET STRING,
	            mdlPbxFraFramerSlot INTEGER,
				mdlPbxFraSignaling  INTEGER
                 }

mdlPbxFraCnfgIdx OBJECT-TYPE
SYNTAX INTEGER
        ACCESS read-only
        STATUS mandatory
        DESCRIPTION
      "This attribute indicates the Idx of the Cnfg (1..100) being
       accessed.
       Idx 255 relates to the TmpCnfg. "
        DEFVAL {1}
        ::= { mdlPbxFramerCnfgEntry 1}

mdlPbxFraSltIdx OBJECT-TYPE
        SYNTAX INTEGER{ io1(5), io2(6), io3(7), io4(8), io5(9),
                        io6(10), io7(11), io8(12), io9(13), io10(14),
                        io11(15), io12(16) }
        ACCESS read-only
        STATUS mandatory
        DESCRIPTION
        "The slot relevant to this module."
        ::= { mdlPbxFramerCnfgEntry 2}

mdlPbxFraEnhEcho OBJECT-TYPE
 SYNTAX INTEGER     { notApplicable(1) ,
   disabled(2),
   ms16(3),
   ms32(4)
    }
        ACCESS read-write
        STATUS mandatory
        DESCRIPTION
        "Refers to external ports of an analogue module
        and to the internal ports of the other mvc4 types
        of modules.
        ms16(3) means that the four voice ports have enhanced
                echo of 16ms.
        ms32(4) means that the two first ports have enhanced
                echo of 32 ms while the last two ports have no
                enhanced echo."
        ::= { mdlPbxFramerCnfgEntry 3}

mdlPbxFraTSGroupAss OBJECT-TYPE
        SYNTAX INTEGER{ group1(1), group2(2), group3(3), group4(4),
                        group5(5), group6(6), group7(7), group8(8),
                        notApplicable(255) }
        ACCESS read-write
        STATUS mandatory
        DESCRIPTION
        "In case of T1 modules:
        group1=(1,2,3,4), ...., group6=(21,22,23,24)
        while in case of E1 modules:
		   - If prtExPh1MlLineType=g732sE1 or g732sE1CRC:
             group1=(1,2,3,4),..,group4=(13,14,15,17),
             group5=(18,19,20,21),...,group7=(26,27,28,29)
             group8=(30,31).
		   - If prtExPh1MlLineType=g732nE1 or g732nE1CRC:
             group1=(1,2,3,4),..,group4=(13,14,15,16),
             group5=(17,18,19,20),...,group7=(25,26,27,28)
             group8=(29,30,31)."
        ::= { mdlPbxFramerCnfgEntry 4}

mdlPbxFraSignalMode OBJECT-TYPE
        SYNTAX INTEGER { notApplicable(1),
			tieTrunk(2),
			tieInvert(3),
			casTrans(4),
            userDefined(5),
			ccsTrans(6)
			}
        ACCESS read-write
        STATUS mandatory
        DESCRIPTION
        "Refers to the signaling mode of the Framer module.
         tieTrunk(2), tieInvert(3), casTrans(4) are standard
        coding of the signaling protocol.

        casTrans(4) is Channel Associated Signaling (the signaling is within the
        channels time slot).
		ccsTrans(6) is Common Channel Signaling (the signaling is not within
		the channels time slot).

        userDefined(5) allows the user to define the signaling
        protocol he wants. In this case, the next two MIB fields
        are relevant."
        DEFVAL { casTrans }
        ::= { mdlPbxFramerCnfgEntry 5}

mdlPbxFraSignalVector OBJECT-TYPE
        SYNTAX OCTET STRING
        ACCESS read-write
        STATUS mandatory
        DESCRIPTION
        "In the case of mdlPbxFraSignalMode = userDefined(5), this
        field defines the A,B,C Bits. D bit is supplied for future
        versions.
        Bit  1 = Bit A ON Hook  - Local
        Bit  2 = Bit B ON Hook  - Local
        Bit  3 = Bit C ON Hook  - Local
        Bit  4 = Bit D ON Hook  - Local
        Bit  5 = Bit A OFF Hook - Local
        Bit  6 = Bit B OFF Hook - Local
        Bit  7 = Bit C OFF Hook - Local
        Bit  8 = Bit D OFF Hook - Local

        Bit  9 = Bit A ON Hook  - Remote
        Bit 10 = Bit B ON Hook  - Remote
        Bit 11 = Bit C ON Hook  - Remote
        Bit 12 = Bit D ON Hook  - Remote
        Bit 13 = Bit A OFF Hook - Remote
        Bit 14 = Bit B OFF Hook - Remote
        Bit 15 = Bit C OFF Hook - Remote
        Bit 16 = Bit D OFF Hook - Remote

        In conjunction with the Mask, mdlPbxFraSignalMask, it is
        possible to compute the signal mode."
        DEFVAL { '0000'H}
        ::= { mdlPbxFramerCnfgEntry 6}

mdlPbxFraSignalMask OBJECT-TYPE
        SYNTAX OCTET STRING
        ACCESS read-write
        STATUS mandatory
        DESCRIPTION
        "In the case of mdlPbxFraSignalMode = userDefined(5), this
        field defines the 'don't care' A,B,C Bits. D bit is supplied
        for future versions.
        Bit  1 = Bit A ON Hook  - Local
        Bit  2 = Bit B ON Hook  - Local
        Bit  3 = Bit C ON Hook  - Local
        Bit  4 = Bit D ON Hook  - Local
        Bit  5 = Bit A OFF Hook - Local
        Bit  6 = Bit B OFF Hook - Local
        Bit  7 = Bit C OFF Hook - Local
        Bit  8 = Bit D OFF Hook - Local

        Bit  9 = Bit A ON Hook  - Remote
        Bit 10 = Bit B ON Hook  - Remote
        Bit 11 = Bit C ON Hook  - Remote
        Bit 12 = Bit D ON Hook  - Remote
        Bit 13 = Bit A OFF Hook - Remote
        Bit 14 = Bit B OFF Hook - Remote
        Bit 15 = Bit C OFF Hook - Remote
        Bit 16 = Bit D OFF Hook - Remote."
	DEFVAL { 'ffff'H }
        ::= { mdlPbxFramerCnfgEntry 7}

mdlPbxFraFramerSlot OBJECT-TYPE
        SYNTAX INTEGER { io1(5), io2(6), io3(7), io4(8), io5(9),
                        io6(10), io7(11), io8(12), io9(13), io10(14),
                        io11(15), io12(16) }
        ACCESS read-write
        STATUS mandatory
        DESCRIPTION
        "Slot where is sitting the Framer."
     ::= { mdlPbxFramerCnfgEntry 8}

mdlPbxFraSignaling OBJECT-TYPE
        SYNTAX INTEGER {
            notApplicable   (1),
			endToEnd        (2),
			localTermination(3)
			}
        ACCESS read-write
        STATUS mandatory
        DESCRIPTION
        "Signaling - describes the way the signaling ABCD bits pass from the
		             local extension to the remote extension and vice-versa.

         endToEnd = the signaling ABCD bits pass without change from local to
                    remote extension.
         localTermination = the signaling ABCD bits received from the local extension
                    are translated to different ON Hook/OFF Hook bit values and then
                    passed to remote extension. This is relevant when the Local
                    and Remote ON Hook/OFF Hook values are different."
        DEFVAL { endToEnd }
        ::= { mdlPbxFramerCnfgEntry 9}


--
-- Specific port config for each module Type
-- *****************************************

--
-- MPCL.1 configuration parameters
--
--prtExClCnfgTable   OBJECT IDENTIFIER ::= {prtClCnfg 1}
-- prtInClInbandTable OBJECT IDENTIFIER ::= {prtClCnfg 2}

prtExClCnfgTable OBJECT-TYPE
      SYNTAX SEQUENCE OF PrtExClCnfgEntry
      ACCESS not-accessible
      STATUS  mandatory
      DESCRIPTION "" ::= {prtClCnfg 1}

prtExClCnfgEntry OBJECT-TYPE
      SYNTAX PrtExClCnfgEntry
      ACCESS not-accessible
      STATUS mandatory
      DESCRIPTION
      "All the entries at this table are identical (have the same
       value) for all the configurations (1..100) except the
       TmpCnfg.
       The write operation into the Table Objects is valid only
       to the TmpCnfg entry."
      INDEX {prtExClCnfgIdx, prtExClSltIdx, prtExClPrtIdx }
      ::= { prtExClCnfgTable 1}

PrtExClCnfgEntry ::=
      SEQUENCE {
      prtExClCnfgIdx         INTEGER,
      prtExClSltIdx          INTEGER,
      prtExClPrtIdx          INTEGER,
   prtExClUsage           INTEGER,
   prtExClRate            INTEGER,
   prtExClDataBits        INTEGER,
   prtExClParity          INTEGER,
   prtExClStopBits        INTEGER,
   prtExClRoutingProtocol INTEGER
      }


prtExClCnfgIdx OBJECT-TYPE
      SYNTAX  INTEGER (1..255)
      ACCESS  read-only
      STATUS  mandatory
      DESCRIPTION
      "This attribute indicates the Idx of the Cnfg (1..100) being
       accessed.
       Idx 255 relates to the TmpCnfg."
      ::= { prtExClCnfgEntry 1}
-- In phase I only the values 1 (Cnfg1) and 255 (temp) are valid.

prtExClSltIdx OBJECT-TYPE
      SYNTAX  INTEGER
        {
       clA   (3),
          clB   (4),
    notApplicable (255)
        }
      ACCESS  read-only
      STATUS  mandatory
      DESCRIPTION
      "This attribute indicates a unique  slot  position where
       the card is inserted. Because the second Cl is only for
       redundancy, all the parameters are identical in the two
       modules, i.e. change of any parameter in one module will
       change automatically the value of the other module..
       In the ?004 Unit the entry clB(4) is not valid."
      ::= { prtExClCnfgEntry 2}

prtExClPrtIdx OBJECT-TYPE
      SYNTAX  INTEGER
      {
  exPrt1    (1) ,
  exPrt2    (2)
      }
      ACCESS  read-only
      STATUS  mandatory
      DESCRIPTION
      "This attribute indicates a unique  port number. "
      ::= { prtExClCnfgEntry 3}

prtExClUsage OBJECT-TYPE
      SYNTAX  INTEGER
       {
  unknown (1),
  noUse   (2),
  nmsSlip (3),
  nmsPpp  (4),
  muxSlip (5),
  muxPpp  (6),
  terminal(7)
       }
      ACCESS  read-only
      STATUS  mandatory
      DESCRIPTION
      "This attribute indicates what is the usage of the port."
      ::= { prtExClCnfgEntry 4}

prtExClRate OBJECT-TYPE
      SYNTAX  INTEGER
       {
        r300Bps (1),
        r1200Bps (2),
        r2400Bps (3),
        r4800Bps (4),
        r9600Bps (5),
        r19200Bps (6),
        r38400Bps (7),
        r57600Bps (8),
        r115200Bps (9)
       }
      ACCESS  read-only
      STATUS  mandatory
      DESCRIPTION
      "This attribute indicates the operation rate of the port."
      ::= { prtExClCnfgEntry 5}

prtExClDataBits OBJECT-TYPE
      SYNTAX  INTEGER
       {
        dataBits7Bits (1),
        dataBits8Bits (2)
       }
      ACCESS  read-only
      STATUS  mandatory
      DESCRIPTION
      "This attribute indicates the number of data bits in async
       frame"
      ::= { prtExClCnfgEntry 6}

prtExClParity OBJECT-TYPE
      SYNTAX  INTEGER
       {
        odd   (1),
        even  (2),
        none  (3)
       }
      ACCESS  read-only
      STATUS  mandatory
      DESCRIPTION
      "This attribute indicates if the parity operation mode in
       async frame"
      ::= { prtExClCnfgEntry 7}

prtExClStopBits OBJECT-TYPE
      SYNTAX  INTEGER
       {
          stopBits1Bit      (1),
          stopBits1dot5Bits (2),
          stopBits2Bits     (3)
       }
      ACCESS  read-only
      STATUS  mandatory
      DESCRIPTION
      "This attribute indicates the minimum number of stop bits in
       the tx async frame"
      ::= { prtExClCnfgEntry 8}

prtExClRoutingProtocol OBJECT-TYPE
      SYNTAX  INTEGER
       {
  none    (1),
  rip2    (2)
       }
      ACCESS  read-only
      STATUS  mandatory
      DESCRIPTION
      "This attribute indicates the routing protocol of the port.
       When prtExClUsage is nmsSlip or nmsPpp - all values are
                                                applicable .
       Else - only 'none' is applicable."
      ::= { prtExClCnfgEntry 9}


--
-- MPH1.T1, MPH1.E1, MTML.1/T1 , MTML.1/E1, ML-20
-- TDM and Hybrid(TDM & Packet) Main Link Modules
--
--prtExPh1MlCnfgTable OBJECT IDENTIFIER ::= {prtPh1MlCnfg 1}
--prtExPh1MlTsTable   OBJECT IDENTIFIER ::= {prtPh1MlCnfg 2}
--prtInPh1MlCnfgTable OBJECT IDENTIFIER ::= {prtPh1MlCnfg 3}
--prtInPh1MlDlciTable OBJECT IDENTIFIER ::= {prtPh1MlCnfg 4}
--prtPhMlCnfgTable    OBJECT IDENTIFIER ::= {prtPh1MlCnfg 5}

--
-- MPH1.T1 & MPH1.E1
-- External Port Objects
--
prtExPh1MlCnfgTable  OBJECT-TYPE
     SYNTAX SEQUENCE OF PrtExPh1MlCnfgEntry
     ACCESS not-accessible
     STATUS  mandatory
     DESCRIPTION
      "The write operation into the Table Objects is valid only
       to the TmpCnfg entry."
     ::= {prtPh1MlCnfg 1}

prtExPh1MlCnfgEntry OBJECT-TYPE
      SYNTAX PrtExPh1MlCnfgEntry
      ACCESS not-accessible
      STATUS mandatory
      DESCRIPTION "" INDEX {prtExPh1MlCnfgIdx, prtExPh1MlSltIdx, prtExPh1MlPrtIdx }
      ::= { prtExPh1MlCnfgTable 1}

PrtExPh1MlCnfgEntry ::=
      SEQUENCE {
      prtExPh1MlCnfgIdx        INTEGER,
      prtExPh1MlSltIdx         INTEGER,
      prtExPh1MlPrtIdx         INTEGER,
      prtExPh1MlConnect        INTEGER,
      prtExPh1MlLineType       INTEGER,
      prtExPh1MlLineCode       INTEGER,
      prtExPh1MlLineLen        INTEGER,
      prtExPh1MlRestoreTime    INTEGER,
      prtExPh1MlTxGain         INTEGER,
      prtExPh1MlRxSensitivity  INTEGER,
      prtExPh1MlIdleCode       INTEGER,
      prtExPh1MlTdmTrunk       INTEGER,
      prtExPh1MlClkMode        INTEGER,
      prtExPh1MlMfClkSrcSlt    INTEGER,
      prtExPh1MlMfClkSrcPrt    INTEGER,
      prtExPh1MlFdlType        INTEGER,
      prtExPh1MlInbandMng      INTEGER,
      prtExPh1MlInbandMngRate  INTEGER,
      prtExPh1MlRedundType     INTEGER,
      prtExPh1MlRedundSlot     INTEGER,
      prtExPh1MlRedundPort     INTEGER,
      prtExPh1MlRedundRecTime  INTEGER,
   prtExPh1MlInbandMngRoutProt INTEGER,
      prtExPh1MlIfType         INTEGER
      }


prtExPh1MlCnfgIdx OBJECT-TYPE
      SYNTAX  INTEGER (1..255)
      ACCESS  read-only
      STATUS  mandatory
      DESCRIPTION
      "This attribute indicates the Idx of the Cnfg (1..100) being
       accessed.
       Idx 255 relates to the TmpCnfg. "
      ::= { prtExPh1MlCnfgEntry 1}
-- In phase I only the values 1 (Cnfg1) and 255 (temp) are valid.

prtExPh1MlSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      ACCESS  read-only
      STATUS  mandatory
      DESCRIPTION
      "This attribute indicates a unique  slot  position where
       the module is inserted.
       In the ?004 Unit the entries io6(10)..io16) are not valid."
      ::= { prtExPh1MlCnfgEntry 2}

prtExPh1MlPrtIdx OBJECT-TYPE
      SYNTAX  INTEGER
       {
       exPrt1    (1),
       exPrt2    (2),
       exPrt3    (3),
       exPrt4    (4),
       inPrt1  (101)
       }
      ACCESS  read-only
      STATUS  mandatory
      DESCRIPTION
      "This attribute indicates a unique  port number.
       MTML-1/E1 and MTML-1/T1 cards have only one external interface.
       inPrt1 - for MTML-H/E1 cards.
       exPrt2..exPrt4 - for MTML-4 cards and others."
      ::= { prtExPh1MlCnfgEntry 3}

prtExPh1MlConnect OBJECT-TYPE
      SYNTAX  INTEGER
       {
  no  (2),
  yes (3)
       }
      ACCESS  read-write
      STATUS  mandatory
      DESCRIPTION
      "This attribute indicates whether the port should be considered
       in any of the mux  algorithms. It also affects all the card
       considerations because it may indicate that the module has only
       one physical interface."
      ::= {prtExPh1MlCnfgEntry 4}

prtExPh1MlLineType OBJECT-TYPE
      SYNTAX  INTEGER
       {
  esfT1          (2), --> dsx1ESF
  sfT1           (3), --> dsx1D4
  g732nE1        (4), --> dsx1E1
  g732nE1CRC     (5), --> dsx1E1-CRC
  g732sE1        (6), --> dsx1E1-MF
  g732sE1CRC     (7)  --> dsx1E1-MF-CRC
       }
      ACCESS  read-write
      STATUS  mandatory
      DESCRIPTION
      "This attribute is the line type parameter for T1/E1 interface.
       The user should select only the parameters which are relevant
       to the specific card:
       T1 line code parameters for the MPH.1/T1
       E1 line code parameters for the MPH.1/E1.
       This parameter has the same values as dsx1LineType in T1/E1
       MIB (RFC-1406). The parameters in dsx1LineType are:
                     other          (1)
      esfT1          dsx1ESF        (2)
      sfT1           dsx1D4         (3)
      g732nE1        dsx1E1         (4)
      g732nE1CRC     dsx1E1-CRC     (5)
      g732sE1        dsx1E1-MF      (6)
      g732sE1CRC     dsx1E1-MF-CRC  (7)"
      ::= { prtExPh1MlCnfgEntry 5}


prtExPh1MlLineCode OBJECT-TYPE
      SYNTAX  INTEGER
       {
  b7T1   (1),  --> dsx1JBZS
  b8zsT1 (2),  --> dsx1B8ZS
        transT1(3),  --> dsx1AMI
        hdb3E1 (4),   --> dsx1HDB3
     notApplicable(255)
       }
      ACCESS  read-write
      STATUS  mandatory
      DESCRIPTION
      "This attribute is the line code parameter used for T1/E1
       interface.
       The user should select only the parameters which are relevant
       to the specific card:
       T1 line code parameters for MPH.1/T1
       E1 line code parameters for MPH.1/E1.
       This parameter has the same values as dsx1LineCoding in T1/E1
       MIB (RFC-1406).  The parameters in dsx1LineCoding are:
     dsx1JBZS  (1)
     dsx1B8ZS  (2)
     dsx1HDB3  (3)
     dsx1ZBTSI (4)
     dsx1AMI   (5)
     other     (6)"
      ::= { prtExPh1MlCnfgEntry 6}

prtExPh1MlLineLen OBJECT-TYPE
      SYNTAX  INTEGER
       {
        unknown      (1),
        len0p133ft   (2),
        len134p266ft (3),
        len267p399ft (4),
        len400p533ft (5),
        len534p655ft (6),
        lenFcc68     (7),
  notApplicable(255)
       }
      ACCESS  read-write
      STATUS  mandatory
      DESCRIPTION
      "This attribute is the line length parameter used only for T1/DSU
       interfaces.
       lenXXXpXXXft = len-XXX-XXXft."
      ::= { prtExPh1MlCnfgEntry 7}

prtExPh1MlRestoreTime OBJECT-TYPE
      SYNTAX  INTEGER
       {
        restoreT1secFast      (2),
        restoreT10sec62411    (3),
        ccittE1                (4)
       }
      ACCESS  read-write
      STATUS  mandatory
      DESCRIPTION
      "The time passing from the disappearance of the loss of
       synchronization condition (red alarm) to the restoration of
       normal service. The options 1secFast(2) and 10sec62411(3)
       for E1 interfaces are proprietary implementation of the T1
       standard to the E1 interface."
      ::= { prtExPh1MlCnfgEntry 8}

prtExPh1MlTxGain OBJECT-TYPE
      SYNTAX  INTEGER
       {
          notApplicable(1),
          txGain0db         (2),
          txGain7dot5db     (3),
          txGain15db        (4),
          txGain22dot5db    (5)
       }
      ACCESS  read-write
      STATUS  mandatory
      DESCRIPTION
      "This attribute is the tx gain parameter used only for
       T1/CSU interfaces."
      ::= { prtExPh1MlCnfgEntry 9}

prtExPh1MlRxSensitivity OBJECT-TYPE
      SYNTAX  INTEGER
       {
        notApplicable(1),
        low26dBm  (2),
        high36dBm (3),
		shortHaul (4),
		longHaul  (5)
       }
      ACCESS  read-write
      STATUS  mandatory
      DESCRIPTION
      "This attribute is the rx line sensitivity parameter.
       low26dBm, high36dBm - applicable for T1-CSU
       shortHaul, longHaul - applicable for MTML-4 cards."
      ::= { prtExPh1MlCnfgEntry 10}

prtExPh1MlIdleCode OBJECT-TYPE
      SYNTAX  INTEGER
      ACCESS  read-write
      STATUS  mandatory
      DESCRIPTION
     "Determines the code for transmission in empty time slots.
      Type value(00-FFH), Excluding 0H,8H,10H,12H,21H,24H,42H,49H,
      84H,92H"
      ::= { prtExPh1MlCnfgEntry 11}

prtExPh1MlTdmTrunk  OBJECT-TYPE
      SYNTAX  INTEGER
       {
        linkA   (1),
        linkB   (2),
        none    (3),
  notApplicable (255)
       }
      ACCESS  read-write
      STATUS  mandatory
      DESCRIPTION
      "This attribute indicates whether the port is used to transfer
       TDM cards data and through which Bus."
      ::= {prtExPh1MlCnfgEntry 12}

prtExPh1MlClkMode OBJECT-TYPE
      SYNTAX  INTEGER
       {
    internalLocal (1),
    loopBackLocal (2),
    nodalTiming   (3)
       }
      ACCESS  read-write
      STATUS  mandatory
      DESCRIPTION
      "Defines the clock operation mode of the T1/E1 interface.
       Ports that are connected to the TDM Buses must be in
       nodalTiming(3) clock mode. "
      ::= {prtExPh1MlCnfgEntry 13}

prtExPh1MlMfClkSrcSlt  OBJECT-TYPE
      SYNTAX  INTEGER
       {
          notApplicable(1),
          local (2),
          io1   (5),
          io2   (6),
          io3   (7),
          io4   (8),
          io5   (9),
          io6  (10),
          io7  (11),
          io8  (12),
          io9  (13),
          io10 (14),
          io11 (15),
          io12 (16)
       }
      ACCESS  read-write
      STATUS  mandatory
      DESCRIPTION
      "This attribute indicates whether the port Tx multiframe is
       synchronized with Rx multiframe of another port and the slot
       position of that port.
       This operation is required in order to bypass signaling of
       PCM voice channels. Its value is always local(2) when the port
       isn't connected to any TDM bus. When it's value is local(2)
       there is no meaning to 'prtExPh1MlMfClkSrcPrt' parameter.
       In the ?004 Unit the entries io6(10)..io16) are not valid"
      ::= {prtExPh1MlCnfgEntry 14}

prtExPh1MlMfClkSrcPrt  OBJECT-TYPE
      SYNTAX  INTEGER
       {
          exPrt1         (1),
		  exPrt2         (2),
          inPrt1       (101),
          notApplicable(255)
       }
      ACCESS  read-write
      STATUS  mandatory
      DESCRIPTION
      "A unique number to identify a port position in the mux. It
       has no effect when the prtExPh1MlMfClkSrcSlt selected is Local.
       inPrt1 - for MTML-H/E1 cards."
    ::= {prtExPh1MlCnfgEntry 15}

prtExPh1MlFdlType  OBJECT-TYPE
      SYNTAX  INTEGER
       {
          notApplicable(1),
          response   (2),
          command    (3)
       }
      ACCESS  read-write
      STATUS  mandatory
      DESCRIPTION
      "A unique number to identify  the side of the FDL operation.
      Normal: 'response' for the user side and 'command' for the PTT
      side.
      Applicable only when working with ESF-T1 link"
      ::= {prtExPh1MlCnfgEntry 16}

prtExPh1MlInbandMng  OBJECT-TYPE
      SYNTAX  INTEGER
       {
          off                 (2),
          fdlOrTs0            (3),
    dedicatedTs         (4),
    dedicatedPpp        (5),
    dedicatedFr         (6),
       notApplicable     (255)
       }
      ACCESS  read-write
      STATUS  mandatory
      DESCRIPTION
      "A unique number to identify an Inband management over the
       link."
      ::= {prtExPh1MlCnfgEntry 17}

prtExPh1MlInbandMngRate  OBJECT-TYPE
      SYNTAX  INTEGER
       {
          notApplicable(1),
          r4k   (2),
          r8k   (3),
          r12k  (4),
          r16k  (5),
    r32k  (6),
    r64k  (7),
    r20k  (8)
       }
      ACCESS  read-write
      STATUS  mandatory
      DESCRIPTION
      "A unique number to identify the rate of the Inband
       management.
       E1 port - it is not applicable when prtExPh1MlInbandMng
                 selected is off.
       T1 port - it is not applicable when prtExPh1MlInbandMng
                 selected is off OR fdlOrTs0."
      ::= {prtExPh1MlCnfgEntry 18}

prtExPh1MlRedundType  OBJECT-TYPE
      SYNTAX  INTEGER
       {
          none                (1),
          dualCableAIS        (2),
          yCable              (3),
    dualCableParallelTx (4)
       }
      ACCESS  read-write
      STATUS  mandatory
      DESCRIPTION
      "This object determines the ML redundancy type:
       none - no ML redundacy
       dualCableAIS -        each ML card is connected by a separate
       dualCableParallelTx   cable to the other MUX (two cables
                             connect two MUXes).  There are two
                             types of dual redundancy.
       yCable - Y cable is connected to both ML cards (one cable
                connects two MUXes).
       Default=none
       When only one ML card exists, the type can be only 'none'.
       The value should be the same for both ML slots."
      ::= {prtExPh1MlCnfgEntry 19}

prtExPh1MlRedundSlot  OBJECT-TYPE
      SYNTAX  INTEGER
       {
          notApplicable (1),
          io1   (5),
          io2   (6),
          io3   (7),
          io4   (8),
          io5   (9),
          io6  (10),
          io7  (11),
          io8  (12),
          io9  (13),
          io10 (14),
          io11 (15),
          io12 (16)
       }
      ACCESS  read-write
      STATUS  mandatory
      DESCRIPTION
      "This object indicates the slot containing the redundacy ML
    card, coupled with the current ML (prtExPh1MlSltIdx).
       When prtExPh1MlRedundType=none (no ML redundancy) this
       object will be 'notApplicable'.
       In the ?004 Unit the entries io6(10)..io12(16) are not valid
       When value is not 'none', it should be mutual to the
       redundant ML slot."
      ::= {prtExPh1MlCnfgEntry 20}

prtExPh1MlRedundPort  OBJECT-TYPE
      SYNTAX  INTEGER
       {
          exPrt1          (1),
       exPrt2          (2),
       exPrt3          (3),
       exPrt4          (4),
    inPrt1        (101),
    notApplicable (255)
       }
      ACCESS  read-write
      STATUS  mandatory
      DESCRIPTION
      "This object indicates the redundacy ML port, coupled with the
       current ML port (prtExPh1MlPrtIdx).
       When prtExPh1MlRedundType=none (no ML redundancy) this
       object will be 'notApplicable'.
       When value is not 'none', it should be mutual to the
       redundant ML port.
       inPrt1 - for MTML-H/E1 cards.
       exPrt2..exPrt4 - for MTML-4 cards."
      ::= {prtExPh1MlCnfgEntry 21}

prtExPh1MlRedundRecTime  OBJECT-TYPE
      SYNTAX  INTEGER  (1..99)
      ACCESS  read-write
      STATUS  mandatory
      DESCRIPTION
      "Redundancy Recovery Time (sec). After switching the ML card
       to the current (prtExPh1MlSltIdx), the next ML switch can
       be performed only after a minimum time, indicated by
       this object."
      ::= {prtExPh1MlCnfgEntry 22}

prtExPh1MlInbandMngRoutProt  OBJECT-TYPE
      SYNTAX  INTEGER
       {
  none    (1),
  rip2    (2),
  proprietary (3)
       }
      ACCESS  read-write
      STATUS  mandatory
      DESCRIPTION
      "This attribute indicates the Inband Mng routing protocol of
       the port."
      ::= {prtExPh1MlCnfgEntry 23}

prtExPh1MlIfType  OBJECT-TYPE
      SYNTAX  INTEGER
       {
       notApplicable (1),
       csu    (2),
       dsu    (3),
	   ltu    (4)
       }
      ACCESS  read-write
      STATUS  mandatory
      DESCRIPTION
      "Interface type of the port.
       For T1 - csu, dsu are the valid values
       For E1 - dsu, ltu are the valid values."
      ::= {prtExPh1MlCnfgEntry 24}


--
-- MPH1.T1 & MPH1.E1
-- Time Slot Assignment Table
--
prtExPh1MlTsTable  OBJECT-TYPE
     SYNTAX SEQUENCE OF PrtExPh1MlTsEntry
     ACCESS not-accessible
     STATUS  mandatory
     DESCRIPTION
      "The write operation into the Table Objects is valid only
       to the TmpCnfg entry."
     ::= {prtPh1MlCnfg 2}

prtExPh1MlTsEntry OBJECT-TYPE
      SYNTAX PrtExPh1MlTsEntry
      ACCESS not-accessible
      STATUS mandatory
      DESCRIPTION "" INDEX {prtExPh1MlTsCnfgIdx, prtExPh1MlTsSltIdx, prtExPh1MlTsPrtIdx, prtExPh1MlTsIdx }
      ::= { prtExPh1MlTsTable 1}

PrtExPh1MlTsEntry ::=
      SEQUENCE {
      prtExPh1MlTsCnfgIdx        INTEGER,
      prtExPh1MlTsSltIdx         INTEGER,
      prtExPh1MlTsPrtIdx         INTEGER,
      prtExPh1MlTsIdx            INTEGER,
      prtExPh1MlTsIConSlot       INTEGER,
      prtExPh1MlTsIConPrt        INTEGER,
      prtExPh1MlTsIConTs         INTEGER,
      prtExPh1MlTsExt    OBJECT IDENTIFIER
      }

prtExPh1MlTsCnfgIdx OBJECT-TYPE
      SYNTAX  INTEGER  (1..255)
      ACCESS  read-only
      STATUS  mandatory
      DESCRIPTION
      "This attribute indicates the Idx of the Cnfg (1..100) being
       accessed.
       Idx 255 relates to the TmpCnfg. "
      ::= { prtExPh1MlTsEntry 1}
-- In phase I only the values 1 (Cnfg1) and 255 (temp) are valid.

prtExPh1MlTsSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      ACCESS  read-only
      STATUS  mandatory
      DESCRIPTION
      "This attribute indicates a unique  slot  position where
       the card is inserted.
       In the ?004 Unit the entries io6(10)..io16) are not valid"
      ::= { prtExPh1MlTsEntry 2}

prtExPh1MlTsPrtIdx OBJECT-TYPE
      SYNTAX  INTEGER
	{
          exPrt1    (1),
		  exPrt2    (2),
		  exPrt3    (3),
		  exPrt4    (4),
		  inPrt1  (101)
	      }
      ACCESS  read-only
      STATUS  mandatory
      DESCRIPTION
      "This attribute indicates a unique  port number.
       MPH.1/E1 and MPH.1/T1 cards have only one external interface.
	   exPrt2 - for ME1-2, MT1-2 and mhsPri cards.
	   exPrt3, exPrt4 - for mhsPri cards.
       inPrt1 - for MTML-H/E1 cards."
      ::= { prtExPh1MlTsEntry 3}

prtExPh1MlTsIdx OBJECT-TYPE
      SYNTAX  INTEGER
      ACCESS  read-only
      STATUS  mandatory
      DESCRIPTION
      "This attribute indicates a unique time slot  position.
       The valid time slots are 1..24 for T1 Card and
       1..31 for E1 interface. In G732S-E1 lines time slot 16 is not
       valid for data, it is dedicated for multiframe synchronization bits
       and voice signaling."
      ::= { prtExPh1MlTsEntry 4}

prtExPh1MlTsIConSlot OBJECT-TYPE
      SYNTAX  INTEGER
       {
          noConnect (2),
          split     (4),
          io1       (5),
          io2       (6),
          io3       (7),
          io4       (8),
          io5       (9),
          io6      (10),
          io7      (11),
          io8      (12),
          io9      (13),
          io10     (14),
          io11     (15),
          io12     (16)
       }
      ACCESS  read-write
      STATUS  mandatory
      DESCRIPTION
      "This attribute indicates whether the specified time slot is
       connected/routed internally in the Agent and to which card
       it is connected.
       In the ?004 Unit the entries io6(10)..io16) are not valid.
       split - will be used when the Src TS is connected to more
               than one slot OR more than one port (each needing
               less than a whole TS)."
      ::= {prtExPh1MlTsEntry 5}

prtExPh1MlTsIConPrt OBJECT-TYPE
      SYNTAX  INTEGER
      ACCESS  read-write
      STATUS  mandatory
      DESCRIPTION
      "This attribute indicates the internally (In Mux)
       connected/routed port.
       For MP, the values will be:
       	      {
	      exPrt1    (1) ,
	      exPrt2    (2) ,
	      exPrt3    (3) ,
	      exPrt4    (4) ,
	      exPrt5    (5) ,
	      exPrt6    (6) ,
	      exPrt7    (7) ,
	      exPrt8    (8) ,
	      exPrt9    (9) ,
	      exPrt10  (10) ,
          exPrt11  (11) ,
          exPrt12  (12) ,

          noConnect (100),

	      inPrt1  (101) ,
	      inPrt2  (102) ,
	      inPrt3  (103) ,
	      inPrt4  (104) ,
	      inPrt5  (105) ,
	      inPrt6  (106) ,
	      inPrt7  (107) ,
	      inPrt8  (108) ,
	      inPrt9  (109) ,
	      inPrt10 (110)	,
		  inPrt11 (111) ,
		  inPrt12 (112)
	      }		   "
      ::= {prtExPh1MlTsEntry 6}

prtExPh1MlTsIConTs OBJECT-TYPE
      SYNTAX  INTEGER
      ACCESS  read-write
      STATUS  mandatory
      DESCRIPTION
      "This attribute indicates a unique time slot  position.
       The valid time slots are 1..24 for T1 Card and
       1..31 for E1 interface. In G732S-E1 lines time slot 16 is not
       valid for data, it is dedicated to multiframe synchronization
       and voice signaling."
      ::= {prtExPh1MlTsEntry 7}

prtExPh1MlTsExt OBJECT-TYPE
        SYNTAX  OBJECT IDENTIFIER
        ACCESS  read-only
        STATUS  mandatory
        DESCRIPTION
             "A pointer to an extension of this table:
              prtExTsSplitTable.
              - If prtExPh1MlTsIConSlot='split', its value
                should be set to the OBJECT IDENTIFIER of the
                prtExTsSplitTable, with its relevant CnfgIdx,
                SltIdx, PrtIdx, TsIdx and 1st TsBit.
              - If prtExPh1MlTsIConSlot is not 'split', its value
                should be set to the OBJECT IDENTIFIER { 0 0 }. "
     ::= { prtExPh1MlTsEntry 8 }


--
-- MPH.1/T1 & MPH.1/E1
-- Internal port objects table
-- (only for the Hybrid modules)
--
prtInPh1MlCnfgTable  OBJECT-TYPE
     SYNTAX SEQUENCE OF PrtInPh1MlCnfgEntry
     ACCESS not-accessible
     STATUS  mandatory
     DESCRIPTION
      "The write operation into the Table Objects is valid only
       to the TmpCnfg entry."
     ::= {prtPh1MlCnfg 3}

prtInPh1MlCnfgEntry OBJECT-TYPE
      SYNTAX PrtInPh1MlCnfgEntry
      ACCESS not-accessible
      STATUS mandatory
      DESCRIPTION "" INDEX {prtInPh1MlCnfgIdx, prtInPh1MlSltType, prtInPh1MlPrtIdx }
      ::= { prtInPh1MlCnfgTable 1}

PrtInPh1MlCnfgEntry ::=
      SEQUENCE {
      prtInPh1MlCnfgIdx            INTEGER,
      prtInPh1MlSltType            INTEGER,
      prtInPh1MlPrtIdx             INTEGER,
      prtInPh1MlConnect            INTEGER,
      prtInPh1MlRate               INTEGER,
      prtInPh1MlProtocol           INTEGER,
      prtInPh1MlConnectionTyp      INTEGER,
      prtInPh1MlCongResponse       INTEGER,
      prtInPh1MlCongLevel          INTEGER,
      prtInPh1MlTc                 INTEGER,
      prtInPh1MlFlowControl        INTEGER,
      prtInPh1MlSegment            INTEGER,
      prtInPh1MlFrMngProt          INTEGER,
      prtInPh1MlEnqPeriod          INTEGER,
      prtInPh1MlFullRptPeriod      INTEGER,
      prtInPh1MlFrWindowSize       INTEGER,
      prtInPh1MlErrorsThreshold    INTEGER,
      prtInPh1MlMaxIdleTime        INTEGER,
	  prtInPh1MlBearerCh           INTEGER,
	  prtInPh1MlAssociatedExCh     INTEGER,
	  prtInPh1MlAssociatedExCh     INTEGER,
	  prtInPh1MlClockEncoding      INTEGER,
	  prtInPh1MlMinSeparators      INTEGER,
	  prtInPh1MlCcittCrc           INTEGER,
	  prtInPh1MlFrameSeparator     INTEGER
      }


prtInPh1MlCnfgIdx OBJECT-TYPE
      SYNTAX  INTEGER (1..255)
      ACCESS  read-only
      STATUS  mandatory
      DESCRIPTION
      "This attribute indicates the Idx of the Cnfg (1..100) being
       accessed.
       Idx 255 relates to the TmpCnfg. "
      ::= { prtInPh1MlCnfgEntry 1}
-- In phase I only the values 1 (Cnfg1) and 255 (temp) are valid.

prtInPh1MlSltType OBJECT-TYPE
      SYNTAX  INTEGER
     {
       io1   (5),
       io2   (6),
       io3   (7),
       io4   (8),
       io5   (9),
       io6  (10),
       io7  (11),
       io8  (12),
       io9  (13),
       io10 (14),
       io11 (15),
       io12 (16),
       notApplicable(255)
     }
      ACCESS  read-only
      STATUS  mandatory
      DESCRIPTION
      "This attribute indicates a unique  slot  position where
       the card is inserted.
       For ISDN BRI port of MX300/30:
       io1(5) = isdn1(5) and io2(6) = isdn2(6)
       In the ?004 Unit the entries io6(10)..io12(16) are not valid"
      ::= { prtInPh1MlCnfgEntry 2}

prtInPh1MlPrtIdx OBJECT-TYPE
      SYNTAX  INTEGER
      ACCESS read-only
      STATUS  mandatory
      DESCRIPTION
      "This attribute indicates a unique port number.
       MPH.1/E1 and MPH.1/T1 cards have three internal interfaces.
       MX3000 modules may have up to 50 internal ports."
      ::= { prtInPh1MlCnfgEntry 3}

prtInPh1MlConnect OBJECT-TYPE
      SYNTAX  INTEGER
       {
  no  (2),
  yes (3)
       }
      ACCESS  read-write
      STATUS  mandatory
      DESCRIPTION
      "This attribute indicates whether the port should be
       considered in any of the mux  algorithms."
      ::= { prtInPh1MlCnfgEntry 4}

prtInPh1MlRate OBJECT-TYPE
      SYNTAX  INTEGER
       {
        r1x56eq56Kbps    (1),
        r1x64eq64Kbps    (2),
        r2x56eq112Kbps   (3),
        r2x64eq128Kbps   (4),
        r3x56eq168Kbps   (5),
        r3x64eq192Kbps   (6),
        r4x56eq224Kbps   (7),
        r4x64eq256Kbps   (8),
        r5x56eq280Kbps   (9),
        r5x64eq320Kbps  (10),
        r6x56eq336Kbps  (11),
        r6x64eq384Kbps  (12),
        r7x56eq392Kbps  (13),
        r7x64eq448Kbps  (14),
        r8x56eq448Kbps  (15),
        r8x64eq512Kbps  (16),
        r9x56eq504Kbps  (17),
        r9x64eq576Kbps  (18),
        r10x56eq560Kbps (19),
        r10x64eq640Kbps (20),
        r11x56eq616Kbps (21),
        r11x64eq704Kbps (22),
        r12x56eq672Kbps (23),
        r12x64eq768Kbps (24),
        r13x56eq728Kbps (25),
        r13x64eq832Kbps (26),
        r14x56eq784Kbps (27),
        r14x64eq896Kbps (28),
        r15x56eq840Kbps (29),
        r15x64eq960Kbps (30),
        r16x56eq896Kbps (31),
        r16x64eq1024Kbps(32),
        r17x56eq952Kbps (33),
        r17x64eq1088Kbps(34),
        r18x56eq1008Kbps(35),
        r18x64eq1152Kbps(36),
        r19x56eq1064Kbps(37),
        r19x64eq1216Kbps(38),
        r20x56eq1120Kbps(39),
        r20x64eq1280Kbps(40),
        r21x56eq1176Kbps(41),
        r21x64eq1344Kbps(42),
        r22x56eq1232Kbps(43),
        r22x64eq1408Kbps(44),
        r23x56eq1288Kbps(45),
        r23x64eq1472Kbps(46),
        r24x56eq1344Kbps(47),
        r24x64eq1536Kbps(48),

        -- the next values are only for MPH.1/E1 modules

        r25x56eq1400Kbps(49),
        r25x64eq1600Kbps(50),
        r26x56eq1456Kbps(51),
        r26x64eq1664Kbps(52),
        r27x56eq1512Kbps(53),
        r27x64eq1728Kbps(54),
        r28x56eq1568Kbps(55),
        r28x64eq1792Kbps(56),
        r29x56eq1624Kbps(57),
        r29x64eq1856Kbps(58),
        r30x56eq1680Kbps(59),
        r30x64eq1920Kbps(60),
        r31x56eq1736Kbps(61),
        r31x64eq1984Kbps(62),
		noRate         (100)
     }
      ACCESS  read-write
      STATUS  mandatory
      DESCRIPTION
      "This attribute indicates the port speed. "
      ::= { prtInPh1MlCnfgEntry 5}

prtInPh1MlProtocol OBJECT-TYPE
      SYNTAX  INTEGER
     {
        fr                 (1),
        frPlus             (2),
        pCellRelay         (3),
        hdlcSdlc           (4),
        transparentHdlc    (5)
     }
      ACCESS  read-write
      STATUS  mandatory
      DESCRIPTION
      "This attribute indicates the applied protocol."
      ::= { prtInPh1MlCnfgEntry 6}

prtInPh1MlConnectionTyp OBJECT-TYPE
      SYNTAX  INTEGER
     {
	    sameNetManaged  (1),
	    sameNetNotMana  (2),
	    user            (3),
	    otherNet        (4),
	    pubNet          (5),
		notApplicable (255)
     }
      ACCESS  read-write
      STATUS  mandatory
      DESCRIPTION
      "This attribute indicates the link connection type.
       It is required for three reasons:
     FR/CR Inband management operation (LMI,CLMM...).
     CIR check.
     NMS network management.

       SameNetManaged - indicates network internal line.
       SameNetNotMana - indicates network internal line, but the remote
               mux is not managed by the nms.

       User           - User to Network Interface.
       OtherNet       - Network To Network Interfce.
       PubNet         - Access Mux To PubNet Interface."
      ::= { prtInPh1MlCnfgEntry 7}

prtInPh1MlCongResponse OBJECT-TYPE
      SYNTAX  INTEGER
     {
     no              (2),
        flowControl     (3)
     }
      ACCESS  read-write
      STATUS  mandatory
      DESCRIPTION
"This attribute indicates how to handle the congestion indication
 to/from the mux internal connection side (for example
 transmit/receive becn to/from the network).
   no           - do nothing
   FlowControl  - translate the congestion indication between the
                  port and the internal connection port according to
                  the definition of the prtInPh1MlFlowControl
                  parameters. The operation is done in both directions."
      ::= { prtInPh1MlCnfgEntry 8}

prtInPh1MlCongLevel OBJECT-TYPE
      SYNTAX  INTEGER
      ACCESS  read-write
      STATUS  mandatory
      DESCRIPTION
      "This attribute indicates the level of delayed data in
       precents of the total available dynamic memory,
       for which the port will start to operate .
       The resolution of the parameter is 5 percent.
	   Valid values: 10..70, 255.
       255=notApplicable."
      ::= { prtInPh1MlCnfgEntry 9}

prtInPh1MlTc OBJECT-TYPE
      SYNTAX  INTEGER
          {
          tc1sec  (1),
          tc2sec  (2),
          tc3sec  (3),
          tc4sec  (4),
		  notApplicable (255)
          }
      ACCESS  read-write
      STATUS  mandatory
      DESCRIPTION
      "This attribute indicates the Tc parameter which is the time
       period of the sliding window in which the Bc/Be are tested.
       The value of this parameter is identical for all the ports in the
       specific card.
       255=notApplicable."
      ::= { prtInPh1MlCnfgEntry 10}

prtInPh1MlFlowControl OBJECT-TYPE
      SYNTAX  INTEGER
     {
        none                (2),
        fecnBecn            (3)
     }
      ACCESS  read-write
      STATUS  mandatory
      DESCRIPTION
      "This attribute indicates the required flow control betweeen
       the port and the remote equipment."
      ::= { prtInPh1MlCnfgEntry 11}

prtInPh1MlSegment OBJECT-TYPE
      SYNTAX  INTEGER
   {
   notApplicable (1),
   s36Byte       (2),
   s150Byte      (3),
   s264Byte      (4),
   s378Byte      (5),
   s492Byte      (6),
   s236Byte      (7),
   s472Byte      (8),
   s708Byte      (9),
   s944Byte     (10),
   s1180Byte    (11)
   }
      ACCESS  read-write
      STATUS  mandatory
      DESCRIPTION
      "This object is the Segmentation in Bytes.
	   In protocol FR+, ISDN internals, MX 30/300 the segmentation is:

       50 (2) ,158 (3) ,266 (4) ,376 (5), 484 (6)

       In  MX 3000/4:
       For protocol FR+ (internal ISDN ports of MHS.S, MHS.U, MHS.E1, MHS.T1
       cards) segmentation values are:

       236 (7),472 (8), 708 (9), 944 (10) ,1180 (11)"

      ::= { prtInPh1MlCnfgEntry 12}

prtInPh1MlFrMngProt OBJECT-TYPE
      SYNTAX  INTEGER
   {
   notApplicable (1),
   none          (2),
   lmi           (3),
   ansiT1        (4), --Annex D
   annexA        (5)
   }
      ACCESS  read-write
      STATUS  mandatory
      DESCRIPTION
      "This object indicates the Frame-Relay management protocol.
       ansiT1 = ANSI T1.617 Annex D (this is the default value).
       This parameter is applicable only for FR and FR+ protocols.
       When prtInPh1MlConnectionTyp = sameNetManaged, this object
       will be RO (internally determined). "
      ::= { prtInPh1MlCnfgEntry 13}

prtInPh1MlEnqPeriod OBJECT-TYPE
      SYNTAX  INTEGER (0..30)
      ACCESS  read-write
      STATUS  mandatory
      DESCRIPTION
      "This object is the Status Enquiry Period, in seconds.
       It determines the frequency of the Status Enquiry message
       as sent by the FR user side.
       At the FR network side, it determines the timeout for this
       message reception.
    Default = 4 seconds.
       This parameter is applicable only for FR and FR+ protocols
    AND
       only when prtInPh1MlFrMngProt is NOT (notApplicable or none).
       0=notApplicable."
    ::= { prtInPh1MlCnfgEntry 14}

prtInPh1MlFullRptPeriod OBJECT-TYPE
      SYNTAX  INTEGER (0..255)
      ACCESS  read-write
      STATUS  mandatory
      DESCRIPTION
      "This object is the Full Report Frequency.
       It determines the number of the Status Enquiry messages
       sent by the FR user side, before a Full Report Request is
       sent.
       The units are : Status Enquiry messages (periods).
    Valid values: 1 .. 255.
       255 = infinite (never sent).
       This parameter is applicable only for FR and FR+ protocols
    AND
       only when prtInPh1MlFrMngProt is NOT (notApplicable or none).
       0=notApplicable."
    ::= { prtInPh1MlCnfgEntry 15}

prtInPh1MlFrWindowSize OBJECT-TYPE
      SYNTAX  INTEGER (0..10)
      ACCESS  read-write
      STATUS  mandatory
      DESCRIPTION
      "This object is the FR Window Size.
       It determines the number of samplings in the sliding window
       that counts the errors.
       This parameter is applicable only for FR and FR+ protocols
    AND
       only when prtInPh1MlFrMngProt is NOT (notApplicable or none).
       0=notApplicable."
    ::= { prtInPh1MlCnfgEntry 16}

prtInPh1MlErrorsThreshold OBJECT-TYPE
      SYNTAX  INTEGER (0..10)
      ACCESS  read-write
      STATUS  mandatory
      DESCRIPTION
      "This object is the Max Errors.
       It determines the number of Status Enquiry Errors that
       occured within the FR sliding window, before this port is
       considered DOWN (threshold).
       This parameter is applicable only for FR and FR+ protocols
    AND
       only when prtInPh1MlFrMngProt is NOT (notApplicable or none).
       0=notApplicable. "
    ::= { prtInPh1MlCnfgEntry 17}

prtInPh1MlMaxIdleTime OBJECT-TYPE
     SYNTAX  INTEGER (0..1800)
     ACCESS   read-write
     STATUS   mandatory
     DESCRIPTION
     "Move to higher prioritized connected link	after this period of
      seconds of silence on the current link.
	  0=Never. Never move to higher prioritized connected link.
      UNIT is seconds.
      Valid values are: 0, 1, 2, 3, 4, 5, 10, 20, 30, 40, 50, 60, 120, 180, 240, 300,
      360, 420, 480, 540, 600, 900, 1200, 1500, 1800.
      Attempt to Set an invalid value will result in getting the default value."
     DEFVAL { 10 }
     ::= {prtInPh1MlCnfgEntry 18}

prtInPh1MlBearerCh OBJECT-TYPE
     SYNTAX  INTEGER
	 {
      notApplicable (1),
      channelB1     (3),
      channelB2     (4),
	  chB1andchB2   (5),
	  none          (255)
	       }
	 ACCESS   read-write
     STATUS   mandatory
     DESCRIPTION
	 "Defines which B (bearer) channels are used for transferring ISDN data.
	  Default value is: none (255).
	  anyChannel (2) is skipped because it is not in use here."
	 ::= {prtInPh1MlCnfgEntry 19}

prtInPh1MlAssociatedExCh OBJECT-TYPE
      SYNTAX  INTEGER
     {
        exPrt1        (1),
        exPrt2        (2),
		exPrt3        (3),
		exPrt4        (4),
		notApplicable (255)
     }
      ACCESS  read-write
      STATUS  mandatory
      DESCRIPTION
      "This object indicates the external port associated to this internal
       port. At present, it is used by the Hybrid (mp2100h), MHS-4 cards which
       can have up to 64 dynamic internal ports associated with External ports.

       For ISDN cards, the value will be: notApplicable (255).
       The associated external of an ISDN internal port is represented
       by the MIB object: prtIsdnDirectoryPrtNu."
      ::= { prtInPh1MlCnfgEntry 20}

prtInPh1MlClockEncoding OBJECT-TYPE
      SYNTAX  INTEGER
	  {
	  notApplicable (1),
	  nrz           (2),
	  nrzI          (3),
	  fm0           (4),
	  manchester    (5),
	  diffManchester(6)
	  }
      ACCESS  read-write
      STATUS  mandatory
      DESCRIPTION
      "This object is the Encoding type of the Line.
       This parameter is applicable only for FR and FR+ protocols."
	   ::= { prtInPh1MlCnfgEntry 21}

prtInPh1MlMinSeparators OBJECT-TYPE
      SYNTAX  INTEGER (0..16)
      ACCESS  read-write
      STATUS  mandatory
      DESCRIPTION
      "Minimum number of bytes separating between two adjacent frames (HDLC item).
       0 = notApplicable"
	   ::= { prtInPh1MlCnfgEntry 22}

prtInPh1MlCcittCrc OBJECT-TYPE
      SYNTAX  INTEGER
	  {
	  notApplicable (1),
	  crc16         (2),
	  crc32         (3)
	  }
      ACCESS  read-write
      STATUS  mandatory
      DESCRIPTION
      "This object indicates how many Bits are used for CRC (HDLC item)."
	   ::= { prtInPh1MlCnfgEntry 23}

prtInPh1MlFrameSeparator OBJECT-TYPE
      SYNTAX  INTEGER
	  {
	  notApplicable (1),
	  idles         (2),
	  flags         (3)
	  }
      ACCESS  read-write
      STATUS  mandatory
      DESCRIPTION
      "This object indicates what should be transferred on the line when there
       are no frames to pass (HDLC item).
       idles: mean that FF will pass on the line
       flags: mean that 7E will pass on the line."
	   ::= { prtInPh1MlCnfgEntry 24}

--
-- MPH1.T1 & MPH1.E1
-- Internal port Dlci objects table
--

prtInPh1MlDlciTable  OBJECT-TYPE
     SYNTAX SEQUENCE OF PrtInPh1MlDlciEntry
     ACCESS not-accessible
     STATUS  mandatory
     DESCRIPTION
      "The write operation into the Table Objects is valid only
       to the TmpCnfg entry."
     ::= {prtPh1MlCnfg 4}

prtInPh1MlDlciEntry OBJECT-TYPE
      SYNTAX PrtInPh1MlDlciEntry
      ACCESS not-accessible
      STATUS mandatory
      DESCRIPTION "" INDEX {prtInPh1MlDlciCnfgIdx, prtInPh1MlDlciSltIdx, prtInPh1MlDlciPrtIdx, prtInPh1MlDlciIdx }
      ::= { prtInPh1MlDlciTable 1}

PrtInPh1MlDlciEntry ::=
      SEQUENCE {
      prtInPh1MlDlciCnfgIdx        INTEGER,
      prtInPh1MlDlciSltIdx         INTEGER,
      prtInPh1MlDlciPrtIdx         INTEGER,
      prtInPh1MlDlciIdx            INTEGER,

      prtInPh1MlDlciValid          INTEGER,
      prtInPh1MlDlciIConSlt        INTEGER,
      prtInPh1MlDlciIConPrt        INTEGER,
      prtInPh1MlDlciIConDlci       INTEGER,

      prtInPh1MlDlciTxBc           INTEGER,
      prtInPh1MlDlciTxBe           INTEGER,
      prtInPh1MlDlciRxBc           INTEGER,
      prtInPh1MlDlciRxBe           INTEGER,

      prtInPh1MlDlciPriority       INTEGER,

      prtInPh1MlDlciStatus         INTEGER
      }


prtInPh1MlDlciCnfgIdx OBJECT-TYPE
      SYNTAX  INTEGER (1..255)
      ACCESS  read-only
      STATUS  mandatory
      DESCRIPTION
      "This attribute indicates the Idx of the Cnfg (1..100) being
       accessed.
       Idx 255 relates to the TmpCnfg. "
      ::= { prtInPh1MlDlciEntry 1}
-- In phase I only the values 1 (Cnfg1) and 255 (temp) are valid.

prtInPh1MlDlciSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      ACCESS  read-only
      STATUS  mandatory
      DESCRIPTION
      "This attribute indicates a unique  slot  position where
       the card is inserted.
       In the ?004 Unit the entries io6(10)..io16) are not valid"
      ::= { prtInPh1MlDlciEntry 2}

prtInPh1MlDlciPrtIdx OBJECT-TYPE
      SYNTAX  INTEGER
 {
       inPrt1  (101) ,
       inPrt2  (102) ,
       inPrt3  (103)
       }
      ACCESS  read-only
      STATUS  mandatory
      DESCRIPTION
      "This attribute indicates a unique internal port number.
       MPH.1/E1 and MPH.1/T1 cards have three internal ports."
      ::= { prtInPh1MlDlciEntry 3}

prtInPh1MlDlciIdx OBJECT-TYPE
      SYNTAX  INTEGER (1..991)
      ACCESS  read-only
      STATUS  mandatory
      DESCRIPTION
      "This attribute indicates a unique index for each possible
       used dlci(16..991). When the protocol is not Multiplexing
       protocol, then its type is 'user' and the only valid index
       is 1."
      ::= { prtInPh1MlDlciEntry 4}

prtInPh1MlDlciValid OBJECT-TYPE
      SYNTAX  INTEGER
     {
     no  (2),
     yes (3)
     }
      ACCESS  read-write
      STATUS  mandatory
      DESCRIPTION
      "This attribute indicates whether the attributes in this entry
       are valid or not. The user can add/delete pvc (dlci to dlci
       connection) by modifing this object"
      ::= { prtInPh1MlDlciEntry 5}

prtInPh1MlDlciIConSlt OBJECT-TYPE
      SYNTAX  INTEGER
 {
          noConnect(2),
    cl    (3),
       io1   (5),
       io2   (6),
       io3   (7),
       io4   (8),
       io5   (9),
       io6  (10),
       io7  (11),
       io8  (12),
       io9  (13),
       io10 (14),
       io11 (15),
       io12 (16)
       }
      ACCESS  read-write
      STATUS  mandatory
      DESCRIPTION
      "This attribute indicates a unique slot position In the Mux
       (Agent) where the dlci is routed to.
       In the ?004 Unit the entries io6(10)..io16) are not valid"
      ::= { prtInPh1MlDlciEntry 6}

prtInPh1MlDlciIConPrt OBJECT-TYPE
      SYNTAX  INTEGER
      {
       exPrt1    (1) ,
       exPrt2    (2) ,
       exPrt3    (3) ,
       exPrt4    (4) ,
       exPrt5    (5) ,
       exPrt6    (6) ,
       exPrt7    (7) ,
       exPrt8    (8) ,
       exPrt9    (9) ,
       exPrt10  (10) ,
    clNMS    (99) ,
          noConnect (100),
       inPrt1  (101) ,
       inPrt2  (102) ,
       inPrt3  (103) ,
       inPrt4  (104) ,
       inPrt5  (105) ,
       inPrt6  (106) ,
       inPrt7  (107) ,
       inPrt8  (108) ,
       inPrt9  (109) ,
       inPrt10 (110) ,
    inPrt11 (111) ,
    inPrt12 (112)
       }
      ACCESS  read-write
      STATUS  mandatory
      DESCRIPTION
      "This attribute indicates a unique port id which the dlci is
       routed to."
      ::= { prtInPh1MlDlciEntry 7}


prtInPh1MlDlciIConDlci OBJECT-TYPE
      SYNTAX  INTEGER    (1..991)
      ACCESS  read-write
      STATUS  mandatory
      DESCRIPTION
      "This attribute indicates a unique internal connection dlci
       number which the src dlci is routed to."
      ::= { prtInPh1MlDlciEntry 8}

prtInPh1MlDlciTxBc OBJECT-TYPE
      SYNTAX  INTEGER
        {
         full       (1),
         zero       (2),
         txBc9600bps    (3),
        txBc14200bps    (4),
        txBc19200bps    (5),
        txBc28800bps    (6),
        txBc32000bps    (7),
        txBc38400bps    (8),
        txBc48000bps    (9),
        txBc56000bps   (10),
        txBc57600bps   (11),
          txBc64Kbps   (12),
         txBc128Kbps   (13),
         txBc192Kbps   (14),
         txBc256Kbps   (15),
         txBc320Kbps   (16),
         txBc384Kbps   (17),
         txBc448Kbps   (18),
         txBc512Kbps   (19),
         txBc768Kbps   (20),
        txBc1024Kbps   (21)
        }
      ACCESS  read-write
      STATUS  mandatory
      DESCRIPTION
      "This attribute indicates a unique Tx committed bandwidth on
       the user transmit line or at the port receive line."
      ::= { prtInPh1MlDlciEntry 9}


prtInPh1MlDlciTxBe OBJECT-TYPE
      SYNTAX  INTEGER
        {
         full       (1),
         zero       (2),
         txBe9600bps    (3),
        txBe14200bps    (4),
        txBe19200bps    (5),
        txBe28800bps    (6),
        txBe32000bps    (7),
        txBe38400bps    (8),
        txBe48000bps    (9),
        txBe56000bps   (10),
        txBe57600bps   (11),
          txBe64Kbps   (12),
         txBe128Kbps   (13),
         txBe192Kbps   (14),
         txBe256Kbps   (15),
         txBe320Kbps   (16),
         txBe384Kbps   (17),
         txBe448Kbps   (18),
         txBe512Kbps   (19),
         txBe768Kbps   (20),
        txBe1024Kbps   (21)
        }
      ACCESS  read-write
      STATUS  mandatory
      DESCRIPTION
      "This attribute indicates a unique Tx excess bandwidth on the
      user transmit line or at the port receive line."
      ::= { prtInPh1MlDlciEntry 10}


prtInPh1MlDlciRxBc OBJECT-TYPE
      SYNTAX  INTEGER
        {
         full       (1),
         zero       (2),
         rxBc9600bps    (3),
        rxBc14200bps    (4),
        rxBc19200bps    (5),
        rxBc28800bps    (6),
        rxBc32000bps    (7),
        rxBc38400bps    (8),
        rxBc48000bps    (9),
        rxBc56000bps   (10),
        rxBc57600bps   (11),
          rxBc64Kbps   (12),
         rxBc128Kbps   (13),
         rxBc192Kbps   (14),
         rxBc256Kbps   (15),
         rxBc320Kbps   (16),
         rxBc384Kbps   (17),
         rxBc448Kbps   (18),
         rxBc512Kbps   (19),
         rxBc768Kbps   (20),
        rxBc1024Kbps   (21)
        }
      ACCESS  read-write
      STATUS  mandatory
      DESCRIPTION
      "This attribute indicates a unique Rx committed bandwidth on
       the user receive line or at the port transmit line."
      ::= { prtInPh1MlDlciEntry 11}


prtInPh1MlDlciRxBe OBJECT-TYPE
      SYNTAX  INTEGER
        {
         full       (1),
         zero       (2),
         rxBe9600bps    (3),
        rxBe14200bps    (4),
        rxBe19200bps    (5),
        rxBe28800bps    (6),
        rxBe32000bps    (7),
        rxBe38400bps    (8),
        rxBe48000bps    (9),
        rxBe56000bps   (10),
        rxBe57600bps   (11),
          rxBe64Kbps   (12),
         rxBe128Kbps   (13),
         rxBe192Kbps   (14),
         rxBe256Kbps   (15),
         rxBe320Kbps   (16),
         rxBe384Kbps   (17),
         rxBe448Kbps   (18),
         rxBe512Kbps   (19),
         rxBe768Kbps   (20),
        rxBe1024Kbps   (21)
        }
      ACCESS  read-write
      STATUS  mandatory
      DESCRIPTION
      "This attribute indicates a unique Rx excess bandwidth on the
      user receive line or at the port transmit line."
      ::= { prtInPh1MlDlciEntry 12}


prtInPh1MlDlciPriority OBJECT-TYPE
      SYNTAX  INTEGER  (1..8)
      ACCESS  read-write
      STATUS  mandatory
      DESCRIPTION
      "This attribute indicates a unique priority of the pcv.
       1 is the lowest priority and 8 is the highest priority."
      ::= { prtInPh1MlDlciEntry 13}



prtInPh1MlDlciStatus OBJECT-TYPE
      SYNTAX  INTEGER
 {
          disconnected (1),
          connected    (2)
       }
      ACCESS  read-only
      STATUS  mandatory
      DESCRIPTION
      "This attribute indicates the status of the pvc. The status is
       disconnected(1) when one of the sides is programmed as
       not connected"
      ::= { prtInPh1MlDlciEntry 14}


--
-- ML-20 - High Speed Main Link card
-- External Port Objects
--
prtPhMlCnfgTable  OBJECT-TYPE
     SYNTAX SEQUENCE OF PrtPhMlCnfgEntry
     ACCESS not-accessible
     STATUS  mandatory
     DESCRIPTION
      "The write operation into the Table Objects is valid only
       to the TmpCnfg entry."
     ::= {prtPh1MlCnfg 5}

prtPhMlCnfgEntry OBJECT-TYPE
      SYNTAX PrtPhMlCnfgEntry
      ACCESS not-accessible
      STATUS mandatory
      DESCRIPTION "" INDEX {prtPhMlCnfgIdx, prtPhMlSltIdx, prtPhMlPrtIdx }
      ::= { prtPhMlCnfgTable 1}

PrtPhMlCnfgEntry ::=
      SEQUENCE {
      prtPhMlCnfgIdx        INTEGER,
      prtPhMlSltIdx         INTEGER,
      prtPhMlPrtIdx         INTEGER,
      prtPhMlConnect        INTEGER,
      prtPhMlRate           INTEGER,
      prtPhMlCAS            INTEGER,
      prtPhMlClockMode      INTEGER,
      prtPhMlSatBuffer      INTEGER,
      prtPhMlDialProcess    INTEGER,
      prtPhMlSyncRestore    INTEGER,
      prtPhMlBus            INTEGER,
      prtPhMlMfSyncSlot     INTEGER
      }


prtPhMlCnfgIdx OBJECT-TYPE
      SYNTAX  INTEGER (1..255)
      ACCESS  read-only
      STATUS  mandatory
      DESCRIPTION
      "This attribute indicates the Idx of the Cnfg (1..100) being
       accessed.
       Idx 255 relates to the TmpCnfg. "
      ::= { prtPhMlCnfgEntry 1}
-- In phase I only the values 1 (Cnfg1) and 255 (temp) are valid.

prtPhMlSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      ACCESS  read-only
      STATUS  mandatory
      DESCRIPTION
      "This attribute indicates a unique  slot  position where
       the module is inserted.
       In the ?004 Unit the entries io6(10)..io12(16) are not valid."
      ::= { prtPhMlCnfgEntry 2}

prtPhMlPrtIdx OBJECT-TYPE
      SYNTAX  INTEGER
       {
       exPrt1    (1)
       }
      ACCESS  read-only
      STATUS  mandatory
      DESCRIPTION
      "This attribute indicates a unique  port number.
       ML-20 cards have just one external interface."
      ::= { prtPhMlCnfgEntry 3}

prtPhMlConnect OBJECT-TYPE
      SYNTAX  INTEGER
       {
  no  (2),
  yes (3)
       }
      ACCESS  read-write
      STATUS  mandatory
      DESCRIPTION
      "This attribute indicates whether the port should be considered
       in any of the mux  algorithms."
      ::= {prtPhMlCnfgEntry 4}

prtPhMlRate     OBJECT-TYPE
      SYNTAX  INTEGER
       {
        r2x64eq128Kbps   (4),
        r3x64eq192Kbps   (6),
        r4x64eq256Kbps   (8),
        r5x64eq320Kbps  (10),
        r6x64eq384Kbps  (12),
        r7x64eq448Kbps  (14),
        r8x64eq512Kbps  (16),
        r9x64eq576Kbps  (18),
        r10x64eq640Kbps (20),
        r11x64eq704Kbps (22),
        r12x64eq768Kbps (24),
        r13x64eq832Kbps (26),
        r14x64eq896Kbps (28),
        r15x64eq960Kbps (30),
        r16x64eq1024Kbps(32),
        r17x64eq1088Kbps(34),
        r18x64eq1152Kbps(36),
        r19x64eq1216Kbps(38),
        r20x64eq1280Kbps(40),
        r21x64eq1344Kbps(42),
        r22x64eq1408Kbps(44),
        r23x64eq1472Kbps(46),
        r24x64eq1536Kbps(48),
        r25x64eq1600Kbps(50),
        r26x64eq1664Kbps(52),
        r27x64eq1728Kbps(54),
        r28x64eq1792Kbps(56),
        r29x64eq1856Kbps(58),
        r30x64eq1920Kbps(60),
        r31x64eq1984Kbps(62)
       }
      ACCESS  read-write
      STATUS  mandatory
      DESCRIPTION
      "This attribute indicates the port speed."
      ::= {prtPhMlCnfgEntry 5}

prtPhMlCAS OBJECT-TYPE
      SYNTAX  INTEGER
       {
  no  (2),
  yes (3)
       }
      ACCESS  read-write
      STATUS  mandatory
      DESCRIPTION
      "This attribute indicates whether Channel Associated
       Signaling (CAS) is used."
      ::= {prtPhMlCnfgEntry 6}

prtPhMlClockMode OBJECT-TYPE
      SYNTAX  INTEGER
       {
          dce     (2),
          ext-dce (3),
          dte     (4)
          }
      ACCESS  read-write
      STATUS  mandatory
      DESCRIPTION
      "Clock mode."
      ::= { prtPhMlCnfgEntry 7}

prtPhMlSatBuffer OBJECT-TYPE
      SYNTAX  INTEGER
       {
  notApplicable (1),
  no  (2),
  yes (3)
       }
      ACCESS  read-write
      STATUS  mandatory
      DESCRIPTION
      "Satellite Buffer (+/- 256)."
      ::= {prtPhMlCnfgEntry 8}

prtPhMlDialProcess OBJECT-TYPE
      SYNTAX  INTEGER
       {
  notApplicable (1),
  no            (2),
  callIn        (3),
  callOut       (4)
       }
      ACCESS  read-write
      STATUS  mandatory
      DESCRIPTION
      "Dial Process."
      ::= {prtPhMlCnfgEntry 9}

prtPhMlSyncRestore OBJECT-TYPE
      SYNTAX  INTEGER (0..10)
      ACCESS  read-write
      STATUS  mandatory
      DESCRIPTION
      "Sync Restoration time, in seconds.
       notApplicable=0. "
      ::= {prtPhMlCnfgEntry 10}

prtPhMlBus OBJECT-TYPE
      SYNTAX  INTEGER
       {
  none (1),
  busA (2),
  busB (3)
       }
      ACCESS  read-write
      STATUS  mandatory
      DESCRIPTION
      "The TDM BUS this port is linked to."
      ::= {prtPhMlCnfgEntry 11}

prtPhMlMfSyncSlot  OBJECT-TYPE
      SYNTAX  INTEGER
       {
          none  (2),
          io1   (5),
          io2   (6),
          io3   (7),
          io4   (8),
          io5   (9),
          io6  (10),
          io7  (11),
          io8  (12),
          io9  (13),
          io10 (14),
          io11 (15),
          io12 (16)
       }
      ACCESS  read-write
      STATUS  mandatory
      DESCRIPTION
      "This attribute indicates whether the sync is synchronized
       according to a certain card and the slot of this card.
       This operation is required in order to bypass signaling of
       PCM voice channels.
       In the ?004 Unit the entries io6(10)..io12(16) are not valid"
      ::= {prtPhMlCnfgEntry 12}

-- This table is an extension for new version of MAXcess
-- modules.
prtLogicalCnfgTable  OBJECT-TYPE
     SYNTAX SEQUENCE OF PrtLogicalCnfgEntry
     ACCESS not-accessible
     STATUS  mandatory
     DESCRIPTION
      "The write operation into the Table Objects is valid only
       to the TmpCnfg entry."
     ::= {prtLogicalCnfg 1}

prtLogicalCnfgEntry OBJECT-TYPE
      SYNTAX PrtLogicalCnfgEntry
      ACCESS not-accessible
      STATUS mandatory
      DESCRIPTION "" INDEX {prtLogicalCnfgIdx, prtLogicalSltIdx, prtLogicalPrtIdx }
      ::= { prtLogicalCnfgTable 1}

PrtLogicalCnfgEntry ::=
      SEQUENCE {
      prtLogicalCnfgIdx   INTEGER,
      prtLogicalSltIdx    INTEGER,
      prtLogicalPrtIdx   INTEGER,
      prtLogicalConnect    INTEGER,
      prtLogicalFunction        INTEGER,
      prtLogicalRowStatus      INTEGER
}

prtLogicalCnfgIdx OBJECT-TYPE
      SYNTAX  INTEGER (1..255)
      ACCESS  read-only
      STATUS  mandatory
      DESCRIPTION
      "This attribute indicates the Idx of the Cnfg (1..100) being
       accessed.
       Idx 255 relates to the TmpCnfg. "
      ::= { prtLogicalCnfgEntry 1}
-- In phase I only the values 1 (Cnfg1) and 255 (temp) are valid.

prtLogicalSltIdx OBJECT-TYPE
      SYNTAX  INTEGER
            {
              io1   (5),
              io2   (6),
              io3   (7),
              io4   (8),
              io5   (9),
              io6  (10),
              io7  (11),
              io8  (12),
              io9  (13),
              io10 (14),
              io11 (15),
              io12 (16),
       notApplicable(255)
            }
      ACCESS  read-only
      STATUS  mandatory
      DESCRIPTION
        "Slot Index.
         For ISDN BRI Ports of MX300/30,
    io1(5) = isdn1(5) and io2(6) = isdn2(6)."
      ::= { prtLogicalCnfgEntry 2}

prtLogicalPrtIdx OBJECT-TYPE
      SYNTAX  INTEGER
      ACCESS  read-only
      STATUS  mandatory
      DESCRIPTION
      "This attribute indicates a unique  port number.
       This port number should be an internal port number:
        inPrt1(101)->inPrt50(150), linkSel1(200)->linkSel50(250),
        encaps1(300)-> encaps50(350), huntGr1(101) -> huntGr10(110)."
      ::= { prtLogicalCnfgEntry 3}

prtLogicalConnect OBJECT-TYPE
      SYNTAX  INTEGER
              {
                no  (2),
             yes (3)
              }
      ACCESS  read-write
      STATUS  mandatory
      DESCRIPTION
      "This attribute indicates whether the port should be considered
       in any of the mux  algorithms."
      ::= { prtLogicalCnfgEntry 4}

prtLogicalFunction  OBJECT-TYPE
      SYNTAX  INTEGER
              {
                notApplicable(1),
                linkSelector(2),
         encapsulator(3),
   huntGroup(4)
              }
     ACCESS   read-write
     STATUS   mandatory
     DESCRIPTION
     "This parameter defines the function of the relevant channel."
     ::= { prtLogicalCnfgEntry 5 }

prtLogicalRowStatus  OBJECT-TYPE
      SYNTAX  INTEGER
              {
                active(1),
                destroy(6)
 }
     ACCESS   read-write
     STATUS   mandatory
     DESCRIPTION
     "This parameter allows the NMS to create/delete
       logical ports."
     ::= { prtLogicalCnfgEntry 6 }


-- This group contains management information for the
-- link selector function.

linkSelectorCnfgTable  OBJECT-TYPE
     SYNTAX SEQUENCE OF LinkSelectorCnfgEntry
     ACCESS not-accessible
     STATUS  mandatory
     DESCRIPTION
      "The write operation into the Table Objects is valid only
       to the TmpCnfg entry."
     ::= { prtLogicalCnfg 2}

linkSelectorCnfgEntry OBJECT-TYPE
      SYNTAX LinkSelectorCnfgEntry
      ACCESS not-accessible
      STATUS mandatory
      DESCRIPTION "" INDEX {linkSelectorCnfgIdx, linkSelectorSltIdx, linkSelectorPrtIdx }
      ::= { linkSelectorCnfgTable 1}

LinkSelectorCnfgEntry ::=
      SEQUENCE {
      linkSelectorCnfgIdx      INTEGER,
      linkSelectorSltIdx         INTEGER,
      linkSelectorPrtIdx         INTEGER,
      linkSelectorMaxIdleTime      INTEGER,
      linkSelectorMode INTEGER,
      linkSelectorRevert INTEGER,
      linkSelectorMinBUSession      INTEGER
}

linkSelectorCnfgIdx OBJECT-TYPE
      SYNTAX  INTEGER (1..255)
      ACCESS  read-only
      STATUS  mandatory
      DESCRIPTION
      "This attribute indicates the Idx of
      the Cnfg (1..100) being accessed.
       Idx 255 relates to the TmpCnfg. "
      ::= { linkSelectorCnfgEntry 1}
-- In phase I only the values 1 (Cnfg1) and 255 (temp) are valid.

linkSelectorSltIdx OBJECT-TYPE
      SYNTAX  INTEGER
            {
              io1   (5),
              io2   (6),
              io3   (7),
              io4   (8),
              io5   (9),
              io6  (10),
              io7  (11),
              io8  (12),
              io9  (13),
              io10 (14),
              io11 (15),
              io12 (16),
       notApplicable(255)
            }
      ACCESS  read-only
      STATUS  mandatory
      DESCRIPTION
        "Slot Index"
      ::= { linkSelectorCnfgEntry 2}

linkSelectorPrtIdx OBJECT-TYPE
      SYNTAX  INTEGER
      ACCESS  read-only
      STATUS  mandatory
      DESCRIPTION
      "This attribute indicates a unique  port number.
       This port number should be internal port number:
       higher or equal to linkSeL1(201)."
      ::= { linkSelectorCnfgEntry 3}

linkSelectorMaxIdleTime OBJECT-TYPE
     SYNTAX  INTEGER (0..255)
     ACCESS   read-write
     STATUS   mandatory
     DESCRIPTION
     "Move to higher prioritized connected link
     after this period of seconds of silence on the current link.
     0=move immediately to higher prioritized connected link.
     UNIT is seconds."
     DEFVAL { 0 }
::= {linkSelectorCnfgEntry 4}

linkSelectorMode OBJECT-TYPE
      SYNTAX  INTEGER { notApplicable(1),
    backup(2), bod(3)       }
      ACCESS   read-write
     STATUS   mandatory
     DESCRIPTION
     " If the link selector is in mode:
      backup(2)=then the link with the lower priority will be
                used in case of failure of the higher priority link,
      bod(3)=bandwidth on demand or dynamic bandwidth allocation
             means that links with lower priority will be used
             whenever additional bandwidth is required. "
     DEFVAL { backup }
::= {linkSelectorCnfgEntry 5}

linkSelectorRevert OBJECT-TYPE
      SYNTAX  INTEGER { notApplicable(1),
   auto(2), manual(3)       }
      ACCESS   read-write
     STATUS   mandatory
     DESCRIPTION
     " If the link selector is in mode backup:
      auto(2)=return automatically to Main link when it is OK.
      manual(3)=stays connected to backup link."
     DEFVAL { auto }
::= {linkSelectorCnfgEntry 6}

linkSelectorMinBUSession     OBJECT-TYPE
     SYNTAX  INTEGER (1..255)
     ACCESS   read-write
     STATUS   mandatory
     DESCRIPTION
     "Minimum duration of a backup session before
     returning to Main Link. Relevant in Backup Mode and
     when Revert is auto(2).  Value 255 is for NEVER which
     means never return to Main Link.
     UNIT is minutes."
     DEFVAL { 10 }
::= {linkSelectorCnfgEntry 7}

-- Prioritized Links
linkSelectorPLinkTable  OBJECT-TYPE
     SYNTAX SEQUENCE OF LinkSelectorPLinkEntry
     ACCESS not-accessible
     STATUS  mandatory
     DESCRIPTION
      "The write operation into the Table Objects is valid only
       to the TmpCnfg entry."
     ::= { prtLogicalCnfg 3}

linkSelectorPLinkEntry OBJECT-TYPE
      SYNTAX LinkSelectorPLinkEntry
      ACCESS not-accessible
      STATUS mandatory
      DESCRIPTION "" INDEX {pLinkCnfgIdx, pLinkSltIdx, pLinkPrtIdx, pLinkIdx }
      ::= { linkSelectorPLinkTable 1}

LinkSelectorPLinkEntry ::=
      SEQUENCE {
      pLinkCnfgIdx      INTEGER,
      pLinkSltIdx   INTEGER,
      pLinkPrtIdx       INTEGER,
      pLinkIdx         INTEGER,
      pLinkSlotNu       INTEGER,
      pLinkPortNu       INTEGER,
      pLinkPrioNu       INTEGER,
      pLinkVRate        INTEGER
}

pLinkCnfgIdx OBJECT-TYPE
      SYNTAX  INTEGER (1..255)
      ACCESS  read-only
      STATUS  mandatory
      DESCRIPTION
     "This attribute indicates the Idx of the Cnfg (1..100) being
       accessed.
       Idx 255 relates to the TmpCnfg. "
      ::= { linkSelectorPLinkEntry 1}
-- In phase I only the values 1 (Cnfg1) and 255 (temp) are valid.

pLinkSltIdx OBJECT-TYPE
      SYNTAX  INTEGER
            {
              io1   (5),
              io2   (6),
              io3   (7),
              io4   (8),
              io5   (9),
              io6  (10),
              io7  (11),
              io8  (12),
              io9  (13),
              io10 (14),
              io11 (15),
              io12 (16),
       notApplicable(255)
            }
      ACCESS  read-only
      STATUS  mandatory
      DESCRIPTION
        "Slot Index"
      ::= { linkSelectorPLinkEntry 2}

pLinkPrtIdx OBJECT-TYPE
      SYNTAX  INTEGER(200..250)
      ACCESS  read-only
      STATUS  mandatory
      DESCRIPTION
      "This attribute indicates a unique  port number.
       This port number should be the link selector number."
::= { linkSelectorPLinkEntry 3}


pLinkIdx OBJECT-TYPE
      SYNTAX  INTEGER (1..8)
      ACCESS   read-only
     STATUS   mandatory
     DESCRIPTION
     "This index is the row number."
::= { linkSelectorPLinkEntry 4}

pLinkSlotNu OBJECT-TYPE
      SYNTAX  INTEGER {
      noConnect (2), cl(3),
        io1(5),
        io2(6),
        io3(7),
        io4(8),
        io5(9),
        io6(10),
        io7(11),
        io8(12),
        io9(13),
        io10(14),
        io11(15),
        io12(16),
        notApplicable(255)
       }
     ACCESS   read-write
     STATUS   mandatory
     DESCRIPTION
     "The slot of the prioritized link.
     For ISDN BRI ports of MX300/30,
 io1(5) = isdn1(5) and io2(6) = isdn2(6)."
     DEFVAL { noConnect }
::= { linkSelectorPLinkEntry 5 }

pLinkPortNu OBJECT-TYPE
      SYNTAX  INTEGER
      ACCESS   read-write
      STATUS   mandatory
      DESCRIPTION
      "The port of the prioritized link.
      Value 100 is for noConnect."
      DEFVAL { 100 }
::= { linkSelectorPLinkEntry 6 }

pLinkPrioNu OBJECT-TYPE
      SYNTAX  INTEGER(1..8)
      ACCESS   read-write
      STATUS   mandatory
      DESCRIPTION
      "The priority of the prioritized link.
       MIN=1...., MAX=8."
::= { linkSelectorPLinkEntry 7 }

pLinkVRate OBJECT-TYPE
       SYNTAX INTEGER {
        r1x56eq56Kbps    (1),
        r1x64eq64Kbps    (2),
        r2x56eq112Kbps   (3),
        r2x64eq128Kbps   (4),
        r3x56eq168Kbps   (5),
        r3x64eq192Kbps   (6),
        r4x56eq224Kbps   (7),
        r4x64eq256Kbps   (8),
        r5x56eq280Kbps   (9),
        r5x64eq320Kbps  (10),
        r6x56eq336Kbps  (11),
        r6x64eq384Kbps  (12),
        r7x56eq392Kbps  (13),
        r7x64eq448Kbps  (14),
        r8x56eq448Kbps  (15),
        r8x64eq512Kbps  (16),
        r9x56eq504Kbps  (17),
        r9x64eq576Kbps  (18),
        r10x56eq560Kbps (19),
        r10x64eq640Kbps (20),
        r11x56eq616Kbps (21),
        r11x64eq704Kbps (22),
        r12x56eq672Kbps (23),
        r12x64eq768Kbps (24),
        r13x56eq728Kbps (25),
        r13x64eq832Kbps (26),
        r14x56eq784Kbps (27),
        r14x64eq896Kbps (28),
        r15x56eq840Kbps (29),
        r15x64eq960Kbps (30),
        r16x56eq896Kbps (31),
        r16x64eq1024Kbps(32),
        r17x56eq952Kbps (33),
        r17x64eq1088Kbps(34),
        r18x56eq1008Kbps(35),
        r18x64eq1152Kbps(36),
        r19x56eq1064Kbps(37),
        r19x64eq1216Kbps(38),
        r20x56eq1120Kbps(39),
        r20x64eq1280Kbps(40),
        r21x56eq1176Kbps(41),
        r21x64eq1344Kbps(42),
        r22x56eq1232Kbps(43),
        r22x64eq1408Kbps(44),
        r23x56eq1288Kbps(45),
        r23x64eq1472Kbps(46),
        r24x56eq1344Kbps(47),
        r24x64eq1536Kbps(48),
        r25x56eq1400Kbps(49),
        r25x64eq1600Kbps(50),
        r26x56eq1456Kbps(51),
        r26x64eq1664Kbps(52),
        r27x56eq1512Kbps(53),
        r27x64eq1728Kbps(54),
        r28x56eq1568Kbps(55),
        r28x64eq1792Kbps(56),
        r29x56eq1624Kbps(57),
        r29x64eq1856Kbps(58),
        r30x56eq1680Kbps(59),
        r30x64eq1920Kbps(60),
        r31x56eq1736Kbps(61),
        r31x64eq1984Kbps(62),
        noRate(100)
       }
       ACCESS   read-write
       STATUS   mandatory
       DESCRIPTION
     "The rate to use with this link."
       DEFVAL { noRate }
::= { linkSelectorPLinkEntry 8 }


--
-- Megaplex or Kilomux ?000/?004 MPH.1/3 High speed packet data cards.
-- Megaplex or Kilomux ?000/?004 MPL.6 Low speed packet data cards.
--      (Mph1, Mph3, Mpl6)
-- Maxcess 3000/3004 MLS-3/6, MHS-1/3
--
-- prtExPhPlCnfgTable  OBJECT IDENTIFIER ::= {prtPhPlCnfg 1}
-- prtExPhPlDlciTable  OBJECT IDENTIFIER ::= {prtPhPlCnfg 2}
-- prtExPhPlModemTable OBJECT IDENTIFIER ::= {prtPhPlCnfg 3}

-- Mph.1 Mph.3 Mpl.6/ Kphs.1 Kphs.3 Mls.3 Mls.6 Mhs.1 Mhs.3
-- External port objects table

prtExPhPlCnfgTable  OBJECT-TYPE
      SYNTAX SEQUENCE OF PrtExPhPlCnfgEntry
      ACCESS not-accessible
      STATUS  mandatory
      DESCRIPTION "The write operation into the Table Objects is
      valid only to the TmpCnfg entry."
      ::= {prtPhPlCnfg 1}

prtExPhPlCnfgEntry OBJECT-TYPE
      SYNTAX PrtExPhPlCnfgEntry
      ACCESS not-accessible
      STATUS mandatory
      DESCRIPTION "" INDEX {prtExPhPlCnfgIdx, prtExPhPlSltIdx, prtExPhPlPrtIdx}
      ::= { prtExPhPlCnfgTable 1}

PrtExPhPlCnfgEntry ::=
      SEQUENCE {
      prtExPhPlCnfgIdx            INTEGER,
      prtExPhPlSltIdx             INTEGER,
      prtExPhPlPrtIdx             INTEGER,
      prtExPhPlConnect            INTEGER,
      prtExPhPlHRate              INTEGER,
      prtExPhPlLRate              INTEGER,
      prtExPhPlProtocol           INTEGER,
      prtExPhPlConnectionTyp      INTEGER,
      prtExPhPlClkMode            INTEGER,
      prtExPhPlDceClkSrc          INTEGER,
      prtExPhPlCongResponse       INTEGER,
      prtExPhPlCongLevel          INTEGER,
      prtExPhPlTc                 INTEGER,
      prtExPhPlFlowControl        INTEGER,
      prtExPhPlDcdRts             INTEGER,
      prtExPhPlDcdRtsControlPath  INTEGER,
      prtExPhPlDataBits           INTEGER,
      prtExPhPlParity             INTEGER,
      prtExPhPlStopBits           INTEGER,
      prtExPhPlLXon               INTEGER,
      prtExPhPlLXoff              INTEGER,
	  prtExPhPlFrMngProt          INTEGER,
	  prtExPhPlEnqPeriod          INTEGER,
	  prtExPhPlFullRptPeriod      INTEGER,
	  prtExPhPlFrWindowSize       INTEGER,
	  prtExPhPlErrorsThreshold    INTEGER,
	  prtExPhPlPvcCreateMsg       INTEGER,
	  prtExPhPlCllmMsg            INTEGER,
	  prtExPhPlProtDelayLevel     INTEGER,
	  prtExPhPlClockEncoding      INTEGER,
	  prtExPhPlMinSeparators      INTEGER,
	  prtExPhPlCcittCrc           INTEGER,
	  prtExPhPlFrameSeparator     INTEGER
      }

prtExPhPlCnfgIdx OBJECT-TYPE
      SYNTAX  INTEGER (1..255)
      ACCESS  read-only
      STATUS  mandatory
      DESCRIPTION
      "This attribute indicates the Idx of the Cnfg (1..100) being
       accessed.
       Idx 255 relates to the TmpCnfg. "
      ::= { prtExPhPlCnfgEntry 1}
-- In phase I only the values 1 (Cnfg1) and 255 (temp) are valid.

prtExPhPlSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16),
    notApplicable (255)
     }
      ACCESS  read-only
      STATUS  mandatory
      DESCRIPTION
      "This attribute indicates a unique  slot  position where
       the card is inserted.
       In the ?004 Unit the entries io6(10)..io12(16) are not valid"
      ::= { prtExPhPlCnfgEntry 2}

prtExPhPlPrtIdx OBJECT-TYPE
      SYNTAX  INTEGER
 {
          exPrt1  (1) ,
          exPrt2  (2) ,
          exPrt3  (3) ,
          exPrt4  (4) ,
          exPrt5  (5) ,
          exPrt6  (6)
       }
      ACCESS read-only
      STATUS  mandatory
      DESCRIPTION
      "This attribute indicates a unique port number.
       In case of PH.1 card, only exPrt(1) is valid."
      ::= { prtExPhPlCnfgEntry 3}

prtExPhPlConnect OBJECT-TYPE
      SYNTAX  INTEGER
       {
  no  (2),
  yes (3)
       }
      ACCESS  read-write
      STATUS  mandatory
      DESCRIPTION
      "This attribute indicates whether the port should be considered
       in any of the mux  algorithms."
      ::= { prtExPhPlCnfgEntry 4}

prtExPhPlHRate OBJECT-TYPE
      SYNTAX  INTEGER
       {
        notApplicable (1),
        r32KbpsNLE    (2),
        r48KbpsNLE    (3),
        r56KbpsNLE    (4),
        r64KbpsNLE    (5),
        r112KbpsNLE   (6),
        r128KbpsNLE   (7),
        r168KbpsNLE   (8),
        r192KbpsNLE   (9),
        r224KbpsNLE  (10),
        r256KbpsNLE  (11),
        r280KbpsE    (12),
        r320KbpsE    (13),
        r336KbpsNLE  (14),
        r384KbpsNLE  (15),
        r392KbpsE    (16),
        r448KbpsNLE  (17),
        r504KbpsLE   (18), -- r504KbpsE 
        r512KbpsE    (19), -- r512KbpsNLE			  
        r560KbpsE    (20),
        r576KbpsLE   (21), -- r576KbpsE
        r616KbpsE    (22),
        r640KbpsE    (23),
        r672KbpsNLE  (24),
        r704KbpsE    (25),
        r728KbpsE    (26),
        r768KbpsNLE  (27),
        r784KbpsE    (28),
        r832KbpsE    (29),
        r840KbpsE    (30),
        r896KbpsNLE  (31),
        r952KbpsE    (32),
        r960KbpsE    (33),
       r1008KbpsLE   (34), -- r1008KbpsE
       r1024KbpsE    (35), -- r1024KbpsNLE
       r1064KbpsE    (36),
       r1088KbpsE    (37),
       r1120KbpsE    (38),
       r1152KbpsLE   (39), -- r1152KbpsE
       r1176KbpsE    (40),
       r1216KbpsE    (41),
       r1232KbpsE    (42),
       r1280KbpsE    (43),
       r1288KbpsE    (44),
       r1344KbpsNLE  (45),
       r1400KbpsE    (46),
       r1408KbpsE    (47),
       r1456KbpsE    (48),
       r1472KbpsE    (49),
       r1512KbpsE    (50),
       r1536KbpsE    (51), -- r1536KbpsNLE
       r1568KbpsE    (52),
       r1600KbpsE    (53),
       r1624KbpsE    (54),
       r1664KbpsE    (55),
       r1680KbpsE    (56),
       r1728KbpsE    (57),
       r1736KbpsE    (58),
       r1792KbpsNLE  (59),
       r1856KbpsE    (60),
       r1920KbpsE    (61),
       r1984KbpsE    (62),
       r2048KbpsE    (63), -- r2048KbpsNLE
--
--  Additional rates for: MAXcess, MP2100h 
--
       r9d6KbpsNLE   (65),
       r14d4KbpsNLE  (66),
       r16KbpsNLE    (67),
       r19d2KbpsNLE  (68),
       r28d8KbpsNLE  (69),
       r38d4KbpsNLE  (70),
       r57d6KbpsNLE  (71), -- For Mx 30/300 Only
       r115d2KbpsNLE (72), -- For Mx 30/300 Only
       r24000bps     (73)
       }
      ACCESS  read-write
      STATUS  mandatory
      DESCRIPTION
      "This attribute indicates the port speed for HIGH speed cards.
       The card has limitations about the maximum sigma channel
       speeds and about the possible rates for each clock mode .
       N - The rate is valid for DCE and EXT-DCE Nodal clock mode.
       L - The rate is valid for DCE and EXT-DCE Local clock mode.
       E - The rate is valid for DTE External clock mode.
       'r9d6KbpsNLE' means rate of 9.6 Kbps ('d'=dot).
       
       Note: Some rate attributes have been changed. As the MIB was already
             released with the old attributes, the names of the options were
             not changed. The new names + attributes are in a comment.
             Example:   r2048KbpsE (63), -- r2048KbpsNLE"
      ::= { prtExPhPlCnfgEntry 5}

prtExPhPlLRate  OBJECT-TYPE
      SYNTAX  INTEGER
       {
          notApplicable  (1),
          r300bpsNLE     (2),
          r600bpsNLE     (3),
          r800bpsNLE     (4),
          r1200bpsNLE    (5),
          r2400bpsNLE    (6),
          r4800bpsNLE    (7),
          r9600bpsNLE    (8),
          r14400bpsLE    (9),  -- r14400bpsNLE
          r19200bpsNLE   (10),
          r28800bpsLE    (11), -- r28800bpsNLE
          r32000bpsNLE   (12),
          r38400bpsNLE   (13),
          r48000bpsNLE   (14),
          r56000bpsNLE   (15),
          r57600bpsLE    (16), -- r57600bpsNLE
          r64000bpsNLE   (17),
          r112000bps     (18), -- For Mx 30/300 Only: r112000bpsNLE 
          r115200bps     (19), -- For Mx 30/300 Only: r115200bpsNLE
--
-- additional rates
--
         r16000bpsNLE    (20),
         r100bpsNLE      (21), -- For Mx 30/300 Only
         r128000bps      (22), -- For Mx 30/300 Only
         r24000bps       (23)
       }
      ACCESS  read-write
      STATUS  mandatory
      DESCRIPTION
      "This attribute indicates the port speed for LOW speed cards.
       The card has limitations about the possible rates for each
       clock mode.
       N - The rate is valid for DCE and EXT-DCE Nodal clock mode.
       L - The rate is valid for DCE and EXT-DCE Local clock mode.
       E - The rate is valid for DTE External clock mode.

       Note: Some rate attributes have been changed. As the MIB was already
             released with the old attributes, the names of the options were
             not changed. The new names + attributes are in a comment.
             Example:  r57600bpsLE (16), -- r57600bpsNLE  "

      ::= { prtExPhPlCnfgEntry 6}

prtExPhPlProtocol OBJECT-TYPE
      SYNTAX  INTEGER
     {
        fr                 (1),
        frPlus             (2),
        pCellRelay         (3),
        hdlcSdlc           (4),
        transparentHdlc    (5),
        async              (6),
        asyncReliable      (7),
        activePPP          (8),
        slip               (9),
        pppAgent           (10),
        slipAgent          (11),
        transparent        (12),
        sna                (13)
     }
      ACCESS  read-write
      STATUS  mandatory
      DESCRIPTION
      "This object indicates the applied protocol."
      ::= { prtExPhPlCnfgEntry 7}

prtExPhPlConnectionTyp OBJECT-TYPE
      SYNTAX  INTEGER
     {
     sameNetManaged  (1),
     sameNetNotMana  (2),
     user            (3),
     otherNet        (4),
     pubNet          (5),
        notApplicable (255)
     }
      ACCESS  read-write
      STATUS  mandatory
      DESCRIPTION
      "This attribute indicates the link connection type.
       It is required for three reasons:
     FR/CR Inband management opration (LMI,CLMM...).
     CIR check.
     NMS network management.

       SameNetManaged - indicates network internal line.
       SameNetMotMana - indicates network internal line, but the
                        remote mux is not managed by the NMS.

       User           - User to Network Interface.
       OtherNet       - Network To Network Interface.
       PubNet         - Access Mux To PubNet Interface."
      ::= { prtExPhPlCnfgEntry 8}

prtExPhPlClkMode OBJECT-TYPE
      SYNTAX  INTEGER
              {
                  dce     (1),
                  extDce  (2),
                  dte     (3),
      int     (4),
      lbt     (5)
              }
      ACCESS  read-write
      STATUS  mandatory
      DESCRIPTION
      "Clock mode."
      ::= { prtExPhPlCnfgEntry 9}

prtExPhPlDceClkSrc OBJECT-TYPE
      SYNTAX  INTEGER
              {
                  notApplicable (1),
                  local         (2),
                  nodalTiming   (3)
              }
      ACCESS  read-write
      STATUS  mandatory
      DESCRIPTION
      "This attribute indicates the source of the clock when working
       in dce or ext-dce clock mode.
       notApplicable(1) - is applied for dte(3) and lbt(5) clock modes.
	                      When clock mode is dte, the clock source is
						  always external, therefore this object's value is
						  notApplicable.
       local(2) and nodalTiming(3) - are valid in dce(1), extDce(2)
                                     or int(4) clock modes.
       The recommended clock source is local(2)."
      ::= { prtExPhPlCnfgEntry 10}

prtExPhPlCongResponse OBJECT-TYPE
      SYNTAX  INTEGER
     {
        no                  (2),
        flowControl         (3), -- duplex, to/from flow control
        toFlowControl       (4)  -- simplex , only to flow control
     }
      ACCESS  read-write
      STATUS  mandatory
      DESCRIPTION
"This attribute indicates how to handle the congestion indication
 to/from the mux internal connection side (for example
 transmit/received becn to/from the network).
   no           - do nothing
   flowControl  - translates the congestion indication between the
                  port and the internal connection port according
                  to the definition of the prtInPh1MlFlowControl
                  parameters. The operation is done on both
                  directions.
   toFlowControl- translates the backward congestion indication
                  received from the internal connection port
                  (normally the network side) to flow control and
                  do nothing in the other direction."
      ::= { prtExPhPlCnfgEntry 11}

prtExPhPlCongLevel OBJECT-TYPE
      SYNTAX  INTEGER (0..70)
      ACCESS  read-write
      STATUS  mandatory
      DESCRIPTION
      "This attribute indicates the level of delayed data in
       precents of total available dynamic memory,
       for which the port will start to operate as congested.
       The resolution of the parameter is 5 percent."
      ::= { prtExPhPlCnfgEntry 12}

prtExPhPlTc OBJECT-TYPE
      SYNTAX  INTEGER
          {
          tc1sec  (1),
          tc2sec  (2),
          tc3sec  (3),
          tc4sec  (4),
    notApplicable (255)
          }
      ACCESS  read-write
      STATUS  mandatory
      DESCRIPTION
      "This attribute indicates the Tc parameter which is the time
       period of the sliding window in which the Bc/Be are tested.
       The value of this parameter is identical for all the ports
       of a  specific card ."
      ::= { prtExPhPlCnfgEntry 13}

prtExPhPlFlowControl OBJECT-TYPE
      SYNTAX  INTEGER
     {
        none                (2),
        fecnBecn            (3),
        xonXoff             (4),
        dtrCts              (5),
        speedReduction      (6)   -- simplex response only congestion to flow control
     }
      ACCESS  read-write
      STATUS  mandatory
      DESCRIPTION
      "This attribute indicates the required flow control betweeen
       the port and the remote equipment.
       fecnBecn - is valid only for FR, FR+ and CR protocols.
       xonXoff,dtrCts - are valid only for Async protocols.
       speedReduction - is valid only for DLC protocol when the
                        Clock Mode is DCE and the Clock Source is
                        Local."
      ::= { prtExPhPlCnfgEntry 14}

prtExPhPlDcdRts OBJECT-TYPE
      SYNTAX  INTEGER
     {
        notApplicable     (1),
        on                (2),
        endToEnd          (3)
     }
      ACCESS  read-write
      STATUS  mandatory
      DESCRIPTION
      "Protocol may require end to end connect indication over the
       network. End to end link connection establishment over the
       FR network will be indicated to the user by using DCD or
       RTS control signals, depending on the clock mode: DCE or
       DTE respectively.
       The options are :
       - On :
              DCD(DCE)/RTS(DTE) will be constantly ON no matter
              if the End to End connection is established or not.
       - End to End:
              The DCD(DCE)/RTS(DTE) will be according to the status
              of the End to End connection."
      ::= { prtExPhPlCnfgEntry 15}

prtExPhPlDcdRtsControlPath OBJECT-TYPE
      SYNTAX  INTEGER
     {
        notApplicable     (1),
        off               (2),
        on                (3)
     }
      ACCESS  read-write
      STATUS  mandatory
      DESCRIPTION
      "Protocol may require end to end connect indication over the
       network. This parameter defines whether to take the user
       connection status (RTS(DCE)/DCD(DTE)) and forward it to the
       network side.
      - on : Transmit active connection to the network regardless
              the RTS/DCD control lines status.
      - off: Transmit active connection to the network according
              to the status of the RTS/DCD pin. "
      ::= { prtExPhPlCnfgEntry 16}

prtExPhPlDataBits OBJECT-TYPE
      SYNTAX  INTEGER
         {
         notApplicable  (1),
         dataBits7Bits (2),
         dataBits8Bits (3)
         }
      ACCESS  read-write
      STATUS  mandatory
      DESCRIPTION
      "This attribute indicates the number of data bits in async
       frame.
       It is relevant only for Async protocols."
      ::= { prtExPhPlCnfgEntry 17}

prtExPhPlParity OBJECT-TYPE
      SYNTAX  INTEGER
         {
         notApplicable  (1),
         odd            (2),
         even           (3),
         none           (4)
         }
      ACCESS  read-write
      STATUS  mandatory
      DESCRIPTION
      "This attribute indicates the parity operation mode in
       async frame.
       It is relevant only for Async protocols."
      ::= { prtExPhPlCnfgEntry 18}

prtExPhPlStopBits OBJECT-TYPE
      SYNTAX  INTEGER
         {
         notApplicable  (1),
         sb1Bit           (2),
         sb1dot5Bits      (3),
         sb2Bits          (4)
         }
      ACCESS  read-write
      STATUS  mandatory
      DESCRIPTION
      "This attribute indicates the minimum number of stop bits
       in the tx async frame.
       It is relevant only for Async protocols."
      ::= { prtExPhPlCnfgEntry 19}

prtExPhPlLXon OBJECT-TYPE
      SYNTAX  INTEGER
      ACCESS  read-write
      STATUS  mandatory
      DESCRIPTION
      "This attribute indicates the character used as X-On to
       notify receive enable.
       This parameter is valid only for async protocols.
    Valid values: 0..255.
       The value 256 indicates that it's not applicable "
      ::= { prtExPhPlCnfgEntry 20}

prtExPhPlLXoff OBJECT-TYPE
      SYNTAX  INTEGER
      ACCESS  read-write
      STATUS  mandatory
      DESCRIPTION
      "This attribute indicates the character used as X-Off to
       notify receive disable.
       This parameter is valid only for async protocols.
    Valid values: 0..255.
       The value 256 indicates that it's not applicable "
      ::= { prtExPhPlCnfgEntry 21}

prtExPhPlFrMngProt OBJECT-TYPE
      SYNTAX  INTEGER
   {
   notApplicable (1),
   none          (2),
   lmi           (3),
   ansiT1        (4),  --Annex D
   annexA        (5)
   }
      ACCESS  read-write
      STATUS  mandatory
      DESCRIPTION
      "This object indicates the Frame-Relay management protocol.
       ansiT1 = ANSI T1.617 Annex D (this is the default value).
       This parameter is applicable only for FR and FR+ protocols.
       When prtExPhPlConnectionTyp = sameNetManaged, this object
       will be RO (internally determined). "
      ::= { prtExPhPlCnfgEntry 22}

prtExPhPlEnqPeriod OBJECT-TYPE
      SYNTAX  INTEGER (1..30)
      ACCESS  read-write
      STATUS  mandatory
      DESCRIPTION
      "This object is the Status Enquiry Period, in seconds.
       It determines the frequency of the Status Enquiry message
       as sent by the FR user side.
       At the FR network side, it determines the timeout for this
       message reception.
    Default = 4 seconds.
       This parameter is applicable only for FR and FR+ protocols
    AND
       only when prtExPhPlFrMngProt is NOT (notApplicable or none)."
    ::= { prtExPhPlCnfgEntry 23}

prtExPhPlFullRptPeriod OBJECT-TYPE
      SYNTAX  INTEGER (1..255)
      ACCESS  read-write
      STATUS  mandatory
      DESCRIPTION
      "This object is the Full Report Frequency.
       It determines the number of the Status Enquiry messages
       sent by the FR user side, before a Full Report Request is
       sent.
       The units are : Status Enquiry messages (periods).
    Valid values: 1 .. 255.
       255 = infinite.
       This parameter is applicable only for FR and FR+ protocols
    AND
       only when prtExPhPlFrMngProt is NOT (notApplicable or none)."
    ::= { prtExPhPlCnfgEntry 24}

prtExPhPlFrWindowSize OBJECT-TYPE
      SYNTAX  INTEGER (1..10)
      ACCESS  read-write
      STATUS  mandatory
      DESCRIPTION
      "This object is the FR Window Size.
       It determines the number of samplings in the sliding window
       that counts the errors.
       This parameter is applicable only for FR and FR+ protocols
    AND
       only when prtExPhPlFrMngProt is NOT (notApplicable or none)."
    ::= { prtExPhPlCnfgEntry 25}

prtExPhPlErrorsThreshold OBJECT-TYPE
      SYNTAX  INTEGER (1..10)
      ACCESS  read-write
      STATUS  mandatory
      DESCRIPTION
      "This object is the Max Errors.
       It determines the number of Status Enquiry Errors that
       occured within the FR sliding window, before this port is
       considered DOWN (threshold).
       This parameter is applicable only for FR and FR+ protocols
    AND
       only when prtExPhPlFrMngProt is NOT (notApplicable or none)."
    ::= { prtExPhPlCnfgEntry 26}

prtExPhPlPvcCreateMsg OBJECT-TYPE
      SYNTAX  INTEGER
   {
   notApplicable (1),
   no            (2),
   yes           (3)
   }
      ACCESS  read-write
      STATUS  mandatory
      DESCRIPTION
      "This object is Update Message (if required or not).
       It determines whether a message of a New PVC Creation is
       requested or not (yes/no).
       Default = no.
       This parameter is applicable only for FR and FR+ protocols
    AND
       only when prtExPhPlFrMngProt is NOT (notApplicable or none)."
    ::= { prtExPhPlCnfgEntry 27}

prtExPhPlCllmMsg OBJECT-TYPE
      SYNTAX  INTEGER
   {
   notApplicable (1),
   no            (2),
   yes           (3)
   }
      ACCESS  read-write
      STATUS  mandatory
      DESCRIPTION
      "This object is CLLM Message (if required or not).
       It determines whether to send (or not) a congestion message
       when the port is Rx congested.
       Default = no.
       This parameter is applicable only for FR and FR+ protocols
    AND
       only when prtExPhPlFrMngProt is NOT (notApplicable or none)."
    ::= { prtExPhPlCnfgEntry 28}

prtExPhPlProtDelayLevel OBJECT-TYPE
      SYNTAX  INTEGER
	  {
	  notApplicable (1),
	  s36Byte       (2),  --level 1
	  s150Byte      (3),  --level 2
	  s264Byte      (4),  --level 3
	  s378Byte      (5),  --level 4
	  s492Byte      (6)	  --level 5
	  }
      ACCESS  read-write
      STATUS  mandatory

      DESCRIPTION
      "This object is the Segmentation in Bytes.
       	In some cases, the enumerated values will mean
	    other segmentation values than specified:

	   Product:    MX-3000 	    MX-3000 	   MX-300/MX-30
	   Protocol:     FR+     	Transparent		FR+
	   -----------------------------------------------------
	   level 1     50 Bytes		44 Bytes		50 Bytes
	   level 2    158 Bytes	   155 Bytes	   158 Bytes
	   level 3    266 Bytes	   266 Bytes	   266 Bytes
	   level 4    376 Bytes	   377 Bytes	   376 Bytes
	   level 5    484 Bytes	   488 Bytes	   484 Bytes

	   Defval=level 1 value

       This parameter is applicable only for FR+ and
       transparent protocols."
	   ::= { prtExPhPlCnfgEntry 29}

prtExPhPlClockEncoding OBJECT-TYPE
      SYNTAX  INTEGER
	  {
	  notApplicable (1),
	  nrz           (2),
	  nrzI          (3),
	  fm0           (4),
	  manchester    (5),
	  diffManchester(6)
	  }
      ACCESS  read-write
      STATUS  mandatory
      DESCRIPTION
      "This object is the Encoding type of the Line.
       This parameter is applicable only for FR and FR+ protocols."
	   ::= { prtExPhPlCnfgEntry 30}

prtExPhPlMinSeparators OBJECT-TYPE
      SYNTAX  INTEGER (0..16)
      ACCESS  read-write
      STATUS  mandatory
      DESCRIPTION
      "Minimum number of bytes separating between two adjacent frames (HDLC item).
       0 = notApplicable"
	   ::= { prtExPhPlCnfgEntry 31}

prtExPhPlCcittCrc OBJECT-TYPE
      SYNTAX  INTEGER
	  {
	  notApplicable (1),
	  crc16         (2),
	  crc32         (3)
	  }
      ACCESS  read-write
      STATUS  mandatory
      DESCRIPTION
      "This object indicates how many Bits are used for CRC (HDLC item)."
	   ::= { prtExPhPlCnfgEntry 32}

prtExPhPlFrameSeparator OBJECT-TYPE
      SYNTAX  INTEGER
	  {
	  notApplicable (1),
	  idles         (2),
	  flags         (3)
	  }
      ACCESS  read-write
      STATUS  mandatory
      DESCRIPTION
      "This object indicates what should be transferred on the line when there
       are no frames to pass (HDLC item).
       idles: mean that FF will pass on the line
       flags: mean that 7E will pass on the line."
	   ::= { prtExPhPlCnfgEntry 33}


--
-- PH.1 & PH.3
-- External port Dlci table
--
prtExPhPlDlciTable  OBJECT-TYPE
     SYNTAX SEQUENCE OF PrtExPhPlDlciEntry
     ACCESS not-accessible
     STATUS  mandatory
     DESCRIPTION
      "The write operation into the Table Objects is valid only
       at the TmpCnfg entry."
     ::= {prtPhPlCnfg 2}

prtExPhPlDlciEntry OBJECT-TYPE
      SYNTAX PrtExPhPlDlciEntry
      ACCESS not-accessible
      STATUS mandatory
      DESCRIPTION "" INDEX {prtExPhPlDlciCnfgIdx, prtExPhPlDlciSltIdx, prtExPhPlDlciPrtIdx, prtExPhPlDlciIdx }
      ::= { prtExPhPlDlciTable 1}

PrtExPhPlDlciEntry ::=
      SEQUENCE {
      prtExPhPlDlciCnfgIdx        INTEGER,
      prtExPhPlDlciSltIdx         INTEGER,
      prtExPhPlDlciPrtIdx         INTEGER,
      prtExPhPlDlciIdx            INTEGER,

      prtExPhPlDlciValid          INTEGER,
      prtExPhPlDlciIConSlt        INTEGER,
      prtExPhPlDlciIConPrt        INTEGER,
      prtExPhPlDlciIConDlci       INTEGER,

      prtExPhPlDlciTxBc           INTEGER,
      prtExPhPlDlciTxBe           INTEGER,
      prtExPhPlDlciRxBc           INTEGER,
      prtExPhPlDlciRxBe           INTEGER,

      prtExPhPlDlciPriority       INTEGER,

      prtExPhPlDlciStatus         INTEGER
      }


prtExPhPlDlciCnfgIdx OBJECT-TYPE
      SYNTAX  INTEGER (1..255)
      ACCESS  read-only
      STATUS  mandatory
      DESCRIPTION
      "This attribute indicates the Idx of the Cnfg (1..100) being
       accessed.
       Idx 255 relates to the TmpCnfg. "
      ::= { prtExPhPlDlciEntry 1}
-- In phase I only the values 1 (Cnfg1) and 255 (temp) are valid.

prtExPhPlDlciSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16),
    notApplicable (255)
     }
      ACCESS  read-only
      STATUS  mandatory
      DESCRIPTION
      "This attribute indicates a unique  slot  position where
       the card is inserted.
       In the ?004 Unit the entries io6(10)..io16) are not valid"
      ::= { prtExPhPlDlciEntry 2}

prtExPhPlDlciPrtIdx OBJECT-TYPE
      SYNTAX  INTEGER
 {
          exPrt1  (1) ,
          exPrt2  (2) ,
          exPrt3  (3) ,
    exPrt4  (4) ,
    exPrt5  (5) ,
    exPrt6  (6)
       }
      ACCESS  read-only
      STATUS  mandatory
      DESCRIPTION
      "This attribute indicates a unique internal port number.
       PH.1/E1 and PH.1/T1 cards have three internal ports.
       Stand-alone units may have six such ports."
      ::= { prtExPhPlDlciEntry 3}

prtExPhPlDlciIdx OBJECT-TYPE
      SYNTAX  INTEGER (1..991)
      ACCESS  read-only
      STATUS  mandatory
      DESCRIPTION
      "This attribute indicates a unique index for each possible
       used dlci(16..991). When the protocol is not Multiplexing
       protocol, its type is 'user' and the only valid index is 1."
      ::= { prtExPhPlDlciEntry 4}

prtExPhPlDlciValid OBJECT-TYPE
      SYNTAX  INTEGER
     {
     no  (2),
     yes (3)
     }
      ACCESS  read-write
      STATUS  mandatory
      DESCRIPTION
      "This attribute indicates whether the attributes in this
       entry are valid or not. The user can add/delete pvc (dlci
       to dlci connection) by modifing this object"
      ::= { prtExPhPlDlciEntry 5}

prtExPhPlDlciIConSlt OBJECT-TYPE
      SYNTAX  INTEGER
 {
          noConnect (2),
    cl    (3),
       io1   (5),
       io2   (6),
       io3   (7),
       io4   (8),
       io5   (9),
       io6  (10),
       io7  (11),
       io8  (12),
       io9  (13),
       io10 (14),
       io11 (15),
       io12 (16),
    notApplicable (255)
       }
      ACCESS  read-write
      STATUS  mandatory
      DESCRIPTION
      "This attribute indicates a unique slot position In the Mux
       (Agent) where the dlci is routed to.
    cl - will represent any of the CL slots. This value can be
         selected for multiple DLCIs of the product.
       In the ?004 Unit the entries io6(10)..io16) are not valid"
      ::= { prtExPhPlDlciEntry 6}

prtExPhPlDlciIConPrt OBJECT-TYPE
      SYNTAX  INTEGER
      {
       exPrt1    (1) ,
       exPrt2    (2) ,
       exPrt3    (3) ,
       exPrt4    (4) ,
       exPrt5    (5) ,
       exPrt6    (6) ,
       exPrt7    (7) ,
       exPrt8    (8) ,
       exPrt9    (9) ,
       exPrt10  (10) ,
    clNMS      (99),
          noConnect (100),
       inPrt1  (101) ,
       inPrt2  (102) ,
       inPrt3  (103) ,
       inPrt4  (104) ,
       inPrt5  (105) ,
       inPrt6  (106) ,
       inPrt7  (107) ,
       inPrt8  (108) ,
       inPrt9  (109) ,
       inPrt10 (110)
       }
      ACCESS  read-write
      STATUS  mandatory
      DESCRIPTION
      "This attribute indicates a unique port id which the dlci is
       routed to.
       clNMS - will be used for NMS SNMP messages. It can be any
               port of the CL card.
               This value will be selectable only if
               prtExPhPlDlciIConSlt='cl' or 'notApplicable'."
      ::= { prtExPhPlDlciEntry 7}


prtExPhPlDlciIConDlci OBJECT-TYPE
      SYNTAX  INTEGER    (1..991)
      ACCESS  read-write
      STATUS  mandatory
      DESCRIPTION
      "This attribute indicates a unique internal connection dlci
       number,  the dlci is routed to."
      ::= { prtExPhPlDlciEntry 8}

prtExPhPlDlciTxBc OBJECT-TYPE
      SYNTAX  INTEGER
        {
         full       (1),
         zero       (2),
         txBc9600bps    (3),
        txBc14400bps    (4),
        txBc19200bps    (5),
        txBc28800bps    (6),
        txBc32000bps    (7),
        txBc38400bps    (8),
        txBc48000bps    (9),
        txBc56000bps   (10),
        txBc57600bps   (11),
          txBc64Kbps   (12),
         txBc128Kbps   (13),
         txBc192Kbps   (14),
         txBc256Kbps   (15),
         txBc320Kbps   (16),
         txBc384Kbps   (17),
         txBc448Kbps   (18),
         txBc512Kbps   (19),
         txBc768Kbps   (20),
        txBc1024Kbps   (21),
--
--KM30 ; KM300 additional rates
--
        txBc16000bps   (25),
   txBc112Kbps   (26)
        }
      ACCESS  read-write
      STATUS  mandatory
      DESCRIPTION
      "This attribute indicates a unique Tx committed bandwidth on
       the user transmit line (or at the port receive line)."
      ::= { prtExPhPlDlciEntry 9}


prtExPhPlDlciTxBe OBJECT-TYPE
      SYNTAX  INTEGER
        {
         full       (1),
         zero       (2),
         txBe9600bps    (3),
        txBe14400bps    (4),
        txBe19200bps    (5),
        txBe28800bps    (6),
        txBe32000bps    (7),
        txBe38400bps    (8),
        txBe48000bps    (9),
        txBe56000bps   (10),
        txBe57600bps   (11),
          txBe64Kbps   (12),
         txBe128Kbps   (13),
         txBe192Kbps   (14),
         txBe256Kbps   (15),
         txBe320Kbps   (16),
         txBe384Kbps   (17),
         txBe448Kbps   (18),
         txBe512Kbps   (19),
         txBe768Kbps   (20),
        txBe1024Kbps   (21),
--
--KM30 ; KM300 additional rates
--
        txBc16000bps   (25),
   txBc112Kbps   (26)
        }
      ACCESS  read-write
      STATUS  mandatory
      DESCRIPTION
      "This attribute indicates a unique Tx excess bandwidth on the
      user transmit line (or at the port receive line)."
      ::= { prtExPhPlDlciEntry 10}


prtExPhPlDlciRxBc OBJECT-TYPE
      SYNTAX  INTEGER
        {
         full       (1),
         zero       (2),
         rxBc9600bps    (3),
        rxBc14400bps    (4),
        rxBc19200bps    (5),
        rxBc28800bps    (6),
        rxBc32000bps    (7),
        rxBc38400bps    (8),
        rxBc48000bps    (9),
        rxBc56000bps   (10),
        rxBc57600bps   (11),
        rxBc64Kbps   (12),
         rxBc128Kbps   (13),
         rxBc192Kbps   (14),
         rxBc256Kbps   (15),
         rxBc320Kbps   (16),
         rxBc384Kbps   (17),
         rxBc448Kbps   (18),
         rxBc512Kbps   (19),
         rxBc768Kbps   (20),
        rxBc1024Kbps   (21),
--
--KM30 ; KM300 additional rates
--
        rxBc16000bps   (25),
   rxBc112Kbps   (26)
        }
      ACCESS  read-write
      STATUS  mandatory
      DESCRIPTION
      "This attribute indicates a unique Rx committed bandwidth on the
      user receive line (or at the port transmit line)."
      ::= { prtExPhPlDlciEntry 11}


prtExPhPlDlciRxBe OBJECT-TYPE
      SYNTAX  INTEGER
        {
         full       (1),
         zero       (2),
         rxBe9600bps    (3),
        rxBe14400bps    (4),
        rxBe19200bps    (5),
        rxBe28800bps    (6),
        rxBe32000bps    (7),
        rxBe38400bps    (8),
        rxBe48000bps    (9),
        rxBe56000bps   (10),
        rxBe57600bps   (11),
          rxBe64Kbps   (12),
         rxBe128Kbps   (13),
         rxBe192Kbps   (14),
         rxBe256Kbps   (15),
         rxBe320Kbps   (16),
         rxBe384Kbps   (17),
         rxBe448Kbps   (18),
         rxBe512Kbps   (19),
         rxBe768Kbps   (20),
        rxBe1024Kbps   (21),
--
--KM30 ; KM300 additional rates
--
        rxBc16000bps   (25),
   rxBc112Kbps   (26)
        }
      ACCESS  read-write
      STATUS  mandatory
      DESCRIPTION
      "This attribute indicates a unique Rx excess bandwidth on the
      user receive line (or at the port transmit line)."
      ::= { prtExPhPlDlciEntry 12}


prtExPhPlDlciPriority OBJECT-TYPE
      SYNTAX  INTEGER  (1..8)
      ACCESS  read-write
      STATUS  mandatory
      DESCRIPTION
      "This attribute indicates a unique priority of the pcv.
       1 is the lowest priority and 8 is the highest priority."
      ::= { prtExPhPlDlciEntry 13}


prtExPhPlDlciStatus OBJECT-TYPE
      SYNTAX  INTEGER
 {
          disconnected (1),
          connected    (2)
       }
      ACCESS  read-only
      STATUS  mandatory
      DESCRIPTION
      "This attribute indicates the status of the pvc. The status is
       disconnected(1) when one of the sides is programmed as not
       connected"
      ::= { prtExPhPlDlciEntry 14}


-- Parameters of an external Modem which is connected to a High/Low Speed
-- Port.

prtExPhPlModemTable  OBJECT-TYPE
      SYNTAX SEQUENCE OF PrtExPhPlModemEntry
      ACCESS not-accessible
      STATUS  mandatory
      DESCRIPTION "External Modem Parameters.
      The write operation into the
      Table Objects is valid only for the TmpCnfg entry."
      ::= {prtPhPlCnfg 3}

prtExPhPlModemEntry OBJECT-TYPE
      SYNTAX PrtExPhPlModemEntry
      ACCESS not-accessible
      STATUS mandatory
      DESCRIPTION "" INDEX {prtExPhPlModemCnfgIdx,prtExPhPlModemSltIdx,prtExPhPlModemPrtIdx}
      ::= { prtExPhPlModemTable 1}

PrtExPhPlModemEntry ::=
      SEQUENCE {
      prtExPhPlModemCnfgIdx           INTEGER,
      prtExPhPlModemSltIdx            INTEGER,
      prtExPhPlModemPrtIdx            INTEGER,
      prtExPhPlModemStatus            INTEGER,
      prtExPhPlModemActivate          INTEGER,
      prtExPhPlModemMaxIdleTime       INTEGER,
      prtExPhPlModemTimeBtwnCalls     INTEGER,
	  prtExPhPlModemCallDelay         INTEGER
      }

prtExPhPlModemCnfgIdx OBJECT-TYPE
      SYNTAX  INTEGER (1..255)
      ACCESS  read-only
      STATUS  mandatory
      DESCRIPTION
      "This attribute indicates the Idx of the Cnfg (1..100) being
       accessed.
       Idx 255 relates to the TmpCnfg. "
      ::= { prtExPhPlModemEntry 1}

prtExPhPlModemSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16),
       notApplicable (255)
     }
      ACCESS  read-only
      STATUS  mandatory
      DESCRIPTION
      "This attribute indicates a unique  slot  position where
       the card is inserted.
       In the ?004 Unit the entries io6(10)..io12(16) are not valid"
      ::= { prtExPhPlModemEntry 2}

prtExPhPlModemPrtIdx OBJECT-TYPE
      SYNTAX  INTEGER
 {
          exPrt1  (1) ,
          exPrt2  (2) ,
          exPrt3  (3) ,
          exPrt4  (4) ,
          exPrt5  (5) ,
          exPrt6  (6)
       }
      ACCESS read-only
      STATUS  mandatory
      DESCRIPTION
      "This attribute indicates a unique port number.
       In case of PH.1 card, only exPrt(1) is valid."
      ::= { prtExPhPlModemEntry 3}

prtExPhPlModemStatus OBJECT-TYPE
      SYNTAX INTEGER
      {
       disable (2),
       enable  (3)
      }
      ACCESS  read-write
      STATUS  mandatory
      DESCRIPTION
      "This object indicates whether a Dial Up Modem is enabled
       on this port.
       Default: disable"
      ::= { prtExPhPlModemEntry 4}

prtExPhPlModemActivate OBJECT-TYPE
      SYNTAX INTEGER
     {
      onFirstFrame(2),
      always    (3),
      notApplicable (255)
     }
      ACCESS  read-write
      STATUS  mandatory
      DESCRIPTION
      "This object indicates whether the Dial Up Modem is activated when
       the first frame is received or it is always activated.
       Default: onFirstFrame"
      ::= { prtExPhPlModemEntry 5}

prtExPhPlModemMaxIdleTime OBJECT-TYPE
      SYNTAX INTEGER
      ACCESS  read-write
      STATUS  mandatory
      DESCRIPTION
      "Max Time allowed in Seconds without any traffic before the line
       is disconnected.

       Legal Values are: 1 sec, 2 sec .. 5 sec, 10 sec, 20 sec..
       1 min, 2 min .. 10 min, 15 min, 20 min, 25 min, 30 min.
       65535 sec. means that this parameter is not applicable. 

       Default: 1 sec."
       ::= { prtExPhPlModemEntry 6}

prtExPhPlModemTimeBtwnCalls OBJECT-TYPE
      SYNTAX INTEGER
      ACCESS  read-write
      STATUS  mandatory
      DESCRIPTION
      "Minimum Time in Seconds which is required after a call was
       disconnected. In this time no other call will be initiated
       from this Modem port even if there were frames transmitted
       to this port. This time is required for some Modems which
       have initializations that take a few seconds.
       
       Legal Values are:
	   0 sec. - 30 sec., 1-5 min.
       65535 sec. means that this parameter is not applicable. 

       Default: 0 sec"
       ::= { prtExPhPlModemEntry 7}

prtExPhPlModemCallDelay OBJECT-TYPE
      SYNTAX INTEGER
      ACCESS  read-write
      STATUS  mandatory
      DESCRIPTION
      "Time in Seconds that the device will wait before dialing to the remote
	   device.
	   
	   This feature is mostly used when there is a backup modem to the 
	   main link and the main link is down. In this case it is important to prevent
	   the 2 devices from dialing through the backup modems to each other at the same time.
	   It is advised to configure one side with a small call delay and the other side
	   with a large call delay.
       
       Legal Values are:
	   0 - 30, 60, 120, 180, 240, 300, 600, 900, 1200, 1500, 1800 . 
       65535 sec. means that this parameter is not applicable. 

       Default: 0 sec"
       ::= { prtExPhPlModemEntry 8}

--
-- Megaplex ?000/?004 LS-2 TDM I/O family card include:
-- Ls2-CCITT-X.50, Ls2-CCITT-X.58, Ls2-AT&T-SDM
--
--prtExLs2CnfgTable OBJECT IDENTIFIER ::= {prtLs2Cnfg 1}
--prtInLs2CnfgTable OBJECT IDENTIFIER ::= {prtLs2Cnfg 2}

prtExLs2CnfgTable OBJECT-TYPE
      SYNTAX SEQUENCE OF PrtExLs2CnfgEntry
      ACCESS not-accessible
      STATUS  mandatory
      DESCRIPTION
       "The write operation into the Table Objects is valid only
        to the TmpCnfg entry."
      ::= {prtLs2Cnfg 1}

prtExLs2CnfgEntry OBJECT-TYPE
      SYNTAX PrtExLs2CnfgEntry
      ACCESS not-accessible
      STATUS mandatory
      DESCRIPTION "" INDEX {prtExLs2CnfgIdx, prtExLs2SltIdx, prtExLs2PrtIdx }
      ::= {prtExLs2CnfgTable  1}

PrtExLs2CnfgEntry ::=
      SEQUENCE {
        prtExLs2CnfgIdx   INTEGER,
        prtExLs2SltIdx    INTEGER,
        prtExLs2PrtIdx    INTEGER,
        prtExLs2Connect   INTEGER,
        prtExLs2Rate      INTEGER,
        prtExLs2ClkMode   INTEGER,
        prtExLs2Cts       INTEGER,
        prtExLs2Dcd       INTEGER,
        prtExLs2EnvIdx    INTEGER
      }

prtExLs2CnfgIdx OBJECT-TYPE
      SYNTAX  INTEGER (1..255)
      ACCESS  read-only
      STATUS  mandatory
      DESCRIPTION
      "This attribute indicates the Idx of the Cnfg (1..100) being
       accessed.
       Idx  255 relates to the TmpCnfg"
      ::= {prtExLs2CnfgEntry 1}
-- In phase I only the values 1 (Cnfg1) and 255 (temp) are valid.

prtExLs2SltIdx OBJECT-TYPE
      SYNTAX  INTEGER
          {
       io1   (5),
       io2   (6),
       io3   (7),
       io4   (8),
       io5   (9),
       io6  (10),
       io7  (11),
       io8  (12),
       io9  (13),
       io10 (14),
       io11 (15),
       io12 (16)
       }
      ACCESS  read-only
      STATUS  mandatory
      DESCRIPTION
      "This attribute indicates a unique  slot  position where
       the card is inserted.
       In the ?004 Unit the entries io6(10)..io16) are not valid."
      ::= {prtExLs2CnfgEntry 2}

prtExLs2PrtIdx OBJECT-TYPE
      SYNTAX  INTEGER
          {
          exPrt1    (1) ,
          exPrt2    (2) ,
          exPrt3    (3) ,
          exPrt4    (4) ,
          exPrt5    (5) ,
          exPrt6    (6) ,
          exPrt7    (7) ,
          exPrt8    (8) ,
          exPrt9    (9) ,
          exPrt10  (10)
          }
      ACCESS  read-only
      STATUS  mandatory
      DESCRIPTION
      "This attribute indicates a unique  port index.
      For the Ls2/X.58 exPrt(7)..exPrt(10) are not valid."
      ::= {prtExLs2CnfgEntry 3}


prtExLs2Connect OBJECT-TYPE
      SYNTAX  INTEGER
              {
                no  (2),
                yes (3)
              }
      ACCESS  read-write
      STATUS  mandatory
      DESCRIPTION
      "This attribute indicates whether the  port  should be
       considered in any of the mux algorithms."
      ::= {prtExLs2CnfgEntry 4}

prtExLs2Rate OBJECT-TYPE
      SYNTAX  INTEGER
       {
          r2400bps  (2),
          r4800bps  (3),
          r9600bps  (4),
          r19200bps (5)
       }
      ACCESS  read-write
      STATUS  mandatory
      DESCRIPTION
      "Port rates."
      ::= {prtExLs2CnfgEntry 5}

prtExLs2ClkMode OBJECT-TYPE
      SYNTAX  INTEGER
       {
          dce     (1),
          ext-dce (2),
          dte     (3)
       }
      ACCESS  read-write
      STATUS  mandatory
      DESCRIPTION
      "This attribute indicates a unique port operation clock mode."
      ::= {prtExLs2CnfgEntry 6}

prtExLs2Cts OBJECT-TYPE
      SYNTAX  INTEGER
       {
    on       (2),
    rts-min  (3),
    rts-max  (4)
       }
      ACCESS  read-write
      STATUS  mandatory
      DESCRIPTION
      "CTS."
      ::= {prtExLs2CnfgEntry 7}

prtExLs2Dcd OBJECT-TYPE
      SYNTAX  INTEGER
       {
    on        (2),
    card-sync (3)
       }
      ACCESS  read-write
      STATUS  mandatory
      DESCRIPTION
      "DCD."
      ::= {prtExLs2CnfgEntry 8}

prtExLs2EnvIdx OBJECT-TYPE
      SYNTAX  INTEGER (0..24)
      ACCESS  read-write
      STATUS  mandatory
      DESCRIPTION
      "Envelope Index.
       When prtInLs2EnvAssign=auto, the value is 0 (not applicable)."
      ::= {prtExLs2CnfgEntry 9}

-- Ls2 Internal composit channel parameters
--
prtInLs2CnfgTable OBJECT-TYPE
      SYNTAX SEQUENCE OF PrtInLs2CnfgEntry
      ACCESS not-accessible
      STATUS  mandatory
      DESCRIPTION
       "The write operation into the Table Objects is valid only
        to the TmpCnfg entry."
      ::= {prtLs2Cnfg 2}

prtInLs2CnfgEntry OBJECT-TYPE
      SYNTAX PrtInLs2CnfgEntry
      ACCESS not-accessible
      STATUS mandatory
      DESCRIPTION "" INDEX {prtInLs2CnfgIdx, prtInLs2SltIdx, prtInLs2PrtIdx }
      ::= {prtInLs2CnfgTable 1}

PrtInLs2CnfgEntry ::=
      SEQUENCE {
        prtInLs2CnfgIdx   INTEGER,
        prtInLs2SltIdx    INTEGER,
        prtInLs2PrtIdx    INTEGER,
        prtInLs2Connect   INTEGER,
        prtInLs2Group     INTEGER,
        prtInLs2Member    INTEGER,
        prtInLs2LinkTo    INTEGER,
        prtInLs2EnvAssign INTEGER
      }

prtInLs2CnfgIdx OBJECT-TYPE
      SYNTAX  INTEGER (1..255)
      ACCESS  read-only
      STATUS  mandatory
      DESCRIPTION
      "This attribute indicates the Idx of the Cnfg (1..100) being
       accessed.
       Idx  255 relates to the TmpCnfg"
      ::= {prtInLs2CnfgEntry 1}
-- In phase I only the values 1 (Cnfg1) and 255 (temp) are valid.

prtInLs2SltIdx OBJECT-TYPE
      SYNTAX  INTEGER
          {
       io1   (5),
       io2   (6),
       io3   (7),
       io4   (8),
       io5   (9),
       io6  (10),
       io7  (11),
       io8  (12),
       io9  (13),
       io10 (14),
       io11 (15),
       io12 (16)
       }
      ACCESS  read-only
      STATUS  mandatory
      DESCRIPTION
      "This attribute indicates a unique  slot  position where
       the card is inserted.
       In the ?004 Unit the entries io6(10)..io16) are not valid."
      ::= {prtInLs2CnfgEntry 2}

prtInLs2PrtIdx OBJECT-TYPE
      SYNTAX  INTEGER
          {
          inPrt1    (101),
    inPrt2    (102)
          }
      ACCESS  read-only
      STATUS  mandatory
      DESCRIPTION
      "This attribute indicates a unique internal port index."
      ::= {prtInLs2CnfgEntry 3}

prtInLs2Connect OBJECT-TYPE
      SYNTAX  INTEGER
              {
                no  (2),
                yes (3)
              }
      ACCESS  read-write
      STATUS  mandatory
      DESCRIPTION
      "This attribute indicates whether the port should be considered in
       any of the mux  algorithms. It also affects all the module
       considerations because the module has only one Internal
       interface which is the composite channel."
      ::= {prtInLs2CnfgEntry 4}

prtInLs2Group OBJECT-TYPE
      SYNTAX  INTEGER (1..12)
      ACCESS  read-write
      STATUS  mandatory
      DESCRIPTION
      "This attribute indicates the group number of the port.
       LS-2 internal ports with the same group number share the same Time slot of the main
       link"
      ::= {prtInLs2CnfgEntry 5}

prtInLs2Member OBJECT-TYPE
      SYNTAX  INTEGER (1..4)
      ACCESS  read-write
      STATUS  mandatory
      DESCRIPTION
      "This attribute indicates the group member id of the port.
       This parameter is for the automatic envelope assignment
       algorithm."
      ::= {prtInLs2CnfgEntry 6}

prtInLs2LinkTo OBJECT-TYPE
      SYNTAX  INTEGER
       {
       io1   (5),
       io2   (6),
       io3   (7),
       io4   (8),
       io5   (9),
       io6  (10),
       io7  (11),
       io8  (12),
       io9  (13),
       io10 (14),
       io11 (15),
       io12 (16)
       }
      ACCESS  read-write
      STATUS  deprecated
      DESCRIPTION
      "It indicates the slot of the main link card to which the
       LS2 card is mapped.
       STATUS  deprecated - this object is replaced by prtGenCnfgLinkToSlot
       and prtGenCnfgLinkToPort."
      ::= {prtInLs2CnfgEntry 7}

prtInLs2EnvAssign OBJECT-TYPE
      SYNTAX  INTEGER
       {
        auto    (2),
        manual  (3)
       }
      ACCESS  read-write
      STATUS  mandatory
      DESCRIPTION
      "Envelope assignment type."
      ::= {prtInLs2CnfgEntry 8}


--
-- Megaplex?000/?004 VC-2, VC-6, VC-2/R2, VC-Q TDM I/O family port.
-- (Vc2E&m,Vc2Fxs1Plar,Vc2Fxo1,Vc2Fxs2,Vc2Fxo2,Vc2Fxs3,Vc2Fxo3)
-- Vc6E&M, Vc6Fxo, Vc6Fxs, Vc6aE&M, Vc6aFxo, Vc6aFxs
-- Vc2/R2(Fxs)
-- VC-Q
-- VC-12, VC-12/6

prtVc2CnfgTable OBJECT-TYPE
      SYNTAX SEQUENCE OF PrtVc2CnfgEntry
      ACCESS not-accessible
      STATUS  mandatory
      DESCRIPTION
       "The write operation into the Table Objects is valid only
        to the TmpCnfg entry."
      ::= { cnfgPrtMux 5}

prtVc2CnfgEntry OBJECT-TYPE
      SYNTAX PrtVc2CnfgEntry
      ACCESS not-accessible
      STATUS mandatory
      DESCRIPTION "" INDEX {prtVc2CnfgIdx, prtVc2SltIdx, prtVc2PrtIdx }
      ::= { prtVc2CnfgTable 1}

PrtVc2CnfgEntry ::=
      SEQUENCE {
        prtVc2CnfgIdx       INTEGER,
        prtVc2SltIdx        INTEGER,
        prtVc2PrtIdx        INTEGER,

        prtExVc2Connect     INTEGER,
        prtExVc2TransGain   INTEGER,
        prtExVc2ReceiveGain INTEGER,

        prtExVc2Wire        INTEGER,
        prtExVc2CodingLaw   INTEGER,
        prtExVc2Sig         INTEGER,
        prtExVc2Oos         INTEGER,
        prtExVc2LinkTo      INTEGER,
        prtExVc2OperMode    INTEGER,
        prtExVc2SigProfile  INTEGER,
        prtExVc2CallEnable  INTEGER,
        prtExVc2R2Delay     INTEGER,
        prtExVc2CasStd      INTEGER,
        prtExVc2EchoCanceler INTEGER,
        prtExVc2IfType      INTEGER,
        prtExVc2Encoding    INTEGER,
        prtExVc2TxBitCode   OCTET STRING,
        prtExVc2RxBitOutput OCTET STRING,
		prtExVc2MeterRate   INTEGER,
		prtExVc2IfSignaling INTEGER,
        prtExVc2SeizeAck    INTEGER,
        prtExVc2EandMType   INTEGER
      }

prtVc2CnfgIdx OBJECT-TYPE
      SYNTAX  INTEGER  (1..255)
      ACCESS  read-only
      STATUS  mandatory
      DESCRIPTION
      "This attribute indicates the Idx of the Cnfg (1..100) being
       accessed.
       Idx  255 relates to the TmpCnfg"
      ::= {prtVc2CnfgEntry 1}
-- In phase I only the values 1 (Cnfg1) and 255 (temp) are valid.

prtVc2SltIdx OBJECT-TYPE
      SYNTAX  INTEGER
 {
       io1   (5),
       io2   (6),
       io3   (7),
       io4   (8),
       io5   (9),
       io6  (10),
       io7  (11),
       io8  (12),
       io9  (13),
       io10 (14),
       io11 (15),
       io12 (16),
       notApplicable (255)
 }
      ACCESS  read-only
      STATUS  mandatory
      DESCRIPTION
      "This attribute indicates a unique  slot  position where
       the card is inserted.
       For Stand Alone products like WR: notApplicable (255)"
      ::= {prtVc2CnfgEntry 2}

prtVc2PrtIdx OBJECT-TYPE
      SYNTAX  INTEGER
 {
       exPrt1    (1) ,
       exPrt2    (2) ,
       exPrt3    (3) ,
       exPrt4    (4) ,
       exPrt5    (5) ,
       exPrt6    (6) ,
       exPrt7    (7) ,
       exPrt8    (8) ,
       exPrt9    (9) ,
       exPrt10  (10) ,
       exPrt11  (11) ,
       exPrt12  (12)
 }
      ACCESS  read-only
      STATUS  mandatory
      DESCRIPTION
      "A unique identifier of the port, within the card."
      ::= {prtVc2CnfgEntry 3}

prtExVc2Connect OBJECT-TYPE
      SYNTAX  INTEGER
              {
                no  (2),
                yes (3)
              }
      ACCESS  read-write
      STATUS  mandatory
      DESCRIPTION
      "This attribute indicates whether the  port  should be
       considered in any of the mux algorithms."
      ::= {prtVc2CnfgEntry 4}

prtExVc2TransGain OBJECT-TYPE
      SYNTAX  INTEGER
      ACCESS  read-write
      STATUS  mandatory
      DESCRIPTION
      "Transmit gain in dBm.
       For ports of VC-6A and VC-6AG cards, the units will be 0.1dBm
       because valid values can be in 0.5dBm steps."
      ::= {prtVc2CnfgEntry 5}

prtExVc2ReceiveGain OBJECT-TYPE
      SYNTAX  INTEGER
      ACCESS  read-write
      STATUS  mandatory
      DESCRIPTION
      "Receive gain in dBm.
       For ports of VC-6A and VC-6AG cards, the units will be 0.1dBm
       because valid values can be in 0.5dBm steps."
      ::= {prtVc2CnfgEntry 6}

prtExVc2Wire OBJECT-TYPE
      SYNTAX  INTEGER
       {
          w2wire   (1),
          w4wire   (2),
		  notApplicable  (255)
       }
      ACCESS  read-write
      STATUS  mandatory
      DESCRIPTION
      "This object is equal for all the ports in the specific
       card because of HW limitations.
       For FXO & FXS this parameter is not applicable."
      ::= {prtVc2CnfgEntry 7}

prtExVc2CodingLaw OBJECT-TYPE
      SYNTAX  INTEGER
       {
          aLAW    (1),
          uLAW    (2)
       }
      ACCESS  read-write
      STATUS  mandatory
      DESCRIPTION
      "This attribute indicates the Method/Law for decoding/encoding the voice
       information.
       aLaw(1) is the standard Law for E1 links.
       uLaw(2) is the standard Law for T1 links.

       This object is equal for all the ports in the specific module because
       of HW limitations"
      ::= {prtVc2CnfgEntry 8}

prtExVc2Sig OBJECT-TYPE
      SYNTAX  INTEGER
       {
          noSignaling           (1),
          robbedBitMultiFrame   (2),
          chAssociatedE1        (3),
          robbedBitFrame        (4)
       }
      ACCESS  read-write
      STATUS  mandatory
      DESCRIPTION
      "This attribute indicates the method for decoding/encoding the signaling
       information(on/off hook).
       noSignaling        (1) - not using signaling (only voice).
       robbedBitMultiFrame(2) - is the standard method for T1 links and
                                proprietary method for E1 links.
       chAssociatedE1     (3) - is valid only for E1 G.732S links.
       robbedBitFrame     (4) - is proprietary method implimenting 7 bit for
                                the voice and 1 bit dedicated for signaling.

       This object is equal for all the ports in the specific module because
       of HW limitations."
      ::= {prtVc2CnfgEntry 9}

prtExVc2Oos OBJECT-TYPE
      SYNTAX  INTEGER
       {
          forcedIdle     (1),
          forcedBusy     (2),
          busyIdle       (3),
          idleBusy       (4),
          notApplicable  (5)
       }
      ACCESS  read-write
      STATUS  mandatory
      DESCRIPTION
      "This object is equal for all the ports in the specific card
       because of HW limitations"
      ::= {prtVc2CnfgEntry 10}

prtExVc2LinkTo OBJECT-TYPE
      SYNTAX  INTEGER
       {
       io1   (5),
       io2   (6),
       io3   (7),
       io4   (8),
       io5   (9),
       io6  (10),
       io7  (11),
       io8  (12),
       io9  (13),
       io10 (14),
       io11 (15),
       io12 (16),
	   notApplicable  (255)
       }
      ACCESS  read-write
      STATUS  deprecated
      DESCRIPTION
      "This attribute indicates the slot of the ML card to which
       the VC card is mapped.
       STATUS  deprecated - this object is replaced by prtGenCnfgLinkToSlot
       and prtGenCnfgLinkToPort."
      ::= {prtVc2CnfgEntry 11}

prtExVc2OperMode OBJECT-TYPE
      SYNTAX  INTEGER
       {
       normal          (2),
       unidirectRx     (3),
       broadcast       (4)
       }
      ACCESS  read-write
      STATUS  mandatory
      DESCRIPTION
      "This object indicates the operation mode of the port.
       normal = bi-directional (Tx/Rx)
       unidirectRx = unidirectional Rx.
       broadcast = Tx upon request."
      ::= {prtVc2CnfgEntry 12}


prtExVc2SigProfile OBJECT-TYPE
      SYNTAX  INTEGER
       {
       notApplicable   (1),
       manual          (2),
       p1              (3),
       p2              (4),
       p3Fxo3S3        (5),
       reversePolarity (6),	 --3RP
       meteringPulse   (7),	 --3MP
	   p4              (8)
       }
      ACCESS  read-write
      STATUS  mandatory
      DESCRIPTION
      "This object indicates the Signaling Profile of the port.
       notApplicable - for VC-2 family and when
                       prtExVc2Sig=noSignaling(1)
       p1 = profile 1
       p2 = profile 2
       p3 = profile 3 
       p4 = profile 4 "
      ::= {prtVc2CnfgEntry 13}

prtExVc2CallEnable OBJECT-TYPE
      SYNTAX  INTEGER
       {
       notApplicable (1),
       incoming      (2),
       outgoing      (3),
       both          (4)
       }
      ACCESS  read-write
      STATUS  mandatory
      DESCRIPTION
      "This object indicates the Enabled Call direction.
       notApplicable - for all cards except VC-2/R2.
       both     - incoming + outgoing."
      ::= {prtVc2CnfgEntry 14}

prtExVc2R2Delay OBJECT-TYPE
      SYNTAX  INTEGER
       {
       notApplicable (1),
       terrestrial   (2),
       satellite     (3)
       }
      ACCESS  read-write
      STATUS  mandatory
      DESCRIPTION
      "This object indicates the R2 Delay.
       notApplicable - for all cards except VC-2/R2."
      ::= {prtVc2CnfgEntry 15}

prtExVc2CasStd OBJECT-TYPE
      SYNTAX  INTEGER
       {
       notApplicable (1),
       r2Q422        (2),
       specialA      (3),
       specialB      (4),
	   specialC      (5),
	   specialD      (6),
	   specialE      (7),
   	   specialF      (8),
       specialG      (9)
       }
      ACCESS  read-write
      STATUS  mandatory
      DESCRIPTION
      "This object indicates the CAS (Channel Associated Signaling)
       Standard.
       notApplicable - for all cards except VC-2/R2."
      ::= {prtVc2CnfgEntry 16}

prtExVc2EchoCanceler OBJECT-TYPE
      SYNTAX  INTEGER
       {
       notApplicable (1),
          off    (2),
          on     (3)
       }
      ACCESS  read-write
      STATUS  mandatory
      DESCRIPTION
      "Echo canceler activation.
       notApplicable - for VC-2 and VC-6 cards."
      ::= {prtVc2CnfgEntry 17}

prtExVc2IfType OBJECT-TYPE
      SYNTAX  INTEGER
       {
       notApplicable (1),
       w2Em     (2),
       w4Em     (3),
       fxo      (4),
       fxs      (5)
       }
      ACCESS  read-write
      STATUS  mandatory
      DESCRIPTION
      "Interface Type."
      ::= {prtVc2CnfgEntry 18}

prtExVc2Encoding OBJECT-TYPE
      SYNTAX  INTEGER
       {
          notApplicable (1),
          pcm           (2),
          adpcm         (3)
       }
      ACCESS  read-write
      STATUS  mandatory
      DESCRIPTION
      "Voice Encoding Mode."
      ::= {prtVc2CnfgEntry 19}

prtExVc2TxBitCode OBJECT-TYPE
      SYNTAX  OCTET STRING
      ACCESS  read-write
      STATUS  mandatory
      DESCRIPTION
      "
       - - - For MP & FCD - - -

       This object represents 4 parameters, by 2 Octets :
       Tx D Bit Code-MSB nibble,
       Tx C Bit Code-    nibble,
       Tx B Bit Code-    nibble,
       Tx A Bit Code-LSB nibble.

       Each nibble:
    0 hex = 0000 = Not Applicable
       1 hex = 0001 = M lead
    2 hex = 0010 = M lead inverse
    3 hex = 0011 = Reverse Polarity
    4 hex = 0100 = Metering Pulse
    5 hex = 0101 = Forced 1
    6 hex = 0110 = Forced 0
    7-F hex - not used (invalid values)
       This object will be RO if prtExVc2SigProfile is NOT manual.
      
       
      - - - For WR II - - -

   This object represents the following 4 parameters by 2 Octets:
   1. On/Off hook signaling transmission mode from the FXS towards the T1/E1 (MSB nibble 1).
   2. Default signaling bits that are not in use (nibble 2).
   3. Ring Detection signaling transmission mode from the FXO towards the T1/E1(nibble 3).
   4. M (Mouth) Signaling transmission mode from the E&M towards the T1/E1(LSB nibble 4). 

      Each nibble:
	---------------------------------------------------------------------------------------
	Value          On/Off Hook       Default sig.      Ring Detect.        M (Mouth)
	---------------------------------------------------------------------------------------
    0 hex = 0000   Not Applicable    Not Applicable.  Not Applicable	   Not Applicable
    1 hex = 0001   Tx A bit			 Values 1-3 are	  Tx A bit			   Tx A bit
    2 hex = 0010   Tx A bit inverse	 for On/Off Hook  Tx A bit inv.	  	   Tx A bit inv.
    3 hex = 0011   Tx B bit			 A,B,A Inv,B Inv. Tx B bit			   Tx B bit
    4 hex = 0100   Tx B bit inverse	 Values 4-7 are	  Tx B bit inv.		   Tx B bit inv.
    5 hex = 0101   not Used-invalid	 for On/Off Hook  not Used-invalid	   not Used-invalid
    6 hex = 0110   not Used-invalid	 A, A Inverse.	  not Used-invalid 	   not Used-invalid
    7 hex = 0111   not Used-invalid			 		  not Used-invalid	   not Used-invalid	 
    8 hex = 1000   not Used-invalid	 Values 8-11 are  not Used-invalid	   not Used-invalid
    9 hex = 1001   not Used-invalid	 for On/Off Hook  not Used-invalid	   not Used-invalid
	A hex = 1010   not used-invalid	 B, B Inverse.	  not Used-invalid	   not Used-invalid
	B hex = 1011   not used-invalid	 The Bits order:  not Used-invalid	   not Used-invalid
    C-F hex 	   not used-invalid	 ABCD			  not Used-invalid	   not Used-invalid
   

    Default value: 11 11 "
      ::= {prtVc2CnfgEntry 20}

prtExVc2RxBitOutput OBJECT-TYPE
      SYNTAX  OCTET STRING
      ACCESS  read-write
      STATUS  mandatory
      DESCRIPTION
      "
       - - - For MP & FCD - - -
       This object represents 3  parameters by 2 Octets:
       Spare       -MSB nibble, always=0 hex
       E Lead Output          -    nibble,
       Reverse Polarity Output-    nibble,
       Metering Pulse Output  -LSB nibble.

       Each nibble:
    0 hex = 0000 = Not Applicable
       1 hex = 0001 = Rx A bit
    2 hex = 0010 = Rx A bit inverse
    3 hex = 0011 = Rx B bit
    4 hex = 0100 = Rx B bit inverse
    5 hex = 0101 = Rx C bit
    6 hex = 0110 = Rx C bit inverse
    7 hex = 0111 = Rx D bit
    8 hex = 1000 = Rx D bit inverse
    9 hex = 1001 = none
    A-F hex - not used (invalid values)
       This object will be RO if prtExVc2SigProfile is NOT manual.
       
             
      - - - For WR II - - -

   This object represents the following 2 parameters in 1 Octet:
   1. On/Off hook signaling receive mode from the T1/E1 into the FXS/FXO (MSB nibble 1).
   2. E (Ear) Signaling receive mode from the T1/E1 into the E&M (LSB nibble 2). 

      Each nibble:
	---------------------------------------------------------------------------------------
	Value          On/Off Hook       E (Ear)
	---------------------------------------------------------------------------------------
    0 hex = 0000   Not Applicable    Not Applicable
    1 hex = 0001   Rx A bit			 Rx A bit
    2 hex = 0010   Rx A bit inverse	 Rx A bit inverse
    3 hex = 0011   Rx B bit			 Rx B bit
    4 hex = 0100   Rx B bit inverse	 Rx B bit inverse
    5-F hex 	   not used-invalid	 not Used-invalid
   

    Default value: 11 "

      ::= {prtVc2CnfgEntry 21}

prtExVc2MeterRate OBJECT-TYPE
      SYNTAX  INTEGER
      {
        notApplicable(1),
        r16Khz (2),
        r12Khz (3)
      }
      ACCESS  read-write
      STATUS  mandatory
      DESCRIPTION
      "This entry is applicable only for VC-6A/FXO and VC-6A/FXS.
       Meter Rate means rate of Call Meter in Public Phones, in KHz units.
       Must be the same for all card's ports."
      ::= {prtVc2CnfgEntry 22}

prtExVc2IfSignaling OBJECT-TYPE
      SYNTAX  INTEGER
      {
        notApplicable(1),
        loopStart    (2),
		groundStart  (3)
      }
      ACCESS  read-write
      STATUS  mandatory
      DESCRIPTION
      "This entry is applicable only for VC-6A and VC-6AG cards.
       Interface Analog Signaling.
       Must be the same for all card's ports.
       loopStart - for the usual trunk/phone types.
       groundStart - for trunks that need Ground signaling (applicable
       for VC-6AG cards."
      ::= {prtVc2CnfgEntry 23}

prtExVc2SeizeAck OBJECT-TYPE
      SYNTAX INTEGER
      {
      notApplicable (1),
	  no  (2),
      yes (3)
      }
      ACCESS  read-write
      STATUS  mandatory
      DESCRIPTION
      "This parameter shows whether the device will acknowledge
       a seize signal (On/Off Hook).
       When the value is set to yes(3) & the device receives an on/off hook signal
       it will transmit back an on/off hook signal.
	   When the value is set to no(2) & the device receives an on/off hook signal
       it will NOT transmit back an on/off hook signal.
       
       Default value for WR FXO: no(2)."
       ::= {prtVc2CnfgEntry 24}

prtExVc2EandMType OBJECT-TYPE
       SYNTAX INTEGER
	   {
       notApplicable (1),
	   type1 (2),
       type2 (3),
       type3 (4),
       type5 (5)  -- SSDC5  
       }
      ACCESS  read-write
      STATUS  mandatory
      DESCRIPTION
      "This is the signaling type on the E&M analog side.
       The analog signaling includes voltage, no. of pins and other parameters."
       ::= {prtVc2CnfgEntry 25}


--
-- Megaplex?000/?004 port specific config for HS(TDM) modules
-- HS-2,HS-3,HS-Q, HS-Q/SC, HS-6, HS-12
--
prtHsfCnfgTable OBJECT-TYPE
      SYNTAX SEQUENCE OF PrtHsfCnfgEntry
      ACCESS not-accessible
      STATUS  mandatory
      DESCRIPTION
       "The write operation into the Table Objects is valid only
        to the TmpCnfg entry."
      ::= { cnfgPrtMux 6}

prtHsfCnfgEntry OBJECT-TYPE
      SYNTAX PrtHsfCnfgEntry
      ACCESS not-accessible
      STATUS mandatory
      DESCRIPTION "" INDEX {prtHsfCnfgIdx, prtHsfSltIdx, prtHsfPrtIdx }
      ::= { prtHsfCnfgTable 1}

PrtHsfCnfgEntry ::=
      SEQUENCE {
        prtHsfCnfgIdx       	INTEGER,
        prtHsfSltIdx        	INTEGER,
        prtHsfPrtIdx        	INTEGER,
        prtExHsfConnect     	INTEGER,
        prtExHsfRate        	INTEGER,
        prtExHsfClkMode     	INTEGER,
        prtExHsfCts        	 	INTEGER,
        prtExHsfFifoSize    	INTEGER,
        prtExHsfLinkTo      	INTEGER,
  		prtExHsfOperMode    	INTEGER,
  		prtExHsfInbandLoopback 	INTEGER,
		prtExHsfClkPolarity     INTEGER
      }

prtHsfCnfgIdx OBJECT-TYPE
      SYNTAX  INTEGER (1..255)
      ACCESS  read-only
      STATUS  mandatory
      DESCRIPTION
      "This attribute indicates the Idx of the Cnfg (1..100) being
       accessed.
       Idx  255 relate to the TmpCnfg. "
      ::= {prtHsfCnfgEntry 1}
-- In phase I only the values 1 (Cnfg1) and 255 (temp) are valid.

prtHsfSltIdx OBJECT-TYPE
      SYNTAX  INTEGER
          {
       io1   (5),
       io2   (6),
       io3   (7),
       io4   (8),
       io5   (9),
       io6  (10),
       io7  (11),
       io8  (12),
       io9  (13),
       io10 (14),
       io11 (15),
       io12 (16)
       }
      ACCESS  read-only
      STATUS  mandatory
      DESCRIPTION
      "This attribute indicates a unique  slot  position where
       the card is inserted.
       In the ?004 Unit the entries io6(10)..io16) are not valid."
      ::= {prtHsfCnfgEntry 2}

prtHsfPrtIdx OBJECT-TYPE
      SYNTAX  INTEGER
          {
          exPrt1    (1) ,
          exPrt2    (2) ,
          exPrt3    (3) ,
         exPrt4    (4) ,
         exPrt5    (5) ,
         exPrt6    (6) ,
         exPrt7    (7) ,
         exPrt8    (8) ,
         exPrt9    (9) ,
         exPrt10  (10) ,
         exPrt11  (11) ,
         exPrt12  (12)
          }
      ACCESS  read-only
      STATUS  mandatory
      DESCRIPTION
      "This attribute indicates a unique  external port index.
        Hs2 has only two ports (exPrt1,exPrt2).
        Hs3 has three ports (exPrt1,exPrt2,exPrt3).
        Hsq and hsqN has four ports.
        Hs6 has six external ports.
        Hs12 has twelve external ports."
      ::= {prtHsfCnfgEntry 3}

prtExHsfConnect OBJECT-TYPE
      SYNTAX  INTEGER
              {
                no  (2),
                yes (3)
              }
      ACCESS  read-write
      STATUS  mandatory
      DESCRIPTION
      "This attribute indicates whether the port should be
       considered in any of the mux algorithms."
      ::= {prtHsfCnfgEntry 4}


prtExHsfRate     OBJECT-TYPE
      SYNTAX  INTEGER
       {
        r1x56eq56Kbps    (1),
        r1x64eq64Kbps    (2),
        r2x56eq112Kbps   (3),
        r2x64eq128Kbps   (4),
        r3x56eq168Kbps   (5),
        r3x64eq192Kbps   (6),
        r4x56eq224Kbps   (7),
        r4x64eq256Kbps   (8),
        r5x56eq280Kbps   (9),
        r5x64eq320Kbps  (10),
        r6x56eq336Kbps  (11),
        r6x64eq384Kbps  (12),
        r7x56eq392Kbps  (13),
        r7x64eq448Kbps  (14),
        r8x56eq448Kbps  (15),
        r8x64eq512Kbps  (16),
        r9x56eq504Kbps  (17),
        r9x64eq576Kbps  (18),
        r10x56eq560Kbps (19),
        r10x64eq640Kbps (20),
        r11x56eq616Kbps (21),
        r11x64eq704Kbps (22),
        r12x56eq672Kbps (23),
        r12x64eq768Kbps (24),
        r13x56eq728Kbps (25),
        r13x64eq832Kbps (26),
        r14x56eq784Kbps (27),
        r14x64eq896Kbps (28),
        r15x56eq840Kbps (29),
        r15x64eq960Kbps (30),
        r16x56eq896Kbps (31),
        r16x64eq1024Kbps(32),
        r17x56eq952Kbps (33),
        r17x64eq1088Kbps(34),
        r18x56eq1008Kbps(35),
        r18x64eq1152Kbps(36),
        r19x56eq1064Kbps(37),
        r19x64eq1216Kbps(38),
        r20x56eq1120Kbps(39),
        r20x64eq1280Kbps(40),
        r21x56eq1176Kbps(41),
        r21x64eq1344Kbps(42),
        r22x56eq1232Kbps(43),
        r22x64eq1408Kbps(44),
        r23x56eq1288Kbps(45),
        r23x64eq1472Kbps(46),
        r24x56eq1344Kbps(47),
        r24x64eq1536Kbps(48),
        r25x56eq1400Kbps(49),
        r25x64eq1600Kbps(50),
        r26x56eq1456Kbps(51),
        r26x64eq1664Kbps(52),
        r27x56eq1512Kbps(53),
        r27x64eq1728Kbps(54),
        r28x56eq1568Kbps(55),
        r28x64eq1792Kbps(56),
        r29x56eq1624Kbps(57),
        r29x64eq1856Kbps(58),
        r30x56eq1680Kbps(59),
        r30x64eq1920Kbps(60),
        r31x56eq1736Kbps(61),
        r31x64eq1984Kbps(62),
  r32Kbps         (63)
       }
      ACCESS  read-write
      STATUS  mandatory
      DESCRIPTION
      "This attribute indicates the port speed. "
      ::= {prtHsfCnfgEntry 5}

prtExHsfClkMode OBJECT-TYPE
      SYNTAX  INTEGER
       {
          dce     (1),
          ext-dce (2),
          dte     (3),
    none    (4)
       }
      ACCESS  read-write
      STATUS  mandatory
      DESCRIPTION
      "This attribute indicates a unique port operation clock mode."
      ::= { prtHsfCnfgEntry 6}

prtExHsfCts OBJECT-TYPE
      SYNTAX  INTEGER
       {
     notApplicable (1),
     on            (2),
     rts           (3)
       }
      ACCESS  read-write
      STATUS  mandatory
      DESCRIPTION
      "This attribute indicates a unique CTS control line
       operation mode."
      ::= {prtHsfCnfgEntry 7}

prtExHsfFifoSize OBJECT-TYPE
      SYNTAX  INTEGER
       {
     auto     (2),
           s16bits  (3),
           s30bits  (4),
           s52bits  (5),
           s72bits  (6)
       }
      ACCESS  read-write
      STATUS  mandatory
      DESCRIPTION
      "Size in bits."
      ::= {prtHsfCnfgEntry 8}

prtExHsfLinkTo  OBJECT-TYPE
      SYNTAX  INTEGER
       {
       io1   (5),
       io2   (6),
       io3   (7),
       io4   (8),
       io5   (9),
       io6  (10),
       io7  (11),
       io8  (12),
       io9  (13),
       io10 (14),
       io11 (15),
       io12 (16)
       }
      ACCESS  read-write
      STATUS  deprecated
      DESCRIPTION
      "This attribute indicates a slot of Main Link module, that the
       port is linked to. This object is the same for all the
       ports in the specific card because of HW limitations.
       STATUS  deprecated - this object is replaced by prtGenCnfgLinkToSlot
       and prtGenCnfgLinkToPort."
      ::= {prtHsfCnfgEntry 9}

prtExHsfOperMode OBJECT-TYPE
      SYNTAX  INTEGER
       {
       normal          (2),
       unidirectRx     (3),
    broadcast       (4)
       }
      ACCESS  read-write
      STATUS  mandatory
      DESCRIPTION
      "This object indicates the operation mode of the port.
       normal = bi-directional (Tx/Rx)
       unidirectRx = unidirectional Rx.
       broadcast = Tx upon request."
      ::= {prtHsfCnfgEntry 10}


prtExHsfInbandLoopback OBJECT-TYPE
      SYNTAX  INTEGER
       {
       notApplicable   (1),
       disabled        (2),
       ft1Enabled      (3)
       }
      ACCESS  read-write
      STATUS  mandatory
      DESCRIPTION
      "This object indicates if Inband Loopback from the Network
       should be enabled or disabled."
      ::= {prtHsfCnfgEntry 11}

prtExHsfClkPolarity OBJECT-TYPE
      SYNTAX  INTEGER
       {
       notApplicable   (1),
       normal          (2),
       invert          (3)
       }
      ACCESS  read-write
      STATUS  mandatory
      DESCRIPTION
      "This object indicates the clock polarity.
       For FCD-M this object will be applicable only for the fixed HS port
       (the fixed port on the device)."
      ::= {prtHsfCnfgEntry 12}


--
-- Megaplex?000/?004 Hs-4/1(HS4T1) HS-4/2(HS4E1) port configuration
--
--prtExHs4CnfgTable   OBJECT IDENTIFIER ::= {prtHs4Cnfg 1}
--prtExHs4TsCnfgTable OBJECT IDENTIFIER ::= {prtHs4Cnfg 2}

prtExHs4CnfgTable OBJECT-TYPE
      SYNTAX SEQUENCE OF PrtExHs4CnfgEntry
      ACCESS not-accessible
      STATUS  mandatory
      DESCRIPTION
       "The write operation into the Table Objects is valid only
        to the TmpCnfg entry."
      ::= {prtHs4Cnfg 1}

prtExHs4CnfgEntry OBJECT-TYPE
      SYNTAX PrtExHs4CnfgEntry
      ACCESS not-accessible
      STATUS mandatory
      DESCRIPTION "" INDEX {prtExHs4CnfgIdx, prtExHs4SltIdx,  prtExHs4PrtIdx }
      ::= { prtExHs4CnfgTable 1}

PrtExHs4CnfgEntry ::=
      SEQUENCE {
        prtExHs4CnfgIdx     INTEGER,
        prtExHs4SltIdx      INTEGER,
        prtExHs4PrtIdx      INTEGER,

     prtExHs4Connect     INTEGER,
     prtExHs4LineType    INTEGER,
     prtExHs4LineCode    INTEGER,
     prtExHs4LineLen     INTEGER,
     prtExHs4RestoreT    INTEGER,
     prtExHs4OosSig      INTEGER,
     prtExHs4OosCode     INTEGER,
     prtExHs4IdleCode    INTEGER,
     prtExHs4MfClkSrcSlt INTEGER,
     prtExHs4MfClkSrcPrt INTEGER
      }

prtExHs4CnfgIdx OBJECT-TYPE
      SYNTAX  INTEGER  (1..255)
      ACCESS  read-only
      STATUS  mandatory
      DESCRIPTION
      "This attribute indicates the Idx of the Cnfg (1..100) being
       accessed.
       Idx  255 relates to the TmpCnfg"
      ::= {prtExHs4CnfgEntry 1}
-- In phase I only the values 1 (Cnfg1) and 255 (temp) are valid.

prtExHs4SltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      ACCESS  read-only
      STATUS  mandatory
      DESCRIPTION
      "This attribute indicates a unique  slot  position where
       the card is inserted."
      ::= {prtExHs4CnfgEntry 2}

prtExHs4PrtIdx OBJECT-TYPE
      SYNTAX  INTEGER
     {
       exPrt1    (1)
     }
      ACCESS  read-only
      STATUS  mandatory
      DESCRIPTION
      "A unique identifier of the port, within the card."
      ::= {prtExHs4CnfgEntry 3}

prtExHs4Connect OBJECT-TYPE
      SYNTAX  INTEGER
       {
  no  (2),
  yes (3)
       }
      ACCESS  read-write
      STATUS  mandatory
      DESCRIPTION
      "This attribute indicates whether the port should be
       considered in any of the mux  algorithm. It also affects
       all the module considerations because the card has only
       one external (physical) interface."
      ::= {prtExHs4CnfgEntry 4}

prtExHs4LineType    OBJECT-TYPE
      SYNTAX  INTEGER
       {
  esfT1          (2), --> dsx1ESF
  sfT1           (3), --> dsx1D4
  g732nE1        (4), --> dsx1E1
  g732nE1CRC    (5), --> dsx1E1-CRC
  g732sE1        (6), --> dsx1E1-MF
  g732sE1CRC    (7)  --> dsx1E1-MF-CRC
       }
      ACCESS  read-write
      STATUS  mandatory
      DESCRIPTION
      "This attribute is the line type parameter for T1/E1
       interface.
       The user should select only the parameters relevant to the
       specific card:
       T1 line code parameters for the HS-4/1 and
       E1 line code parameters for the HS-4/2.
       This parameter has the same values as dsx1LineType in T1/E1
       MIB (RFC-1406). The parameters in dsx1LineType are:
      other          (1)
      dsx1ESF        (2)
      dsx1D4         (3)
      dsx1E1         (4)
      dsx1E1-CRC     (5)
      dsx1E1-MF      (6)
      dsx1E1-MF-CRC  (7)"
      ::= {prtExHs4CnfgEntry 5}

prtExHs4LineCode OBJECT-TYPE
      SYNTAX  INTEGER
       {
  b7T1   (1),  --> dsx1JBZS
  b8zsT1 (2),  --> dsx1B8ZS
        hdb3E1 (4)   --> dsx1HDB3
       }
      ACCESS  read-write
      STATUS  mandatory
      DESCRIPTION
      "This attribute is the line code parameter used for T1/E1
       interface.
       The user should select only the parameters relevant to the
       specific card:
       T1 line code parameters for the MPH.1/T1 and
       E1 line code parameters for the MPH.1/E1.
       This parameter has the same values as dsx1LineCoding in T1/E1
       MIB (RFC-1406).  The parameters in dsx1LineCoding are:
     dsx1JBZS  (1)
     dsx1B8ZS  (2)
     dsx1HDB3  (3)
     dsx1ZBTSI (4)
     dsx1AMI   (5)
     other     (6)"
      ::= {prtExHs4CnfgEntry 6}

prtExHs4LineLen  OBJECT-TYPE
      SYNTAX  INTEGER
       {
  unknown   (1),
        len0p133ft   (2),
        len134p266ft (3),
        len267p399ft (4),
        len400p533ft (5),
        len534p655ft (6),
        fcc68    (7)
       }
      ACCESS  read-write
      STATUS  mandatory
      DESCRIPTION
      "This attribute is the line length parameter used only for
       T1 interfaces.
       len399p533ft=len-399-533ft "
      ::= {prtExHs4CnfgEntry 7}

prtExHs4RestoreT OBJECT-TYPE
      SYNTAX  INTEGER
       {
        restoreT1secFast      (2),
        restoreT10sec62411    (3),
  ccittE1       (4)
       }
      ACCESS  read-write
      STATUS  mandatory
      DESCRIPTION
      "Time passing from the disappearance of the loss of
       synchronization condition (red alarm), to the restoration
       of normal service."
      ::= {prtExHs4CnfgEntry 8}

prtExHs4OosSig   OBJECT-TYPE
      SYNTAX  INTEGER
       {
        notsupported  (2),
        forcedIdle    (3),
        forcedBusy    (4),
        busyIdle      (5),
        idleBusy      (6)
       }
      ACCESS  read-write
      STATUS  mandatory
      DESCRIPTION
      "Out of Service signal type."
      ::= {prtExHs4CnfgEntry 9}

prtExHs4OosCode  OBJECT-TYPE
      SYNTAX  INTEGER
          {
          notsupported (2),
            oosCode00H        (3),
            oosCode1aH        (4),
            oosCode54H        (5),
            oosCode7eH        (6),
            oosCode7fH        (7),
            oosCode98H        (8),
            oosCode9eH        (9),
            oosCoded5H        (10),
            oosCodee4H        (11),
            oosCodeffH        (12)
          }
      ACCESS  read-write
      STATUS  mandatory
      DESCRIPTION
      "OOS Code"
      ::= {prtExHs4CnfgEntry 10}

prtExHs4IdleCode  OBJECT-TYPE
      SYNTAX  INTEGER
      ACCESS  read-write
      STATUS  mandatory
      DESCRIPTION
      " Type value(00 - FF HEX), excluding 0H,8H,10H,12H,21H,24H,
        42H,49H,84H,92H"
      ::= {prtExHs4CnfgEntry 11}

prtExHs4MfClkSrcSlt  OBJECT-TYPE
      SYNTAX  INTEGER
       {
          local (2),
       io1   (5),
       io2   (6),
       io3   (7),
       io4   (8),
       io5   (9),
       io6  (10),
       io7  (11),
       io8  (12),
       io9  (13),
       io10 (14),
       io11 (15),
       io12 (16)
       }
      ACCESS  read-write
      STATUS  mandatory
      DESCRIPTION
"This attribute indicates whether the port Tx is multiframe
synchronized with Rx multiframe of another port and the slot position of that port.
This opration is required in order to bypass signaling of PCM
voice channels.
When its value is Local(2) there is no meaning to 'prtExHs4MfClkSrcPrt'
parameter.
In the ?004 Unit the entries io6(10)..io16) are not valid"
      ::= {prtExHs4CnfgEntry 12}

prtExHs4MfClkSrcPrt  OBJECT-TYPE
      SYNTAX  INTEGER
      {
       exPrt1    (1),
       exPrt2    (2),
       inPrt1  (101)
      }
      ACCESS  read-write
      STATUS  mandatory
      DESCRIPTION
      "A unique number to identify a port position in the mux if the
       MultiFrame clock source is valid (YES).
       inPrt1 - for MTML-H/E1 cards."
      ::= {prtExHs4CnfgEntry 13}

--
-- Hs4 Time Slot Config Table
--
prtExHs4TsCnfgTable OBJECT-TYPE
     SYNTAX SEQUENCE OF PrtExHs4TsEntry
     ACCESS not-accessible
     STATUS  mandatory
     DESCRIPTION
      "The write operation into the Table Objects is valid only
       to the TmpCnfg entry."
     ::= {prtHs4Cnfg 2}

prtExHs4TsEntry OBJECT-TYPE
      SYNTAX PrtExHs4TsEntry
      ACCESS not-accessible
      STATUS mandatory
      DESCRIPTION "" INDEX {prtExHs4TsCnfgIdx, prtExHs4TsSltIdx, prtExHs4TsPrtIdx, prtExHs4TsIdx }
      ::= { prtExHs4TsCnfgTable 1}

PrtExHs4TsEntry ::=
      SEQUENCE {
      prtExHs4TsCnfgIdx        INTEGER,
      prtExHs4TsSltIdx         INTEGER,
      prtExHs4TsPrtIdx         INTEGER,
      prtExHs4TsIdx            INTEGER,
      prtExHs4TsIConSlot       INTEGER,
      prtExHs4TsIConPrt        INTEGER,
      prtExHs4TsIConTs         INTEGER
      }

prtExHs4TsCnfgIdx OBJECT-TYPE
      SYNTAX  INTEGER  (1..255)
      ACCESS  read-only
      STATUS  mandatory
      DESCRIPTION
      "This attribute indicates the Idx of the Cnfg (1..100) being
       accessed.
       Idx 255 relates to the TmpCnfg. "
      ::= { prtExHs4TsEntry 1}
-- In phase I only the values 1 (Cnfg1) and 255 (temp) are valid.

prtExHs4TsSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      ACCESS  read-only
      STATUS  mandatory
      DESCRIPTION
      "This attribute indicates a unique  slot  position where
       the card is inserted.
       In the ?004 Unit the entries io6(10)..io16) are not valid"
      ::= { prtExHs4TsEntry 2}

prtExHs4TsPrtIdx OBJECT-TYPE
      SYNTAX  INTEGER
 {
          exPrt1    (1)
       }
      ACCESS  read-only
      STATUS  mandatory
      DESCRIPTION
      "This attribute indicates a unique  port number.
       Hs4/T1 and Hs4/T1 cards have only one external interface."
      ::= { prtExHs4TsEntry 3}

prtExHs4TsIdx OBJECT-TYPE
      SYNTAX  INTEGER
      ACCESS  read-only
      STATUS  mandatory
      DESCRIPTION
      "This attribute indicates a unique time slot  position.
       The valid time slots are:
       1..24 for T1 Card and
       1..31 for E1 interface.
       In G732S-E1 lines, time slot 16 is not valid for data,
       it is dedicated to multiframe synchronization bits
       and voice signaling."
      ::= { prtExHs4TsEntry 4}

prtExHs4TsIConSlot OBJECT-TYPE
      SYNTAX  INTEGER
       {
       noConnect (2),
          io1       (5),
          io2       (6),
          io3       (7),
          io4       (8),
          io5       (9),
          io6      (10),
          io7      (11),
          io8      (12),
          io9      (13),
          io10     (14),
          io11     (15),
          io12     (16),
    split   (100)
       }
      ACCESS  read-write
      STATUS  mandatory
      DESCRIPTION
      "This attribute indicates whether the specified time slot is
       connected/routed internally in the Agent and to which card
       it is connected.
       In the ?004 Unit the entries io6(10)..io16) are not valid.
    split - will be used when the Src TS is connected to more
               than one slot OR more than one port (each needing
               less than a whole TS)."
      ::= {prtExHs4TsEntry 5}

prtExHs4TsIConPrt OBJECT-TYPE
      SYNTAX  INTEGER
       {
       exPrt1    (1) ,
       exPrt2    (2) ,
       exPrt3    (3) ,
       exPrt4    (4) ,
       exPrt5    (5) ,
       exPrt6    (6) ,
       exPrt7    (7) ,
       exPrt8    (8) ,
       exPrt9    (9) ,
       exPrt10  (10) ,
       exPrt11  (11) ,
       exPrt12  (12) ,
       noConnect (100)
       }
      ACCESS  read-write
      STATUS  mandatory
      DESCRIPTION
      "This attribute indicates the internally (In Mux)
       connected/routed port."
      ::= {prtExHs4TsEntry 6}

prtExHs4TsIConTs OBJECT-TYPE
      SYNTAX  INTEGER
      ACCESS  read-write
      STATUS  mandatory
      DESCRIPTION
      "This attribute indicates a unique time slot  position.
       The valid time slots are:
       1..24 for T1 Module and
       1..31 for E1 interface.
       In G732S-E1 lines time slot 16 is not valid for data,
       it is dedicated for multiframe synchronization bits
       and voice signaling."
      ::= { prtExHs4TsEntry 7}

--
-- Megaplex?000/?004 Hs-U port configuration
--
--prtExHsiCnfgTable   OBJECT IDENTIFIER ::= {prtHsiCnfg 1}

prtExHsiCnfgTable OBJECT-TYPE
      SYNTAX SEQUENCE OF PrtExHsiCnfgEntry
      ACCESS not-accessible
      STATUS  mandatory
      DESCRIPTION
       "The write operation into the Table Objects is valid only
        to the TmpCnfg entry."
      ::= {prtHsiCnfg 1}

prtExHsiCnfgEntry OBJECT-TYPE
      SYNTAX PrtExHsiCnfgEntry
      ACCESS not-accessible
      STATUS mandatory
      DESCRIPTION "" INDEX {prtExHsiCnfgIdx, prtExHsiSltIdx,  prtExHsiPrtIdx }
      ::= { prtExHsiCnfgTable 1}

PrtExHsiCnfgEntry ::=
      SEQUENCE {
        prtExHsiCnfgIdx     INTEGER,
        prtExHsiSltIdx      INTEGER,
        prtExHsiPrtIdx      INTEGER,

        prtExHsiConnect     INTEGER,
        prtExHsiRate        INTEGER,
        prtExHsiLinkTo      INTEGER,
        prtExHsiInterface   INTEGER,
		prtExHsiActType		INTEGER
      }

prtExHsiCnfgIdx OBJECT-TYPE
      SYNTAX  INTEGER  (1..255)
      ACCESS  read-only
      STATUS  mandatory
      DESCRIPTION
      "This attribute indicates the Idx of the Cnfg (1..100) being
       accessed.
       Idx 255 relates to the TmpCnfg"
      ::= {prtExHsiCnfgEntry 1}
-- In phase I only the values 1 (Cnfg1) and 255 (temp) are valid.

prtExHsiSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      ACCESS  read-only
      STATUS  mandatory
      DESCRIPTION
      "This attribute indicates a unique  slot  position where
       the card is inserted."
      ::= {prtExHsiCnfgEntry 2}

prtExHsiPrtIdx OBJECT-TYPE
      SYNTAX  INTEGER
     {
          exPrt1    (1),
          exPrt2    (2),
          exPrt3    (3),
          exPrt4    (4),
          exPrt5    (5),
          exPrt6    (6),
          exPrt7    (7),
          exPrt8    (8),
          exPrt9    (9),
          exPrt10  (10),
          exPrt11  (11),
          exPrt12  (12)
        }
      ACCESS  read-only
      STATUS  mandatory
      DESCRIPTION
      "A unique prt identifier within the card."
      ::= {prtExHsiCnfgEntry 3}

prtExHsiConnect OBJECT-TYPE
      SYNTAX  INTEGER
       {
        no  (2),
        yes (3),
		v51 (4)
       }
      ACCESS  read-write
      STATUS  mandatory
      DESCRIPTION
      "This attribute indicates whether the port should be considered in
       any of the mux  algorithms.
       v51 - this port is connected to a V5.1 interface. All rest of the
             values will be 'notApplicable' in this case. V5.1 MIB will be
             used instead."
      ::= {prtExHsiCnfgEntry 4}

prtExHsiRate    OBJECT-TYPE
      SYNTAX  INTEGER
       {
          r600bps   (2),
          r1200bps  (3),
          r2400bps  (4),
          r4800bps  (5),
          r9600bps  (6),
          r19200bps (7),
          r38400bps (8),
          r48kbps   (9),
          r56kbps  (10),
          r64kbps  (11),
          r128kbps (12),
    notApplicable (255)
       }
      ACCESS  read-write
      STATUS  mandatory
      DESCRIPTION
      "This attribute indicates the port speed."
      ::= {prtExHsiCnfgEntry 5}

prtExHsiLinkTo  OBJECT-TYPE
      SYNTAX  INTEGER
       {
       io1   (5),
       io2   (6),
       io3   (7),
       io4   (8),
       io5   (9),
       io6  (10),
       io7  (11),
       io8  (12),
       io9  (13),
       io10 (14),
       io11 (15),
       io12 (16)
       }
      ACCESS  read-write
      STATUS  deprecated
      DESCRIPTION
      "It indicates the slot of the main link card to which the HS-? card
       is mapped.
       STATUS  deprecated - this object is replaced by prtGenCnfgLinkToSlot
       and prtGenCnfgLinkToPort."
      ::= {prtExHsiCnfgEntry 6}

prtExHsiInterface  OBJECT-TYPE
      SYNTAX  INTEGER
       {
       lt   (1),
       nt   (2),
       te   (3),
	   lt1  (4),
    notApplicable (255)
       }
      ACCESS  read-write
      STATUS  mandatory
      DESCRIPTION
      "It indicates the interface type:
       lt = line termination
       nt = network termination
       te = terminal equipment.
	   lt1 - for ASMi-31 connection (not ISDN)
       For HS-U/I and HS-U/1 only 'lt' and 'nt' are applicable.
       For HS-S , only 'te' and 'nt' are applicable.
       For HS-U, this object is not applicable.
       For HS-U6, HS-U12, are applicable: 'lt'=lt-i,'nt'=nt-i, lt1."
      ::= {prtExHsiCnfgEntry 7}

prtExHsiActType  OBJECT-TYPE
      SYNTAX  INTEGER
       {
       notApplicable (1),
       type1 (2),
       type2 (3),
	   type3 (4)
       }
      ACCESS  read-write
      STATUS  mandatory
      DESCRIPTION
      "It indicates the Activation Type. Activation Type is the Synchronization
	   type towards the PBX. It is applicable only when prtExHsiInterface=nt.
	   notApplicable - for cards that do not support this object, or when 
	   prtExHsiInterface is NOT nt."
      ::= {prtExHsiCnfgEntry 8}


--prtInHsiCnfgTable   OBJECT IDENTIFIER ::= {prtHsiCnfg 2}
--This table is not applicable for HS-U card type

prtInHsiCnfgTable OBJECT-TYPE
      SYNTAX SEQUENCE OF PrtInHsiCnfgEntry
      ACCESS not-accessible
      STATUS  mandatory
      DESCRIPTION
       "The write operation into the Table Objects is valid only
        to the TmpCnfg entry.
        This table is not applicable for HS-U card type."
      ::= {prtHsiCnfg 2}

prtInHsiCnfgEntry OBJECT-TYPE
      SYNTAX PrtInHsiCnfgEntry
      ACCESS not-accessible
      STATUS mandatory
      DESCRIPTION "" INDEX {prtInHsiCnfgIdx, prtInHsiSltIdx,  prtInHsiPrtIdx }
      ::= { prtInHsiCnfgTable 1}

PrtInHsiCnfgEntry ::=
      SEQUENCE {
        prtInHsiCnfgIdx     INTEGER,
        prtInHsiSltIdx      INTEGER,
        prtInHsiPrtIdx      INTEGER,

        prtInHsiConnect     INTEGER,
        prtInHsiRate        INTEGER,
		prtInHsiConcentratedTo INTEGER
      }

prtInHsiCnfgIdx OBJECT-TYPE
      SYNTAX  INTEGER  (1..255)
      ACCESS  read-only
      STATUS  mandatory
      DESCRIPTION
      "This object indicates the Idx of the Cnfg (1..100) being
       accessed.
       Idx 255 relates to the TmpCnfg"
      ::= {prtInHsiCnfgEntry 1}

prtInHsiSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      ACCESS  read-only
      STATUS  mandatory
      DESCRIPTION
      "This object indicates a unique  slot  position where
       the card is inserted."
      ::= {prtInHsiCnfgEntry 2}

prtInHsiPrtIdx OBJECT-TYPE
      SYNTAX  INTEGER
      ACCESS  read-only
      STATUS  mandatory
      DESCRIPTION
      "A unique port identifier within the card.
       Valid values: inPrt1 (101) .. inPrt48 (148)."
      ::= {prtInHsiCnfgEntry 3}

prtInHsiConnect OBJECT-TYPE
      SYNTAX  INTEGER
       {
  no  (2),
  yes (3)
       }
      ACCESS  read-write
      STATUS  mandatory
      DESCRIPTION
      "This attribute indicates whether the port should be considered in
       any of the mux  algorithms."
      ::= {prtInHsiCnfgEntry 4}

prtInHsiRate    OBJECT-TYPE
      SYNTAX  INTEGER
       {
          r600bps   (2),
          r1200bps  (3),
          r2400bps  (4),
          r4800bps  (5),
          r9600bps  (6),
          r19200bps (7),
          r38400bps (8),
          r48kbps   (9),
          r56kbps  (10),
          r64kbps  (11),
          r128kbps (12),
		  concentrated (13),  
          notApplicable   (255)
          }
      ACCESS  read-write
      STATUS  mandatory
      DESCRIPTION
      "This object indicates the port speed.
       For HS-U/I and HS-S ports:
       2 bit - up to 9600bps
       4 bit - 19200bps
       8 bit - 38400bps .. 64kbps.
       concentrated - this D channel goes to a Concentration channel,
                      that represents many channels that this value was
                      selected for them. The Concentrated channel is an
                      Internal D Channel of the same card. 
                      This value is applicable only for	D channels, except 
                      Concentration channel itself.
                      --for HS-S and HS-U/I cards the Concentration channel 
                        will always be: internal-13
                      --for HS-S12, HS-S6, HS-U12, HS-U6, the Concentration channel
                        is selected via the prtInHsiConcentratedTo object."
      ::= {prtInHsiCnfgEntry 5}

prtInHsiConcentratedTo OBJECT-TYPE
      SYNTAX  INTEGER
      ACCESS  read-write
      STATUS  mandatory
      DESCRIPTION
      "The Concentration D Channel of the prtInHsiPrtIdx port.
	   The port always belongs to the same card as prtInHsiPrtIdx port.
	   This object is applicable only when prtInHsiRate=concentrated.
       Valid values:
	   - notApplicable: 255
       - for HS-S12, HS-U12 cards: inPrt37 (137) .. inPrt48 (148)."
      ::= {prtInHsiCnfgEntry 6}

--
-- Megaplex?000/?004 Hs-R and HS-U port configuration
--
--prtExHsrCnfgTable   OBJECT IDENTIFIER ::= {prtHsrCnfg 1}

prtExHsrCnfgTable OBJECT-TYPE
      SYNTAX SEQUENCE OF PrtExHsrCnfgEntry
      ACCESS not-accessible
      STATUS  mandatory
      DESCRIPTION
       "The write operation into the Table Objects is valid only
        to the TmpCnfg entry."
      ::= {prtHsrCnfg 1}

prtExHsrCnfgEntry OBJECT-TYPE
      SYNTAX PrtExHsrCnfgEntry
      ACCESS not-accessible
      STATUS mandatory
      DESCRIPTION "" INDEX {prtExHsrCnfgIdx, prtExHsrSltIdx,  prtExHsrPrtIdx }
      ::= { prtExHsrCnfgTable 1}

PrtExHsrCnfgEntry ::=
      SEQUENCE {
        prtExHsrCnfgIdx     INTEGER,
        prtExHsrSltIdx      INTEGER,
        prtExHsrPrtIdx      INTEGER,

        prtExHsrConnect     INTEGER,
        prtExHsrProtocol    INTEGER,
        prtExHsrRate        INTEGER,
        prtExHsrDataBits    INTEGER,
        prtExHsrParity      INTEGER,
        prtExHsrStopBits    INTEGER,
        prtExHsrCts         INTEGER,
        prtExHsrClkMode     INTEGER,
        prtExHsrLinkTo      INTEGER,
        prtExHsrDcdDsr      INTEGER,
        prtExHsrOperMode    INTEGER,
        prtExHsrRtsDtr      INTEGER,
		prtExHsrLlbEnable   INTEGER,
		prtExHsrRlbEnable   INTEGER,
		prtExHsrRateAdapt   INTEGER 
      }

prtExHsrCnfgIdx OBJECT-TYPE
      SYNTAX  INTEGER  (1..255)
      ACCESS  read-only
      STATUS  mandatory
      DESCRIPTION
      "This object indicates the Idx of the Cnfg (1..100) being
       accessed.
       Idx 255 relates to the TmpCnfg"
      ::= {prtExHsrCnfgEntry 1}

prtExHsrSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      ACCESS  read-only
      STATUS  mandatory
      DESCRIPTION
      "This object indicates a unique  slot  position where
       the card is inserted."
      ::= {prtExHsrCnfgEntry 2}

prtExHsrPrtIdx OBJECT-TYPE
      SYNTAX  INTEGER
      ACCESS  read-only
      STATUS  mandatory
      DESCRIPTION
      "A unique prt identifier within the card.
       Valid values:
        - For HS-R cards: exPrt1 (1)   .. exPrt4 (4)
        - For HS-U/1 cards: inPrt1 (101) .. inPrt4 (104)
        - For HS-S12, HS-S6, HS-U12, HS-U6 cards:
          exPrt1 (1) .. exPrt12 (12). This MIB table is used only
          for LT-1 interface. "
      ::= {prtExHsrCnfgEntry 3}

prtExHsrConnect OBJECT-TYPE
      SYNTAX  INTEGER
       {
  no  (2),
  yes (3)
       }
      ACCESS  read-write
      STATUS  mandatory
      DESCRIPTION
      "This object indicates whether the port should be considered in
       any of the mux  algorithms."
      ::= {prtExHsrCnfgEntry 4}

prtExHsrProtocol OBJECT-TYPE
      SYNTAX  INTEGER
              {
                sync  (2),
                async (3)
              }
      ACCESS  read-write
      STATUS  mandatory
      DESCRIPTION
      "This object indicates the protocol."
      ::= {prtExHsrCnfgEntry 5}

prtExHsrRate    OBJECT-TYPE
      SYNTAX  INTEGER
       {
          r600bps    (2),
          r1200bps   (3),
          r2400bps   (4),
          r4800bps   (5),
          r9600bps   (6),
          r19200bps  (7),
          r38400bps  (8),
          r48kbps    (9),
          r56kbps   (10),
          r64kbps   (11),
          r16000bps (12),
          r32000bps (13),
          r57600bps (14),
          r115200bps(15),
          r128000bps(16)
       }
      ACCESS  read-write
      STATUS  mandatory
      DESCRIPTION
      "This object indicates the port speed.
       The 16,32,48,56,64 and 128 kbps rates are applicable only for Sync
       protocol.
       The 57.6 and 115.2 kbps rates are applicable only for Async
       protocol."
      ::= {prtExHsrCnfgEntry 6}

prtExHsrDataBits OBJECT-TYPE
      SYNTAX  INTEGER
       {
    d5bits    (1),
    d6bits    (2),
    d7bits    (3),
    d8bits    (4),
    notApplicable (255)
       }
      ACCESS  read-write
      STATUS  mandatory
      DESCRIPTION
      "Data Bits.
       This object is applicable for Async protocol only."
      ::= {prtExHsrCnfgEntry 7}

prtExHsrParity OBJECT-TYPE
      SYNTAX  INTEGER
       {
        no  (2),
        yes (3),
		odd (4),
		even(5),
        notApplicable (255)
       }
      ACCESS  read-write
      STATUS  mandatory
      DESCRIPTION
      "- For HS-R card, this object indicates if the parity bit is needed or not.
	     Therefore, the 'no' and 'yes; values are applicable. 
       - For HS-S12, HS-U12, the parity type is selected: no, odd, even.
       This object is applicable for Async protocol only."
      ::= { prtExHsrCnfgEntry 8}

prtExHsrStopBits OBJECT-TYPE
      SYNTAX  INTEGER
       {
        stopBits1Bit      (1),
        stopBits2Bits     (2),
        notApplicable   (255)
       }
      ACCESS  read-write
      STATUS  mandatory
      DESCRIPTION
      "This object indicates the minimum number of stop bits in
       the tx async frame.
       This object is applicable for Async protocol only."
      ::= { prtExHsrCnfgEntry 9}

prtExHsrCts OBJECT-TYPE
      SYNTAX  INTEGER
       {
    on       (2),
    rts      (3),
    notApplicable   (255)
       }
      ACCESS  read-write
      STATUS  mandatory
      DESCRIPTION
      "CTS.
       This object is applicable for Async protocol only."
      ::= {prtExHsrCnfgEntry 10}

prtExHsrClkMode OBJECT-TYPE
      SYNTAX  INTEGER
              {
              dce     (1),
              extDce  (2),
              notApplicable  (255)
              }
      ACCESS  read-write
      STATUS  mandatory
      DESCRIPTION
      "Clock mode.
       This object is applicable for Sync protocol only."
      ::= { prtExHsrCnfgEntry 11}

prtExHsrLinkTo  OBJECT-TYPE
      SYNTAX  INTEGER
       {
	   notApplicable (1),
       io1   (5),
       io2   (6),
       io3   (7),
       io4   (8),
       io5   (9),
       io6  (10),
       io7  (11),
       io8  (12),
       io9  (13),
       io10 (14),
       io11 (15),
       io12 (16)
       }
      ACCESS  read-write
      STATUS  deprecated
      DESCRIPTION
      "It indicates the slot of the main link card to which the HS-R card
       is mapped.
       notApplicable - for HS-U/1 internal ports.
       STATUS  deprecated - this object is replaced by prtGenCnfgLinkToSlot
       and prtGenCnfgLinkToPort."
      ::= {prtExHsrCnfgEntry 12}

prtExHsrDcdDsr OBJECT-TYPE
      SYNTAX  INTEGER
       {
    notApplicable (1),
    local         (2),
    endToEnd      (3)
       }
      ACCESS  read-write
      STATUS  mandatory
      DESCRIPTION
      "DCD & DSR."
      ::= {prtExHsrCnfgEntry 13}


prtExHsrOperMode OBJECT-TYPE
      SYNTAX  INTEGER
       {
       normal          (2),
       unidirectRx     (3),
       broadcast       (4)
       }
      ACCESS  read-write
      STATUS  mandatory
      DESCRIPTION
      "This object indicates the operation mode of the port.
       normal = bi-directional (Tx/Rx)
       unidirectRx = unidirectional Rx.
       broadcast = Tx upon request."
      ::= {prtExHsrCnfgEntry 14}

prtExHsrRtsDtr OBJECT-TYPE
      SYNTAX  INTEGER
       {
    notApplicable (1),
    local         (2),
    endToEnd      (3)
       }
      ACCESS  read-write
      STATUS  mandatory
      DESCRIPTION
      "RTS & DTR."
      ::= {prtExHsrCnfgEntry 15}

prtExHsrLlbEnable OBJECT-TYPE
      SYNTAX  INTEGER
       {
       notApplicable (1),
       disabled      (2),
       enabled       (3)
       }
      ACCESS  read-write
      STATUS  mandatory
      DESCRIPTION
      "Enable/Disable LLB."
      ::= {prtExHsrCnfgEntry 16}

prtExHsrRlbEnable OBJECT-TYPE
      SYNTAX  INTEGER
       {
       notApplicable (1),
       disabled      (2),
       enabled       (3)
       }
      ACCESS  read-write
      STATUS  mandatory
      DESCRIPTION
      "Enable/Disable RLB."
      ::= {prtExHsrCnfgEntry 17}

prtExHsrRateAdapt OBJECT-TYPE
      SYNTAX  INTEGER
       {
       notApplicable (1),
       proprietary   (2),
       v110          (3)
       }
      ACCESS  read-write
      STATUS  mandatory
      DESCRIPTION
      "Rate Adaptation - takes a low rate and adapts it to 64Kbps.
       This object specifies the means this adaptation is done by."
      ::= {prtExHsrCnfgEntry 18}

--
-- Megaplex?000/?004 MBE port configuration
--

prtExMbeCnfgTable OBJECT-TYPE
      SYNTAX SEQUENCE OF PrtExMbeCnfgEntry
      ACCESS not-accessible
      STATUS  mandatory
      DESCRIPTION
       "The write operation into the Table Objects is valid only
        to the TmpCnfg entry."
      ::= {prtMbeCnfg 1}

prtExMbeCnfgEntry OBJECT-TYPE
      SYNTAX PrtExMbeCnfgEntry
      ACCESS not-accessible
      STATUS mandatory
      DESCRIPTION "" INDEX {prtExMbeCnfgIdx, prtExMbeSltIdx,  prtExMbePrtIdx }
      ::= { prtExMbeCnfgTable 1}

PrtExMbeCnfgEntry ::=
      SEQUENCE {
        prtExMbeCnfgIdx     INTEGER,
        prtExMbeSltIdx      INTEGER,
        prtExMbePrtIdx      INTEGER,

        prtExMbeLan         INTEGER
      }

prtExMbeCnfgIdx OBJECT-TYPE
      SYNTAX  INTEGER  (1..255)
      ACCESS  read-only
      STATUS  mandatory
      DESCRIPTION
      "This attribute indicates the Idx of the Cnfg (1..100) being
       accessed.
       Idx 255 relates to the TmpCnfg"
      ::= {prtExMbeCnfgEntry 1}
-- In phase I only the values 1 (Cnfg1) and 255 (temp) are valid.

prtExMbeSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      ACCESS  read-only
      STATUS  mandatory
      DESCRIPTION
      "This attribute indicates a unique  slot  position where
       the card is inserted.
       In the ?004 Unit the entries io6(10)..io16) are not valid."
      ::= {prtExMbeCnfgEntry 2}

prtExMbePrtIdx OBJECT-TYPE
      SYNTAX  INTEGER
     {
          exPrt1    (1)
     }
      ACCESS  read-only
      STATUS  mandatory
      DESCRIPTION
      "A unique port identifier within the card."
      ::= {prtExMbeCnfgEntry 3}

prtExMbeLan OBJECT-TYPE
      SYNTAX  INTEGER
       {
        remote  (1),
        main    (2)
       }
      ACCESS  read-write
      STATUS  mandatory
      DESCRIPTION
      "This attribute indicates whether the MBE port is operated
       as main or remote bridge."
      ::= {prtExMbeCnfgEntry 4}

prtInMbeCnfgTable OBJECT-TYPE
      SYNTAX SEQUENCE OF PrtInMbeCnfgEntry
      ACCESS not-accessible
      STATUS  mandatory
      DESCRIPTION
       "The write operation into the Table Objects is valid only
        to the TmpCnfg entry."
      ::= {prtMbeCnfg 2}

prtInMbeCnfgEntry OBJECT-TYPE
      SYNTAX PrtInMbeCnfgEntry
      ACCESS not-accessible
      STATUS mandatory
      DESCRIPTION "" INDEX {prtInMbeCnfgIdx, prtInMbeSltIdx,  prtInMbePrtIdx }
      ::= { prtInMbeCnfgTable 1}

PrtInMbeCnfgEntry ::=
      SEQUENCE {
        prtInMbeCnfgIdx     INTEGER,
        prtInMbeSltIdx      INTEGER,
        prtInMbePrtIdx      INTEGER,

        prtInMbeConnect     INTEGER,
        prtInMbeRate        INTEGER,
        prtInMbeLinkTo      INTEGER
      }

prtInMbeCnfgIdx OBJECT-TYPE
      SYNTAX  INTEGER  (1..255)
      ACCESS  read-only
      STATUS  mandatory
      DESCRIPTION
      "This attribute indicates the Idx of the Cnfg (1..100) being
       accessed.
       Idx 255 relates to the TmpCnfg"
      ::= {prtInMbeCnfgEntry 1}
-- In phase I only the values 1 (Cnfg1) and 255 (temp) are valid.

prtInMbeSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      ACCESS  read-only
      STATUS  mandatory
      DESCRIPTION
      "This attribute indicates a unique  slot  position where
       the card is inserted.
       In the ?004 Unit the entries io6(10)..io16) are not valid."
      ::= {prtInMbeCnfgEntry 2}

prtInMbePrtIdx OBJECT-TYPE
      SYNTAX  INTEGER
     {
          inPrt1    (101)
     }
      ACCESS  read-only
      STATUS  mandatory
      DESCRIPTION
      "A unique port identifier within the card."
      ::= {prtInMbeCnfgEntry 3}

prtInMbeConnect OBJECT-TYPE
      SYNTAX  INTEGER
       {
  no  (2),
  yes (3)
       }
      ACCESS  read-write
      STATUS  mandatory
      DESCRIPTION
      "This attribute indicates whether the port should be considered in
       any of the mux  algorithms."
      ::= {prtInMbeCnfgEntry 4}

prtInMbeRate    OBJECT-TYPE
      SYNTAX  INTEGER
	      {
        r1x64eq64Kbps    (1),
        r2x64eq128Kbps   (2),
        r3x64eq192Kbps   (3),
        r4x64eq256Kbps   (4),
        r5x64eq320Kbps   (5),
        r6x64eq384Kbps   (6),
        r7x64eq448Kbps   (7),
        r8x64eq512Kbps   (8),
        r9x64eq576Kbps   (9),
        r10x64eq640Kbps (10),
        r11x64eq704Kbps (11),
        r12x64eq768Kbps (12),
        r13x64eq832Kbps (13),
        r14x64eq896Kbps (14),
        r15x64eq960Kbps (15),
        r16x64eq1024Kbps(16),
        r17x64eq1088Kbps(17),
        r18x64eq1152Kbps(18),
        r19x64eq1216Kbps(19),
        r20x64eq1280Kbps(20),
        r21x64eq1344Kbps(21),
        r22x64eq1408Kbps(22),
        r23x64eq1472Kbps(23),
        r24x64eq1536Kbps(24)
	      }
      ACCESS  read-write
      STATUS  mandatory
      DESCRIPTION
      "This attribute indicates the port speed."
      ::= {prtInMbeCnfgEntry 5}

prtInMbeLinkTo  OBJECT-TYPE
      SYNTAX  INTEGER
       {
       io1   (5),
       io2   (6),
       io3   (7),
       io4   (8),
       io5   (9),
       io6  (10),
       io7  (11),
       io8  (12),
       io9  (13),
       io10 (14),
       io11 (15),
       io12 (16)
       }
      ACCESS  read-write
      STATUS  deprecated
      DESCRIPTION
      "It indicates the slot of the main link card to which the
       MBE card is mapped.
       In the ?004 Unit the entries io6(10)..io16) are not valid.
       STATUS  deprecated - this object is replaced by prtGenCnfgLinkToSlot
       and prtGenCnfgLinkToPort."
      ::= {prtInMbeCnfgEntry 6}


--
-- Megaplex?000/?004 TRE port configuration
--

prtExTreCnfgTable OBJECT-TYPE
      SYNTAX SEQUENCE OF PrtExTreCnfgEntry
      ACCESS not-accessible
      STATUS  mandatory
      DESCRIPTION
       "The write operation into the Table Objects is valid only
        to the TmpCnfg entry."
      ::= {prtTreCnfg 1}

prtExTreCnfgEntry OBJECT-TYPE
      SYNTAX PrtExTreCnfgEntry
      ACCESS not-accessible
      STATUS mandatory
      DESCRIPTION "" INDEX {prtExTreCnfgIdx, prtExTreSltIdx,  prtExTrePrtIdx }
      ::= { prtExTreCnfgTable 1}

PrtExTreCnfgEntry ::=
      SEQUENCE {
        prtExTreCnfgIdx     INTEGER,
        prtExTreSltIdx      INTEGER,
        prtExTrePrtIdx      INTEGER,

        prtExTreLan         INTEGER,
        prtExTreLanRate     INTEGER

      }

prtExTreCnfgIdx OBJECT-TYPE
      SYNTAX  INTEGER  (1..255)
      ACCESS  read-only
      STATUS  mandatory
      DESCRIPTION
      "This attribute indicates the Idx of the Cnfg (1..100) being
       accessed.
       Idx 255 relates to the TmpCnfg"
      ::= {prtExTreCnfgEntry 1}
-- In phase I only the values 1 (Cnfg1) and 255 (temp) are valid.

prtExTreSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      ACCESS  read-only
      STATUS  mandatory
      DESCRIPTION
      "This attribute indicates a unique  slot  position where
       the card is inserted.
       In the ?004 Unit the entries io6(10)..io16) are not valid."
      ::= {prtExTreCnfgEntry 2}

prtExTrePrtIdx OBJECT-TYPE
      SYNTAX  INTEGER
     {
          exPrt1    (1)
     }
      ACCESS  read-only
      STATUS  mandatory
      DESCRIPTION
      "A unique port identifier within the card."
      ::= {prtExTreCnfgEntry 3}

prtExTreLan OBJECT-TYPE
      SYNTAX  INTEGER
       {
        remote  (1),
        main    (2)
       }
      ACCESS  read-write
      STATUS  mandatory
      DESCRIPTION
      "This attribute indicates whether the TRE port is operated
       as main or remote bridge.
       Default=remote."
      ::= {prtExTreCnfgEntry 4}

prtExTreLanRate OBJECT-TYPE
      SYNTAX  INTEGER
       {
        r4M  (1),
        r16M (2)
       }
      ACCESS  read-write
      STATUS  mandatory
      DESCRIPTION
      "This attribute indicates the Rate of the TRE port
       in Mbit/sec.
       Default-r4M."
      ::= {prtExTreCnfgEntry 5}



prtInTreCnfgTable OBJECT-TYPE
      SYNTAX SEQUENCE OF PrtInTreCnfgEntry
      ACCESS not-accessible
      STATUS  mandatory
      DESCRIPTION
       "The write operation into the Table Objects is valid only
        to the TmpCnfg entry."
      ::= {prtTreCnfg 2}

prtInTreCnfgEntry OBJECT-TYPE
      SYNTAX PrtInTreCnfgEntry
      ACCESS not-accessible
      STATUS mandatory
      DESCRIPTION "" INDEX {prtInTreCnfgIdx, prtInTreSltIdx,  prtInTrePrtIdx }
      ::= { prtInTreCnfgTable 1}

PrtInTreCnfgEntry ::=
      SEQUENCE {
        prtInTreCnfgIdx     INTEGER,
        prtInTreSltIdx      INTEGER,
        prtInTrePrtIdx      INTEGER,

        prtInTreConnect     INTEGER,
        prtInTreRate        INTEGER,
        prtInTreLinkTo      INTEGER
      }

prtInTreCnfgIdx OBJECT-TYPE
      SYNTAX  INTEGER  (1..255)
      ACCESS  read-only
      STATUS  mandatory
      DESCRIPTION
      "This attribute indicates the Idx of the Cnfg (1..100) being
       accessed.
       Idx 255 relates to the TmpCnfg"
      ::= {prtInTreCnfgEntry 1}
-- In phase I only the values 1 (Cnfg1) and 255 (temp) are valid.

prtInTreSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      ACCESS  read-only
      STATUS  mandatory
      DESCRIPTION
      "This attribute indicates a unique  slot  position where
       the card is inserted.
       In the ?004 Unit the entries io6(10)..io16) are not valid."
      ::= {prtInTreCnfgEntry 2}

prtInTrePrtIdx OBJECT-TYPE
      SYNTAX  INTEGER
     {
          inPrt1    (101)
     }
      ACCESS  read-only
      STATUS  mandatory
      DESCRIPTION
      "A unique port identifier within the card."
      ::= {prtInTreCnfgEntry 3}

prtInTreConnect OBJECT-TYPE
      SYNTAX  INTEGER
       {
  no  (2),
  yes (3)
       }
      ACCESS  read-write
      STATUS  mandatory
      DESCRIPTION
      "This attribute indicates whether the port should be considered
       in any of the mux  algorithms."
      ::= {prtInTreCnfgEntry 4}

prtInTreRate    OBJECT-TYPE
      SYNTAX  INTEGER
       {
        r1x56eq56Kbps    (1),
        r1x64eq64Kbps    (2),
        r2x56eq112Kbps   (3),
        r2x64eq128Kbps   (4),
        r3x56eq168Kbps   (5),
        r3x64eq192Kbps   (6),
        r4x56eq224Kbps   (7),
        r4x64eq256Kbps   (8),
        r5x56eq280Kbps   (9),
        r5x64eq320Kbps   (10),
        r6x56eq336Kbps   (11),
        r6x64eq384Kbps   (12),
        r7x56eq392Kbps   (13),
        r7x64eq448Kbps   (14),
        r8x56eq448Kbps   (15),
        r8x64eq512Kbps   (16),
        r9x56eq504Kbps   (17)
       }
      ACCESS  read-write
      STATUS  mandatory
      DESCRIPTION
      "This attribute indicates the port speed."
      ::= {prtInTreCnfgEntry 5}

prtInTreLinkTo  OBJECT-TYPE
      SYNTAX  INTEGER
       {
       io1   (5),
       io2   (6),
       io3   (7),
       io4   (8),
       io5   (9),
       io6  (10),
       io7  (11),
       io8  (12),
       io9  (13),
       io10 (14),
       io11 (15),
       io12 (16)
       }
      ACCESS  read-write
      STATUS  deprecated
      DESCRIPTION
      "It indicates the slot of the main link card to which the
       MBE card is mapped.
       In the ?004 Unit the entries io6(10)..io16) are not valid.
       STATUS  deprecated - this object is replaced by prtGenCnfgLinkToSlot
       and prtGenCnfgLinkToPort."
      ::= {prtInTreCnfgEntry 6}


--Packet VC4 card. This is a voice card with 4 ports.
--
--Each pair of ports (1-2 , 3-4) may have a different type:
--E&M, FXO, FXS.

prtExPVc4CnfgTable OBJECT-TYPE
      SYNTAX SEQUENCE OF PrtExPVc4CnfgEntry
      ACCESS not-accessible
      STATUS  mandatory
      DESCRIPTION
       "The write operation into the Table Objects is valid only
        to the TmpCnfg entry."
      ::= { prtPVc4Cnfg 1}

prtExPVc4CnfgEntry OBJECT-TYPE
      SYNTAX PrtExPVc4CnfgEntry
      ACCESS not-accessible
      STATUS mandatory
      DESCRIPTION "" INDEX {prtExPVc4CnfgIdx, prtExPVc4SltIdx, prtExPVc4PrtIdx }
      ::= { prtExPVc4CnfgTable 1}

PrtExPVc4CnfgEntry ::=
      SEQUENCE {
        prtExPVc4CnfgIdx      INTEGER,
        prtExPVc4SltIdx       INTEGER,
        prtExPVc4PrtIdx       INTEGER,

		prtExPVc4PrtType      INTEGER,
        prtExPVc4Connect      INTEGER,
		prtExPVc4IfType       INTEGER,
        prtExPVc4TxGain       INTEGER,
        prtExPVc4RxGain       INTEGER,
		prtExPVc4MaxRate      INTEGER,
        prtExPVc4Tc           INTEGER,
        prtExPVc4Oos          INTEGER,
		prtExPVc4EchoCanceler INTEGER,
		prtExPVc4VarDelay     INTEGER,
		prtExPVc4CongLevel    INTEGER,
		prtExPVc4Wire         INTEGER,
		prtExPVc4ExtensionType		INTEGER,
		prtExPVc4ExtensionNumber	DisplayString,
		prtExPVc4OutPulsing 		INTEGER,
		prtExPVc4HuntGroupMb		INTEGER,
		prtExPVc4HuntGroupIdx		INTEGER,
		prtExPVc4AutoFaxMode		INTEGER,
		prtExPVc4FaxRate            INTEGER,
		prtExPVc4SeizeAck           INTEGER,
		prtExPVc4SignalingProtocol  INTEGER,
		prtExPVc4DelayStart         INTEGER,
		prtExPVc4WinkMinDuration    INTEGER,
		prtExPVc4WinkMaxDuration    INTEGER
 
      }

prtExPVc4CnfgIdx OBJECT-TYPE
      SYNTAX  INTEGER  (1..255)
      ACCESS  read-only
      STATUS  mandatory
      DESCRIPTION
      "This attribute indicates the Idx of the Cnfg (1..100) being
       accessed.
       Idx  255 relates to the TmpCnfg"
      ::= {prtExPVc4CnfgEntry 1}
-- In phase I only the values 1 (Cnfg1) and 255 (temp) are valid.

prtExPVc4SltIdx OBJECT-TYPE
      SYNTAX  INTEGER
 {
       io1   (5),
       io2   (6),
       io3   (7),
       io4   (8),
       io5   (9),
       io6  (10),
       io7  (11),
       io8  (12),
       io9  (13),
       io10 (14),
       io11 (15),
       io12 (16),
    notApplicable (255)
 }
      ACCESS  read-only
      STATUS  mandatory
      DESCRIPTION
      "This attribute indicates a unique  slot  position where
       the card is inserted."
      ::= {prtExPVc4CnfgEntry 2}

prtExPVc4PrtIdx OBJECT-TYPE
      SYNTAX  INTEGER
 {
       exPrt1    (1) ,
       exPrt2    (2) ,
       exPrt3    (3) ,
       exPrt4    (4),
       inPrt1(101),
       inPrt2(102),
       inPrt3(103),
       inPrt4(104)
 }
      ACCESS  read-only
      STATUS  mandatory
      DESCRIPTION
      "This object indicates the port number in the selected card
       (slot)."
      ::= {prtExPVc4CnfgEntry 3}

prtExPVc4PrtType OBJECT-TYPE
      SYNTAX  INTEGER
	{
	      eAndM  (1),
	      fxo    (2),
	      fxs    (3),
	      internal(4),
	      s0      (5)
	}
      ACCESS  read-only
      STATUS  mandatory
      DESCRIPTION
      "This object indicates the type of the selected port.
	   In Mx 30/300: s0 is for Voice over ISDN."
      ::= {prtExPVc4CnfgEntry 4}

prtExPVc4Connect OBJECT-TYPE
      SYNTAX  INTEGER
              {
                no  (2),
                yes (3)
              }
      ACCESS  read-write
      STATUS  mandatory
      DESCRIPTION
      "This attribute indicates whether the  port  should be
       considered in any of the mux algorithms."
      ::= {prtExPVc4CnfgEntry 5}

prtExPVc4IfType OBJECT-TYPE
      SYNTAX  INTEGER
              {
                unknown     (1),
                eAndM4wires (2),
   			    eAndM2wires (3),
                fxoGnd      (4),
                fxoLoop     (5),
                fxsGnd      (6),
				fxsLoop     (7),
				e1Framer    (8),
				e1Slave     (9),
				t1Framer   (10),
				t1Slave    (11)
              }
      ACCESS  read-only
      STATUS  mandatory
      DESCRIPTION
      "This attribute indicates the interface type of the  port.
       eAndM4wires and eAndM2wires - are valid only for E&M
                                     port type
	   eAndM4wires - means 2/4 wires
       fxoGnd and fxoLoop - are valid only for FXO port type
       fxsGnd and fxsLoop - are valid only for FXS port type
       e1Framer, e1Slave, t1Framer, t1Slave - are applicable for the mvc4Pbx
       cards only."
      ::= {prtExPVc4CnfgEntry 6}



prtExPVc4TxGain OBJECT-TYPE
      SYNTAX  INTEGER
      ACCESS  read-write
      STATUS  mandatory
      DESCRIPTION
      "Transmission gain in dBm."
      ::= {prtExPVc4CnfgEntry 7}

prtExPVc4RxGain OBJECT-TYPE
      SYNTAX  INTEGER
      ACCESS  read-write
      STATUS  mandatory
      DESCRIPTION
      "Reception gain in dBm."
      ::= {prtExPVc4CnfgEntry 8}

prtExPVc4MaxRate OBJECT-TYPE
      SYNTAX  INTEGER
       {
         notConnected  (1),
         r4800bps      (2),
         r7200bps      (3),
         r9600bps      (4)
       }
      ACCESS  read-write
      STATUS  mandatory
      DESCRIPTION
      "Voice rate."
      ::= {prtExPVc4CnfgEntry 9}

prtExPVc4Tc OBJECT-TYPE
      SYNTAX  INTEGER
       {
          t1sec    (1),
          t2sec    (2),
    t3sec    (3),
    t4sec    (4)
       }
      ACCESS  read-write
      STATUS  mandatory
      DESCRIPTION
      "Time interval for CIR control, in seconds. The value will
       be the same for all cards' ports."
      ::= {prtExPVc4CnfgEntry 10}

prtExPVc4Oos OBJECT-TYPE
      SYNTAX  INTEGER
       {
          notSupported   (2),
          forcedIdle     (3),
          forcedBusy     (4),
          busyIdle       (5),
          idleBusy       (6)
       }
      ACCESS  read-write
      STATUS  mandatory
      DESCRIPTION
      "Handling type, when connection is lost."
      ::= {prtExPVc4CnfgEntry 11}

prtExPVc4EchoCanceler OBJECT-TYPE
      SYNTAX  INTEGER
       {
          off    (2),
          on     (3)
       }
      ACCESS  read-write
      STATUS  mandatory
      DESCRIPTION
      "Echo canceler activation."
      ::= {prtExPVc4CnfgEntry 12}

prtExPVc4VarDelay OBJECT-TYPE
      SYNTAX  INTEGER  (0..300)
      ACCESS  read-write
      STATUS  mandatory
      DESCRIPTION
      "Maximum variant delay of the FR network, in msec."
      ::= {prtExPVc4CnfgEntry 13}

prtExPVc4CongLevel OBJECT-TYPE
      SYNTAX  INTEGER (0..70)
      ACCESS  read-write
      STATUS  mandatory
      DESCRIPTION
      "This object indicates the level of delayed data in
       precents of total available dynamic memory,
       for which the port will start to operate as congested.
       The resolution of the parameter is 5%."
      ::= {prtExPVc4CnfgEntry 14}

prtExPVc4Wire OBJECT-TYPE
      SYNTAX  INTEGER
       {
          w2wire   (1),
          w4wire   (2),
    notApplicable (255)
       }
      ACCESS  read-write
      STATUS  mandatory
      DESCRIPTION
      "This object indicates the wiring of the E&M port.
       It is applicable only for E&M card type."
      ::= {prtExPVc4CnfgEntry 15}

prtExPVc4ExtensionType OBJECT-TYPE
       SYNTAX  INTEGER { notApplicable(1),
   forceConnect(2),
   voiceSwitching(3) }
 ACCESS  read-write
       STATUS  mandatory
       DESCRIPTION
      "This object indicates the type of extension
         relevant to this port."
      ::= {prtExPVc4CnfgEntry 16}

prtExPVc4ExtensionNumber OBJECT-TYPE
       SYNTAX  DisplayString (SIZE(2))
     ACCESS  read-write
       STATUS  mandatory
       DESCRIPTION
      "This is the extension number of this port.
      This field is relevant only when the extension
     type is voice switching and is read only if the
     port is member of a hunt group."
      ::= {prtExPVc4CnfgEntry 17}

prtExPVc4OutPulsing OBJECT-TYPE
       SYNTAX  INTEGER { notApplicable(1), no(2), yes(3) }
     ACCESS  read-write
       STATUS  mandatory
       DESCRIPTION
      "This field indicates whether to outpulse the received
     digits. It is notApplicable(1) when the extension type
     is forceConnect(2)."
      ::= {prtExPVc4CnfgEntry 18}

prtExPVc4HuntGroupMb OBJECT-TYPE
     SYNTAX  INTEGER { notApplicable(1), no(2), yes(3) }
     ACCESS  read-write
       STATUS  mandatory
       DESCRIPTION
      "This object indicates if this port belongs to
      an hunt group."
      ::= {prtExPVc4CnfgEntry 19}

prtExPVc4HuntGroupIdx	OBJECT-TYPE
	    SYNTAX  INTEGER(0..10)
    	ACCESS  read-write
      	STATUS  mandatory
      	DESCRIPTION
     	"If it belongs to an hunt group, this fields
	     indicates the index of the relevant hunt group.
	     0 = notApplicable "
      ::= {prtExPVc4CnfgEntry 20}

prtExPVc4AutoFaxMode	OBJECT-TYPE
    	SYNTAX  INTEGER { notApplicable(1), no(2), yes(3) }
    	ACCESS  read-write
      	STATUS  mandatory
      	DESCRIPTION
     	"This object indicates if the system will switch automatically to
     	 FAX mode when detecting FAX activity.
     	 Default=Yes."
      ::= {prtExPVc4CnfgEntry 21}

prtExPVc4FaxRate OBJECT-TYPE
      SYNTAX  INTEGER
	      {
          notConnected  (1),
          r4800bps      (2),
		  r7200bps      (3),
		  r9600bps      (4)
	      }
      ACCESS  read-write
      STATUS  mandatory
      DESCRIPTION
      "FAX initial rate.
       Default=9600 bps."
      ::= {prtExPVc4CnfgEntry 22}

prtExPVc4SeizeAck OBJECT-TYPE
      SYNTAX INTEGER
      {
	  no   (2),
      yes  (3)
      }
      ACCESS  read-write
      STATUS  mandatory
      DESCRIPTION
      "This parameter shows whether the device will acknowledge
       a seize signal (On/Off Hook).
       When the value is set to yes(3) & the device receives an on/off hook signal
       it will transmit back an on/off hook signal.
	   When the value is set to no(2) & the device receives an on/off hook signal
       it will NOT transmit back an on/off hook signal.
       
       Example:
       If Seize Ack Parameter = YES, when the MVC.4 receives a seize signal (Off Hook) 
       from the PBX it will send an Off Hook to the PBX.

       The Seize Parameter is relevant for all the following cards:
       MVC-4
       MVC-4/E1-Framer
       MVC-4/T1-DSU-Framer
       MVC-4/T1-CSU-Framer
       MVC-4/E1-SLAVE
       MVC-4/T1-SLAVE

       Default values:
       Analog FXS - No (value can't be changed).
       Analog FXO - Yes (value can't be changed).
       Analog E&M - No (values NO/YES).
       Digital E1/T1 Framer & Slave - No."
      ::= {prtExPVc4CnfgEntry 23}

prtExPVc4SignalingProtocol OBJECT-TYPE
      SYNTAX INTEGER
      {
	  delayStart      (2),
      immediateStart  (3),
	  winkStart       (4)
      }
      ACCESS  read-write
      STATUS  mandatory
      DESCRIPTION
      "The signaling protocol that will be used between the PABX & the voice port.

	   Delay Start Protocol: the line is seized by sending an Off hook signal
	   and after a delay, if the called party is available (On hook)   
	   DTMF (Dual Tone Multi Frequency) digits are sent towards the called party.

       Immediate Start Protocol: the line is seized by sending an Off Hook signal
       and immediately DTMF digits are sent towards the called party.
       
       Wink start protocol: the line is seized by sending an Off Hook signal
       and then the called party sends a short Off Hook wink signal.
       Now the calling party starts sending DTMF digits."
      ::= {prtExPVc4CnfgEntry 24}


prtExPVc4DelayStart OBJECT-TYPE
      SYNTAX INTEGER
      ACCESS  read-write
      STATUS  mandatory
      DESCRIPTION
      "This parameter is used only for Delay Protocol.
	   This is the time that the calling party will wait after sending an Off hook
	   signal and before sending DTMF digits to the called party.
       The delay values are 100..4000 msec in intervals of 100 msec."
      ::= {prtExPVc4CnfgEntry 25}

prtExPVc4WinkMinDuration OBJECT-TYPE
      SYNTAX INTEGER
      ACCESS  read-write
      STATUS  mandatory
      DESCRIPTION
      "This parameter is used only for Wink Protocol.
	   Min Duration of the Wink Signal (off hook duration from the called party).
       Legal values: 40..400 msec in intervals of 10 msec."
      ::= {prtExPVc4CnfgEntry 26}

prtExPVc4WinkMaxDuration OBJECT-TYPE
      SYNTAX INTEGER
      ACCESS  read-write
      STATUS  mandatory
      DESCRIPTION
      "This parameter is used only for Wink Protocol.
	   Max Duration of the Wink Signal (off hook duration from the called party).
       Legal values: 40..400 msec in intervals of 10 msec."
      ::= {prtExPVc4CnfgEntry 27}


--
-- Packet VC4 card
-- External port Dlci table
--
prtExPVc4DlciTable  OBJECT-TYPE
     SYNTAX SEQUENCE OF PrtExPVc4DlciEntry
     ACCESS not-accessible
     STATUS  mandatory
     DESCRIPTION
      "The write operation into the Table Objects is valid only
       at the TmpCnfg entry."
     ::= {prtPVc4Cnfg 2}

prtExPVc4DlciEntry OBJECT-TYPE
      SYNTAX PrtExPVc4DlciEntry
      ACCESS not-accessible
      STATUS mandatory
      DESCRIPTION "" INDEX {prtExPVc4DlciCnfgIdx, prtExPVc4DlciSltIdx, prtExPVc4DlciPrtIdx}
      ::= { prtExPVc4DlciTable 1}

PrtExPVc4DlciEntry ::=
      SEQUENCE {
      prtExPVc4DlciCnfgIdx        INTEGER,
      prtExPVc4DlciSltIdx         INTEGER,
      prtExPVc4DlciPrtIdx         INTEGER,

      prtExPVc4DlciValid          INTEGER,
      prtExPVc4DlciIConSlt        INTEGER,
      prtExPVc4DlciIConPrt        INTEGER,
      prtExPVc4DlciIConDlci       INTEGER,

      prtExPVc4DlciTxBc           INTEGER,
      prtExPVc4DlciTxBe           INTEGER,
      prtExPVc4DlciRxBc           INTEGER,
      prtExPVc4DlciRxBe           INTEGER,

      prtExPVc4DlciPriority       INTEGER,

      prtExPVc4DlciStatus         INTEGER
      }


prtExPVc4DlciCnfgIdx OBJECT-TYPE
      SYNTAX  INTEGER (1..255)
      ACCESS  read-only
      STATUS  mandatory
      DESCRIPTION
      "This attribute indicates the Idx of the Cnfg (1..100) being
       accessed.
       Idx 255 relates to the TmpCnfg. "
      ::= { prtExPVc4DlciEntry 1}
-- In phase I only the values 1 (Cnfg1) and 255 (temp) are valid.

prtExPVc4DlciSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16),
    notApplicable (255)
     }
      ACCESS  read-only
      STATUS  mandatory
      DESCRIPTION
      "This attribute indicates a unique  slot  position where
       the card is inserted.
       In the ?004 Unit the entries io6(10)..io16) are not valid"
      ::= { prtExPVc4DlciEntry 2}

prtExPVc4DlciPrtIdx OBJECT-TYPE
      SYNTAX  INTEGER
 {
          exPrt1  (1) ,
          exPrt2  (2) ,
          exPrt3  (3) ,
    exPrt4  (4)
       }
      ACCESS  read-only
      STATUS  mandatory
      DESCRIPTION
      "This attribute indicates a unique internal port number.
       VC4 cards have four external ports."
      ::= { prtExPVc4DlciEntry 3}


prtExPVc4DlciValid OBJECT-TYPE
      SYNTAX  INTEGER
     {
     no  (2),
     yes (3)
     }
      ACCESS  read-write
      STATUS  mandatory
      DESCRIPTION
      "This attribute indicates whether the attributes in this
       entry are valid or not. The user can add/delete pvc (dlci
       to dlci connection) by modifing this object"
      ::= { prtExPVc4DlciEntry 4}

prtExPVc4DlciIConSlt OBJECT-TYPE
      SYNTAX  INTEGER
 {
          noConnect (2),
       io1   (5),
       io2   (6),
       io3   (7),
       io4   (8),
       io5   (9),
       io6  (10),
       io7  (11),
       io8  (12),
       io9  (13),
       io10 (14),
       io11 (15),
       io12 (16),
    notApplicable (255)
       }
      ACCESS  read-write
      STATUS  mandatory
      DESCRIPTION
      "This attribute indicates a unique slot position In the Mux
       (Agent) where the dlci is routed to.
       In the ?004 Unit the entries io6(10)..io16) are not valid"
      ::= { prtExPVc4DlciEntry 5}

prtExPVc4DlciIConPrt OBJECT-TYPE
      SYNTAX  INTEGER
      {
       exPrt1    (1) ,
       exPrt2    (2) ,
       exPrt3    (3) ,
       exPrt4    (4) ,
       exPrt5    (5) ,
       exPrt6    (6) ,
       exPrt7    (7) ,
       exPrt8    (8) ,
       exPrt9    (9) ,
       exPrt10  (10) ,
          noConnect (100),
       inPrt1  (101) ,
       inPrt2  (102) ,
       inPrt3  (103) ,
       inPrt4  (104) ,
       inPrt5  (105) ,
       inPrt6  (106) ,
       inPrt7  (107) ,
       inPrt8  (108) ,
       inPrt9  (109) ,
       inPrt10 (110) ,
    inPrt11 (111) ,
    inPrt12 (112)
       }
      ACCESS  read-write
      STATUS  mandatory
      DESCRIPTION
      "This attribute indicates a unique port id which the dlci is
       routed to."
      ::= { prtExPVc4DlciEntry 6}


prtExPVc4DlciIConDlci OBJECT-TYPE
      SYNTAX  INTEGER    (1..991)
      ACCESS  read-write
      STATUS  mandatory
      DESCRIPTION
      "This attribute indicates a unique internal connection dlci
       number,  the dlci is routed to."
      ::= { prtExPVc4DlciEntry 7}

prtExPVc4DlciTxBc OBJECT-TYPE
      SYNTAX  INTEGER
        {
         full       (1),
         zero       (2),
         txBc9600bps    (3),
        txBc14400bps    (4),
        txBc19200bps    (5),
        txBc28800bps    (6),
        txBc32000bps    (7),
        txBc38400bps    (8),
        txBc48000bps    (9),
        txBc56000bps   (10),
        txBc57600bps   (11),
          txBc64Kbps   (12),
         txBc128Kbps   (13),
         txBc192Kbps   (14),
         txBc256Kbps   (15),
         txBc320Kbps   (16),
         txBc384Kbps   (17),
         txBc448Kbps   (18),
         txBc512Kbps   (19),
         txBc768Kbps   (20),
        txBc1024Kbps   (21),
--
--KM30 ; KM300 additional rates
--
        txBc16000bps   (25),
   txBc112Kbps   (26)
        }
      ACCESS  read-write
      STATUS  mandatory
      DESCRIPTION
      "This attribute indicates a unique Tx committed bandwidth on
       the user transmit line (or at the port receive line)."
      ::= { prtExPVc4DlciEntry 8}


prtExPVc4DlciTxBe OBJECT-TYPE
      SYNTAX  INTEGER
        {
         full       (1),
         zero       (2),
         txBe9600bps    (3),
        txBe14400bps    (4),
        txBe19200bps    (5),
        txBe28800bps    (6),
        txBe32000bps    (7),
        txBe38400bps    (8),
        txBe48000bps    (9),
        txBe56000bps   (10),
        txBe57600bps   (11),
          txBe64Kbps   (12),
         txBe128Kbps   (13),
         txBe192Kbps   (14),
         txBe256Kbps   (15),
         txBe320Kbps   (16),
         txBe384Kbps   (17),
         txBe448Kbps   (18),
         txBe512Kbps   (19),
         txBe768Kbps   (20),
        txBe1024Kbps   (21),
--
--KM30 ; KM300 additional rates
--
        txBc16000bps   (25),
   txBc112Kbps   (26)
        }
      ACCESS  read-write
      STATUS  mandatory
      DESCRIPTION
      "This attribute indicates a unique Tx excess bandwidth on the
      user transmit line (or at the port receive line)."
      ::= { prtExPVc4DlciEntry 9}


prtExPVc4DlciRxBc OBJECT-TYPE
      SYNTAX  INTEGER
        {
         full       (1),
         zero       (2),
         rxBc9600bps    (3),
        rxBc14400bps    (4),
        rxBc19200bps    (5),
        rxBc28800bps    (6),
        rxBc32000bps    (7),
        rxBc38400bps    (8),
        rxBc48000bps    (9),
        rxBc56000bps   (10),
        rxBc57600bps   (11),
        rxBc64Kbps   (12),
         rxBc128Kbps   (13),
         rxBc192Kbps   (14),
         rxBc256Kbps   (15),
         rxBc320Kbps   (16),
         rxBc384Kbps   (17),
         rxBc448Kbps   (18),
         rxBc512Kbps   (19),
         rxBc768Kbps   (20),
        rxBc1024Kbps   (21),
--
--KM30 ; KM300 additional rates
--
        rxBc16000bps   (25),
   rxBc112Kbps   (26)
        }
      ACCESS  read-write
      STATUS  mandatory
      DESCRIPTION
      "This attribute indicates a unique Rx committed bandwidth on the
      user receive line (or at the port transmit line)."
      ::= { prtExPVc4DlciEntry 10}


prtExPVc4DlciRxBe OBJECT-TYPE
      SYNTAX  INTEGER
        {
         full       (1),
         zero       (2),
         rxBe9600bps    (3),
        rxBe14400bps    (4),
        rxBe19200bps    (5),
        rxBe28800bps    (6),
        rxBe32000bps    (7),
        rxBe38400bps    (8),
        rxBe48000bps    (9),
        rxBe56000bps   (10),
        rxBe57600bps   (11),
          rxBe64Kbps   (12),
         rxBe128Kbps   (13),
         rxBe192Kbps   (14),
         rxBe256Kbps   (15),
         rxBe320Kbps   (16),
         rxBe384Kbps   (17),
         rxBe448Kbps   (18),
         rxBe512Kbps   (19),
         rxBe768Kbps   (20),
        rxBe1024Kbps   (21),
--
--KM30 ; KM300 additional rates
--
        rxBc16000bps   (25),
   rxBc112Kbps   (26)
        }
      ACCESS  read-write
      STATUS  mandatory
      DESCRIPTION
      "This attribute indicates a unique Rx excess bandwidth on the
      user receive line (or at the port transmit line)."
      ::= { prtExPVc4DlciEntry 11}


prtExPVc4DlciPriority OBJECT-TYPE
      SYNTAX  INTEGER  (6..8)
      ACCESS  read-write
      STATUS  mandatory
      DESCRIPTION
      "This attribute indicates a unique priority of the pvc.
       6 is the lowest priority and 8 is the highest priority."
      ::= { prtExPVc4DlciEntry 12}



prtExPVc4DlciStatus OBJECT-TYPE
      SYNTAX  INTEGER
 {
          disconnected (1),
          connected    (2)
       }
      ACCESS  read-only
      STATUS  mandatory
      DESCRIPTION
      "This attribute indicates the status of the pvc. The status is
       disconnected(1) when one of the sides is programmed as not
       connected"
      ::= { prtExPVc4DlciEntry 13}


--
-- Megaplex ?000/?004 LS-6 TDM I/O family card include:
-- Ls6, Ls6V1/E, Ls6V1/O, Ls6V1/S, Ls6V2/E, Ls6V2/O, Ls6V2/S,
-- Ls6Vf/E, Ls6Vf/O, Ls6Vf/S
--
--prtExLs6CnfgTable OBJECT IDENTIFIER ::=  {prtLs6Cnfg 1}
--prtExLs6VCnfgTable OBJECT IDENTIFIER ::= {prtLs6Cnfg 2}
--prtInLs6CnfgTable OBJECT IDENTIFIER ::=  {prtLs6Cnfg 3}

--prtExLs6CnfgTable defines the parameters of the
-- LS-6 cards family external Data ports (1-6) ; LS-12 (1-12)

prtExLs6CnfgTable OBJECT-TYPE
      SYNTAX SEQUENCE OF PrtExLs6CnfgEntry
      ACCESS not-accessible
      STATUS  mandatory
      DESCRIPTION
       "The write operation into the Table Objects is valid only
        to the TmpCnfg entry."
      ::= {prtLs6Cnfg 1}

prtExLs6CnfgEntry OBJECT-TYPE
      SYNTAX PrtExLs6CnfgEntry
      ACCESS not-accessible
      STATUS mandatory
      DESCRIPTION "" INDEX {prtExLs6CnfgIdx, prtExLs6SltIdx, prtExLs6PrtIdx }
      ::= {prtExLs6CnfgTable  1}

PrtExLs6CnfgEntry ::=
      SEQUENCE {
        prtExLs6CnfgIdx    INTEGER,
        prtExLs6SltIdx     INTEGER,
        prtExLs6PrtIdx     INTEGER,
        prtExLs6Connect    INTEGER,
        prtExLs6Protocol   INTEGER,
        prtExLs6Rate       INTEGER,
        prtExLs6ClkMode    INTEGER,
        prtExLs6CtrlSignal INTEGER,
        prtExLs6DataBits   INTEGER,
        prtExLs6Cts        INTEGER,
        prtExLs6LinkToInternal INTEGER
      }

prtExLs6CnfgIdx OBJECT-TYPE
      SYNTAX  INTEGER (1..255)
      ACCESS  read-only
      STATUS  mandatory
      DESCRIPTION
      "This attribute indicates the Idx of the Cnfg (1..100) being
       accessed.
       Idx  255 relates to the TmpCnfg"
      ::= {prtExLs6CnfgEntry 1}

prtExLs6SltIdx OBJECT-TYPE
      SYNTAX  INTEGER
          {
       io1   (5),
       io2   (6),
       io3   (7),
       io4   (8),
       io5   (9),
       io6  (10),
       io7  (11),
       io8  (12),
       io9  (13),
       io10 (14),
       io11 (15),
       io12 (16),
       notApplicable (255)
       }
      ACCESS  read-only
      STATUS  mandatory
      DESCRIPTION
      "This attribute indicates a unique  slot  position where
       the card is inserted.
       In the ?004 Unit the entries io6(10)..io12(16) are not valid."
      ::= {prtExLs6CnfgEntry 2}

prtExLs6PrtIdx OBJECT-TYPE
      SYNTAX  INTEGER
          {
          exPrt1    (1) ,
          exPrt2    (2) ,
          exPrt3    (3) ,
          exPrt4    (4) ,
          exPrt5    (5) ,
          exPrt6    (6) ,
          exPrt7    (7) ,
          exPrt8    (8) ,
          exPrt9    (9) ,
          exPrt10  (10) ,
          exPrt11  (11) ,
          exPrt12  (12)
          }
      ACCESS  read-only
      STATUS  mandatory
      DESCRIPTION
      "This attribute indicates a unique  port index."
      ::= {prtExLs6CnfgEntry 3}

prtExLs6Connect OBJECT-TYPE
      SYNTAX  INTEGER
              {
                no  (2),
                yes (3)
              }
      ACCESS  read-write
      STATUS  mandatory
      DESCRIPTION
      "This attribute indicates whether the  port  should be
       considered in any of the mux algorithms."
      ::= {prtExLs6CnfgEntry 4}

prtExLs6Protocol OBJECT-TYPE
      SYNTAX  INTEGER
              {
                sync  (2),
                async (3)
              }
      ACCESS  read-write
      STATUS  mandatory
      DESCRIPTION
      "This attribute indicates the protocol.
       async - can be selected only for ports 1-2."
      ::= {prtExLs6CnfgEntry 5}

prtExLs6Rate OBJECT-TYPE
      SYNTAX  INTEGER
       {
          r300bps      (2),
          r600bps      (3),
          r1200bps     (4),
          r2400bps     (5),
          r4800bps     (6),
          r7200bps     (7),
          r8000bps     (8),
          r9600bps     (9),
          r14400bps   (10),
          r16000bps   (11),
          r19200bps   (12),
          r24000bps   (13),
          r28800bps   (14),
          r32000bps   (15),
          r38400bps   (16),
          r48000bps   (17),
          r56000bps   (18),
          r57600bps   (19),
          r64000bps   (20)
       }
      ACCESS  read-write
      STATUS  mandatory
      DESCRIPTION
      "Port rates in bps.
       g1 - contains the values : (2)-(6),(9),(12),(16)
       g2 - contains the values : (7),(10),(14),(19)
       g3 - contains the values : (8),(11),(13),(15),(17),(18),(20);
            it is not applicable when using Async protocol.
       Rates of pair ports (1-2, 3-4, 5-6) must be from the same
       group."
      ::= {prtExLs6CnfgEntry 6}

prtExLs6ClkMode OBJECT-TYPE
      SYNTAX  INTEGER
       {
          dce     (1),
          extDce  (2),
          dte1    (3),
          notApplicable (255)
       }
      ACCESS  read-write
      STATUS  mandatory
      DESCRIPTION
      "This attribute indicates a unique port operation clock mode.
       It is applicable for Sync protocol only ."
      ::= {prtExLs6CnfgEntry 7}

prtExLs6CtrlSignal OBJECT-TYPE
      SYNTAX  INTEGER
       {
    local     (2),
    rts       (3),
    dtrAndRts (4)
       }
      ACCESS  read-write
      STATUS  mandatory
      DESCRIPTION
      "Control Signal."
      ::= {prtExLs6CnfgEntry 8}

prtExLs6DataBits OBJECT-TYPE
      SYNTAX  INTEGER
       {
    d6bits    (1),
    d7bits    (2),
    d8bits    (3),
    d9bits    (4),
    notApplicable (255)
       }
      ACCESS  read-write
      STATUS  mandatory
      DESCRIPTION
      "Data Bits.
       This object is applicable for Async protocol only."
      ::= {prtExLs6CnfgEntry 9}

prtExLs6Cts OBJECT-TYPE
      SYNTAX  INTEGER
       {
     notApplicable (1),
     on            (2),
     rts           (3)
       }
      ACCESS  read-write
      STATUS  mandatory
      DESCRIPTION
      "This object indicates the CTS control line
       operation mode."
      ::= {prtExLs6CnfgEntry 10}

prtExLs6LinkToInternal OBJECT-TYPE
      SYNTAX  INTEGER
          {
          inPrt1        (101) ,
          inPrt2        (102) ,
    notApplicable (255)
          }
      ACCESS  read-write
      STATUS  mandatory
      DESCRIPTION
      "This object indicates which internal port of the card,
       the external port is linked to."
      ::= {prtExLs6CnfgEntry 11}


--prtExLs6VCnfgTable defines the parameters of the
-- LS-6 cards family external Voice & FAX ports (7-8)

prtExLs6VCnfgTable OBJECT-TYPE
      SYNTAX SEQUENCE OF PrtExLs6VCnfgEntry
      ACCESS not-accessible
      STATUS  mandatory
      DESCRIPTION
       "The write operation into the Table Objects is valid only
        to the TmpCnfg entry."
      ::= {prtLs6Cnfg 2}

prtExLs6VCnfgEntry OBJECT-TYPE
      SYNTAX PrtExLs6VCnfgEntry
      ACCESS not-accessible
      STATUS mandatory
      DESCRIPTION "" INDEX {prtExLs6VCnfgIdx, prtExLs6VSltIdx, prtExLs6VPrtIdx }
      ::= {prtExLs6VCnfgTable  1}


PrtExLs6VCnfgEntry ::=
      SEQUENCE {
        prtExLs6VCnfgIdx       INTEGER,
        prtExLs6VSltIdx        INTEGER,
        prtExLs6VPrtIdx        INTEGER,

        prtExLs6VConnect       INTEGER,
        prtExLs6VRate          INTEGER,
        prtExLs6VEchoCanceler  INTEGER,
        prtExLs6VIfType        INTEGER,
        prtExLs6VTxGain        INTEGER,
        prtExLs6VRxGain        INTEGER,
        prtExLs6VOos           INTEGER
      }

prtExLs6VCnfgIdx OBJECT-TYPE
      SYNTAX  INTEGER  (1..255)
      ACCESS  read-only
      STATUS  mandatory
      DESCRIPTION
      "This attribute indicates the Idx of the Cnfg (1..100) being
       accessed.
       Idx  255 relates to the TmpCnfg"
      ::= {prtExLs6VCnfgEntry 1}

prtExLs6VSltIdx OBJECT-TYPE
      SYNTAX  INTEGER
 {
       io1   (5),
       io2   (6),
       io3   (7),
       io4   (8),
       io5   (9),
       io6  (10),
       io7  (11),
       io8  (12),
       io9  (13),
       io10 (14),
       io11 (15),
       io12 (16)
 }
      ACCESS  read-only
      STATUS  mandatory
      DESCRIPTION
      "This attribute indicates a unique  slot  position where
       the card is inserted.
       In the ?004 Unit the entries io6(10)..io12(16) are not valid."
    ::= {prtExLs6VCnfgEntry 2}

prtExLs6VPrtIdx OBJECT-TYPE
      SYNTAX  INTEGER
 {
       exPrt7    (7) ,
       exPrt8    (8)
 }
      ACCESS  read-only
      STATUS  mandatory
      DESCRIPTION
      "A unique identifier of the port, within the card."
      ::= {prtExLs6VCnfgEntry 3}

prtExLs6VConnect OBJECT-TYPE
      SYNTAX  INTEGER
              {
                no  (2),
                yes (3)
              }
      ACCESS  read-write
      STATUS  mandatory
      DESCRIPTION
      "This attribute indicates whether the  port  should be
       considered in any of the mux algorithms."
      ::= {prtExLs6VCnfgEntry 4}


prtExLs6VRate OBJECT-TYPE
      SYNTAX  INTEGER
       {
          r6400bps      (2),
    r7200bps      (3),
    r8000bps      (4),
    r9600bps      (5),
    r16000bps     (6),
    r24000bps     (7),
    r32000bps     (8),
    r64000bps     (9)
       }
      ACCESS  read-write
      STATUS  mandatory
      DESCRIPTION
      "Rate (bps) used for FAX transmission and Voice coding."
      ::= {prtExLs6VCnfgEntry 5}

prtExLs6VEchoCanceler OBJECT-TYPE
      SYNTAX  INTEGER
       {
          off    (2),
          on     (3)
       }
      ACCESS  read-write
      STATUS  mandatory
      DESCRIPTION
      "Echo canceler activation."
      ::= {prtExLs6VCnfgEntry 6}

prtExLs6VIfType OBJECT-TYPE
      SYNTAX  INTEGER
              {
          w2wire   (1),
          w4wire   (2)
              }
      ACCESS  read-write
      STATUS  mandatory
      DESCRIPTION
      "This attribute indicates the interface type of the  port.
       w4wire - is applicable only for E&M port type."
      ::= {prtExLs6VCnfgEntry 7}

prtExLs6VTxGain OBJECT-TYPE
      SYNTAX  INTEGER
      ACCESS  read-write
      STATUS  mandatory
      DESCRIPTION
      "Transmit gain in dBm.
       E&M - values range: -17 .. 8
       FXO - values range: -16 .. 4
       FXS - values range: -13 .. 8  "
      ::= {prtExLs6VCnfgEntry 8}

prtExLs6VRxGain OBJECT-TYPE
      SYNTAX  INTEGER
      ACCESS  read-write
      STATUS  mandatory
      DESCRIPTION
      "Receive gain in dBm.
       E&M - values range: -17 .. 2
       FXO - values range: -17 .. -1
       FXS - values range: -17 .. 2  "
      ::= {prtExLs6VCnfgEntry 9}

prtExLs6VOos OBJECT-TYPE
      SYNTAX  INTEGER
       {
          forcedIdle     (1),
          forcedBusy     (2),
          busyIdle       (3),
          idleBusy       (4)
       }
      ACCESS  read-write
      STATUS  mandatory
      DESCRIPTION
      "Out of Service signaling mode."
      ::= {prtExLs6VCnfgEntry 10}



-- Ls6 and Ls12 Internal composite channel parameters
--

prtInLs6CnfgTable OBJECT-TYPE
      SYNTAX SEQUENCE OF PrtInLs6CnfgEntry
      ACCESS not-accessible
      STATUS  mandatory
      DESCRIPTION
       "The write operation into the Table Objects is valid only
        to the TmpCnfg entry."
      ::= {prtLs6Cnfg 3}

prtInLs6CnfgEntry OBJECT-TYPE
      SYNTAX PrtInLs6CnfgEntry
      ACCESS not-accessible
      STATUS mandatory
      DESCRIPTION "" INDEX {prtInLs6CnfgIdx, prtInLs6SltIdx, prtInLs6PrtIdx }
      ::= {prtInLs6CnfgTable 1}

PrtInLs6CnfgEntry ::=
      SEQUENCE {
        prtInLs6CnfgIdx    INTEGER,
        prtInLs6SltIdx     INTEGER,
        prtInLs6PrtIdx     INTEGER,
        prtInLs6Connect    INTEGER,
        prtInLs6TandemMode INTEGER,
        prtInLs6Rate       INTEGER,
        prtInLs6RemoteType INTEGER,
        prtInLs6LinkTo     INTEGER
      }

prtInLs6CnfgIdx OBJECT-TYPE
      SYNTAX  INTEGER (1..255)
      ACCESS  read-only
      STATUS  mandatory
      DESCRIPTION
      "This attribute indicates the Idx of the Cnfg (1..100) being
       accessed.
       Idx  255 relates to the TmpCnfg"
      ::= {prtInLs6CnfgEntry 1}

prtInLs6SltIdx OBJECT-TYPE
      SYNTAX  INTEGER
          {
       io1   (5),
       io2   (6),
       io3   (7),
       io4   (8),
       io5   (9),
       io6  (10),
       io7  (11),
       io8  (12),
       io9  (13),
       io10 (14),
       io11 (15),
       io12 (16)
       }
      ACCESS  read-only
      STATUS  mandatory
      DESCRIPTION
      "This attribute indicates a unique  slot  position where
       the card is inserted.
       In the ?004 Unit the entries io6(10)..io12(16) are not valid."
      ::= {prtInLs6CnfgEntry 2}

prtInLs6PrtIdx OBJECT-TYPE
      SYNTAX  INTEGER
          {
          inPrt1    (101),
          inPrt2    (102)
          }
      ACCESS  read-only
      STATUS  mandatory
      DESCRIPTION
      "This attribute indicates a unique internal port index."
      ::= {prtInLs6CnfgEntry 3}

prtInLs6Connect OBJECT-TYPE
      SYNTAX  INTEGER
              {
                no  (2),
                yes (3)
              }
      ACCESS  read-write
      STATUS  mandatory
      DESCRIPTION
      "This attribute indicates whether the port should be considered in
       any of the mux  algorithms. It also affects all the module
       considerations because the module has only one Internal
       interface which is the composite channel."
      ::= {prtInLs6CnfgEntry 4}

prtInLs6TandemMode  OBJECT-TYPE
      SYNTAX  INTEGER
       {
     noTandem     (1),
     tandemMaster (2),
     tandemSlave  (3)
    }
      ACCESS  read-write
      STATUS  mandatory
      DESCRIPTION
      "This object indicates the Tandem Mode.
       tandemSlave - is valid only for an LS-6 card having on
    the (current slot-1) an LS-6 card with 'tandemMaster' mode."
       ::= {prtInLs6CnfgEntry 5}

prtInLs6Rate OBJECT-TYPE
      SYNTAX  INTEGER
       {
     r32Kbps   (1),
     r56Kbps   (2),
     r64Kpbs   (3),
     r128Kbps  (4),
     r256Kbps  (5),
     r384Kbps  (6),
     r192Kbps  (7),
     r512Kbps  (8),
     r768Kbps  (9)
    }
      ACCESS  read-write
      STATUS  mandatory
      DESCRIPTION
      "Main Rate in Kbps."
      ::= {prtInLs6CnfgEntry 6}

prtInLs6RemoteType OBJECT-TYPE
      SYNTAX  INTEGER
       {
     ls6            (1),
     km2kSlave      (2),
     km2kStandalone (3),
     notApplicable (255)
    }
      ACCESS  read-write
      STATUS  mandatory
      DESCRIPTION
      "Remote Type.
       notApplicable - when prtInLs6TandemMode=tandemSlave "
      ::= {prtInLs6CnfgEntry 7}

prtInLs6LinkTo OBJECT-TYPE
      SYNTAX  INTEGER
       {
       io1   (5),
       io2   (6),
       io3   (7),
       io4   (8),
       io5   (9),
       io6  (10),
       io7  (11),
       io8  (12),
       io9  (13),
       io10 (14),
       io11 (15),
       io12 (16),
    notApplicable (255)
       }
      ACCESS  read-write
      STATUS  deprecated
      DESCRIPTION
      "It indicates the slot of the main link card to which the
       Ls6 card is mapped.
       In the ?004 Unit the entries io6(10)..io12(16) are not valid.
       notApplicable - when prtInLs6TandemMode=tandemSlave.
       STATUS  deprecated - this object is replaced by prtGenCnfgLinkToSlot
       and prtGenCnfgLinkToPort. "
      ::= {prtInLs6CnfgEntry 8}

--
-- Megaplex?000/?004 VC-3 TDM I/O family port.
-- (VC3/E&M,VC3/FXO,VC3/FXS)
--
--

--prtExVc3CnfgTable defines the parameters of the
-- VC-3 and VF-3 cards family external ports

prtExVc3CnfgTable OBJECT-TYPE
      SYNTAX SEQUENCE OF PrtExVc3CnfgEntry
      ACCESS not-accessible
      STATUS  mandatory
      DESCRIPTION
       "The write operation into the Table Objects is valid only
        to the TmpCnfg entry."
      ::= { prtVc3Cnfg 1}

prtExVc3CnfgEntry OBJECT-TYPE
      SYNTAX PrtExVc3CnfgEntry
      ACCESS not-accessible
      STATUS mandatory
      DESCRIPTION "" INDEX {prtExVc3CnfgIdx, prtExVc3SltIdx, prtExVc3PrtIdx }
      ::= { prtExVc3CnfgTable 1}

PrtExVc3CnfgEntry ::=
      SEQUENCE {
        prtExVc3CnfgIdx        INTEGER,
        prtExVc3SltIdx         INTEGER,
        prtExVc3PrtIdx         INTEGER,

        prtExVc3Connect      INTEGER,
        prtExVc3TransGain    INTEGER,
        prtExVc3ReceiveGain  INTEGER,
        prtExVc3Wire         INTEGER,
        prtExVc3Rate         INTEGER,
        prtExVc3EchoCanceler INTEGER
      }

prtExVc3CnfgIdx OBJECT-TYPE
      SYNTAX  INTEGER  (1..255)
      ACCESS  read-only
      STATUS  mandatory
      DESCRIPTION
      "This attribute indicates the Idx of the Cnfg (1..100) being
       accessed.
       Idx  255 relates to the TmpCnfg"
      ::= {prtExVc3CnfgEntry 1}

prtExVc3SltIdx OBJECT-TYPE
      SYNTAX  INTEGER
 {
       io1   (5),
       io2   (6),
       io3   (7),
       io4   (8),
       io5   (9),
       io6  (10),
       io7  (11),
       io8  (12),
       io9  (13),
       io10 (14),
       io11 (15),
       io12 (16)
 }
      ACCESS  read-only
      STATUS  mandatory
      DESCRIPTION
      "This attribute indicates a unique  slot  position where
       the card is inserted.
       In the ?004 Unit the entries io6(10)..io12(16) are not valid."
      ::= {prtExVc3CnfgEntry 2}

prtExVc3PrtIdx OBJECT-TYPE
      SYNTAX  INTEGER
 {
       exPrt1    (1) ,
       exPrt2    (2) ,
       exPrt3    (3)
 }
      ACCESS  read-only
      STATUS  mandatory
      DESCRIPTION
      "A unique identifier of the port, within the card."
      ::= {prtExVc3CnfgEntry 3}

prtExVc3Connect OBJECT-TYPE
      SYNTAX  INTEGER
              {
                no  (2),
                yes (3)
              }
      ACCESS  read-write
      STATUS  mandatory
      DESCRIPTION
      "This attribute indicates whether the  port  should be
       considered in any of the mux algorithms."
      ::= {prtExVc3CnfgEntry 4}

prtExVc3TransGain OBJECT-TYPE
      SYNTAX  INTEGER
      ACCESS  read-write
      STATUS  mandatory
      DESCRIPTION
      "Transmit gain in dBm."
      ::= {prtExVc3CnfgEntry 5}

prtExVc3ReceiveGain OBJECT-TYPE
      SYNTAX  INTEGER
      ACCESS  read-write
      STATUS  mandatory
      DESCRIPTION
      "Receive gain in dBm."
      ::= {prtExVc3CnfgEntry 6}

prtExVc3Wire OBJECT-TYPE
      SYNTAX  INTEGER
       {
          w2wire   (1),
          w4wire   (2)
       }
      ACCESS  read-write
      STATUS  mandatory
      DESCRIPTION
      "This object is equal for all the ports in the specific
       card because of HW limitations"
      ::= {prtExVc3CnfgEntry 7}

prtExVc3Rate OBJECT-TYPE
      SYNTAX  INTEGER
       {
          r9600bps    (1),
    r4800bps    (2)
       }
      ACCESS  read-write
      STATUS  mandatory
      DESCRIPTION
      "Rate in bps."
      ::= {prtExVc3CnfgEntry 8}

prtExVc3EchoCanceler OBJECT-TYPE
      SYNTAX  INTEGER
       {
          off    (2),
          on     (3)
       }
      ACCESS  read-write
      STATUS  mandatory
      DESCRIPTION
      "Echo canceler activation. The value will be the same for
       all the card's external ports."
      ::= {prtExVc3CnfgEntry 9}

--prtInVc3CnfgTable defines the parameters of the
-- VC-3 or VF-3 cards family internal ports

prtInVc3CnfgTable OBJECT-TYPE
      SYNTAX SEQUENCE OF PrtInVc3CnfgEntry
      ACCESS not-accessible
      STATUS  mandatory
      DESCRIPTION
       "The write operation into the Table Objects is valid only
        to the TmpCnfg entry."
      ::= { prtVc3Cnfg 2}

prtInVc3CnfgEntry OBJECT-TYPE
      SYNTAX PrtInVc3CnfgEntry
      ACCESS not-accessible
      STATUS mandatory
      DESCRIPTION "" INDEX {prtInVc3CnfgIdx, prtInVc3SltIdx, prtInVc3PrtIdx }
      ::= { prtInVc3CnfgTable 1}

PrtInVc3CnfgEntry ::=
      SEQUENCE {
        prtInVc3CnfgIdx        INTEGER,
        prtInVc3SltIdx         INTEGER,
        prtInVc3PrtIdx         INTEGER,

        prtInVc3Connect        INTEGER,
        prtInVc3Rate           INTEGER,
        prtInVc3Oos            INTEGER,
        prtInVc3LinkTo         INTEGER

      }

prtInVc3CnfgIdx OBJECT-TYPE
      SYNTAX  INTEGER  (1..255)
      ACCESS  read-only
      STATUS  mandatory
      DESCRIPTION
      "This attribute indicates the Idx of the Cnfg (1..100) being
       accessed.
       Idx  255 relates to the TmpCnfg"
      ::= {prtInVc3CnfgEntry 1}

prtInVc3SltIdx OBJECT-TYPE
      SYNTAX  INTEGER
 {
       io1   (5),
       io2   (6),
       io3   (7),
       io4   (8),
       io5   (9),
       io6  (10),
       io7  (11),
       io8  (12),
       io9  (13),
       io10 (14),
       io11 (15),
       io12 (16)
 }
      ACCESS  read-only
      STATUS  mandatory
      DESCRIPTION
      "This attribute indicates a unique  slot  position where
       the card is inserted.
       In the ?004 Unit the entries io6(10)..io12(16) are not valid."
      ::= {prtInVc3CnfgEntry 2}

prtInVc3PrtIdx OBJECT-TYPE
      SYNTAX  INTEGER
 {
       inPrt1    (101)
 }
      ACCESS  read-only
      STATUS  mandatory
      DESCRIPTION
      "A unique identifier of the port, within the card."
      ::= {prtInVc3CnfgEntry 3}

prtInVc3Connect OBJECT-TYPE
      SYNTAX  INTEGER
              {
                no  (2),
                yes (3)
              }
      ACCESS  read-write
      STATUS  mandatory
      DESCRIPTION
      "This attribute indicates whether the  port  should be
       considered in any of the mux algorithms."
      ::= {prtInVc3CnfgEntry 4}

prtInVc3Rate OBJECT-TYPE
      SYNTAX  INTEGER
       {
          r32000bps    (1),
    r16000bps    (2)
       }
      ACCESS  read-write
      STATUS  mandatory
      DESCRIPTION
      "Rate in bps."
      ::= {prtInVc3CnfgEntry 5}

prtInVc3Oos OBJECT-TYPE
      SYNTAX  INTEGER
       {
          forcedIdle     (1),
          forcedBusy     (2),
          busyIdle       (3),
          idleBusy       (4)
       }
      ACCESS  read-write
      STATUS  mandatory
      DESCRIPTION
      " This object is equal for all the ports in the specific
        card because of HW limitations"
      ::= {prtInVc3CnfgEntry 6}

prtInVc3LinkTo OBJECT-TYPE
      SYNTAX  INTEGER
       {
       io1   (5),
       io2   (6),
       io3   (7),
       io4   (8),
       io5   (9),
       io6  (10),
       io7  (11),
       io8  (12),
       io9  (13),
       io10 (14),
       io11 (15),
       io12 (16)
       }
      ACCESS  read-write
      STATUS  deprecated
      DESCRIPTION
      "This attribute indicates the slot of the ML card to which
       the VC card is mapped.
       In the ?004 Unit the entries io6(10)..io12(16) are not valid.
       STATUS  deprecated - this object is replaced by prtGenCnfgLinkToSlot
       and prtGenCnfgLinkToPort."
      ::= {prtInVc3CnfgEntry 7}


--
-- Megaplex?000/?004 VC-3 TDM I/O family port.
-- (VC-PBX, VC-PBX/T1,VC-PBX/E1)
--
--

--prtExVcPbxCnfgTable defines the parameters of the
-- VC-PBX or VF-PBX cards family external ports

prtExVcPbxCnfgTable OBJECT-TYPE
      SYNTAX SEQUENCE OF PrtExVcPbxCnfgEntry
      ACCESS not-accessible
      STATUS  mandatory
      DESCRIPTION
       "The write operation into the Table Objects is valid only
        to the TmpCnfg entry."
      ::= { prtVcPbxCnfg 1}

prtExVcPbxCnfgEntry OBJECT-TYPE
      SYNTAX PrtExVcPbxCnfgEntry
      ACCESS not-accessible
      STATUS mandatory
      DESCRIPTION "" INDEX {prtExVcPbxCnfgIdx, prtExVcPbxSltIdx, prtExVcPbxPrtIdx }
      ::= { prtExVcPbxCnfgTable 1}

PrtExVcPbxCnfgEntry ::=
      SEQUENCE {
        prtExVcPbxCnfgIdx        INTEGER,
        prtExVcPbxSltIdx         INTEGER,
        prtExVcPbxPrtIdx         INTEGER,

        prtExVcPbxConnect        INTEGER,
        prtExVcPbxGroup          INTEGER,
        prtExVcPbxTransparent    INTEGER,
        prtExVcPbxTransSignalTs  INTEGER,
        prtExVcPbxFrame          INTEGER,
        prtExVcPbxRestoreTime    INTEGER,
  prtExVcPbxLineCode       INTEGER,
        prtExVcPbxLineLength     INTEGER,
        prtExVcPbxLinkTo         INTEGER,
     prtExVcPbxSignalOper     INTEGER,
  prtExVcPbxIdleCode       INTEGER
      }

prtExVcPbxCnfgIdx OBJECT-TYPE
      SYNTAX  INTEGER  (1..255)
      ACCESS  read-only
      STATUS  mandatory
      DESCRIPTION
      "This object indicates the Idx of the Cnfg (1..100) being
       accessed.
       Idx  255 relates to the TmpCnfg"
      ::= {prtExVcPbxCnfgEntry 1}

prtExVcPbxSltIdx OBJECT-TYPE
      SYNTAX  INTEGER
 {
       io1   (5),
       io2   (6),
       io3   (7),
       io4   (8),
       io5   (9),
       io6  (10),
       io7  (11),
       io8  (12),
       io9  (13),
       io10 (14),
       io11 (15),
       io12 (16)
 }
      ACCESS  read-only
      STATUS  mandatory
      DESCRIPTION
      "This object indicates a unique  slot  position where
       the card is inserted.
       In the ?004 Unit the entries io6(10)..io12(16) are not valid."
      ::= {prtExVcPbxCnfgEntry 2}

prtExVcPbxPrtIdx OBJECT-TYPE
      SYNTAX  INTEGER
 {
       exPrt1    (1)
 }
      ACCESS  read-only
      STATUS  mandatory
      DESCRIPTION
      "A unique identifier of the port, within the card."
      ::= {prtExVcPbxCnfgEntry 3}

prtExVcPbxConnect OBJECT-TYPE
      SYNTAX  INTEGER
              {
                no  (2),
                yes (3)
              }
      ACCESS  read-write
      STATUS  mandatory
      DESCRIPTION
      "This object indicates whether the  port  should be
       considered in any of the mux algorithms."
      ::= {prtExVcPbxCnfgEntry 4}

prtExVcPbxGroup OBJECT-TYPE
      SYNTAX  INTEGER
 {
       io1   (5),
       io2   (6),
       io3   (7),
       io4   (8),
       io5   (9),
       io6  (10),
       io7  (11),
       io8  (12),
       io9  (13),
       io10 (14),
       io11 (15),
       io12 (16),
    notApplicable (255)
 }
      ACCESS  read-only
      STATUS  mandatory
      DESCRIPTION
      "The group object links together several VC-PBX cards,
       concerning compression of the same input T1/E1 link
       time-slots.
       When ports of different slots have the same group, they are
       linked.
       When ports have a different group, they are not linked.
    For VC-PBX/T1 and E1 cards, this object is - their own
    IO Slot.
       In the ?004 Unit the entries io6(10)..io12(16) are not valid."
      ::= {prtExVcPbxCnfgEntry 5}

prtExVcPbxTransparent     OBJECT-TYPE
      SYNTAX  INTEGER
              {
                no  (2),
                yes (3),
    notApplicable (255)
              }
      ACCESS  read-write
      STATUS  mandatory
      DESCRIPTION
      "This object indicates whether the Transparent transfer
       of Time-Slots is required or not.
       Time-Slots transferred by Transparent, will not be
       compressed.
       no  - applicable only for VC-PBX/T1 and VC-PBX/E1 cards
       yes - applicable only for VC-PBX/T1 and VC-PBX/E1 cards
       notApplicable - only for VC-PBX cards."
      ::= {prtExVcPbxCnfgEntry 6}

prtExVcPbxTransSignalTs     OBJECT-TYPE
      SYNTAX  INTEGER
      ACCESS  read-write
      STATUS  mandatory
      DESCRIPTION
      "This object specifies the ML Time-Slot dedicated to
       the signaling of the PABX Transparent TSs.
       None = 255.
       When prtExVcPbxTransparent=no this object's value=None (255)
       When prtExVcPbxTransparent=notApplicable, this object's
       value=None (255).
       When prtExVcPbxTransparent=yes:
    - for VC-PBX/T1 ports, this object's valid values are 1..16
      or None (255).
       - for VC-PBX/E1 ports, this object's value will be 16 or None
      (255)."
      ::= {prtExVcPbxCnfgEntry 7}

prtExVcPbxFrame OBJECT-TYPE
      SYNTAX  INTEGER
       {
  esfT1          (2), --> dsx1ESF
  sfT1           (3), --> dsx1D4
  g732nE1        (4), --> dsx1E1
  g732nE1CRC     (5), --> dsx1E1-CRC
  g732sE1        (6), --> dsx1E1-MF
  g732sE1CRC     (7),  --> dsx1E1-MF-CRC
  notApplicable  (255)
       }
      ACCESS  read-write
      STATUS  mandatory
      DESCRIPTION
      "This object is the frame parameter for T1/E1 interface.
       The user should select only the parameters which are relevant
       to the specific card:
       T1 values for the VC-PBX/T1 card.
       E1 values for the VC-PBX/E1 card.
    notApplicable - for the VC-PBX card.
       This parameter has the same values as dsx1LineType in T1/E1
       MIB (RFC-1406). The parameters in dsx1LineType are:
                     other          (1)
      esfT1          dsx1ESF        (2)
      sfT1           dsx1D4         (3)
      g732nE1        dsx1E1         (4)
      g732nE1CRC     dsx1E1-CRC     (5)
      g732sE1        dsx1E1-MF      (6)
      g732sE1CRC     dsx1E1-MF-CRC  (7)  "
      ::= {prtExVcPbxCnfgEntry 8}

prtExVcPbxRestoreTime OBJECT-TYPE
      SYNTAX  INTEGER
       {
        restoreT1secFast      (2),
        restoreT10sec62411    (3),
        ccittE1               (4),
  notApplicable         (255)
       }
      ACCESS  read-write
      STATUS  mandatory
      DESCRIPTION
      "The time passing from the disappearance of the loss of
       synchronization condition (red alarm) to the restoration of
       normal service. The options 1secFast(2) and 10sec62411(3)
       for E1 interfaces are proprietary implementation of the T1
       standard to the E1 interface.
       ccittE1 - is applicable only for VC-PBX/E1 card
       notApplicable - is applicable for VC-PBX card"
      ::= {prtExVcPbxCnfgEntry 9}

prtExVcPbxLineCode OBJECT-TYPE
      SYNTAX  INTEGER
       {
  b7zsT1 (1),  --> dsx1JBZS
  b8zsT1 (2),  --> dsx1B8ZS
        transT1(3),  --> dsx1AMI
        hdb3E1 (4),  --> dsx1HDB3
  notApplicable (255)
       }
      ACCESS  read-write
      STATUS  mandatory
      DESCRIPTION
      "This object is the line code parameter used for T1/E1
       interface.
       The user should select only the parameters which are relevant
       to the specific card:
       T1 line code parameters for VC-PBX/T1
       E1 line code parameters for VC-PBX/E1
    notApplicable - for VC-PBX
       This parameter has the same values as dsx1LineCoding in T1/E1
       MIB (RFC-1406).  The parameters in dsx1LineCoding are:
     dsx1JBZS  (1)
     dsx1B8ZS  (2)
     dsx1HDB3  (3)
     dsx1ZBTSI (4)
     dsx1AMI   (5)
     other     (6)"
      ::= {prtExVcPbxCnfgEntry 10}

prtExVcPbxLineLength OBJECT-TYPE
      SYNTAX  INTEGER
       {
        unknown      (1),
        len0p133ft   (2),
        len134p266ft (3),
        len267p399ft (4),
        len400p533ft (5),
        len534p655ft (6),
        notApplicable (255)
       }
      ACCESS  read-write
      STATUS  mandatory
      DESCRIPTION
      "This object is the line length parameter.
       It is applicable only for the VC-PBX/T1 card.
       notApplicable - for the VC-PBX and VC-PBX/E1 card.
       lenXXXpXXXft = len-XXX-XXXft."
      ::= {prtExVcPbxCnfgEntry 11}

prtExVcPbxLinkTo OBJECT-TYPE
      SYNTAX  INTEGER
       {
       io1   (5),
       io2   (6),
       io3   (7),
       io4   (8),
       io5   (9),
       io6  (10),
       io7  (11),
       io8  (12),
       io9  (13),
       io10 (14),
       io11 (15),
       io12 (16),
    notApplicable (255)
       }
      ACCESS  read-write
      STATUS  deprecated
      DESCRIPTION
      "This object indicates the slot of the ML card to which
       the VC-PBX/T1, VC-PBX/E1 card Transparent TSs are mapped.
       notApplicable - for VC-PBX card AND
       for VC-PBX/T1, VC-PBX/E1 cards, when prtExVcPbxTransparent=no .
       In the ?004 Unit the entries io6(10)..io12(16) are not valid.
       STATUS  deprecated - this object is replaced by prtGenCnfgLinkToSlot
       and prtGenCnfgLinkToPort."
      ::= {prtExVcPbxCnfgEntry 12}

prtExVcPbxSignalOper OBJECT-TYPE
      SYNTAX  INTEGER
          {
          notApplicable (1),
          normal        (2),
          bEqA          (3),
    inverseA      (4)
          }
      ACCESS  read-write
      STATUS  mandatory
      DESCRIPTION
      "This object indicates the Signaling Operation of the
       VC-PBX/T1, VC-PBX/E1 external port.
       notApplicable - for VC-PBX card
    normal - all 4 signaling bits are transferred.
    bEqA   - copy the A bit into the B bit. Applicable only for
             VC-PBX/T1."
      ::= {prtExVcPbxCnfgEntry 13}

prtExVcPbxIdleCode OBJECT-TYPE
      SYNTAX  INTEGER
          {
          notApplicable  (1),
          hff            (2),
          he4            (3),
    hd5            (4),
    h9e            (5),
    h98            (6),
    h7f            (7),
    h7e            (8),
    h54            (9),
    h1a           (10)
          }
      ACCESS  read-write
      STATUS  mandatory
      DESCRIPTION
      "Determines the code for transmission in empty time slots.
       notApplicable - for VC-PBX card ."
      ::= {prtExVcPbxCnfgEntry 14}



--prtIn1p6VcPbxCnfgTable defines the parameters of the
-- VC-PBX or VF-PBX cards family internal ports 1-6

prtIn1p6VcPbxCnfgTable OBJECT-TYPE
      SYNTAX SEQUENCE OF PrtIn1p6VcPbxCnfgEntry
      ACCESS not-accessible
      STATUS  mandatory
      DESCRIPTION
       "The write operation into the Table Objects is valid only
        to the TmpCnfg entry."
      ::= { prtVcPbxCnfg 2}

prtIn1p6VcPbxCnfgEntry OBJECT-TYPE
      SYNTAX PrtIn1p6VcPbxCnfgEntry
      ACCESS not-accessible
      STATUS mandatory
      DESCRIPTION "" INDEX {prtIn1p6VcPbxCnfgIdx, prtIn1p6VcPbxSltIdx, prtIn1p6VcPbxPrtIdx }
      ::= { prtIn1p6VcPbxCnfgTable 1}

PrtIn1p6VcPbxCnfgEntry ::=
      SEQUENCE {
        prtIn1p6VcPbxCnfgIdx        INTEGER,
        prtIn1p6VcPbxSltIdx         INTEGER,
        prtIn1p6VcPbxPrtIdx         INTEGER,

        prtIn1p6VcPbxConnect      INTEGER,
        prtIn1p6VcPbxRate         INTEGER,
        prtIn1p6VcPbxEchoCanceler INTEGER,
        prtIn1p6VcPbxPabxTs       INTEGER
      }

prtIn1p6VcPbxCnfgIdx OBJECT-TYPE
      SYNTAX  INTEGER  (1..255)
      ACCESS  read-only
      STATUS  mandatory
      DESCRIPTION
      "This object indicates the Idx of the Cnfg (1..100) being
       accessed.
       Idx  255 relates to the TmpCnfg"
      ::= {prtIn1p6VcPbxCnfgEntry 1}

prtIn1p6VcPbxSltIdx OBJECT-TYPE
      SYNTAX  INTEGER
 {
       io1   (5),
       io2   (6),
       io3   (7),
       io4   (8),
       io5   (9),
       io6  (10),
       io7  (11),
       io8  (12),
       io9  (13),
       io10 (14),
       io11 (15),
       io12 (16)
 }
      ACCESS  read-only
      STATUS  mandatory
      DESCRIPTION
      "This object indicates a unique  slot  position where
       the card is inserted.
       In the ?004 Unit the entries io6(10)..io12(16) are not valid."
      ::= {prtIn1p6VcPbxCnfgEntry 2}

prtIn1p6VcPbxPrtIdx OBJECT-TYPE
      SYNTAX  INTEGER
 {
       inPrt1  (101) ,
       inPrt2  (102) ,
       inPrt3  (103) ,
       inPrt4  (104) ,
       inPrt5  (105) ,
       inPrt6  (106)
 }
      ACCESS  read-only
      STATUS  mandatory
      DESCRIPTION
      "A unique identifier of the port, within the card."
      ::= {prtIn1p6VcPbxCnfgEntry 3}

prtIn1p6VcPbxConnect OBJECT-TYPE
      SYNTAX  INTEGER
              {
                no  (2),
                yes (3)
              }
      ACCESS  read-write
      STATUS  mandatory
      DESCRIPTION
      "This object indicates whether the  port  should be
       considered in any of the mux algorithms."
      ::= {prtIn1p6VcPbxCnfgEntry 4}

prtIn1p6VcPbxRate OBJECT-TYPE
      SYNTAX  INTEGER
              {
                r4800bps  (1),
                r6400bps  (2),
                r7200bps  (3),
                r8000bps  (4),
    r9600bps  (5),
    r12800bps (6)
              }
      ACCESS  read-write
      STATUS  mandatory
      DESCRIPTION
      "This object indicates the port Rate.
       For Normal mode (prtIn7p8VcPbxMode=normal), only part of the values
       are valid (constant rate).
       For Server mode (prtIn7p8VcPbxMode=server), all values are
       applicable (user can select the desired compression rate). "
      ::= {prtIn1p6VcPbxCnfgEntry 5}

prtIn1p6VcPbxEchoCanceler OBJECT-TYPE
      SYNTAX  INTEGER
       {
          off    (2),
          on     (3)
       }
      ACCESS  read-write
      STATUS  mandatory
      DESCRIPTION
      "Echo canceler activation."
      ::= {prtIn1p6VcPbxCnfgEntry 6}

prtIn1p6VcPbxPabxTs OBJECT-TYPE
      SYNTAX  INTEGER (1..31)
      ACCESS  read-only
      STATUS  mandatory
      DESCRIPTION
      "This object defines the PABX Time-Slot assigned to this
       internal port.
       For a  T1 link, the valid values are: 1 .. 24.
       For an E1 link, the valid values are: 1 .. 31.
       This object is NOT applicable when prtIn1p6VcPbxConnect=no.
       This object is applicable for all cards of VC-PBX family.
       Default=the internal port index (1..6)."
      ::= {prtIn1p6VcPbxCnfgEntry 7}

--prtIn7p8VcPbxCnfgTable defines the parameters of the
-- VC-PBX or VF-PBX cards family internal ports 7-8

prtIn7p8VcPbxCnfgTable OBJECT-TYPE
      SYNTAX SEQUENCE OF PrtIn7p8VcPbxCnfgEntry
      ACCESS not-accessible
      STATUS  mandatory
      DESCRIPTION
       "The write operation into the Table Objects is valid only
        to the TmpCnfg entry."
      ::= { prtVcPbxCnfg 3}

prtIn7p8VcPbxCnfgEntry OBJECT-TYPE
      SYNTAX PrtIn7p8VcPbxCnfgEntry
      ACCESS not-accessible
      STATUS mandatory
      DESCRIPTION "" INDEX {prtIn7p8VcPbxCnfgIdx, prtIn7p8VcPbxSltIdx, prtIn7p8VcPbxPrtIdx }
      ::= { prtIn7p8VcPbxCnfgTable 1}

PrtIn7p8VcPbxCnfgEntry ::=
      SEQUENCE {
        prtIn7p8VcPbxCnfgIdx        INTEGER,
        prtIn7p8VcPbxSltIdx         INTEGER,
        prtIn7p8VcPbxPrtIdx         INTEGER,

        prtIn7p8VcPbxConnect      INTEGER,
        prtIn7p8VcPbxMode         INTEGER,
        prtIn7p8VcPbxRate         INTEGER,
        prtIn7p8VcPbxSignalMode   INTEGER,
        prtIn7p8VcPbxOos          INTEGER,
        prtIn7p8VcPbxLinkTo       INTEGER
      }

prtIn7p8VcPbxCnfgIdx OBJECT-TYPE
      SYNTAX  INTEGER  (1..255)
      ACCESS  read-only
      STATUS  mandatory
      DESCRIPTION
      "This object indicates the Idx of the Cnfg (1..100) being
       accessed.
       Idx  255 relates to the TmpCnfg"
      ::= {prtIn7p8VcPbxCnfgEntry 1}

prtIn7p8VcPbxSltIdx OBJECT-TYPE
      SYNTAX  INTEGER
 {
       io1   (5),
       io2   (6),
       io3   (7),
       io4   (8),
       io5   (9),
       io6  (10),
       io7  (11),
       io8  (12),
       io9  (13),
       io10 (14),
       io11 (15),
       io12 (16)
 }
      ACCESS  read-only
      STATUS  mandatory
      DESCRIPTION
      "This object indicates a unique  slot  position where
       the card is inserted.
       In the ?004 Unit the entries io6(10)..io12(16) are not valid."
      ::= {prtIn7p8VcPbxCnfgEntry 2}

prtIn7p8VcPbxPrtIdx OBJECT-TYPE
      SYNTAX  INTEGER
 {
       inPrt7  (107) ,
       inPrt8  (108)
 }
      ACCESS  read-only
      STATUS  mandatory
      DESCRIPTION
      "A unique identifier of the port, within the card."
      ::= {prtIn7p8VcPbxCnfgEntry 3}

prtIn7p8VcPbxConnect OBJECT-TYPE
      SYNTAX  INTEGER
              {
                no  (2),
                yes (3)
              }
      ACCESS  read-write
      STATUS  mandatory
      DESCRIPTION
      "This object indicates whether the  port  should be
       considered in any of the mux algorithms."
      ::= {prtIn7p8VcPbxCnfgEntry 4}

prtIn7p8VcPbxMode OBJECT-TYPE
      SYNTAX  INTEGER
              {
                normal  (1),
                server  (2)
              }
      ACCESS  read-write
      STATUS  mandatory
      DESCRIPTION
      "This object indicates the working mode of the port:
       - normal - the compressed voice will be sent to an MTML
                  card inside the Mux.
       - server - the compressed voice will be sent to the Digital
                  Voice connector, as a service to an outside user."
      ::= {prtIn7p8VcPbxCnfgEntry 5}

prtIn7p8VcPbxRate OBJECT-TYPE
      SYNTAX  INTEGER
              {
                r32Kbps  (1),
    r16Kbps  (2),
                notApplicable (255)
              }
      ACCESS  read-write
      STATUS  mandatory
      DESCRIPTION
      "This object indicates the port Main Rate.
       For Server mode (prtIn7p8VcPbxMode=server), the value will
       be notApplicable. "
      ::= {prtIn7p8VcPbxCnfgEntry 6}

prtIn7p8VcPbxSignalMode OBJECT-TYPE
      SYNTAX  INTEGER
              {
                none    (1),
                aBit    (2),
    abcBit  (3),
    abcdBit (4)
              }
      ACCESS  read-write
      STATUS  mandatory
      DESCRIPTION
      "This object indicates the Signal Mode.
       For Server mode (prtIn7p8VcPbxMode=server), the only valid
       values are:
       - none
       - aBit "
      ::= {prtIn7p8VcPbxCnfgEntry 7}

prtIn7p8VcPbxOos OBJECT-TYPE
      SYNTAX  INTEGER
       {
          forcedIdle     (1),
          forcedBusy     (2)
       }
      ACCESS  read-write
      STATUS  mandatory
      DESCRIPTION
      " Out of service Signaling mode."
      ::= {prtIn7p8VcPbxCnfgEntry 8}

prtIn7p8VcPbxLinkTo OBJECT-TYPE
      SYNTAX  INTEGER
       {
       io1   (5),
       io2   (6),
       io3   (7),
       io4   (8),
       io5   (9),
       io6  (10),
       io7  (11),
       io8  (12),
       io9  (13),
       io10 (14),
       io11 (15),
       io12 (16),
       notApplicable (255)
       }
      ACCESS  read-write
      STATUS  deprecated
      DESCRIPTION
      "This object indicates the slot of the ML card to which
       the VC card is mapped.
       In the ?004 Unit the entries io6(10)..io12(16) are not valid.
       For Server mode (prtIn7p8VcPbxMode=server), this object is
       not applicable.
       Both ports, 7 and 8 should be linked to the same Slot.
       STATUS  deprecated - this object is replaced by prtGenCnfgLinkToSlot
       and prtGenCnfgLinkToPort."
      ::= {prtIn7p8VcPbxCnfgEntry 9}

--prtExVcPbxTsTable defines PABX Time Slots assignment of the
-- VC-PBX E1/T1 cards

prtExVcPbxTsTable OBJECT-TYPE
      SYNTAX SEQUENCE OF PrtExVcPbxTsEntry
      ACCESS not-accessible
      STATUS  mandatory
      DESCRIPTION
       "The write operation into the table objects is valid only
        to the TmpCnfg entry."
      ::= { prtVcPbxCnfg 4}

prtExVcPbxTsEntry OBJECT-TYPE
      SYNTAX PrtExVcPbxTsEntry
      ACCESS not-accessible
      STATUS mandatory
      DESCRIPTION "" INDEX {prtExVcPbxTsCnfgIdx, prtExVcPbxTsSltIdx, prtExVcPbxTsPrtIdx, prtExVcPbxTsIdx }
      ::= { prtExVcPbxTsTable 1}

PrtExVcPbxTsEntry ::=
      SEQUENCE {
      prtExVcPbxTsCnfgIdx        INTEGER,
      prtExVcPbxTsSltIdx         INTEGER,
      prtExVcPbxTsPrtIdx         INTEGER,
      prtExVcPbxTsIdx            INTEGER,
      prtExVcPbxTsMode           INTEGER,
      prtExVcPbxTsIConSlot       INTEGER,
      prtExVcPbxTsIConPrt        INTEGER
      }

prtExVcPbxTsCnfgIdx OBJECT-TYPE
      SYNTAX  INTEGER  (1..255)
      ACCESS  read-only
      STATUS  mandatory
      DESCRIPTION
      "This attribute indicates the Idx of the Cnfg (1..100) being
       accessed.
       Idx 255 relates to the TmpCnfg. "
      ::= { prtExVcPbxTsEntry 1}

prtExVcPbxTsSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      ACCESS  read-only
      STATUS  mandatory
      DESCRIPTION
      "This attribute indicates a unique  slot  position where
       the card is inserted.
       In the ?004 Unit the entries io6(10)..io12(16) are not valid"
      ::= { prtExVcPbxTsEntry 2}

prtExVcPbxTsPrtIdx OBJECT-TYPE
      SYNTAX  INTEGER
      {
          exPrt1    (1)
      }
      ACCESS  read-only
      STATUS  mandatory
      DESCRIPTION
      "This attribute indicates a unique  port number.
       VCPBX/E1 and VCPBX/T1 cards have only one external interface."
      ::= { prtExVcPbxTsEntry 3}

prtExVcPbxTsIdx OBJECT-TYPE
      SYNTAX  INTEGER
      ACCESS  read-only
      STATUS  mandatory
      DESCRIPTION
      "This attribute indicates a unique PABX time slot  position.
       The valid time slots are 1..24 for VC-PBX/T1 and
       1..31 for VC-PBX/E1."
      ::= { prtExVcPbxTsEntry 4}

prtExVcPbxTsMode OBJECT-TYPE
      SYNTAX  INTEGER
              {
                unused      (1),
                compressed  (2),
                transparent (3)
              }
      ACCESS  read-write
      STATUS  mandatory
      DESCRIPTION
      "This attribute indicates the usage, process and way of the
       specific PABX TS towards its destination:
       unused - the TS is not used (no processing, no destination).
       compressed - the TS is used, sent for compression to an
                internal port 1..6 of either the same card or a
                VC-PBX card of the same group.
       transparent - the TS is used, no processing, it is sent
                directly to the ML card the VC-PBX/T1,(E1) is
                linked to."
      ::= { prtExVcPbxTsEntry 5}

prtExVcPbxTsIConSlot OBJECT-TYPE
      SYNTAX  INTEGER
       {
       noConnect (2),
          io1       (5),
          io2       (6),
          io3       (7),
          io4       (8),
          io5       (9),
          io6      (10),
          io7      (11),
          io8      (12),
          io9      (13),
          io10     (14),
          io11     (15),
          io12     (16)
       }
      ACCESS  read-write
      STATUS  mandatory
      DESCRIPTION
      "The object's io1..io12 values are applicable only when
       prtExVcPbxTsMode=compressed. Otherwise, its value should be
       noConnect.
       This object indicates whether the specified compressed
       time slot is connected/routed internally in the Agent and
       to which card it is connected.
       The valid selectable slots are either the current one,
    (prtExVcPbxTsSltIdx), or a slot containing a VC-PBX card.
       In the ?004 Unit the entries io6(10)..io12(16) are not valid."
      ::= {prtExVcPbxTsEntry 6}

prtExVcPbxTsIConPrt OBJECT-TYPE
      SYNTAX  INTEGER
       {
          noConnect (100),

       inPrt1  (101) ,
       inPrt2  (102) ,
       inPrt3  (103) ,
       inPrt4  (104) ,
       inPrt5  (105) ,
          inPrt6  (106)
       }
      ACCESS  read-write
      STATUS  mandatory
      DESCRIPTION
      "This attribute indicates the internal VC-PBX port to which
       this PABX TS is connected for compression.
       noConnect - when prtExVcPbxTsIConSlot=noConnect."
      ::= {prtExVcPbxTsEntry 7}

-- The following tables contains information specific to
-- the isdn access modules

prtIsdnCnfgTable OBJECT-TYPE
      SYNTAX SEQUENCE OF PrtIsdnCnfgEntry
      ACCESS not-accessible
      STATUS  mandatory
      DESCRIPTION
       "The write operation into the table objects is valid only
        to the TmpCnfg entry."
      ::= { prtIsdnCnfg 1}

prtIsdnCnfgEntry OBJECT-TYPE
      SYNTAX PrtIsdnCnfgEntry
      ACCESS not-accessible
      STATUS mandatory
      DESCRIPTION "" INDEX {prtIsdnCnfgIdx, prtIsdnSltIdx, prtIsdnPrtIdx}
      ::= { prtIsdnCnfgTable 1}

PrtIsdnCnfgEntry ::=
      SEQUENCE {
      prtIsdnCnfgIdx           INTEGER,
      prtIsdnSltIdx            INTEGER,
      prtIsdnPrtIdx            INTEGER,
      prtIsdnConnect           INTEGER,
      prtIsdnSignalingProtocol      INTEGER,
      prtIsdnBasicRateLineTopology  INTEGER,
      prtIsdnMode              INTEGER,
      prtIsdnFilter            INTEGER,
      prtIsdnSimultaneousCall  INTEGER,
      prtIsdnNumOfAbstractTerm INTEGER,
      prtIsdnSwitchMode        INTEGER
        }

prtIsdnCnfgIdx OBJECT-TYPE
      SYNTAX  INTEGER  (1..255)
      ACCESS  read-only
      STATUS  mandatory
      DESCRIPTION
      "This attribute indicates the Idx of the Cnfg (1..100) being
       accessed.
       Idx 255 relates to the TmpCnfg. "
      ::= { prtIsdnCnfgEntry 1}

prtIsdnSltIdx OBJECT-TYPE
      SYNTAX  INTEGER
            {
              io1  (5),
              io2  (6),
              io3  (7),
              io4  (8),
              io5  (9),
              io6 (10),
              io7 (11),
              io8 (12),
              io9 (13),
              io10(14),
              io11(15),
              io12(16),
              kmxMlA (103),
              kmxMlB (104),
              notApplicable(255)
            }
      ACCESS  read-only
      STATUS  mandatory
      DESCRIPTION
      "This attribute indicates a unique  slot  position where
       the card is inserted.
       In the ?004 Unit the entries io6(10)..io12(16) are not valid
       For KM2100/4 Valid entries are 'kmxMlA ' or 'kmxMlB'"
      ::= { prtIsdnCnfgEntry 2}

prtIsdnPrtIdx OBJECT-TYPE
      SYNTAX  INTEGER
      ACCESS  read-only
      STATUS  mandatory
      DESCRIPTION
      "This attribute indicates a unique  port number.
       For MAXcess the values will be:
          exPrt1(1),
          exPrt2(2),
          exPrt3(3),
          exPrt4(4),
       For KM-2100 the port index is calculated as follows:
       100*Slot+Ch"
       ::= { prtIsdnCnfgEntry 3}

prtIsdnConnect OBJECT-TYPE
      SYNTAX  INTEGER { no(2), yes(3) }
      ACCESS  read-write
      STATUS  mandatory
      DESCRIPTION
      "This attribute indicates if the port is connected."
      ::= { prtIsdnCnfgEntry 4 }

prtIsdnSignalingProtocol OBJECT-TYPE
      SYNTAX  INTEGER
      {
        other(1), etsi(3), ess5(6), dms100(7), ni1(9),
        ni2(10), ins64(17), ins1500(18),
        notApplicable(255)
      }
      ACCESS  read-write
      STATUS  mandatory
      DESCRIPTION
      "This attribute fixes which signaling protocol
        is used at this port (D-Channel).
        It is equivalent to isdnSignalingProtocol
        in the isdn MIB."
      DEFVAL { etsi }
      ::= { prtIsdnCnfgEntry 5 }

prtIsdnBasicRateLineTopology OBJECT-TYPE
      SYNTAX  INTEGER
      {
        pointToPoint(1),
        pointToMultipoint(2),
        notApplicable(255)
      }
      ACCESS  read-write
      STATUS  mandatory
      DESCRIPTION
      "This attribute is relevant for ISDN BRI only.
        It is equivalent to isdnBasicRateLineTopology
        in the isdn MIB."
      ::= { prtIsdnCnfgEntry 6 }

prtIsdnMode OBJECT-TYPE
      SYNTAX  INTEGER
      {
        dialup(1),
        leased(2),
		syncLeased(3),
        notApplicable(255)
      }
      ACCESS  read-write
      STATUS  mandatory
      DESCRIPTION
      "This attribute allows the user to configure the port as
       leased(2) in case of connection to a TDM network."
      ::= { prtIsdnCnfgEntry 7}

prtIsdnFilter OBJECT-TYPE
      SYNTAX  INTEGER
      { notApplicable(1),
 answerAll(2), rejectAll(3),
 selective(4)
      }
      ACCESS  read-write
      STATUS  mandatory
      DESCRIPTION
      "This attribute allows the user to configure the port:
       answerAll(2): accept all incoming calls,
       rejectAll(3): reject all incoming calls,
       selective(4): accept or reject according directory table."
      ::= { prtIsdnCnfgEntry 8}

prtIsdnSimultaneousCall OBJECT-TYPE
      SYNTAX  INTEGER
      { notApplicable(1),
 accept(2), reject(3) }
      ACCESS  read-write
      STATUS  mandatory
      DESCRIPTION
      "In case of simultaneous call (local,remote and remote,local):
       accept(2): accept the incoming call,
       reject(3): reject the incoming call."
      ::= { prtIsdnCnfgEntry 9}

prtIsdnNumOfAbstractTerm OBJECT-TYPE
      SYNTAX  INTEGER
      ACCESS  read-write
      STATUS  mandatory
      DESCRIPTION
      "An object for KM2100/4 agents.
    255=Not Applicable
       When ISDN Standard = ETSI or NTT (European) the value should be 255 (NotApplicable)
       else If ML speed is 64Kbps value should be 1.
       If ML speed is 128Kbps value can be either 1 or 2 (user selection)."
      ::= { prtIsdnCnfgEntry 10}

prtIsdnSwitchMode OBJECT-TYPE
      SYNTAX  INTEGER
      {
        notApplicable(1),
        auto   (2),
        manual (3),
		connect(4)
      }
      ACCESS  read-write
      STATUS  mandatory
      DESCRIPTION
      "For KM2100.
       auto   - The call is initiated automatically by one of the IO cards connected
                to KML.10(ISDN card) having ISDN Switch Mode.
       manual - The call is initiated by the user manually,  for KML.10
                having ISDN Switch Mode (via mdlSCmd).
       connect- The call is initiated 'immediately', for KML.10 having ISDN Switch Mode.
                'immediately'- means: immediately after power-up (when product performed
                                      Reset) OR, since this value appears in the active
                 					  configuration.
                In this case, the call can be disconnected only by power-off of the
                product or by changing this object to another value (or actual Remove
                of the KML.10 relevant card).
       notApplicable - For other card types."
      ::= { prtIsdnCnfgEntry 11}

prtIsdnEndpointTable OBJECT-TYPE
      SYNTAX SEQUENCE OF PrtIsdnEndpointEntry
      ACCESS not-accessible
      STATUS  mandatory
      DESCRIPTION
       "The write operation into the table objects is valid only
        to the TmpCnfg entry."
      ::= { prtIsdnCnfg 2}

prtIsdnEndpointEntry OBJECT-TYPE
      SYNTAX PrtIsdnEndpointEntry
      ACCESS not-accessible
      STATUS mandatory
      DESCRIPTION "" INDEX {prtIsdnEndpointCnfgIdx, prtIsdnEndpointSltIdx,
        prtIsdnEndpointPrtIdx, prtIsdnEndpointIdx }
      ::= { prtIsdnEndpointTable 1}

PrtIsdnEndpointEntry ::=
      SEQUENCE {
      prtIsdnEndpointCnfgIdx        INTEGER,
      prtIsdnEndpointSltIdx         INTEGER,
      prtIsdnEndpointPrtIdx         INTEGER,
      prtIsdnEndpointIdx            INTEGER,
      prtIsdnEndpointTeiType        INTEGER,
      prtIsdnEndpointTeiValue       INTEGER,
      prtIsdnEndpointSpid           DisplayString,
	  prtIsdnEndpointBearerCh       INTEGER,
      prtIsdnEndpointRowStatus      INTEGER
        }

prtIsdnEndpointCnfgIdx OBJECT-TYPE
      SYNTAX  INTEGER  (1..255)
      ACCESS  read-only
      STATUS  mandatory
      DESCRIPTION
      "This attribute indicates the Idx of the Cnfg (1..100) being
       accessed.
       Idx 255 relates to the TmpCnfg. "
      ::= { prtIsdnEndpointEntry 1}

prtIsdnEndpointSltIdx OBJECT-TYPE
      SYNTAX  INTEGER
            {
              io1(5),
              io2(6),
              io3(7),
              io4(8),
              io5(9),
              io6(10),
              io7(11),
              io8(12),
              io9(13),
              io10(14),
              io11(15),
              io12(16),
              kmxMlA (103),
              kmxMlB (104),
              notApplicable(255)
            }
      ACCESS  read-only
      STATUS  mandatory
      DESCRIPTION
      "This attribute indicates a unique  slot  position where
       the card is inserted.
       In ?004 Unit the entries io6(10)..io12(16) are not valid
       For KM2100/4 Valid entries are 'kmxMlA ' or 'kmxMlB'"
      ::= { prtIsdnEndpointEntry 2}

prtIsdnEndpointPrtIdx OBJECT-TYPE
        SYNTAX  INTEGER
        ACCESS read-only
        STATUS mandatory
        DESCRIPTION
       "This attribute indicates a unique  port number.
         For MAXcess the values will be:
          exPrt1(1),
          exPrt2(2),
          exPrt3(3),
          exPrt4(4),
         For KM-2100 the port index is calculated as follows:
         100*Slot+Ch"
       ::= { prtIsdnEndpointEntry 3}

prtIsdnEndpointIdx OBJECT-TYPE
        SYNTAX  INTEGER { atei1(1), atei2(2) }
        ACCESS read-only
        STATUS mandatory
        DESCRIPTION
        "Since more than one endpoint may be defined per
        isdn entity, this field is a simple index.
        It corresponds to isdnEndpointIdx in the isdn MIB."
         DEFVAL { atei1 }
        ::= { prtIsdnEndpointEntry 4}

prtIsdnEndpointTeiType OBJECT-TYPE
        SYNTAX  INTEGER { dynamic(1), static(2), notApplicable(255) }
        ACCESS read-write
        STATUS mandatory
        DESCRIPTION
        "The type of TEI (Terminal Endpoint Identifier)
             used for this Terminal Endpoint. In case of dynamic(1),
             the TEI value is selected by the switch. In
             case of static(2), a valid TEI value has to be
             entered in the isdnEndpointTeiValue object.
             interface type as well as the Terminal Endpoint type.
             static(2). On Basic Rate interfaces the default value
             is dynamic(1) for isdn(63) Terminal Endpoints.
        It corresponds to isdnEndpointTeiType in the isdn MIB."
        ::= { prtIsdnEndpointEntry 5}

prtIsdnEndpointTeiValue OBJECT-TYPE
        SYNTAX  INTEGER
        ACCESS read-write
        STATUS mandatory
        DESCRIPTION
        "When the TEI Type is static, the value of the TEI should be
         between 0 and 63. Else, it is not selectable by user.
		 255 = notApplicable.
         It corresponds to isdnEndpointTeiValue in the isdn MIB"
        ::= { prtIsdnEndpointEntry 6 }

prtIsdnEndpointSpid OBJECT-TYPE
        SYNTAX  DisplayString
        ACCESS read-write
        STATUS mandatory
        DESCRIPTION
        "The Service profile IDentifier (SPID) information
         for this Terminal Endpoint. It is is composed of
         9-20 numeric characters.
        It corresponds to isdnEndpointSpid in the isdn MIB."
        ::= { prtIsdnEndpointEntry 7 }

prtIsdnEndpointBearerCh OBJECT-TYPE
        SYNTAX  INTEGER {
                notApplicable(1),
                anyChannel (2),
                channelB1  (3),
                channelB2  (4) }
        ACCESS read-write
        STATUS mandatory
        DESCRIPTION
        "This is the selected dialing channel.
         anyChannel - the system selects the dialing channel."
        ::= { prtIsdnEndpointEntry 8}

prtIsdnEndpointRowStatus OBJECT-TYPE
        SYNTAX  INTEGER { active(1), destroy(6) }
        ACCESS read-write
        STATUS mandatory
        DESCRIPTION
        "This field indicates whether to consider this endpoint
         or not."
        ::= { prtIsdnEndpointEntry 9}

prtIsdnDirectoryTable OBJECT-TYPE
      SYNTAX SEQUENCE OF PrtIsdnDirectoryEntry
      ACCESS not-accessible
      STATUS  mandatory
      DESCRIPTION
       "The write operation into the table objects is valid only
        to the TmpCnfg entry."
      ::= { prtIsdnCnfg 3}

prtIsdnDirectoryEntry OBJECT-TYPE
      SYNTAX PrtIsdnDirectoryEntry
      ACCESS not-accessible
      STATUS mandatory
      DESCRIPTION "" INDEX { prtIsdnDirectoryCnfgIdx, prtIsdnDirectorySltIdx, prtIsdnDirectoryPrtIdx }
      ::= { prtIsdnDirectoryTable 1}

PrtIsdnDirectoryEntry ::=
      SEQUENCE {
      prtIsdnDirectoryCnfgIdx   INTEGER,
      prtIsdnDirectorySltIdx         INTEGER,
      prtIsdnDirectoryPrtIdx         INTEGER,
      prtIsdnDirectoryLocalAddr    DisplayString,
      prtIsdnDirectoryLocalSubAddr   DisplayString,
      prtIsdnDirectoryRemoteAddr    DisplayString,
      prtIsdnDirectoryRemoteSubAddr  DisplayString,
      prtIsdnDirectoryPrtNu          INTEGER,
      prtIsdnDirectoryTeiId          INTEGER,
      prtIsdnDirectoryRowStatus      INTEGER,
      prtIsdnDirectoryLocalAddr2     DisplayString,
      prtIsdnDirectoryLocalSubAddr2  DisplayString,
      prtIsdnDirectoryRemoteAddr2    DisplayString,
      prtIsdnDirectoryRemoteSubAddr2 DisplayString
      }

prtIsdnDirectoryCnfgIdx OBJECT-TYPE
      SYNTAX  INTEGER  (1..255)
      ACCESS  read-only
      STATUS  mandatory
      DESCRIPTION
      "This attribute indicates the Idx of the Cnfg (1..100) being
       accessed.
       Idx 255 relates to the TmpCnfg. "
      ::= { prtIsdnDirectoryEntry 1}

prtIsdnDirectorySltIdx OBJECT-TYPE
      SYNTAX  INTEGER
            {
              io1(5),
              io2(6),
              io3(7),
              io4(8),
              io5(9),
              io6(10),
              io7(11),
              io8(12),
              io9(13),
              io10(14),
              io11(15),
              io12(16),
              kmxMlA (103),
              kmxMlB (104)
            }
      ACCESS  read-only
      STATUS  mandatory
      DESCRIPTION
      "This attribute indicates a unique  slot  position where
       the card is inserted.
       For MX300/30 ports:
       io1(5) = isdn1(5) and io2(6) = isdn2(6).
       In ?004 Unit the entries io6(10)..io12(16) are not valid
       For KM2100/4 Valid entries are 'kmxMlA ' or 'kmxMlB'"
      ::= { prtIsdnDirectoryEntry 2}

prtIsdnDirectoryPrtIdx OBJECT-TYPE
        SYNTAX  INTEGER
        ACCESS read-only
        STATUS mandatory
        DESCRIPTION
        "For MAXcess this is the internal port number: 101, 102,....
         For KM-2100 the port index is calculated as follows:
         100*Slot+Ch"
        ::= { prtIsdnDirectoryEntry 3}

prtIsdnDirectoryLocalAddr OBJECT-TYPE
        SYNTAX DisplayString (SIZE(17..20))
        ACCESS read-write
        STATUS mandatory
        DESCRIPTION
        "This is the local address associated with this
         entry.
         - For MX: Size=17 , Default=0	(17 characters)
         - For KM: Size=20, Default=blank (20 characters) "
        ::= { prtIsdnDirectoryEntry 4}

prtIsdnDirectoryLocalSubAddr OBJECT-TYPE
        SYNTAX DisplayString (SIZE(4..6))
        ACCESS read-write
        STATUS mandatory
        DESCRIPTION
        "This is the local subaddress associated with this
         entry.
         - For MX: Size=6 , Default=0	(6 characters)
         - For KM: Size=4 , Default=blank (4 characters)"
        ::= { prtIsdnDirectoryEntry 5}

prtIsdnDirectoryRemoteAddr OBJECT-TYPE
        SYNTAX DisplayString (SIZE(17..20))
        ACCESS read-write
        STATUS mandatory
        DESCRIPTION
        "This is the remote address associated with this
         entry.
         - For MX: Size=17 , Default=0	(17 characters)
         - For KM: Size=20, Default=blank (20 characters)"
        ::= { prtIsdnDirectoryEntry 6}

prtIsdnDirectoryRemoteSubAddr OBJECT-TYPE
        SYNTAX  DisplayString (SIZE(4..6))
        ACCESS read-write
        STATUS mandatory
        DESCRIPTION
        "This is the remote subaddress associated with this
         entry.
         - For MX: Size=6 , Default=0 (6 characters)
         - For KM: Size=4 , Default=blank (4 characters)"
        ::= { prtIsdnDirectoryEntry 7}


prtIsdnDirectoryPrtNu OBJECT-TYPE
        SYNTAX  INTEGER
        ACCESS read-write
        STATUS mandatory
        DESCRIPTION
        "This is the external port number connected to
         this entry."
         DEFVAL { 1 }
        ::= { prtIsdnDirectoryEntry 8}

prtIsdnDirectoryTeiId OBJECT-TYPE
        SYNTAX  INTEGER
        ACCESS read-write
        STATUS mandatory
        DESCRIPTION
        "This is the abstract terminal id if relevant,
        connected to this entry."
        DEFVAL { 1 }
        ::= { prtIsdnDirectoryEntry 9}

prtIsdnDirectoryRowStatus OBJECT-TYPE
        SYNTAX  INTEGER { active(1), destroy(6) }
        ACCESS read-write
        STATUS mandatory
        DESCRIPTION
        "This is the status for the row. It allows to know
        whether to consider this row or not."
        ::= { prtIsdnDirectoryEntry 10}

prtIsdnDirectoryLocalAddr2 OBJECT-TYPE
        SYNTAX DisplayString (SIZE(17..20))
        ACCESS read-write
        STATUS mandatory
        DESCRIPTION
        "This is the second local address associated with this
         entry.
         - For MX: Size=17 , Default=0 (17 characters)
         - For KM: Size=20, Default=blank (20 characters)"
        ::= { prtIsdnDirectoryEntry 11}

prtIsdnDirectoryLocalSubAddr2 OBJECT-TYPE
        SYNTAX DisplayString (SIZE(4..6))
        ACCESS read-write
        STATUS mandatory
        DESCRIPTION
        "This is the second local subaddress associated with this
         entry.
         - For MX: Size=6 , Default=0 (6 characters)
         - For KM: Size=4 , Default=blank (4 characters)"
        ::= { prtIsdnDirectoryEntry 12}

prtIsdnDirectoryRemoteAddr2 OBJECT-TYPE
        SYNTAX DisplayString (SIZE(17..20))
        ACCESS read-write
        STATUS mandatory
        DESCRIPTION
        "This is the second remote address associated with this
         entry.
         - For MX: Size=17 , Default=0 (17 characters)
         - For KM: Size=20, Default=blank(20 characters) "
        ::= { prtIsdnDirectoryEntry 13}

prtIsdnDirectoryRemoteSubAddr2 OBJECT-TYPE
        SYNTAX  DisplayString (SIZE(4..6))
        ACCESS read-write
        STATUS mandatory
        DESCRIPTION
        "This is the second remote subaddress associated with this
         entry.
         - For MX: Size=6 , Default=0 (6 characters)
         - For KM: Size=4 , Default=blank (4 characters) "
        ::= { prtIsdnDirectoryEntry 14}



-- This table is an extension for new version of MAXcess
-- modules.
prtFrPlusCnfgTable  OBJECT-TYPE
     SYNTAX SEQUENCE OF PrtFrPlusCnfgEntry
     ACCESS not-accessible
     STATUS  mandatory
     DESCRIPTION
      "The write operation into the Table Objects is valid only
       to the TmpCnfg entry."
     ::= {prtFrPlusCnfg 1}

prtFrPlusCnfgEntry OBJECT-TYPE
      SYNTAX PrtFrPlusCnfgEntry
      ACCESS not-accessible
      STATUS mandatory
      DESCRIPTION "" INDEX {prtFrPlusCnfgIdx, prtFrPlusSltIdx, prtFrPlusPrtIdx }
      ::= { prtFrPlusCnfgTable 1}

PrtFrPlusCnfgEntry ::=
      SEQUENCE {
      prtFrPlusCnfgIdx   INTEGER,
      prtFrPlusSltIdx    INTEGER,
      prtFrPlusPrtIdx   INTEGER,
      prtFrPlusNotSegmentedPriorities  OCTET STRING
}

prtFrPlusCnfgIdx OBJECT-TYPE
      SYNTAX  INTEGER (1..255)
      ACCESS  read-only
      STATUS  mandatory
      DESCRIPTION
      "This attribute indicates the Idx of the Cnfg (1..100) being
       accessed.
       Idx 255 relates to the TmpCnfg. "
      ::= { prtFrPlusCnfgEntry 1}

prtFrPlusSltIdx OBJECT-TYPE
      SYNTAX  INTEGER
            {
              io1   (5),
              io2   (6),
              io3   (7),
              io4   (8),
              io5   (9),
              io6  (10),
              io7  (11),
              io8  (12),
              io9  (13),
              io10 (14),
              io11 (15),
              io12 (16),
       notApplicable(255)
            }
      ACCESS  read-only
      STATUS  mandatory
      DESCRIPTION
        "Slot Index.
         For ISDN BRI Ports of MX300/30,
    io1(5) = isdn1(5) and io2(6) = isdn2(6)."
      ::= { prtFrPlusCnfgEntry 2}

prtFrPlusPrtIdx  OBJECT-TYPE
      SYNTAX  INTEGER
      ACCESS  read-only
      STATUS  mandatory
      DESCRIPTION
      "This attribute indicates a unique  port number.
       This port number should be:
       - for ISDN cards: inPrt1(101)->inPrt50(150)
       - for MHS1 card : exPrt1(1)
       - for MHS3, MLS3 cards: exPrt1(1)->exPrt3(3)
       - for MLS6 cards: exPrt1(1)->exPrt6(6)."
      ::= { prtFrPlusCnfgEntry 3}

prtFrPlusNotSegmentedPriorities OBJECT-TYPE
       SYNTAX OCTET STRING(SIZE(1))
       ACCESS   read-write
       STATUS   mandatory
       DESCRIPTION
      "This parameter is relevant only for FR+ protocol and
       asks the MXcess NOT to segment data with specified
       priorities:  from LSB:
       bit 1  is for priority 1,
       bit 2  is for priority 2, .... till bit 7 for priority 7.
	   - a priority selected to be segmented : its bit will be '0'
	   - a priority not to be segmented : its bit will be '1'
       Default is 00000000; i.e, segment all priorities."
     DEFVAL { '00'H }
     ::= { prtFrPlusCnfgEntry 4 }


-- This table is an extension of prtExPh1MlCnfgTable for MTML-4 cards
-- of MP-2200

    prtMl4CnfgTable  OBJECT-TYPE
     SYNTAX SEQUENCE OF PrtMl4CnfgEntry
     ACCESS not-accessible
     STATUS  mandatory
     DESCRIPTION
      "This is an extension table for MTML-4 card parameters."
     ::= {prtMl4Cnfg 1}

prtMl4CnfgEntry OBJECT-TYPE
      SYNTAX PrtMl4CnfgEntry
      ACCESS not-accessible
      STATUS mandatory
      DESCRIPTION "" INDEX {prtMl4CnfgIdx, prtMl4SltIdx, prtMl4PrtIdx }
      ::= { prtMl4CnfgTable 1}

PrtMl4CnfgEntry ::=
      SEQUENCE {
      prtMl4CnfgIdx        INTEGER,
      prtMl4SltIdx         INTEGER,
      prtMl4PrtIdx         INTEGER,
      prtMl4SigProfile     INTEGER,
      prtMl4CGA            INTEGER,
      prtMl4Oos            INTEGER,
      prtMl4VoiceOos  OCTET STRING,
      prtMl4DataOos   OCTET STRING,
	  prtMl4Service        INTEGER
      }


prtMl4CnfgIdx OBJECT-TYPE
      SYNTAX  INTEGER (1..255)
      ACCESS  read-only
      STATUS  mandatory
      DESCRIPTION
      "This attribute indicates the Idx of the Cnfg (1..100) being
       accessed.
       Idx 255 relates to the TmpCnfg. The write operation is valid only
       to the TmpCnfg."
      ::= { prtMl4CnfgEntry 1}

prtMl4SltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      ACCESS  read-only
      STATUS  mandatory
      DESCRIPTION
      "This attribute indicates a unique  slot  position where
       the module is inserted."
      ::= { prtMl4CnfgEntry 2}

prtMl4PrtIdx OBJECT-TYPE
      SYNTAX  INTEGER
       {
       exPrt1    (1),
       exPrt2    (2),
       exPrt3    (3),
       exPrt4    (4)
       }
      ACCESS  read-only
      STATUS  mandatory
      DESCRIPTION
      "This attribute indicates a unique  port number."
      ::= { prtMl4CnfgEntry 3}

prtMl4SigProfile OBJECT-TYPE
      SYNTAX  INTEGER
       {
       notApplicable (1),
       none          (2),
       p1            (3),
       p2            (4),
       p3            (5),
       p4            (6),
       p5            (7)
       }
      ACCESS  read-write
      STATUS  mandatory
      DESCRIPTION
      "This object indicates the Signaling Profile of the port.
       none - when the Frame is G732N (no MF).
       p1 = profile 1
       p2 = profile 2
       p3 = profile 3
       p4 = profile 4
       p5 = profile 5 "
      ::= {prtMl4CnfgEntry 4}

prtMl4CGA OBJECT-TYPE
    SYNTAX  INTEGER {
      none (1),
      trans(2),
      full (3)
            }
    ACCESS  read-write
    STATUS  mandatory
    DESCRIPTION
    "This object selects the method used to signal the CGA state
     to the other end, through the main link.
     'none'  - non-transparent mode. When one of the links
               (main) will be in Out Of Service state, both
               'Data/Voice Oos' and 'Oos' will be
               transmitted to the other end.
     'trans' - when one of the links (main) will be in Out
               Of Service state, 'Data/Voice Oos' will be
               transmitted to the other end.
     'full'  - fully-transparent mode. When one of the links
                  (main) will be in Out Of Service state,
                  neither 'Data/Voice Oos' nor 'Oos' will
                  be transmitted to the other end."
 ::= { prtMl4CnfgEntry 5 }

prtMl4Oos  OBJECT-TYPE
      SYNTAX  INTEGER
       {
        notSupported  (2),
        forcedIdle    (3),
        forcedBusy    (4),
        busyIdle      (5),
        idleBusy      (6)
       }
      ACCESS  read-write
      STATUS  mandatory
      DESCRIPTION
      "'idle' = '0' = on-hook, idle state
       'busy' = '1' = off-hook, busy state
       'forcedIdle' = SP = both A and B signaling bits are forced
                      to '0' during out-of-service periods.
       'forcedBusy' = MK = both A and B signaling bits are forced
                      to '1' during out-of-service periods.
       'busyIdle'   = MK_SP = A and B bits are forced to '1' for
                      2.5 seconds; then they are switched to '0'
                      until out-of-service condition disappears.
       'idleBusy'   = SP_MK = A and B bits are forced to '0' for
                      2.5 seconds; then they are switched to '1'
                      until out-of-service condition disappears.
       - for T1:    '0'=0   ;  '1'=1
       - for E1:    '0'=1   ;  '1'=0   "
   ::= { prtMl4CnfgEntry 6 }

prtMl4VoiceOos  OBJECT-TYPE
 SYNTAX  OCTET STRING (SIZE (0..4))
    ACCESS  read-write
    STATUS  mandatory
    DESCRIPTION
    "Voice Out-Of-Service code. Valid range: (0 - FF HEX).
     For agents that do not support this feature, the value will
     always be 0."
   ::= { prtMl4CnfgEntry 7 }

prtMl4DataOos  OBJECT-TYPE
 SYNTAX  OCTET STRING (SIZE (0..4))
    ACCESS  read-write
    STATUS  mandatory
    DESCRIPTION
    "Data Out-Of-Service code. Valid range: (0 - FF HEX).
     For agents that do not support this feature, the value will
     always be 0."
   ::= { prtMl4CnfgEntry 8 }

prtMl4Service OBJECT-TYPE
      SYNTAX  INTEGER
       {
       notApplicable (1),
       leasedLine    (2),
       v51           (3)
       }
      ACCESS  read-write
      STATUS  mandatory
      DESCRIPTION
      "Link Service.
       leasedLine - usual TDM interface.
       v51        - V5.1 interface. "
      ::= {prtMl4CnfgEntry 9}


--prtAcmCnfgTable defines the parameters of the
--ACM cards family external ports 1-8

prtAcmCnfgTable  OBJECT-TYPE
     SYNTAX SEQUENCE OF PrtAcmCnfgEntry
     ACCESS not-accessible
     STATUS  mandatory
     DESCRIPTION
      "This is a table for ACM port parameters."
     ::= {prtAcmCnfg 1}

prtAcmCnfgEntry OBJECT-TYPE
      SYNTAX PrtAcmCnfgEntry
      ACCESS not-accessible
      STATUS mandatory
      DESCRIPTION "" INDEX {prtAcmCnfgIdx, prtAcmSltIdx, prtAcmPrtIdx }
      ::= { prtAcmCnfgTable 1}

PrtAcmCnfgEntry ::=
      SEQUENCE {
      prtAcmCnfgIdx        INTEGER,
      prtAcmSltIdx         INTEGER,
      prtAcmPrtIdx         INTEGER,
      prtAcmConnect        INTEGER,
      prtAcmActiveState    INTEGER,
      prtAcmAlrString      DisplayString
      }

prtAcmCnfgIdx OBJECT-TYPE
      SYNTAX  INTEGER (1..255)
      ACCESS  read-only
      STATUS  mandatory
      DESCRIPTION
      "This attribute indicates the Idx of the Cnfg (1..100) being
       accessed.
       Idx 255 relates to the TmpCnfg. The write operation is valid only
       to the TmpCnfg."
      ::= { prtAcmCnfgEntry 1}

prtAcmSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      ACCESS  read-only
      STATUS  mandatory
      DESCRIPTION
      "This attribute indicates a unique  slot  position where
       the module is inserted."
      ::= { prtAcmCnfgEntry 2}

prtAcmPrtIdx OBJECT-TYPE
      SYNTAX  INTEGER
       {
       exPrt1    (1),
       exPrt2    (2),
       exPrt3    (3),
       exPrt4    (4),
       exPrt5    (5),
       exPrt6    (6),
       exPrt7    (7),
       exPrt8    (8) ,
       exPrt9    (9) ,
       exPrt10  (10) ,
       exPrt11  (11) ,
       exPrt12  (12)
       }
      ACCESS  read-only
      STATUS  mandatory
      DESCRIPTION
      "This attribute indicates a unique  port number."
      ::= { prtAcmCnfgEntry 3}

prtAcmConnect OBJECT-TYPE
      SYNTAX  INTEGER
              {
                no  (2),
                yes (3)
              }
      ACCESS  read-write
      STATUS  mandatory
      DESCRIPTION
      "This attribute indicates whether the port should be
       connected or not. Only a connected port can perform activity."
      ::= {prtAcmCnfgEntry 4}

prtAcmActiveState OBJECT-TYPE
      SYNTAX  INTEGER
              {
                low  (2),
                high (3)
              }
      ACCESS  read-write
      STATUS  mandatory
      DESCRIPTION
      "This attribute indicates the Electric Active State of the port."
      ::= {prtAcmCnfgEntry 5}

prtAcmAlrString OBJECT-TYPE
        SYNTAX DisplayString (SIZE(0..35))
        ACCESS read-write
        STATUS mandatory
        DESCRIPTION
        "Alarm string selected by user for the Inbound ports.
         This object is applicable only for the Inbound Ports: ext-5..ext-12.
         For the Outbound Ports (ext-1..ext-4), the size of this string will be 0."
      ::= {prtAcmCnfgEntry 6}

--
-- The following table includes the IP addresses of all the NMS to which
-- Traps will be sent
--

--mngTrapIpTable  OBJECT-TYPE
--      SYNTAX  SEQUENCE OF MngTrapIpEntry
--      ACCESS  not-accessible
--      STATUS mandatory
--      DESCRIPTION
--        "This table indicates  the destination address of the traps.
--         Internally it will be limited to ten addresses. "
--      ::= { agnt 7 }
--
--mngTrapIpEntry OBJECT-TYPE
--      SYNTAX  MngTrapIpEntry
--      ACCESS  not-accessible
--      STATUS  mandatory
--      INDEX   { mngTrapIpIdx }
--      ::= { mngTrapIpTable 1 }
--
--MngTrapIpEntry  ::=
--      SEQUENCE {
--      mngTrapIpIdx   INTEGER,
--      mngTrapIpIP    IpAddress,
--      mngTrapIpIPMask IpAddress
--      }
--
--mngTrapIpIdx OBJECT-TYPE
--      SYNTAX  INTEGER
--      ACCESS  read-only
--      STATUS mandatory
--      DESCRIPTION
--      " This value indicates an index of a specific IP address"
--      ::= { mngTrapIpEntry 1 }
--
--mngTrapIpIP OBJECT-TYPE
--      SYNTAX  IpAddress
--      ACCESS  read-write
--      STATUS mandatory
--      DESCRIPTION
--      "This value indicates  the  destination addresses of the traps. "
--      ::= { mngTrapIpEntry 2 }
--
--mngTrapIpIPMask OBJECT-TYPE
--      SYNTAX  IpAddress
--      ACCESS  read-write
--      STATUS mandatory
--      DESCRIPTION
--      "This value indicates  the  mask of the destination addresses of the traps. "
--      ::= { mngTrapIpEntry 3 }
--
--
-- Traps

 alarmsTrap  TRAP-TYPE
     ENTERPRISE      muxHub
     VARIABLES       { alrBufDescription }
     DESCRIPTION
     "This trap is sent whenever alarm occurs in the agent."
     ::= 1

  sanityTrap  TRAP-TYPE
     ENTERPRISE      muxHub
     VARIABLES       { agnSSanityCheckStatus, agnCSaveCnfgIdxCmd }
     DESCRIPTION
     "This trap is sent after a data base update.
      It returns the sanity result status and the configuration no.
      checked.
      If the result is of Flip DB Sanity Check, the configuration
      no. sent will be 0.
      If the result is of Variant Sanity Check, the configuration
      no. sent will be 100."
     ::= 2

  cnfgFlipTrap  TRAP-TYPE
     ENTERPRISE      muxHub
     VARIABLES       { agnSActiveCnfg }
     DESCRIPTION
     "This trap is sent upon change of the active Configuration DB.
      Attached, is the new active Configuration no."
     ::= 3

  flipDbChangeTrap  TRAP-TYPE
     ENTERPRISE      muxHub
     DESCRIPTION
     "This trap is sent upon change of the active Flip tables
      (Flip DB)."
     ::= 4

  statusChangedTrap  TRAP-TYPE
     ENTERPRISE      muxHub
     VARIABLES       { agnLed }
     DESCRIPTION
     "This trap is sent upon any change of the LEDs status."
     ::= 5
-- 
-- file :v:\doc\rdv\mib\ver450\tsa.txt
-- 

--Title:  RAD's WAN TSA (Time-Slot Assignment) MIB
--By:     Smadar Tauber
--Date :  30.11.1998

--Last Update: 10/03/99 - agnTsDirection Description was updated 
--By: Smadar 
--File:  v:\doc\rdv\mib\ver450\tsa.txt

--***********************************************************************
--Products that use this file WITHOUT the MPMX.TXT file,have to add the
--following definitions to their *.pkb files:
--
--wanGen   OBJECT IDENTIFIER ::= {radWan 1}
--agnWanGen   OBJECT IDENTIFIER ::= {wanGen 2}
--agnSystemTs      OBJECT IDENTIFIER ::= {agnWanGen 11}
--***********************************************************************

--
-- TS Assignment Table from system point of view
--

agnTsTable  OBJECT-TYPE
     SYNTAX SEQUENCE OF AgnTsEntry
     ACCESS not-accessible
     STATUS  mandatory
     DESCRIPTION
     "The write operation into the Table Objects is valid only
      to the TmpCnfg entry."
     ::= { agnSystemTs 1}

agnTsEntry OBJECT-TYPE
      SYNTAX AgnTsEntry
      ACCESS not-accessible
      STATUS mandatory
      DESCRIPTION "" INDEX {agnTsCnfgIdx, agnTsSltIdx, agnTsPrtIdx, agnTsIdx,
             agnTsBitIdx, agnTsConSltIdx, agnTsConPrtIdx, agnTsConIdx }
      ::= { agnTsTable 1}

AgnTsEntry ::=
      SEQUENCE {
     agnTsCnfgIdx   INTEGER,
     agnTsSltIdx    INTEGER,
     agnTsPrtIdx    INTEGER,
     agnTsIdx       INTEGER,
     agnTsBitIdx    INTEGER,
     agnTsConSltIdx INTEGER,
     agnTsConPrtIdx INTEGER,
     agnTsConIdx    INTEGER,
     agnTsType      INTEGER,
     agnTsRowStatus INTEGER,
	 agnTsDirection INTEGER
      }


agnTsCnfgIdx OBJECT-TYPE
      SYNTAX  INTEGER (1..255)
      ACCESS  read-only
      STATUS  mandatory
      DESCRIPTION
      "This attribute indicates the Idx of the Cnfg (1..100) being
       accessed.
       Idx 255 relates to the TmpCnfg. "
      ::= { agnTsEntry 1}

agnTsSltIdx OBJECT-TYPE
      SYNTAX  INTEGER
     { io1   (5),
       io2   (6),
       io3   (7),
       io4   (8),
       io5   (9),
       io6  (10),
       io7  (11),
       io8  (12),
       io9  (13),
       io10 (14),
       io11 (15),
       io12 (16),
       io13 (17),
       io14 (18),
       io15 (19),
       notApplicable(255)
     }
      ACCESS  read-only
      STATUS  mandatory
      DESCRIPTION
      "This attribute indicates a unique  slot  position where
       the card is inserted."
      ::= { agnTsEntry 2}

agnTsPrtIdx OBJECT-TYPE
      SYNTAX  INTEGER
      ACCESS  read-only
      STATUS  mandatory
      DESCRIPTION
      "This attribute indicates a unique external or internal port number.
       For MP:
        exPrt1    (1) ,
        exPrt2    (2) ,
        exPrt3    (3) ,
        exPrt4    (4) ,
        exPrt5    (5) ,
        exPrt6    (6) ,
        exPrt7    (7) ,
        exPrt8    (8) ,
        exPrt9    (9) ,
        exPrt10  (10) ,
        exPrt11  (11) ,
        exPrt12  (12) ,

        inPrt1  (101) ,
        inPrt2  (102) ,
        inPrt3  (103) ,
        inPrt4  (104) ,
        inPrt5  (105) ,
        inPrt6  (106) ,
        inPrt7  (107) ,
        inPrt8  (108) ,
        inPrt9  (109) ,
        inPrt10 (110) ,
        inPrt11 (111) ,
        inPrt12 (112)   "
      ::= { agnTsEntry 3}

agnTsIdx OBJECT-TYPE
      SYNTAX  INTEGER (1..32)
      ACCESS  read-only
      STATUS  mandatory
      DESCRIPTION
      "This attribute indicates a unique index for TS (Time-Slot).
       - for T1 ports - 1..24, Fbit(25)
       - for E1 ports - 1..31
       - for HDSL ports - 1..32 ; 32 will represent TS0."
      ::= { agnTsEntry 4}

agnTsBitIdx OBJECT-TYPE
      SYNTAX  INTEGER
      ACCESS  read-only
      STATUS  mandatory
      DESCRIPTION
      "This attribute indicates a unique index for the Bit
       of each TS (Time-Slot).
       1..8 - Bit 1.. Bit 8
       255  - notApplicable
       This object is applicable only in Split Time-Slot cases."
      ::= { agnTsEntry 5}

agnTsConSltIdx OBJECT-TYPE
      SYNTAX  INTEGER
   {   io1   (5),
       io2   (6),
       io3   (7),
       io4   (8),
       io5   (9),
       io6  (10),
       io7  (11),
       io8  (12),
       io9  (13),
       io10 (14),
       io11 (15),
       io12 (16),
       io13 (17),
       io14 (18),
       io15 (19),
       notApplicable(255)
       }
      ACCESS  read-only
      STATUS  mandatory
      DESCRIPTION
      "This attribute indicates a unique slot position In the Mux
       where the TS is routed to."
      ::= { agnTsEntry 6}

agnTsConPrtIdx OBJECT-TYPE
      SYNTAX  INTEGER
      ACCESS  read-only
      STATUS  mandatory
      DESCRIPTION
      "This attribute indicates a unique port id the TS is 
       routed to.
	   notApplicable - when agnTsType=mng or spare
       For MP:
       exPrt1    (1) .. exPrt12  (12) ,
       notApplicable(100),
       inPrt1  (101) .. inPrt48 (148). "
      ::= { agnTsEntry 7}


agnTsConIdx OBJECT-TYPE
      SYNTAX  INTEGER    (1..255)
      ACCESS  read-only
      STATUS  mandatory
      DESCRIPTION
      "This attribute indicates a unique TS number the Src TS is 
       routed to.
	   Valid values:
       - for T1 ports - 1..24, Fbit(25)
       - for E1 ports - 1..31
       - for HDSL ports - 1..32 ; 32 will represent TS0.
       - notApplicable - 255 (for ports that don't have TSs)."
      ::= { agnTsEntry 8}

agnTsType  OBJECT-TYPE
      SYNTAX  INTEGER
      {
       unknown   (1),
       voice     (2),
       data      (3),
       vcMP      (4),
       mng       (6),
	   spare     (7)
      }
      ACCESS  read-write
      STATUS  mandatory
      DESCRIPTION
      "Time-Slot Type - regarding its connection and media type.
       voice, data, vcMP - connected and the media is specified.
       mng - management. This TS is Dedicated to Management (not
             disconnected, but not connected to another port).
       spare - applicable for ML-20 only. These TSs should be reserved for future
             connection, though at the moment are not connected."
   ::= { agnTsEntry 9}

agnTsRowStatus OBJECT-TYPE
      SYNTAX  INTEGER
      { active  (1),
        destroy (6)
      }
      ACCESS  read-write
      STATUS  mandatory
      DESCRIPTION
      "This attribute allows to create/delete a row in this table.
        For creating a row, the NMS should set
        agnTsRowStatus.255.id2.id3.id4.id5.id6.id7.id8 = active(1).
        For destroying a row, the NMS should set:
        agnTsRowStatus.255.id2.id3.id4.id5.id6.id7.id8 = destroy(6).
        Only rows with status active(1) are relevant."
      ::= { agnTsEntry 10}

agnTsDirection  OBJECT-TYPE
      SYNTAX  INTEGER
      {
       notApplicable (1),
       rx            (2),
       tx            (3),
       both          (4),
       bcastSrc      (5),
	   bcastDst      (6)
      }
      ACCESS  read-write
      STATUS  mandatory
      DESCRIPTION
      "Direction of the connection. This parameter is especially important
	   when in MP a ML is connected to an IO port that has no TSs, so it doesn't
	   appear in the TS Assignment for the first 5 indexes.
	   notApplicable - for products that do not support this object	or for
	        certain TS Types (for example: mng, spare)
       rx - the ML only Receives from the IO Port (the ML will appear in the
            first 5 indexes).
       tx - the ML only Transmits to the IO Port (the ML will appear in the
            first 5 indexes). Nothing is received back.
       both - the ML Receives and Transmits to the IO Port (the ML will appear in the
            first 5 indexes).
       bcastSrc - the ML is a Broadcast-Bidirectional Source. It Transmits to
            one or several IO Ports (including the one that appears in the last
            3 indexes) and sometimes receives.
            The Port that responds is dynamic (it can be another each time).
            The ML will appear in the first 5 indexes.
       bcastDst - the ML is a Broadcast-Bidirectional Destination. Therefore,
             it Receives and sometimes Transmits.  The ML will appear in the
             first 5 indexes."
      ::= { agnTsEntry 11}

-- 
-- file :v:\doc\rdv\mib\ver450\dacs.txt
-- 

--Title:     RAD's DACS PRODUCTS MIB
--Version:   3.0
--Date:      27.04.95
--By:        Smadar Tauber
--File:      dacs.txt
--
--Last update: 01.07.99 Smadar  


dacsMux       OBJECT IDENTIFIER ::= {radWan 3}

systemDacsMux OBJECT IDENTIFIER ::= {dacsMux 1}
mdlDacsMux    OBJECT IDENTIFIER ::= {dacsMux 2}
prtDacsMux    OBJECT IDENTIFIER ::= {dacsMux 3}
genDacsMux    OBJECT IDENTIFIER ::= {dacsMux 4}
    

--System level of DACS MIB
--
--Sa  - data specific to a stand-alone unit
--Hub - data specific to a Hub unit
--Rest of the branches are common to both types of units.

sysSa         OBJECT IDENTIFIER ::= {systemDacsMux 1}
sysHub        OBJECT IDENTIFIER ::= {systemDacsMux 2}
sysStatus     OBJECT IDENTIFIER ::= {systemDacsMux 3}
sysCurrentAlr OBJECT IDENTIFIER ::= {systemDacsMux 4}
sysBufferAlr  OBJECT IDENTIFIER ::= {systemDacsMux 5}
sysConfig     OBJECT IDENTIFIER ::= {systemDacsMux 6}
sysDbase      OBJECT IDENTIFIER ::= {systemDacsMux 7}


--Stand-alone specific parameters

sysSaSwchStatus OBJECT-TYPE
      SYNTAX  INTEGER
      ACCESS  read-only
      STATUS  mandatory
      DESCRIPTION
      "This object indicates the status of the switches on 
       the SA unit.
       Each switch is represented by a bit. The status is a sum
       of 2**n, according to the bits.
       
	   For SMODs products see modem's specification.
	   
	   For DXC product see the following:
       There are 4 switches:
       bit 0  SP-PAR (LSB)  '1' - Default parameters    
       bit 1  PSWRD         '1' - Password=default
                            '0' - Password=user selected
       bit 2  DB-INIT       '1' - DB initiated with default
                            '0' - DB initiated with NVRAM contents 
       bit 3  PC-SP  (MSB)  '1' - Management by terminal only
                            '0' - Management by NMS
       Example: If SP-PAR  and PSWRD bits are set ('1'), the value
             will be 3 (2**1 + 2**0).
       When the status of the switches is unknown, the value of
       this object will be 255."
      ::= { sysSa 1}

sysSaSwRevision OBJECT-TYPE
      SYNTAX  DisplayString (SIZE (0..255))
      ACCESS  read-only
      STATUS  mandatory
      DESCRIPTION
      "This object indicates the Software revision of the 
       system."
      ::= {sysSa 2}

sysSaHwVersion OBJECT-TYPE
      SYNTAX  DisplayString (SIZE (0..255))
      ACCESS  read-only
      STATUS  mandatory
      DESCRIPTION
      "This object indicates the Hardware version of the 
       system."
      ::= {sysSa 3}

sysSaPorts OBJECT-TYPE
      SYNTAX  INTEGER
      ACCESS  read-only
      STATUS  mandatory
      DESCRIPTION
   "This object indicates the ports that are present in the 
    system.
    Each possible port is represented by a bit.
    The value of this object is a sum of 2**n, n=number of bits.
    '1' - means that the port exists
    '0' - means that the port does not exist
    For detailed bit assignment, see product's spec.
    Bit 0 = LSB
    When this object is not relevant, the value will be 0.
    In some cases, this object may represent ports configuration
    of the system AND its far-end unit."
   ::= {sysSa 4}

sysSaReadSwch OBJECT-TYPE
      SYNTAX  INTEGER
      ACCESS  read-write
      STATUS  mandatory
      DESCRIPTION
      "This object indicates wether the configuration will be read from the DIP switches
       on the SA (stand alone) unit.
       Each switch is represented by a bit.
       If the bit is 1: the configuration will be read from the HW switch position.
       If the bit is 0: the configuration will be read from the SW user configuration.
       
       The DIP switches are different in each of the RAD devices.
       In the Tiny Router (starting from the LSB) the following switches exist:
       Bit 0: WAN Loop
       Bit 1: LAN Full Duplex (When LAN AUI connector, it is SQE)
       Bit 2: PPP (When WAN 4 Wire connector, it is LONG)
       Bit 3: IP Learn"
   ::= {sysSa 5}


--Hub specific parameters

--Hub Cassis data

sysChas  OBJECT IDENTIFIER ::= {sysHub 1}

chassTotalNoOfSlt  OBJECT-TYPE
      SYNTAX  INTEGER
      ACCESS  read-only
      STATUS  mandatory
      DESCRIPTION
      "This object indicates the number of physical slots in 
       the Hub chassis."
      ::= { sysChas 1 }

chassTotalNoOfIoSlt  OBJECT-TYPE
      SYNTAX  INTEGER
      ACCESS  read-only
      STATUS  mandatory
      DESCRIPTION
      "This object indicates the total number of physical IO slots 
       in the chassis, (not all slots must be occupied and active)."
      ::= { sysChas 2 }

chassTotalNoOfPsSlt  OBJECT-TYPE
      SYNTAX  INTEGER
      ACCESS  read-only
      STATUS  mandatory
      DESCRIPTION
      "This object indicates the number of physical Power Supply 
       slots in the chassis."
      ::= { sysChas 3 }

chassTotalNoOfClSlt  OBJECT-TYPE
      SYNTAX  INTEGER
      ACCESS  read-only
      STATUS  mandatory
      DESCRIPTION
      "This object indicates the number of physical Common Logic 
       slots in the chassis."
      ::= { sysChas 4 }

chassTotalNoOfMlSlt  OBJECT-TYPE
      SYNTAX  INTEGER
      ACCESS  read-only
      STATUS  mandatory
      DESCRIPTION
      "This object indicates the number of physical Main Link 
       slots in the chassis (Kmux)."
      ::= { sysChas 5 }


--Hub DCL parameters

sysDcl  OBJECT IDENTIFIER ::= {sysHub 2}


sysDclTable  OBJECT-TYPE
      SYNTAX SEQUENCE OF SysDclEntry
      ACCESS not-accessible
      STATUS  mandatory
      DESCRIPTION
      "All the entries of this table are identical (have the 
       same value) for all the configurations (1..255) except 
       the TmpCnfg.
       The write operation into the Table Objects is valid only
       for the TmpCnfg entry."
       ::= { sysDcl 1}

sysDclEntry OBJECT-TYPE
      SYNTAX SysDclEntry
      ACCESS not-accessible
      STATUS mandatory
      DESCRIPTION "" INDEX {sysDclCnfgIdx}
      ::= { sysDclTable 1}

SysDclEntry ::=
      SEQUENCE {
   		sysDclCnfgIdx       INTEGER,
   		sysDclRedundancy    INTEGER,
   		sysDclActiveCl      INTEGER,
   		sysDclFlipDelay     INTEGER
      }

sysDclCnfgIdx OBJECT-TYPE
      SYNTAX INTEGER (1..255)
      ACCESS read-only
      STATUS mandatory
      DESCRIPTION
      "This object indicates the Idx of the Cnfg(1..255) 
       being accessed ; Idx of 255 relates to the TmpCnfg.
       This object is identical for all the configurations (1..255).
       Only the TmpCnf(255) might have a  different value."
      ::= { sysDclEntry 1}
-- In phase I only the values 1 (Cnfg1) and 255 (temp) are valid.


sysDclRedundancy  OBJECT-TYPE
      SYNTAX  INTEGER
   {
   off (2),
   on  (3)
   }
      ACCESS  read-write
      STATUS  mandatory
      DESCRIPTION
   " DCL redundancy desired state."
   ::= {sysDclEntry 2}

sysDclActiveCl  OBJECT-TYPE
      SYNTAX  INTEGER
   {
   auto (1),
   dclA (2),
   dclB (3)
   }
      ACCESS  read-write
      STATUS  mandatory
      DESCRIPTION
   "Active desired DCL.
    When 'auto' is selected, the system automatically selects
    the active DCL."
   ::= {sysDclEntry 3}

sysDclFlipDelay  OBJECT-TYPE
      SYNTAX  INTEGER
   {
   t1min (1),
   t2min (2),
   t3min (3),
   t4min (4)
   }    
      ACCESS  read-write
      STATUS  mandatory
      DESCRIPTION
   "If one DCL flip occured and a second one should be
    performed, the time from the previous flip is checked.
    If the time is shorter than the delay specified here
    (in minutes), the system should delay the flip operation 
    until time reaches the specified delay."
   ::= {sysDclEntry 4}

sysDclOnline  OBJECT-TYPE
      SYNTAX  INTEGER
   {
   dclA (1),
   dclB (2)
   }
      ACCESS  read-only
      STATUS  mandatory
      DESCRIPTION
   "The active Dcl card of the agent."
   ::= {sysDcl 2}

sysDclCopyDbTable  OBJECT-TYPE
      SYNTAX SEQUENCE OF SysDclCopyDbEntry
      ACCESS not-accessible
      STATUS  mandatory
      DESCRIPTION
      "This table enables to copy a cofiguration from the Offline
       Dcl to the Online Dcl."
       ::= { sysDcl 3}

sysDclCopyDbEntry OBJECT-TYPE
      SYNTAX SysDclCopyDbEntry
      ACCESS not-accessible
      STATUS mandatory
      DESCRIPTION "" INDEX {sysDclCopyDbIdx}
      ::= { sysDclCopyDbTable 1}

SysDclCopyDbEntry ::=
      SEQUENCE {
   		sysDclCopyDbIdx       INTEGER,
   		sysDclCopyDbCmd       INTEGER
      }

sysDclCopyDbIdx OBJECT-TYPE
      SYNTAX INTEGER (1..255)
      ACCESS read-only
      STATUS mandatory
      DESCRIPTION
      "This object indicates the Idx of the Cnfg(1..255) 
       being accessed. "
      ::= { sysDclCopyDbEntry 1}

sysDclCopyDbCmd OBJECT-TYPE
      SYNTAX INTEGER {
   off(2),
   on (3)
   }
      ACCESS read-write
      STATUS mandatory
      DESCRIPTION
      "When this command is sent to the agent, on(3), the Database
       specified (Db Idx), will be copied from the Offline Dcl 
       to the Online Dcl. Afterwards the value of this object will 
       automatically change to off(2). "
      ::= { sysDclCopyDbEntry 2}



--General System - General Status parameters 

sysSDateFormat  OBJECT-TYPE
      SYNTAX  INTEGER
       {
          ddMMYYYY (1),
          mmDDYYYY (2),
		  yyyyMMDD (4)
       }
      ACCESS  read-write
      STATUS  mandatory
      DESCRIPTION
      "This object indicates the date and time format used for the
       sysSDateAndTimeCmd and for the alarm buffer report.
       KM-2100 V1 and FCD-T1/E1 do not support the 'yyyyMMDD' format."
      ::= { sysStatus 1 }

sysSDateCmd  OBJECT-TYPE
      SYNTAX  DisplayString (SIZE (0..255))
      ACCESS  read-write
      STATUS  mandatory
      DESCRIPTION
      "This object indicates the current date as it is known by the
       agent using its own real-time clock. The format would be as
       specified by the sysSDateFormat.
       This  parameter can be set for time synchronization between
       the NMS and the Agent.
       * For KM-2100 V1 and FCD-T1/E1 - the string should contain 
         '/' signs between day, month and year. Example: 12/08/1998.
       * For DXC and rest of the products - the string should contain 
         '-' signs between day, month and year. Example: 12-08-1998.
       The day value will be in the range: 1..31.
       The month value will be in the range: 1..12.
       The year value will be in the range: 1996..2050 for products
       supporting the '-' format."
      ::= { sysStatus 2 }

sysSTimeCmd  OBJECT-TYPE
      SYNTAX  DisplayString (SIZE (0..255))
      ACCESS  read-write
      STATUS  mandatory
      DESCRIPTION
      "This object indicates the current time as it is known by the
       agent using its own real-time clock.
       This  parameter can be set for time synchronization between
       the NMS and the Agent.
       The string should contain ':' signs between hour, minute 
       and second. Example: 11:05:58."
      ::= { sysStatus 3 }

sysSActiveCnfg  OBJECT-TYPE
      SYNTAX  INTEGER
      ACCESS  read-only
      STATUS  mandatory
      DESCRIPTION
      "This object specifies the configuration number,
       that is currently  active and running."
      ::= { sysStatus 4 }
-- return 1 (db1) in phase I

sysSEditCnfg OBJECT-TYPE
      SYNTAX  INTEGER
      ACCESS  read-only
      STATUS  mandatory
      DESCRIPTION
      "This object indicates the  unique configuration number that
       is currently loaded into the tmp working space  for 
       manipulation and update operations. Value of 255 means no 
       config. is under editing process."
      ::= { sysStatus 5 }
-- return 1 (db1) in phase I


sysSEditBy OBJECT-TYPE
      SYNTAX  INTEGER
       {
           none            (1),
           snmp            (2),
           terCon1         (3),
           terCon2         (4),
           terInbandCon1   (5),
           terInbandCon2   (6),
           lcd             (7)
       }
      ACCESS  read-only
      STATUS  mandatory
      DESCRIPTION
      "This entry indicates which MMI application is working on  
       the edited config.
       The editing phase starts at the first modify operation and 
       ends after a load operation."
      ::= { sysStatus 6 }

sysSClkSrc  OBJECT-TYPE
      SYNTAX  INTEGER
    {
        master  (1),
        fallback(2),
        internal(3),
        ml      (4) 
    }
      ACCESS  read-only
      STATUS  mandatory
      DESCRIPTION
     "This entry indicates the source of the system clock."
      ::= { sysStatus 7 }

sysSAlrStatus OBJECT-TYPE
      SYNTAX  INTEGER
       {
  off   (2),
  major (3),
  minor (4)
--  event (5)
       }
      ACCESS  read-only
      STATUS  mandatory
      DESCRIPTION
      "Indicates the current alarm state only for system level.
       This object will be set to: 
       - major (3): when there is at least one active (ON) major 
                    alarm .
       - minor (4): when there is no active major alarm, but 
                    there is at least one active minor alarm.
       - off(2): when there is no active (ON) major or minor alarms
                 (since last clear operation)."
      ::= { sysStatus 8 }

sysSAlrStatusAll OBJECT-TYPE
      SYNTAX  INTEGER
       {
  off   (2),
  major (3),
  minor (4)
--  event (5)

       }
      ACCESS  read-only
      STATUS  mandatory
      DESCRIPTION
      "Indicates the current alarm state including all levels: 
       system, card, port.
       This object will be set to: 
       - major (3): when there is at least one active (ON) major 
                    alarm .
       - minor (4): when there is no active major alarm, but 
                    there is at least one active minor alarm.
       - off(2): when there is no active (ON) major or minor alarms
                 (since last clear operation)."
      ::= { sysStatus 9 }



sysSTestStatus OBJECT-TYPE
      SYNTAX  INTEGER
       {
  off(2),
  on (3)
       }
      ACCESS  read-only
      STATUS  mandatory
      DESCRIPTION
      "Indicates the current test status (for all levels: system,
       card, port).
       This attribute will be set to: 
       - on(3): when there is at least one test in progress on the
                system/card/port
         otherwise the value will be off(2)."
      ::= { sysStatus 10 }


sysSSanityCheckStatus OBJECT-TYPE
      SYNTAX  INTEGER
       {
  unknown (1),
  fail    (2),
  warning (3),
  ok      (4)
       }
      ACCESS  read-only
      STATUS  mandatory
      DESCRIPTION
      "Upon completion of the Sanity Check process on the TmpCnfg 
       this object will be set to:
       - fail(2): when there is at least one error (which is 
                  not just a warning) encountered
                  otherwise,
       - warning(3): when there are only warnings
                  otherwise,
       - ok(4).
       The value should be unknown(1), if the TmpCnfg was changed 
       after the last Sanity check."
      ::= { sysStatus 11 }

sysSNoOfSanityCheckErr OBJECT-TYPE
      SYNTAX  INTEGER
      ACCESS  read-only
      STATUS  mandatory
      DESCRIPTION
      "This object indicates the number of errors/warnings 
       discovered by the last Sanity Check process."
      ::= { sysStatus 12 }

sysSErrListTable OBJECT-TYPE
      SYNTAX SEQUENCE OF SysSErrListEntry
      ACCESS not-accessible
      STATUS mandatory
      DESCRIPTION "" ::= { sysStatus 13 }

sysSErrListEntry OBJECT-TYPE
      SYNTAX SysSErrListEntry
      ACCESS not-accessible
      STATUS mandatory
      DESCRIPTION "" INDEX { sysSErrType, sysSErrIdx}
      ::= { sysSErrListTable 1}

SysSErrListEntry ::=
      SEQUENCE {
  sysSErrType         INTEGER,
  sysSErrIdx          INTEGER,
     sysSErrDescription  DisplayString (SIZE (0..255))
      }

sysSErrType OBJECT-TYPE
      SYNTAX  INTEGER
   {
   error    (1),
   warning  (2)
   }
      ACCESS  read-only
      STATUS  mandatory
      DESCRIPTION
      "The errors are recorded in the agent, in two separate lists, 
       according to their type:  error or warning."
    ::= { sysSErrListEntry 1}

sysSErrIdx OBJECT-TYPE
      SYNTAX  INTEGER
      ACCESS  read-only
      STATUS  mandatory
      DESCRIPTION
      "Unique index number to identify an entry in the error 
       or warning list .
       The maximum value  cannot exceed the value of
       'sysSNoOfSanityCheckErr' (actually, the sum of the Errors
       list max. index and the Warning list max. index should
       equal the value of'sysSNoOfSanityCheckErr')."
    ::= { sysSErrListEntry 2}

sysSErrDescription OBJECT-TYPE
      SYNTAX  DisplayString (SIZE (0..255))
      ACCESS  read-only
      STATUS  mandatory
      DESCRIPTION
      "This object is a full text description of the sanity check
       error including error code, IO slot and port numbers related to
       the code ."
  ::= { sysSErrListEntry 3}

sysSMaxNoOfCnfg OBJECT-TYPE
      SYNTAX  INTEGER
      ACCESS  read-only
      STATUS  mandatory
      DESCRIPTION
      "Maximum number of configurations that can be defined and 
       stored in the DACS agent.
       If the DACS agent has a large capacity, the maximum will be 
       limited to 254."
      ::= { sysStatus 14 }
-- return 1 (db1) in phase I

sysSSelfTestResult OBJECT-TYPE
      SYNTAX  INTEGER
      ACCESS  read-only
      STATUS  mandatory
      DESCRIPTION
      "The test is performed by the active Common Logic card.
       The result will be a sum of 2**n according to the following
       bit convention:
    For DXC:
    bit 0   Database 1 Checksum Error (LSB)
    bit 1   Database 2 Checksum Error
    bit 2   I/O Expander Error
    bit 3   Counter Error
    bit 4   Matrix DPR Error
    bit 5   PS-A  5 Volt Error
    bit 6   PS-A 12 Volt Error
    bit 7   PS-B  5 Volt Error
    bit 8   PS-B 12 Volt Error
    bit 9   EPROM Failure

    For FCD:
    bit 0   I/O Expander Error (LSB)
    bit 1   Counter Error
    bit 2   EPROM Failure
    bit 3   Illegal Sys Config
    bit 4   SFIFO
 bit 5 EPIC Failure (ISDN) 

    When a bit is ('1'), the error exists.
    When NO ERROR is encountered, this object's value will be 0."
      ::= { sysStatus 15 }

sysSRelayState OBJECT-TYPE
      SYNTAX  INTEGER
       {
  notApplicable (1),
  off(2),
  on (3)
       }
      ACCESS  read-only
      STATUS  mandatory
      DESCRIPTION
      "Indicates the current state of the alarm relay.
       notApplicable - for agents that do not support this object."
      ::= { sysStatus 16 }

sysSInvertedAlr OBJECT-TYPE
      SYNTAX  INTEGER
       {
  notApplicable (1),
  no  (2),
  yes (3)
       }
      ACCESS  read-only
      STATUS  mandatory
      DESCRIPTION
      "Indicates if there is any Inverted alarm at any level of the 
       system (sys, card, port).
       notApplicable - for agents that do not support this object."
      ::= { sysStatus 17 }

--The following table reports all the Flip events due to I/O Redundancy
--since last Clear command of the table. 

sysSRdnFlipTable OBJECT-TYPE
      SYNTAX SEQUENCE OF SysSRdnFlipEntry
      ACCESS not-accessible
      STATUS mandatory
      DESCRIPTION
      "This table includes all the Flip events due to I/O Redundancy since
       last Clear command of this table."
      ::= { sysStatus 18 }

sysSRdnFlipEntry OBJECT-TYPE
      SYNTAX SysSRdnFlipEntry
      ACCESS not-accessible
      STATUS mandatory
      DESCRIPTION "" INDEX { sysSRdnFlipIdx}
      ::= { sysSRdnFlipTable 1}

SysSRdnFlipEntry ::=
      SEQUENCE {
     sysSRdnFlipIdx   INTEGER,
     sysSRdnFlipSlot  INTEGER,
     sysSRdnFlipPort  INTEGER,
     sysSRdnFlipCause DisplayString,
     sysSRdnFlipDate  DisplayString,
     sysSRdnFlipTime  DisplayString
      }

sysSRdnFlipIdx OBJECT-TYPE
      SYNTAX  INTEGER
      ACCESS  read-only
      STATUS  mandatory
      DESCRIPTION
      "Unique index number to identify an entry in the Redundancy Flip list."
      ::= { sysSRdnFlipEntry 1}

sysSRdnFlipSlot OBJECT-TYPE
      SYNTAX  INTEGER
       {
       io1   (5),
       io2   (6),
       io3   (7),
       io4   (8),
       io5   (9),
       io6  (10),
       io7  (11),
       io8  (12),
       io9  (13),
       io10 (14),
       io11 (15),
       io12 (16),
       io13 (17),
       io14 (18),
       io15 (19),
       notApplicable (255)
       }
      ACCESS  read-only
      STATUS  mandatory
      DESCRIPTION
      "The slot number from which Flip was performed."      
      ::= { sysSRdnFlipEntry 2}

sysSRdnFlipPort OBJECT-TYPE
      SYNTAX  INTEGER 
      ACCESS  read-only
      STATUS  mandatory
      DESCRIPTION
      "The port number from which Flip was performed.
	   For DXC:
	   For external ports the convention used will be:
         - first two digits will be: (IO slot number+10)
         - last one/two digits will be the port number within the 
           card, in odd numbers:
           port1 = 1
           port2 = 3
           port3 = 5 
           etc...
           Example: port2 of IO slot 11 will be: 213 .
       For internal ports the convention used will be:
         - first two digits will be: (IO slot number+10)
         - last one/two digits will be the port number within the 
           card, in even numbers:
           port1 = 2
           port2 = 4
           port3 = 6 
           etc...
           Example: port2 of IO slot 11 will be: 214 .

       For MP:
	   For external ports, the value will be as that of the port in the
	       card. Example: external-3 -> 3
                          external-4 -> 4
	   For internal ports, the value will be 100 + the port in the
	       card. Example: internal-1 -> 101
                          internal-4 -> 104	       
    
       100=notApplicable (when Redundancy is at card level)."      
      ::= { sysSRdnFlipEntry 3 }

sysSRdnFlipCause OBJECT-TYPE
      SYNTAX  DisplayString 
      ACCESS  read-only
      STATUS  mandatory
      DESCRIPTION
      "The last cause that caused the Flip from the Slot (Port)
       of sysSRdnSlot, sysSRdnPort."
      ::= { sysSRdnFlipEntry 4}

sysSRdnFlipDate OBJECT-TYPE
      SYNTAX  DisplayString 
      ACCESS  read-only
      STATUS  mandatory
      DESCRIPTION
      "Flip event Date. The format will be the one selected by user for 
       sysSDateFormat."
      ::= { sysSRdnFlipEntry 5}

sysSRdnFlipTime OBJECT-TYPE
      SYNTAX  DisplayString 
      ACCESS  read-only
      STATUS  mandatory
      DESCRIPTION
      "Flip event Time. The format will be hh:mm:ss."
      ::= { sysSRdnFlipEntry 6}

sysSRdnFlipTableClearCmd OBJECT-TYPE
      SYNTAX  INTEGER
       {
         off  (2),
         on   (3)
       }
      ACCESS  read-write
      STATUS  mandatory
      DESCRIPTION
      "This command, when Set to 'on', clears the Redundancy  Flip 
       table (sysSRdnFlipTable).
       After clear is performed, the agent will turn the value to 'off'
       automatically."
      ::= { sysStatus 19 }

sysSRdnFlipCmd OBJECT-TYPE
      SYNTAX  OBJECT IDENTIFIER
      ACCESS  read-write
      STATUS  mandatory
      DESCRIPTION
      "This object enables the user to send a command to the Agent, to Flip
       from a current Online IO card to its Redundant card.  
       The value sent will be an Object Identifier of an entry in the sysCRdnTable.
       This entry defines the Redundant couple of Slots on which the Flip
       is applied.
       Setting this object, will cause the Agent to Flip from current Online
       card to its Redundant card.
       This manual flip command is applicable only for entries having 
       Redundancy Mode=Y Cable. 
       Agent will send the value 0 for Get."
      ::= { sysStatus 20}


--System Current Alarm Table
--
--This table contains all Events and only the major/minor alarms
--whose status is ON.

sysSAlrTable OBJECT-TYPE
      SYNTAX SEQUENCE OF SysSAlrEntry
      ACCESS not-accessible
      STATUS mandatory
      DESCRIPTION
      "List of system level current existing alarms ."
      ::= { sysCurrentAlr 1 }

sysSAlrEntry OBJECT-TYPE
      SYNTAX SysSAlrEntry
      ACCESS not-accessible
      STATUS mandatory
      DESCRIPTION "" INDEX { sysSAlrIdx}
      ::= { sysSAlrTable 1}

SysSAlrEntry ::=
      SEQUENCE {
     	sysSAlrIdx      INTEGER,
     	sysSAlrCode     INTEGER,
     	sysSAlrState    INTEGER,
     	sysSAlarmMask   INTEGER,
     	sysSAlarmInvert INTEGER
      }

sysSAlrIdx OBJECT-TYPE
      SYNTAX  INTEGER
      ACCESS  read-only
      STATUS  mandatory
      DESCRIPTION
      "An index number of the current system alarms."
      ::= { sysSAlrEntry 1 }

sysSAlrCode OBJECT-TYPE
      SYNTAX  INTEGER
      ACCESS  read-only
      STATUS  mandatory
      DESCRIPTION
      "This object indicates a code related to a specific
       alarm description. The list of codes and their related
       descriptions will be sent to NMS request (for display purpose)
       by alrGenTable."
      ::= { sysSAlrEntry 2 }

sysSAlrState OBJECT-TYPE
      SYNTAX  INTEGER {
--   event (3),
   minor (4),
   major (5)
       }
      ACCESS  read-only
      STATUS  mandatory
      DESCRIPTION
      "This object indicates the alarm state."      
      ::= { sysSAlrEntry 3 }

sysSAlarmMask OBJECT-TYPE
      SYNTAX  INTEGER {
  off(2),
  on (3)
       }
      ACCESS  read-only
      STATUS  mandatory
      DESCRIPTION
      "Alarm Mask is : on/off."
      ::= { sysSAlrEntry 4 }

sysSAlarmInvert OBJECT-TYPE
      SYNTAX  INTEGER {
  off(2),
  on (3)
       }
      ACCESS  read-only
      STATUS  mandatory
      DESCRIPTION
      "Alarm Invert is : on/off."
      ::= { sysSAlrEntry 5 }

sysSAlrClearCmd  OBJECT-TYPE
      SYNTAX  INTEGER
       {
  off(2),
  on (3)
       }
      ACCESS  read-write
      STATUS  mandatory
      DESCRIPTION
      "Setting this attribute to ON, will enforce a  clear 
       operation on the system level alarms . Upon completion, 
       the value will automatically change to off(2)."
      ::= { sysCurrentAlr 2 }


sysSAlrClearAllCmd  OBJECT-TYPE
      SYNTAX  INTEGER
       {
  off(2),
  on (3)
       }
      ACCESS  read-write
      STATUS  mandatory
      DESCRIPTION
      "Setting this attribute to ON, will enforce a  clear 
       operation on all levels alarms . Upon completion, 
       the value will automatically change to off(2)."
      ::= { sysCurrentAlr 3 }

sysSAlrMaskAll  OBJECT-TYPE
      SYNTAX  INTEGER
       {
  off(2),
  on (3)
       }
      ACCESS  read-write
      STATUS  mandatory
      DESCRIPTION
      "on(3)  - will cause masking of all the system level alarms.
                These alarms will not be sent to NMS and will not 
                be taken into account for Alarms Status.
       off(2) - will unmask all system level alarms except those 
                masked via the sysSAlrMask. "
      ::= { sysCurrentAlr 4 }

sysSAlrMask OBJECT-TYPE
      SYNTAX OCTET STRING  (SIZE (8))
      ACCESS read-write
      STATUS mandatory
   DESCRIPTION
   "This object is a mask that indicates which system level 
    alarms are masked. The masked alarms (their bit is set to 
    '1') are neither sent to the manager, nor taken into account
    for alarm status and LEDs.
    Bit no. = Alarm code
    The bits that do not belong to the system level will be 0.
    This object is applicable only when sysSAlrMaskAll=off 
    (otherwise all system alarms are masked).
    Example: When Alarms having the codes 6 and 11 are masked,
             the value of this object will be 840 (hex)."
      ::= { sysCurrentAlr 5 }

sysSAlrDataUpdateCmd  OBJECT-TYPE
      SYNTAX  INTEGER
       {
        off(2),
        on (3)
       }
      ACCESS  read-write
      STATUS  mandatory
      DESCRIPTION
      "on(3)  - will cause Update of the Alarms Severity, Attributes and Report
                tables.
       off(2) - Upon completion, the value will automatically change to off(2)."
      ::= { sysCurrentAlr 6 }


--System Buffer Alarm Table
--
--This table contains all Events and all the major/minor alarms
--The buffer is cyclic and contains the most recent alarms.
--Since this table contains also the alarms occurence time,
--(appearance/disappearance for major/minor alarms), an alarm may 
--appear several times in this table, with alternate state: major, 
--off, major, etc.. 

sysBufferAlrTable OBJECT-TYPE
      SYNTAX SEQUENCE OF SysBufferAlrEntry
      ACCESS not-accessible
      STATUS mandatory
      DESCRIPTION
      "List of current existing alarms (of all levels)."
      ::= { sysBufferAlr 1 }

sysBufferAlrEntry OBJECT-TYPE
      SYNTAX SysBufferAlrEntry
      ACCESS not-accessible
      STATUS mandatory
      DESCRIPTION "" INDEX { sysBufferAlrIdx}
      ::= { sysBufferAlrTable 1}

SysBufferAlrEntry ::=
      SEQUENCE {
     	sysBufferAlrIdx   INTEGER,
     	sysBufferAlrCode  INTEGER,
     	sysBufferAlrState INTEGER,
     	sysBufferAlrSlot  INTEGER,
     	sysBufferAlrPort  INTEGER,
     	sysBufferAlrDate  DisplayString,
     	sysBufferAlrTime  DisplayString
      }

sysBufferAlrIdx OBJECT-TYPE
      SYNTAX  INTEGER
      ACCESS  read-only
      STATUS  mandatory
      DESCRIPTION
      "An index number of the current alarms."
      ::= { sysBufferAlrEntry 1 }

sysBufferAlrCode OBJECT-TYPE
      SYNTAX  INTEGER
      ACCESS  read-only
      STATUS  mandatory
      DESCRIPTION
      "This object indicates a code related to a specific
       alarm description. The list of codes and thir related
       descriptions will be known by the NMS (for display purpose)
       and will appear in the unit's user manual."
      ::= { sysBufferAlrEntry 2 }

sysBufferAlrState OBJECT-TYPE
      SYNTAX  INTEGER {
     off   (2),
--   event (3),
     minor (4),
     major (5)
       }
      ACCESS  read-only
      STATUS  mandatory
      DESCRIPTION
      "This object indicates the alarm type.
       minor/major - indicates appearance of the problem 
                     and the type.
       event       - indicates occurence of an event.
       off         - indicates disappearance of a minor/major type
                     alarm. "      
      ::= { sysBufferAlrEntry 3 }


sysBufferAlrSlot OBJECT-TYPE
      SYNTAX  INTEGER 
       {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16),
       io13 (17),
       io14 (18),
       io15 (19),
    kmxPsA (101),
    kmxPsB (102),
    kmxMlA (103),
    kmxMlB (104),
    kmxCl  (105),
    kmxOpt (106),
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118),
    notApplicable (255)
       }
      ACCESS  read-only
      STATUS  mandatory
      DESCRIPTION
      "The slot number this alarm refers to.
       When the alarm refers to a system function OR the DACS agent 
       is a stand-alone unit, the value will be 'notApplicable(255)'."      
      ::= { sysBufferAlrEntry 4 }

sysBufferAlrPort OBJECT-TYPE
      SYNTAX  INTEGER 
      ACCESS  read-only
      STATUS  mandatory
      DESCRIPTION
      "The port number this alarm refers to.
       If the port number is irrelevant to this alarm (if it is
       a system/card level alarm) the value will be 9999."     
      ::= { sysBufferAlrEntry 5 }

sysBufferAlrDate OBJECT-TYPE
      SYNTAX  DisplayString (SIZE (0..255))
      ACCESS  read-only
      STATUS  mandatory
      DESCRIPTION
      "The date when the alarm occured. The format will be according
       to sysSDateFormat."     
      ::= { sysBufferAlrEntry 6 }


sysBufferAlrTime OBJECT-TYPE
      SYNTAX  DisplayString (SIZE (0..255))
      ACCESS  read-only
      STATUS  mandatory
      DESCRIPTION
      "The time when the alarm occured." 
      ::= { sysBufferAlrEntry 7 }


sysBufferAlrClearCmd OBJECT-TYPE
      SYNTAX  INTEGER
       {
  off(2),
  on (3)
       }
      ACCESS  read-write
      STATUS  mandatory
      DESCRIPTION
      "Setting this attribute to ON, will enforce a  clear 
       operation on the Alarms Buffer. Upon completion, 
       the value will automatically change to off(2)."
      ::= { sysBufferAlr 2 }


--System Configuration Parameters

sysCClkSrcTable  OBJECT-TYPE
      SYNTAX SEQUENCE OF SysCClkSrcEntry
      ACCESS not-accessible
      STATUS  mandatory
      DESCRIPTION
      "All the entries of this table are identical (have the 
       same value) for all the configurations (1..255) except 
       the TmpCnfg.
       The write operation into the Table Objects is valid only
       for the TmpCnfg entry."
       ::= { sysConfig 1}

sysCClkSrcEntry OBJECT-TYPE
      SYNTAX SysCClkSrcEntry
      ACCESS not-accessible
      STATUS mandatory
      DESCRIPTION "" INDEX {sysCClkCnfgIdx, sysCClkSrcIdx}
      ::= { sysCClkSrcTable 1}

SysCClkSrcEntry ::=
      SEQUENCE {
   sysCClkCnfgIdx      INTEGER,
   sysCClkSrcIdx       INTEGER,
   sysCClkSrcMode      INTEGER,
   sysCClkSrcPrt       INTEGER,
   sysCClkStationFreq  INTEGER
      }

sysCClkCnfgIdx OBJECT-TYPE
      SYNTAX INTEGER (1..255)
      ACCESS read-only
      STATUS mandatory
      DESCRIPTION
      "This attribute indicates the Idx of the Cnfg(1..255) being 
       accessed ; Idx of 255 relates to the TmpCnfg."
      ::= { sysCClkSrcEntry 1}
-- In phase I of DXC and FCD, only the values 1 (Cnfg1) and 255 
-- (temp) are valid.

sysCClkSrcIdx OBJECT-TYPE
      SYNTAX  INTEGER 
       {
     master    (1),
     fallback  (2)
    }
      ACCESS  read-only
      STATUS  mandatory
      DESCRIPTION
      "An index in the table. There are only two entries in the 
       table. 
       master   - refers Master clock parameters 
       fallback - refers Fallback clock parameters"
      ::= { sysCClkSrcEntry 2}

sysCClkSrcMode OBJECT-TYPE
      SYNTAX  INTEGER
       {
     none            (1),
     internal        (2),
     rxClk           (3),
     station         (4),
     lbt             (5),
     notApplicable (255)
       }
      ACCESS  read-write
      STATUS  mandatory
      DESCRIPTION
      "This entry indicates the source the nodal timing is 
       locked to.
       none     - is an invalid option for Master clock.
       internal - is an invalid option for Fallback clock .
       station  - is an invalid option for a stand-alone unit. 
       lbt      - loop-back timing
       notApplicable - for ML source of Kmux or ML Timing 
                       combinations when Master/Fallback clock are
                       not applicable."
      ::= { sysCClkSrcEntry 3}


sysCClkSrcPrt OBJECT-TYPE
      SYNTAX  INTEGER
      ACCESS  read-write
      STATUS  mandatory
      DESCRIPTION
      "This entry is valid only when working in rxClk mode.
       For invalid entry the return value will be 9999.

       The valid port number depends on the IO slot no.,  the 
       installed card type and the port type: outside, inside, 
       SP.
    * The SP ports will be numbered as follows:
     - SP port 1 :  1
     - SP port 2 :  2
	   For external ports the convention used will be (for DXC):
         - first two digits will be: (IO slot number+10)
         - last one/two digits will be the port number within the 
           card, in odd numbers:
           port1 = 1
           port2 = 3
           port3 = 5 
           etc...
           Example: port2 of IO slot 11 will be: 213 .
       For internal ports the convention used will be (for DXC):
         - first two digits will be: (IO slot number+10)
         - last one/two digits will be the port number within the 
           card, in even numbers:
           port1 = 2
           port2 = 4
           port3 = 6 
           etc...
           Example: port2 of IO slot 11 will be: 214 .

      For Kmux, the port will be according to : Slot*100+Ch."
      ::= { sysCClkSrcEntry 4}

sysCClkStationFreq OBJECT-TYPE
      SYNTAX  INTEGER
       {
     notApplicable   (1),
     f1544Khz        (2),
     f2048Khz        (3)
       }
      ACCESS  read-write
      STATUS  mandatory
      DESCRIPTION
      "This entry indicates the frequency of the station clock 
       when the source is 'station'.  
       The value will be applicable only when the sysCClkSrcMode is 
       'station'. "
      ::= { sysCClkSrcEntry 5}


sysCnfgTable  OBJECT-TYPE
      SYNTAX SEQUENCE OF SysCnfgEntry
      ACCESS not-accessible
      STATUS  mandatory
      DESCRIPTION
      "All the entries of this table are identical (have the 
       same value) for all the configurations (1..255) except 
       the TmpCnfg.
       The write operation into the Table Objects is valid only
       for the TmpCnfg entry."
       ::= { sysConfig 2}

sysCnfgEntry OBJECT-TYPE
      SYNTAX SysCnfgEntry
      ACCESS not-accessible
      STATUS mandatory
      DESCRIPTION "" INDEX {sysCnfgIdx}
      ::= { sysCnfgTable 1}

SysCnfgEntry ::=
      SEQUENCE {
   sysCnfgIdx       INTEGER,
   sysCMatrixMode   INTEGER,
   sysCIsdnFormat   INTEGER,
   sysCRoutingOnEth INTEGER
      }

sysCnfgIdx OBJECT-TYPE
      SYNTAX INTEGER (1..255)
      ACCESS read-only
      STATUS mandatory
      DESCRIPTION
      "This attribute indicates the Idx of the Cnfg(1..255) being 
       accessed ; Idx of 255 relates to the TmpCnfg."
      ::= { sysCnfgEntry 1}

sysCMatrixMode OBJECT-TYPE
      SYNTAX  INTEGER
       {
  notApplicable  (1),
  bidirectional  (2),
  unidirectional (3)
       }
      ACCESS  read-write
      STATUS  mandatory
      DESCRIPTION
      "Indicates the TS Matrix Mode:
    bidirectional  - TS Assignment Matrix is symmetric.
    unidirectional - TS Assignment Matrix can be asymmetric.
       notApplicable - for agents that do not support this feature."
      ::= { sysCnfgEntry 2}

sysCIsdnFormat OBJECT-TYPE
      SYNTAX  INTEGER
       {
  notApplicable (1),
  te  (2),
  nt  (3)
       }
      ACCESS  read-write
      STATUS  mandatory
      DESCRIPTION
      "ISDN format. This parameter controls the operation mode of
    the ISDN ports.
    te - ISDN timing is derived from the signal received
         from the equipment it is connected to.
    nt - timing of the transmit path is locked to the nodal 
         timing source.
       notApplicable - for agents that do not support this feature."
      ::= { sysCnfgEntry 3}

sysCRoutingOnEth OBJECT-TYPE
      SYNTAX  INTEGER
       {
      notApplicable (1),
      none          (2),  
      proprietary   (3),
      rip2          (4)
       }
      ACCESS  read-write
      STATUS  mandatory
      DESCRIPTION
      "Mng Routing Protocol on the online CL Ethernet port."
      ::= { sysCnfgEntry 4}



--System I/O Redundacy Table
--
--This table contains all I/O cards/ports that have redundancy,
--data about the redundant card/port and parameters regarding the
--redundancy operation.
--The table indexes are Cnfg and the Primary card&port 


sysCRdnTable OBJECT-TYPE
      SYNTAX SEQUENCE OF SysCRdnEntry
      ACCESS not-accessible
      STATUS mandatory
      DESCRIPTION
      "Configuration of all Redundant I/O cards and ports.
       The write operation into the table objects is valid only
       for the TmpCnfg.
       A Slot/Port that have no Redundancy, will not exist in this
       table."
      ::= { sysConfig 3 }

sysCRdnEntry OBJECT-TYPE
      SYNTAX SysCRdnEntry
      ACCESS not-accessible
      STATUS mandatory
      DESCRIPTION "" INDEX { sysCRdnCnfgIdx, sysCRdnPrimeSlot, sysCRdnPrimePort}
      ::= { sysCRdnTable 1}

SysCRdnEntry ::=
      SEQUENCE {
     sysCRdnCnfgIdx   INTEGER,
     sysCRdnPrimeSlot INTEGER,
     sysCRdnPrimePort INTEGER,
     sysCRdnSecSlot   INTEGER,
     sysCRdnSecPort   INTEGER,
     sysCRdnMode      INTEGER,
     sysCRdnRecMode   INTEGER,
     sysCRdnRecTime   INTEGER,
     sysCRdnHwSwFlip  INTEGER,
     sysCRdnRowStatus INTEGER,
	 sysCRdnOnline    INTEGER
      }

sysCRdnCnfgIdx OBJECT-TYPE
      SYNTAX  INTEGER
      ACCESS  read-only
      STATUS  mandatory
      DESCRIPTION
      "This object indicates the Idx of the Cnfg(1..255) being 
       accessed ; Idx of 255 relates to the TmpCnfg."
      ::= { sysCRdnEntry 1 }

sysCRdnPrimeSlot OBJECT-TYPE
      SYNTAX  INTEGER 
       {
       io1   (5),
       io2   (6),
       io3   (7),
       io4   (8),
       io5   (9),
       io6  (10),
       io7  (11),
       io8  (12),
       io9  (13),
       io10 (14),
       io11 (15),
       io12 (16),
       io13 (17),
       io14 (18),
       io15 (19),
       notApplicable (255)
       }
      ACCESS  read-only
      STATUS  mandatory
      DESCRIPTION
      "The slot number of the Primary card of Redundancy.
       The Primary card should be the card that user wishes to be
       the online card (usually the more important one).
       For some Redundancy modes the importance of the redundant 
       cards/ports is the same. "      
      ::= { sysCRdnEntry 2 }

sysCRdnPrimePort OBJECT-TYPE
      SYNTAX  INTEGER 
      ACCESS  read-only
      STATUS  mandatory
      DESCRIPTION
      "The port number.
	   For DXC:
	   For external ports the convention used will be:
         - first two digits will be: (IO slot number+10)
         - last one/two digits will be the port number within the 
           card, in odd numbers:
           port1 = 1
           port2 = 3
           port3 = 5 
           etc...
           Example: port2 of IO slot 11 will be: 213 .
       For internal ports the convention used will be:
         - first two digits will be: (IO slot number+10)
         - last one/two digits will be the port number within the 
           card, in even numbers:
           port1 = 2
           port2 = 4
           port3 = 6 
           etc...
           Example: port2 of IO slot 11 will be: 214 .

       For MP:
	   For external ports, the value will be as that of the port in the
	       card. Example: external-3 -> 3
                          external-4 -> 4
	   For internal ports, the value will be 100 + the port in the
	       card. Example: internal-1 -> 101
                          internal-4 -> 104	       
       100=notApplicable (when Redundancy is at card level)."      
      ::= { sysCRdnEntry 3 }

sysCRdnSecSlot OBJECT-TYPE
      SYNTAX  INTEGER 
       {
       io1   (5),
       io2   (6),
       io3   (7),
       io4   (8),
       io5   (9),
       io6  (10),
       io7  (11),
       io8  (12),
       io9  (13),
       io10 (14),
       io11 (15),
       io12 (16),
       io13 (17),
       io14 (18),
       io15 (19),
       notApplicable (255)
       }
      ACCESS  read-write
      STATUS  mandatory
      DESCRIPTION
      "The slot number of the Secondary card of Redundancy matching
       the Primary slot."      
      ::= { sysCRdnEntry 4 }

sysCRdnSecPort OBJECT-TYPE
      SYNTAX  INTEGER 
      ACCESS  read-write
      STATUS  mandatory
      DESCRIPTION
      "The port number.
	   For DXC:
	   For external ports the convention used will be:
         - first two digits will be: (IO slot number+10)
         - last one/two digits will be the port number within the 
           card, in odd numbers:
           port1 = 1
           port2 = 3
           port3 = 5 
           etc...
           Example: port2 of IO slot 11 will be: 213 .
       For internal ports the convention used will be:
         - first two digits will be: (IO slot number+10)
         - last one/two digits will be the port number within the 
           card, in even numbers:
           port1 = 2
           port2 = 4
           port3 = 6 
           etc...
           Example: port2 of IO slot 11 will be: 214 .

       For MP:
	   For external ports, the value will be as that of the port in the
	       card. Example: external-3 -> 3
                          external-4 -> 4
	   For internal ports, the value will be 100 + the port in the
	       card. Example: internal-1 -> 101
                          internal-4 -> 104	       

       100=notApplicable (when Redundancy is at card level)."      
      ::= { sysCRdnEntry 5 }

sysCRdnMode OBJECT-TYPE
      SYNTAX  INTEGER
       {
          dualCableAIS        (2),
          yCable              (3),
          dualCableParallelTx (4),
          backup              (5),
          singleSlotProtection(6)
       }
      ACCESS  read-write
      STATUS  mandatory
      DESCRIPTION
      "Redundancy Mode.
       DXC supports: yCable(3), singleSlotProtection(6) and dualCableParallelTx(4)
       MP  supports: dualCableAIS(2), yCable(3), dualCableParallelTx(4) and
                     backup(5).
       backup - will be used when a port is backup of more than one port."
      ::= { sysCRdnEntry 6 }

sysCRdnRecMode OBJECT-TYPE
      SYNTAX  INTEGER
       {
          auto        (2),
          manual      (3)
       }
      ACCESS  read-write
      STATUS  mandatory
      DESCRIPTION
      "Recovery Mode. This object determines if after recovery
       of the failed card/port it will become on-line again or not:
       auto - automatic . In this case, the failed card/port will become
           on-line again after recovery, automatically.
       manual - In this case, the failed card/port will not become
             on-line again after recovery."
      ::= { sysCRdnEntry 7 }

sysCRdnRecTime OBJECT-TYPE
      SYNTAX  INTEGER (1..99)
      ACCESS  read-write
      STATUS  mandatory
      DESCRIPTION
      "Redundancy Recovery Time (sec). After switching to the current 
       online card, the next switch can be performed only after a 
       minimum time, indicated by this object.
       This object is applicable only when sysCRdnRecMode=auto."
      ::= { sysCRdnEntry 8 }

sysCRdnHwSwFlip OBJECT-TYPE
      SYNTAX  INTEGER
       {
          notApplicable(1),
          hw           (2),
          sw           (3)
       }
      ACCESS  read-write
      STATUS  mandatory
      DESCRIPTION
      "HW or SW decision for Redundancy Flip. 
       This object is applicable only for sysCRdnMode=singleSlotProtection.
       HW - decision is by I/O card
       SW - decision is by CL SW."
      ::= { sysCRdnEntry 9 }

sysCRdnRowStatus  OBJECT-TYPE
      SYNTAX  INTEGER
       {
        active (1),
        destroy(6)
       }
     ACCESS   read-write
     STATUS   mandatory
     DESCRIPTION
     "This parameter allows NMS to create/delete entries of this table."
     ::= { sysCRdnEntry 10 }

sysCRdnOnline OBJECT-TYPE
      SYNTAX  INTEGER
       {
          notApplicable (1),
          primary       (2),
          secondary     (3)
       }
      ACCESS  read-only
      STATUS  mandatory
      DESCRIPTION
      "Status - who is the Online (current) Redundancy Slot/Port. 
       This object shows only the Online Slot/Port regarding the Redundancy. 
       mdlSActivity or prtGenActiveStatus of the same Slot/Port may be Offline."
      ::= { sysCRdnEntry 11 }


--System Database operations

sysDbaseSanityCheckCmd OBJECT-TYPE
      SYNTAX  INTEGER
       {
       off(2),
       on (3)
       }
      ACCESS  read-write
      STATUS  mandatory
      DESCRIPTION
      "Setting this attribute to on(3) will initiate the process 
       of Sanity check on the TmpCnfg. Upon completion, the value 
       will automatically change to off(2)."
      ::= { sysDbase 1 }

sysDbaseDownloadCnfgIdxCmd OBJECT-TYPE
      SYNTAX  INTEGER   (1..255)
      ACCESS  read-write
      STATUS  mandatory
      DESCRIPTION
      "This attribute specifies the Id of the target RealCnfg to 
       which the TmpCnfg should be transferred. Upon set command, 
       the DACS agent will initiate the Sanity-Check  process.  
       If successful, the actual transfer will be performed. 
       If there will be errors, the user will have to perform
       the command again after errors correction.       
       The operation is valid only on configuration numbers
       that do not exceed sysSMaxNoOfCnfg."
      ::= { sysDbase 2 }
-- In phase I of DXC and FCD only the value 1 (Cnfg1) is valid.

sysDbaseUploadCnfgIdxCmd OBJECT-TYPE
      SYNTAX  INTEGER  (1..255)
      ACCESS  read-write
      STATUS  mandatory
      DESCRIPTION
      "This attribute specifies the Id of the source Cnfg to be 
       loaded into the TmpCnfg. Upon set operation the actual 
       transfer will be initiated.
       The operation is valid only on configuration numbers
       that do not exceed sysSMaxNoOfCnfg."
      ::= { sysDbase 3 }
-- In phase I of DXC and FCD only the value 1 (Cnfg1) is valid.

sysDbaseFlipTable  OBJECT-TYPE
      SYNTAX SEQUENCE OF SysDbaseFlipEntry
      ACCESS not-accessible
      STATUS  mandatory
      DESCRIPTION
      "Dbase Flip time and activation for every configuration."
       ::= { sysDbase 4 }

sysDbaseFlipEntry OBJECT-TYPE
      SYNTAX SysDbaseFlipEntry
      ACCESS not-accessible
      STATUS mandatory
      DESCRIPTION "" INDEX {sysDbaseFlipIdx}
      ::= { sysDbaseFlipTable 1}

SysDbaseFlipEntry ::=
      SEQUENCE {
   sysDbaseFlipIdx        INTEGER,
   sysDbaseFlipTime       DisplayString,
   sysDbaseFlipActivation INTEGER      }

sysDbaseFlipIdx OBJECT-TYPE
      SYNTAX INTEGER (1..255)
      ACCESS read-only
      STATUS mandatory
      DESCRIPTION
      "This attribute indicates the Idx of the Cnfg being 
       the target Configuration."
      ::= { sysDbaseFlipEntry 1}

sysDbaseFlipTime OBJECT-TYPE
      SYNTAX DisplayString (SIZE(0..255))
      ACCESS read-write
      STATUS mandatory
      DESCRIPTION
      "This attribute indicates the time (HH:MM) when this data 
       base will start being used by the Tmp config."
      ::= { sysDbaseFlipEntry 2}

sysDbaseFlipActivation OBJECT-TYPE
      SYNTAX INTEGER {
      disable (1),
      enable  (2)
   }
      ACCESS read-write
      STATUS mandatory
      DESCRIPTION
      "This attribute indicates if the Dbase flip will be 
       activated at the time specified for this configuration 
       (enable) or not (disable). 
       No more than one flip should be enabled for the same time."
      ::= { sysDbaseFlipEntry 3}


--Module (card) level of DACS MIB

mdlGen   OBJECT IDENTIFIER ::= {mdlDacsMux 1}
mdlCl   OBJECT IDENTIFIER ::=  {mdlDacsMux 2}
mdlPs   OBJECT IDENTIFIER ::=  {mdlDacsMux 3}

--DACS module (card) general parameters (common to all cards 
--type)

--General Card - Status information table 
--This table is NOT-APPLICABLE for a stand-alone unit  

mdlSTable  OBJECT-TYPE
      SYNTAX SEQUENCE OF MdlSEntry
      ACCESS not-accessible
      STATUS  mandatory
      DESCRIPTION "" ::= { mdlGen 1 }

mdlSEntry OBJECT-TYPE
      SYNTAX MdlSEntry
      ACCESS not-accessible
      STATUS mandatory
      DESCRIPTION "" INDEX { mdlSSltIdx }
      ::= { mdlSTable 1}

MdlSEntry ::=
      SEQUENCE {
  mdlSSltIdx            INTEGER,
  mdlSCardType          INTEGER,
  mdlSHwVer             DisplayString (SIZE (0..255)),
  mdlSSwVer             DisplayString (SIZE (0..255)),
  mdlSAlarmStatus       INTEGER,
  mdlSAlarmStatusAll    INTEGER,
  mdlSTestStatus        INTEGER,
  mdlSHwStatus          INTEGER,
  mdlSActivity          INTEGER,
  mdlSAlrClearCmd       INTEGER,
  mdlSAlrClearAllCmd    INTEGER,
  mdlSAlrMaskAll        INTEGER,
  mdlSCmd               INTEGER
      }

mdlSSltIdx OBJECT-TYPE
      SYNTAX  INTEGER
       {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16),
       io13 (17),
       io14 (18),
       io15 (19),
    kmxPsA (101),
    kmxPsB (102),
    kmxMlA (103),
    kmxMlB (104),
    kmxCl  (105),
    kmxOpt (106),
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118)
       }
      ACCESS  read-only
      STATUS  mandatory
      DESCRIPTION
      "A unique number to identify a slot position in the DACS.
       The Kilomux should use enumerated values starting with kmx."
      ::= { mdlSEntry 1}


mdlSCardType OBJECT-TYPE
      SYNTAX  INTEGER
       {
  --
  -- General types
  --
  unknown        (1),
  empty          (2),


  -- Power Supply Modules
  --
        psAC           (10),
        psDC           (11),
        
  --
  -- Cl Modules
  --
        dCl            (20),
        kCl            (21),
        dcl2           (22),
		dcl2Eth        (23),
		kClEth         (24),

  --
  -- T1/E1 Modules
  --
        dT1DSU         (30),
        dT1CSU         (31),
        dE1DSU         (32),
        dE1LTU         (33),
        dE1aDSU        (34),
        dE1aLTU        (35),
        dT1F           (36),
        dE1F           (37),
  
  --
  -- HDSL Modules
  
        dE1Hdsl        (40),  --Double Slot
        dT1Hdsl        (41),  --Double Slot   
        dE1HdslS       (42),  --Single Slot
        dT1HdslS       (43),  --Single Slot   

        -- KMUX Main Links
  --
  kML1           (50),
  kML2           (51),
  kML3           (52),
  kML4           (53),
  kML5           (54),
  kML6           (55),
  kML7           (56),
  kML8           (57),
  kML10          (59),
  kMLF           (60),
  kML10New       (61),
        --LS  Modules
  --
  kLS1           (70),
  kLS1New        (71),
  kLS2           (72),

        --LAN  Modules
  --
  kTRE           (80),
  kMBE           (81),
  kMBENew        (82),

        --Optional  Modules
  --
  kai           (90),
  kdi           (91),
  kdiCH         (92),

  -- HS Modules
  --
  dHS2           (100),

  kHS1           (110),
  kHS2           (111),
  kHSU1          (112),
  kHSU2          (113),
  kHS703         (114),

  -- Voice Modules
  --
  kVC1EM         (130),
  kVC1FXO        (131),
  kVC1FXS        (132),
  kVC1MEM        (133),
  kVC1MFXO       (134),
  kVC1MFXS       (135),
  kVC1MFXSW      (136),
  kVC2EM         (137),
  kVC2FXO        (138),
  kVC2FXS        (139),
  kVC2s1EM       (140), --KVC2/1/E&M
  kVC2s1FXO      (141), --KVC2/1/FXO
  kVC2s1FXS      (142), --KVC2/1/FXS
  kVC3EM         (143),
  kVC3FXO        (144),
  kVC3FXS        (145),
  kVC3S0         (146),

  -- Fax Modules
  --     
  kVF1EM            (170),
  kVF1FXO           (171),
  kVF1FXS           (172),
  kVF3EM            (173),
  kVF3FXO           (174),
  kVF3FXS           (175),
  kVF4EM            (176),
  kVF4FXO           (177),
  kVF4FXS           (178),
  kVF4FXSW          (179),
  kVF4S0            (180),
  kVF5PbxE1         (181),
  kVF5E1PbxSlave    (182),
  kVF5PbxT1         (183),
  kVF5T1PbxSlave    (184),
  kVF5PbxE1New      (185),
  kVF5E1PbxSlaveNew (186),
  kVF5PbxT1New      (187),
  kVF5T1PbxSlaveNew (188),
  kVF4FXO3          (189), 
  kVF4FXS3          (190), 
  kVF4NS0           (191),
  kVF6E1s16         (192), --KVF.6/E1/16
  kVF6E1s31         (193), --KVF.6/E1/31
  kVF6T1s12         (194), --KVF.6/T1/12
  kVF6T1s24         (195), --KVF.6/T1/24
  kVF8EM            (196),
  kVF8FXO           (197),
  kVF8FXS           (198),

  -- DIM Modules
  --
  dimV35         (201),
  dimRS422       (202),
  dimRS530       (203),
  dimHssi        (204),
  dimX21         (205),
  dim10BaseT     (206),
  dimE1          (207),

  --DACS T3/E3 Modules
  --
  dt3            (210),
  dt3f           (211),
  de3            (212),
  de3f           (213)
       }
      ACCESS  read-only
      STATUS  mandatory
      DESCRIPTION
      "This attribute indicates the type of  the card installed
       in the specific slot position.
       Only PS's are possible in the PS slots.
       Only CL's are possible in the CL slots.
       Only IO modules are possible in the IO slots.
       Kmux card type start with the letter k."
      ::= { mdlSEntry 2}

mdlSHwVer OBJECT-TYPE
      SYNTAX  DisplayString (SIZE (0..255))
      ACCESS  read-only
      STATUS  mandatory
      DESCRIPTION
      "This attribute indicates the Hardware version of the 
       card installed in the specific slot position."
      ::= { mdlSEntry 3 }

mdlSSwVer OBJECT-TYPE
      SYNTAX  DisplayString (SIZE (0..255))
      ACCESS  read-only
      STATUS  mandatory
      DESCRIPTION
      "This attribute indicates the Software version of the 
       card installed in the specific slot position."
      ::= {mdlSEntry 4}


mdlSAlarmStatus OBJECT-TYPE
      SYNTAX  INTEGER
       {
  off   (2),
  major (3),
  minor (4)
--  event (5)
       }
      ACCESS  read-only
      STATUS  mandatory
      DESCRIPTION
      "Indicates the current alarm state only for card level.
       This object will be set to: 
       - major (3): when there is at least one active (ON) major 
                    alarm .
       - minor (4): when there is no active major alarm, but 
                    there is at least one active minor alarm.
       - off(2): when there is no active (ON) major or minor alarms
                 (since last clear operation)."
      ::= { mdlSEntry 5 }

mdlSAlarmStatusAll OBJECT-TYPE
      SYNTAX  INTEGER
       {
  off   (2),
  major (3),
  minor (4)
--  event (5)
       }
      ACCESS  read-only
      STATUS  mandatory
      DESCRIPTION
      "Indicates the current card alarm state including the 
       lower level:  card, port.
       This object will be set to: 
       - major (3): when there is at least one active (ON) major 
                    alarm .
       - minor (4): when there is no active major alarm, but 
                    there is at least one active minor alarm.
       - off(2): when there is no active (ON) major or minor alarms
                 (since last clear operation)."
      ::= { mdlSEntry 6 }



mdlSTestStatus OBJECT-TYPE
      SYNTAX  INTEGER
       {
  off(2),
  on (3)
       }
      ACCESS  read-only
      STATUS  mandatory
      DESCRIPTION
      "This attribute will be on(3) when there is at least 
       one test running on a port of the module; otherwise the value 
       will be off(2)."
      ::= { mdlSEntry 7 }

mdlSHwStatus OBJECT-TYPE
      SYNTAX  INTEGER
       {
  fail(2),
  ok  (3)
       }
      ACCESS  read-only
      STATUS  mandatory
      DESCRIPTION
      "This attribute will be fail(2) when a HW FAIL exists
       on this module (discovered by periodic self test); 
       otherwise the value will be ok(3)."
      ::= { mdlSEntry 8 }

mdlSActivity OBJECT-TYPE
      SYNTAX  INTEGER
       {
  notApplicable (1),
  offline       (2),
  online        (3)
       }
      ACCESS  read-only
      STATUS  mandatory
      DESCRIPTION
      "notApplicable - when the slot is empty (no module)
       offline(1) - when the module is not active (redundant) 
       online (2) - when the module is active ."
      ::= { mdlSEntry 9 }

mdlSAlrClearCmd  OBJECT-TYPE
      SYNTAX  INTEGER
       {
  off(2),
  on (3)
       }
      ACCESS  read-write
      STATUS  mandatory
      DESCRIPTION
      "Setting this attribute to ON, will enforce a  clear 
       operation on the card level alarms . Upon completion, 
       the value will automatically change to off(2)."
      ::= { mdlSEntry 10 }


mdlSAlrClearAllCmd  OBJECT-TYPE
      SYNTAX  INTEGER
       {
  off(2),
  on (3)
       }
      ACCESS  read-write
      STATUS  mandatory
      DESCRIPTION
      "Setting this attribute to ON, will enforce a  clear 
       operation on card and port level alarms . Upon completion, 
       the value will automatically change to off(2)."
      ::= { mdlSEntry 11 }

mdlSAlrMaskAll  OBJECT-TYPE
      SYNTAX  INTEGER
       {
  off(2),
  on (3)
       }
      ACCESS  read-write
      STATUS  mandatory
      DESCRIPTION
      "on(3)  - will cause masking of all the card level alarms.
                These alarms will not be sent to NMS and will not 
                be taken into account for Alarms Status.
       off(2) - will unmask all card level alarms except those 
                masked via the mdlAlrMaskTable. "
      ::= { mdlSEntry 12 }

mdlSCmd  OBJECT-TYPE
      SYNTAX  INTEGER
      ACCESS  read-write
      STATUS  mandatory
      DESCRIPTION
      "General object for any special command at card level.
       0=NotApplicable, for cards that don't support this object.

       For KML.10(ISDN) card of KM-2100,  the object will indicate 
       Manual Call Command in Switch mode. It is applicable only when
       for KML.10, prtIsdnSwitchMode=manual.
       KML.10 valid values:
       '1' =  noOp, will be used by agents that does not support this 
              feature or object
       '2' = off, Set call command mode to disconnect state. Disconnects the call.
       '3' = on,  Set call command mode to connect state. Connects the call."
      ::= { mdlSEntry 13 } 
      
--General Card - Configuration table 
--This table is NOT-APPLICABLE for a stand-alone unit  

mdlCTable  OBJECT-TYPE
      SYNTAX SEQUENCE OF MdlCEntry
      ACCESS not-accessible
      STATUS  mandatory
      DESCRIPTION "" ::= { mdlGen 2 }

mdlCEntry OBJECT-TYPE
      SYNTAX MdlCEntry
      ACCESS not-accessible
      STATUS mandatory
      DESCRIPTION "" INDEX { mdlCConfigIdx, mdlCSlotIdx  }
      ::= { mdlCTable 1}

MdlCEntry ::=
      SEQUENCE {
   mdlCConfigIdx         INTEGER,
   mdlCSlotIdx           INTEGER,
   mdlCProgCardType      INTEGER,
   mdlCNoOfExtPrt        INTEGER,   -- RO
   mdlCNoOfIntPrt        INTEGER    -- RO
      }

mdlCConfigIdx OBJECT-TYPE
      SYNTAX  INTEGER (1..255)
      ACCESS  read-only
      STATUS  mandatory
      DESCRIPTION
      "This object indicates the Configuration number (1..255) 
       referred.
       Value of  255 specifies the TmpCnfg (Scratch)."
      ::= { mdlCEntry 1}
-- In phase 1 only the values 1 (Cnfg1) and 255 (temp) are valid.

mdlCSlotIdx OBJECT-TYPE
      SYNTAX  INTEGER
       {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16),
       io13 (17),
       io14 (18),
       io15 (19),
    kmxPsA (101),
    kmxPsB (102),
    kmxMlA (103),
    kmxMlB (104),
    kmxCl  (105),
    kmxOpt (106),
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118)
       }
      ACCESS  read-only
      STATUS  mandatory
      DESCRIPTION
      "This object indicates a unique number of the slot position 
       in which the module is inserted.
       The Kilomux should use enumerated values starting with kmx."
      ::= { mdlCEntry 2}

mdlCProgCardType OBJECT-TYPE
      SYNTAX  INTEGER
       {
  --
  -- General types
  --
  unknown        (1),
  empty          (2),


  -- Power Supply Modules
  --
  psAC           (10),
  psDC           (11),
        
  --
  -- Cl Modules
  --
        dCl            (20),
        kCl            (21),
        dcl2           (22),
		dcl2Eth        (23),
		kClEth         (24),

  --
  -- T1/E1 Modules
  --
        dT1DSU         (30),
        dT1CSU         (31),
        dE1DSU         (32),
        dE1LTU         (33),
        dE1aDSU        (34),
        dE1aLTU        (35),
        dT1F           (36),
        dE1F           (37), 

  --
  -- HDSL Modules
  
        dE1Hdsl        (40),  --Double Slot
        dT1Hdsl        (41),  --Double Slot   
        dE1HdslS       (42),  --Single Slot
        dT1HdslS       (43),  --Single Slot   


        -- KMUX Main Links
  --
  kML1           (50),
  kML2           (51),
  kML3           (52),
  kML4           (53),
  kML5           (54),
  kML6           (55),
  kML7           (56),
  kML8           (57),
  kML10          (59),
  kMLF           (60),
  kML10New       (61),

        --LS  Modules
  --
  kLS1           (70),
  kLS1New        (71),
  kLS2           (72),

        --LAN  Modules
  --
  kTRE           (80),
  kMBE           (81),
  kMBENew        (82),

        --Optional  Modules
  --
  kai           (90),
  kdi           (91),
  kdiCH         (92),

  -- HS Modules
  --
  dHS2           (100),

  kHS1           (110),
  kHS2           (111),
  kHSU1          (112),
  kHSU2          (113),
  kHS703         (114),


  -- Voice Modules
  --
  kVC1EM         (130),
  kVC1FXO        (131),
  kVC1FXS        (132),
  kVC1MEM        (133),
  kVC1MFXO       (134),
  kVC1MFXS       (135),
  kVC1MFXSW      (136),
  kVC2EM         (137),
  kVC2FXO        (138),
  kVC2FXS        (139),
  kVC2s1EM       (140), --KVC2/1/E&M
  kVC2s1FXO      (141), --KVC2/1/FXO
  kVC2s1FXS      (142), --KVC2/1/FXS
  kVC3EM         (143),
  kVC3FXO        (144),
  kVC3FXS        (145),
  kVC3S0         (146),

  -- Fax Modules
  --
  kVF1EM            (170),
  kVF1FXO           (171),
  kVF1FXS           (172),
  kVF3EM            (173),
  kVF3FXO           (174),
  kVF3FXS           (175),
  kVF4EM            (176),
  kVF4FXO           (177),
  kVF4FXS           (178),
  kVF4FXSW          (179),
  kVF4S0            (180),
  kVF5PbxE1         (181),
  kVF5E1PbxSlave    (182),
  kVF5PbxT1         (183),
  kVF5T1PbxSlave    (184),
  kVF5PbxE1New      (185),
  kVF5E1PbxSlaveNew (186),
  kVF5PbxT1New      (187),
  kVF5T1PbxSlaveNew (188),
  kVF4FXO3          (189), 
  kVF4FXS3          (190), 
  kVF4NS0           (191), 
  kVF6E1s16         (192), --KVF.6/E1/16
  kVF6E1s31         (193), --KVF.6/E1/31
  kVF6T1s12         (194), --KVF.6/T1/12
  kVF6T1s24         (195), --KVF.6/T1/24
  kVF8EM            (196),
  kVF8FXO           (197),
  kVF8FXS           (198),


  -- DIM Modules
  --
  dimV35         (201),
  dimRS422       (202),
  dimRS530       (203),
  dimHssi        (204),
  dimX21         (205),
  dim10BaseT     (206),
  dimE1          (207),

  --DACS T3/E3 Modules
  --
  dt3            (210),
  dt3f           (211),
  de3            (212),
  de3f           (213)
       }
      ACCESS  read-write
      STATUS  mandatory
      DESCRIPTION
      "This object indicates the card type assigned to the specific 
       slot in the common configuration.
       This object is identical for all the configurations (1..255).
       Only the TmpCnf(255) might have a  different value.
       The write operation is valid only for the TmpCnfg entry."
      ::= { mdlCEntry 3}

mdlCNoOfExtPrt OBJECT-TYPE
      SYNTAX  INTEGER
      ACCESS  read-only
      STATUS  mandatory
      DESCRIPTION
      "Number of external ports in the programmed module of 
       the specific slot position"
      ::= { mdlCEntry 4}

mdlCNoOfIntPrt OBJECT-TYPE
      SYNTAX  INTEGER
      ACCESS  read-only
      STATUS  mandatory
      DESCRIPTION
      "Number of internal ports in the programmed module of 
       the specific slot position."
      ::= { mdlCEntry 5}

--Module level current alarms

mdlAlr OBJECT IDENTIFIER ::= {mdlGen 3}

mdlAlrTable OBJECT-TYPE
      SYNTAX SEQUENCE OF MdlAlrEntry
      ACCESS not-accessible
      STATUS mandatory
      DESCRIPTION
      "The list of card alarms. "
      ::= { mdlAlr 1 }

mdlAlrEntry OBJECT-TYPE
      SYNTAX MdlAlrEntry
      ACCESS not-accessible
      STATUS mandatory
      DESCRIPTION "" INDEX {mdlAlrSltIdx , mdlAlrIdx}
      ::= { mdlAlrTable 1}

MdlAlrEntry ::=
      SEQUENCE {
  mdlAlrSltIdx           INTEGER,
  mdlAlrIdx              INTEGER,
  mdlAlrCode             INTEGER,
  mdlAlrState            INTEGER,
  mdlAlarmMask           INTEGER,
  mdlAlarmInvert         INTEGER    
      }

mdlAlrIdx OBJECT-TYPE
      SYNTAX  INTEGER
      ACCESS  read-only
      STATUS  mandatory
      DESCRIPTION
      "A unique number to identify an entry in the alarm status 
       table.
       Users should use the get next function to read this table 
       because the indexes are not consecutive"
      ::= { mdlAlrEntry 1}

mdlAlrSltIdx OBJECT-TYPE
      SYNTAX  INTEGER
       {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16),
       io13 (17),
       io14 (18),
       io15 (19),
    kmxPsA (101),
    kmxPsB (102),
    kmxMlA (103),
    kmxMlB (104),
    kmxCl  (105),
    kmxOpt (106),
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118)
       }
      ACCESS  read-only
      STATUS  mandatory
      DESCRIPTION
      "This attribute indicates the  desired slot position. 
       The Kilomux should use enumerated values starting with kmx."
      ::= { mdlAlrEntry 2}

mdlAlrCode OBJECT-TYPE
      SYNTAX  INTEGER
      ACCESS  read-only
      STATUS  mandatory
      DESCRIPTION
      "This object indicates a code related to a specific
       alarm description. The list of codes and their related
       descriptions will be sent to NMS request (for display purpose)
       by alrGenTable."
      ::= { mdlAlrEntry 3 }

mdlAlrState OBJECT-TYPE
      SYNTAX  INTEGER {
--   event (3),
   minor (4),
   major (5)
       }
      ACCESS  read-only
      STATUS  mandatory
      DESCRIPTION
      "This object indicates the card alarm state."      
      ::= { mdlAlrEntry 4 }

mdlAlarmMask OBJECT-TYPE
      SYNTAX  INTEGER {
  off(2),
  on (3)
       }
      ACCESS  read-only
      STATUS  mandatory
      DESCRIPTION
      "Alarm Mask is : on/off."
      ::= { mdlAlrEntry 5 }

mdlAlarmInvert OBJECT-TYPE
      SYNTAX  INTEGER {
  off(2),
  on (3)
       }
      ACCESS  read-only
      STATUS  mandatory
      DESCRIPTION
      "Alarm Invert is : on/off."
      ::= { mdlAlrEntry 6 }


mdlAlrMaskTable OBJECT-TYPE
      SYNTAX SEQUENCE OF MdlAlrMaskEntry
      ACCESS not-accessible
      STATUS mandatory
      DESCRIPTION
      "The list of card masked alarms. "
      ::= { mdlAlr 2 }

mdlAlrMaskEntry OBJECT-TYPE
      SYNTAX MdlAlrMaskEntry
      ACCESS not-accessible
      STATUS mandatory
      DESCRIPTION "" INDEX {mdlAlrMaskSltIdx}
      ::= { mdlAlrMaskTable 1}

MdlAlrMaskEntry ::=
      SEQUENCE {
     mdlAlrMaskSltIdx           INTEGER,
     mdlAlrMask            OCTET STRING    
      }

mdlAlrMaskSltIdx OBJECT-TYPE
      SYNTAX  INTEGER
       {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16),
       io13 (17),
       io14 (18),
       io15 (19),
    kmxPsA (101),
    kmxPsB (102),
    kmxMlA (103),
    kmxMlB (104),
    kmxCl  (105),
    kmxOpt (106),
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118)
       }
      ACCESS  read-only
      STATUS  mandatory
      DESCRIPTION
      "This attribute indicates the  desired slot position.
       The Kilomux should use enumerated values starting with kmx."
      ::= { mdlAlrMaskEntry 1}

mdlAlrMask OBJECT-TYPE
      SYNTAX OCTET STRING  (SIZE (8..10))
      ACCESS read-write
      STATUS mandatory
   DESCRIPTION
   "This object is a mask that indicates which card level 
    alarms are masked. The masked alarms (their bit is set to 
    '1') are neither sent to the manager, nor taken into account
    for alarm status and LEDs.
    Bit no. = Alarm code
    The bits that do not belong to the card level will be 0.
    This object is applicable only when mdlSAlrMaskAll=off 
    (otherwise all card alarms are masked).
    Example: When Alarm having the code 8 is masked,
             the value of this object will be 100 (hex)."
     ::= { mdlAlrMaskEntry 2 } 


--DACS dcl (Common Logic) card specific parameters  

mdlClTable  OBJECT-TYPE
      SYNTAX SEQUENCE OF MdlClEntry
      ACCESS not-accessible
      STATUS  mandatory
      DESCRIPTION "" ::= { mdlCl 1 }

mdlClEntry OBJECT-TYPE
      SYNTAX MdlClEntry
      ACCESS not-accessible
      STATUS mandatory
      DESCRIPTION "" INDEX { mdlClIdx }
      ::= { mdlClTable 1}

MdlClEntry ::=
      SEQUENCE {
   mdlClIdx           INTEGER,
   mdlClSwchStatus    INTEGER,
   mdlClLastFlipDate  DisplayString,
   mdlClLastFlipTime  DisplayString,
   mdlClLastFlipCause DisplayString
     }

mdlClIdx OBJECT-TYPE
      SYNTAX  INTEGER {
   clA   (3),
   clB   (4)
   }
      ACCESS  read-only
      STATUS  mandatory
      DESCRIPTION
      "This object indicates the Cl slot referred."
      ::= { mdlClEntry 1}

mdlClSwchStatus OBJECT-TYPE
      SYNTAX  INTEGER
      ACCESS  read-only
      STATUS  mandatory
      DESCRIPTION
      "This object indicates the status of the switches on 
       the referred DCL card.
       Each switch is represented by a bit. The status is a sum
       of 2**n, according to the bits. There are 4 switches:
       bit 0  SP-PAR (LSB)  '1' - Default parameters    
       bit 1  PSWRD         '1' - Password=default
                         '0' - Password=user selected
       bit 2  DB-INIT       '1' - DB initiated with default
                         '0' - DB initiated with NVRAM contents 
       bit 3  PC-SP  (MSB)  '1' - Management by terminal only
                         '0' - Management by NMS
       Example: If SP-PAR  and PSWRD bits are set ('1'), the value
                will be 3 (2**1 + 2**0).
       When the status of the switches is unknown, the value of
       this object will be 255."
      ::= { mdlClEntry 2}

mdlClLastFlipDate  OBJECT-TYPE
      SYNTAX  DisplayString (SIZE (0..255))
      ACCESS  read-only
      STATUS  mandatory
      DESCRIPTION
      "Date when last flip occured.
       The format would be as specified by the sysSDateFormat."
   ::= {mdlClEntry 3}

mdlClLastFlipTime  OBJECT-TYPE
      SYNTAX  DisplayString (SIZE (0..255))
      ACCESS  read-only
      STATUS  mandatory
      DESCRIPTION
      "Time when last flip occured."
   ::= {mdlClEntry 4}

mdlClLastFlipCause  OBJECT-TYPE
      SYNTAX  DisplayString (SIZE (0..255))
      ACCESS  read-only
      STATUS  mandatory
      DESCRIPTION
      "The cause of last flip."
   ::= {mdlClEntry 5}



--DACS Ps (Power Supply) card specific parameters  

mdlPsTable  OBJECT-TYPE
      SYNTAX SEQUENCE OF MdlPsEntry
      ACCESS not-accessible
      STATUS  mandatory
      DESCRIPTION "" ::= { mdlPs 1 }

mdlPsEntry OBJECT-TYPE
      SYNTAX MdlPsEntry
      ACCESS not-accessible
      STATUS mandatory
      DESCRIPTION "" INDEX { mdlPsIdx }
      ::= { mdlPsTable 1}

MdlPsEntry ::=
      SEQUENCE {
   mdlPsIdx          INTEGER,
   mdlPsStatus       INTEGER,
   mdlPsTestResult   INTEGER
     }

mdlPsIdx OBJECT-TYPE
      SYNTAX  INTEGER {
   psA   (1),
   psB   (2)
   }
      ACCESS  read-only
      STATUS  mandatory
      DESCRIPTION
      "This object indicates the PS card referred."
      ::= { mdlPsEntry 1}

mdlPsStatus OBJECT-TYPE
      SYNTAX  INTEGER {
   notActive  (1),
   active     (2)
   }
      ACCESS  read-only
      STATUS  mandatory
      DESCRIPTION
      "This object indicates the status of the PS card."
      ::= { mdlPsEntry 2}

mdlPsTestResult OBJECT-TYPE
      SYNTAX  INTEGER {
   ok   (1),
   f12V (2),
   f5V  (3)
   }
      ACCESS  read-only
      STATUS  mandatory
      DESCRIPTION
      "This object indicates the result of the PS card test.
       ok   (1) - the test passed successfully.
       f12V (2) - 12V FAIL was detected
       f5V  (3) -  5V FAIL was detected."
      ::= { mdlPsEntry 3}



--Port level of DACS MIB

prtGen    OBJECT IDENTIFIER ::= {prtDacsMux 1}
prtT1E1   OBJECT IDENTIFIER ::= {prtDacsMux 2}
prtHS     OBJECT IDENTIFIER ::= {prtDacsMux 3}
prtSP     OBJECT IDENTIFIER ::= {prtDacsMux 4}
prtDim    OBJECT IDENTIFIER ::= {prtDacsMux 5}
prtI      OBJECT IDENTIFIER ::= {prtDacsMux 6} --ISDN port
prtHdsl   OBJECT IDENTIFIER ::= {prtDacsMux 7} --HDSL Line
prtT3E3   OBJECT IDENTIFIER ::= {prtDacsMux 8} --T3/E3 interface

--DACS port general parameters (common to all ports type except SP)
--The table contains both status and configuration information 

prtGenParamTable  OBJECT-TYPE
      SYNTAX SEQUENCE OF PrtGenEntry
      ACCESS not-accessible
      STATUS  mandatory
      DESCRIPTION "" ::= { prtGen 1 }

prtGenEntry OBJECT-TYPE
      SYNTAX PrtGenEntry
      ACCESS not-accessible
      STATUS mandatory
      DESCRIPTION "" INDEX { prtGenPrtIdx }
      ::= { prtGenParamTable 1}

PrtGenEntry ::=
     SEQUENCE {
  prtGenPrtIdx        INTEGER,
  prtGenSlt           INTEGER,
  prtGenExtInt        INTEGER,
  prtGenIfIndex       INTEGER,
  prtGenActiveStatus  INTEGER,
  prtGenAlrStatus     INTEGER,
  prtGenTestStatus    INTEGER,
  prtGenTestMask      INTEGER,
  prtGenTestCmd       INTEGER,
  prtGenTestRunning   INTEGER,
  prtGenType          INTEGER,
  prtGenInterfaceType DisplayString (SIZE (0..255)),
  prtGenAlrClearCmd   INTEGER,
  prtGenAlrMaskAll    INTEGER,
  prtGenParamStatus   OCTET STRING
  }
 prtGenPrtIdx OBJECT-TYPE
      SYNTAX  INTEGER
      ACCESS  read-only
      STATUS  mandatory
      DESCRIPTION
      "This attribute indicates a unique number to identify a port. 
       The valid port number depends on the IO slot no.,  the 
       installed card type and the port type: outside/external, inside/internal. 

    In the Kilomux, the port index is calculated as follows:
    100*Slot+Ch. The external Ch numbers are 1..10, and the
    internal Ch numbers are 11..20.
       
    In the DXC :
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 ."
      ::= { prtGenEntry 1}

prtGenSlt     OBJECT-TYPE
      SYNTAX  INTEGER
       {
       io1   (5),
       io2   (6),
       io3   (7),
       io4   (8),
       io5   (9),
       io6  (10),
       io7  (11),
       io8  (12),
       io9  (13),
       io10 (14),
       io11 (15),
       io12 (16),
       io13 (17),
       io14 (18),
       io15 (19),
    kmxMlA (103),
    kmxMlB (104),
    kmxCl  (105),
    kmxOpt (106),
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118),
    standAlone (255)
       }
      ACCESS  read-only
      STATUS  mandatory
      DESCRIPTION
      "This attribute indicates a unique number to identify the slot where
       the card is inserted in.
       When the unit is stand-alone, this object is not applicable
       and 255 will be used.
       The Kilomux should use the enumerated starting with kmx."
      ::= { prtGenEntry 2}

prtGenExtInt  OBJECT-TYPE
      SYNTAX  INTEGER
       {
  external (2),
  internal (3)
       }
      ACCESS  read-only
      STATUS  mandatory
      DESCRIPTION
      "This attribute describes the type of the designated port. 
       Exteral  port is a port with  a physical connector. Internal 
       port might be of two types, one is a composite port which 
       collects data of a few external ports into a common 
       bandwidth (usually routed trough DS1 link); the other type is
       internal ports which get only part of external port data 
       (usually a few DS0's).
       In the Kilomux-2100, the internal(3) value is used for 
       composite channels or sub-channels of an ISDN Ch."
      ::= { prtGenEntry 3}

prtGenIfIndex  OBJECT-TYPE
      SYNTAX  INTEGER
      ACCESS  read-only
      STATUS  mandatory
      DESCRIPTION
      "This attribute indicates the  unique  interface number 
       assigned to the port. The specific interface of this 
       attribute is the same as the interface identified by the  
       value of ifindex in MIB-II.If there is no interface for the 
       specific prtIdx, the value will be '7fffffff'h."
      ::= { prtGenEntry 4}

prtGenActiveStatus   OBJECT-TYPE
      SYNTAX  INTEGER
       {
         unknown           (1),
         notUsed           (2),
         offLine           (3),
         onLine            (4),
         offLineRedundancy (5),
         onLineRedundancy  (6)
       }
      ACCESS  read-only
      STATUS  mandatory
      DESCRIPTION
      "This attribute describes the activity status of the port.
       unknown(1) indicates that the information is not supported.
       notUsed(2) indicates that the port is not connected according
                  to the active config.
       offLine(3) indicates that the port is down (not working) 
                  due to any problem.
       onLine (4) indicates that the port is up (working)
       offLineRedundancy(5) indicates that the port is down because
                            it is a redundant port.
       onLineRedundancy (6) indicates that this is a redundant port 
                            which is up and works as the active link."
      ::= { prtGenEntry 5}

prtGenAlrStatus OBJECT-TYPE
      SYNTAX  INTEGER
       {
  off   (2),
  major (3),
  minor (4)
       }
      ACCESS  read-only
      STATUS  mandatory
      DESCRIPTION
      "Indicates the alarm state at port (ch) agent level.
       This object will be set to: 
       - major (3): when there is at least one active (ON) major 
                    alarm .
       - minor (4): when there is no active major alarm, but 
                    there is at least one active minor alarm.
       - off(2): when there is no active (ON) major or minor alarms
                 (since last clear operation)."
      ::= { prtGenEntry 6}

prtGenTestStatus OBJECT-TYPE
     SYNTAX  INTEGER
         {
       off(2),
       on (3)
         }
     ACCESS  read-only
     STATUS  mandatory
     DESCRIPTION
     "This attribute will be on(3) when there is at least one test 
      in progress (running) on the port; otherwise the value will 
      be off(2)."
     ::= { prtGenEntry 7}

prtGenTestMask OBJECT-TYPE
      SYNTAX  INTEGER
      ACCESS  read-only
      STATUS  mandatory
      DESCRIPTION
      "This is a mask which indicates which tests from the
       'prtGenTestCmd' list are allowed for the selected port.
       If a specific test is allowed, its respective bit will be SET 
       in the mask :

         TEST                  BIT
        -----------            ---
        localLoop               1
        remoteLoop              2
        bert                    3
        plb                     4
        inband                  5

        prbs                    8
        loop2-v54  (RLB)        9
        loop3-v54  (LLB)       10

        Tone injection         13
        Tx-plb                 14
        Tx-llb                 15
        DTE loop (HSSI)        16

        HDSL-Tx-Inband         20
        HDSL-Rx-Inband         21
		Monitor                22  (test port)
		User Line Loopback	   23

        e.g : If the return value is 3 -> 0000000000000011  ->
              Bits 1 & 2 are set -> the allowed tests are :
                                           local-loop
                                           remote-loop  "
      ::= { prtGenEntry 8}


prtGenTestCmd OBJECT-TYPE
      SYNTAX  INTEGER
      ACCESS  read-write
      STATUS  mandatory
      DESCRIPTION
      "Setting this object to a value as detailed furter on 
       (except 0) will initiate a test on the specific port, 
       if the operation is allowed (according to TestMask). 
       If the operation is not allowed, the mux will ignore the 
       operation.
       The test/s requested will be set according to the respective
       bit:
         TEST                  BIT
        -----------            ---
        localLoop               1
        remoteLoop              2
        bert                    3
        plb                     4
        inband                  5

        prbs                    8
        loop2-v54  (RLB)        9
        loop3-v54  (LLB)       10

        Tone injection         13
        Tx-plb                 14
        Tx-llb                 15
        DTE loop (HSSI)        16

        HDSL-Tx-Inband         20
        HDSL-Rx-Inband         21
		Monitor                22  (test port)
		User Line Loopback	   23

        e.g : If the requested value is 3 -> 0000000000000011  ->
              Bits 1 & 2 are set -> the requested tests are :
                                           local-loop
                                           remote-loop  

       Setting this object to stop (value=0 ; all bits are 0), 
       will stop all the user requested tests running on the 
       selected port; it will NOT stop the tests initiated by 
       the system."
      ::= { prtGenEntry 9}

prtGenTestRunning OBJECT-TYPE
      SYNTAX  INTEGER
      ACCESS  read-only
      STATUS  mandatory
      DESCRIPTION
      "This object indicates which tests are running currently on 
       the selected port (initiated by user and/or by the system).
       If a specific test is currently running on the port, its 
       respective bit will be SET: 

         TEST                  BIT
        -----------            ---
        localLoop               1
        remoteLoop              2
        bert                    3
        plb                     4
        llb                     5
        txInband                6
        rxInband                7
        prbs                    8
        loop2-v54  (RLB)        9
        loop3-v54  (LLB)       10
        DDS DSU loop           11
        DDS CSU loop           12
        Tone injection         13
        Tx-plb                 14
        Tx-llb                 15
        DTE loop (HSSI)        16
        Local  DTE  loop (HSSI)17
        Local  Line loop (HSSI)18
        Remote Line loop (HSSI)19
        HDSL-Tx-Inband         20
        HDSL-Rx-Inband         21
		Monitor                22  (test port)
		User Line Loopback	   23
		Network Line Loopback  24

        e.g : If the return value is 3 -> 0000000000000011  ->
              Bits 1 & 2 are set -> the running tests are :
                                           local-loop
                                           remote-loop  
        llb (Bit 5) - can be initiated by system only!            "
      ::= { prtGenEntry 10}


prtGenType OBJECT-TYPE
      SYNTAX  INTEGER {
   unknown (1),
   t1      (2),
   e1      (3),
   hs      (4),
   t1Csu   (5),
   t1Dsu   (6),
   e1Ltu   (7),
   e1Dsu   (8),
   hdsl    (9),
   sp      (10),
   t1F     (11),  --T1 Fiber-optic
   e1F     (12),  --E1 Fiber-optic
   dim     (13),
   isdn    (14),
   t3      (15),
   e3      (16),
   t3f     (17),
   e3f     (18),
   other   (255)
   }
      ACCESS  read-only
      STATUS  mandatory
      DESCRIPTION
      "This object describes the type of the selected port."
      ::= { prtGenEntry 11}


prtGenInterfaceType OBJECT-TYPE
      SYNTAX  DisplayString (SIZE (0..255))
      ACCESS  read-only
      STATUS  mandatory
      DESCRIPTION
      "This attribute indicates a unique HW interface type of the
       selected port.
       Examples: 
       - for T1 cards: DSU, CSU
       - for E1 cards: DSU, LTU
       - for HS cards: v35, rs422, x21
       etc..."
      ::= { prtGenEntry 12}

prtGenAlrClearCmd  OBJECT-TYPE
      SYNTAX  INTEGER
       {
  noOp (1),
  off  (2),
  on   (3)
       }
      ACCESS  read-write
      STATUS  mandatory
      DESCRIPTION
      "Setting this attribute to ON, will enforce a  clear 
       operation on the port level alarms . Upon completion, 
       the value will automatically change to off(2).
       noOp - will be used by agents that do not support this 
              feature or object."
      ::= { prtGenEntry 13 }

prtGenAlrMaskAll  OBJECT-TYPE
      SYNTAX  INTEGER
       {
  noOp (1),
  off  (2),
  on   (3)
       }
      ACCESS  read-write
      STATUS  mandatory
      DESCRIPTION
      "on(3) - will mask all the alarms of the selected port
       off(2)- will unmask all alarms of the selected port except
               the ones selected by the prtAlrMaskTable.
       noOp - will be used by agents that do not support this 
              feature or object."
      ::= { prtGenEntry 14 }

prtGenParamStatus OBJECT-TYPE
      SYNTAX  OCTET STRING
      ACCESS  read-only
      STATUS  mandatory
      DESCRIPTION
      "This object indicates Status of parameters specific to the 
       selected port.
       - For a port that has no special status or is supported
         by prtSExHsfStatTable - 1 Octet: 00hex

       - For HS cards - 1 octet:
         Bit 7 (MSB)..Bit 2 = 0 (NA)
		 Bit 0 and 1 indicates RTS control signal state:
		 Bit 1:       '1'=active  ; '0'=notActive
         Bit 0 (LSB): '1'=unknown ; '0'=NA

       - For VC-6, VC-12, VC-12/6 external ports - 1 Octet :
         Bit 7 (MSB)..Bit 2 = 0 (NA)
         Bit 1:       Tx Signaling '1'=On ; '0'=Off
         Bit 0 (LSB): Rx Signaling '1'=On ; '0'=Off

       - For VC-2/R2(FXS) external ports - 1 Octet : 
         Bit  -   7 6 5 4 3 2 1 0
                  |_| |_________|
                  Call  Call State
             Direction     

         Bit 7 (MSB) and Bit 6  : Call Direction
         00 - Incoming
         01 - Outgoing
         Bit 5..Bit 0: Call State
         000000 - Idle
         000001 - Seized
         000010 - Both-Way Conflict
         000011 - Seizure Ack
         000100 - Answered
         000101 - Clear Backward
         000110 - Clear Forward
         000111 - Blocked
         001000 - Fault
         001001 - Fault 3
         001010 - Fault 4
         001011 - Fault 5
         001100 - Fault 6
         001101 - Fault 7 
   
       - For ML-20 external port - 3 Octets :
         - 1 MS Octet will represent the Real Rate used:
           Bit    - 7 6 5 4 3 2 1 0
                    |___| |_______|
                     spare  Rate
             
          Valid values: 0..31, meaning 0..31x64Kbps
          Invalid values: 32..255.
           - 2 LS Octets will represent the Status of 7 Control 
             Signals:
             Signal - ---  CTS  DSR  DCD   RJ   TM   DTR  RTS
             Bit   - 7 6  5 4  3 2  1 0    7 6  5 4  3 2  1 0
             Octet  -          2                     3 (LS)
             '---' will always have the value 00
             Rest of the Signals (2 bits each) can have the following
             values:
             00=NA   ;  01=Unused ; 10=Off  ; 11=On 
         
       - For ML-H/E1, ML-H/1/E1, ML-H/S/E1 internal port - 1 Octet
         Bit    - 7 6 5 4 3 2 1 0
                  |___________|
                        spare   Mode of Operation

         Mode of Operation: '1'=Central  ; '0'=Remote 

       - For KM2100, KVF.5 cards - indicates the status of A and B signaling
	                               for each internal channel.
	     1 Octet:

		 Bit  -   7 6 5 4 3 2 1 0
                  |_____| |_| |_| 
                   spare   B   A

		 Bit 0 (LSB) and Bit 1 : A status
		 Bit 2 and Bit 3       : B status

		 00 - Off
		 01 - On
		 11 - Unknown
		  
	   - For FCD-W, NETWORK and USER ports - 1 Octet
         Status of Control Signals: '1'=On  ; '0'=Off or when not applicable

         Bit    - 7 6 5 4 3 2 1 0

         Bit 7 (MSB) - Signal Loss (applicable only for G.703 interface)
         Bit 6       - CONTROL     (applicable only for X.21 interface)
         Bit 5       - INDICATION  (applicable only for X.21 interface)
         Bit 4       - DSR         (applicable only for V.35 interface)
         Bit 3       - RTS         (applicable only for V.35 interface)
         Bit 2       - CTS         (applicable only for V.35 interface)
         Bit 1       - DTR         (applicable only for V.35 interface)
         Bit 0       - DCD         (applicable only for V.35 interface) "
      ::= { prtGenEntry 15}


--prtGenTestDuration - Setting Duration of tests

prtGenTestDurationTable  OBJECT-TYPE
      SYNTAX SEQUENCE OF PrtGenTestDurationEntry
      ACCESS not-accessible
      STATUS  mandatory
      DESCRIPTION "" ::= { prtGen 2 }

prtGenTestDurationEntry OBJECT-TYPE
      SYNTAX PrtGenTestDurationEntry
      ACCESS not-accessible
      STATUS mandatory
      DESCRIPTION "" INDEX { prtGenTestPrtIdx, prtGenTestIdx }
      ::= { prtGenTestDurationTable 1}

PrtGenTestDurationEntry ::=
     SEQUENCE {
  prtGenTestPrtIdx     INTEGER,
  prtGenTestIdx        INTEGER,
  prtGenTestDuration   INTEGER
  }

prtGenTestPrtIdx OBJECT-TYPE
      SYNTAX  INTEGER
      ACCESS  read-only
      STATUS  mandatory
      DESCRIPTION
      "This attribute indicates a unique number to identify a port. 
       The valid port number depends on the IO slot no.,  the 
       installed card type and the port type: outside/external, inside/internal. 

    In the Kilomux, the port index is calculated as follows:
    100*Slot+Ch. The external Ch numbers are 1..10, and the
    internal Ch numbers are 11..20.
       
    In the DXC :
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 ."
      ::= { prtGenTestDurationEntry 1}


prtGenTestIdx OBJECT-TYPE
      SYNTAX  INTEGER  
   {
   localLoop  (1),
   remoteLoop (2),
   bert       (3),
   plb        (4),
   rlb        (5),
   llb        (6),
   toneInjection (7),
   txInband (8),
   rxInband (9)
   }
      ACCESS  read-only
      STATUS  mandatory
      DESCRIPTION
      "This attribute indicates the test, the duration refers. "
      ::= { prtGenTestDurationEntry 2}


prtGenTestDuration OBJECT-TYPE
      SYNTAX  INTEGER
      ACCESS  read-write
      STATUS  mandatory
      DESCRIPTION
      "This attribute indicates the maximum duration of executing
       a test on the specific port. This entry applies to the
       specified test . The resolution will be a minute, and the
       maximum duration is limited to 30 minutes .
       A zero  value specifies no time limitation.
       When the test isn't active the agent initiates this object to
       2 min. when the duration is needed and to 0 if it's not 
       required."
      ::= { prtGenTestDurationEntry 3}
       

--prtGen TS (TimeSlot) Assignment Table - for all ports of IO cards

prtGenTsTable  OBJECT-TYPE
     SYNTAX SEQUENCE OF PrtGenTsEntry
     ACCESS not-accessible
     STATUS  mandatory
     DESCRIPTION
      "The write operation into the Table's Objects is valid only
       for the TmpCnfg entry (Scratch)."
  ::= { prtGen 3}

prtGenTsEntry OBJECT-TYPE
      SYNTAX PrtGenTsEntry
      ACCESS not-accessible
      STATUS mandatory
      DESCRIPTION "" INDEX {prtGenTsCnfgIdx, prtGenTsPrtIdx, prtGenTsIdx }
      ::= { prtGenTsTable 1}

PrtGenTsEntry ::=
      SEQUENCE {
      prtGenTsCnfgIdx        INTEGER,
      prtGenTsPrtIdx         INTEGER,
      prtGenTsIdx            INTEGER,
      prtGenTsType           INTEGER,
      prtGenTsIConPrt        INTEGER,
      prtGenTsIConTs         INTEGER
      }

prtGenTsCnfgIdx OBJECT-TYPE
      SYNTAX  INTEGER  (1..255)
      ACCESS  read-only
      STATUS  mandatory
      DESCRIPTION
      "This attribute indicates the Idx of the Cnfg(1..255) being 
       accessed.
       Idx of 255 relates to the TmpCnfg. "
      ::= { prtGenTsEntry 1}


prtGenTsPrtIdx OBJECT-TYPE
      SYNTAX  INTEGER
     ACCESS  read-only
      STATUS  mandatory
      DESCRIPTION
      "This attribute indicates a unique  port number.
       The valid port number depends on the IO slot no.,  the 
       installed card type and the port type: outside, inside, 
       SP.
      In the DXC :
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 ."
      ::= { prtGenTsEntry 2}

prtGenTsIdx OBJECT-TYPE
      SYNTAX  INTEGER
      ACCESS  read-only
      STATUS  mandatory
      DESCRIPTION
      "This attribute indicates a unique time slot  position.
       The valid time slots are 
       1..25 for T1 Card (25=Fbit)
       0..31 for E1 or HS Card . 
       In G732S-E1 lines time slot 16 is not valid for data, 
       it is dedicated for multiframe synchronization bits
       and voice signaling."
      ::= { prtGenTsEntry 3}

prtGenTsType  OBJECT-TYPE
      SYNTAX  INTEGER
   {
   unknown   (1),
   voice     (2),
   data      (3),
   vcMP      (4),
   nc        (5),
   mng       (6)
   }
      ACCESS  read-write
      STATUS  mandatory
      DESCRIPTION
   "The type of Timeslot. 
    If the source or destination port is an HS port,'TS Type'    
    must be 'data'.
    nc - means that this TimeSlot is not connected.
    voice, data, vcMP - also mean that this TS is connected.
    mng - means that this TS is dedicated to Management (not 
          connected to another port." 
   ::= { prtGenTsEntry 4}

prtGenTsIConPrt OBJECT-TYPE
      SYNTAX  INTEGER
      ACCESS  read-write
      STATUS  mandatory
      DESCRIPTION
      "This attribute indicates the internally (In Mux) 
       connected port.
       The valid port number depends on the IO slot no.,  the 
       installed card type and the port type: outside, inside, 
       SP.
       * The outside ports will be the T1/E1 cards ports. 
         The convention used will be (for DXC):
         - first two digits will be: (IO slot number+10)
           for a stand-alone unit, the IO slot will be considered 1.
         - last one/two digits will be the port number within the 
           card, in odd numbers:
        port1 = 1
        port2 = 3
        port3 = 5 
        etc...
        Example: port2 of IO slot 11 will be: 213 .
       * The inside ports will be for example, the HS cards ports. 
         The convention used will be (for DXC):
         - first two digits will be: (IO slot number+10)
           for a stand-alone unit, the IO slot will be considered 1.
         - last one/two digits will be the port number within the 
           card, in even numbers:
           port1 = 2
           port2 = 4
           port3 = 6 
           etc...
           Example: port2 of IO slot 11 will be: 214 .
       * noConnection - will be indicated as 10 for DXC and FCD-E1/T1.
                      - will be indicated as 100 for FCD-E1/I and SMODs.   
       * Split TS (same TS is Split to several ports) - 11. 
       
       All HS port's timeslots must have the same destination
       port."
      ::= {prtGenTsEntry 5}

prtGenTsIConTs OBJECT-TYPE
      SYNTAX  INTEGER
      ACCESS  read-write
      STATUS  mandatory
      DESCRIPTION
      "This attribute indicates a unique time slot  position.
       The valid time slots are 
       1..25 for T1 Card (25=Fbit)
       0..31 for E1 (or HS) Card. 
       In G732S-E1 lines time slot 16 is not valid for data, it is 
       dedicated for multiframe synchronization bits and voice 
       signaling.
       * For DXC: All HS port's timeslots must start with Timeslot 
         no.1 "
      ::= {prtGenTsEntry 6}

--Port current alarms table

prtAlr  OBJECT IDENTIFIER ::= {prtGen 4}

prtSAlarmTable OBJECT-TYPE
      SYNTAX SEQUENCE OF PrtSAlarmEntry
      ACCESS not-accessible
      STATUS mandatory
      DESCRIPTION "" ::= { prtAlr 1 }

prtSAlarmEntry OBJECT-TYPE
      SYNTAX PrtSAlarmEntry
      ACCESS not-accessible
      STATUS mandatory
      DESCRIPTION "" INDEX { prtSAlarmPrtIdx, prtSAlarmIdx}
      ::= { prtSAlarmTable 1}

PrtSAlarmEntry ::=
      SEQUENCE {
  prtSAlarmPrtIdx            INTEGER,
  prtSAlarmIdx               INTEGER,
  prtSAlarmCode              INTEGER,
  prtSAlarmState             INTEGER,
  prtSAlarmMask              INTEGER,
  prtSAlarmInvert            INTEGER    
      }        

prtSAlarmIdx OBJECT-TYPE
      SYNTAX  INTEGER
      ACCESS  read-only
      STATUS  mandatory
      DESCRIPTION
      "A unique number to identify an entry in the alarm status 
       table.
       Users should use the get next function to read this table 
       because the indexes are not consecutive."
      ::= { prtSAlarmEntry 1}

prtSAlarmPrtIdx OBJECT-TYPE
      SYNTAX  INTEGER
      ACCESS  read-only
      STATUS  mandatory
      DESCRIPTION
      "This attribute indicates a unique number to identify a port. 
       The valid port number depends on the IO slot no.,  the 
       installed card type and the port type: outside/external, inside/internal. 

    In the Kilomux, the port index is calculated as follows:
    100*Slot+Ch. The external Ch numbers are 1..10, and the
    internal Ch numbers are 11..20.
       
    In the DXC :
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 ."
    ::= { prtSAlarmEntry 2}

prtSAlarmCode OBJECT-TYPE
      SYNTAX  INTEGER
      ACCESS  read-only
      STATUS  mandatory
      DESCRIPTION
      "This object indicates a code related to a specific
       alarm description. The list of codes and their related
       descriptions will be sent to NMS request (for display purpose)
       by alrGenTable."
      ::= { prtSAlarmEntry 3 }

prtSAlarmState OBJECT-TYPE
      SYNTAX  INTEGER {
--   event (3),
   minor (4),
   major (5)
       }
      ACCESS  read-only
      STATUS  mandatory
      DESCRIPTION
      "This object indicates the port alarm state."      
      ::= { prtSAlarmEntry 4 }

prtSAlarmMask OBJECT-TYPE
      SYNTAX  INTEGER {
  off(2),
  on (3)
       }
      ACCESS  read-only
      STATUS  mandatory
      DESCRIPTION
      "Alarm Mask is : on/off."
      ::= { prtSAlarmEntry 5 }

prtSAlarmInvert OBJECT-TYPE
      SYNTAX  INTEGER {
  off(2),
  on (3)
       }
      ACCESS  read-only
      STATUS  mandatory
      DESCRIPTION
      "Alarm Invert is : on/off."
      ::= { prtSAlarmEntry 6 }


prtAlrMaskTable OBJECT-TYPE
      SYNTAX SEQUENCE OF PrtAlrMaskEntry
      ACCESS not-accessible
      STATUS mandatory
      DESCRIPTION "" ::= { prtAlr 2 }

prtAlrMaskEntry OBJECT-TYPE
      SYNTAX PrtAlrMaskEntry
      ACCESS not-accessible
      STATUS mandatory
      DESCRIPTION "" INDEX { prtAlrMaskPrtIdx}
      ::= { prtAlrMaskTable 1}

PrtAlrMaskEntry ::=
      SEQUENCE {
  prtAlrMaskPrtIdx         INTEGER,
  prtAlrMask               OCTET STRING
      }        


prtAlrMaskPrtIdx OBJECT-TYPE
      SYNTAX  INTEGER
      ACCESS  read-only
      STATUS  mandatory
      DESCRIPTION
      "This attribute indicates a unique number to identify a port. 
       The valid port number depends on the IO slot no.,  the 
       installed card type and the port type: outside/external, inside/internal. 

    In the Kilomux, the port index is calculated as follows:
    100*Slot+Ch. The external Ch numbers are 1..10, and the
    internal Ch numbers are 11..20.
       
    In the DXC :
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 ."
    ::= { prtAlrMaskEntry 1}

prtAlrMask OBJECT-TYPE
      SYNTAX OCTET STRING  (SIZE (8))
      ACCESS read-write
      STATUS mandatory
   DESCRIPTION
   "This object is a mask that indicates which port level 
    alarms are masked. The masked alarms (their bit is set to 
    '1') are neither sent to the manager, nor taken into account
    for alarm status and LEDs.
    Bit no. = Alarm code
    The bits that do not belong to the port level will be 0.
    This object is applicable only when prtGenAlrMaskAll=off 
    (otherwise all port alarms are masked).
    Example: When Alarms having the codes 31 and 40 are masked,
             the value of this object will be 10080000000 (hex)."
      ::= { prtAlrMaskEntry 2 }
      
      
--Port BERT table


prtBertTable OBJECT-TYPE
      SYNTAX SEQUENCE OF PrtBertEntry
      ACCESS not-accessible
      STATUS mandatory
   DESCRIPTION   
      "This table includes the BERT parameters, counters and 
       commands.
    The configurable parameters:
    - prtBertPattern
    - prtBertInjectRate
    - prtBertTs
    are not Set per configuration (same for all Configurations)
    but start being applied by the Agent only upon successful
    Update/Download operation. Therefore, Set will enter the 
    values to the Temporary Configuration of the agent, while
    Get will get the values of the Active Configuration."
    ::= { prtGen 5 }

prtBertEntry OBJECT-TYPE
      SYNTAX PrtBertEntry
      ACCESS not-accessible
      STATUS mandatory
      DESCRIPTION "" INDEX { prtBertPrtIdx}
      ::= { prtBertTable 1}

PrtBertEntry ::=
      SEQUENCE {
  prtBertPrtIdx             INTEGER,
  prtBertPattern            INTEGER,
  prtBertInjectRate         INTEGER,
  prtBertInjectErrRateCmd   INTEGER,
  prtBertInjectSingleErrCmd INTEGER,
  prtBertRunTime            INTEGER,
  prtBertESs                INTEGER,
  prtBertSyncLoss           INTEGER,
  prtBertErrorBits          INTEGER,
  prtBertClearCounters      INTEGER,
  prtBertSyncStatus         INTEGER,     
  prtBertTs                 OCTET STRING 
      }        

prtBertPrtIdx OBJECT-TYPE
      SYNTAX  INTEGER
      ACCESS  read-only
      STATUS  mandatory
      DESCRIPTION
      "This attribute indicates a unique number to identify a port. 
       The valid port number depends on the IO slot no.,  the 
       installed card type and the port type: outside/external, inside/internal. 

    In the Kilomux, the port index is calculated as follows:
    100*Slot+Ch. The external Ch numbers are 1..10, and the
    internal Ch numbers are 11..20.
       
    In the DXC :
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 .

    In the MP :   
      - first two digits will be: (IO slot number+10)
      - last one/two digits will be according to the external port 
        number within the card:
        exPrt1 -> 1
        exPrt2 -> 3
        exPrt3 -> 5
        exPrt4 -> 7 . "
    ::= { prtBertEntry 1}

prtBertPattern OBJECT-TYPE
      SYNTAX  INTEGER
    {
     p2E3m1   (1),
     p2E4m1   (2),
     p2E5m1   (3),
     p2E6m1   (4),
     p2E7m1   (5),
     p511     (6),
     p2E10m1  (7),
     p2047    (8),
     p2E15m1  (9),
     p2E17m1 (10),
     p2E18m1 (11),
     p2E20m1 (12),
     qrss    (13),
     p2E21m1 (14),
     p2E22m1 (15),
     p2E23m1 (16),
     p2E25m1 (17),
     p2E28m1 (18),
     p2E29m1 (19),
     p2E31m1 (20),
     p2E32m1 (21),
     rj011   (22),  
     p63     (23),  
     p1M7S   (24),  
     p1S7M   (25),  
     alternate(26), 
     mark    (27),  
     space   (28),  
     notApplicable (255)
    }    
      ACCESS  read-write
      STATUS  mandatory
      DESCRIPTION
      "This object indicates the pattern of the BERT.
       p2Exxm1 = 2Exx-1.
       pxx     = pattern xx.
       This object is the same for all configurations.
       notApplicable - when this object is not supported."
      ::= { prtBertEntry 2}

prtBertInjectRate OBJECT-TYPE
      SYNTAX  INTEGER
    {
     noError  (1),
     r10Em1   (2),
     r10Em2   (3),
     r10Em3   (4),
     r10Em4   (5),
     r10Em5   (6),
     r10Em6   (7),
     r10Em7   (8),
     single   (9),
     notApplicable (255)
    }    
      ACCESS  read-write
      STATUS  mandatory
      DESCRIPTION
      "This object indicates the error rate injection of the BERT.
       r10Emx = 10E-x
       This object is the same for all configurations.
    single - single error injection.
       notApplicable - when this object is not supported."
      ::= { prtBertEntry 3}

prtBertInjectErrRateCmd OBJECT-TYPE
      SYNTAX  INTEGER
    {
     off  (2),
     on   (3)
    }    
      ACCESS  read-write
      STATUS  mandatory
      DESCRIPTION
      "This object controls activation/deactivation of the Error 
       Rate Injection during BERT."   
      ::= { prtBertEntry 4}

prtBertInjectSingleErrCmd OBJECT-TYPE
      SYNTAX  INTEGER
    {
     off  (2),
     on   (3)
    }    
      ACCESS  read-write
      STATUS  mandatory
      DESCRIPTION
      "This object enables to initiate a Single Error Injection 
       during BERT (on). Upon completion, the value will 
       automatically change to off(2)."   
      ::= { prtBertEntry 5}

prtBertRunTime OBJECT-TYPE
      SYNTAX  INTEGER
      ACCESS  read-only
      STATUS  mandatory
      DESCRIPTION
      "This object indicates how much time (seconds) passed since
       BERT started to run."   
      ::= { prtBertEntry 6}

prtBertESs OBJECT-TYPE
      SYNTAX  INTEGER
      ACCESS  read-only
      STATUS  mandatory
      DESCRIPTION
      "How many Errored Seconds were detected since BERT started
       to run.
       Counter for Kmux and MP."  
      ::= { prtBertEntry 7}
       
prtBertSyncLoss OBJECT-TYPE
      SYNTAX  INTEGER
      ACCESS  read-only
      STATUS  mandatory
      DESCRIPTION
      "How many times Sync Loss was detected since BERT started
       to run.
       For some products: number of seconds in which Sync Loss occured 
       since BERT started to run. See product specification."   
      ::= { prtBertEntry 8}
         
prtBertErrorBits OBJECT-TYPE
      SYNTAX  INTEGER
      ACCESS  read-only
      STATUS  mandatory
      DESCRIPTION
      "How many Error Bits were detected since BERT started
       to run."   
      ::= { prtBertEntry 9}

prtBertClearCounters  OBJECT-TYPE
      SYNTAX  INTEGER
       {
       off(2),
       on (3)
       }
      ACCESS  read-write
      STATUS  mandatory
      DESCRIPTION
      "Setting this object to ON, will enforce a  clear 
       operation of some BERT Counters. Upon completion, 
       the value will automatically change to off(2)."
      ::= { prtBertEntry 10}

prtBertSyncStatus  OBJECT-TYPE
      SYNTAX  INTEGER
       {
  notApplicable(1),
  syncLoss     (2),
  sync         (3)
       }
      ACCESS  read-only
      STATUS  mandatory
      DESCRIPTION
      "Sync Status while BERT runs."
      ::= { prtBertEntry 11}

prtBertTs  OBJECT-TYPE
      SYNTAX  OCTET STRING (SIZE(0..4))
      ACCESS  read-write
      STATUS  mandatory
      DESCRIPTION
     "This object indicates on which TSs of the selected port, BERT 
      should be applied. 
      Each Bit of the Octet represents a TS:
      31 ......0
      MSB     LSB

      Bit 0 will not be used.
      If the bit value is '1' - BERT should be applied on this TS.
      For a  T1 port, the valid raised bits ('1') are: 1..25.
      For an E1 port, the valid raised bits ('1') are: 1..31.
      
      Agents that do not support this feature will send SIZE 0."
      ::= { prtBertEntry 12}


--Port Monitoring Table - for Monitoring ports
--The table is applicable only for T1/E1/HS ports

prtMonTable  OBJECT-TYPE
     SYNTAX SEQUENCE OF PrtMonEntry
     ACCESS not-accessible
     STATUS  mandatory
     DESCRIPTION
      "The write operation into the Table's Objects is valid only
       for the TmpCnfg entry (Scratch)."
  ::= { prtGen 6}

prtMonEntry OBJECT-TYPE
      SYNTAX PrtMonEntry
      ACCESS not-accessible
      STATUS mandatory
      DESCRIPTION "" INDEX {prtMonCnfgIdx, prtMonitoringIdx }
      ::= { prtMonTable 1}

PrtMonEntry ::=
      SEQUENCE {
      prtMonCnfgIdx        INTEGER,
      prtMonitoringIdx     INTEGER,
	  prtMonitoringEnable  INTEGER,
      prtMonitoringTSs     OCTET STRING,
      prtMonitoredPort     INTEGER,
      prtMonitoredTSs      OCTET STRING
      }

prtMonCnfgIdx OBJECT-TYPE
      SYNTAX  INTEGER  (1..255)
      ACCESS  read-only
      STATUS  mandatory
      DESCRIPTION
      "This object indicates the Idx of the Cnfg(1..255) being 
       accessed.
       Idx of 255 relates to the TmpCnfg. "
      ::= { prtMonEntry 1}

prtMonitoringIdx OBJECT-TYPE
      SYNTAX  INTEGER
      ACCESS  read-only
      STATUS  mandatory
      DESCRIPTION
      "This object indicates the Monitoring Port Index.
       The valid port number depends on the IO slot no.,  the 
       installed card type and the port type: external, internal.
       * The external ports will according to the convention (for DXC):
         - first two digits will be: (IO slot number+10)
         - last one/two digits will be the port number within the 
           card, in odd numbers:
           port1 = 1
           port2 = 3
           port3 = 5 
           etc...
         Example: port2 of IO slot 11 will be: 213 .
       * The internal ports will be according to the convention (for DXC):
         - first two digits will be: (IO slot number+10)
         - last one/two digits will be the port number within the 
           card, in even numbers:
           port1 = 2
           port2 = 4
           port3 = 6 
           etc...
         Example: port2 of IO slot 11 will be: 214 ."
      ::= { prtMonEntry 2}

prtMonitoringEnable  OBJECT-TYPE
      SYNTAX  INTEGER
       {
      notApplicable(1),
      disabled     (2),
      enabled      (3)
       }
      ACCESS  read-write
      STATUS  mandatory
      DESCRIPTION
      "This object indicates if the prtMonitoringIdx is configured as 
       a monitoring port or not.
       disabled = the port is NOT configured to monitor. Setting this object
	              to this value will cause reset (to 0) of the prtMonitoringTSs
				  and prtMonitoredTSs objects.
       enabled  = the port IS configured to monitor."
      ::= {prtMonEntry 3}

prtMonitoringTSs OBJECT-TYPE
      SYNTAX  OCTET STRING (SIZE(0..4))
      ACCESS  read-write
      STATUS  mandatory
      DESCRIPTION
     "This object indicates which TSs of the Monitoring port, 
      the test equipment should monitor. 
      Each Bit of the Octet represents a TS:
      31 ......0
      MSB     LSB

      Bit 0 will not be used.
      If the bit value is '1' - this TS should be monitored.
      For a  T1 port, the valid raised bits ('1') are: 1..24.
      For an E1 port, the valid raised bits ('1') are: 1..31.
      Default: all bits='0'
      Agents that do not support this feature will send SIZE 0.
      This object can be Set as described only if prtMonitoringEnable=enabled. "
      ::= {prtMonEntry 4}

prtMonitoredPort  OBJECT-TYPE
      SYNTAX  INTEGER
      ACCESS  read-write
      STATUS  mandatory
      DESCRIPTION
      "This object indicates the MONITORED Port Index that the Monitoring
       port monitors.
       The valid port number depends on the IO slot no.,  the 
       installed card type and the port type: external, internal.
       * The external ports will according to the convention (for DXC):
         - first two digits will be: (IO slot number+10)
         - last one/two digits will be the port number within the 
           card, in odd numbers:
           port1 = 1
           port2 = 3
           port3 = 5 
           etc...
         Example: port2 of IO slot 11 will be: 213 .
       * The internal ports will be according to the convention (for DXC):
         - first two digits will be: (IO slot number+10)
         - last one/two digits will be the port number within the 
           card, in even numbers:
           port1 = 2
           port2 = 4
           port3 = 6 
           etc...
         Example: port2 of IO slot 11 will be: 214 .
       * 100 - no port monitored "
   ::= { prtMonEntry 5}

prtMonitoredTSs OBJECT-TYPE
      SYNTAX  OCTET STRING (SIZE(0..4))
      ACCESS  read-write
      STATUS  mandatory
      DESCRIPTION
     "This object indicates which TSs of the Monitored port, should be monitored. 
      Each Bit of the Octet represents a TS:
      31 ......0
      MSB     LSB

      Bit 0 will not be used.
      If the bit value is '1' - this TS should be monitored.
      For a  T1 port, the valid raised bits ('1') are: 1..24.
      For an E1 port, the valid raised bits ('1') are: 1..31.
      Default: all bits='0'
      Agents that do not support this feature will send SIZE 0.
      This object can be Set as described only if prtMonitoringEnable=enabled."
      ::= {prtMonEntry 6}


-- Port Configuration Table
-- This table is applicable only for KMUX ports 

prtCfgParam  OBJECT IDENTIFIER  ::=  {prtGen 7}

prtCfgParamTable OBJECT-TYPE
      SYNTAX SEQUENCE OF PrtCfgParamEntry
      ACCESS not-accessible
      STATUS  mandatory
      DESCRIPTION
       "The write operation into the Table Objects is valid only
        to the TmpCnfg entry.
        Parameters for the channels of the KMUX Cards: KMBE/New, KVF.6 family."
      ::= { prtCfgParam 1}

prtCfgParamEntry OBJECT-TYPE
      SYNTAX PrtCfgParamEntry
      ACCESS not-accessible
      STATUS mandatory
      DESCRIPTION "" INDEX {prtCfgParamCnfgIdx, prtCfgParamIdx }
      ::= { prtCfgParamTable 1}

PrtCfgParamEntry ::=
      SEQUENCE {
        prtCfgParamCnfgIdx        INTEGER,
        prtCfgParamIdx            INTEGER,
        prtCfgParamSlt            INTEGER,
        prtCfgParamOperatedMl     INTEGER,
        prtCfgParamMlAtoMlBPrio   INTEGER,
        prtCfgParamMlBtoMlAPrio   INTEGER,
		prtCfgParamInbandLoopDetection INTEGER
        }

prtCfgParamCnfgIdx OBJECT-TYPE
      SYNTAX  INTEGER  (1..255)
      ACCESS  read-only
      STATUS  mandatory
      DESCRIPTION
      "This attribute indicates the Idx of the Cnfg (1..100) being 
       accessed.
       Idx  255 relates to the TmpCnfg."
      ::= {prtCfgParamEntry 1}

prtCfgParamIdx OBJECT-TYPE
      SYNTAX  INTEGER
      ACCESS  read-only
      STATUS  mandatory
      DESCRIPTION
      "A unique identifier of the port (within the card when applicable).
       - For KM-2100:  Slot*100+Ch
         external ports:  Ch=1..10
         internal ports (sub-channels): Ch=11..20.
       - For FCD-T1/E1: SUB=113, CH1=122, CH2=124. "
      ::= {prtCfgParamEntry 2}

prtCfgParamSlt OBJECT-TYPE
      SYNTAX  INTEGER
 {
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118),
	notApplicable(255)
       }
      ACCESS  read-only
      STATUS  mandatory
      DESCRIPTION
      "This attribute indicates a unique number to identify the slot where
       the card is inserted in.
       In the 2104 Unit the entries kmxIO5(111)..kmxIO12(118) are not valid.
       notApplicable(255) - for products that do not have Slots."
      ::= {prtCfgParamEntry 3}

 prtCfgParamOperatedMl OBJECT-TYPE
      SYNTAX  INTEGER {
                  notApplicable(1),
                  kmxMlA     (103),
                  kmxMlB     (104)				  
        }
      ACCESS  read-write
      STATUS  mandatory
      DESCRIPTION
      "The main link for this channel.
       The field is relevant only for ML modes of Dual, Priority 
       Bumping and Switched Backup."
      ::= {prtCfgParamEntry 4}

prtCfgParamMlAtoMlBPrio OBJECT-TYPE
      SYNTAX  INTEGER {
                       notApplicable(1),
                       low          (2),
                       high         (3)
        }
      ACCESS  read-write
      STATUS  mandatory
      DESCRIPTION
      "ML-A to ML-B Priority.
       The field is relevant only for ML modes of Priority Bumping
       and Switched Backup."
      ::= {prtCfgParamEntry 5}

prtCfgParamMlBtoMlAPrio OBJECT-TYPE
      SYNTAX  INTEGER {
                     notApplicable(1),
                     low          (2),
                     high         (3)
        }
      ACCESS  read-write
      STATUS  mandatory
      DESCRIPTION
      "ML-B to ML-A Priority.
       The field is relevant only for ML modes of Priority Bumping."
      ::= {prtCfgParamEntry 6}

prtCfgParamInbandLoopDetection OBJECT-TYPE
      SYNTAX  INTEGER {
                     notApplicable(1),
                     disabled     (2),
                     enabled      (3)
        }
      ACCESS  read-write
      STATUS  mandatory
      DESCRIPTION
      "Inband Loop Detection.
       The field is relevant for the following FCD-T1/E1 ports:
       SUB, CH1, CH2."
      ::= {prtCfgParamEntry 7}

--DACS T1/E1 port specific parameters  

--DACS T1/E1 port statistics parameters.
--These parameters are in addition to those of RFC-1406 MIB. 

prtT1E1StatTable OBJECT-TYPE
  SYNTAX  SEQUENCE OF PrtT1E1StatEntry
  ACCESS  not-accessible
  STATUS  mandatory
  DESCRIPTION
  "T1/E1 port statistics table."
  ::= { prtT1E1 1}

prtT1E1StatEntry   OBJECT-TYPE
  SYNTAX  PrtT1E1StatEntry
  ACCESS  not-accessible
  STATUS  mandatory
  DESCRIPTION
  " An entry in the T1/E1 port statistics table."
  INDEX { prtT1E1SPrtIdx }
  ::= { prtT1E1StatTable 1}

PrtT1E1StatEntry ::=
     SEQUENCE {
  prtT1E1SPrtIdx
  INTEGER,
  prtT1E1SSlt
  INTEGER,
  prtT1E1OosCount
  Gauge,
  prtT1E1BpvLastMin
  Gauge,
  prtT1E1BpvMax
  Gauge
  }

prtT1E1SPrtIdx OBJECT-TYPE
      SYNTAX  INTEGER
      ACCESS  read-only
      STATUS  mandatory
      DESCRIPTION
      "This attribute indicates a unique  port number.
       The same numbering as for prtGenPrtIdx.
       The valid port number depends on the IO slot no.,  the 
       installed card type and the port type: outside, inside. 
      * The outside ports will be the T1/E1 cards ports. 
        The convention used will be (for DXC):
        - first two digits will be: (IO slot number+10)
        - last one/two digits will be the port number within the 
          card, in odd numbers:
          port1 = 1
          port2 = 3
          port3 = 5 
          etc...
        Example: port2 of IO slot 11 will be: 213 ."
      ::= { prtT1E1StatEntry 1}

prtT1E1SSlt     OBJECT-TYPE
      SYNTAX  INTEGER
       {
       clA   (3),
       clB   (4),
       io1   (5),
       io2   (6),
       io3   (7),
       io4   (8),
       io5   (9),
       io6  (10),
       io7  (11),
       io8  (12),
       io9  (13),
       io10 (14),
       io11 (15),
       io12 (16),
    io13 (17),
    io14 (18),
    io15 (19),
    standAlone (255)
       }
      ACCESS  read-only
      STATUS  mandatory
      DESCRIPTION
      "This attribute indicates a unique number to identify the slot where
       the card is inserted in.
       When the unit is stand-alone, this object is not applicable
       and 255 will be used."
      ::= { prtT1E1StatEntry 2}

prtT1E1OosCount  OBJECT-TYPE
   SYNTAX  Gauge
      ACCESS  read-only
      STATUS  mandatory
      DESCRIPTION
   "This object is applicable only for an E1 active port.
    It provides the number of red alarm events since the last
    count clearing."
   ::= { prtT1E1StatEntry 3 }

prtT1E1BpvLastMin  OBJECT-TYPE
   SYNTAX  Gauge
      ACCESS  read-only
      STATUS  mandatory
      DESCRIPTION
   "This object is applicable only for an E1 active port.
    It provides the number of BPV (BiPolar Violation) events 
    detected during the last minute."
   ::= { prtT1E1StatEntry 4 }

prtT1E1BpvMax  OBJECT-TYPE
   SYNTAX  Gauge
      ACCESS  read-only
      STATUS  mandatory
      DESCRIPTION
   "This object is applicable only for an E1 active port.
    It provides the maximal number of BPV (BiPolar Violation) 
    events (per minute), detected during the worst minute."
   ::= { prtT1E1StatEntry 5 }


--DACS T1/E1 port configuration parameters.
--
--Objects 2..9 appear in RFC-1406 MIB (dsx1ConfigTable) as RW
--objects. They were entered in this private MIB, because in
--RFC-1406 MIB there is no reference to configuration number.


prtT1E1CnfgTable OBJECT-TYPE
  SYNTAX  SEQUENCE OF PrtT1E1CnfgEntry
  ACCESS  not-accessible
  STATUS  mandatory
  DESCRIPTION
  "T1/E1 port configuration table."
  ::= { prtT1E1 2}

prtT1E1CnfgEntry   OBJECT-TYPE
  SYNTAX  PrtT1E1CnfgEntry
  ACCESS  not-accessible
  STATUS  mandatory
  DESCRIPTION
  " An entry in the T1/E1 port configuration table."
  INDEX { prtT1E1CnfgIdx, prtT1E1PrtIdx }
  ::= { prtT1E1CnfgTable 1}

PrtT1E1CnfgEntry ::=
     SEQUENCE {
  prtT1E1CnfgIdx
  INTEGER,
  prtT1E1PrtIdx
  INTEGER,
  prtT1E1Slt
  INTEGER,
  prtT1E1LineType
  INTEGER,
  prtT1E1LineCode
  INTEGER,
  prtT1E1SignalMode
  INTEGER,
  prtT1E1Fdl
  INTEGER,
  prtT1E1FdlMode
  INTEGER,
  prtT1E1Sync
  INTEGER,
  prtT1E1CGA
  INTEGER,
  prtT1E1IdleCode
  OCTET STRING,
  prtT1E1OosSignal
  INTEGER,
  prtT1E1VoiceOos
  OCTET STRING,
  prtT1E1DataOos
  OCTET STRING,
  prtT1E1LineLengthMask
  INTEGER,
  prtT1E1TxGainMask
  INTEGER,
  prtT1E1InbandMng
  INTEGER,
  prtT1E1InbandMngRate
  INTEGER,
  prtT1E1DedicatedTs
  INTEGER,
  prtT1E1InbandMngRoutProt
  INTEGER,
  prtT1E1LinkMode
  INTEGER,
  prtT1E1Multiplier 
  INTEGER,
  prtT1E1RxGain 
  INTEGER,
  prtT1E1RAI
  INTEGER, 
  prtT1E1LineMode	  
  INTEGER,
  prtT1E1TS0SaBits
  OCTET STRING
  }
 
prtT1E1CnfgIdx OBJECT-TYPE
      SYNTAX  INTEGER (1..255)
      ACCESS  read-only
      STATUS  mandatory
      DESCRIPTION
      "This attribute indicates the Idx of the Config being accessed.
       Idx of 255 relates to the Temporary (Scratch) Config. "
      ::= { prtT1E1CnfgEntry 1}

prtT1E1PrtIdx OBJECT-TYPE
      SYNTAX  INTEGER
      ACCESS  read-only
      STATUS  mandatory
      DESCRIPTION
      "This attribute indicates a unique  port number.
    The same numbering as for prtGenPrtIdx.
       The valid port number depends on the IO slot no.,  the 
       installed card type and the port type: outside, inside. 
       In the DXC :
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 .
   
       In the Kilomux, the port index is calculated as follows:
       100*Slot+Ch. The external Ch numbers are 1..10, and the
       internal Ch numbers are 11..20."
      ::= { prtT1E1CnfgEntry 2}

prtT1E1Slt     OBJECT-TYPE
      SYNTAX  INTEGER
       {
       clA   (3),
       clB   (4),
       io1   (5),
       io2   (6),
       io3   (7),
       io4   (8),
       io5   (9),
       io6  (10),
       io7  (11),
       io8  (12),
       io9  (13),
       io10 (14),
       io11 (15),
       io12 (16),
       io13 (17),
       io14 (18),
       io15 (19),
   
    kmxMlA (103),
    kmxMlB (104),

    kmxOpt (106),
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118),
    standAlone (255)
       }
      ACCESS  read-only
      STATUS  mandatory
      DESCRIPTION
      "This attribute indicates a unique number to identify the slot where
       the card is inserted in.
       When the unit is stand-alone, this object is not applicable
       and 255 will be used."
      ::= { prtT1E1CnfgEntry 3}


prtT1E1LineType OBJECT-TYPE
    SYNTAX  INTEGER {
                other    (1),
                esf      (2),
                d4       (3), --sf
                e1       (4),
                e1Crc    (5),
                e1MF     (6),
                e1CrcMF  (7),
                unframed (8)
            }
    ACCESS  read-write
    STATUS  mandatory
    DESCRIPTION
       "This variable indicates  the  variety  of T1/E1
        Line  implementing  this  circuit.  The type of
        circuit affects the number of bits  per  second
        that  the circuit can reasonably carry, as well
        as the interpretation of the  usage  and  error
        statistics.  The values, in sequence, describe:

       TITLE:        SPECIFICATION:
       esf       Extended SuperFrame DS1
       d4        AT&T D4 format DS1  - SF
       e1        CCITT Recommendation G.704
                 (Table 4a) - G732N
       e1Crc     CCITT Recommendation G.704
                 (Table 4b) - G732N with CRC
       e1MF      G.704 (Table 4a) with TS16
                 multiframing enabled - G732S
       e1CrcMF   G.704 (Table 4b) with TS16
                 multiframing enabled - G732S with CRC
       unframed  
     
       T1 - applicable values: (1),(2),(3),(8)
       E1 - applicable values: (1),(4),(5),(6),(7),(8) "
           ::= { prtT1E1CnfgEntry 4 }


prtT1E1LineCode OBJECT-TYPE
    SYNTAX  INTEGER {
                jbzs (1),
                b8zs (2),
                hdb3 (3),
                zbtsi(4),
                ami  (5),
                other(6)
            }
    ACCESS  read-write
    STATUS  mandatory
    DESCRIPTION
       "This variable describes the  variety  of  Zero
       Code  Suppression  used  on  the link, which in
       turn affects a number of its characteristics.

       jbzs=b7zs refers the Jammed  Bit  Zero  Suppres-
       sion,  in  which  the  AT&T specification of at
       least one pulse every 8 bit periods is literal-
       ly  implemented  by forcing a pulse in bit 8 of
       each channel.  Thus, only seven bits per  chan-
       nel, or 1.344 Mbps, is available for data (used for T1).

       b8zs refers to the use of a specified pattern
       of  normal  bits  and  bipolar violations
       which are used to replace a sequence  of  eight
       zero bits (used for T1).

       ANSI Clear Channels may use zbtsi, or  Zero
       Byte Time Slot Interchange.

       E1 links, with or without CRC, use hdb3  or
       ami (= TRAN).

       amI (=TRAN) refers to a mode wherein no zero code
       suppression  is  present  and the line encoding
       does not solve the problem directly. In this
       application, the higher layer must provide data
       which meets or exceeds the  pulse  density  re-
       quirements, such as inverting HDLC data."
   ::= { prtT1E1CnfgEntry 5 }


prtT1E1SignalMode OBJECT-TYPE
    SYNTAX  INTEGER {
                none            (1),
                robbedBit       (2),
                bitOriented     (3),  --CAS
                messageOriented (4)   --CCS
            }
    ACCESS  read-write
    STATUS  mandatory
    DESCRIPTION
       "'none' indicates that no bits are reserved for
               signaling on this channel.

        'robbedBit' indicates that T1 Robbed Bit Signaling is in use.

        'bitOriented' indicates that E1 Channel  Associated 
               Signaling (CAS) is in use.

        'messageOriented' indicates that Common  Channel Signaling 
               (CCS) is in use either on channel 16 of an E1 link or 
               channel 24 of a T1."
   ::= { prtT1E1CnfgEntry 6 }

prtT1E1Fdl OBJECT-TYPE
    SYNTAX  INTEGER {
                  other      (1),
                  ansi-T1-403(2),
                  att-54016  (4),
                  fdl-none   (8),
                  transFdl   (16)
            }
    ACCESS  read-write
    STATUS  mandatory
    DESCRIPTION
       "This bitmap describes the use of  the  facili-
        ties data link, and is the sum of the capabili-
        ties:

        'other' indicates that a protocol  other  than
         one following is used.

        'ansi-T1-403' refers to the  FDL  exchange
         recommended by ANSI.

        'att-54016' refers to ESF FDL exchanges.

        'fdl-none' indicates that the device  does
         not use the FDL.
        'transFdl' indicates transition between two ports of 
         the same card. "
   ::= { prtT1E1CnfgEntry 7 }


prtT1E1FdlMode OBJECT-TYPE
    SYNTAX  INTEGER {
                  other     (1),
                  user      (2),
                  carrier   (3),
      notApplicable (255)
            }
    ACCESS  read-write
    STATUS  mandatory
    DESCRIPTION
 " Fdl Mode of the T1 selected port.
   notApplicable - will be used for an E1 port."
   ::= { prtT1E1CnfgEntry 8 }



prtT1E1Sync OBJECT-TYPE
    SYNTAX  INTEGER {
                  other  (1),
                  tr62411(2),
                  ccitt  (3),
                  fast   (4)                 
            }
    ACCESS  read-write
    STATUS  mandatory
    DESCRIPTION
    "This object enables returning to normal operation, after 
     the end of a main/sub link red alarm event, in reduced time.
        'tr62411' - complies with AT&T TR-62411 (after 10 seconds).
              Applicable for both T1 and E1 interfaces.
  'ccitt'   - complies with CCITT standard. Applicable only
              for E1 interfaces.
        'fast'    - after 1 second."
 ::= { prtT1E1CnfgEntry 9 }

prtT1E1CGA OBJECT-TYPE
    SYNTAX  INTEGER {
                  none (1),
                  trans(2),
      full (3)                                   
            }
    ACCESS  read-write
    STATUS  mandatory
    DESCRIPTION
    "This object selects the method used to signal the CGA state
     to the other end, through the main/sub link. 
     'none'  - non-transparent mode. When one of the links 
               (main/sub) will be in Out Of Service state, both 
               'Data/Voice Oos' and 'Oos Signal' will be 
               transmitted to the other end.
        'trans' - when one of the links (main/sub) will be in Out
      Of Service state, 'Data/Voice Oos' will be 
      transmitted to the other end.
        'full'  - fully-transparent mode. When one of the links 
                  (main/sub) will be in Out Of Service state, 
                  neither 'Data/Voice Oos' nor 'Oos Signal' will 
                  be transmitted to the other end."
 ::= { prtT1E1CnfgEntry 10 }

prtT1E1IdleCode OBJECT-TYPE
 SYNTAX  OCTET STRING (SIZE (0..4))
    ACCESS  read-write
    STATUS  mandatory
    DESCRIPTION
    "This object selects the code transmitted to fill idle 
     (unused) time slots in the main link frame. 
     Valid range: (0 - FF HEX) ."
 ::= { prtT1E1CnfgEntry 11 }


prtT1E1OosSignal  OBJECT-TYPE
      SYNTAX  INTEGER
       {
        notsupported  (2),
        forcedIdle    (3),
        forcedBusy    (4),
        busyIdle      (5),
        idleBusy      (6)
       }
      ACCESS  read-write
      STATUS  mandatory
      DESCRIPTION
      "'idle' = '0' = on-hook, idle state
       'busy' = '1' = off-hook, busy state
       'forcedIdle' = SP = both A and B signaling bits are forced
                      to '0' during out-of-service periods.
       'forcedBusy' = MK = both A and B signaling bits are forced
                      to '1' during out-of-service periods.
       'busyIdle'   = MK_SP = A and B bits are forced to '1' for
                      2.5 seconds; then they are switched to '0'
                      until out-of-service condition disappears.
       'idleBusy'   = SP_MK = A and B bits are forced to '0' for
                      2.5 seconds; then they are switched to '1'
                      until out-of-service condition disappears.
       - for T1:    '0'=0   ;  '1'=1                         
       - for E1:    '0'=1   ;  '1'=0   "
   ::= { prtT1E1CnfgEntry 12 }

prtT1E1VoiceOos  OBJECT-TYPE
 SYNTAX  OCTET STRING (SIZE (0..4))
    ACCESS  read-write
    STATUS  mandatory
    DESCRIPTION
 "Voice Out-Of-Service code. Valid range: (0 - FF HEX).
  For agents that do not support this feature, the value will
  always be 0."
   ::= { prtT1E1CnfgEntry 13 }

prtT1E1DataOos  OBJECT-TYPE
 SYNTAX  OCTET STRING (SIZE (0..4))
    ACCESS  read-write
    STATUS  mandatory
    DESCRIPTION
 "Data Out-Of-Service code. Valid range: (0 - FF HEX).
  For agents that do not support this feature, the value will
  always be 0."
   ::= { prtT1E1CnfgEntry 14 }

prtT1E1LineLengthMask  OBJECT-TYPE
      SYNTAX  INTEGER
       {
        unknown      (1),
        len0p133ft   (2),
        len134p266ft (3),
        len267p399ft (4),
        len400p533ft (5),
        len534p655ft (6),
        fcc68        (7)
       }
      ACCESS  read-write
      STATUS  mandatory
      DESCRIPTION
      "This attribute is the line length mask parameter used only 
       for T1/DSU interfaces.
       len400p533ft=length range: 400ft to 533ft 
       'fcc68' - provides compliance with the FCC 68.308 Option A
                 output pulse mask. "
   ::= { prtT1E1CnfgEntry 15 }

prtT1E1TxGainMask  OBJECT-TYPE
      SYNTAX  INTEGER
       {
          notApplicable     (1),
          txGain0db         (2),
          txGain7dot5db     (3),
          txGain15db        (4),
          txGain22dot5db    (5)
       }
      ACCESS  read-write
      STATUS  mandatory
      DESCRIPTION
      "This attribute is the tx gain mask parameter (dB), used 
       only for T1/CSU interfaces."
   ::= { prtT1E1CnfgEntry 16 }

prtT1E1InbandMng  OBJECT-TYPE
      SYNTAX  INTEGER
       {
          off         (2),
          fdlOrTs0    (3),
          dedicatedTs (4),
          dedicatedPpp(5),
          dedicatedFr (6),
          internal    (7)
       }
      ACCESS  read-write
      STATUS  mandatory
      DESCRIPTION
      "A unique number to identify an Inband management over the 
       link.
       internal - supported by KM-2100 only. It means that the management is internal
                  to the frame. It takes part of the ML Frame bits (instead of data)."
      ::= {prtT1E1CnfgEntry 17}

prtT1E1InbandMngRate  OBJECT-TYPE
      SYNTAX  INTEGER
       {
          notApplicable(1),
          r4k   (2),
          r8k   (3),
          r12k  (4),
          r16k  (5),
          r32k  (6),
          r64k  (7),
          r20k  (8)
       }
      ACCESS  read-write
      STATUS  mandatory
      DESCRIPTION
      "A unique number to identify the rate of the Inband management.
       It is required only for E1 links and is applicable only when 
       prtExT1E1InbandMng selected is FdlOrTs0 or dedicatedTs."
      ::= {prtT1E1CnfgEntry 18}

prtT1E1DedicatedTs  OBJECT-TYPE
      SYNTAX  INTEGER
      ACCESS  read-write
      STATUS  mandatory
      DESCRIPTION
      "A unique number to identify Dedicated TS of the T1/E1 port.
       It is applicable only when prtExT1E1InbandMng selected is 
       dedicatedTs.
       1..24 - Dedicated TS of T1
       1..31 - Dedicated TS of E1
       255   - notApplicable (for agents that do not support this 
               feature)
       Other values are invalid."
      ::= {prtT1E1CnfgEntry 19}

prtT1E1InbandMngRoutProt  OBJECT-TYPE
      SYNTAX  INTEGER
       {
  notApplicable (1),
  none          (2),  
  proprietary   (3),
  rip2          (4)
       }
      ACCESS  read-write
      STATUS  mandatory
      DESCRIPTION
      "Inband Mng Routing Protocol of the port.
       When prtT1E1InbandMng is 'dedicatedPpp'-'proprietary' and
                                               'rip2' are applicable.
       For other values  - only 'proprietary' is applicable."             
      ::= {prtT1E1CnfgEntry 20}

prtT1E1LinkMode  OBJECT-TYPE
      SYNTAX  INTEGER
       {
  notApplicable (1),
  regular       (2),  
  transparent   (3)
       }
      ACCESS  read-write
      STATUS  mandatory
      DESCRIPTION
      "regular - TSs are connected by user via TS Assignment only
       transparent - when a port with this Link Mode is connected to an 
                     internal T1/E1 port of a T3/E3 card, TS0, TS16 and Fbit
                     are transparently transferred to the E3/T3 stream."             
      ::= {prtT1E1CnfgEntry 21}

prtT1E1Multiplier OBJECT-TYPE
              SYNTAX  INTEGER { 
                             notApplicable (1), 
                             br56 (2),
                             br64 (3)
              }
              ACCESS  read-write
              STATUS  mandatory
              DESCRIPTION
                      "The data rate of each TS. The multiplier values
                       can be 56 kbps or 64 kbps. For T1 only."
              ::= { prtT1E1CnfgEntry 22 }


prtT1E1RxGain OBJECT-TYPE
      SYNTAX  INTEGER
       {
          notApplicable  (1),
          rxGain12dB     (2),
          rxGain30dB     (3),
          rxGain36dB     (4),
		  shortHaul      (5),
		  longHaul       (6)
       }
      ACCESS  read-write
      STATUS  mandatory
      DESCRIPTION
      "This attribute is the rx volume (dB)."
   ::= { prtT1E1CnfgEntry 23 }

 prtT1E1RAI  OBJECT-TYPE
      SYNTAX  INTEGER
       {
        notApplicable  (1),
        off (2),
        on  (3)
       }
      ACCESS  read-write
      STATUS  mandatory
      DESCRIPTION
      "Remote Alarm Signal"
   ::= { prtT1E1CnfgEntry 24 }

prtT1E1LineMode OBJECT-TYPE
      SYNTAX  INTEGER 
       {
        notApplicable	(1), 
        csu				(2),
        dsu				(3),
		ltu				(4)
       }
        ACCESS  read-write
        STATUS  mandatory
        DESCRIPTION
      "Interface type of the port.
       For T1 - csu, dsu are the valid values
       For E1 - dsu, ltu are the valid values"
   ::= { prtT1E1CnfgEntry 25 }

prtT1E1TS0SaBits OBJECT-TYPE
 SYNTAX  OCTET STRING 
    ACCESS  read-write
    STATUS  mandatory
    DESCRIPTION
    "This object is applicable only for E1 ports. For T1, string size will be 0.
     For E1, it enables user to select the use of TS0 Sa Bits 4..8, by 3 octets:
	 The order (in hexa display):
	 free Sa-Bit-4  Sa-Bit-5  Sa-Bit-6  Sa-Bit-7  Sa-Bit-8
	 |___________|  |________________|  |________________|
	     MSByte                                 LSByte
	     
	 Each Sa Bit will be represented by a nibble, having the following meaning:
	 0000 = zero
	 0001 = one
	 0010 = management
	 0011 = transparent
	 the rest are reserved for future use."      
   ::= { prtT1E1CnfgEntry 26 }

--prtT1E1 Last FDL Message Table - Statistics

prtT1E1FdlMsgTable  OBJECT-TYPE
     SYNTAX SEQUENCE OF PrtT1E1FdlMsgEntry
     ACCESS not-accessible
     STATUS  mandatory
     DESCRIPTION
      "This table is applicable for a T1 interface with 'esf'
       LineType or E1 interface, when CRC is enabled (LineType)."
  ::= { prtT1E1 3}

prtT1E1FdlMsgEntry OBJECT-TYPE
      SYNTAX PrtT1E1FdlMsgEntry
      ACCESS not-accessible
      STATUS mandatory
      DESCRIPTION "" INDEX {prtT1E1FdlMsgPrtIdx, prtT1E1FdlMsgFdlType}
      ::= { prtT1E1FdlMsgTable 1}

PrtT1E1FdlMsgEntry ::=
      SEQUENCE {
      prtT1E1FdlMsgPrtIdx    INTEGER,
      prtT1E1FdlMsgFdlType   INTEGER,
      prtT1E1FdlMsgSlt       INTEGER,
      prtT1E1FdlMsg          OCTET STRING   
      }

prtT1E1FdlMsgPrtIdx OBJECT-TYPE
      SYNTAX  INTEGER
      ACCESS  read-only
      STATUS  mandatory
      DESCRIPTION
      "This attribute indicates a unique  port number.
    The same numbering as for prtGenPrtIdx.
       The valid port number depends on the IO slot no.,  the 
       installed card type and the port type: outside, inside. 
      * The outside ports will be the T1/E1 cards ports. 
        The convention used will be (for DXC):
      - first two digits will be: (IO slot number+10)
         - last one/two digits will be the port number within the 
           card, in odd numbers:
     port1 = 1
     port2 = 3
     port3 = 5 
     etc...
   Example: port2 of IO slot 11 will be: 213 ."
      ::= { prtT1E1FdlMsgEntry 1}

prtT1E1FdlMsgFdlType OBJECT-TYPE
      SYNTAX  INTEGER
       {
          send    (1),
    receive (2)
    }
      ACCESS  read-only
      STATUS  mandatory
      DESCRIPTION
   "The Fdl type reference of the Fdl message."
      ::= { prtT1E1FdlMsgEntry 2}

prtT1E1FdlMsgSlt    OBJECT-TYPE
      SYNTAX  INTEGER
       {
       io1   (5),
       io2   (6),
       io3   (7),
       io4   (8),
       io5   (9),
       io6  (10),
       io7  (11),
       io8  (12),
       io9  (13),
       io10 (14),
       io11 (15),
       io12 (16),
       io13 (17),
       io14 (18),
       io15 (19),
       standAlone (255)
      }
      ACCESS  read-only
      STATUS  mandatory
      DESCRIPTION
      "This attribute indicates a unique number to identify the slot where
       the card is inserted in.
       When the unit is stand-alone, this object is not applicable
       and 255 will be used."
      ::= { prtT1E1FdlMsgEntry 3}

prtT1E1FdlMsg  OBJECT-TYPE
   SYNTAX  OCTET STRING
      ACCESS  read-only
      STATUS  mandatory
      DESCRIPTION
      "FDL message."
      ::= { prtT1E1FdlMsgEntry 4}


--prtHS specific parameters (configuration & status) table

prtHSParamTable  OBJECT-TYPE
      SYNTAX SEQUENCE OF PrtHSParamEntry
      ACCESS not-accessible
      STATUS  mandatory
      DESCRIPTION "" ::= { prtHS 1 }

prtHSParamEntry OBJECT-TYPE
      SYNTAX PrtHSParamEntry
      ACCESS not-accessible
      STATUS mandatory
      DESCRIPTION "" INDEX { prtHSCnfgIdx, prtHSPrtIdx }
      ::= { prtHSParamTable 1}

PrtHSParamEntry ::=
      SEQUENCE {
      prtHSCnfgIdx       INTEGER,
      prtHSPrtIdx        INTEGER,
      prtHSSlt           INTEGER,
      prtHSRate          INTEGER,
      prtHSFifoSize      INTEGER,
      prtHSClkMode       INTEGER,
      prtHSCTS           INTEGER,
      prtHSRtsState      INTEGER
   }    

   
prtHSCnfgIdx OBJECT-TYPE
      SYNTAX  INTEGER (1..255)
      ACCESS  read-only
      STATUS  mandatory
      DESCRIPTION
      "This attribute indicates the Idx of the Config being accessed.
       Idx of 255 relates to the Temporary (Scratch) Config. "
      ::= { prtHSParamEntry 1}

prtHSPrtIdx OBJECT-TYPE
      SYNTAX  INTEGER
      ACCESS  read-only
      STATUS  mandatory
      DESCRIPTION
      "This attribute indicates a unique number to identify a port. 
       The valid port number depends on the IO slot no.,  the 
       installed card type and the port type: outside, inside, 
       SP.
    * The inside ports will be the HS cards ports. The 
      convention used will be (for DXC):
      - first two digits will be: (IO slot number+10)
         - last one/two digits will be the port number within the 
           card, in even numbers:
     port1 = 2
     port2 = 4
     port3 = 6 
     etc...
   Example: port2 of IO slot 11 will be: 214 ."
      ::= { prtHSParamEntry 2}

prtHSSlt      OBJECT-TYPE
      SYNTAX  INTEGER
       {
       io1   (5),
       io2   (6),
       io3   (7),
       io4   (8),
       io5   (9),
       io6  (10),
       io7  (11),
       io8  (12),
       io9  (13),
       io10 (14),
       io11 (15),
       io12 (16),
       io13 (17),
       io14 (18),
       io15 (19),
       standAlone (255)
       }
      ACCESS  read-only
      STATUS  mandatory
      DESCRIPTION
      "This attribute indicates a unique number to identify the slot where
       the card is inserted in.
       When the unit is stand-alone, this object is not applicable
       and 255 will be used."
      ::= { prtHSParamEntry 3}

prtHSRate     OBJECT-TYPE
      SYNTAX  INTEGER {
        r0x56eq0Kbps     (1),
        r1x56eq56Kbps    (2),
        r2x56eq112Kbps   (3),
        r3x56eq168Kbps   (4),
        r4x56eq224Kbps   (5),
        r5x56eq280Kbps   (6),
        r6x56eq336Kbps   (7),
        r7x56eq392Kbps   (8),
        r8x56eq448Kbps   (9),
        r9x56eq504Kbps  (10),
        r10x56eq560Kbps (11),
        r11x56eq616Kbps (12),
        r12x56eq672Kbps (13),
        r13x56eq728Kbps (14),
        r14x56eq784Kbps (15),
        r15x56eq840Kbps (16),
        r16x56eq896Kbps (17),
        r17x56eq952Kbps (18),
        r18x56eq1008Kbps(19),
        r19x56eq1064Kbps(20),
        r20x56eq1120Kbps(21),
        r21x56eq1176Kbps(22),
        r22x56eq1232Kbps(23),
        r23x56eq1288Kbps(24),
        r24x56eq1344Kbps(25),
        r25x56eq1400Kbps(26),
        r26x56eq1456Kbps(27),
        r27x56eq1512Kbps(28),
        r28x56eq1568Kbps(29),
        r29x56eq1624Kbps(30),
        r30x56eq1680Kbps(31),
        r31x56eq1736Kbps(32),
        r0x64eq0Kbps    (33),
        r1x64eq64Kbps   (34),
        r2x64eq128Kbps  (35),
        r3x64eq192Kbps  (36),
        r4x64eq256Kbps  (37),
        r5x64eq320Kbps  (38),
        r6x64eq384Kbps  (39),
        r7x64eq448Kbps  (40),
        r8x64eq512Kbps  (41),
        r9x64eq576Kbps  (42),
        r10x64eq640Kbps (43),
        r11x64eq704Kbps (44),
        r12x64eq768Kbps (45),
        r13x64eq832Kbps (46),
        r14x64eq896Kbps (47),
        r15x64eq960Kbps (48),
        r16x64eq1024Kbps(49),
        r17x64eq1088Kbps(50),
        r18x64eq1152Kbps(51),
        r19x64eq1216Kbps(52),
        r20x64eq1280Kbps(53),
        r21x64eq1344Kbps(54),
        r22x64eq1408Kbps(55),
        r23x64eq1472Kbps(56),
        r24x64eq1536Kbps(57),
        r25x64eq1600Kbps(58),
        r26x64eq1664Kbps(59),
        r27x64eq1728Kbps(60),
        r28x64eq1792Kbps(61),
        r29x64eq1856Kbps(62),
        r30x64eq1920Kbps(63),
        r31x64eq1984Kbps(64),
        r32x64eq2048Kbps(65),

        r32x56eq1792Kbps(66)
     }
      ACCESS  read-write
      STATUS  mandatory
      DESCRIPTION
      "This object indicates the port rate (speed)."
      ::= { prtHSParamEntry 4}

prtHSFifoSize OBJECT-TYPE
      SYNTAX  INTEGER {
   auto    (1),
   b32bit  (2),
   b60bit  (3),
   b104bit (4),
   b144bit (5),
   notApplicable (255)
   }
      ACCESS  read-write
      STATUS  mandatory
      DESCRIPTION
   "This object selects the size of the user data channel buffer
    FIFO used in the DTE2 mode. In the other modes, buffer 
    size is automatically set by the DACS agent. 
    Buffer FIFO size in bits, corresponds to FIFO lengths of 
    +/-16, +/-30, +/-52, +/-72 bits."
      ::= { prtHSParamEntry 5}

prtHSClkMode OBJECT-TYPE
      SYNTAX  INTEGER {
   dce   (1),
   dte1  (2),
   dte2  (3),
   notApplicable (255)
   }
      ACCESS  read-write
      STATUS  mandatory
      DESCRIPTION
   "Clock Mode of the user data channel. 
    dce - DACS operates as a DCE and provides transmit 
          and receive clocks to the synchronous user DTE.
    dte1- DACS supplies the receive clock to the user 
          equipment and accepts the user transmit clock.
    dte2- DACS requires transmit and receive clocks from 
          the user equipment."
      ::= { prtHSParamEntry 6}

prtHSCTS OBJECT-TYPE
      SYNTAX  INTEGER {
   on   (1),
   rts  (2)
   }
      ACCESS  read-write
      STATUS  mandatory
      DESCRIPTION
    "Selection of CTS line state in the user data channel.
     on  - CTS continuously ON.
     rts - CTS line follows the RTS line."
      ::= { prtHSParamEntry 7}

prtHSRtsState OBJECT-TYPE
      SYNTAX  INTEGER {
   off   (2),
   on    (3),
   notApplicable (255)
   }
      ACCESS  read-only
      STATUS  mandatory
      DESCRIPTION
      "RTS state of the port." 
      ::= { prtHSParamEntry 8}


prtHSBertTable  OBJECT-TYPE
      SYNTAX SEQUENCE OF PrtHSBertEntry
      ACCESS not-accessible
      STATUS  mandatory
      DESCRIPTION "" ::= { prtHS 2 }

prtHSBertEntry OBJECT-TYPE
      SYNTAX PrtHSBertEntry
      ACCESS not-accessible
      STATUS mandatory
      DESCRIPTION "" INDEX { prtHSBertPrtIdx }
      ::= { prtHSBertTable 1}

PrtHSBertEntry ::=
     SEQUENCE {
  prtHSBertPrtIdx        INTEGER,
  prtHSBertSlt           INTEGER,
  prtHSBertCountClr      INTEGER,
  prtHSBertTestResult    INTEGER
      }

prtHSBertPrtIdx OBJECT-TYPE
      SYNTAX  INTEGER
      ACCESS  read-only
      STATUS  mandatory
      DESCRIPTION
      "This attribute indicates a unique number to identify a port. 
       The valid port number depends on the IO slot no.,  the 
       installed card type and the port type: outside, inside, 
       SP.
    * The inside ports will be the HS cards ports. The 
      convention used will be (for DXC):
      - first two digits will be: (IO slot number+10)
         - last one/two digits will be the port number within the 
           card, in even numbers:
     port1 = 2
     port2 = 4
     port3 = 6 
     etc...
   Example: port2 of IO slot 11 will be: 214 ."
      ::= { prtHSBertEntry 1}

prtHSBertSlt  OBJECT-TYPE
      SYNTAX  INTEGER
       {
       io1   (5),
       io2   (6),
       io3   (7),
       io4   (8),
       io5   (9),
       io6  (10),
       io7  (11),
       io8  (12),
       io9  (13),
       io10 (14),
       io11 (15),
       io12 (16),
       io13 (17),
       io14 (18),
       io15 (19),
       standAlone (255)
       }
      ACCESS  read-only
      STATUS  mandatory
      DESCRIPTION
      "This attribute indicates a unique number to identify the slot where
       the card is inserted in.
       When the unit is stand-alone, this object is not applicable
       and 255 will be used."
      ::= { prtHSBertEntry 2}


prtHSBertCountClr OBJECT-TYPE
      SYNTAX  INTEGER {
     off(2),
     on (3)
      }
      ACCESS  read-write
      STATUS  mandatory
      DESCRIPTION
      "Setting this object (to on) initiate bert counter clear 
       operation.
       Valid only when bert test is active on the specific port.
       (Every time a new bert test starts, the counter is 
       automatically cleared; this command enables clearing 
       the counter while the test is running)."
      ::= { prtHSBertEntry 3}

prtHSBertTestResult   OBJECT-TYPE
      SYNTAX  INTEGER
      ACCESS  read-only
      STATUS  mandatory
      DESCRIPTION
      "This object indicates the number of Bit Error Rate indicated 
       during the BERT test.
       Active only when bert test is running on the selected port."
      ::= { prtHSBertEntry 4}



--prt SP specific configuration parameters

prtSpCnfgTable OBJECT-TYPE
      SYNTAX SEQUENCE OF PrtSpCnfgEntry
      ACCESS not-accessible
      STATUS  mandatory
      DESCRIPTION "" ::= {prtSP 1}

prtSpCnfgEntry OBJECT-TYPE
      SYNTAX PrtSpCnfgEntry
      ACCESS not-accessible
      STATUS mandatory
      DESCRIPTION
      "All the entries at this table are identical(have the same value)
       at all the configurations(1..255) except at the TmpCnfg.
       - For products supporting more than one configuration, the write operation 
         into the Table Objects is valid only at the TmpCnfg entry.
       - For products that do not support configurations, the write operation 
         into the Table Objects will be to prtSpCnfgIdx=1."
      INDEX {prtSpCnfgIdx, prtSpPrtIdx }
      ::= { prtSpCnfgTable 1}

PrtSpCnfgEntry ::=
      SEQUENCE {
   prtSpCnfgIdx     INTEGER,
   prtSpPrtIdx      INTEGER,
   prtSpUsage       INTEGER,
   prtSpRate        INTEGER,
   prtSpDataBits    INTEGER,
   prtSpParity      INTEGER,
   prtSpCallOutMode INTEGER,
   prtSpInterface   INTEGER,
   prtSpCTS         INTEGER,
   prtSpDcdDelay    INTEGER,
   prtSpDsr         INTEGER,
   prtSpNoOfRetries INTEGER,
   prtSpWaitForConnect INTEGER,
   prtSpDialMode    INTEGER,
   prtSpAltNumMode  INTEGER,
   prtSpPrimaryNum  DisplayString,
   prtSpAltNum      DisplayString,
   prtSpRoutProtocol INTEGER,
   prtSpCmd          OCTET STRING,
   prtSpActCallOut	INTEGER,
   prtSpAlrRelayMode INTEGER
   }   

prtSpCnfgIdx OBJECT-TYPE
      SYNTAX  INTEGER (1..255)
      ACCESS  read-only
      STATUS  mandatory
      DESCRIPTION
      "This attribute indicates the Idx of the Cnfg(1..255) being 
       accessed.
       Idx of 255 relates to the TmpCnfg."
      ::= { prtSpCnfgEntry 1}

prtSpPrtIdx OBJECT-TYPE
      SYNTAX  INTEGER
      ACCESS  read-only
      STATUS  mandatory
      DESCRIPTION
      "This attribute indicates a unique port number of the SPor DP port.
       For DXC, it is the port in the active DCL card: 
       - SP = 1
       - NP ; DP = 2 
                
       For Kilomux, the port index is calculated as follows:
       100*Slot+Ch.
       
       For FCD, PRBi, the SP port index=1."
      ::= { prtSpCnfgEntry 2}


prtSpUsage OBJECT-TYPE
      SYNTAX  INTEGER
       {
  unknown (1),
  noUse   (2),
  nmsSlip (3),
  nmsPpp  (4),
  muxSlip (5),
  muxPpp  (6),
  terminal(7),
  dialOut (8)
       }
      ACCESS  read-write
      STATUS  mandatory
      DESCRIPTION
      "This attribute indicates what is the usage of the port."
      ::= { prtSpCnfgEntry 3}

prtSpRate     OBJECT-TYPE
      SYNTAX  INTEGER
       {
        auto      (1),
        s300bps   (2),
        s1200bps  (3),
        s2400bps  (4),
        s4800bps  (5),
        s9600bps  (6),
        s19200bps (7),
        s38400bps (8),
        s57600bps (9),
		s115200bps(10)
       }
      ACCESS  read-write
      STATUS  mandatory
      DESCRIPTION
      "This attribute indicates the operation rate (speed) of the port.
       auto - automatic rate selection, by the agent."
      ::= { prtSpCnfgEntry 4}

prtSpDataBits OBJECT-TYPE
      SYNTAX  INTEGER
       {
        dataBits7 (1),
        dataBits8 (2)
       }
      ACCESS  read-write
      STATUS  mandatory
      DESCRIPTION
      "This attribute indicates the number of data bits in async 
       frame"
      ::= { prtSpCnfgEntry 5}

prtSpParity OBJECT-TYPE
      SYNTAX  INTEGER
       {
        none  (1),
        odd   (2),
        even  (3)
       }
      ACCESS  read-write
      STATUS  mandatory
      DESCRIPTION
      "This attribute indicates the parity mode in async frame"
      ::= { prtSpCnfgEntry 6}

prtSpCallOutMode OBJECT-TYPE
      SYNTAX  INTEGER
       {
        notApplicable  (1),
        none           (2),
        all            (3),
        major          (4)
       }
      ACCESS  read-write
      STATUS  mandatory
      DESCRIPTION
      "This attribute indicates the call-out mode.
       For DXC - this object is applicable only for the DP port (2)."
      ::= { prtSpCnfgEntry 7}


prtSpInterface OBJECT-TYPE
      SYNTAX  INTEGER
       {
          dce  (1),
          dte  (2)
       }
      ACCESS  read-write
      STATUS  mandatory
      DESCRIPTION
      "This attribute indicates the supervisory port interface.
       dce - the DACS appears as a DCE for the port.
       dte - the DACS operates as a DTE, for connection via modem,
             for the port.
       Port 2 - when DP, will be always dte(2).  "
      ::= { prtSpCnfgEntry 8}

prtSpCTS OBJECT-TYPE
      SYNTAX  INTEGER
       {
          notApplicable (1),
          on            (2),
          rts           (3)
       }
      ACCESS  read-write
      STATUS  mandatory
      DESCRIPTION
   "CTS line state. This object is applicable only for 
    port (1) = SP"
      ::= { prtSpCnfgEntry 9}

prtSpDcdDelay OBJECT-TYPE
      SYNTAX  INTEGER
       {
          notApplicable (1),
          d0   (2),
          d10  (3),
          d50  (4),
          d100 (5),
          d200 (6),
          d300 (7)
       }
      ACCESS  read-write
      STATUS  mandatory
      DESCRIPTION
   "DCD delay in msec. 
    d10 = delay of 10msec.
    This object is applicable only for  port (1) = SP"
      ::= { prtSpCnfgEntry 10}

prtSpDsr OBJECT-TYPE
      SYNTAX  INTEGER
       {
          notApplicable (1),
          on   (2),
          dtr  (3)
       }
      ACCESS  read-write
      STATUS  mandatory
      DESCRIPTION
   "DSR line state. This object is applicable only for 
    port (1) = SP"
      ::= { prtSpCnfgEntry 11}

prtSpNoOfRetries OBJECT-TYPE
      SYNTAX  INTEGER  (0..8)
      ACCESS  read-write
      STATUS  mandatory
      DESCRIPTION
   "For DXC - this object is applicable only for port (2) = DP.
    The number of dialing retries requested.
    Default = 0"
      ::= { prtSpCnfgEntry 12}

prtSpWaitForConnect OBJECT-TYPE
      SYNTAX  INTEGER
       {
          notApplicable (1),
          t30sec        (2),
          t45sec        (3), 
          t60sec        (4)
       }
      ACCESS  read-write
      STATUS  mandatory
      DESCRIPTION
   "For DXC - this object is applicable only for port (2) = DP.
    Waiting time for connect, in seconds.
    Default = 30 sec."
      ::= { prtSpCnfgEntry 13}

prtSpDialMode OBJECT-TYPE
      SYNTAX  INTEGER
       {
          notApplicable (1),
          tone          (2),
          pulse         (3)
    }
      ACCESS  read-write
      STATUS  mandatory
      DESCRIPTION
   "For DXC - this object is applicable only for port (2) = DP.
    Dialing mode.
    Default=tone"
      ::= { prtSpCnfgEntry 14}

prtSpAltNumMode OBJECT-TYPE
      SYNTAX  INTEGER
       {
          no  (2),
          yes (3)
       }
      ACCESS  read-write
      STATUS  mandatory
      DESCRIPTION
   "For DXC - this object is applicable only for port (2) = DP.
    It determines wether to use the alternate number or not.
    Default = no."
      ::= { prtSpCnfgEntry 15}

prtSpPrimaryNum OBJECT-TYPE
      SYNTAX  DisplayString (SIZE(0..20))
      ACCESS  read-write
      STATUS  mandatory
      DESCRIPTION
   "For DXC - this object is applicable only for port (2) = DP.
    It is the Primary dialing number. "
      ::= { prtSpCnfgEntry 16}

prtSpAltNum OBJECT-TYPE
      SYNTAX  DisplayString (SIZE(0..20))
      ACCESS  read-write
      STATUS  mandatory
      DESCRIPTION
   "For DXC - this object is applicable only for port (2) = DP.
    It is the Alternate dialing number. This number 
    is applicable only if prtSpAltNumMode is 'yes'."
      ::= { prtSpCnfgEntry 17}

prtSpRoutProtocol     OBJECT-TYPE
      SYNTAX  INTEGER
       {
        notApplicable (1),
        none          (2),
        proprietary   (3),
        rip2          (4)
       }
      ACCESS  read-write
      STATUS  mandatory
      DESCRIPTION
      "This attribute indicates the routing protocol of the port.
       notApplicable - for DP."
      ::= { prtSpCnfgEntry 18}

prtSpCmd     OBJECT-TYPE
      SYNTAX OCTET STRING  (SIZE (20))
      ACCESS  read-write
      STATUS  mandatory
      DESCRIPTION
      "SP Command.
      For LRS this parameter will be used for a Modem Command. 
      Upon NMS's Get operation for devices that this parameter 
      is notApplicable, agent will send NULL string."
      ::= { prtSpCnfgEntry 19}

prtSpActCallOut     OBJECT-TYPE
      SYNTAX  INTEGER
       {
        notApplicable (1),
        always        (2),
        linkFail      (3)
       }
      ACCESS  read-write
      STATUS  mandatory
      DESCRIPTION
      "This object indicates when to Activate Call-Out.
	   It is used by FCD-T1/E1.
       always - to activate call-out always.
       linkFail - to activate call-out only when Link of Inband Management fails."
      ::= { prtSpCnfgEntry 20}

prtSpAlrRelayMode OBJECT-TYPE
      SYNTAX  INTEGER
       {
  	    notApplicable (1),	
  		normal        (2),
        invert        (3)
       }
      ACCESS  read-write
      STATUS  mandatory
      DESCRIPTION
      "This attribute indicates the Alarm Relay Mode.
       notApplicable - for DP."
      ::= { prtSpCnfgEntry 21}



--prt DIM (DXC Inverse Multiplexer) specific parameters

prtDimCnfgTable OBJECT-TYPE
      SYNTAX SEQUENCE OF PrtDimCnfgEntry
      ACCESS not-accessible
      STATUS  mandatory
      DESCRIPTION "" ::= {prtDim 1}

prtDimCnfgEntry OBJECT-TYPE
      SYNTAX PrtDimCnfgEntry
      ACCESS not-accessible
      STATUS mandatory
      DESCRIPTION
      "The write operation into the Table Objects is valid only
       for the TmpCnfg entry (prtDimCnfgIdx=255)."
      INDEX {prtDimCnfgIdx, prtDimIdx }
      ::= { prtDimCnfgTable 1}

PrtDimCnfgEntry ::=
      SEQUENCE {
   prtDimCnfgIdx  INTEGER,
   prtDimIdx      INTEGER,
   prtDimTxMode   INTEGER,
   prtDimPolarity INTEGER,
   prtDimClkMode  INTEGER,
   prtDimMaxDelay INTEGER,
   prtDimMng      INTEGER
   }      
       

prtDimCnfgIdx OBJECT-TYPE
      SYNTAX  INTEGER (1..255)
      ACCESS  read-only
      STATUS  mandatory
      DESCRIPTION
      "This attribute indicates the Idx of the Cnfg(1..255) being 
       accessed.
       Idx of 255 relates to the TmpCnfg."
      ::= { prtDimCnfgEntry 1}

prtDimIdx OBJECT-TYPE
      SYNTAX  INTEGER
      ACCESS  read-only
      STATUS  mandatory
      DESCRIPTION
      "This attribute indicates a unique  port number of the
       DIM card. 
       The convention used for DXC:
       (IO slot number+10)*10 + 1
       Example: port1 of IO slot 11 will be: 211 ."
      ::= { prtDimCnfgEntry 2}


prtDimTxMode OBJECT-TYPE
      SYNTAX  INTEGER
       {
       regularTx   (2),
       broadcast   (3)
       }
      ACCESS  read-write
      STATUS  mandatory
      DESCRIPTION
      "Tx mode.
       regularTx - the links are connected to a similar outfit on 
                   the other side. In this mode, if a link fails, 
                   the transmitted bandwidth is decreased 
                   accordingly.
       broadcast - the links are connected to MORE than one similar
                   outfit on the other side. In this mode, if a link 
                   fails, the transmitted bandwidth is not affected "
      ::= { prtDimCnfgEntry 3}

prtDimPolarity OBJECT-TYPE
      SYNTAX  INTEGER
       {
       normalClk (2),
       inverted  (3)
       }
      ACCESS  read-write
      STATUS  mandatory
      DESCRIPTION
      "Polarity."
      ::= { prtDimCnfgEntry 4}

prtDimClkMode OBJECT-TYPE
      SYNTAX  INTEGER
       {
       extDce   (2),
       dce      (3),
	   smooth   (4),
	   extSmooth(5)
       }
      ACCESS  read-write
      STATUS  mandatory
      DESCRIPTION
      "Clock Mode.
       smooth - a clock that is not 'pulsed'(has no 'gaps'). In this mode
	            the DXC does NOT receive back the clock signal.
       extSmooth - same as 'smooth' but in this mode, the DXC receives back
                the clock signal."
      ::= { prtDimCnfgEntry 5}

prtDimMaxDelay OBJECT-TYPE
      SYNTAX  INTEGER
       {
       t16msec (2),
       t64msec (3)
       }
      ACCESS  read-write
      STATUS  mandatory
      DESCRIPTION
      "Max Delay permitted between the links, in msec."
      ::= { prtDimCnfgEntry 6}

prtDimMng OBJECT-TYPE
      SYNTAX  INTEGER
       {
       disabled (2),
       ts1      (3)
       }
      ACCESS  read-write
      STATUS  mandatory
      DESCRIPTION
      "Use of DIM port for management.
       disabled - no management on DIM
       ts1      - 1 bit of TS1 is used for management."
      ::= { prtDimCnfgEntry 7}


prtDimDestTable OBJECT-TYPE
      SYNTAX SEQUENCE OF PrtDimDestEntry
      ACCESS not-accessible
      STATUS  mandatory
      DESCRIPTION "" ::= {prtDim 2}

prtDimDestEntry OBJECT-TYPE
      SYNTAX PrtDimDestEntry
      ACCESS not-accessible
      STATUS mandatory
      DESCRIPTION
      "The write operation is valid only for the TmpCnfg entry 
       (prtDimDestCnfgIdx=255)."
      INDEX {prtDestCnfgIdx, prtDestDimIdx, prtDestIdx }
      ::= { prtDimDestTable 1}

PrtDimDestEntry ::=
      SEQUENCE {
   prtDestCnfgIdx INTEGER,
   prtDestDimIdx  INTEGER,
   prtDestIdx     INTEGER,
   prtDest        INTEGER,
   prtDestConnect INTEGER
   }      
       

prtDestCnfgIdx OBJECT-TYPE
      SYNTAX  INTEGER (1..255)
      ACCESS  read-only
      STATUS  mandatory
      DESCRIPTION
      "This attribute indicates the Idx of the Cnfg(1..255) being 
       accessed.
       Idx of 255 relates to the TmpCnfg."
      ::= { prtDimDestEntry 1}

prtDestDimIdx OBJECT-TYPE
      SYNTAX  INTEGER
      ACCESS  read-only
      STATUS  mandatory
      DESCRIPTION
      "This attribute indicates a unique  port number of the
       DIM card. 
       The convention used for DXC:
       (IO slot number+10)*10 + 1
       Example: port1 of IO slot 11 will be: 211 ."
      ::= { prtDimDestEntry 2}

prtDestIdx OBJECT-TYPE
      SYNTAX  INTEGER (1..8)
      ACCESS  read-only
      STATUS  mandatory
      DESCRIPTION
      "This attribute indicates a destination number of the
       DIM card. "
      ::= { prtDimDestEntry 3}


prtDest OBJECT-TYPE
      SYNTAX  INTEGER
      ACCESS  read-write
      STATUS  mandatory
      DESCRIPTION
      "Destination port,(of a T1/E1 port), that is connected to the 
    DIM card, for the specified Destination number.
    0 = No destination port.
    Else:
	For external ports:
    (IO Slot+10)*10 + 1    for port 1 
    (IO Slot+10)*10 + 3    for port 2 
       Example: port2 of IO slot 12 will be: 223 .
    For internal ports :
    (IO Slot+10)*10 + 2    for port 1
    (IO Slot+10)*10 + 4    for port 2
    (IO Slot+10)*10 + 6    for port 3
    (IO Slot+10)*10 + 8    for port 4, etc..."
      ::= { prtDimDestEntry 4}

prtDestConnect OBJECT-TYPE
      SYNTAX  INTEGER
       {
       no (2),
       yes(3)
       }
      ACCESS  read-only
      STATUS  mandatory
      DESCRIPTION
      "Connection Status of the specified destination number.
    For a specified destination port, it depends both on the 
    status of the port and on the status of the far-end port.
    Since this is a RO object, same value will be received for
    all configurations."
      ::= { prtDimDestEntry 5}


--prtI - ISDN specific parameters table

prtICnfgTable  OBJECT-TYPE
      SYNTAX SEQUENCE OF PrtICnfgEntry
      ACCESS not-accessible
      STATUS  mandatory
      DESCRIPTION "" ::= { prtI 1 }

prtICnfgEntry OBJECT-TYPE
      SYNTAX PrtICnfgEntry
      ACCESS not-accessible
      STATUS mandatory
      DESCRIPTION "" INDEX { prtICnfgIdx, prtIIdx }
      ::= { prtICnfgTable 1}

PrtICnfgEntry ::=
      SEQUENCE {
      prtICnfgIdx  INTEGER,
      prtIIdx      INTEGER,
      prtIRate     INTEGER,
      prtIConnect  INTEGER
      }    

   
prtICnfgIdx OBJECT-TYPE
      SYNTAX  INTEGER (1..255)
      ACCESS  read-only
      STATUS  mandatory
      DESCRIPTION
      "This attribute indicates the Idx of the Config being accessed.
       Idx of 255 relates to the Temporary (Scratch) Config. "
      ::= {prtICnfgEntry 1}

prtIIdx OBJECT-TYPE
      SYNTAX  INTEGER
      ACCESS  read-only
      STATUS  mandatory
      DESCRIPTION
      "This attribute indicates a unique number to identify a port. 
       The valid port number depends on the IO slot no.,  the 
       installed card type and the port type: outside, inside, 
       SP.
    * The ISDN B1, B2, D channels will be inside ports. 
      For port index, see product specification."
      ::= {prtICnfgEntry 2}

prtIRate     OBJECT-TYPE
      SYNTAX  INTEGER {
        notApplicable (1),
        nc            (2),
        r2bit         (3),
        r4bit         (4),
        r8bit         (5)
        }
      ACCESS  read-write
      STATUS  mandatory
      DESCRIPTION
      "This object indicates the port rate in bits.
       Each TS contains 8 bits. Thus, 1 bit is equivalent to 8Kbps
       rate."
      ::= {prtICnfgEntry 3}

prtIConnect     OBJECT-TYPE
      SYNTAX  INTEGER {
        notApplicable (1),
        no            (2),
        yes           (3)
        }
      ACCESS  read-write
      STATUS  mandatory
      DESCRIPTION
      "D channel connection.
       no  - disconnected
       yes - connected. "
      ::= {prtICnfgEntry 4}


--prtHdsl - HDSL specific parameters table

prtHdslTable  OBJECT-TYPE
      SYNTAX SEQUENCE OF PrtHdslEntry
      ACCESS not-accessible
      STATUS  mandatory
      DESCRIPTION "" ::= { prtHdsl 1 }

prtHdslEntry OBJECT-TYPE
      SYNTAX PrtHdslEntry
      ACCESS not-accessible
      STATUS mandatory
      DESCRIPTION "" INDEX { prtHdslIdx }
      ::= { prtHdslTable 1}

PrtHdslEntry ::=
      SEQUENCE {
      prtHdslIdx   INTEGER,
      prtHdslMode  INTEGER,
      prtHdslRptrType INTEGER
      }    
   
prtHdslIdx OBJECT-TYPE
      SYNTAX  INTEGER
      ACCESS  read-only
      STATUS  mandatory
      DESCRIPTION
      "This attribute indicates a unique number to identify a port. 
       The valid port number depends on the IO slot no.,  the 
       installed card type and the port type: outside, inside.
    * The HDSL ports will be external. 
      For port index, see product specification."
      ::= {prtHdslEntry 1}

prtHdslMode   OBJECT-TYPE
      SYNTAX  INTEGER {
        notApplicable (1),
        central       (2),
        remote        (3)
        }
      ACCESS  read-only
      STATUS  mandatory
      DESCRIPTION
      "This object indicates the HDSL mode."
      ::= {prtHdslEntry 2}

prtHdslRptrType     OBJECT-TYPE
      SYNTAX  INTEGER {
      notApplicable (1),
      none    (2), 
      hrpt    (3)
        }
      ACCESS  read-only
      STATUS  mandatory
      DESCRIPTION
      "The Repeater between Near and Far modem.
       none - no repeater exists between the modems
       hrpt - HRPT repeater exists between the modems."
      ::= {prtHdslEntry 3}


--DACS T3/E3 port configuration parameters.
--
--These objects were entered in this private MIB, because they do not 
--appear in RFC1407 (except prtT3E3LineLength which appears in meters) and in
--RFC-1407 MIB there is no reference to configuration number.


prtT3E3CnfgTable OBJECT-TYPE
  SYNTAX  SEQUENCE OF PrtT3E3CnfgEntry
  ACCESS  not-accessible
  STATUS  mandatory
  DESCRIPTION
  "T3/E3 port configuration table."
  ::= { prtT3E3 1}

prtT3E3CnfgEntry   OBJECT-TYPE
  SYNTAX  PrtT3E3CnfgEntry
  ACCESS  not-accessible
  STATUS  mandatory
  DESCRIPTION
  " An entry in the T3/E3 port configuration table."
  INDEX { prtT3E3CnfgIdx, prtT3E3PrtIdx }
  ::= { prtT3E3CnfgTable 1}

PrtT3E3CnfgEntry ::=
     SEQUENCE {
  prtT3E3CnfgIdx
  INTEGER,
  prtT3E3PrtIdx
  INTEGER,
  prtT3E3Slt
  INTEGER,
  prtT3E3LineLength
  INTEGER,
  prtT3E3InbandMng
  INTEGER
  }
 
prtT3E3CnfgIdx OBJECT-TYPE
      SYNTAX  INTEGER (1..255)
      ACCESS  read-only
      STATUS  mandatory
      DESCRIPTION
      "This attribute indicates the Idx of the Config being accessed.
       Idx of 255 relates to the Temporary (Scratch) Config.
       Write operations can be performed only on the Temp Config."
      ::= { prtT3E3CnfgEntry 1}

prtT3E3PrtIdx OBJECT-TYPE
      SYNTAX  INTEGER
      ACCESS  read-only
      STATUS  mandatory
      DESCRIPTION
      "This attribute indicates a unique  port number.
    The same numbering as for prtGenPrtIdx.
       The valid port number depends on the IO slot no.,  the 
       installed card type and the port type: outside, inside. 
      * The external ports convention used will be (for DXC):
        - first two digits will be: (IO slot number+10)
        - last one/two digits will be the port number within the 
            card, in odd numbers:
            port1 = 1
            port2 = 3
            port3 = 5 
            etc...
            Example: port2 of IO slot 11 will be: 213 ."
      ::= { prtT3E3CnfgEntry 2}

prtT3E3Slt     OBJECT-TYPE
      SYNTAX  INTEGER
       {
       clA   (3),
       clB   (4),
       io1   (5),
       io2   (6),
       io3   (7),
       io4   (8),
       io5   (9),
       io6  (10),
       io7  (11),
       io8  (12),
       io9  (13),
       io10 (14),
       io11 (15),
       io12 (16),
       io13 (17),
       io14 (18),
       io15 (19),
       standAlone (255)
       }
      ACCESS  read-only
      STATUS  mandatory
      DESCRIPTION
      "This attribute indicates a unique number to identify the slot where
       the card is inserted in.
       When the unit is stand-alone, this object is not applicable
       and 255 will be used."
      ::= { prtT3E3CnfgEntry 3}

prtT3E3LineLength  OBJECT-TYPE
      SYNTAX  INTEGER
       {
        notApplicable(1),
        len0p450ft   (2),
        len451p900ft (3)
       }
      ACCESS  read-write
      STATUS  mandatory
      DESCRIPTION
      "This object is the length of the ds3 line in feet.  
       It provides information for line build out circuitry if it exists 
       and can use this object to adjust the line build out. 
       len0p450ft   = 0   - 450 feet
       len451p900ft = 451 - 900 feet."
   ::= { prtT3E3CnfgEntry 4}

prtT3E3InbandMng  OBJECT-TYPE
      SYNTAX  INTEGER
       {
          notApplicable(1),
          off          (2),
          cBit         (3), --Cbit-Tx-Rx
          cBitTxRxMng  (4),
          cBitTx       (5),
          cBitTxMng    (6),
          m13          (7) 
       }
      ACCESS  read-write
      STATUS  mandatory
      DESCRIPTION
      "A unique number to identify the Frame Type over the link."
      ::= {prtT3E3CnfgEntry 5}


--DACS General data, unrelated to a specific level or unit type

--Compressed data table - applicable for all the MIB leafs,
--Used only by NMS station

cmprTable  OBJECT-TYPE
      SYNTAX SEQUENCE OF CmprEntry
      ACCESS not-accessible
      STATUS  mandatory
      DESCRIPTION "" ::= { genDacsMux 1 }

cmprEntry OBJECT-TYPE
      SYNTAX CmprEntry
      ACCESS not-accessible
      STATUS mandatory
		DESCRIPTION "" 
      INDEX {cmprTypeIdx, cmprCnfgIdx,cmprVersion,cmprSltIdx,cmprPrtIdx}
      ::= {cmprTable  1}

CmprEntry ::=
      SEQUENCE {
  cmprTypeIdx      INTEGER,
  cmprCnfgIdx      INTEGER,
  cmprVersion      INTEGER,
  cmprSltIdx       INTEGER,
  cmprPrtIdx       INTEGER,
  cmprObj          OCTET STRING
      }

cmprTypeIdx OBJECT-TYPE
      SYNTAX  INTEGER
      ACCESS  read-only
      STATUS  mandatory
      DESCRIPTION
      "This object indicates the Type of the Compressed 
       data referred (which table, which level, etc).
       The type is a code according to a convention between
       agent and NMS."
      ::= { cmprEntry 1}

cmprCnfgIdx OBJECT-TYPE
      SYNTAX  INTEGER
      ACCESS  read-only
      STATUS  mandatory
      DESCRIPTION
      "This object indicates the configuration number the
       Compressed information relates to."
      ::= { cmprEntry 2}

cmprVersion OBJECT-TYPE
      SYNTAX  INTEGER
      ACCESS  read-only
      STATUS  mandatory
      DESCRIPTION
      "This object indicates the version of the internal format of
       the Compressed data (the version of the convention used)."
      ::= { cmprEntry 3}

cmprSltIdx  OBJECT-TYPE
     SYNTAX  INTEGER
         {
         psA   (1),
         psB   (2),
         clA   (3),
         clB   (4),
         io1   (5),
         io2   (6),
         io3   (7),
         io4   (8),
         io5   (9),
         io6  (10),
         io7  (11),
         io8  (12),
         io9  (13),
         io10 (14),
         io11 (15),
         io12 (16),
         io13 (17),
         io14 (18),
         io15 (19),
         notApplicable (255)
         }
     ACCESS  read-only
     STATUS  mandatory
     DESCRIPTION
     "This attribute indicates a unique number of  the slot  
      position where the card is inserted.
      When the unit is stand-alone or this object is not applicable,
      255 will be used."
     ::= { cmprEntry 4}


cmprPrtIdx  OBJECT-TYPE
      SYNTAX  INTEGER
      ACCESS  read-only
      STATUS  mandatory
      DESCRIPTION
      "This object indicates a unique identifier of the port,
       the compressed information relates to.
    For DXC - according to the order in the card of cmprSltIdx:
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 .
    For FCD: see product's specification.
       If the port number is irrelevant to this parameter (if it is
       a system/card level alarm) the value will be 9999."
      ::= { cmprEntry 5}

cmprObj OBJECT-TYPE
      SYNTAX  OCTET STRING
      ACCESS  read-write
      STATUS  mandatory
      DESCRIPTION
      "This object is the compressed information itself, 
       according to a predefined format, both agent and NMS agreed
       about."
      ::= { cmprEntry 6}


--mapLinkTable

mapLinkTable OBJECT-TYPE
      SYNTAX SEQUENCE OF MapLinkEntry
      ACCESS not-accessible
      STATUS  mandatory
      DESCRIPTION "" ::= { genDacsMux 2}

mapLinkEntry OBJECT-TYPE
      SYNTAX MapLinkEntry
      ACCESS not-accessible
      STATUS mandatory
      DESCRIPTION "" INDEX {mapLinkIdx}
      ::= {mapLinkTable 1}

MapLinkEntry ::=
      SEQUENCE {
      mapLinkIdx               INTEGER,
      mapLinkSlotIdx           INTEGER,
      mapLinkPortIdx           INTEGER,
      mapLinkState             INTEGER
      }

mapLinkIdx     OBJECT-TYPE
      SYNTAX  INTEGER
      ACCESS  read-only
      STATUS  mandatory
      DESCRIPTION
      "A unique identifier of the link"
::=  {mapLinkEntry 1}

mapLinkSlotIdx    OBJECT-TYPE
      SYNTAX  INTEGER
        {
         io1   (5),
         io2   (6),
         io3   (7),
         io4   (8),
         io5   (9),
         io6  (10),
         io7  (11),
         io8  (12),
         io9  (13),
         io10 (14),
         io11 (15),
         io12 (16),
         io13 (17),
         io14 (18),
         io15 (19),
         standAlone (255)
     }
      ACCESS  read-write
      STATUS  mandatory
      DESCRIPTION
      "This attribute indicates a unique  slot  position where
       the module is inserted."       
::=  {mapLinkEntry 2}

mapLinkPortIdx  OBJECT-TYPE
      SYNTAX  INTEGER
      ACCESS  read-write
      STATUS  mandatory
      DESCRIPTION
      "This attribute indicates a unique  port number.
       The valid port number depends on the IO slot no.,  the 
       installed card type and the port type: outside, inside, 
       SP.
       In the DXC :
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 ."
::=  {mapLinkEntry 3}

mapLinkState   OBJECT-TYPE
      SYNTAX  INTEGER
 {
 unknown(1),
 down(2),
 up(3)
 }
      ACCESS  read-only
      STATUS  mandatory
      DESCRIPTION
      "This attribute indicates the status of the link between 
       the two muxes"
::=  {mapLinkEntry 4}

 
--Alarms List - this list is transmitted from agent to NMS once.
--              Afterwards, when an alarm occurs, only the code
--              is sent.

alrGenTable  OBJECT-TYPE
      SYNTAX SEQUENCE OF AlrGenEntry
      ACCESS not-accessible
      STATUS  mandatory
      DESCRIPTION "" ::= { genDacsMux 3 }

alrGenEntry OBJECT-TYPE
      SYNTAX AlrGenEntry
      ACCESS not-accessible
      STATUS mandatory
      DESCRIPTION "" INDEX { alrGenCode }
      ::= { alrGenTable 1}

AlrGenEntry ::=
      SEQUENCE {
     alrGenCode          INTEGER,
     alrGenDescription  DisplayString (SIZE (0..255)),
     alrGenLevel         INTEGER,
	 alrGenSlotType      INTEGER,
	 alrGenSeverity      INTEGER,
	 alrGenDebounce      INTEGER
      }

alrGenCode OBJECT-TYPE
      SYNTAX  INTEGER
      ACCESS  read-only
      STATUS  mandatory
      DESCRIPTION
      "This object is a unique code number, identifying 
       a certain alarm."
    ::= { alrGenEntry 1}

alrGenDescription  OBJECT-TYPE
      SYNTAX  DisplayString (SIZE (0..255))
      ACCESS  read-only
      STATUS  mandatory
      DESCRIPTION
      "This entry is a unique text description, of the alarm 
       corresponding to the specified code."
       ::= { alrGenEntry 2}
       
alrGenLevel   OBJECT-TYPE
      SYNTAX  INTEGER
      {
       notApplicable(1),
       system       (2),
       card         (3),
       port         (4)
      }
      ACCESS  read-only
      STATUS  mandatory
      DESCRIPTION
      "Alarm level."
      ::=  {alrGenEntry 3}

alrGenSlotType   OBJECT-TYPE
      SYNTAX  INTEGER
      {
       notApplicable(1),
       ps           (2),
       cl           (3),
       io           (4),
	   clAndIo      (5)
      }
      ACCESS  read-only
      STATUS  mandatory
      DESCRIPTION
      "Slot type that the alarm is relevant to.
       clAndIo - an alarm that is relevant for both CL and IO slots."
      ::=  {alrGenEntry 4}

alrGenSeverity   OBJECT-TYPE
      SYNTAX  INTEGER
      {
       notApplicable (1),
       minor    (4),
       major    (5)
       }
      ACCESS  read-write
      STATUS  mandatory
      DESCRIPTION
      "This object enables the user to select a severity for each alarm.
       The severity is set per alarm code (same for all slots/ports
       using this code)."
      ::=  {alrGenEntry 5}

alrGenDebounce   OBJECT-TYPE
      SYNTAX  INTEGER (0..255)
      ACCESS  read-write
      STATUS  mandatory
      DESCRIPTION
      "Debounce time for each alarm code, in seconds.
       The meaning is, that an alarm will be 'declared' as ON (or OFF), only 
       after it was actually ON/OFF the Debouncing time selected by user.
       0 = default debounce selection (each alarm has a default value).
	   1 = minimum value of seconds for debounce.
       255 = mask = the alarm will Never be reported. "
      ::=  {alrGenEntry 6}


-- Traps

     sanityCheckTrap  TRAP-TYPE
        ENTERPRISE      dacsMux
        VARIABLES { sysSSanityCheckStatus, sysDbaseDownloadCnfgIdxCmd }
        DESCRIPTION     
        "This trap is sent after a data base download attempt. 
         It returns the sanity result status and the configuration
         no.checked."
        ::= 1

     dacsMuxAlarmsTrap  TRAP-TYPE
       ENTERPRISE      dacsMux
       DESCRIPTION     
       "This trap is sent when an alarm occurs."
       ::= 2

     mdlConnectTrap  TRAP-TYPE
       ENTERPRISE      dacsMux
       VARIABLES       {mdlSCardType, mdlSActivity}
       DESCRIPTION     
       "This trap is sent when a card is removed."
       ::= 3

     sysAlrStatusTrap  TRAP-TYPE
       ENTERPRISE      dacsMux
       VARIABLES       { sysSAlrStatusAll, sysSAlrStatus }
       DESCRIPTION     
       "This trap is sent upon any change in the value of any of 
        the variables."
       ::= 4
 

     sysStatusChangedTrap  TRAP-TYPE
       ENTERPRISE      dacsMux
       VARIABLES       {agnLed}
       DESCRIPTION     
       "This trap is sent when Leds status is changed."
       ::= 5


     cnfgUpdateTrap  TRAP-TYPE
       ENTERPRISE      dacsMux
       DESCRIPTION     
       "This trap is sent upon change of the active Configuration DB."  
       ::= 6


END
