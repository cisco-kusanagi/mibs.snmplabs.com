-- Do not edit this file.
-- It is generated automatically by mib-expand
-- from chassis.mib.in and *.mibdef.
--			Ascend Chassis Management Group
--
--			Ascend Communications, Inc
--			1275 Harbor Bay Pkwy
--			Alameda, CA 94502
--			+1 510 769 6001
--			info@ascend.com
--
--		Copyright (c) 1993-1999 Ascend Communications, Inc.
--		All rights reserved.
--
-- $Id: chassis.mib.in,v 29.2.16.3 1999/10/05 17:37:34 seanw Exp $
-- This file is generated automatically for TAOS version 8.0.5.
--
-- Nov 09 98: MK initial realease
-- Feb 02 99: RYU added st100-ds3-atm, st100-uds3, st100-sdsl16.
-- Mar 11 99: MK modified Description fields.
-- Mar 16 99: RYU added st100-oc3-atm

ASCEND-CHASSIS-MIB DEFINITIONS ::= BEGIN

    IMPORTS
	slots
	    FROM ASCEND-MIB
	TimeTicks
	    FROM RFC1155-SMI
	DisplayString
	    FROM RFC1213-MIB
	OBJECT-TYPE
	    FROM RFC-1212;


	--
	-- Ascend Slot Types
	--

    AscendSlotType	::= INTEGER {
			other(1), -- none of the following
			empty(2), -- empty slot
			sysT1(3), -- motherboard
			slotT1(4), -- slot card
			sysE1(5), -- motherboard
			slotE1(6), -- slot card
			bri(7), -- basic rate interface
			s56-2(8), -- 2 wire switched 56
			s56-4(9), -- 4 wire switched 56
			dualHost(10), -- 2 port Plus
			quadHost(11), -- 4 port Plus
			aim2(12), -- 2 port Max slot card
			aim6(13), -- 6 port Max slot card
			ethernet(14), -- ethernet
			ethernetData(15), -- ethernet aux HDLC card
			slotBriTE(16), -- BRI TE card for the MAX
			slotBriNT(17), -- BRI NT card for the MAX
			lanModem(18), -- LAN MODEM slot card
			serialWan(19), -- Serial WAN slot card
			v110(20), -- V.110 slot card
			slotBriLT(21), -- BRI LT card for the MAX
			lanModemP(22), -- programmable V.34 LAN MODEM slot card 8 ports
			lanModemP12(23), -- programmable V.34 LAN MODEM slot card 12 ports
			pots(24), -- Plain Old Telephone Service ports
			analogModem(25), -- Analog Modem slot card (TNT) (obsoleted by analogModem2 )
			lanModemP48(26), -- programmable V.34 LAN MODEM slot card 48 ports (TNT)
			router(27), -- dedicated router card (TNT)
			unchanT1(28), -- unchannelized T1 card (TNT)
			t3(29), -- DS3 interface card (TNT)
			hssi(30), -- High Speed Serial Interface card (TNT)
			primaryNailedT1(31), -- Primary Nailed T1
			primaryNailed56(32), -- Primary Nailed 56
			dig-8modem(33), -- MAX slot card with eight 56K digital modems.
			dig-12modem(34), -- MAX slot card with twelve 56K digital modems.
			dig-16modem(35), -- MAX slot card with sixteen 56K digital modems.
			dig-48modem(36), -- TNT slot card with forty-eight 56K digital modems.
			phs-8v32modem(37), -- MAX slot card with eight V.32 PHS modems.
			phs-12v32modem(38), -- MAX slot card with twelve V.32 PHS modems.
			phs-16v32modem(39), -- MAX slot card with sixteen V.32 PHS modems.
			sdsl(40), -- TNT slot card with 16 SDSL lines
			cap-adsl(41), -- TNT slot card with 6 CAP ADSL lines
			dmt-adsl(42), -- TNT slot card with 6 DMT ADSL lines
			idsl(43), -- TNT slot card with 32 ISDN DSL lines
			unchanE1(44), -- TNT unchannelized E1 card
			analogModem2(45), -- TNT new Analog Modem slot card
			voip-8dsp(46), -- MAX slot card with 8 VOIP DSPs
			voip-12dsp(47), -- MAX slot card with 12 VOIP DSPs
			voip-16dsp(48), -- MAX slot card with 16 VOIP DSPs
			csmx(49), -- TNT csm/3 based modem slot card
			uds3(50), -- TNT unchannelized DS3 slot card
			ethernet10-100(51), -- TNT 10/100BaseT Ethernet slot card
			ds3-atm(52), -- TNT DS3 ATM slot card
			ethernet2(53), -- Ethernet Ver 2 card
			ethernetData2(54), -- ethernet aux HDLC2 card
			sdsl-data(55), -- TNT SDSL data card
			madd(56), -- TNT Multiple App Dsp slot card
			sdsl-voice(57), -- TNT SDSL voice card
			slotBriTeU(58), -- BRI TE with U-interface
			slotOc3Daughter(59), -- Stinger-10 ATM OC3 trunk daughter card
			oc3-atm(60), -- Tnt Single interface OC3/ATM card
			ethernet3(61), -- Ethernet Ver 3 card
			srs-ether(62), -- SRS ethernet card
			sdsl-atm(63), -- Stinger-10 SDSL ATM card
			alcatel-dadsl-atm(64), -- Stinger-10 DMT ADSL ATM card
			csm3v(65), -- TNT csm/3v based modem slot card
			st100-ds3-atm(66), -- DS3-ATM I/O card for the stinger 100
			st100-uds3(67), -- Unchannelized DS3 I/O card for the stinger 100
			st100-sdsl16(68), -- SDSL I/O card with 16 ports for the stinger 100
			ethernetData2ec(69), -- ethernet aux HDLC2EC card
			slotDs3Daughter(70), -- Stinger-10 ATM DS3 trunk daughter card
			st100-sdsl8(71), -- SDSL I/O card with 8 ports for the stinger 100
			ether-dual(72), -- Dual 10/100 Ethernet card
			st100-oc3-atm(73), -- OC3-ATM I/O card for the stinger 100
			ethernet4(74), -- Ethernet Ver 4 card
			stm0(75), -- Single STM-0 interface
			st100-cc3-atm(76), -- OC3-ATM I/O card for the stinger 100
			lanModem-csmx(77), -- MAX csm3 modem slot
			maxpotsFxs(78), -- MaxPots FXS slot card
			ds3-atm2(79), -- DS3 ATM slot card Vers 2
			occupied(80), -- for cards that take more than one slot space
			stinger-control-module(81), -- Stinger Control Module card
			tnt-control-module(82), -- TNT Control Module card
			dadsl-atm-16ports(83), -- Stinger-10 16 port DMT ADSL ATM card
			alcatel-dadsl-atm-v2(84), -- Stinger-10 12 port DMT ADSL ATM card Ver. 2
			sdsl-atm-v2(85), -- Stinger-10 SDSL ATM card Ver. 2
			dadsl-atm-16ports-v2(86), -- Stinger-10 16 port DMT ADSL ATM card Ver. 2
			dadsl-atm-24ports(87), -- Stinger-10 24 port DMT ADSL ATM card
			glite-atm-48ports(91), -- Stinger-10 48 port DMT GLITE ATM card
			e3-atm(92), -- E3 ATM slot card
			madd2(93), -- MADD2 96 channel card
			hdsl2(94), -- Stinger-10 32 port HDSL2 card
			annexb-dadsl-atm(96), -- Stinger-10 12 port ANNEX B DMT card
			apx-control-module(97) -- APX Control Module card
			}

	--
	-- Ascend chassis info group
	--
	-- This group contains general information
	-- about the chassis as a whole.

    chassisInfo		OBJECT IDENTIFIER ::=  { slots 6 }

    chassisDesc		OBJECT-TYPE
	SYNTAX		DisplayString
	ACCESS		read-only
	STATUS		mandatory
	DESCRIPTION	"The chassis type description."
	::= { chassisInfo 1 }

    chassisSerialNo	OBJECT-TYPE
	SYNTAX		INTEGER
	ACCESS		read-only
	STATUS		mandatory
	DESCRIPTION	"The chassis serial number."
	::= { chassisInfo 2 }

    chassisHWRev	OBJECT-TYPE
	SYNTAX		DisplayString
	ACCESS		read-only
	STATUS		mandatory
	DESCRIPTION	"The chassis hardware revision.
			 For non-TNT platforms it is
			 always reported as empty string."
	::= { chassisInfo 3 }

    chassisRedundancy	OBJECT-TYPE
	SYNTAX		INTEGER {
				noRedundancy(1),
				redundancy(2)
				}
	ACCESS		read-only
	STATUS		mandatory
	DESCRIPTION	"Value to indicate if this platform is running with
			 redundant controller." 
	::= { chassisInfo 4 }

    chassisMemTotal	OBJECT-TYPE
	SYNTAX		INTEGER
	ACCESS		read-only
	STATUS		mandatory
	DESCRIPTION	"The total RAM (bytes) on the shelf controller."
	::= { chassisInfo 5 }

    chassisMemAvail	OBJECT-TYPE
	SYNTAX		INTEGER
	ACCESS		read-only
	STATUS		mandatory
	DESCRIPTION	"The RAM (bytes) currently available on the shelf controller."
	::= { chassisInfo 6 }

    chassisMemThreshold	OBJECT-TYPE
	SYNTAX		INTEGER
	ACCESS		read-only
	STATUS		mandatory
	DESCRIPTION	"The low water mark for RAM (bytes) on the shelf controller."
	::= { chassisInfo 7 }

        --
        -- Added in TAOS 8.0 for Stinger
        --

    cntrReduGroup OBJECT IDENTIFIER ::= { chassisInfo 8 }

    cntrReduSwitchLastTime	OBJECT-TYPE
	SYNTAX  TimeTicks
	ACCESS  read-only
	STATUS  mandatory
	DESCRIPTION
	    "The value of sysUpTime at the time the controller switched over,
	     0 if none after last system reboot."
	::= { cntrReduGroup 1 }
 
    cntrReduSwitchReason	OBJECT-TYPE
	SYNTAX  INTEGER {
	    unknown(1),
	    failure(2),
	    manual(3),
	    scheduled(4)
	}
	ACCESS  read-only
	STATUS  mandatory
	DESCRIPTION
	    "Reason for last controller switchover, unknown if no switchover
             has occurred."
	::= { cntrReduGroup 2 }

    cntrReduSwitchIndex 	OBJECT-TYPE
	SYNTAX  INTEGER
	ACCESS  read-only
	STATUS  mandatory
	DESCRIPTION
	    "Controller Index into slot-table for last controller 
             that was switched from."
	::= { cntrReduGroup 3 }

    cntrReduCurrentIndex	OBJECT-TYPE
	SYNTAX  INTEGER
	ACCESS  read-only
	STATUS  mandatory
	DESCRIPTION
	    "Current Controller Index into slot-table."
	::= { cntrReduGroup 4 }

    cntrReduAvailGroup OBJECT IDENTIFIER ::= { chassisInfo 9 }

    -- The redundancy transition group provides information on the
    -- availability of controller redundancy. This information is
    -- disjoined from the current primary/secondary selection as 
    -- provided by the cntrReduGroup.

    cntrReduAvailLastTime   OBJECT-TYPE
        SYNTAX  TimeTicks
        ACCESS  read-only
        STATUS  mandatory
        DESCRIPTION 
          "The last time the redundacy availabilty state changed. 
           This object reports 0 if the system did not yet transition
           from the boot stage."
        ::= { cntrReduAvailGroup 1 }

    --            ===> fullRedundancy (3)    <==========
    --           /       | change to/from fullRed.      |
    --          /        |                              | total loss/gain of 
    --  boot(2)======> partialRedundancy (4)            | redundancy
    --          \        | change to/from noRed         |
    --           \       |                              |
    --            ===> noRedundancy (5)      <==========

    CntrReduAvailState ::= INTEGER {
          other(1),             -- state cannot be determined
          boot(2),              -- the system is booting
          fullRedundancy(3),    -- redundant, communicating controller
          partialRedundancy(4), -- redundant controller with no communication
          noRedundancy(5)       -- single controller system
        }

    cntrReduAvailPrevState  OBJECT-TYPE
        SYNTAX  CntrReduAvailState
        ACCESS  read-only
        STATUS  mandatory
        DESCRIPTION 
          "The previous redundancy state. It's value is other before
           the first transition."
        ::= { cntrReduAvailGroup 2 }

    cntrReduAvailCurrState  OBJECT-TYPE
        SYNTAX  CntrReduAvailState
        ACCESS  read-only
        STATUS  mandatory
        DESCRIPTION 
          "The current redundancy state. It's value is boot before
           the first transition."
        ::= { cntrReduAvailGroup 3 }

    cntrReduAvailSlotIndex  OBJECT-TYPE
        SYNTAX  INTEGER
        ACCESS  read-only
        STATUS  mandatory
        DESCRIPTION 
          "The slotIndex as used in the slot table for the slot that
           observed the transition."
        ::= { cntrReduAvailGroup 4 }

	-- Ascend slot management group
	--
	-- This group contains the MIB variables used to determine the
	-- number of slots supported by the device and the type of slot
	-- card currently installed.

    slotNumber		OBJECT-TYPE
	SYNTAX		INTEGER
	ACCESS		read-only
	STATUS		mandatory
	DESCRIPTION	"The number of slots, fixed or removable, supported
			by this device."
	::= { slots 1 }


	-- The slot table
	--
	-- This table contains slotNumber entries describing each slot
	--

    slotTable		OBJECT-TYPE
	SYNTAX		SEQUENCE OF SlotEntry
	ACCESS		not-accessible
	STATUS		mandatory
	DESCRIPTION	"A list of slot entries.  The number of entries is
			given by the value slotNumber."
	::= { slots 2 }

    slotEntry		OBJECT-TYPE
	SYNTAX		SlotEntry
	ACCESS		not-accessible
	STATUS		mandatory
	DESCRIPTION	"A slot entry containing objects to describe the
			slot."
	INDEX		{ slotIndex }
	::= { slotTable 1 }

    SlotEntry ::=
	SEQUENCE {
	    slotIndex
		INTEGER,
	    slotName
		DisplayString,
	    slotType
		AscendSlotType,
	    slotFixed
		INTEGER,
	    slotItems
		INTEGER,
	    slotSpecific
		OBJECT IDENTIFIER,
	    slotSerialNumber
		INTEGER,
	    slotStatus
		INTEGER,
	    slotLastChange
		TimeTicks,
	    slotHWRev
		DisplayString,
	    slotSWRev
		DisplayString,
	    slotAdminStatus
		INTEGER,
	    slotUpTime
		TimeTicks,
	    slotMemoryTotal
		INTEGER,
	    slotMemoryAvail
		INTEGER,
	    slotMemoryThreshold
		INTEGER
	}

    slotIndex		OBJECT-TYPE
	SYNTAX		INTEGER
	ACCESS		read-only
	STATUS		mandatory
	DESCRIPTION	"A unique value for each slot card. Its value ranges
			between 1 and the value slotNumber."
	::= { slotEntry 1 }

   slotName		OBJECT-TYPE
	SYNTAX		DisplayString
	ACCESS		read-only
	STATUS		mandatory
	DESCRIPTION	"The ASCII representation of the name of the card
			in the indexed slot.  The name is the same name
			displayed on the Main Edit Menu less the menu
			number.	 The empty string is returned when there is no
			slot card present.  The value 'Not Avail' is used when
 			the card in the slot has failed POST. The value
                        'Occupied' is used for cards occupying more than
			one slot space."
	::= { slotEntry 2 }

    slotType		OBJECT-TYPE
	SYNTAX		AscendSlotType
	ACCESS		read-only
	STATUS		mandatory
	DESCRIPTION	"The type of card in the indexed slot."
	::= { slotEntry 3 }

    slotFixed		OBJECT-TYPE
	SYNTAX		INTEGER {
			    fixed( 1 ),
			    removable( 2 )
			}
	ACCESS		read-only
	STATUS		mandatory
	DESCRIPTION	"The value fixed( 1 ) returned if the slot card
			is not removable and removable( 2 ) if
			the slot card is removable."
	::= { slotEntry 4 }

    slotItems		OBJECT-TYPE
	SYNTAX		INTEGER
	ACCESS		read-only
	STATUS		mandatory
	DESCRIPTION	"A count of the number of 'items' contained by this
			slot card.  An 'item' is a 'port' for host and a
			'line' for network slot cards."
	::= { slotEntry 5 }

    slotSpecific	OBJECT-TYPE
	SYNTAX		OBJECT IDENTIFIER
	ACCESS		read-only
	STATUS		mandatory
	DESCRIPTION	"A reference to MIB definitions specific to the
			hardware in this slot card. Contains the object
			identifier { 0 0 } if there is no slot specific
			information for the current slot card type."
	::= { slotEntry 6 }

    slotSerialNumber	OBJECT-TYPE
	SYNTAX		INTEGER
	ACCESS		read-only
	STATUS		mandatory
	DESCRIPTION	"The TNT slot card's serial number.

			 The serial number is reported as 0 if the slot card
			 does not have a serial number, if the card did not
			 boot, or if the slot is empty.

			  The serial number is reported as 7777777 if the
			  slot card does not support serialization.

			 The serial number is reported as 0 for platforms
			 other than TNT."
	::= { slotEntry 7 }

    slotStatus	OBJECT-TYPE
	SYNTAX		INTEGER {
			    operStateDown( 1 ),
			    operStateUp( 2 ),
			    operStateDiag( 3 ),
			    operStateCoreDump( 4 ),
			    operStateLoading( 5 ),
			    operStatePost( 6 ),
			    operStateNone( 7 ),
                            operStateOccupied( 8 )
			}
	ACCESS		read-only
	STATUS		mandatory
	DESCRIPTION	"The current status of the TNT slot card
			 For non-TNT systems operStateNone is always reported."
	::= { slotEntry 8 }

    slotLastChange	OBJECT-TYPE
	SYNTAX		TimeTicks
	ACCESS		read-only
	STATUS		mandatory
	DESCRIPTION	"The value of sysUpTime at the time the TNT slot card
			 entered its current state.
			 For non-TNT systems 0 is always reported."
	::= { slotEntry 9 }

    slotHWRev           OBJECT-TYPE
        SYNTAX          DisplayString
        ACCESS          read-only
        STATUS          mandatory
        DESCRIPTION     "Hardware revision of the slot card.
                        On systems that do not support this object,
                        an empty string is returned."
        ::= { slotEntry 10 }

    slotSWRev           OBJECT-TYPE
        SYNTAX          DisplayString
        ACCESS          read-only
        STATUS          mandatory
        DESCRIPTION     "Software revision of the slot card.
                        On systems that do not support this object,
                        an empty string is returned."
        ::= { slotEntry 11 }

    slotAdminStatus	OBJECT-TYPE
	SYNTAX		INTEGER {
				  up(1),
				  down(2),
				  remove(3)
				}
	ACCESS		read-write
	STATUS		mandatory
	DESCRIPTION	"This attribute changes the state of the slot card
			 or deletes the slot card.
			 When read, returns the last admin. state set.
			 For non-TNT systems slotAdminStatusUp(1) always returned.
			 For non-TNT system this attribute can not be SET and
			 GENERAL_ERROR(5) is returned, if a SET-REQUEST is received."

	::= { slotEntry 12 }

    slotUpTime		OBJECT-TYPE
	SYNTAX		TimeTicks
	ACCESS		read-only
	STATUS		mandatory
	DESCRIPTION	"Time the slot card has been up.
			 If the slot card is not UP, returns 0."
	::= { slotEntry 13 }

    slotMemoryTotal	OBJECT-TYPE
	SYNTAX		INTEGER
	ACCESS		read-only
	STATUS		mandatory
	DESCRIPTION	"Total RAM(bytes) present on the slot card."
	::= { slotEntry 14 }

    slotMemoryAvail	OBJECT-TYPE
	SYNTAX		INTEGER
	ACCESS		read-only
        STATUS          mandatory
	DESCRIPTION	"The amount of RAM(bytes) currently available."
	::= { slotEntry 15 }

    slotMemoryThreshold	OBJECT-TYPE
	SYNTAX		INTEGER
	ACCESS		read-only
	STATUS		mandatory
	DESCRIPTION	"The RAM low water mark (bytes) for the slot card."
	::= { slotEntry 16 }


	-- slot item table
	--
	-- Each slot contains 1 or more 'items' that map to an interface
	-- number.  The slotItemTable defines the mapping between item
	-- number and interface.

    slotItemTable	OBJECT-TYPE
	SYNTAX		SEQUENCE OF SlotItemEntry
	ACCESS		not-accessible
	STATUS		mandatory
	DESCRIPTION	"A list of slot item entries.  Each slot contains
			slotItems entries, indexed by slotItemSlotIndex and
			by slotItemIndex"
	::= { slots 3 }

    slotItemEntry	OBJECT-TYPE
	SYNTAX		SlotItemEntry
	ACCESS		not-accessible
	STATUS		mandatory
	DESCRIPTION	"A slot entry containing the starting interface and
			number of interfaces used by the indexed slot/item."
	INDEX		{ slotItemSlotIndex, slotItemIndex }
	::= { slotItemTable 1 }


    SlotItemEntry ::=
	SEQUENCE {
	    slotItemSlotIndex
		INTEGER,
	    slotItemIndex
		INTEGER,
	    slotItemFirstIf
		INTEGER,
	    slotItemIfCount
		INTEGER,
	    slotItemSpecific
		OBJECT IDENTIFIER,
	    slotItemStatus
		INTEGER
	}

    slotItemSlotIndex	OBJECT-TYPE
	SYNTAX		INTEGER
	ACCESS		read-only
	STATUS		mandatory
	DESCRIPTION	"A unique value for each slot card.  The slot card
			identified by a particular value of this index
			is the same slot card as identified by the same value of
			slotIndex."
	::= { slotItemEntry 1 }

    slotItemIndex	OBJECT-TYPE
	SYNTAX		INTEGER
	ACCESS		read-only
	STATUS		mandatory
	DESCRIPTION	"A unique value for each item in each slot card.  Its
			value ranges between 1 and the value of slotItems
			in the slot indexed by the same value as
			slotItemSlotIndex."
	::= { slotItemEntry 2 }

    slotItemFirstIf	OBJECT-TYPE
	SYNTAX		INTEGER
	ACCESS		read-only
	STATUS		mandatory
	DESCRIPTION	"The interface number associated with the indexed
			item on the indexed slot.  May be set to 0 if the
			slot/item is not associated with any interface."
	::= { slotItemEntry 3 }

    slotItemIfCount	OBJECT-TYPE
	SYNTAX		INTEGER
	ACCESS		read-only
	STATUS		mandatory
	DESCRIPTION	"The number of interfaces associated with the
			indexed item on the indexed slot.  Typically set
			to 1 for host slots and the number of channels on
			network (WAN) slots.  May be set to 0 when the item
			is not associated with an interface."
	::= { slotItemEntry 4 }

    slotItemSpecific	OBJECT-TYPE
	SYNTAX		OBJECT IDENTIFIER
	ACCESS		read-only
	STATUS		mandatory
	DESCRIPTION	"A reference to MIB definitions specific to the
			indexed item on the indexed slot. Contains the
			object identifier { 0 0 } if there is no item
			specific information for the indexed item."
	::= { slotItemEntry 5 }

    slotItemStatus	OBJECT-TYPE
	SYNTAX		INTEGER {
			    statusOther( 1 ),
			    slotItemNotRunning( 2 ),
			    briLinkNotStuffed( 3 ),
			    briLinkDisabled( 4 ),
			    briDown( 5 ),
			    briNotInit( 6 ),
			    briNotInitWithL2( 7 ),
			    briPInit( 8 ),
			    briMInit( 9 )
			}
	ACCESS		read-only
	STATUS		mandatory
	DESCRIPTION	"The current status of this item in this slot card."
	::= { slotItemEntry 6 }


	-- The slot IF table
	--
	-- An interface to slot/item lookup table.  This table contains one
	-- entry per interface and the contents of the table are the slot
	-- and item associated with the index.	Items not related to a
	-- specific slot, e.g. console ports, are also mapped here.
	-- Note: multiple intefaces can point to the same slot/item.

    slotIfTable		OBJECT-TYPE
	SYNTAX		SEQUENCE OF SlotIfEntry
	ACCESS		not-accessible
	STATUS		mandatory
	DESCRIPTION	"A list of interfaces and the slot/item entry that
			the interface is associated with."
	::= { slots 4 }

    slotIfEntry		OBJECT-TYPE
	SYNTAX		SlotIfEntry
	ACCESS		not-accessible
	STATUS		mandatory
	DESCRIPTION	"A slot interface entry containing the slot and item
			that the interface is associated with."
	INDEX		{ slotIfIndex }
	::= { slotIfTable 1 }

    SlotIfEntry ::=
	SEQUENCE {
	    slotIfIndex
		INTEGER,
	    slotIfSlotIndex
		INTEGER,
	    slotIfItemIndex
		INTEGER
	}

    slotIfIndex		OBJECT-TYPE
	SYNTAX		INTEGER
	ACCESS		read-only
	STATUS		mandatory
	DESCRIPTION	"The interface index, ranging from 1 to the number
			of interfaces specified in the MIB-II variable
			ifNumber. The interface identified by a particular
			value of this index is the same interface as
			identified by the same value of ifIndex."
	::= { slotIfEntry 1 }

    slotIfSlotIndex		OBJECT-TYPE
	SYNTAX		INTEGER
	ACCESS		read-only
	STATUS		mandatory
	DESCRIPTION	"The slot index, ranging from 0 to the number
			of slots specified in slotNumber.  When zero the
			interface references an item in the console group
			of this MIB.  Otherwise the slot identified by a
			particular value of this index is the same slot as
			identified by the same value of slotIndex."
	::= { slotIfEntry 2 }

    slotIfItemIndex	OBJECT-TYPE
	SYNTAX		INTEGER
	ACCESS		read-only
	STATUS		mandatory
	DESCRIPTION	"The item index, ranging from 1 to the number
			of items supported on the slot indicated by
			slotIfSlotIndex.  When slotIfSlotIndex is non-zero
			the number of items supported is specified in
			slotItems for the slot entry index by slotIfSlotIndex.
			The item identified by a particular value of this
			index is the same item as identified by the same
			value of  slotItemIndex."
	::= { slotIfEntry 3 }


END
