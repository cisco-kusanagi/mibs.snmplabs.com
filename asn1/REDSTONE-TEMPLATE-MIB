-- *****************************************************************
-- REDSTONE-TEMPLATE-MIB
--
-- Redstone Communications Inc. Enterprise MIB
-- Template MIB
--
-- Copyright 1999 Unisphere Solutions Inc.
-- All Rights Reserved.
-- *****************************************************************

REDSTONE-TEMPLATE-MIB DEFINITIONS ::= BEGIN

IMPORTS
    MODULE-IDENTITY, 
    OBJECT-TYPE,
    Unsigned32
        FROM SNMPv2-SMI

    DisplayString,
    RowStatus
        FROM SNMPv2-TC

    MODULE-COMPLIANCE, 
    OBJECT-GROUP  
        FROM SNMPv2-CONF

    rsMgmt
		FROM REDSTONE-SMI;


rsTemplateMIB MODULE-IDENTITY
    LAST-UPDATED "9908170000Z"
    ORGANIZATION "Redstone Communications Inc."
	CONTACT-INFO
        "
        Redstone Communications, Inc.
		5 Carlisle Road
        Westford MA 01886
        USA
        Tel:    +1-978-692-1999
		Email:  mib@redstonecom.com
        "
	DESCRIPTION
		"The Template MIB for the
		Redstone Communications Inc. enterprise."
	REVISION      "9906010000Z"
	DESCRIPTION
		"Initial version of this MIB module."
    ::= { rsMgmt 25 }


-- ++++++++++++++++++++++++++++++++++++++++++++++++++++++++++++++++++++++
-- Textual conventions
-- ++++++++++++++++++++++++++++++++++++++++++++++++++++++++++++++++++++++

-- No textual conventions are currently defined.


-- ++++++++++++++++++++++++++++++++++++++++++++++++++++++++++++++++++++++
-- Managed object groups
-- ++++++++++++++++++++++++++++++++++++++++++++++++++++++++++++++++++++++

rsTemplateObjects                OBJECT IDENTIFIER ::= {rsTemplateMIB 1}

-- Functional groups

rsTemplateName                   OBJECT IDENTIFIER ::= {rsTemplateObjects 1}

-- ++++++++++++++++++++++++++++++++++++++++++++++++++++++++++++++++++++++
-- Managed objects for Template Names
-- ++++++++++++++++++++++++++++++++++++++++++++++++++++++++++++++++++++++

rsTemplateNameTable OBJECT-TYPE
    SYNTAX      SEQUENCE OF RsTemplateNameEntry
    MAX-ACCESS  not-accessible
    STATUS      current
    DESCRIPTION
        "The entries in this table provide mappings of configuration template 
        names to local integer identifiers for those templates. These integers
        are used as indexes into other MIB tables containing template configuration
        parameters associated with the same template name."
    ::= { rsTemplateName 1 }

rsTemplateNameEntry OBJECT-TYPE
    SYNTAX      RsTemplateNameEntry
    MAX-ACCESS  not-accessible
    STATUS      current
    DESCRIPTION
        "A mapping of a template name to an integer identifier for that name."
    INDEX { IMPLIED rsTemplateNameName }
    ::= { rsTemplateNameTable 1 }

RsTemplateNameEntry ::= SEQUENCE {
    rsTemplateNameName               DisplayString,
    rsTemplateNameRowStatus          RowStatus,
    rsTemplateNameId                 Unsigned32
}

rsTemplateNameName OBJECT-TYPE
    SYNTAX      DisplayString(SIZE(1..80))
    MAX-ACCESS  read-only
    STATUS      current
    DESCRIPTION
        "The template name uniquely identifying this entry."
    ::= { rsTemplateNameEntry 1 }

rsTemplateNameRowStatus OBJECT-TYPE
    SYNTAX      RowStatus
    MAX-ACCESS  read-create
    STATUS      current
    DESCRIPTION
        "Controls creation/deletion of entries in this table.
        Only the values 'createAndGo' and 'destroy' may be SET."
    ::= { rsTemplateNameEntry 2 }

rsTemplateNameId OBJECT-TYPE
    SYNTAX      Unsigned32
    MAX-ACCESS  read-only
    STATUS      current
    DESCRIPTION
        "The integer identifier associated with this template name.

        This value of this identifier is assigned by the device when 
        an entry in this table is created."
    ::= { rsTemplateNameEntry 3 }


rsTemplateIdTable OBJECT-TYPE
    SYNTAX      SEQUENCE OF RsTemplateIdEntry
    MAX-ACCESS  not-accessible
    STATUS      current
    DESCRIPTION
        "Provides inverse mapping of template IDs to template names."
    ::= { rsTemplateName 2 }

rsTemplateIdEntry OBJECT-TYPE
    SYNTAX      RsTemplateIdEntry
    MAX-ACCESS  not-accessible
    STATUS      current
    DESCRIPTION
        "A mapping of an integer identifier to a template name."
    INDEX { rsTemplateIdId }
    ::= { rsTemplateIdTable 1 }

RsTemplateIdEntry ::= SEQUENCE {
    rsTemplateIdId                  Unsigned32,
    rsTemplateIdName                DisplayString
}

rsTemplateIdId OBJECT-TYPE
    SYNTAX      Unsigned32
    MAX-ACCESS  not-accessible
    STATUS      current
    DESCRIPTION
        "The integer identifier associated with this template name."
    ::= { rsTemplateIdEntry 1 }

rsTemplateIdName OBJECT-TYPE
    SYNTAX      DisplayString(SIZE(1..80))
    MAX-ACCESS  read-only
    STATUS      current
    DESCRIPTION
        "The template name having the associated identifier."
    ::= { rsTemplateIdEntry 2 }



-- ++++++++++++++++++++++++++++++++++++++++++++++++++++++++++++++++++++++
-- Notification control objects
-- ++++++++++++++++++++++++++++++++++++++++++++++++++++++++++++++++++++++

-- No notifications are defined in this MIB. Placeholder follows.

-- rsTemplateTrapControl      OBJECT IDENTIFIER ::= { rsTemplateMIB 2 }



-- ++++++++++++++++++++++++++++++++++++++++++++++++++++++++++++++++++++++
-- Notifications
-- ++++++++++++++++++++++++++++++++++++++++++++++++++++++++++++++++++++++

-- No notifications are defined in this MIB. Placeholder follows.

-- The following two OBJECT IDENTIFIERS are used to define SNMPv2 
-- Notifications that are easily translated into SNMPv1 Traps.

-- rsTemplateTraps            OBJECT IDENTIFIER ::= { rsTemplateMIB 3 }
-- rsTemplateTrapPrefix       OBJECT IDENTIFIER ::= { rsTemplateTraps 0 }



-- ++++++++++++++++++++++++++++++++++++++++++++++++++++++++++++++++++++++
-- Conformance information
-- ++++++++++++++++++++++++++++++++++++++++++++++++++++++++++++++++++++++

rsTemplateMIBConformance
             OBJECT IDENTIFIER ::= { rsTemplateMIB 4 }
rsTemplateMIBCompliances
             OBJECT IDENTIFIER ::= { rsTemplateMIBConformance 1 }
rsTemplateMIBGroups
             OBJECT IDENTIFIER ::= { rsTemplateMIBConformance 2 }


-- compliance statements

rsTemplateCompliance MODULE-COMPLIANCE
    STATUS      current
    DESCRIPTION
        "The compliance statement for systems supporting naming of 
        configuration templates."
    MODULE  -- this module
    MANDATORY-GROUPS { rsTemplateGroup }
    ::= { rsTemplateMIBCompliances 1 }


-- units of conformance

rsTemplateGroup OBJECT-GROUP
    OBJECTS {
        rsTemplateNameName,
        rsTemplateNameRowStatus,
        rsTemplateNameId,

        rsTemplateIdName
    }
    STATUS      current
    DESCRIPTION
        "The basic collection of objects providing management
        of Template naming functionality in a Redstone product."
    ::= { rsTemplateMIBGroups 1 }

END
