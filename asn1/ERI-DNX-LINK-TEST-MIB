ERI-DNX-LINK-TEST-MIB DEFINITIONS ::= BEGIN

IMPORTS
	MODULE-IDENTITY, OBJECT-IDENTITY, OBJECT-TYPE, Integer32,
	Counter32, Unsigned32, IpAddress
		FROM SNMPv2-SMI
    DisplayString, TEXTUAL-CONVENTION
        FROM SNMPv2-TC
    eriMibs
        FROM ERI-ROOT-SMI
    LinkPortAddress, dnx, DataSwitch, DecisionType, 
    OneByteField
        FROM ERI-DNX-SMC-MIB;

eriDNXLinkTestMIB MODULE-IDENTITY 
      LAST-UPDATED    "200307160000Z"
      ORGANIZATION    "Eastern Research, Inc."
      CONTACT-INFO
                      "Customer Service
                Postal: Eastern Research, Inc.
                        225 Executive Drive
                        Moorestown, NJ 08057
                Phone:  +1-800-337-4374
                Email:  support@erinc.com"
      DESCRIPTION
              "The ERI Enterprise MIB Module for the DNX DSx1 links and HS ports."

      REVISION        "200307160000Z"   -- July 16, 2003
      DESCRIPTION
              "Nevio Poljak - eri_DnxRoot MIB Rev 02.2
               Added new error code 211 to dsx1TestCmdStatus & dsx1StatusCmdStatus 
               lists per Bug #6439. Added extra error injection modes to dsx1StatusInsErrMode 
               per Bug #6438. Converted history comments to MODULE-IDENTITY REVISION format."

      REVISION        "200204080000Z"   -- April 8, 2002
      DESCRIPTION
              "Nevio Poljak - - Software Release 14.2
               Converted to SMIv2 format. Removed all unframed BERT patterns from 
               the dsx1Test Table and added 2 new BERTS: framed-3-in-24(69) & 
               framed-1-in-8(85)."

      REVISION        "200201300000Z"   -- January 30, 2002
      DESCRIPTION
              "Nevio Poljak - - Software Release 14.1
               Modified the Test Table to handle the User Defined, SmartJack, 
               and Remote Loops."

      REVISION        "200112140000Z"   -- December 14, 2001
      DESCRIPTION
              "Nevio Poljak - - Software Release 14.1
               Added E1 National bits Receive field to the Status Table.
               Added new Bert types for Optical links (STM1/OC3)."

      REVISION        "200110160000Z"   -- October 16, 2001
      DESCRIPTION
              "Nevio Poljak - - Software Release 13.0
               Added Remote Line loop as read-only loop to the Test Table 
               Added New DSX1 Link Status Table and modified multiple errors
               in Link state field."

      REVISION        "200108170000Z"   -- August 17, 2001
      DESCRIPTION
              "Nevio Poljak - - Software Release 12.4
               Modified Test Table Error codes and Insert Error Modes."

      REVISION        "200107180000Z"   -- July 18, 2001
      DESCRIPTION
              "Nevio Poljak - - Software Release 12.2
               Modified Test Table to provide Insert Error command."

      REVISION        "200106180000Z"   -- June 18, 2001
      DESCRIPTION
              "Nevio Poljak - - Software Release 12.0
               Modified Test Table to provide ClearErrs command and
               added All-Line and All-Local loops."

      REVISION        "200105220000Z"   -- May 22, 2001
      DESCRIPTION
              "Nevio Poljak - - Software Release 11.1
               Updated High Speed Link Test Table with DDN Stats."

      REVISION        "200103010000Z"   -- March 1, 2001
      DESCRIPTION
              "Nevio Poljak - - Software Release 11.0
               Added High Speed Link Test Table."

      REVISION        "200012280000Z"   -- December 28, 2000
      DESCRIPTION
              "Nevio Poljak - Software Release 10.0
               Initial Release of this MIB module."

  	::= { eriMibs 8 }

-- *************************************************************************
-- The enterprise OID will be { iso(1) org(3) dod(6) internet(1) private(4)
--                              enterprises(1) virent(644) eri(2) dnx (4) 
--								diagnostics (5) }
-- *************************************************************************
diagnostics OBJECT IDENTIFIER 	::= { dnx 5 }

dsx1Test 	OBJECT IDENTIFIER 	::= { diagnostics 1 }

-- *************************************************************************
-- The DNX Link Test Statistics are currently provided in 1 table. 
-- The Link Test Statistics Table will provide Loop and Test data for all 
-- applicable DS1/E1 links in the system. 

-- *************************************************************************
-- This table is the DS1/E1 Link Test Statistics table

UserDefFormat ::= TEXTUAL-CONVENTION
		STATUS  current
        DESCRIPTION
                "Used for the user defined loop format."
	    SYNTAX IpAddress 

dsx1TestTable OBJECT-TYPE
        SYNTAX SEQUENCE OF DSx1TestEntry
        MAX-ACCESS not-accessible
        STATUS current
        DESCRIPTION
            "This is the DS1/E1 Bit Error Test Statistics table which consists
            of an entry for each DS1/E1 port in the system.  This table 
            provides the total counters accumulated since the test has 
            been on or since the last time the counts were cleared. The
            counters are calculated in accordance with the ITU-T G.821 
            Error performance events and parameters, August 1996."
        ::= { dsx1Test 1 }

dsx1TestEntry OBJECT-TYPE
        SYNTAX DSx1TestEntry
        MAX-ACCESS not-accessible
        STATUS current
        DESCRIPTION
            "The conceptual row of the DS1/E1 Bit Error Test Statistics table. 
            A row in this table cannot be added or deleted but the
            counter time period can be reset to zero."
        INDEX { dsx1TestLinkAddr }
        ::= { dsx1TestTable 1 }

DSx1TestEntry ::=
        SEQUENCE {
                dsx1TestLinkAddr        LinkPortAddress,
                dsx1TestResrcId  		Integer32,
                dsx1TestLinkState		INTEGER,
                dsx1TestLinkLoop		INTEGER,      	-- RW
                dsx1TestBackplnLoop		INTEGER,        -- RW
                dsx1TestBertState		INTEGER,        -- RW
                dsx1TestDuration		Integer32,
                dsx1TestBitErrs		    Unsigned32,
                dsx1TestESs				Counter32,
                dsx1TestRemoteESs		Counter32,
                dsx1TestErrFreeSecs		Counter32,
                dsx1TestSESs	        Counter32,
                dsx1TestUASs     	    Counter32,
                dsx1TestASs			    Counter32,
                dsx1TestESNonUASs	    Counter32,
                dsx1TestSevereError		Integer32,      -- RW
                dsx1TestBitSpeed		Integer32,
                dsx1TestCmdStatus		INTEGER,        -- RW              
                dsx1TestInsErrMode      INTEGER,        -- RW 
                dsx1TestUsrLoopUnframed INTEGER,        -- RW
                dsx1TestUsrDefLoop      UserDefFormat   -- RW
                }

dsx1TestLinkAddr OBJECT-TYPE
        SYNTAX LinkPortAddress
        MAX-ACCESS read-only
        STATUS current
        DESCRIPTION
            "This number uniquely identifies an DS1/E1 link resource. 
            This number will be used throughout the system to identify 
            a unique link. The format is represented using an IP address 
            syntax (4 byte string). Note that the maximum valid link 
            number will vary depending on the specified carrier and framing 
            options. For example, an octal T1/E1 device has 8 DS1 links but the 
            DS3 has 28 DS1 links.
            
               The 1st byte is reserved for future Nest Number use
               The 2nd byte represents the Slot Number (1-11)            
               The 3rd byte represents the Link Number (1-32)
               The 4th byte is reserved for future use           
            "
        ::= { dsx1TestEntry 1 }

dsx1TestResrcId OBJECT-TYPE
        SYNTAX Integer32
        MAX-ACCESS read-only
        STATUS current
        DESCRIPTION
            "Uniquely identifies a link in the system.
             This number is provided as key to allow the manager to 
             map this entry to a corresponding Resource Table entry."
        ::= { dsx1TestEntry 2 }

dsx1TestLinkState OBJECT-TYPE
        SYNTAX INTEGER {
        	ok  (0),
        	yel (2),              -- bit 1
        	ais (8),              -- bit 3
        	lof (32),             -- bit 5
        	los (64),             -- bit 6
        	red (2048),           -- bit 11
        	cfa (4096),           -- bit 12
        	oos (65535),          -- all bits
        	txSlip (2097152),     -- bit 21
        	rxSlip (4194304),     -- bit 22
        	slip (6291456),       -- bits 21,22
        	sef (8388608),        -- bit 23
        	underTest(1073741824),-- bit 30
        	errors(2147483647)    -- all
        	}
        MAX-ACCESS read-only
        STATUS current
        DESCRIPTION
           "Determines the current line condition status of the link.
           In order to turn on a loop, the link must be configured In Service.
        	ok       (0)          - In Sync
        	yel      (2)          - Yellow Alarm
        	ais      (8)          - Sending All Ones
        	lof      (32)         - Loss of Frame
        	los      (64)         - Loss of Signal
        	red      (2048)       - Red Alarm
        	cfa      (4096)       - Carrier Frame Alignment
        	oos      (65535)	  - Out of Service
        	txSlip   (2097152)    - Transmit Slip
        	rxSlip   (4194304)    - Receive Slip
        	slip     (6291456)    - Transmit/Receive Slip
        	sef      (8388608)    - Severely Errored Frames
        	underTest(1073741824) - Running Bit Error Test (BERT) 
        	errors   (2147483647) - Multiple Errors displays raw bit field value
           "
       ::= { dsx1TestEntry 3 }

dsx1TestLinkLoop OBJECT-TYPE
        SYNTAX INTEGER {
        	off (0),
        	local (1),
        	remote (2),
        	line (3),
        	payload (4),
        	analog (5),       -- only applies to Octal T1/E1 links
        	smartjack (6),    -- only applies to Octal T1/E1 links
        	remoteLine(7),
        	user-defined (8), -- only applies to T1 links on Octal,HDS3, STS1
        	allLocal (12),    -- only applies to HDS3 links
        	allLine (16),     -- only applies to HDS3 links
        	loopUpReq (74),
        	loopDwnReq (75)
        	}
        MAX-ACCESS read-write
        STATUS current
        DESCRIPTION
           "Determines the status of the line loopback associated with this link.
           In order to turn on a loop, the link must be configured In Service.
            off        (0)	- indicates loopback is disabled
        	local      (1)	- indicates local data is looped back to itself
        	remote     (2)  - indicates data is looped back from remote to local
        	                  not applicable to links configured for Clear mode
        	line       (3)  - entire Frame is looped, framing is not regenerated
        	payload    (4)  - only payload data is looped, framing is regenerated
        	                  not applicable to links configured for Clear mode
        	analog     (5)  - LIU is looped back
        	remoteLine (7)  - Remote Line (network) loop indicator, CANNOT be used in SET.
        	smartjack  (6)  - special remote loop for 'smartjack' devices
        	                  not applicable to links configured for Clear mode
      	    user-defined (8)  - user defined loop applicable for T1 links.                  
         	allLocal   (12) - places all links are in local loop
        	allLine    (16) - places all links are in line loop
        	loopUpReq  (74) - Remote loop status indicator, CANNOT be used in SET.
        	loopDwnReq (75) - Remote loop status indicator, CANNOT be used in SET."
       ::= { dsx1TestEntry 4 }

dsx1TestBackplnLoop OBJECT-TYPE
        SYNTAX INTEGER {
        	loopOffBackplane (20),
        	loopBackplane (21)
            }
        MAX-ACCESS read-write
        STATUS current
        DESCRIPTION
           "Determines whether or not the link has connection loopback 
           via the Backplane.  This affects a data connection which must 
           already be in place prior to invoking this function."
       ::= { dsx1TestEntry 5 }

dsx1TestBertState OBJECT-TYPE
        SYNTAX INTEGER {
        	bertOff (50),
            all-ones (51),         
            all-zeros (52),        
--            unframed-2047 (53),
--            unframed-2-15th (54),
--            unframed-2-20th (55),
--            unframed-2-23rd (56),
--            unframed-2-11th-with7zeros (57),
--            unframed-2-15th-with7zeros (58),
--            unframed-QRSS (59),
--            unframed-2-23rd-with14zeros (60),
            framed-2047 (61),
            framed-2-15th (62),
            framed-2-20th (63),
            framed-2-23rd (64),
            framed-2-11th-with7zeros (65),
            framed-2-15th-with7zeros (66),
            framed-QRSS (67),
            framed-2-23rd-with14zeros (68),
            framed-3-in-24 (69),
            all-2047 (70),        	            -- only applies to HDS3 links
            system-2047 (71),                   -- only applies to HDS3 links
            system-framed-2-15th-invert (80),   -- only applies to Optical links     
            system-framed-2047 (81),            -- only applies to Optical links
            system-framed-2-15 (82),            -- only applies to Optical links
            system-framed-2-20 (83),            -- only applies to Optical links
            system-framed-QRSS (84),            -- only applies to Optical links
            framed-1-in-8 (85),
            framed-2-15th-invert (86)           -- only applies to Optical links
           }
        MAX-ACCESS read-write
        STATUS current
        DESCRIPTION
            "This indicates the current BERT test running and can be used to
            start and stop a desired Test Period. In order to turn on a loop, 
            the link must be configured In Service.  As of release 14.2, all
            unframed bert patterns are no longer supported."
        ::= { dsx1TestEntry 6 }

dsx1TestDuration OBJECT-TYPE
        SYNTAX Integer32
        MAX-ACCESS read-only
        STATUS current
        DESCRIPTION
            "This the total number of seconds the test data has been collected."
        ::= { dsx1TestEntry 7 }

dsx1TestBitErrs OBJECT-TYPE
        SYNTAX Unsigned32(0..4294967295)
        MAX-ACCESS read-only
        STATUS current
        DESCRIPTION
            "This is the total number of bits in error since the Test has
            been running."
        ::= { dsx1TestEntry 8 } 
        
dsx1TestESs OBJECT-TYPE
        SYNTAX Counter32
        MAX-ACCESS read-only
        STATUS current
        DESCRIPTION
            "This is the total number of errored seconds that have
            occurred on the local link since the Test has been turned on.
            
            This Errored Second is defined as a one second period in which 
            one or more bits are in error."
        ::= { dsx1TestEntry 9 }

dsx1TestRemoteESs OBJECT-TYPE
        SYNTAX Counter32
        MAX-ACCESS read-only
        STATUS current
        DESCRIPTION
            "This is the total number of errored seconds that have
            occurred on the remote link since the Test has been turned on.
            This only applies to bi-directional Berts which are not supported
            on the Octal T1/E1 device.
            
            This Errored Second is defined as a one second period in which 
            one or more bits are in error."
        ::= { dsx1TestEntry 10 }

dsx1TestErrFreeSecs OBJECT-TYPE
        SYNTAX Counter32
        MAX-ACCESS read-only
        STATUS current
        DESCRIPTION
            "This is the total number of error free seconds since the
             Test has been running."
        ::= { dsx1TestEntry 11 }
        
dsx1TestSESs OBJECT-TYPE
        SYNTAX Counter32
        MAX-ACCESS read-only
        STATUS current
        DESCRIPTION
            "This is the total number of severely errored seconds that have
            occurred since the Test has been running.
            
            This Severely Errored Second is defined as a one second period that
            contains bit errors equal to or greater than the Severe Error field."
        ::= { dsx1TestEntry 12 }

dsx1TestUASs OBJECT-TYPE
        SYNTAX Counter32
        MAX-ACCESS read-only
        STATUS current
        DESCRIPTION
            "This is the number of Unavailable Seconds (UAS) that have occurred 
            since the Test has been running.
            
            The UAS is a period of time consisting of 10 or more consecutive ESs."
        ::= { dsx1TestEntry 13 }

dsx1TestASs OBJECT-TYPE
        SYNTAX Counter32
        MAX-ACCESS read-only
        STATUS current
        DESCRIPTION
            "This is the number of Available Seconds (AS) that have occurred 
            since the Test has been running.
            
            The AS is the Test duration seconds minus the UAS."
        ::= { dsx1TestEntry 14 }

dsx1TestESNonUASs OBJECT-TYPE
        SYNTAX Counter32
        MAX-ACCESS read-only
        STATUS current
        DESCRIPTION
            "This is the number of Error Seconds (ES) which are not part of
            the UAS that occurred since the Test has been running."
        ::= { dsx1TestEntry 15 }

dsx1TestSevereError OBJECT-TYPE
        SYNTAX Integer32 (1..65535)
        MAX-ACCESS read-write
        STATUS current
        DESCRIPTION
            "This is the number of bits in error in a given second that determine a 
            severely errored second."
        ::= { dsx1TestEntry 16 } 
        
dsx1TestBitSpeed OBJECT-TYPE
        SYNTAX Integer32
        MAX-ACCESS read-only
        STATUS current
        DESCRIPTION
            "This is the current bit rate at which the link is configured for."
        ::= { dsx1TestEntry 17 }

dsx1TestCmdStatus OBJECT-TYPE
        SYNTAX INTEGER {
    -- Initial default status for a row
            ready-for-command (0),
    -- Action States used in SET Command (1..99)
            updateTest (1),
            clearErrors (14),
            insertError (16),
                		
    -- Response States used in GET RESPONSE Command (100..199)
            update-successful (101),
            clear-successful (114),
            insert-successful (116),
                		
    -- Test Error Codes used in GET RESPONSE Command (200..799)
            err-general-test-error (200),
            err-link-not-in-service (201),
            err-invalid-loop-type (202),
            err-invalid-bert-type (203),
            err-link-in-clear-mode (204),
            err-test-in-progress (205),
            err-field-cannot-be-set (206),
            err-link-not-connected (207),
            err-invalid-command (208),
            err-invalid-user-defined-loop (209), 
            err-link-in-E1-mode (210),
            err-link-not-in-test (211),
            err-snmp-parse-failed(500),
            err-invalid-snmp-type(501),
            err-invalid-snmp-var-size(502) 
            }
        MAX-ACCESS read-write
        STATUS current
        DESCRIPTION
            "This is the command status for the DS1/E1 Link Test Row.
           The value used in a SET will be replaced by a response
           value in the GET RESPONSE indicating success or failure.

            Default Response State used in GET RESPONSE Command
                ready-for-command (0)
                    initial default status for a row           
                    
            DS1/E1 Action Commands used in SET Command (1..99)            
                updateTest (1)
                    Can be used optionally when activating loops and berts
                    in order to get status code back in response
                clearErrors (14)
                    Resets all error counters and bert test time to zero
                insertError (16)
                    Inserts the current invalid bit pattern as indicated
                    by the value of dsx1TestInsErrMode. 
                		
            Response States used in GET RESPONSE Command (100..199)
                update-successful (101)
                    Test action has been successfully performed
                clear-successful (114)
                    Error counts have been successfully cleared
                insert-successful (116)
                    Errored bits have been successfully inserted
                		
            DS1/E1 Test Error Codes used in GET RESPONSE Command (200..799)
                err-general-test-error (200)
                    Unknown Test request error occurred.
                err-link-not-in-service (201)
                    Requested action cannot be performed for OOS links                
                err-invalid-loop-type (202)
                    Unrecognized loop selection
                err-invalid-bert-type (203)
                    Unrecognized bert selection
                err-link-in-clear-mode (204)
                    Requested action cannot be performed for clear framed
                    or clear unframed configured links               
                err-test-in-progress (205)
                    Requested action cannot be performed during bert
                err-field-cannot-be-set (206)
                    Read-only field was included in SET request
                err-link-not-connected (207)
                    Requested action cannot be performed without link connection
                err-invalid-command (208)
                    Unrecognized Test Command requested                    
                err-invalid-user-defined-loop (209), 
          			The field specifying the Activate and Deactivate values is invalid.	  		
            	err-link-in-E1-mode (210),
            	    Must be in set in T1 mode for User Defined loops.
                err-link-not-in-test (211)
                    Requested action cannot be performed without a bert
            	err-snmp-parse-failed (500)
                    Agent could not parse variable
                err-invalid-snmp-type (501)
                    Variable ASN type does not match Agent defined type 
                err-invalid-snmp-var-size (502)
                    Variable size is too big" 
        ::= { dsx1TestEntry 18 } 
        
dsx1TestInsErrMode OBJECT-TYPE
        SYNTAX INTEGER {
            not-applicable (0),
        	cas-multiframe (1),
        	multiframe (2),
        	bert-error (3),
        	bit-slip (4),    
        	frame-alignment (5),
        	crc (6),     
        	fbit (7),
        	line-code-violation (8),    
        	allErrors (9),
        	yellow-alarm (10),
        	ybit (11),
        	fas-inverted (12),
        	nfas-bit2-inverted (13),
        	rai (14),
        	ts16-ais (15),
        	ais-unframed-all-ones (16)
        	}
        MAX-ACCESS read-write
        STATUS current
        DESCRIPTION
           "Determines the status of the current Insert Error mode associated 
           with this link. In order to insert an error, the dsx1TestCmdStatus 
           must be sent in a SET PDU with a value of 'insertError'."
       ::= { dsx1TestEntry 19 } 

dsx1TestUsrLoopUnframed OBJECT-TYPE
        SYNTAX DecisionType
		MAX-ACCESS read-write
        STATUS current
        DESCRIPTION
           " This specifies the type of framing to use during User Defined remote loops.
              no  (0) - Loop data will be framed.
              yes (1) - Loop data will be unframed. This is the default."           
       ::= { dsx1TestEntry 20 } 

dsx1TestUsrDefLoop OBJECT-TYPE
        SYNTAX UserDefFormat 
        MAX-ACCESS read-write
        STATUS current
        DESCRIPTION
          " The user defined loop provides the length and value options for activating 
            as well as deactivating the loop. The format is represented using an IP address 
            syntax (4 byte string). 
            
               The 1st byte signifies the Activate loop code bit length (4-7)
               The 2nd byte represents the Activate loop code value (0-255)            
               The 3rd byte signifies the Deactivate loop code bit length (4-7) 
               The 4th byte represents the Deactivate loop code value (0-255)           

            The default Loop format is 5.8.6.36: 
               Activate  : 5 bits (length)   00001000 (decimal value = 8)
               Deactivate: 6 bits (length)   00100100 (decimal value = 36)            
            
            Notes: - Loop code uses 4,5,6 or 7 high order bits of the code value.
                   - Bit 7 is transmitted first.
                   - Unframed code overwrites the framing bits.
          "                       
       ::= { dsx1TestEntry 21 } 
        
-- *************************************************************************
-- This table is the High Speed Link Test Statistics table

hsTest 	    OBJECT IDENTIFIER 	::= { diagnostics 2 }

hsTestTable OBJECT-TYPE
        SYNTAX SEQUENCE OF HSTestEntry
        MAX-ACCESS not-accessible
        STATUS current
        DESCRIPTION
            "This is the High Speed Bit Error Test Statistics table which consists
            of an entry for each High Speed port in the system.  This table 
            provides the total counters accumulated since the test has 
            been running or since the last time the counts were cleared."
        ::= { hsTest 1 }

hsTestEntry OBJECT-TYPE
        SYNTAX HSTestEntry
        MAX-ACCESS not-accessible
        STATUS current
        DESCRIPTION
            "The conceptual row of the High Speed Bit Error Test Statistics table. 
            A row in this table cannot be added or deleted but can be modified."
        INDEX { hsTestLinkAddr }
        ::= { hsTestTable 1 }

HSTestEntry ::=
        SEQUENCE {
                hsTestLinkAddr      LinkPortAddress,
                hsTestResrcId  	    Integer32,
                hsTestLinkState	    INTEGER,
                hsTestLocalLoop	    INTEGER,      	-- RW
                hsTestRemoteLoop    INTEGER,      	-- RW
                hsTestBackplnLoop   INTEGER,        -- RW
                hsTestBertState	    INTEGER,        -- RW
                hsTestDuration	    Integer32,
                hsTestLocESs        Counter32,
                hsTestRemESs        Counter32,
                hsTestBitSpeed	    Integer32,
                hsTestCmdStatus	    INTEGER,        -- RW
          -- additional DDN Statistics for the Network Link data     
                hsTestLocEFSs       Counter32,
                hsTestLocUASs       Counter32,
                hsTestLocASs        Counter32,
                hsTestLocESNonUASs  Counter32,
          -- additional DDN Statistics for the Bus data                                    
                hsTestRemEFSs       Counter32,
                hsTestRemUASs       Counter32,
                hsTestRemASs        Counter32,
                hsTestRemESNonUASs  Counter32               
                }

hsTestLinkAddr OBJECT-TYPE
        SYNTAX LinkPortAddress
        MAX-ACCESS read-only
        STATUS current
        DESCRIPTION
            "This number uniquely identifies an High Speed link resource. 
            This number will be used throughout the system to identify 
            a unique link. The format is represented using an IP address 
            syntax (4 byte string).
            
               The 1st byte is reserved for future Nest Number use
               The 2nd byte represents the Slot Number (1-11)            
               The 3rd byte represents the Link Number (1-8)
               The 4th byte is reserved for future use           
            "
        ::= { hsTestEntry 1 }

hsTestResrcId OBJECT-TYPE
        SYNTAX Integer32
        MAX-ACCESS read-only
        STATUS current
        DESCRIPTION
            "Uniquely identifies a link in the system.
             This number is provided as key to allow the manager to 
             map this entry to a corresponding Resource Table entry."
        ::= { hsTestEntry 2 }

hsTestLinkState OBJECT-TYPE
        SYNTAX INTEGER {
        	ok  (0),
        	rxFifo (2),         -- bit 1
        	txFifo (4),			-- bit 2
        	fifo (6),           -- bits 1 & 2
        	clkEdgeErr (8),     -- bit 3
        	carrierDrop (16),	-- bit 4
            noConn (255),
        	oos (65535)         
        	}
        MAX-ACCESS read-only
        STATUS current
        DESCRIPTION
           "Determines the current line condition status of the link.
           In order to turn on a loop, the link must be configured In Service
           with a Connection.
        	ok         (0)       - In Sync
        	rxFifo     (2)       - Receive FIFO Err
        	txFifo     (4)       - Transmit FIFO Err
        	fifo       (6)       - Transmit & Receive FIFO Errs
        	clkEdgeErr (8)       - Clock Edge Error
        	carrierDrop(16)      - Carrier Dropped on Link Failure
        	noConn     (255)	 - Connectionless Port
        	oos        (65535)	 - Out of Service
        	errors     (*)       - Multiple Errors will display raw bit field value
           "
       ::= { hsTestEntry 3 }

hsTestLocalLoop OBJECT-TYPE
        SYNTAX INTEGER {
        	off (0),
        	local (1)
        	}
        MAX-ACCESS read-write
        STATUS current
        DESCRIPTION
           "Determines the status of the local loopback associated with this link.
           In order to turn on a loop, the link must be configured In Service
           with a Connection.
            	off        (0)	- indicates loopback is disabled
        	    local      (1)	- indicates local data is looped back to itself"
       ::= { hsTestEntry 4 }

hsTestRemoteLoop OBJECT-TYPE
        SYNTAX INTEGER {
        	off (10),
        	remote (11),
        	loopUpReq (74),
        	loopDwnReq (75)
        	}
        MAX-ACCESS read-write
        STATUS current
        DESCRIPTION
           "Determines the status of the remote side loopback associated with 
           this link. In order to turn on a loop, the link must be configured 
           In Service with a Connection.
            	off        (10)	- indicates remote loopback is disabled
        	    remoteV54  (11) - indicates data is looped back from remote to local
        	    loopUpReq  (74) - Remote loop status indicator, CANNOT be used in SET.
        	    loopDwnReq (75) - Remote loop status indicator, CANNOT be used in SET."
       ::= { hsTestEntry 5 }

hsTestBackplnLoop OBJECT-TYPE
        SYNTAX INTEGER {
        	loopOffBackplane (20),
        	loopBackplane (21)
            }
        MAX-ACCESS read-write
        STATUS current
        DESCRIPTION
           "Determines whether or not the link has connection loopback 
           via the Backplane.  This affects a data connection which must 
           already be in place prior to invoking this function."
       ::= { hsTestEntry 6 }

hsTestBertState OBJECT-TYPE
        SYNTAX INTEGER {
        	bertOff (50),
            allOnes (51),       -- (0xFF)  
            allZeros (52),      -- (0x00)  
            bertQRSS (76),
            bert2047 (77),        
            bert511 (78),
            bertOCU (79)       
            }
        MAX-ACCESS read-write
        STATUS current
        DESCRIPTION
            "This indicates the current BERT test running and can be used to
            start and stop a desired Test Period. In order to turn on a loop, 
            the link must be configured In Service."
        ::= { hsTestEntry 7 }

hsTestDuration OBJECT-TYPE
        SYNTAX Integer32
        MAX-ACCESS read-only
        STATUS current
        DESCRIPTION
            "This the total number of seconds the test data has been collected."
        ::= { hsTestEntry 8 }

hsTestLocESs OBJECT-TYPE
        SYNTAX Counter32
        MAX-ACCESS read-only
        STATUS current
        DESCRIPTION
            "This is the total number of errored seconds that have
            occurred on the local link since the Test has been turned on.
            
            This Errored Second is defined as a one second period in which 
            one or more bits are in error."
        ::= { hsTestEntry 9 }

hsTestRemESs OBJECT-TYPE
        SYNTAX Counter32
        MAX-ACCESS read-only
        STATUS current
        DESCRIPTION
            "This is the total number of errored seconds that have
            occurred on the remote side (backplane bus) since the Test 
            has been turned on.
            
            This Errored Second is defined as a one second period in which 
            one or more bits are in error."
        ::= { hsTestEntry 10 }

hsTestBitSpeed OBJECT-TYPE
        SYNTAX Integer32
        MAX-ACCESS read-only
        STATUS current
        DESCRIPTION
            "This is the current bit rate at which the link is configured for."
        ::= { hsTestEntry 11 }

hsTestCmdStatus OBJECT-TYPE
        SYNTAX INTEGER {
    -- Initial default status for a row
            ready-for-command (0),
    -- Action States used in SET Command (1..99)
            updateTest (1),
            clearErrors (14),
            insertError (16),
                		
    -- Response States used in GET RESPONSE Command (100..199)
            update-successful (101),
            clear-successful (114),
            insert-successful (116),
                		
    -- Test Error Codes used in GET RESPONSE Command (200..799)
            err-general-test-error (200),
            err-link-not-in-service (201),
            err-invalid-loop-type (202),
            err-invalid-bert-type (203),
            err-link-not-connected (204),
            err-test-in-progress (205),
            err-field-cannot-be-set (206),
            err-snmp-parse-failed(500),
            err-invalid-snmp-type(501),
            err-invalid-snmp-var-size(502) 
            }
        MAX-ACCESS read-write
        STATUS current
        DESCRIPTION
            "This is the command status for the High Speed Test Row.
           The value used in a SET will be replaced by a response
           value in the GET RESPONSE indicating success or failure.

            Default Response State used in GET RESPONSE Command
                ready-for-command (0)
                    initial default status for a row           
                    
            High Speed Action Commands used in SET Command (1..99)            
                updateTest (1)
                    Can be used optionally when activating loops and berts
                    in order to get status code back in response
                clearErrors (14)
                    Resets all error counters and bert test time to zero
                insertError (16)
                    Inserts an invalid bit pattern on both local and
                    remote sides causing an Errored Second for both.
                		
            Response States used in GET RESPONSE Command (100..199)
                update-successful (101)
                    Test action has been successfully performed
                clear-successful (114)
                    Error counts have been successfully cleared
                insert-successful (116)
                    Errored bits have been successfully inserted
                		
            High Speed Test Error Codes used in GET RESPONSE Command (200..799)
                err-general-test-error (200)
                    Unknown Test request error occurred.
                err-link-not-in-service (201)
                    Requested action cannot be performed for OOS ports                
                err-invalid-loop-type (202)
                    Unrecognized loop selection
                err-invalid-bert-type (203)
                    Unrecognized bert selection
                err-link-not-connected (204)
                    Requested action cannot be performed without connection                
                err-test-in-progress (205)
                    Requested action cannot be performed during bert
                err-field-cannot-be-set (206)
                    Read-only field was included in SET request
                err-snmp-parse-failed (500)
                    Agent could not parse variable
                err-invalid-snmp-type (501)
                    Variable ASN type does not match Agent defined type 
                err-invalid-snmp-var-size (502)
                    Variable size is too big" 

        ::= { hsTestEntry 12 } 
        
hsTestLocEFSs OBJECT-TYPE
        SYNTAX Counter32
        MAX-ACCESS read-only
        STATUS current
        DESCRIPTION
            "This is the total number of Local Error Free Seconds since the
             Test has been running."
        ::= { hsTestEntry 13 }
        
hsTestLocUASs OBJECT-TYPE
        SYNTAX Counter32
        MAX-ACCESS read-only
        STATUS current
        DESCRIPTION
            "This is the number of Local Unavailable Seconds (UAS) that have 
            occurred since the Test has been running.
            
            The UAS is a period of time consisting of 10 or more consecutive ESs."
        ::= { hsTestEntry 14 }

hsTestLocASs OBJECT-TYPE
        SYNTAX Counter32
        MAX-ACCESS read-only
        STATUS current
        DESCRIPTION
            "This is the number of Local Available Seconds (AS) that have occurred 
            since the Test has been running.
            
            The AS is the Test duration seconds minus the UAS."
        ::= { hsTestEntry 15 }

hsTestLocESNonUASs OBJECT-TYPE
        SYNTAX Counter32
        MAX-ACCESS read-only
        STATUS current
        DESCRIPTION
            "This is the number of Local Error Seconds (ES) which are not part of
            the UAS that occurred since the Test has been running."
        ::= { hsTestEntry 16 }

hsTestRemEFSs OBJECT-TYPE
        SYNTAX Counter32
        MAX-ACCESS read-only
        STATUS current
        DESCRIPTION
            "This is the total number of Remote Error Free Seconds since the
             Test has been running."
        ::= { hsTestEntry 17 }
        
hsTestRemUASs OBJECT-TYPE
        SYNTAX Counter32
        MAX-ACCESS read-only
        STATUS current
        DESCRIPTION
            "This is the number of Remote Unavailable Seconds (UAS) that have 
            occurred since the Test has been running.
            
            The UAS is a period of time consisting of 10 or more consecutive ESs."
        ::= { hsTestEntry 18 }

hsTestRemASs OBJECT-TYPE
        SYNTAX Counter32
        MAX-ACCESS read-only
        STATUS current
        DESCRIPTION
            "This is the number of Remote Available Seconds (AS) that have occurred 
            since the Test has been running.
            
            The AS is the Test duration seconds minus the UAS."
        ::= { hsTestEntry 19 }

hsTestRemESNonUASs OBJECT-TYPE
        SYNTAX Counter32
        MAX-ACCESS read-only
        STATUS current
        DESCRIPTION
            "This is the number of Remote Error Seconds (ES) which are not part of
            the UAS that occurred since the Test has been running."
        ::= { hsTestEntry 20 }

-- *************************************************************************
-- The DNX Link Status Counters are currently provided in 1 table. 
-- The Link Status Statistics Table will provide statistical counters for all 
-- applicable DS1/E1 links in the system. 

dsx1Status 	OBJECT IDENTIFIER 	::= { diagnostics 3 }

-- *************************************************************************
-- This table is the DS1/E1 Link Status Counters table

dsx1StatusTable OBJECT-TYPE
        SYNTAX SEQUENCE OF Dsx1StatusEntry
        MAX-ACCESS not-accessible
        STATUS current
        DESCRIPTION
            "This is the DS1/E1 Link Status Counters table which consists
            of an entry for each DS1/E1 port in the system.  This table 
            provides the total counters accumulated since the link has 
            been up or since the last time the counts were cleared."
        ::= { dsx1Status 1 }

dsx1StatusEntry OBJECT-TYPE
        SYNTAX Dsx1StatusEntry
        MAX-ACCESS not-accessible
        STATUS current
        DESCRIPTION
            "The conceptual row of the DS1/E1 Link Status Counters table. 
            A row in this table cannot be added or deleted but the
            counter time period can be reset to zero."
        INDEX { dsx1StatusAddr }
        ::= { dsx1StatusTable 1 }

Dsx1StatusEntry ::=
        SEQUENCE {
                dsx1StatusAddr             LinkPortAddress,
                dsx1StatusResrcId          Integer32,
                dsx1StatusState            INTEGER,
                dsx1StatusRedAlrmErrs      Counter32,
                dsx1StatusRAIErrs          Counter32,      -- Yellow Alarm
                dsx1StatusMFRAIErrs        Counter32,      -- MF Yellow Alarm
                dsx1StatusLOSErrs          Counter32,
                dsx1StatusAISErrs          Counter32,
                dsx1StatusOOFErrs          Counter32,
                dsx1StatusSEFErrs          Counter32,
                dsx1StatusTransSlipErrs    Counter32,
                dsx1StatusRecvSlipErrs     Counter32,
                dsx1StatusCRCErrs          Counter32,
                dsx1StatusBPVErrs          Counter32,
                dsx1StatusFrameBitErrs     Counter32,
                dsx1StatusFarEndBlockErrs  Counter32,
                dsx1StatusTrunkCondition   DataSwitch,                                     
                dsx1StatusInsErrMode       INTEGER,      -- RW              
                dsx1StatusCmdStatus		   INTEGER,      -- RW
                dsx1StatusRcvNationalBits  OneByteField              
                }

dsx1StatusAddr OBJECT-TYPE
        SYNTAX LinkPortAddress
        MAX-ACCESS read-only
        STATUS current
        DESCRIPTION
            "This number uniquely identifies an DS1/E1 link resource. 
            This number will be used throughout the system to identify 
            a unique link. The format is represented using an IP address 
            syntax (4 byte string). Note that the maximum valid link 
            number will vary depending on the specified carrier and framing 
            options. For example, an octal T1/E1 device has 8 DS1 links but the 
            DS3 has 28 DS1 links.
            
               The 1st byte is reserved for future Nest Number use
               The 2nd byte represents the Slot Number (1-11)            
               The 3rd byte represents the Link Number (1-32)
               The 4th byte is reserved for future use           
            "
        ::= { dsx1StatusEntry 1 }

dsx1StatusResrcId OBJECT-TYPE
        SYNTAX Integer32
        MAX-ACCESS read-only
        STATUS current
        DESCRIPTION
            "Uniquely identifies a link in the system.
             This number is provided as key to allow the manager to 
             map this entry to a corresponding Resource Table entry."
        ::= { dsx1StatusEntry 2 }

dsx1StatusState OBJECT-TYPE
        SYNTAX INTEGER {
        	ok  (0),
        	yel (2),              -- bit 1
        	ais (8),              -- bit 3
        	lof (32),             -- bit 5
        	los (64),             -- bit 6
        	red (2048),           -- bit 11
        	cfa (4096),           -- bit 12
        	oos (65535),          -- all bits
        	txSlip (2097152),     -- bit 21
        	rxSlip (4194304),     -- bit 22
        	slip (6291456),       -- bits 21,22
        	sef (8388608),        -- bit 23
        	underTest(1073741824),-- bit 30
        	errors(2147483647)    -- all
        	}
        MAX-ACCESS read-only
        STATUS current
        DESCRIPTION
           "Determines the current line condition status of the link.
           In order to turn on a loop, the link must be configured In Service.
        	ok       (0)          - In Sync
        	yel      (2)          - Yellow Alarm
        	ais      (8)          - Sending All Ones
        	lof      (32)         - Loss of Frame
        	los      (64)         - Loss of Signal
        	red      (2048)       - Red Alarm
        	cfa      (4096)       - Carrier Frame Alignment
        	oos      (65535)	  - Out of Service
        	txSlip   (2097152)    - Transmit Slip
        	rxSlip   (4194304)    - Receive Slip
        	slip     (6291456)    - Transmit/Receive Slip
        	sef      (8388608)    - Severely Errored Frames
        	underTest(1073741824) - Running Bit Error Test (BERT) 
        	errors   (2147483647) - Multiple Errors displays raw bit field value
           "
       ::= { dsx1StatusEntry 3 }

dsx1StatusRedAlrmErrs OBJECT-TYPE
        SYNTAX Counter32
        MAX-ACCESS read-only
        STATUS current
        DESCRIPTION
            "This is the number of seconds a Loss of Signal was declared."
        ::= { dsx1StatusEntry 4 } 

dsx1StatusRAIErrs OBJECT-TYPE
        SYNTAX Counter32
        MAX-ACCESS read-only
        STATUS current
        DESCRIPTION
            "This is the number of seconds a Remote Alarm Indication was received.
            Sometimes referred to as a Yellow Alarm Indication."
        ::= { dsx1StatusEntry 5 } 
        
dsx1StatusMFRAIErrs OBJECT-TYPE
        SYNTAX Counter32
        MAX-ACCESS read-only
        STATUS current
        DESCRIPTION
            "This is the number of seconds a Far End CAS Multi-Frame 
            Alarm Indication was received. Sometimes referred to as 
            a MF Yellow Alarm Indication."
        ::= { dsx1StatusEntry 6 } 
        
dsx1StatusLOSErrs OBJECT-TYPE
        SYNTAX Counter32
        MAX-ACCESS read-only
        STATUS current
        DESCRIPTION
            "This is the number of seconds a Loss of Signal was declared."
        ::= { dsx1StatusEntry 7 } 
        
dsx1StatusAISErrs OBJECT-TYPE
        SYNTAX Counter32
        MAX-ACCESS read-only
        STATUS current
        DESCRIPTION
            "This is the number of seconds a Alarm Indication Signal was declared."
        ::= { dsx1StatusEntry 8 } 
        
dsx1StatusOOFErrs OBJECT-TYPE
        SYNTAX Counter32
        MAX-ACCESS read-only
        STATUS current
        DESCRIPTION
            "This is the number of seconds a Out Of Frame alignement error was declared."
        ::= { dsx1StatusEntry 9 } 
        
dsx1StatusSEFErrs OBJECT-TYPE
        SYNTAX Counter32
        MAX-ACCESS read-only
        STATUS current
        DESCRIPTION
            "This is the number of seconds a Severely Errored Frame was declared."
        ::= { dsx1StatusEntry 10 } 
        
dsx1StatusTransSlipErrs OBJECT-TYPE
        SYNTAX Counter32
        MAX-ACCESS read-only
        STATUS current
        DESCRIPTION
            "This is the number of seconds a controlled slip was detected on 
            outgoing path."
        ::= { dsx1StatusEntry 11 } 
        
dsx1StatusRecvSlipErrs OBJECT-TYPE
        SYNTAX Counter32
        MAX-ACCESS read-only
        STATUS current
        DESCRIPTION
            "This is the number of seconds a controlled slip was detected on 
            incoming path."
        ::= { dsx1StatusEntry 12 } 
        
dsx1StatusCRCErrs OBJECT-TYPE
        SYNTAX Counter32
        MAX-ACCESS read-only
        STATUS current
        DESCRIPTION
            "This is the total number of CRC-6 (T1) or CRC-4 (E1) errors detected."
        ::= { dsx1StatusEntry 13 } 
        
dsx1StatusBPVErrs OBJECT-TYPE
        SYNTAX Counter32
        MAX-ACCESS read-only
        STATUS current
        DESCRIPTION
            "This is the total number of invalid Bipolar Violations or 
            Code Violations detected."
        ::= { dsx1StatusEntry 14 } 
        
dsx1StatusFrameBitErrs OBJECT-TYPE
        SYNTAX Counter32
        MAX-ACCESS read-only
        STATUS current
        DESCRIPTION
            "This is the total number of Frame Alignment Signal (FAS) framing
            words received incorrectly."
        ::= { dsx1StatusEntry 15 } 
        
dsx1StatusFarEndBlockErrs OBJECT-TYPE
        SYNTAX Counter32
        MAX-ACCESS read-only
        STATUS current
        DESCRIPTION
            "This is the total number of Remote CRC errors reported."
        ::= { dsx1StatusEntry 16 } 
        
dsx1StatusTrunkCondition OBJECT-TYPE
        SYNTAX DataSwitch
        MAX-ACCESS read-only
        STATUS current
        DESCRIPTION
            "Detetermines if Trunk Conditioning state is 'On' or 'Off'."
        ::= { dsx1StatusEntry 17 } 
        
dsx1StatusInsErrMode OBJECT-TYPE
        SYNTAX INTEGER {
            not-applicable (0),
        	cas-multiframe (1),
        	multiframe (2),
        	bert-error (3),
        	bit-slip (4),    
        	frame-alignment (5),
        	crc (6),     
        	fbit (7),
        	line-code-violation (8),    
        	allErrors (9),
        	yellow-alarm (10),
        	ybit (11),
        	fas-inverted (12),
        	nfas-bit2-inverted (13),
        	rai (14),
        	ts16-ais (15),
        	ais-unframed-all-ones (16)
        	}
        MAX-ACCESS read-write
        STATUS current
        DESCRIPTION
           "Determines the status of the current Insert Error mode associated 
           with this link. In order to insert an error, the dsx1StatusCmdStatus 
           must be sent in a SET PDU with a value of 'insertError'."
       ::= { dsx1StatusEntry 18 }

dsx1StatusCmdStatus OBJECT-TYPE
        SYNTAX INTEGER {
    -- Initial default status for a row
            ready-for-command (0),
    -- Action States used in SET Command (1..99)
            update (1),
            clearErrors (14),
            insertError (16),
                		
    -- Response States used in GET RESPONSE Command (100..199)
            update-successful (101),
            clear-successful (114),
            insert-successful (116),
                		
    -- Status Error Codes used in GET RESPONSE Command (200..799)
            err-general-status-error (200),
            err-link-not-in-service (201),
            err-link-in-clear-mode (204),
            err-test-in-progress (205),
            err-field-cannot-be-set (206),
            err-link-not-connected (207),
            err-invalid-command (208),
            err-link-not-in-test (211),
            err-snmp-parse-failed(500),
            err-invalid-snmp-type(501),
            err-invalid-snmp-var-size(502) 
            }
        MAX-ACCESS read-write
        STATUS current
        DESCRIPTION
            "This is the command status for the DS1/E1 Link Test Row.
           The value used in a SET will be replaced by a response
           value in the GET RESPONSE indicating success or failure.

            Default Response State used in GET RESPONSE Command
                ready-for-command (0)
                    initial default status for a row           
                    
            DS1/E1 Action Commands used in SET Command (1..99)            
                update (1)
                    Can be used optionally when modifing insert mode
                    in order to get status code back in response
                clearErrors (14)
                    Resets all error counters to zero
                insertError (16)
                    Inserts the current invalid bit pattern as indicated
                    by the value of dsx1StatusInsErrMode. 
                		
            Response States used in GET RESPONSE Command (100..199)
                update-successful (101)
                    Test action has been successfully performed
                clear-successful (114)
                    Error counts have been successfully cleared
                insert-successful (116)
                    Errored bits have been successfully inserted
                		
            DS1/E1 Status Error Codes used in GET RESPONSE Command (200..799)
                err-general-status-error (200)
                    Unknown link status table request error occurred.
                err-link-not-in-service (201)
                    Requested action cannot be performed for OOS links                
                err-link-in-clear-mode (204)
                    Requested action cannot be performed for clear framed
                    or clear unframed configured links               
                err-test-in-progress (205)
                    Requested action cannot be performed during bert
                err-field-cannot-be-set (206)
                    Read-only field was included in SET request
                err-link-not-connected (207)
                    Requested action cannot be performed without link connection
                err-invalid-command (208)
                    Unrecognized Test Command requested                    
                err-link-not-in-test (211)
                    Requested action cannot be performed without a bert
                err-snmp-parse-failed (500)
                    Agent could not parse variable
                err-invalid-snmp-type (501)
                    Variable ASN type does not match Agent defined type 
                err-invalid-snmp-var-size (502)
                    Variable size is too big" 
        ::= { dsx1StatusEntry 19 } 
        
dsx1StatusRcvNationalBits OBJECT-TYPE
        SYNTAX OneByteField
        MAX-ACCESS read-only
        STATUS current
        DESCRIPTION
           "Displays the E1 National S-bits being received on the link.
           This single byte field shows the values in Hex 
           of the E1 NFA byte in odd frames as depicted below:
           
              sa8 sa7 sa6 sa5 sa4 reserved bits
              --- --- --- --- --- -------------
              1    1   1   1   1   0   0   0      = F8
              
           Reserved bits are always zero.                 
           "
        ::= { dsx1StatusEntry 20 }
END

-- *************************************************************************
--
--  MIB:    ERI-DNX-ALARM-TRAP-MIB
--
--	Purpose:
--          This will be the MIB for the DNX Alarm Traps.
--
--  Contact: Eastern Research Inc. 1-800-337-4374  Email: support@erinc.com
--
-- *************************************************************************
