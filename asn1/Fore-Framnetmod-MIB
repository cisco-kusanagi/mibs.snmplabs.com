-- 
-- Copyright 1999 by Fore Systems, Inc. 
-- Converted to SMIv2 rfc 2578,2579,2580 - STD 58
--
-- Copyright 1997-1999 by Fore Systems, Inc.
--
-- This is the FRAM netmod proprietory MIB. Currently, this mib defines one 
-- table:    nmFramNetmodConfTable
-- This table contains configuration information for FRAM netmod.
-- If the netmod is up and running, all the configuration objects,
-- which can be set by user, will take effect by setting moduleState
-- to reset. moduleState is defined in moduleTable of fore-switch.mib.
--
-- The following description is applicable to the definition of those
-- objects which config the FRAM netmod EPD/PPD controller. 
--
-- (1) PPD CLP=0 is not configurable but fixed at 87.5% of the available buffer
-- for each priority. 
-- For instance, assuming the buffer size is configured as 16384 cells,     
-- then the PPD CLP=0 threshold is 16384 * 0.875 = 14336 cells.
--
-- (2) EPD CLP=1 threshold is configured as follows:
--                 ________________________________
--                 | Config bits | Threshold (x%) |
--                 |______________________________|
--                 |     00      |     25         |
--                 |______________________________|
--                 |     01      |     37         |
--                 |______________________________|
--                 |     10      |     50         |
--                 |______________________________|
--                 |     11      |     62         |
--                 |______________________________|
--
-- This x% value is relative to the PPD CLP=0 threshold (see (1)) cell value.
-- if x% == 50%, then the EPD CLP=1 threshold is 14336 * x% = 7168 cells.
--
-- (3) EPD CLP=0 threshold is configured as follows:
--                 ________________________________
--                 | Config bits | Threshold (y%) |
--                 |______________________________|
--                 |     00      |     50         |
--                 |______________________________|
--                 |     01      |     62.5       |
--                 |______________________________|
--                 |     10      |     75         |
--                 |______________________________|
--                 |     11      |     87.5       |
--                 |______________________________|
--
-- This y% value is relative to the difference between the PPD CLP=0 (see (1))
-- and the EPD CLP=1 threshold (see (2)) cell value.  
-- if y% == 50%, then the EPD CLP=0 threshold is
--          ((14336 - 7168) * y% + 7168) = 10752 cells.
--
-- (4) PPD CLP=1 threshold is configured as follows:
--                 ________________________________
--                 | Config bits | Threshold (z%) |
--                 |______________________________|
--                 |     00      |     50         |
--                 |______________________________|
--                 |     01      |     62.5       |
--                 |______________________________|
--                 |     10      |     75         |
--                 |______________________________|
--                 |     11      |     87.5       |
--                 |______________________________|
--
-- This z% value is relative to the difference between the EPD CLP=0 (see (3))
-- and the EPD CLP=1 threshold (see (2)) cell value.
-- if z% == 50%, then the PPD CLP=1 threshold is
--          ((10752 - 7168) * z% + 7168) = 8960 cells. 
--

Fore-Framnetmod-MIB DEFINITIONS ::= BEGIN

  IMPORTS
	     TimeTicks, Integer32,
             OBJECT-TYPE,
             MODULE-IDENTITY,
	     NOTIFICATION-TYPE                FROM SNMPv2-SMI
             DisplayString                    FROM SNMPv2-TC
	     frameInternetworking,
             atmSwitch                        FROM Fore-Common-MIB
             ifConvertToIfIndexPortId,
	     ifConvertToIfIndexChannelId      FROM Fore-Ifcreate-MIB
             frCircuitDlci                    FROM FRAME-RELAY-DTE-MIB	     
             funiConnFuniVpi, funiConnFuniVci FROM Fore-Funi-MIB;

--  internet         OBJECT IDENTIFIER ::= { iso(1) org(3) dod(6) 1 }
--  private          OBJECT IDENTIFIER ::= { internet 4 }
--  enterprises      OBJECT IDENTIFIER ::= { private 1 }
--  fore             OBJECT IDENTIFIER ::= { enterprises 326 }
--  admin            OBJECT IDENTIFIER ::= { fore 1 }

fram MODULE-IDENTITY
          LAST-UPDATED         "9911050000Z"
          ORGANIZATION         "FORE"
          CONTACT-INFO         
               "      Postal:   FORE Systems Inc.
                                 1000 FORE Drive
                                 Warrendale, PA 15086-7502
                       Tel:      +1 724 742 6900
                       Email:    nm_mibs@fore.com
                       Web:      http://www.fore.com"
          DESCRIPTION "
	      This is the FRAM netmod proprietory MIB. Currently, this mib
	      defines one table:    nmFramNetmodConfTable
	      This table contains configuration information for FRAM netmod."
	  
               ::= { frameInternetworking 3 }

-- The following  table supports for configuration of the EPD/PPD controller 
-- and Frame Relay / ATM interworking service OAM cell generation rate.

  nmFramNetmodConfTable   OBJECT-TYPE
  SYNTAX                    SEQUENCE OF NmFramNetmodConfEntry
  MAX-ACCESS                    not-accessible
  STATUS                    current
  DESCRIPTION
    "This  table  has  the  objects  for  configuration of a FRAM netmod.
     Creation of an entry for this table is triggered by setting 
     moduleState to inService. moduleState is one of the objects of
     moduleTable defined in fore-switch.mib"
  ::= { fram 1 }

  nmFramNetmodConfEntry  OBJECT-TYPE
  SYNTAX                   NmFramNetmodConfEntry
  MAX-ACCESS                   not-accessible
  STATUS                   current
  DESCRIPTION
    "A table entry containing FRAM netmod specific config information"
  INDEX {nmFramBoard, nmFramModule }
  ::= { nmFramNetmodConfTable 1 }

 NmFramNetmodConfEntry ::= SEQUENCE {
    nmFramBoard                       Integer32,
    nmFramModule                      Integer32,
    nmFramEpdPpdBufferProportion      INTEGER,
    nmFramEpdclp1HighPrio             INTEGER,
    nmFramEpdclp0HighPrio             INTEGER,
    nmFramPpdclp1HighPrio             INTEGER,
    nmFramEpdclp1LowPrio              INTEGER,
    nmFramEpdclp0LowPrio              INTEGER,
    nmFramPpdclp1LowPrio              INTEGER,
    nmFramOamF5Supervision            INTEGER,
    nmFramOamF5AISRxPeriod            INTEGER,
    nmFramOamF5AISTxPeriod            INTEGER,
    nmFramOamF5RDIRxPeriod            INTEGER,
    nmFramOamF5RDITxPeriod            INTEGER,   
    nmFramOperState                   INTEGER,
    nmFramApplSwRelease               DisplayString,
    nmFramBootSwRelease	              DisplayString,
    nmFramApplKey                     DisplayString, 
    nmFramApplication                 INTEGER,
    nmFramOosLED                      INTEGER,
    nmFramMaxSigPathsPerPort          INTEGER,
    nmFramStatsMonitor                INTEGER,               
    nmFramStatsEnabledTimeStamp       TimeTicks,
    nmFramMsgType                     Integer32,
    nmFramNakCause                    Integer32
  }  

 nmFramBoard   OBJECT-TYPE
       SYNTAX  Integer32       
       MAX-ACCESS  read-only
       STATUS  current
       DESCRIPTION
       " the index of this board within the ATM switch, equivalent to
        moduleBoard of moduleTable defined in fore-switch.mib"
       ::={ nmFramNetmodConfEntry 1 }

 nmFramModule   OBJECT-TYPE
       SYNTAX  Integer32       
       MAX-ACCESS  read-only
       STATUS  current
       DESCRIPTION
       " the number of this network module within the ATM switch board,
	equivalent to moduleNumber of moduleTable defined in fore-switch.mib"
       ::={ nmFramNetmodConfEntry 2 }

 nmFramEpdPpdBufferProportion   OBJECT-TYPE
       SYNTAX  INTEGER {
                 highzero (1),
                 high1quarter (2),
                 high2quarter (3),
                 high3quarter (4)
                 }
       MAX-ACCESS  read-write
       STATUS  current
       DESCRIPTION
       "Configuration  of  the  buffer size configuration for the high and
       low  priority  cell.  The  sum  of  high  and  low priority buffers
       capacity is fixed, i.e., highzero selection means low priority buffer
       size being the maximum which is 32768 cells capacity. 4 possible 
       way of partitioning the buffer:
          ________________________________
         |  High Priority | Low Priority |
         |_______________________________|
         |      0 cells   | 32768 cells  |
         |_______________________________|
         |   8192 cells   | 24576 cells  |
         |_______________________________|
         |  16384 cells   | 16384 cells  |
         |_______________________________|
         |  24576 cells   |  8192 cells  |
         |_______________________________|
       "
       DEFVAL { high2quarter }
       ::= { nmFramNetmodConfEntry  3  }

 nmFramEpdclp1HighPrio    OBJECT-TYPE
       SYNTAX  INTEGER ( 25 | 37 | 50 | 62 )
       MAX-ACCESS  read-write
       STATUS  current
       DESCRIPTION
       "The threshold for the high priority buffer for EPD and CLP=1 in
       percentage of the available size"
       DEFVAL { 25 }
       ::= { nmFramNetmodConfEntry 4 }

 nmFramEpdclp0HighPrio    OBJECT-TYPE
       SYNTAX  INTEGER ( 50 | 62 | 75 | 87 )
       MAX-ACCESS  read-write
       STATUS  current
       DESCRIPTION
       "The threshold for the high priority buffer for EPD and CLP=0 in
       percentage of the available size"
       DEFVAL { 50 }
       ::= { nmFramNetmodConfEntry 5 }

 nmFramPpdclp1HighPrio    OBJECT-TYPE
       SYNTAX  INTEGER ( 50 | 62 | 75 | 87 )
       MAX-ACCESS  read-write
       STATUS  current
       DESCRIPTION
       "The  threshold  for the high priority buffer for PPD and CLP=1, in
       percentage of the available size"
       DEFVAL { 50 }
       ::= {  nmFramNetmodConfEntry  6  }

 nmFramEpdclp1LowPrio    OBJECT-TYPE
       SYNTAX  INTEGER ( 25 | 37 | 50 | 62 )
       MAX-ACCESS  read-write
       STATUS  current
       DESCRIPTION
       "The threshold for the Low priority buffer for EPD and CLP=1 in
       percentage of the available size"
       DEFVAL { 25 }
       ::= { nmFramNetmodConfEntry 7  }

 nmFramEpdclp0LowPrio    OBJECT-TYPE
       SYNTAX  INTEGER ( 50 | 62 | 75 | 87 ) 
       MAX-ACCESS  read-write
       STATUS  current
       DESCRIPTION
       "The threshold for the Low priority buffer for EPD and CLP=0 in
       percentage of the available size"
       DEFVAL { 50 }
       ::= { nmFramNetmodConfEntry 8 }

 nmFramPpdclp1LowPrio    OBJECT-TYPE
       SYNTAX  INTEGER ( 50 | 62 | 75 | 87 )
       MAX-ACCESS  read-write
       STATUS  current
       DESCRIPTION
       "The threshold for the Low priority buffer for ppd and CLP=1 in
       percentage of the available size"
       DEFVAL { 50 }
       ::= { nmFramNetmodConfEntry 9  }

 nmFramOamF5Supervision  OBJECT-TYPE
       SYNTAX  INTEGER {
		    enabled(1),
		    disabled(2)
                  }
       MAX-ACCESS  read-write
       STATUS  current
       DESCRIPTION
        " enable/disable the FR/ATM interworking OAM F5 function on 
	  FRAM netmod"
       DEFVAL { enabled }
       ::= { nmFramNetmodConfEntry 10 }

 nmFramOamF5AISRxPeriod  OBJECT-TYPE
       SYNTAX    INTEGER (1..5)
       MAX-ACCESS    read-write
       STATUS    current
       DESCRIPTION
       "Time interval at which an AIS OAM cells is to be received,
       value is a measurement in seconds"
       DEFVAL { 3 }
       ::= { nmFramNetmodConfEntry 11 }

 nmFramOamF5AISTxPeriod  OBJECT-TYPE
       SYNTAX    INTEGER (1..5)
       MAX-ACCESS    read-write
       STATUS    current
       DESCRIPTION
       "Time interval at which an AIS OAM cells is to be transmitted,
       value is a measurement in seconds"
       DEFVAL { 1 }
       ::= { nmFramNetmodConfEntry 12 }

 nmFramOamF5RDIRxPeriod  OBJECT-TYPE
       SYNTAX    INTEGER  (1..5)
       MAX-ACCESS    read-write
       STATUS    current
       DESCRIPTION
       "Time interval at which an RDI OAM cells is to be received,
       value is a measurement in seconds"
       DEFVAL { 3 }
       ::={ nmFramNetmodConfEntry 13 }

 nmFramOamF5RDITxPeriod  OBJECT-TYPE
       SYNTAX    INTEGER  (1..5)
       MAX-ACCESS    read-write
       STATUS    current
       DESCRIPTION
       "Time interval at which an RDI OAM cells is to be transmitted,
       value is a measurement in seconds"
       DEFVAL { 1 }
       ::= { nmFramNetmodConfEntry 14 }

 nmFramOperState  OBJECT-TYPE
       SYNTAX    INTEGER  {
                   justinserted(1),
		   releasedreset(2),
		   waitmsgstartup(3),
		   waittestend(4),

		   waitapplstartup(5),
		   selftest(6),
		   startupfailed(7),
		   pulledout(8),
		   bootconsole(9),
		   appluprunning(10),
		   down(11)       
               }
       MAX-ACCESS    read-only
       STATUS    deprecated
       DESCRIPTION
       "This is the operational state corresponding to the FRAM netmod startup
       state machine."
       ::= { nmFramNetmodConfEntry 15 }
         
 nmFramApplSwRelease OBJECT-TYPE
       SYNTAX DisplayString
       MAX-ACCESS read-only
       STATUS deprecated
       DESCRIPTION
       "The Embedded Software Version number running on this netmod"
       ::= { nmFramNetmodConfEntry 16 }

 nmFramBootSwRelease OBJECT-TYPE
       SYNTAX DisplayString
       MAX-ACCESS read-only
       STATUS deprecated
       DESCRIPTION
       "The Boot Software Version number running on this netmod"
       ::= { nmFramNetmodConfEntry 17 }

 nmFramApplKey  OBJECT-TYPE
       SYNTAX DisplayString
       MAX-ACCESS read-write
       STATUS deprecated
       DESCRIPTION
       "This object is for the purpose of setting up the Application
       type for the FRAM netmod. The application key should be specified
       when the application type is `unconfigured' or whenever the user
       want to reconfigure the netmod to run a different type of application.
       Changing the application type will cause the netmod to be reset 
       and old configuration lost.

       Note this object is write-only and reading it will
       result in implementation-specific results."
       ::= { nmFramNetmodConfEntry 18 }

 nmFramApplication OBJECT-TYPE
       SYNTAX INTEGER {
            frAtmServiceAppl(1),
	    frAtmNetworkAppl(2),
            framFuniAppl(3)  
        } 
        MAX-ACCESS read-write
        STATUS current
        DESCRIPTION
        "This object is for the purpose of setting up the Application
        type for the FRAM netmod. Changing the application type will cause 
        the netmod to be reset and old configuration lost."
        DEFVAL { frAtmServiceAppl }
        ::= { nmFramNetmodConfEntry 19 }

 nmFramOosLED     OBJECT-TYPE
       SYNTAX  INTEGER {
              off(1),
              red(3)
            }
       MAX-ACCESS  read-only
       STATUS  deprecated
       DESCRIPTION
       "Indicates the netmod service status. This LED is normally
       dark. When it becomes red, the netmod is Out Of Service (OOS)
       and can be removed. FRAM netmod can be set to OOS by user which
       means the netmod will stop passing data when the user set this
       LED to red(3). See the definition of moduleState object of
       moduleTable in fore-switch.mib"
       DEFVAL { off }
       ::= { nmFramNetmodConfEntry 20 }

 nmFramMaxSigPathsPerPort   OBJECT-TYPE
       SYNTAX  INTEGER (1..31)
       MAX-ACCESS  read-write
       STATUS  current
       DESCRIPTION
       "This object specifies the max number of UNI instances per port 
       which can be created for FUNI SVC Signaling Support. In other
       words, this object defines the max number of FUNI services per 
       port which can have SVC Signaling enabled."
       DEFVAL { 1 }
       ::= { nmFramNetmodConfEntry 21 } 

 nmFramStatsMonitor  OBJECT-TYPE
       SYNTAX  INTEGER {
             enabled (1),
	     disabled (2)
	   }
       MAX-ACCESS   read-write
       STATUS   current
       DESCRIPTION 
       "This object specifies whether statistics are to be counted by the 
        netmod system. The object controls from an overall perspective whether
        netmod, service and connection level statistics are to be counted.
        The object state will override the service level StatsMonitor objects,
        such that if the nmFramStatsMonitor is disabled then no statistics will
        be counted irrespective of whether the service level StatsMonitor is
        enabled. When the state changes from enabled to disabled all the 
        related statistics will be frozen at their current value. When the 
        state changes from disabled to enabled then all related statistics 
        will be reset (zeroised)."
       DEFVAL { enabled }
       ::= { nmFramNetmodConfEntry 22 }    

 nmFramStatsEnabledTimeStamp  OBJECT-TYPE
       SYNTAX  TimeTicks
       MAX-ACCESS  read-only
       STATUS  current
       DESCRIPTION
       "nmFramStatsEnabledTimeStamp reflects the time, with reference to
        sysUpTime, when nmFramStatsMonitor is set to enabled. This will, 
        therefore, provide a starting timestamp for the current statistics 
        that are being counted."
       ::= { nmFramNetmodConfEntry 23 }

 nmFramMsgType  OBJECT-TYPE
       SYNTAX  Integer32 
       MAX-ACCESS   read-only 
       STATUS   current
       DESCRIPTION
        "This object is the identifier number of the messages that are 
         sent from The SCP to the FRAM netmods." 
       ::= { nmFramNetmodConfEntry 24 }

 nmFramNakCause OBJECT-TYPE
       SYNTAX  Integer32 
       MAX-ACCESS   read-only 
       STATUS   current
       DESCRIPTION
        "This object is the error code that indicates why a message sent
         from the SCP to the FRAM  netmod did not succeed."
       ::= { nmFramNetmodConfEntry 25 }
------------------------------------------------------------------------

framNakMsg   NOTIFICATION-TYPE
             OBJECTS  { nmFramMsgType,
                        nmFramNakCause,
                        nmFramBoard,
                        nmFramModule,
                        ifConvertToIfIndexPortId,
                        ifConvertToIfIndexChannelId,
                        frCircuitDlci,
                        funiConnFuniVpi,
                        funiConnFuniVci }
             STATUS      current
             DESCRIPTION
             "This trap is sent when a message from the SCP to the 
             FRAM netmod does not succeed."
             ::= { atmSwitch 0 2003 }
END
