Novell-LANtern-Admin-MIB DEFINITIONS ::= BEGIN

          -- Title: Lantern Network Monitor Version 1.3
          -- Date:  September 10, 1991

          -- Now RMON aligned (and politically correct!).


              IMPORTS
                     enterprises, TimeTicks, IpAddress, Counter, Gauge
                         FROM RFC1155-SMI
                     TRAP-TYPE
                         FROM RFC-1215
                     OBJECT-TYPE
                         FROM RFC-1212;


          novell           OBJECT IDENTIFIER ::= { enterprises 23 }

          productType      OBJECT IDENTIFIER ::= { novell 1 }
          mibDoc           OBJECT IDENTIFIER ::= { novell 2 }

          networkMonitor   OBJECT IDENTIFIER ::= { productType 1 }

          ethernetLANtern  OBJECT IDENTIFIER ::= { networkMonitor 1 }

          lantern          OBJECT IDENTIFIER ::= { mibDoc 1 }

          lanternAdmin     OBJECT IDENTIFIER ::= { lantern 1 }



          -- textual conventions

          Time ::=
          INTEGER
          -- The date and time expressed as the number of seconds
          -- since midnight January 1, 1900 GMT


          DisplayString ::=
          OCTET STRING
          -- This type is used to model textual information taken
          -- from the NVT ASCII character set.

          PhysAddress ::=
          OCTET STRING
          -- This data type is used to model media addresses.

          Seconds ::=
          INTEGER
          -- This type is used to model durations in seconds.



          -- The Administrative Group

          adminIdentification OBJECT-TYPE
              SYNTAX DisplayString
              ACCESS read-write
              STATUS mandatory
              DESCRIPTION
                     "An identifying ASCII string may be attached to the
                     LANtern network monitor by writing
                     adminIdentification.  Conversely, the LANtern
                     network monitor may be identified by reading
                     adminIdentification.
                     adminIdentification is stored in nonvolatile RAM."
              DEFVAL { "" }
              ::= { lanternAdmin 1 }

          adminDateAndTime OBJECT-TYPE
              SYNTAX Time
              ACCESS read-write
              STATUS mandatory
              DESCRIPTION
                     "Reading adminDateAndTime returns the current date
                     and time in use by the LANtern network monitor.
                     The LANtern network monitor's date and time may be
                     adjusted at any time by writing to
                     adminDateAndTime.  However, although the new value
                     is updated correctly as time advances, it does not
                     replace the previous value until the LANtern
                     network monitor is restarted.
                     adminDateAndTime is stored in the clock/calendar
                     chip."
              ::= { lanternAdmin 2 }

          adminTimeZone OBJECT-TYPE
              SYNTAX DisplayString
              ACCESS read-write
              STATUS mandatory
              DESCRIPTION
                     "A DisplayString defining the time zone of the
                     LANtern network monitor.  adminTimeZone is neither
                     parsed nor used by the LANtern network monitor, it
                     is merely stored and divulged upon request.  It is
                     strongly recommended that adminTimeZone be used to
                     store time zone information in a manner identical
                     to the UNIX System V time zone environment variable
                     (TZ).  This standard approach would permit
                     interoperability with network management consoles
                     from multiple vendors.
                     adminTimeZone is stored in nonvolatile RAM."
              DEFVAL { "" }
              ::= { lanternAdmin 3 }

          adminPowerOnTime OBJECT-TYPE
              SYNTAX Time
              ACCESS read-only
              STATUS mandatory
              DESCRIPTION
                     "The date and time when the LANtern network monitor
                     was last powered on or restarted."
              ::= { lanternAdmin 4 }

          adminPowerOffTime OBJECT-TYPE
              SYNTAX Time
              ACCESS read-only
              STATUS mandatory
              DESCRIPTION
                     "The date and time when the LANtern network monitor
                     was last powered off or restarted.  The value is 0
                     (midnight, 1 January 1900) after a cold start."
              ::= { lanternAdmin 5 }

          adminNetworkDataLink OBJECT-TYPE
              SYNTAX INTEGER {
                         ethernetDIX(1)
                     }
              ACCESS read-write
              STATUS mandatory
              DESCRIPTION
                     "The type of data link encapsulation to be used on
                     the monitored network.  adminNetworkDataLink may be
                     written at any time; however, the change does not
                     take effect until the LANtern network monitor is
                     restarted.  When adminNetworkDataLink is read, it
                     returns the value currently in use, regardless of
                     any previous writes.
                     adminNetworkDataLink is stored in nonvolatile RAM."
              DEFVAL { 1 } -- ethernetDIX
              ::= { lanternAdmin 6 }

          adminNetworkIPAddr OBJECT-TYPE
              SYNTAX IpAddress
              ACCESS read-write
              STATUS mandatory
              DESCRIPTION
                     "The IP address to be used by the LANtern network
                     monitor on the monitored network.
                     adminNetworkIPAddr may be written at any time;
                     however, the change does not take effect until the
                     LANtern network monitor is restarted.  When
                     adminNetworkIPAddr is read, it returns the IP
                     address currently in use, regardless of any
                     previous writes.
                     adminNetworkIPAddr is stored in nonvolatile RAM.
                     On start up, if the LANtern does not have an IP
                     address, it will attempt to acquire one via BOOTP
                     and/or RARP.  If neither method is successful, the
                     address 192.68.205.1 is used."
              DEFVAL { 'c044cd01'H } --192.68.205.1
              ::= { lanternAdmin 7 }

          adminNetworkSubnetMask OBJECT-TYPE
              SYNTAX IpAddress
              ACCESS read-write
              STATUS mandatory
              DESCRIPTION
                     "The subnet mask for the monitored network.
                     adminNetworkSubnetMask may be written at any time;
                     however, the change does not take effect until the
                     LANtern network monitor is restarted.  When
                     adminNetworkSubnetMask is read, it returns the
                     subnet mask currently in use, regardless of any
                     previous writes.
                     adminNetworkSubnetMask is stored in nonvolatile
                     RAM.
                     When the value 0.0.0.0 is stored in this variable,
                     the LANtern assumes no subnetting.
                     This value is acquired via BOOTP if the value of
                     adminNetworkIPAddr is acquired via BOOTP.  If
                     neither BOOTP nor RARP succeeds in acquiring
                     adminNetworkIPAddr, the value 255.255.255.128 is
                     used"
              DEFVAL { 'ffffff80'H } -- 255.255.255.128
              ::= { lanternAdmin 8 }

          adminNetworkGateway OBJECT-TYPE
              SYNTAX IpAddress
              ACCESS read-write
              STATUS mandatory
              DESCRIPTION
                     "The IP address of a gateway directly connected to
                     the monitored network (the LANtern network
                     monitor's default gateway).  adminNetworkGateway
                     may be written at any time; however, the change
                     does not take effect until the LANtern network
                     monitor is restarted.  When adminNetworkGateway is
                     read it returns the gateway IP address currently in
                     use, regardless of any previous writes.
                     adminNetworkGateway is stored in nonvolatile RAM."
              DEFVAL { '00000000'H } -- No gateway
              ::= { lanternAdmin 9 }

          adminClientTable OBJECT-TYPE
              SYNTAX SEQUENCE OF AdminClientEntry
              ACCESS not-accessible
              STATUS mandatory
              DESCRIPTION
                     "A table providing data on all authorized LANtern
                     clients.  The table is accessed by
                     adminClientIPAddr.  A new entry may be created by
                     writing to a nonexistent instance.  Note that
                     adminClientIPAddr is set implicitly from this
                     write; it cannot be written directly.  An entry may
                     subsequently be deleted by writing (any value) to
                     adminClientDelete.
                     adminClientTable is stored in nonvolatile RAM.
                     Default:  a single entry with:
                         adminClientIPAddr.0.0.0.0=0.0.0.0,
                         adminClientIPMask.0.0.0.0=0.0.0.0,
                         adminClientCommunities.0.0.0.0=7"
              ::= { lanternAdmin 10 }

          adminClientEntry OBJECT-TYPE
              SYNTAX AdminClientEntry
              ACCESS not-accessible
              STATUS mandatory
              DESCRIPTION
                     "Data about each authorized client."
              INDEX  { adminClientIPAddr }
              ::= { adminClientTable 1 }

          AdminClientEntry ::=
              SEQUENCE {
                  adminClientIPAddr               IpAddress,
                  adminClientIPMask               IpAddress,
                  adminClientCommunities          INTEGER,
                  adminClientDelete               INTEGER
              }

          adminClientIPAddr OBJECT-TYPE
              SYNTAX IpAddress
              ACCESS read-only
              STATUS mandatory
              DESCRIPTION
                     "The IP address (or portion thereof) of a station
                     authorized to access the LANtern network monitor."
              ::= { adminClientEntry 1 }
          adminClientIPMask OBJECT-TYPE
              SYNTAX IpAddress
              ACCESS read-write
              STATUS mandatory
              DESCRIPTION
                     "A 32-bit mask that is bitwise anded with the
                     candidate client's IP address before attempting to
                     match against adminClientIPAddr."
              DEFVAL { 'ffffffff'H }
              ::= { adminClientEntry 2 }

          adminClientCommunities OBJECT-TYPE
              SYNTAX INTEGER
              ACCESS read-write
              STATUS mandatory
              DESCRIPTION
                     "A bit array where the presence of a particular bit
                     indicates that use of that particular community
                     name is permitted.
                         Bit  Community
                         2^0  administrator
                         2^1  logger
                         2^2  monitor."
              DEFVAL { 4 } -- monitor
              ::= { adminClientEntry 3 }

          adminClientDelete OBJECT-TYPE
              SYNTAX INTEGER
              ACCESS write-only
              STATUS mandatory
              DESCRIPTION
                     "A write (any value) causes the table entry to be
                     deleted."
              ::= { adminClientEntry 4 }

          adminUnauthorizedIPAddr OBJECT-TYPE
              SYNTAX IpAddress
              ACCESS not-accessible
              STATUS mandatory
              DESCRIPTION
                     "The IP address of the station that generated the
                     authentication failure."
              ::= { lanternAdmin 11 }

          adminUnauthorizedCommunity OBJECT-TYPE
              SYNTAX OCTET STRING
              ACCESS not-accessible
              STATUS mandatory
              DESCRIPTION
                     "The community name string used in the PDU that
                     generated the authentication failure."
              ::= { lanternAdmin 12 }

          adminNotificationTable OBJECT-TYPE
              SYNTAX SEQUENCE OF AdminNotificationEntry
              ACCESS not-accessible
              STATUS mandatory
              DESCRIPTION
                     "A list of all stations wishing to receive traps
                     from the LANtern network monitor; accessed by
                     adminNotificationIPAddr.  A new entry may be
                     created by writing to a nonexistent instance.  Note
                     that adminNotificationIPAddr is set implicitly from
                     this write; it cannot be written directly.  An
                     entry may subsequently be deleted by writing (any
                     value) to adminNotificationDelete
                     adminNotificationTable is stored in nonvolatile
                     RAM."
              ::= { lanternAdmin 13 }

          adminNotificationEntry OBJECT-TYPE
              SYNTAX AdminNotificationEntry
              ACCESS not-accessible
              STATUS mandatory
              DESCRIPTION
                     "Data for each station on the notification list."
              INDEX  { adminNotificationIPAddr }
              ::= { adminNotificationTable 1 }

          AdminNotificationEntry ::=
              SEQUENCE {
                  adminNotificationIPAddr         IpAddress,
                  adminNotificationStatus         INTEGER,
                  adminNotificationTrapMask       INTEGER,
                  adminNotificationConfirmMask    INTEGER,
                  adminNotificationTimeout        INTEGER,
                  adminNotificationRetries        INTEGER,
                  adminNotificationBackupIPAddr   IpAddress,
                  adminNotificationDelete         INTEGER
              }

          adminNotificationIPAddr OBJECT-TYPE
              SYNTAX IpAddress
              ACCESS read-only
              STATUS mandatory
              DESCRIPTION
                     "The IP address of the station wishing to receive
                     traps from the LANtern network monitor."
              ::= { adminNotificationEntry 1 }

          adminNotificationStatus OBJECT-TYPE
              SYNTAX INTEGER {
                         primaryContact(1),
                         backupContact(2)
                     }
              ACCESS read-write
              STATUS mandatory
              DESCRIPTION
                     "Traps are sent to all primaryContacts who have the
                     corresponding bit set in adminNotificationTrapMask.
                     Traps are sent to backupContacts only if they have
                     the corresponding bit set in
                     adminNotificationTrapMask and if a confirmed
                     delivery to a station naming it as backup failed.
                     Default:  primaryContact(1)"
              DEFVAL { 1 } -- primaryContact
              ::= { adminNotificationEntry 2 }

          adminNotificationTrapMask OBJECT-TYPE
              SYNTAX INTEGER
              ACCESS read-write
              STATUS mandatory
              DESCRIPTION
                     "A bit array specifying which traps the station
                     wishes to receive.
                         Bit  Trap
                         2^0  warmStart
                         2^1  cableFailure
                         2^2  reserved
                         2^3  duplicateIPAddr
                         2^4  utilizationAlarm
                         2^5  errorsAlarm
                         2^6  broadcastsAlarm
                         2^7  collisionsAlarm
                         2^8  authenticationFailure
                         2^9  hostInactive
                         2^10 hostActive
                         2^11 newHost
                         2^12 hostLimitExceeded"
              DEFVAL { 0 } -- No traps
              ::= { adminNotificationEntry 3 }

          adminNotificationConfirmMask OBJECT-TYPE
              SYNTAX INTEGER
              ACCESS read-write
              STATUS mandatory
              DESCRIPTION
                     "A bit array specifying which traps the station
                     wishes to receive with confirmed delivery.  Any
                     bits set must also be set in
                     adminNotificationTrapMask.  If a trap sent with
                     confirmed delivery is not acknowledged within
                     adminNotificationTimeout seconds it is sent again.
                     After adminNotificationRetries attempts to deliver
                     the trap, the LANtern network monitor gives up, and
                     tries to deliver it to the station specified by
                     adminNotificationBackup."
              DEFVAL { 0 } -- No confirmed traps
              ::= { adminNotificationEntry 4 }

          adminNotificationTimeout OBJECT-TYPE
              SYNTAX Seconds
              ACCESS read-write
              STATUS mandatory
              DESCRIPTION
                     "For traps with confirmed delivery,
                     adminNotificationTimeout specifies the interval (in
                     seconds) between retries."
              DEFVAL { 10 }
              ::= { adminNotificationEntry 5 }

          adminNotificationRetries OBJECT-TYPE
              SYNTAX INTEGER
              ACCESS read-write
              STATUS mandatory
              DESCRIPTION
                     "For traps with confirmed delivery,
                     adminNotificationRetries specifies the number of
                     retries that should be attempted before giving up
                     and trying to deliver the trap to
                     adminNotificationBackupIPAddr."
              DEFVAL { 2 }
              ::= { adminNotificationEntry 6 }

          adminNotificationBackupIPAddr OBJECT-TYPE
              SYNTAX IpAddress
              ACCESS read-write
              STATUS mandatory
              DESCRIPTION
                     "For traps with confirmed delivery,
                     adminNotificationBackupIPAddr specifies the IP
                     address of a backup station (also in
                     adminNotificationTable) to be contacted should
                     delivery of the trap to this station fail.
                     Default:  0.0.0.0  (no backup)"
              DEFVAL { '00000000'H } -- 0.0.0.0 (No backup)
              ::= { adminNotificationEntry 7 }
          adminNotificationDelete OBJECT-TYPE
              SYNTAX INTEGER
              ACCESS write-only
              STATUS mandatory
              DESCRIPTION
                     "A write (any value) causes the table entry to be
                     deleted."
              ::= { adminNotificationEntry 8 }

          adminTrapHandle OBJECT-TYPE
              SYNTAX INTEGER
              ACCESS not-accessible
              STATUS mandatory
              DESCRIPTION
                     "A unique handle that is generated for each trap
                     issued and that is passed in the trap-PDU along
                     with any other variable bindings."
              ::= { lanternAdmin 14 }

          adminTrapAcknowledge OBJECT-TYPE
              SYNTAX INTEGER
              ACCESS write-only
              STATUS mandatory
              DESCRIPTION
                     "A trap is acknowledged by writing the value of
                     adminTrapHandle passed in the trap-PDU to
                     adminTrapAcknowledge."
              ::= { lanternAdmin 15 }

          adminDownLoadFile OBJECT-TYPE
              SYNTAX OCTET STRING
              ACCESS read-write
              STATUS mandatory
              DESCRIPTION
                     "The name of the executable file to be downloaded
                     from adminDownLoadServer."
              ::= { lanternAdmin 16 }

          adminDownLoadServer OBJECT-TYPE
              SYNTAX IpAddress
              ACCESS read-write
              STATUS mandatory
              DESCRIPTION
                     "The name of the file server from which to download
                     a new executable image (adminDownLoadFile)."
              ::= { lanternAdmin 17 }

          adminDownload OBJECT-TYPE
              SYNTAX INTEGER {
                         temporaryChange(1),
                         permanentChange(2),
                         downloadSuccess(3),
                         tftpFailed(4),
                         badFile(5),
                         tftpUndefined(6),
                         tftpFileNotFound(7),
                         tftpAccessViolation(8),
                         tftpIllegalOperation(10),
                         tftpUnknownTransferID(11)
                     }
              ACCESS read-write
              STATUS mandatory
              DESCRIPTION
                     "A write to adminDownload of temporaryChange(1) or
                     permanentChange(2) causes the LANtern network
                     monitor to discontinue its normal functions and
                     perform a TFTP read of the file specified by
                     adminDownLoadFile from the server specified by
                     adminDownLoadServer into RAM.  Upon successful
                     completion of the file transfer, the new image is
                     written to the flash EPROM memory (permanentChange
                     only), destroying the previous image.  The LANtern
                     network monitor then performs a warm restart to
                     activate the new image.

                     A read of adminDownLoad returns the status of the
                     last download. The values temporaryChange(1) and
                     permanentChange(2) indicate a download is in
                     progress.  tftpFailed(4) indicates the server
                     failed to respond or the transfer timed out.
                     badFile(5)  occurs if the LANtern network monitor
                     determines the downloaded file has been corrupted
                     or is not a LANtern executable.  All other error
                     codes are the values defined by the TFTP protocol
                     [RFC 783], offset by six.

                     Note: adminDownloadFile and adminDownLoadServer
                     must be set prior (separate PDU) to setting
                     adminDownLoad."
              ::= { lanternAdmin 18 }

          adminReset OBJECT-TYPE
              SYNTAX INTEGER {
                         coldRestart(1),
                         warmRestart(2)
                     }
              ACCESS write-only
              STATUS mandatory
              DESCRIPTION
                     "A write to adminReset causes the LANtern network
                     monitor to discontinue its normal functions and
                     commence a restart sequence.  The contents of RAM,
                     including all counters and statistics, are lost.

                     A coldRestart destroys the contents of the
                     nonvolatile RAM and causes the LANtern network
                     monitor to start up exactly as if power was
                     supplied for the first time.  This is equivalent to
                     supplying power to the LANtern network monitor
                     while holding the hardware reset button depressed.

                     A warmRestart preserves the contents of the
                     nonvolatile RAM and causes the LANtern network
                     monitor to start up exactly as if the reset button
                     had been pressed (or power was being restored after
                     an outage)."
              ::= { lanternAdmin 19 }

          adminSerialDataLink OBJECT-TYPE
              SYNTAX INTEGER {
                         slip(1)
                     }
              ACCESS read-write
              STATUS mandatory
              DESCRIPTION
                     "The type of data link encapsulation to be used on
                     the serial line.  adminSerialDataLink may be
                     written at any time; however, the change does not
                     take effect until the LANtern network monitor is
                     restarted.  When adminSerialDataLink is read, it
                     returns the value currently in use, regardless of
                     any previous writes.
                     adminSerialDataLink is stored in nonvolatile RAM."
              DEFVAL { 1 } -- slip
              ::= { lanternAdmin 20 }

          adminSerialIPAddr OBJECT-TYPE
              SYNTAX IpAddress
              ACCESS read-write
              STATUS mandatory
              DESCRIPTION
                     "The IP address currently in use by the LANtern
                     network monitor on the serial channel.
                     adminSerialIPAddr may be written at any time;
                     however, the change does not take effect until the
                     LANtern network monitor is restarted.  When
                     adminSerialIPAddr is read, it returns the IP
                     address currently in use, regardless of any
                     previous writes.
                     adminSerialIPAddr is stored in nonvolatile RAM."
              DEFVAL { 'c044cd81'H } -- 192.68.205.129
              ::= { lanternAdmin 21 }

          adminSerialSubnetMask OBJECT-TYPE
              SYNTAX IpAddress
              ACCESS read-write
              STATUS mandatory
              DESCRIPTION
                     "The subnet mask for the serial channel.
                     adminSerialSubnetMask may be written at any time;
                     however, the change does not take effect until the
                     LANtern network monitor is restarted.  When this
                     variable is read, it returns the subnet mask
                     currently in use, regardless of any previous
                     writes. When the value 0.0.0.0 is stored in this
                     variable, the LANtern assumes no subnetting.
                     adminSerialSubnetMask is stored in nonvolatile
                     RAM."
              DEFVAL { 'ffffff80'H } -- 255.255.255.128
              ::= { lanternAdmin 22 }

          adminSerialBaudRate OBJECT-TYPE
              SYNTAX INTEGER {
                         baud300(1),
                         baud1200(2),
                         baud2400(3),
                         baud4800(4),
                         baud7200(5),
                         baud9600(6),
                         baud19200(7),
                         baud38400(8)
                     }
              ACCESS read-write
              STATUS mandatory
              DESCRIPTION
                     "A codification of the baud rate to be used on the
                     serial line for incoming calls or when the line is
                     directly connected.  Change does not switch line
                     speed until next state change of modem or reset.
                     adminSerialBaudRate is stored in nonvolatile RAM."
              DEFVAL { 3 } -- 2400 baud
              ::= { lanternAdmin 23 }

          adminSerialTimeout OBJECT-TYPE
              SYNTAX Seconds
              ACCESS read-write
              STATUS mandatory
              DESCRIPTION
                     "Once a phone connection has been established, the
                     LANtern network monitor maintains that connection
                     until either the other end hangs up or
                     adminSerialTimeout seconds elapses with no
                     communication.
                     adminSerialTimeout is stored in nonvolatile RAM."
              DEFVAL { 60 }
              ::= { lanternAdmin 24 }

          adminSerialConnection OBJECT-TYPE
              SYNTAX INTEGER {
                         modem(1),
                         direct(2)
                     }
              ACCESS read-write
              STATUS mandatory
              DESCRIPTION
                     "The type of connection used by the serial line.
                     adminSerialConnection may be written at any time;
                     however, the change does not take effect until the
                     LANtern network monitor is restarted. When
                     adminSerialConnection is read, it returns the value
                     currently in use, regardless of any previous
                     writes.
                     adminSerialConnection is stored in nonvolatile
                     RAM."
              DEFVAL { 1 } -- modem
              ::= { lanternAdmin 25 }

          adminSerialFlowControl OBJECT-TYPE
              SYNTAX INTEGER {
                         none(1),
                         rts-cts(2)
                     }
              ACCESS read-write
              STATUS mandatory
              DESCRIPTION
                     "The type of flow control used on the serial line.
                     adminSerialFlowControl may be written at any time;
                     however, the change does not take effect until the
                     LANtern network monitor is restarted. When
                     adminSerialFlowControl  is read, it returns the
                     value currently in use, regardless of any previous
                     writes.
                     adminSerialFlowControl is stored in nonvolatile
                     RAM."
              DEFVAL { 1 } -- No flow control
              ::= { lanternAdmin 26 }

          adminModemControl OBJECT-TYPE
              SYNTAX OCTET STRING
              ACCESS read-write
              STATUS mandatory
              DESCRIPTION
                     "A delimited string containing commands to
                     initialize, dial, and hang up the modem.  See
                     Section 3.1.2 for more details on the format of
                     this string.  adminModemControl may be written at
                     any time; however, the change does not take effect
                     until the LANtern network monitor is restarted.
                     When adminModemControl is read, it returns the
                     value currently in use, regardless of any previous
                     writes.
                     adminModemControl is stored in nonvolatile RAM."
              DEFVAL { "#^ATS0=1 Q0 V1 X4 &S1 &D2^M^1AT &W0
                     &Y0^M#^1ATDT#^2+++^2ATH0^M#" }
                     -- (Hayes-compatible commands)
              ::= { lanternAdmin 27 }

          adminModemConnect OBJECT-TYPE
              SYNTAX OCTET STRING
              ACCESS read-write
              STATUS mandatory
              DESCRIPTION
                     "A delimited string containing baud rates and modem
                     responses when it connects at particular baud
                     rates.  See Section 3.1.2 for more details on the
                     format of this string.  adminModemConnect may be
                     written at any time; however, the change does not
                     take effect until the LANtern network monitor is
                     restarted. When adminModemConnect is read, it
                     returns the value currently in use, regardless of
                     any previous writes.
                     adminModemConnect is stored in nonvolatile RAM."
              DEFVAL { "#19200#CONNECT 19200#9600#CONNECT
                     9600#4800#CONNECT 4800#2400#CONNECT
                     2400#1200#CONNECT 1200#300#CONNECT#" }
                     -- (Hayes modem compatible responses)
              ::= { lanternAdmin 28 }

          adminModemNoConnect OBJECT-TYPE
              SYNTAX OCTET STRING
              ACCESS read-write
              STATUS mandatory
              DESCRIPTION
                     "A delimited string containing baud rates and modem
                     responses when it connects at particular baud
                     rates. See Section 3 for more details on the format
                     of this string.  adminModemNoConnect may be written
                     at any time; however, the change does not take
                     effect until the LANtern network monitor is
                     restarted. When adminModemNoConnect is read, it
                     returns the value currently in use, regardless of
                     any previous writes.
                     adminModemNoConnect is stored in nonvolatile RAM."
              DEFVAL { "#NO DIALTONE#NO CARRIER#BUSY#VOICE#TIMEOUT#" }
              ::= { lanternAdmin 29 }

          adminGatewayControl OBJECT-TYPE
              SYNTAX INTEGER {
                         gateway-off(1),
                         gateway-on(2)
                     }
              ACCESS read-write
              STATUS mandatory
              DESCRIPTION
                     "A switch to enable or disable IP gatewaying
                     between the serial line and the network.
                     See Section 3 for more details on the format of
                     this string.  adminGatewayControl may be written at
                     any time; however, the change does not take effect
                     until the LANtern network monitor is restarted.
                     When adminGatewayControl is read, it returns the
                     value currently in use, regardless of any previous
                     writes.
                     adminGatewayControl is stored in nonvolatile RAM."
              DEFVAL { 1 } -- Gateway off
              ::= { lanternAdmin 30 }

          adminPhoneTable OBJECT-TYPE
              SYNTAX SEQUENCE OF AdminPhoneEntry
              ACCESS not-accessible
              STATUS mandatory
              DESCRIPTION
                     "A table that provides information about each
                     possible phone connection that can be made over the
                     serial channel.  The table is accessed by
                     adminPhoneIPAddr.  A new entry can be created by
                     writing to a nonexistent instance.  Note that
                     adminPhoneIPAddr is set implicitly from this write.
                     adminPhoneIPAddr cannot be written directly.  An
                     entry may subsequently be deleted by writing (any
                     value) to adminPhoneDelete.  See Section 3 for more
                     details about using the phone table.
                     adminPhoneTable is stored in nonvolatile RAM."
              ::= { lanternAdmin 31 }

          adminPhoneEntry OBJECT-TYPE
              SYNTAX AdminPhoneEntry
              ACCESS not-accessible
              STATUS mandatory
              DESCRIPTION
                     "Data for a particular phone connection that can be
                     established over the serial channel."
              INDEX  { adminPhoneIPAddr }
              ::= { adminPhoneTable 1 }

          AdminPhoneEntry ::=
              SEQUENCE {
                  adminPhoneIPAddr                IpAddress,
                  adminPhoneIPMask                IpAddress,
                  adminPhoneLocalIPAddr           IpAddress,
                  adminPhoneNumber                OCTET STRING,
                  adminPhoneConnectionProtocol    OCTET STRING,
                  adminPhoneDelete                INTEGER
              }

          adminPhoneIPAddr OBJECT-TYPE
              SYNTAX IpAddress
              ACCESS read-only
              STATUS mandatory
              DESCRIPTION
                     "The IP address of the machine or IP network (SLIP
                     gateway) at adminPhoneNumber."
              ::= { adminPhoneEntry 1 }

          adminPhoneIPMask OBJECT-TYPE
              SYNTAX IpAddress
              ACCESS read-write
              STATUS mandatory
              DESCRIPTION
                     "The IP subnet mask to be used when communicating
                     over this phone connection. When the value 0.0.0.0
                     is stored in this variable, the LANtern network
                     monitor assumes no subnetting.
                     Default:  0.0.0.0  (no subnetting)"
              DEFVAL { '00000000'H } -- 0.0.0.0 (No subnetting)
              ::= { adminPhoneEntry 2 }

          adminPhoneLocalIPAddr OBJECT-TYPE
              SYNTAX IpAddress
              ACCESS read-write
              STATUS mandatory
              DESCRIPTION
                     "The IP address the LANtern network monitor uses
                     for its serial port while communicating over this
                     phone connection."
              DEFVAL { '00000000'H } -- 0.0.0.0 (use adminSerialIPAddr)
              ::= { adminPhoneEntry 3 }

          adminPhoneNumber OBJECT-TYPE
              SYNTAX OCTET STRING
              ACCESS read-write
              STATUS mandatory
              DESCRIPTION
                     "The phone number string the modem uses to dial the
                     machine with IP address adminPhoneIPAddr."
              ::= { adminPhoneEntry 4 }

          adminPhoneConnectionProtocol OBJECT-TYPE
              SYNTAX OCTET STRING
              ACCESS read-write
              STATUS mandatory
              DESCRIPTION
                     "An ASCII string specifying the logon sequence once
                     the phone is connected."
              ::= { adminPhoneEntry 5 }

          adminPhoneDelete OBJECT-TYPE
              SYNTAX INTEGER
              ACCESS write-only
              STATUS mandatory
              DESCRIPTION
                     "A write (any value) causes the table entry to be
                     deleted."
              ::= { adminPhoneEntry 6 }

          adminFCBControl OBJECT-TYPE
              SYNTAX INTEGER {
				disable(1),
				enable(2)
			}		
              ACCESS read-write
              STATUS mandatory
              DESCRIPTION
                     "A switch to disable the packet capture feature.
		      To enable this flag (after disabling it) a cool
		      start must apply to the LANtern in order to gain
		      access into the administrator menu via the terminal
		      hookup to the LANtern's serial port."
	      DEFVAL { 2 } -- enable
              ::= { lanternAdmin 32 }

          END
