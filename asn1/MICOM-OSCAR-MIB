-- 
-- Version Dated: 05-31-96
--
-- 
-- MIB Revision : 1.0 dated 1-17-97
-- Change Desc. : None. 
-- 
MICOM-OSCAR-MIB DEFINITIONS ::= BEGIN
        IMPORTS
                enterprises
                                        FROM RFC1155-SMI;

-- group OBJECT IDENTIFIERs

        micom                           OBJECT IDENTIFIER ::= {enterprises 335}
        products                        OBJECT IDENTIFIER ::= {micom 1}
        micom-oscar                     OBJECT IDENTIFIER ::= {products 4}
END
