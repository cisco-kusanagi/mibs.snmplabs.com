--
-- This SMIv2 module has been generated by smidump 0.2-cvs. Do not edit.
--

SONUS-TCAP-CLIENT-SERVICES-MIB DEFINITIONS ::= BEGIN

IMPORTS
    Integer32, MODULE-IDENTITY, OBJECT-TYPE
        FROM SNMPv2-SMI
    DisplayString, RowStatus
        FROM SNMPv2-TC
    sonusServicesMIBs
        FROM SONUS-SMI
    PointCode, SonusName
        FROM SONUS-TC;

sonusTcapClientServicesMIB MODULE-IDENTITY
    LAST-UPDATED    "200102030000Z"
    ORGANIZATION    
            "Sonus Networks, Inc."
    CONTACT-INFO    
            "   Customer Support    
             Sonus Networks, Inc,
             5 carlisle Road
             Westford, MA 01886
             USA
             
             Tel: 978-692-8999
             Fax: 978-392-9118
             E-mail: cs.snmp@sonusnet.com"
    DESCRIPTION     
            "The MIB Module for TCAP Client Services Management."
    REVISION        "200010240000Z"
    DESCRIPTION     
            "This MIB was obsoleted because TCAP services have been removed from the GSX."
    ::= { sonusServicesMIBs 4 }


sonusTcapClientServicesMIBObjects OBJECT IDENTIFIER
    ::= { sonusTcapClientServicesMIB 1 }

sonusScpAdmn OBJECT IDENTIFIER
    ::= { sonusTcapClientServicesMIBObjects 1 }

sonusScpAdmnNextIndex OBJECT-TYPE
    SYNTAX          Integer32
    MAX-ACCESS      read-only
    STATUS          obsolete
    DESCRIPTION     
            "The next valid index to use when creating an entry in
             the sonusScpAdmnTable."
    ::= { sonusScpAdmn 1 }

sonusScpAdmnTable OBJECT-TYPE
    SYNTAX          SEQUENCE OF SonusScpAdmnEntry
    MAX-ACCESS      not-accessible
    STATUS          obsolete
    DESCRIPTION     
            "This table contains information about each SCP configured to 
             provide a particular TCAP application service. A management 
             			entity may create rows for SCP that are anticipated to provide
             			services in the future."
    ::= { sonusScpAdmn 2 }

sonusScpAdmnEntry OBJECT-TYPE
    SYNTAX          SonusScpAdmnEntry
    MAX-ACCESS      not-accessible
    STATUS          obsolete
    DESCRIPTION     
            "This table describes the SCPs' configurations that GSX9000 
             node has access to their services."
    INDEX           { sonusScpAdmnIndex }
    ::= { sonusScpAdmnTable 1 }

SonusScpAdmnEntry ::=
    SEQUENCE {
        sonusScpAdmnIndex               Integer32,
        sonusScpAdmnName                SonusName,
        sonusScpAdmnCarrier             DisplayString,
        sonusScpAdmnNode                DisplayString,
        sonusScpAdmnPc                  PointCode,
        sonusScpAdmnSsn                 Integer32,
        sonusScpAdmnTimeout             Integer32,
        sonusScpAdmnType                INTEGER,
        sonusScpAdmnProtocol            INTEGER,
        sonusScpAdmnState               INTEGER,
        sonusScpAdmnRowStatus           RowStatus
    }

sonusScpAdmnIndex OBJECT-TYPE
    SYNTAX          Integer32
    MAX-ACCESS      read-only
    STATUS          obsolete
    DESCRIPTION     
            "A unique value for each SCP that is between 1 and maximum
             allowed"
    ::= { sonusScpAdmnEntry 1 }

sonusScpAdmnName OBJECT-TYPE
    SYNTAX          SonusName
    MAX-ACCESS      read-write
    STATUS          obsolete
    DESCRIPTION     
            "The name of the SCP."
    ::= { sonusScpAdmnEntry 2 }

sonusScpAdmnCarrier OBJECT-TYPE
    SYNTAX          DisplayString (SIZE(1..23))
    MAX-ACCESS      read-write
    STATUS          obsolete
    DESCRIPTION     
            "The name of the carrier using this SCP. "
    ::= { sonusScpAdmnEntry 3 }

sonusScpAdmnNode OBJECT-TYPE
    SYNTAX          DisplayString (SIZE(1..23))
    MAX-ACCESS      read-write
    STATUS          obsolete
    DESCRIPTION     
            "The name of the SS7 Node connecting to this SCP. "
    ::= { sonusScpAdmnEntry 4 }

sonusScpAdmnPc OBJECT-TYPE
    SYNTAX          PointCode
    MAX-ACCESS      read-write
    STATUS          obsolete
    DESCRIPTION     
            "The point code of this SCP"
    ::= { sonusScpAdmnEntry 5 }

sonusScpAdmnSsn OBJECT-TYPE
    SYNTAX          Integer32
    MAX-ACCESS      read-write
    STATUS          obsolete
    DESCRIPTION     
            "The subsystem number of this SCP service"
    ::= { sonusScpAdmnEntry 6 }

sonusScpAdmnTimeout OBJECT-TYPE
    SYNTAX          Integer32
    MAX-ACCESS      read-write
    STATUS          obsolete
    DESCRIPTION     
            "The timeout value of this SCP service"
    ::= { sonusScpAdmnEntry 7 }

sonusScpAdmnType OBJECT-TYPE
    SYNTAX          INTEGER { tollfree(1), lnp(2), credit(3), authen(4) }
    MAX-ACCESS      read-write
    STATUS          obsolete
    DESCRIPTION     
            "The type of service of this SCP"
    ::= { sonusScpAdmnEntry 8 }

sonusScpAdmnProtocol OBJECT-TYPE
    SYNTAX          INTEGER { none(1), ain(2), inap(3) }
    MAX-ACCESS      read-write
    STATUS          obsolete
    DESCRIPTION     
            "The encoding/decoding protocol on top of TCAP"
    DEFVAL          { none }
    ::= { sonusScpAdmnEntry 9 }

sonusScpAdmnState OBJECT-TYPE
    SYNTAX          INTEGER { disabled(1), enabled(2) }
    MAX-ACCESS      read-write
    STATUS          obsolete
    DESCRIPTION     
            "The configured state of the SCP."
    DEFVAL          { disabled }
    ::= { sonusScpAdmnEntry 10 }

sonusScpAdmnRowStatus OBJECT-TYPE
    SYNTAX          RowStatus
    MAX-ACCESS      read-write
    STATUS          obsolete
    DESCRIPTION     
            ""
    ::= { sonusScpAdmnEntry 11 }

sonusScpStatTable OBJECT-TYPE
    SYNTAX          SEQUENCE OF SonusScpStatEntry
    MAX-ACCESS      not-accessible
    STATUS          obsolete
    DESCRIPTION     
            "This table contains status information about each SCP"
    ::= { sonusTcapClientServicesMIBObjects 2 }

sonusScpStatEntry OBJECT-TYPE
    SYNTAX          SonusScpStatEntry
    MAX-ACCESS      not-accessible
    STATUS          obsolete
    DESCRIPTION     
            "This table describes the SCP stat"
    INDEX           { sonusScpStatIndex }
    ::= { sonusScpStatTable 1 }

SonusScpStatEntry ::=
    SEQUENCE {
        sonusScpStatIndex               Integer32,
        sonusScpStatQueryNum            Integer32,
        sonusScpStatQueryFailed         Integer32
    }

sonusScpStatIndex OBJECT-TYPE
    SYNTAX          Integer32
    MAX-ACCESS      read-only
    STATUS          obsolete
    DESCRIPTION     
            "Identifies the SCP"
    ::= { sonusScpStatEntry 1 }

sonusScpStatQueryNum OBJECT-TYPE
    SYNTAX          Integer32
    MAX-ACCESS      read-only
    STATUS          obsolete
    DESCRIPTION     
            "The total number of queries performed at the moment"
    ::= { sonusScpStatEntry 2 }

sonusScpStatQueryFailed OBJECT-TYPE
    SYNTAX          Integer32
    MAX-ACCESS      read-only
    STATUS          obsolete
    DESCRIPTION     
            "The total number of queries failed at the moment"
    ::= { sonusScpStatEntry 3 }

END -- end of module SONUS-TCAP-CLIENT-SERVICES-MIB.
