XYLAN-ATM-MIB DEFINITIONS ::= BEGIN

     --  RCSID information

     --  $RCSfile: xylan-atm.mib,v $
     --  $Revision: 1.44 $		$State: Exp $
     --  $Date: 1998/05/07 19:45:17 $
     --  $Author: lsl $


     --  xylan-atm.mib
     --  Revision: 1.00
     --  Date: Feb 6, 1995

     --  Alcatel Internetworking, Inc.
     --  26801 W. Agoura Road
     --  Calabasas, CA 91301
     --  (818) 880-3500
     --  support@ind.alcatel.com

     --  This module provides authoritative definitions for Alcatel Internetworking, Inc.
     --  enterprise-specific atm MIB.

     --  This module will be extended, as needed.


     --  Alcatel Internetworking, Inc. reserves the right to make changes in 
     --  specification and other information contained in this document 
     --  without prior notice.  The reader should consult Alcatel Internetworking,
     --  Inc. to determine whether any such changes have been made.

     --  In no event shall Alcatel Internetworking, Inc. be liable for any incidental, 
     --  indirect, special, or consequential damages whatsoever (including 
     --  but not limited to lost profits) arising out of or related to this
     --  document or the information contained in it, even if Alcatel Internetworking,
     --  Inc. has been advised of, known, or should have known, the 
     --  possibility of such damages.
     --  Alcatel Internetworking, Inc. grants vendors, end-users, and other interested
     --  parties a non-exclusive license to use this Specification in connection
     --  with the management of Alcatel Internetworking, Inc. products.

     --  Copyright (C) 1995, Alcatel Internetworking, Inc. All Rights Reserved.

     
     	IMPORTS
		Counter, IpAddress
			FROM RFC1155-SMI
		OBJECT-TYPE
			FROM RFC-1212
		DisplayString 
			FROM RFC1213-MIB
	        xylanAtmArch
			FROM XYLAN-BASE-MIB 
		lecIndex
		        FROM LAN-EMULATION-CLIENT-MIB 			
                MacAddress
                        FROM BRIDGE-MIB
                LecDataFrameSize			
		        FROM LAN-EMULATION-CLIENT-MIB 			

			;

     -- Textual Conventions
     
     -- All representations of ATM addresses in this MIB Module use,
     -- the data type:

     -- Note this data type is used only by the deprecated object
     -- atmfPortAddress. Another definition (a refined one) is 
     -- specified in the separate MIB for Address Registration
    
     -- Object Identifier defintions

     -- The following values are defined for use as possible values
     -- of the atmfPortTransmissionType object.

	--  various type codes.

	AtmAdminStatCodes ::= INTEGER {
	    disable(1),
	    enable(2),
	    delete(3),
            create(4)
	}

	AtmOperStatCodes ::= INTEGER {
	    other(1),
       	    inService(2),
	    outOfService(3),
       	    loopBack(4)
	}

	AtmServiceOperStatCodes ::= INTEGER {
	    disable(1),
	    enabling(2),
	    enabled(3),
	    unknown(4)
	}

	AtmConnectionOperStatCodes ::= INTEGER {
	    unknown(1),
	    end2EndUp(2),
	    end2EndDown(3),
	    localUpEnd2EndUnknown(4),
	    localDown(5)
	}

	AtmTransmissionTypes ::= INTEGER {
	    unknown(1),
	    sonetSTS3c(2),
	    ds3(3),
	    atm4b5b(4), 
	    atm8b10b(5),
            e3(6),
            sonetSTS12c(7)
	}      
	
     -- The following values are defined for use as possible values
     -- of the atmfPortMediaType object.

	AtmMediaTypes ::= INTEGER {
	    unknown(1),
	    coaxCable(2),
	    singleMode(3),
	    multiMode(4), 
	    stp(5),
	    utp(6)
	}         
	
     -- The following values are defined for use as possible values
     -- of the atmxVccTransmitTrafficDescriptorType,
     -- atmxVccReceiveTrafficDescriptorType objects.

	AtmTrafficDescrTypes ::= INTEGER {
		none(1),
		peakrate(2),
		noClpNoScr(3),
		clpNoTaggingNoScr(4),
		clpTaggingNoScr(5),
		noClpScr(6),
		clpNoTaggingScr(7), 
   		clpTaggingScr(8)
 	}  		  
            
--      RowStatus ::= INTEGER {
--               up(1),
--               down(2)
--      }
     --         
     -- The following are for LAN Emulation.
     --         
   
        XylanAtmLaneAddress ::= DisplayString

        VpiInteger ::= INTEGER 

        VciInteger ::= INTEGER

        LecState ::= INTEGER {
                       initialState(1),
                       lecsConnect(2),
                       configure(3),
                       join(4),
                       initialRegistration(5),
                       busConnect(6),
                       operational(7)
                     }

        LecDataFrameFormat ::= INTEGER {
                                 unspecified(1),
                                 aflane8023(2),
                                 aflane8025(3)
                               }

--        LecDataFrameSize ::= INTEGER {
--                               unspecified(1),
--                               max1516(2),
--                               max4544(3),
--                               max9234(4),
--                               max18190(5)
--                             }

        LeArpTableEntryType ::= INTEGER {
                                  other(1),
                                  learnedViaControl(2),
                                  learnedViaData(3),
                                  staticVolatile(4),
                                  staticNonVolatile(5)
                                }

        LeArpType ::= INTEGER {
                        other(1),
                        arpRdType(2),
                        arpEsiType(3)
                       }


     --
     --                    The MIB groups
     --
     atmxPortGroup         OBJECT IDENTIFIER ::= { xylanAtmArch 1 }
     atmxServiceGroup      OBJECT IDENTIFIER ::= { xylanAtmArch 2 }
     atmxLayerStatsGroup   OBJECT IDENTIFIER ::= { xylanAtmArch 3 }
     atmxVccStatsGroup     OBJECT IDENTIFIER ::= { xylanAtmArch 4 }
     atmxVccGroup          OBJECT IDENTIFIER ::= { xylanAtmArch 5 }
     atmxAddressGroup      OBJECT IDENTIFIER ::= { xylanAtmArch 6 }
     atmxArpGroup          OBJECT IDENTIFIER ::= { xylanAtmArch 7 }
     atmxLaneGroup         OBJECT IDENTIFIER ::= { xylanAtmArch 8 }
     atmxCIPstatsGroup     OBJECT IDENTIFIER ::= { xylanAtmArch 9 }
     atmxSahiBWGroup       OBJECT IDENTIFIER ::= { xylanAtmArch 11 }
     -- ATM circuit emulation agent is dynamically loaded.  atmxCesGroup
     -- is defined in xylan-ce.mib.  Please don't use 10!
     -- atmxCesGroup         OBJECT IDENTIFIER ::= { xylanAtmArch 10 }
     -- ATM LSM agent is dynamically loaded.
     atmxLsmGroup          OBJECT IDENTIFIER ::= { xylanAtmArch 13 }

     atmx1483ScaleGroup    OBJECT IDENTIFIER ::= { xylanAtmArch 12 }
     
     --		The Port Group

     -- The Port Table

         atmxPortTable   OBJECT-TYPE
	    SYNTAX   SEQUENCE OF AtmxPortEntry 
            ACCESS   not-accessible
            STATUS   mandatory
            DESCRIPTION
            	"A table of port layer status and parameter information 
	            for the UNI's physical interface." 
            ::= { atmxPortGroup 1 }

         atmxPortEntry   OBJECT-TYPE
            SYNTAX   AtmxPortEntry
            ACCESS   not-accessible
            STATUS   mandatory
            DESCRIPTION
            	"An entry in the table, containing information about 
                the physical layer of a UNI interface."
            INDEX   { atmxPortSlotIndex, atmxPortPortIndex }
            ::= { atmxPortTable 1 }

         AtmxPortEntry ::=
             SEQUENCE {
                 atmxPortSlotIndex
                     INTEGER,
                 atmxPortPortIndex
                     INTEGER,
                 atmxPortDescription
                     DisplayString,
                 atmxPortConnectionType
                     INTEGER,
                 atmxPortTransmissionType
                     AtmTransmissionTypes,
                 atmxPortMediaType
                     AtmMediaTypes,
                 atmxPortOperStatus
               	     AtmOperStatCodes,
                 atmxPortUniType 
                     INTEGER,
                 atmxPortMaxVCCs 
                     INTEGER,
                 atmxPortMaxVciBits
                     INTEGER, 
                 atmxPortTxSegmentSize
                     INTEGER,
                 atmxPortRxSegmentSize
                     INTEGER,
                 atmxPortTxBufferSize
                     INTEGER,
                 atmxPortRxBufferSize
                     INTEGER,      
                 atmxPortUniPortIndex
                     INTEGER,
                 atmxPortAddress
                     DisplayString,
                 atmxPortSignalingVersion
                     INTEGER,
                 atmxPortSignalingVci
                     INTEGER,
                 atmxPortILMIVci
                     INTEGER, 
                 atmxPortEnableILMI
                     INTEGER,
                 atmxPortPlScramble
                     INTEGER,
                 atmxPortTimingMode
                     INTEGER, 
                 atmxPortProtocolType
                     INTEGER, 
                 atmxPortLoopbackConfig
                     INTEGER,
                 atmxPortSSCOPstatus
                     INTEGER, 
                 atmxPortILMIstatus
                     INTEGER 
         }

         atmxPortSlotIndex OBJECT-TYPE
             SYNTAX   INTEGER (1..9)
             ACCESS   read-only
             STATUS   mandatory
             DESCRIPTION
                "A unique value which identifies this hsm board slot."
             ::= { atmxPortEntry 1 }

         atmxPortPortIndex OBJECT-TYPE
             SYNTAX   INTEGER (1..2)
             ACCESS   read-only
             STATUS   mandatory
             DESCRIPTION
                "A unique value which identifies this atm submodule port."
             ::= { atmxPortEntry 2 }

         atmxPortDescription OBJECT-TYPE
             SYNTAX   DisplayString (SIZE (0..31))
             ACCESS   read-write
             STATUS   mandatory
             DESCRIPTION
                "A description for this atm port."
             ::= { atmxPortEntry 3 }

         atmxPortConnectionType OBJECT-TYPE
             SYNTAX   INTEGER { pvc(1), svc(2) }
             ACCESS   read-write
             STATUS   mandatory
             DESCRIPTION
                "The connection type of this board."
             ::= { atmxPortEntry 4 }

         atmxPortTransmissionType OBJECT-TYPE
             SYNTAX   AtmTransmissionTypes
             ACCESS   read-only
             STATUS   mandatory
             DESCRIPTION
                "The transmission type of this port. For example, for a port using
                 the Sonet STS-3c physical layer at 155.52 Mbs, this object would
                 have the Object Identifier value: atmxSonetSTS3c."
             ::= { atmxPortEntry 5 }

         atmxPortMediaType OBJECT-TYPE
             SYNTAX   AtmMediaTypes
             ACCESS   read-only
             STATUS   mandatory
             DESCRIPTION
                "The type of media being used on this port. For example for a port
                 using coaxial cable, the object would have the Object Identifier 
                 value: atmxMediaCoaxCable."
             ::= { atmxPortEntry 6 }
                             
         atmxPortOperStatus OBJECT-TYPE
             SYNTAX   AtmOperStatCodes
             ACCESS   read-only
             STATUS   mandatory
             DESCRIPTION
                "The operational state (i.e., actual) of this port.

                 The ILMI should not alarm on a physical interface for when the 
                 value of this object is outOfService(3). This capability is useful
                 if the equipment is to be disconnected, or for troubleshooting
                 purposes.

                 A value of loopBack(4) indicates that a local loopback is in place." 
             ::= { atmxPortEntry 7 }
                			                          
         atmxPortUniType OBJECT-TYPE
             SYNTAX   INTEGER { public(1), private(2) }
             ACCESS   read-write
             STATUS   mandatory
             DESCRIPTION
                "The type of the ATM UNI, either public or private." 
             ::= { atmxPortEntry 8 }

         atmxPortMaxVCCs OBJECT-TYPE
             SYNTAX   INTEGER (0..1023)
             ACCESS   read-only
             STATUS   mandatory
             DESCRIPTION
                "The maximum number of VCCs supported on this UNI." 
             ::= { atmxPortEntry 9 }
              
         atmxPortMaxVciBits OBJECT-TYPE
             SYNTAX   INTEGER (0..10)
             ACCESS   read-only
             STATUS   mandatory
             DESCRIPTION
                "The number of active VCI bits on this interface."
             ::= { atmxPortEntry 10 }

         atmxPortTxSegmentSize OBJECT-TYPE
             SYNTAX   INTEGER (2048..131072)
             ACCESS   read-write
             STATUS   mandatory
             DESCRIPTION
                "The transmit segment size on this UNI. The nearest power of two
		 less than or equal to this value will be used internally.
		The max memory is 512K, therefore the maximum number of 
		 channels will be 512K/internal tx seg size." 
             ::= { atmxPortEntry 11 }
              
         atmxPortRxSegmentSize OBJECT-TYPE
             SYNTAX   INTEGER (2048..131072)
             ACCESS   read-write
             STATUS   mandatory
             DESCRIPTION
                "The receive segment size on this UNI. The nearest power of two
		 less than or equal to this value will be used internally.
		The max memory is 512K, therefore the maximum number of 
		 channels will be 512K/internal rx seg size." 
             ::= { atmxPortEntry 12 }
              
         atmxPortTxBufferSize OBJECT-TYPE
             SYNTAX   INTEGER (1800..131072)
             ACCESS   read-write
             STATUS   mandatory
             DESCRIPTION
                "The transmit buffer size on this UNI. The buffer size must be less
                 than or equal to the segment size and should be greater than or 
                 equal to the maximum frame size."
             ::= { atmxPortEntry 13 }
              
         atmxPortRxBufferSize OBJECT-TYPE
             SYNTAX   INTEGER (1800..131072)
             ACCESS   read-write
             STATUS   mandatory
             DESCRIPTION
                "The receive buffer size on this UNI. The buffer size must be less
                 than or equal to the segment size and should be greater than or 
                 equal to the maximum frame size."
             ::= { atmxPortEntry 14 }  
                                   
         atmxPortUniPortIndex OBJECT-TYPE
             SYNTAX   INTEGER (0..2147483647) 
             ACCESS   read-only
             STATUS   deprecated
             DESCRIPTION
                "This object should not be implemented except as required for
                 backward compatibility with version 2.0 of the UNI specification.
                 This object provide a port index link to the UNI MIB"
             ::= { atmxPortEntry 15 }
                                                
         atmxPortAddress OBJECT-TYPE
             SYNTAX   DisplayString (SIZE (0..40))
             ACCESS   read-write
             STATUS   mandatory
             DESCRIPTION
                "This object should not be implemented except as required for
                 backward compatibility with version 2.0 of the UNI specification.
                 The Address Group, as defined as part of the separate Address
                 Registration MIB should be used instead."
             ::= { atmxPortEntry 16 }       
             
         atmxPortSignalingVersion OBJECT-TYPE
             SYNTAX   INTEGER { ver30(1), ver31(2) }
             ACCESS   read-write
             STATUS   mandatory
             DESCRIPTION
                "Version of the ATM forum UNI Signaling."
             ::= { atmxPortEntry 17 } 
              
         atmxPortSignalingVci OBJECT-TYPE
             SYNTAX   INTEGER (0..1023)
             ACCESS   read-write
             STATUS   mandatory
             DESCRIPTION
                "Signaling Vci."
             ::= { atmxPortEntry 18 } 
             
         atmxPortILMIVci OBJECT-TYPE
             SYNTAX   INTEGER (0..1023)
             ACCESS   read-write
             STATUS   mandatory
             DESCRIPTION
                "ILMI Vci."
             ::= { atmxPortEntry 19 }             
                         
         atmxPortEnableILMI OBJECT-TYPE
	     SYNTAX   INTEGER { false(1), true(2) }
             ACCESS   read-write
             STATUS   mandatory
             DESCRIPTION
                "ILMI Enable."
             ::= { atmxPortEntry 20 }
             
         atmxPortPlScramble OBJECT-TYPE
	     SYNTAX   INTEGER { false(1), true(2) }
             ACCESS   read-write
             STATUS   mandatory
             DESCRIPTION
                "Payload Scrambling Enable."
             ::= { atmxPortEntry 21 }
             
         atmxPortTimingMode OBJECT-TYPE
	     SYNTAX   INTEGER { loop(1), local(2) }
             ACCESS   read-write
             STATUS   mandatory
             DESCRIPTION
                "Timing mode to use. Use local timing or 
                 loop timing. "
             ::= { atmxPortEntry 22 }
             
         atmxPortProtocolType OBJECT-TYPE
	     SYNTAX   INTEGER { sonet(1), sdh(2), notApplicable(3) }
             ACCESS   read-write
             STATUS   mandatory
             DESCRIPTION
                "Physical layer protocol type. "
             ::= { atmxPortEntry 23 }
             
         atmxPortLoopbackConfig OBJECT-TYPE
             SYNTAX   INTEGER (1..5)
             ACCESS   read-write
             STATUS   mandatory
             DESCRIPTION
                "Loopback config. for this physical layer. 
                 
                    1 = NoLoop,
                    2 = DiagLoop,
                    3 = LineLoop,
                    4 = CellLoop,
                    5 = PayloadLoop "
             ::= { atmxPortEntry 24 }
             
         atmxPortSSCOPstatus OBJECT-TYPE
	     SYNTAX   INTEGER { up(1), down(2) }
             ACCESS   read-only
             STATUS   mandatory
             DESCRIPTION
                "SSCOP status of this physical layer. "
             ::= { atmxPortEntry 25 }
             
         atmxPortILMIstatus OBJECT-TYPE
	     SYNTAX   INTEGER { up(1), down(2) }
             ACCESS   read-only
             STATUS   mandatory
             DESCRIPTION
                "ILMI status of this physical layer. "
             ::= { atmxPortEntry 26 }
             
 
  --		The Service Group

     -- The Service Table

         atmxServiceTable   OBJECT-TYPE
             SYNTAX   SEQUENCE OF AtmxServiceEntry 
             ACCESS   not-accessible
             STATUS   mandatory
             DESCRIPTION
             	"A table of ATM services status and parameter information." 
             ::= { atmxServiceGroup 1 }

         atmxServiceEntry   OBJECT-TYPE
             SYNTAX   AtmxServiceEntry
             ACCESS   not-accessible
             STATUS   mandatory
             DESCRIPTION
                "An entry in the table, containing information about 
                the ATM services."
             INDEX   { atmxServiceSlotIndex, atmxServicePortIndex, atmxServiceNumber }
             ::= { atmxServiceTable 1 }

         AtmxServiceEntry ::=
             SEQUENCE {
                 atmxServiceSlotIndex
                     INTEGER,
                 atmxServicePortIndex
                     INTEGER,
                 atmxServiceNumber
                     INTEGER,
                 atmxServiceDescription
                     DisplayString,
                 atmxServiceType
                     INTEGER,
                 atmxServiceConnectionType
                     INTEGER,
                 atmxServiceOperStatus
                     AtmServiceOperStatCodes,
                 atmxServiceAdmStatus 
                     AtmAdminStatCodes,
                 atmxServiceEncapsType
                     INTEGER,
                  atmxServiceArpRequestServer
                     INTEGER,
                  atmxServiceConnections
                     OCTET STRING,
                  atmxServiceAddress
                     DisplayString,
                  atmxServiceAddresses
                     OCTET STRING,
                  atmxServiceVlan
                     OCTET STRING,
                 atmxServiceSEL
                     INTEGER,
                 atmxServiceLaneCfgTblIdx
                     INTEGER,
                 atmxServiceMulticastOutVcc
                     INTEGER,
                 atmxServiceNumVclMembers
                     INTEGER,
                 atmxServiceVclEncapType
                     INTEGER,
                 atmxServiceSahiBwgNum
                     INTEGER
		 }
 
         atmxServiceSlotIndex OBJECT-TYPE
             SYNTAX   INTEGER (1..9)
             ACCESS   read-write
             STATUS   mandatory
             DESCRIPTION
                "A unique value which identifies this hsm board slot."
             ::= { atmxServiceEntry 1 }

         atmxServicePortIndex OBJECT-TYPE
             SYNTAX   INTEGER (1..2)
             ACCESS   read-write
             STATUS   mandatory
             DESCRIPTION
                "A unique value which identifies this atm submodule port."
             ::= { atmxServiceEntry 2 }

         atmxServiceNumber	OBJECT-TYPE
	     SYNTAX   INTEGER (1..256)
             ACCESS   read-write
             STATUS   mandatory
             DESCRIPTION
                "The unique service number for this particular slot/port."
             ::= { atmxServiceEntry 3 }

         atmxServiceDescription OBJECT-TYPE
             SYNTAX   DisplayString (SIZE (0..31))
             ACCESS   read-write
             STATUS   mandatory
             DESCRIPTION
                "A description for this atm service."
             ::= { atmxServiceEntry 4 }

         atmxServiceType OBJECT-TYPE  
	     SYNTAX   INTEGER {
                lanEmulation(1),
                scaling1483(2),
                trunking(4),
                classicalIP(5),
                ptopBridging(6),
                vlanCluster(7),
		laneServiceModule(8),
		mpoaClient(9)
	     }
             ACCESS   read-write
             STATUS   mandatory
             DESCRIPTION
                "The service type.

                 For 1483 Scaling Service, create it only with 1 group 
                 and 1 vc thru this atmxServiceGroup. Adding Other group-to-vc 
                 mapping should utilize the atmx1483ScaleGroup."

             ::= { atmxServiceEntry 5 }

         atmxServiceConnectionType OBJECT-TYPE
             SYNTAX   INTEGER { pvc(1), svc(2) }
             ACCESS   read-write
             STATUS   mandatory
             DESCRIPTION
                "The connection type of this board."
             ::= { atmxServiceEntry 6 }

         atmxServiceOperStatus OBJECT-TYPE
	     SYNTAX   AtmServiceOperStatCodes
             ACCESS   read-only
             STATUS   mandatory
             DESCRIPTION
                "The service operational status."
             ::= { atmxServiceEntry 7 }

         atmxServiceAdmStatus OBJECT-TYPE
	     SYNTAX   AtmAdminStatCodes
             ACCESS   read-write
             STATUS   mandatory
             DESCRIPTION
                "The service adminstration status."
             ::= { atmxServiceEntry 8 }

	 atmxServiceEncapsType OBJECT-TYPE
	     SYNTAX   INTEGER { private(1), rfc1483(2), none(3) }
             ACCESS   read-write
             STATUS   mandatory
             DESCRIPTION
                "The service encapsulation type.  This object is
                 applicable only to PTOP service."
             ::= { atmxServiceEntry 9 }

	 atmxServiceArpRequestServer OBJECT-TYPE 
	     SYNTAX   INTEGER (0..2)
             ACCESS   read-write
             STATUS   mandatory
             DESCRIPTION
                "The Arp request server.
                    0 = not applicable,
                    1 = Non arp server,
                    2 = arp server."
             ::= { atmxServiceEntry 10 }
             
	 atmxServiceConnections	OBJECT-TYPE
	     SYNTAX   OCTET STRING (SIZE(0..512))
             ACCESS   read-write
             STATUS   mandatory
             DESCRIPTION
                "The connections for this service. Interpret this as a 16 bit
                field per connection: Trunking 1, PTOP Bridging 1, 
                Classical IP 1..255.

                For Vlan cluster, this object is interpreted as a 32 bit field 
                where each 32 bit represent the vci value of the Data Direct vcc 
                and the Multicast In vcc.  Each vcc take up 16 bits.  There can 
                be up to 32 pairs of Data Direct vcc and Mulitcast In vcc.

                For 1483 Scaling Service, create it only with 1 group 
                and 1 vc thru this atmxServiceGroup. Adding Other group-to-vc 
                mapping should utilize the atmx1483ScaleGroup."

             ::= { atmxServiceEntry 11 }

	 atmxServiceAddress OBJECT-TYPE
             SYNTAX   DisplayString (SIZE (0..40))
             ACCESS   read-write
             STATUS   mandatory
             DESCRIPTION
                "The unique service address."
             ::= { atmxServiceEntry 12 }
   
	 atmxServiceAddresses OBJECT-TYPE
	     SYNTAX   OCTET STRING (SIZE(0..512))
             ACCESS   read-write
             STATUS   mandatory
             DESCRIPTION
                "The addresses for this service. Interpret this as a 16 bit
                field per address: Trunking 1, PTOP Bridging 1, Classical IP 1..255."
             ::= { atmxServiceEntry 13 }

         atmxServiceVlan OBJECT-TYPE
	     SYNTAX   OCTET STRING (SIZE(0..64))
             ACCESS   read-write
             STATUS   mandatory
             DESCRIPTION
                "The Vlans for this service. Interpret this as a 16 bit field
                per vlan: Trunking 1-32, PTOP Bridging 1, Classical IP 1.
  
                For Vlan Cluster, it will depend on the encapsulation type
                selected.  If RFC 1483, only 1 vlan while Xylan ATM trunking
                up to 32 vlans are allowed.

                For 1483 Scaling Service, create it only with 1 group 
                and 1 vc thru this atmxServiceGroup. Adding Other group-to-vc 
                mapping should utilize the atmx1483ScaleGroup."

             ::= { atmxServiceEntry 14 }

	 atmxServiceSEL OBJECT-TYPE 
	     SYNTAX   INTEGER (1..255)
             ACCESS   read-write
             STATUS   mandatory
             DESCRIPTION
                "The SEL for the ATM address of this service."
             ::= { atmxServiceEntry 15 }
             
	 atmxServiceLaneCfgTblIdx OBJECT-TYPE 
	     SYNTAX   INTEGER (0..255)
             ACCESS   read-write
             STATUS   mandatory
             DESCRIPTION
                "Index to the LAN Emulation Configuration Table.
                 This index is only used when the Service type is 
                 ATM LAN Emulation.  For other service type this 
                 should be set to zero (0)."
             ::= { atmxServiceEntry 16 }
             
	 atmxServiceMulticastOutVcc OBJECT-TYPE 
	     SYNTAX   INTEGER (1..1023)
             ACCESS   read-write
             STATUS   mandatory
             DESCRIPTION
                "The Multicast Out VCC for this Vlan Cluster (X-LANE)
                 service.  This is only applicable to service type
                 Vlan Cluster.  For other ATM services, this object
                 will return a zero (0).  For Vlan Cluster service
                 if a zero (0) is returned means no Multicast out
                 is specified."
             ::= { atmxServiceEntry 17 }
             
	 atmxServiceNumVclMembers OBJECT-TYPE 
	     SYNTAX   INTEGER (1..32)
             ACCESS   read-write
             STATUS   mandatory
             DESCRIPTION
                "The number of other Vlan cluster members defined
                 and have a data direct VCC associated with the
                 connection.  This object is valid only for Vlan
                 cluster services.  Zero (0) will be returned for
                 other ATM services."
             ::= { atmxServiceEntry 18 }
             
	 atmxServiceVclEncapType OBJECT-TYPE 
	     SYNTAX   INTEGER (1..3)
             ACCESS   read-write
             STATUS   mandatory
             DESCRIPTION
                "The Encapsulation type for the Vlan Cluster
                 service.

                   1 = RFC 1483 encapsulation.
                   2 = Xylan ATM trunking.
                   3 = not applicable.

                 This object is only valid for Vlan cluster
                 services.  All other ATM services will return
                 a value of 3.

                 If the encapsulation type is RFC 1483, only 
                 one (1) vlan as defined in atmxServiceVlan
                 can be associated with this service.  If 
                 encapsulation type is Xylan ATM trunking more
                 than 1 vlan can be assocated with this service."
             ::= { atmxServiceEntry 19 }

	 atmxServiceSahiBwgNum OBJECT-TYPE 
	     SYNTAX   INTEGER (1..8)
             ACCESS   read-write
             STATUS   mandatory
             DESCRIPTION
                "The bwg num for sahi based hsm's. The user can set the
                 pcr, scr, mbs using the bwg table and chose the desired
                 bwg num for this service ensuring that this service obtains
                 the desired bandwidth"
             ::= { atmxServiceEntry 20 }
                              
     --		The ATM Statistics Group

     -- ATM-Layer statistics Table

         atmxLayerStatsTable   OBJECT-TYPE
             SYNTAX   SEQUENCE OF AtmxLayerStatsEntry 
             ACCESS   not-accessible
             STATUS   mandatory
             DESCRIPTION
             	"A table of ATM layer statistics information." 
             ::= { atmxLayerStatsGroup 1 }

         atmxLayerStatsEntry   OBJECT-TYPE
             SYNTAX   AtmxLayerStatsEntry
             ACCESS   not-accessible
             STATUS   mandatory
             DESCRIPTION
             	"An entry in the table, containing information about 
                the ATM layer statistics."
             INDEX   { atmxLayerStatsSlotIndex, atmxLayerStatsPortIndex }
             ::= { atmxLayerStatsTable 1 }

         AtmxLayerStatsEntry ::=
             SEQUENCE {
                 atmxLayerStatsSlotIndex
                     INTEGER,
                 atmxLayerStatsPortIndex
                     INTEGER,
                 atmxLayerStatsTxSDUs
		     Counter,
                 atmxLayerStatsTxCells
		     Counter,
		 atmxLayerStatsTxOctets
		     Counter,
                 atmxLayerStatsRxSDUs
		     Counter,
                 atmxLayerStatsRxCells
		     Counter,
                 atmxLayerStatsRxOctets
		     Counter,
                 atmxLayerStatsTxSDUDiscards
		     Counter,
                 atmxLayerStatsTxSDUErrors
		     Counter,
                 atmxLayerStatsTxSDUNoBuffers
		     Counter,
                 atmxLayerStatsTxCellDiscards
		     Counter,
                 atmxLayerStatsTxCellErrors
		     Counter,
                 atmxLayerStatsTxCellNoBuffers
		     Counter,
                 atmxLayerStatsRxSDUDiscards
		     Counter,
                 atmxLayerStatsRxSDUErrors
		     Counter,
		 atmxLayerStatsRxSDUInvalidSz
		     Counter,
                 atmxLayerStatsRxSDUNoBuffers
		     Counter,
		 atmxLayerStatsRxSDUTrash
		     Counter,
		 atmxLayerStatsRxSDUCrcErrors
		     Counter,
                 atmxLayerStatsRxCellDiscards
		     Counter,
                 atmxLayerStatsRxCellErrors
		     Counter,
                 atmxLayerStatsRxCellNoBuffers
		     Counter,
		 atmxLayerStatsRxCellTrash
		     Counter,
		 atmxLayerStatsRxCellCrcErrors
		     Counter
         }
                                               
         atmxLayerStatsSlotIndex OBJECT-TYPE
             SYNTAX   INTEGER (1..9)
             ACCESS   read-only
             STATUS   mandatory
             DESCRIPTION
                "A unique value which identifies this hsm board slot."
             ::= { atmxLayerStatsEntry 1 }

         atmxLayerStatsPortIndex OBJECT-TYPE
             SYNTAX   INTEGER (1..2)
             ACCESS   read-only
             STATUS   mandatory
             DESCRIPTION
                "A unique value which identifies this atm submodule port."
             ::= { atmxLayerStatsEntry 2 }

         atmxLayerStatsTxSDUs OBJECT-TYPE
             SYNTAX   Counter
             ACCESS   read-only
             STATUS   mandatory
             DESCRIPTION
                "The total number of successfully transmitted SDU's on the physical port."
             ::= { atmxLayerStatsEntry 3 }

         atmxLayerStatsTxCells OBJECT-TYPE
             SYNTAX   Counter
             ACCESS   read-only
             STATUS   mandatory
             DESCRIPTION
                "The total number of successfully transmitted cells."
             ::= { atmxLayerStatsEntry 4 }

	 atmxLayerStatsTxOctets OBJECT-TYPE
             SYNTAX   Counter
             ACCESS   read-only
             STATUS   mandatory
             DESCRIPTION
                "The total number of successfully transmitted octets."
             ::= { atmxLayerStatsEntry 5 }

         atmxLayerStatsRxSDUs OBJECT-TYPE
             SYNTAX   Counter
             ACCESS   read-only
             STATUS   mandatory
             DESCRIPTION
                "The total number of successfully received SDU's."
             ::= { atmxLayerStatsEntry 6 }

         atmxLayerStatsRxCells OBJECT-TYPE
             SYNTAX   Counter
             ACCESS   read-only
             STATUS   mandatory
             DESCRIPTION
                "The total number of successfully received cells."
             ::= { atmxLayerStatsEntry 7 }

         atmxLayerStatsRxOctets	OBJECT-TYPE
             SYNTAX   Counter
             ACCESS   read-only
             STATUS   mandatory
             DESCRIPTION
                "The total number of successfully received octets."
             ::= { atmxLayerStatsEntry 8 }

         atmxLayerStatsTxSDUDiscards OBJECT-TYPE
             SYNTAX   Counter
             ACCESS   read-only
             STATUS   mandatory
             DESCRIPTION
                "The total number of transmit SDUs that are discarded."
             ::= { atmxLayerStatsEntry 9 }

         atmxLayerStatsTxSDUErrors OBJECT-TYPE
             SYNTAX   Counter
             ACCESS   read-only
             STATUS   mandatory
             DESCRIPTION
                "The total number of transmit SDU with errors."
             ::= { atmxLayerStatsEntry 10 }

         atmxLayerStatsTxSDUNoBuffers OBJECT-TYPE
             SYNTAX   Counter
             ACCESS   read-only
             STATUS   mandatory
             DESCRIPTION
                "The number of transmitted SDU's with no buffers available
                on the physical port."
             ::= { atmxLayerStatsEntry 11 }

         atmxLayerStatsTxCellDiscards OBJECT-TYPE
             SYNTAX   Counter
             ACCESS   read-only
             STATUS   mandatory
             DESCRIPTION
                "The total number of transmit cells that are dicscarded."
             ::= { atmxLayerStatsEntry 12 }

         atmxLayerStatsTxCellErrors	OBJECT-TYPE
             SYNTAX   Counter
             ACCESS   read-only
             STATUS   mandatory
             DESCRIPTION
                "The total number of transmit cell with errors."
             ::= { atmxLayerStatsEntry 13 }

         atmxLayerStatsTxCellNoBuffers OBJECT-TYPE
             SYNTAX   Counter
             ACCESS   read-only
             STATUS   mandatory
             DESCRIPTION
                "The total number of transmit cell with no buffers available."
             ::= { atmxLayerStatsEntry 14 }

         atmxLayerStatsRxSDUDiscards OBJECT-TYPE
             SYNTAX   Counter
             ACCESS   read-only
             STATUS   mandatory
             DESCRIPTION
                "The total number of receive SDU's that are discarded."
             ::= { atmxLayerStatsEntry 15 }

         atmxLayerStatsRxSDUErrors OBJECT-TYPE
             SYNTAX   Counter
             ACCESS   read-only
             STATUS   mandatory
             DESCRIPTION
                "The total number of receive SDU's with errors."
             ::= { atmxLayerStatsEntry 16 }

	 atmxLayerStatsRxSDUInvalidSz OBJECT-TYPE
             SYNTAX   Counter
             ACCESS   read-only
             STATUS   mandatory
             DESCRIPTION
                "The total number of receive SDU's with invalid size"
             ::= { atmxLayerStatsEntry 17 }

         atmxLayerStatsRxSDUNoBuffers OBJECT-TYPE
             SYNTAX   Counter
             ACCESS   read-only
             STATUS   mandatory
             DESCRIPTION
                "The total number of receive SDU's with no buffers"
             ::= { atmxLayerStatsEntry 18 }

	 atmxLayerStatsRxSDUTrash OBJECT-TYPE
             SYNTAX   Counter
             ACCESS   read-only
             STATUS   mandatory
             DESCRIPTION
                "The total number of receive trash SDU's"
             ::= { atmxLayerStatsEntry 19 }

	 atmxLayerStatsRxSDUCrcErrors OBJECT-TYPE
             SYNTAX   Counter
             ACCESS   read-only
             STATUS   mandatory
             DESCRIPTION
                "The total number of receive SDU's with crc errors"
             ::= { atmxLayerStatsEntry 20 }

         atmxLayerStatsRxCellDiscards OBJECT-TYPE
             SYNTAX   Counter
             ACCESS   read-only
             STATUS   mandatory
             DESCRIPTION
                "The total number of receive cells that are discarded."
             ::= { atmxLayerStatsEntry 21 }

         atmxLayerStatsRxCellErrors	OBJECT-TYPE
             SYNTAX   Counter
             ACCESS   read-only
             STATUS   mandatory
             DESCRIPTION
                "The total number of recieve cell with errors"
             ::= { atmxLayerStatsEntry 22 }

         atmxLayerStatsRxCellNoBuffers OBJECT-TYPE
             SYNTAX   Counter
             ACCESS   read-only
             STATUS   mandatory
             DESCRIPTION
                "The total number of receive cell with no buffers"
             ::= { atmxLayerStatsEntry 23 }

		 atmxLayerStatsRxCellTrash OBJECT-TYPE
             SYNTAX   Counter
             ACCESS   read-only
             STATUS   mandatory
             DESCRIPTION
                "The total number of recieve trash cells."
             ::= { atmxLayerStatsEntry 24 }

		 atmxLayerStatsRxCellCrcErrors OBJECT-TYPE
             SYNTAX   Counter
             ACCESS   read-only
             STATUS   mandatory
             DESCRIPTION
                "The total number of receive cells with crc errors."
             ::= { atmxLayerStatsEntry 25 }
        

    -- ATM-Virtual Channel connection statistics Table

         atmxVccStatsTable   OBJECT-TYPE
             SYNTAX   SEQUENCE OF AtmxVccStatsEntry 
             ACCESS   not-accessible
             STATUS   mandatory
             DESCRIPTION
             	"A table of ATM virtual channel connection statistics information." 
             ::= { atmxVccStatsGroup 1 }

         atmxVccStatsEntry   OBJECT-TYPE
             SYNTAX   AtmxVccStatsEntry
             ACCESS   not-accessible
             STATUS   mandatory
             DESCRIPTION
                "An entry in the table, containing information about 
                the ATM virtual channel connection statistics."
             INDEX   { atmxVccStatsSlotIndex, atmxVccStatsPortIndex, atmxVccStatsVci }
             ::= { atmxVccStatsTable 1 }

         AtmxVccStatsEntry ::=
             SEQUENCE {
                 atmxVccStatsSlotIndex
                     INTEGER,
                 atmxVccStatsPortIndex
                     INTEGER,
                 atmxVccStatsVci
		     INTEGER,
                 atmxVccStatsTxSDUs
		     Counter,
                 atmxVccStatsTxCells
		     Counter,
		 atmxVccStatsTxOctets
		     Counter,
                 atmxVccStatsRxSDUs
		     Counter,
                 atmxVccStatsRxCells
		     Counter,
                 atmxVccStatsRxOctets
		     Counter,
                 atmxVccStatsTxSDUDiscards
		     Counter,
                 atmxVccStatsTxSDUErrors
		     Counter,
                 atmxVccStatsTxSDUNoBuffers
		     Counter,
                 atmxVccStatsTxCellDiscards
		     Counter,
                 atmxVccStatsTxCellErrors
		     Counter,
                 atmxVccStatsTxCellNoBuffers
		     Counter,
                 atmxVccStatsRxSDUDiscards
		     Counter,
                 atmxVccStatsRxSDUErrors
		     Counter,
		 atmxVccStatsRxSDUInvalidSz
		     Counter,
                 atmxVccStatsRxSDUNoBuffers
		     Counter,
		 atmxVccStatsRxSDUTrash
		     Counter,
		 atmxVccStatsRxSDUCrcErrors
		     Counter,
                 atmxVccStatsRxCellDiscards
		     Counter,
                 atmxVccStatsRxCellErrors
		     Counter,
                 atmxVccStatsRxCellNoBuffers
		     Counter,
		 atmxVccStatsRxCellTrash
		     Counter,
		 atmxVccStatsRxCellCrcErrors
		     Counter
         }
                                                                                        

         atmxVccStatsSlotIndex OBJECT-TYPE
             SYNTAX   INTEGER (1..9)
             ACCESS   read-only
             STATUS   mandatory
             DESCRIPTION
                "A unique value which identifies this hsm board slot."
             ::= { atmxVccStatsEntry 1 }

         atmxVccStatsPortIndex OBJECT-TYPE
             SYNTAX   INTEGER (1..2)
             ACCESS   read-only
             STATUS   mandatory
             DESCRIPTION
                "A unique value which identifies this atm submodule port."
             ::= { atmxVccStatsEntry 2 }

         atmxVccStatsVci OBJECT-TYPE  
             SYNTAX   INTEGER (1..1024)
             ACCESS   read-only
             STATUS   mandatory
             DESCRIPTION
                "A unique value which identifies this atm port."
             ::= { atmxVccStatsEntry 3 }

         atmxVccStatsTxSDUs OBJECT-TYPE
             SYNTAX   Counter
             ACCESS   read-only
             STATUS   mandatory
             DESCRIPTION
                "The total number of transmitted SDU's on this virtual channel."
             ::= { atmxVccStatsEntry 4 }

         atmxVccStatsTxCells OBJECT-TYPE
             SYNTAX   Counter
             ACCESS   read-only
             STATUS   mandatory
             DESCRIPTION
                "The total number of transmitted cells on this virtual channel."
             ::= { atmxVccStatsEntry 5 }

	 atmxVccStatsTxOctets OBJECT-TYPE
             SYNTAX   Counter
             ACCESS   read-only
             STATUS   mandatory
             DESCRIPTION
                "The total number of transmitted octets on this virtual channel."
             ::= { atmxVccStatsEntry 6 }

         atmxVccStatsRxSDUs OBJECT-TYPE
             SYNTAX   Counter
             ACCESS   read-only
             STATUS   mandatory
             DESCRIPTION
                "The total number of received SDU's on this virtual channel."
             ::= { atmxVccStatsEntry 7 }

         atmxVccStatsRxCells OBJECT-TYPE
             SYNTAX   Counter
             ACCESS   read-only
             STATUS   mandatory
             DESCRIPTION
                "The total number of received cells on this virtual channel."
             ::= { atmxVccStatsEntry 8 }

         atmxVccStatsRxOctets	OBJECT-TYPE
             SYNTAX   Counter
             ACCESS   read-only
             STATUS   mandatory
             DESCRIPTION
                "The total number of received octets on this virtual channel."
             ::= { atmxVccStatsEntry 9 }

         atmxVccStatsTxSDUDiscards OBJECT-TYPE
             SYNTAX   Counter
             ACCESS   read-only
             STATUS   mandatory
             DESCRIPTION
                "The total number of transmit SDU discards on 
                this virtual channel."
             ::= { atmxVccStatsEntry 10 }	 
         atmxVccStatsTxSDUErrors OBJECT-TYPE
             SYNTAX   Counter
             ACCESS   read-only
             STATUS   mandatory
             DESCRIPTION
                "The total number of transmit SDU errors on 
                this virtual channel."
             ::= { atmxVccStatsEntry 11 }

         atmxVccStatsTxSDUNoBuffers OBJECT-TYPE
             SYNTAX   Counter
             ACCESS   read-only
             STATUS   mandatory
             DESCRIPTION
                "The number of transmit SDU's with no buffers on 
                this virtual channel."
             ::= { atmxVccStatsEntry 12 }

         atmxVccStatsTxCellDiscards OBJECT-TYPE
             SYNTAX   Counter
             ACCESS   read-only
             STATUS   mandatory
             DESCRIPTION
                "The total number of transmit cells that are dicscarded on 
                this virtual channel."
             ::= { atmxVccStatsEntry 13 }

         atmxVccStatsTxCellErrors OBJECT-TYPE
             SYNTAX   Counter
             ACCESS   read-only
             STATUS   mandatory
             DESCRIPTION
                "The total number of transmit cell with errors on 
                this virtual channel."
             ::= { atmxVccStatsEntry 14 }

         atmxVccStatsTxCellNoBuffers OBJECT-TYPE
             SYNTAX   Counter
             ACCESS   read-only
             STATUS   mandatory
             DESCRIPTION
                "The total number of transmit cell with no buffers on 
                this virtual channel."
             ::= { atmxVccStatsEntry 15 }

         atmxVccStatsRxSDUDiscards OBJECT-TYPE
             SYNTAX   Counter
             ACCESS   read-only
             STATUS   mandatory
             DESCRIPTION
                "The total number of receive SDU's discarded on 
                this virtual channel."
             ::= { atmxVccStatsEntry 16 }

         atmxVccStatsRxSDUErrors OBJECT-TYPE
             SYNTAX   Counter
             ACCESS   read-only
             STATUS   mandatory
             DESCRIPTION
                "The total number of receive SDU's with errors on 
                this virtual channel."
             ::= { atmxVccStatsEntry 17 }

	 atmxVccStatsRxSDUInvalidSz OBJECT-TYPE
             SYNTAX   Counter
             ACCESS   read-only
             STATUS   mandatory
             DESCRIPTION
                "The total number of received SDU's with invalid size 
                on this virtual channel."
             ::= { atmxVccStatsEntry 18 }

         atmxVccStatsRxSDUNoBuffers OBJECT-TYPE
             SYNTAX   Counter
             ACCESS   read-only
             STATUS   mandatory
             DESCRIPTION
                "The total number of receive SDU's with no buffers
                on this virtual channel."
             ::= { atmxVccStatsEntry 19 }

		 atmxVccStatsRxSDUTrash OBJECT-TYPE
             SYNTAX   Counter
             ACCESS   read-only
             STATUS   mandatory
             DESCRIPTION
                "The total number of receive trash SDU's on 
                this virtual channel."
             ::= { atmxVccStatsEntry 20 }

	 atmxVccStatsRxSDUCrcErrors OBJECT-TYPE
             SYNTAX   Counter
             ACCESS   read-only
             STATUS   mandatory
             DESCRIPTION
                "The total number of receive SDU's crc errors on 
                this virtual channel."
             ::= { atmxVccStatsEntry 21 }

         atmxVccStatsRxCellDiscards OBJECT-TYPE
             SYNTAX   Counter
             ACCESS   read-only
             STATUS   mandatory
             DESCRIPTION
                "The total number of receive cells discarded 
                on this virtual channel."
             ::= { atmxVccStatsEntry 22 }

         atmxVccStatsRxCellErrors OBJECT-TYPE
             SYNTAX   Counter
             ACCESS   read-only
             STATUS   mandatory
             DESCRIPTION
                "The total number of recieve cell with errors on 
                this virtual channel."
             ::= { atmxVccStatsEntry 23 }

         atmxVccStatsRxCellNoBuffers OBJECT-TYPE
             SYNTAX   Counter
             ACCESS   read-only
             STATUS   mandatory
             DESCRIPTION
                "The total number of receive cells with no buffers 
                on this virtual channel."
             ::= { atmxVccStatsEntry 24 }

	 atmxVccStatsRxCellTrash OBJECT-TYPE
             SYNTAX   Counter
             ACCESS   read-only
             STATUS   mandatory
             DESCRIPTION
                "The total number of recieve trash cells on 
                this virtual channel."
             ::= { atmxVccStatsEntry 25 }

	 atmxVccStatsRxCellCrcErrors OBJECT-TYPE
             SYNTAX   Counter
             ACCESS   read-only
             STATUS   mandatory
             DESCRIPTION
                "The total number of receive cells with crc errors 
                on this virtual channel."
             ::= { atmxVccStatsEntry 26 }
 

     --		The Virtual Channel Connections Group

     -- The Virtual Channel Connections Table

         atmxVccTable   OBJECT-TYPE
             SYNTAX   SEQUENCE OF AtmxVccEntry 
             ACCESS   not-accessible
             STATUS   mandatory
             DESCRIPTION
                "A table of ATM virtual channel connections status and 
                parameter information." 
                ::= { atmxVccGroup 1 }

         atmxVccEntry   OBJECT-TYPE
             SYNTAX   AtmxVccEntry
             ACCESS   not-accessible
             STATUS   mandatory
             DESCRIPTION
                "An entry in the table, containing information about 
                the ATM virtual channel connections."
             INDEX   { atmxVccSlotIndex, atmxVccPortIndex, atmxVccVci}
                ::= { atmxVccTable 1 }

         AtmxVccEntry ::=
             SEQUENCE {
                 atmxVccSlotIndex
                     INTEGER,
                 atmxVccPortIndex
                     INTEGER,
		 atmxVccVpi
		     INTEGER,
		 atmxVccVci
		     INTEGER,
                 atmxVccDescription
                     DisplayString,
		 atmxVccConnType
		     INTEGER,
		 atmxVccCircuitType
		     INTEGER,
		 atmxVccOperStatus
                     AtmConnectionOperStatCodes,
		 atmxVccUpTime
		     DisplayString,
		 atmxVccDownTime
		     DisplayString,
		 atmxVccTransmitMaxFrameSize
		     INTEGER, 
		 atmxVccReceiveMaxFrameSize
		     INTEGER,
		 atmxVccRequestedTransmitTrafficDescriptor
		     AtmTrafficDescrTypes,
		 atmxVccRequestedTransmitTrafficDescriptorParam1
		     INTEGER,
		 atmxVccRequestedTransmitTrafficDescriptorParam2
		     INTEGER,
		 atmxVccRequestedTransmitTrafficDescriptorParam3
		     INTEGER,
		 atmxVccRequestedTransmitTrafficQoSClass
		     INTEGER,
		 atmxVccRequestedTransmitTrafficBestEffort
		     INTEGER,
		 atmxVccRequestedReceiveTrafficDescriptor
		     AtmTrafficDescrTypes,
		 atmxVccRequestedReceiveTrafficDescriptorParam1
		     INTEGER,
		 atmxVccRequestedReceiveTrafficDescriptorParam2
		     INTEGER,
		 atmxVccRequestedReceiveTrafficDescriptorParam3
		     INTEGER,
		 atmxVccRequestedReceiveTrafficQoSClass
		     INTEGER,
		 atmxVccRequestedReceiveTrafficBestEffort
		     INTEGER,
		 atmxVccAcceptableTransmitTrafficDescriptor
		     AtmTrafficDescrTypes,
		 atmxVccAcceptableTransmitTrafficDescriptorParam1
		     INTEGER,
		 atmxVccAcceptableTransmitTrafficDescriptorParam2
		     INTEGER,
		 atmxVccAcceptableTransmitTrafficDescriptorParam3
		     INTEGER,
		 atmxVccAcceptableTransmitTrafficQoSClass
		     INTEGER,
		 atmxVccAcceptableTransmitTrafficBestEffort
		     INTEGER,
		 atmxVccAcceptableReceiveTrafficDescriptor
		     AtmTrafficDescrTypes,
		 atmxVccAcceptableReceiveTrafficDescriptorParam1
		     INTEGER,
		 atmxVccAcceptableReceiveTrafficDescriptorParam2
		     INTEGER,
		 atmxVccAcceptableReceiveTrafficDescriptorParam3
		     INTEGER,
		 atmxVccAcceptableReceiveTrafficQoSClass
		     INTEGER,
		 atmxVccAcceptableReceiveTrafficBestEffort
		     INTEGER,
		 atmxVccActualTransmitTrafficDescriptor
		     AtmTrafficDescrTypes,
		 atmxVccActualTransmitTrafficDescriptorParam1
		     INTEGER,
		 atmxVccActualTransmitTrafficDescriptorParam2
		     INTEGER,
		 atmxVccActualTransmitTrafficDescriptorParam3
		     INTEGER,
		 atmxVccActualTransmitTrafficQoSClass
		     INTEGER,
		 atmxVccActualTransmitTrafficBestEffort
		     INTEGER,
		 atmxVccActualReceiveTrafficDescriptor
		     AtmTrafficDescrTypes,
		 atmxVccActualReceiveTrafficDescriptorParam1
		     INTEGER,
		 atmxVccActualReceiveTrafficDescriptorParam2
		     INTEGER,
		 atmxVccActualReceiveTrafficDescriptorParam3
		     INTEGER,
		 atmxVccActualReceiveTrafficQoSClass
		     INTEGER,
		 atmxVccActualReceiveTrafficBestEffort
		     INTEGER,
                 atmxVccAdmStatus 
                     AtmAdminStatCodes,
		 atmxVccServiceUsed
		     INTEGER,
		 atmxVccConnectionUsed
		     INTEGER
         }
                        
         atmxVccSlotIndex OBJECT-TYPE
             SYNTAX   INTEGER (1..9)
             ACCESS   read-write
             STATUS   mandatory
             DESCRIPTION
                "A unique value which identifies this hsm board slot."
             ::= { atmxVccEntry 1 }

         atmxVccPortIndex OBJECT-TYPE
             SYNTAX   INTEGER (1..2)
             ACCESS   read-write
             STATUS   mandatory
             DESCRIPTION
                "A unique value which identifies this atm submodule port."
             ::= { atmxVccEntry 2 }

	 atmxVccVpi OBJECT-TYPE
	     SYNTAX   INTEGER (0..0)
             ACCESS   read-only
             STATUS   mandatory
             DESCRIPTION
                "The virtual path identifier associated with this 
                virtual connection."
             ::= { atmxVccEntry 3 }

	 atmxVccVci OBJECT-TYPE
	     SYNTAX   INTEGER (1..1023)
             ACCESS   read-write
             STATUS   mandatory
             DESCRIPTION
                "The virtual channel identifier associated with the 
                virtual connection."
             ::= { atmxVccEntry 4 }

         atmxVccDescription OBJECT-TYPE
             SYNTAX   DisplayString (SIZE (0..31))
             ACCESS   read-write
             STATUS   mandatory
             DESCRIPTION
                "A description for this virtual connection."
             ::= { atmxVccEntry 5 }

	 atmxVccConnType OBJECT-TYPE
	     SYNTAX   INTEGER { vcc(1), vpc(2) }
             ACCESS   read-write
             STATUS   mandatory
             DESCRIPTION
                "The virtual connection type."
             ::= { atmxVccEntry 6 }

	 atmxVccCircuitType OBJECT-TYPE
	     SYNTAX   INTEGER {	pvc(1), svc(2) }
             ACCESS   read-write
             STATUS   mandatory
             DESCRIPTION
	        "The virtual connection circuit type."
             ::= { atmxVccEntry 7 }

	 atmxVccOperStatus OBJECT-TYPE
	     SYNTAX   AtmConnectionOperStatCodes
             ACCESS   read-only
             STATUS   mandatory
             DESCRIPTION
	        "The actual operational status of the VCC
		        
	        A value of end2endUp(2) or end2endDown(3) would be used if end-to-end
	        status is known. If only local status information is available, a value
	        of localUpEnd2endUnknown(4) or localDown(5) would be used."
             ::= { atmxVccEntry 8 }

	 atmxVccUpTime OBJECT-TYPE
             SYNTAX   DisplayString (SIZE (0..31))
             ACCESS   read-only
             STATUS   mandatory
             DESCRIPTION
	        "The virtual channel connection up time for this connection."
             ::= { atmxVccEntry 9 }

	 atmxVccDownTime OBJECT-TYPE
             SYNTAX   DisplayString (SIZE (0..31))
             ACCESS   read-only
             STATUS   mandatory
             DESCRIPTION
     		"The virtual channel connection down time for this connection."
             ::= { atmxVccEntry 10 }

	 atmxVccTransmitMaxFrameSize OBJECT-TYPE
	     SYNTAX   INTEGER (0..353208)
             ACCESS   read-write
             STATUS   mandatory
             DESCRIPTION
	        "The virtual channel connection maximum transmit frame size
		for this connection."
             ::= { atmxVccEntry 11 }

	 atmxVccReceiveMaxFrameSize OBJECT-TYPE
	     SYNTAX   INTEGER (64..32678)
             ACCESS   read-write
             STATUS   mandatory
             DESCRIPTION
	        "The virtual channel connection maximum receive frame size
		for this connection."
             ::= { atmxVccEntry 12 }

	 atmxVccRequestedTransmitTrafficDescriptor OBJECT-TYPE
	     SYNTAX   AtmTrafficDescrTypes
             ACCESS   read-write
             STATUS   mandatory
             DESCRIPTION
	        "The virtual channel connection traffic descriptor
		for this connection."
             ::= { atmxVccEntry 13 }

	 atmxVccRequestedTransmitTrafficDescriptorParam1 OBJECT-TYPE
  	     SYNTAX   INTEGER (0..353208)
             ACCESS   read-write
             STATUS   mandatory
             DESCRIPTION
	       "The virtual channel connection traffic parameter 1
		for this connection."
             ::= { atmxVccEntry 14 }

	 atmxVccRequestedTransmitTrafficDescriptorParam2 OBJECT-TYPE
 	     SYNTAX   INTEGER (0..353208)
             ACCESS   read-write
             STATUS   mandatory
             DESCRIPTION
	       "The virtual channel connection traffic parameter 2
		for this connection."
             ::= { atmxVccEntry 15 }

	 atmxVccRequestedTransmitTrafficDescriptorParam3 OBJECT-TYPE
	     SYNTAX   INTEGER (0..353208)
             ACCESS   read-write
             STATUS   mandatory
             DESCRIPTION
	       "The virtual channel connection traffic parameter 3
		for this connection."
             ::= { atmxVccEntry 16 }

	 atmxVccRequestedTransmitTrafficQoSClass	OBJECT-TYPE
	     SYNTAX   INTEGER (0..4)
             ACCESS   read-write
             STATUS   mandatory
             DESCRIPTION
	        "The virtual channel connection QOS Class for this connection."
             ::= { atmxVccEntry 17 }

	 atmxVccRequestedTransmitTrafficBestEffort OBJECT-TYPE
	     SYNTAX   INTEGER { false(1), true(2) }
             ACCESS   read-write
             STATUS   mandatory
             DESCRIPTION
	        "The virtual channel connection best effort value 
		for this connection."
             ::= { atmxVccEntry 18 }

	 atmxVccRequestedReceiveTrafficDescriptor OBJECT-TYPE
	     SYNTAX   AtmTrafficDescrTypes
             ACCESS   read-write
             STATUS   mandatory
             DESCRIPTION
	       	"The virtual channel connection traffic descriptor
		for this connection."
             ::= { atmxVccEntry 19 }

	 atmxVccRequestedReceiveTrafficDescriptorParam1 OBJECT-TYPE
	     SYNTAX   INTEGER (0..353208)
             ACCESS   read-write
             STATUS   mandatory
             DESCRIPTION
	        "The virtual channel connection traffic parameter 1
		for this connection."
             ::= { atmxVccEntry 20 }

	 atmxVccRequestedReceiveTrafficDescriptorParam2 OBJECT-TYPE
  	     SYNTAX   INTEGER (0..353208)
             ACCESS   read-write
             STATUS   mandatory
             DESCRIPTION
	        "The virtual channel connection traffic parameter 2
		for this connection."
             ::= { atmxVccEntry 21 }

	 atmxVccRequestedReceiveTrafficDescriptorParam3 OBJECT-TYPE
	     SYNTAX   INTEGER (0..353208)
             ACCESS   read-write
             STATUS   mandatory
             DESCRIPTION
	        "The virtual channel connection traffic parameter 3
		for this connection."
             ::= { atmxVccEntry 22 }

	 atmxVccRequestedReceiveTrafficQoSClass OBJECT-TYPE
	     SYNTAX   INTEGER (0..4)
             ACCESS   read-write
             STATUS   mandatory
             DESCRIPTION
	       	"The virtual channel connection traffic QOS Class 
	        for this connection."
             ::= { atmxVccEntry 23 }

	 atmxVccRequestedReceiveTrafficBestEffort OBJECT-TYPE
	     SYNTAX   INTEGER { false(1), true(2) }
             ACCESS   read-write
             STATUS   mandatory
             DESCRIPTION
	       	"The virtual channel connection best effort value
		for this connection."
             ::= { atmxVccEntry 24 }

	 atmxVccAcceptableTransmitTrafficDescriptor OBJECT-TYPE
	     SYNTAX   AtmTrafficDescrTypes
             ACCESS   read-write
             STATUS   mandatory
             DESCRIPTION
	        "The virtual channel connection traffic descriptor
		for this connection."
             ::= { atmxVccEntry 25 }

	 atmxVccAcceptableTransmitTrafficDescriptorParam1 OBJECT-TYPE
  	     SYNTAX   INTEGER (0..353208)
             ACCESS   read-write
             STATUS   mandatory
             DESCRIPTION
	       "The virtual channel connection traffic parameter 1
		for this connection."
             ::= { atmxVccEntry 26 }

	 atmxVccAcceptableTransmitTrafficDescriptorParam2 OBJECT-TYPE
 	     SYNTAX   INTEGER (0..353208)
             ACCESS   read-write
             STATUS   mandatory
             DESCRIPTION
	       "The virtual channel connection traffic parameter 2
		for this connection."
             ::= { atmxVccEntry 27 }

	 atmxVccAcceptableTransmitTrafficDescriptorParam3 OBJECT-TYPE
	     SYNTAX   INTEGER (0..353208)
             ACCESS   read-write
             STATUS   mandatory
             DESCRIPTION
	       "The virtual channel connection traffic parameter 3
		for this connection."
             ::= { atmxVccEntry 28 }

	 atmxVccAcceptableTransmitTrafficQoSClass	OBJECT-TYPE
	     SYNTAX   INTEGER (0..4)
             ACCESS   read-write
             STATUS   mandatory
             DESCRIPTION
	        "The virtual channel connection QOS Class for this connection."
             ::= { atmxVccEntry 29 }

	 atmxVccAcceptableTransmitTrafficBestEffort OBJECT-TYPE
	     SYNTAX   INTEGER { false(1), true(2) }
             ACCESS   read-write
             STATUS   mandatory
             DESCRIPTION
	        "The virtual channel connection best effort value 
		for this connection."
             ::= { atmxVccEntry 30 }

	 atmxVccAcceptableReceiveTrafficDescriptor OBJECT-TYPE
	     SYNTAX   AtmTrafficDescrTypes
             ACCESS   read-write
             STATUS   mandatory
             DESCRIPTION
	       	"The virtual channel connection traffic descriptor
		for this connection."
             ::= { atmxVccEntry 31 }

	 atmxVccAcceptableReceiveTrafficDescriptorParam1 OBJECT-TYPE
	     SYNTAX   INTEGER (0..353208)
             ACCESS   read-write
             STATUS   mandatory
             DESCRIPTION
	        "The virtual channel connection traffic parameter 1
		for this connection."
             ::= { atmxVccEntry 32 }

	 atmxVccAcceptableReceiveTrafficDescriptorParam2 OBJECT-TYPE
  	     SYNTAX   INTEGER (0..353208)
             ACCESS   read-write
             STATUS   mandatory
             DESCRIPTION
	        "The virtual channel connection traffic parameter 2
		for this connection."
             ::= { atmxVccEntry 33 }

	 atmxVccAcceptableReceiveTrafficDescriptorParam3 OBJECT-TYPE
	     SYNTAX   INTEGER (0..353208)
             ACCESS   read-write
             STATUS   mandatory
             DESCRIPTION
	        "The virtual channel connection traffic parameter 3
		for this connection."
             ::= { atmxVccEntry 34 }

	 atmxVccAcceptableReceiveTrafficQoSClass OBJECT-TYPE
	     SYNTAX   INTEGER (0..4)
             ACCESS   read-write
             STATUS   mandatory
             DESCRIPTION
	       	"The virtual channel connection traffic QOS Class 
	        for this connection."
             ::= { atmxVccEntry 35 }

	 atmxVccAcceptableReceiveTrafficBestEffort OBJECT-TYPE
	     SYNTAX   INTEGER { false(1), true(2) }
             ACCESS   read-write
             STATUS   mandatory
             DESCRIPTION
	       	"The virtual channel connection best effort value
		for this connection."
             ::= { atmxVccEntry 36 }

	 atmxVccActualTransmitTrafficDescriptor OBJECT-TYPE
	     SYNTAX   AtmTrafficDescrTypes
             ACCESS   read-only
             STATUS   mandatory
             DESCRIPTION
	        "The virtual channel connection traffic descriptor
		for this connection."
             ::= { atmxVccEntry 37 }

	 atmxVccActualTransmitTrafficDescriptorParam1 OBJECT-TYPE
  	     SYNTAX   INTEGER (0..353208)
             ACCESS   read-only
             STATUS   mandatory
             DESCRIPTION
	       "The virtual channel connection traffic parameter 1
		for this connection."
             ::= { atmxVccEntry 38 }

	 atmxVccActualTransmitTrafficDescriptorParam2 OBJECT-TYPE
 	     SYNTAX   INTEGER (0..353208)
             ACCESS   read-only
             STATUS   mandatory
             DESCRIPTION
	       "The virtual channel connection traffic parameter 2
		for this connection."
             ::= { atmxVccEntry 39 }

	 atmxVccActualTransmitTrafficDescriptorParam3 OBJECT-TYPE
	     SYNTAX   INTEGER (0..353208)
             ACCESS   read-only
             STATUS   mandatory
             DESCRIPTION
	       "The virtual channel connection traffic parameter 3
		for this connection."
             ::= { atmxVccEntry 40 }

	 atmxVccActualTransmitTrafficQoSClass	OBJECT-TYPE
	     SYNTAX   INTEGER (0..4)
             ACCESS   read-only
             STATUS   mandatory
             DESCRIPTION
	        "The virtual channel connection QOS Class for this connection."
             ::= { atmxVccEntry 41 }

	 atmxVccActualTransmitTrafficBestEffort OBJECT-TYPE
	     SYNTAX   INTEGER { false(1), true(2) }
             ACCESS   read-only
             STATUS   mandatory
             DESCRIPTION
	        "The virtual channel connection best effort value 
		for this connection."
             ::= { atmxVccEntry 42 }

	 atmxVccActualReceiveTrafficDescriptor OBJECT-TYPE
	     SYNTAX   AtmTrafficDescrTypes
             ACCESS   read-only
             STATUS   mandatory
             DESCRIPTION
	       	"The virtual channel connection traffic descriptor
		for this connection."
             ::= { atmxVccEntry 43 }

	 atmxVccActualReceiveTrafficDescriptorParam1 OBJECT-TYPE
	     SYNTAX   INTEGER (0..353208)
             ACCESS   read-only
             STATUS   mandatory
             DESCRIPTION
	        "The virtual channel connection traffic parameter 1
		for this connection."
             ::= { atmxVccEntry 44 }

	 atmxVccActualReceiveTrafficDescriptorParam2 OBJECT-TYPE
  	     SYNTAX   INTEGER (0..353208)
             ACCESS   read-only
             STATUS   mandatory
             DESCRIPTION
	        "The virtual channel connection traffic parameter 2
		for this connection."
             ::= { atmxVccEntry 45 }

	 atmxVccActualReceiveTrafficDescriptorParam3 OBJECT-TYPE
	     SYNTAX   INTEGER (0..353208)
             ACCESS   read-only
             STATUS   mandatory
             DESCRIPTION
	        "The virtual channel connection traffic parameter 3
		for this connection."
             ::= { atmxVccEntry 46 }

	 atmxVccActualReceiveTrafficQoSClass OBJECT-TYPE
	     SYNTAX   INTEGER (0..4)
             ACCESS   read-only
             STATUS   mandatory
             DESCRIPTION
	       	"The virtual channel connection traffic QOS Class 
	        for this connection."
             ::= { atmxVccEntry 47 }

	 atmxVccActualReceiveTrafficBestEffort OBJECT-TYPE
	     SYNTAX   INTEGER { false(1), true(2) }
             ACCESS   read-only
             STATUS   mandatory
             DESCRIPTION
	       	"The virtual channel connection best effort value
		for this connection."
             ::= { atmxVccEntry 48 }

         atmxVccAdmStatus OBJECT-TYPE
	     SYNTAX   AtmAdminStatCodes
             ACCESS   read-write
             STATUS   mandatory
             DESCRIPTION
                "The vcc adminstration status - used to delete a vcc."
             ::= { atmxVccEntry 49 }

         atmxVccServiceUsed OBJECT-TYPE
	     SYNTAX   INTEGER
             ACCESS   read-only
             STATUS   mandatory
             DESCRIPTION
                "The service number in which this vcc connection is used."
             ::= { atmxVccEntry 50 }

         atmxVccConnectionUsed OBJECT-TYPE
	     SYNTAX   INTEGER
             ACCESS   read-only
             STATUS   mandatory
             DESCRIPTION
                "Connection being used or not being used, currently not implemented."
             ::= { atmxVccEntry 51 }


     --		The ATM Virtual Address Group

     -- The ATM Virtual Address Table

         atmxAddressTable   OBJECT-TYPE
             SYNTAX   SEQUENCE OF AtmxAddressEntry 
             ACCESS   not-accessible
             STATUS   mandatory
             DESCRIPTION
                "A table of ATM virtual address status and parameter information." 
             ::= { atmxAddressGroup 1 }

         atmxAddressEntry   OBJECT-TYPE
             SYNTAX   AtmxAddressEntry
             ACCESS   not-accessible
             STATUS   mandatory
             DESCRIPTION
             	"An entry in the table, containing information about 
                the ATM virtual address."
             INDEX   { atmxAddressIndex}
             ::= { atmxAddressTable 1 }

         AtmxAddressEntry ::=
             SEQUENCE {
                 atmxAddressIndex
                     INTEGER,
                 atmxAddressAtmAddress
                     DisplayString,
		 atmxAddressType
	             INTEGER,
		 atmxAddressVpi
		     INTEGER,
		 atmxAddressVci
		     INTEGER,
                 atmxAddressDescription
                     DisplayString,
		 atmxAddressTransmitMaxSDU
		     INTEGER,
		 atmxAddressReceiveMaxSDU
		     INTEGER,
		 atmxAddressRequestedTransmitTrafficDescriptor
		     AtmTrafficDescrTypes,
		 atmxAddressRequestedTransmitTrafficDescriptorParam1
		     INTEGER,
		 atmxAddressRequestedTransmitTrafficDescriptorParam2
		     INTEGER,
		 atmxAddressRequestedTransmitTrafficDescriptorParam3
		     INTEGER,
		 atmxAddressRequestedTransmitTrafficQoSClass
		     INTEGER,
		 atmxAddressRequestedTransmitTrafficBestEffort
		     INTEGER,
		 atmxAddressRequestedReceiveTrafficDescriptor
		     AtmTrafficDescrTypes,
		 atmxAddressRequestedReceiveTrafficDescriptorParam1
		     INTEGER,
		 atmxAddressRequestedReceiveTrafficDescriptorParam2
		     INTEGER,
		 atmxAddressRequestedReceiveTrafficDescriptorParam3
		     INTEGER,
		 atmxAddressRequestedReceiveTrafficQoSClass
		     INTEGER,
		 atmxAddressRequestedReceiveTrafficBestEffort
		     INTEGER,
		 atmxAddressAcceptableTransmitTrafficDescriptor
		     AtmTrafficDescrTypes,
		 atmxAddressAcceptableTransmitTrafficDescriptorParam1
		     INTEGER,
		 atmxAddressAcceptableTransmitTrafficDescriptorParam2
		     INTEGER,
		 atmxAddressAcceptableTransmitTrafficDescriptorParam3
		     INTEGER,
		 atmxAddressAcceptableTransmitTrafficQoSClass
		     INTEGER,
		 atmxAddressAcceptableTransmitTrafficBestEffort
		     INTEGER,
		 atmxAddressAcceptableReceiveTrafficDescriptor
		     AtmTrafficDescrTypes,
		 atmxAddressAcceptableReceiveTrafficDescriptorParam1
		     INTEGER,
		 atmxAddressAcceptableReceiveTrafficDescriptorParam2
		     INTEGER,
		 atmxAddressAcceptableReceiveTrafficDescriptorParam3
		     INTEGER,
		 atmxAddressAcceptableReceiveTrafficQoSClass
		     INTEGER,
		 atmxAddressAcceptableReceiveTrafficBestEffort
		     INTEGER,
                 atmxAddressAdmStatus 
                     AtmAdminStatCodes,
		 atmxAddressServiceUsed
		     INTEGER,
		 atmxAddressAddrUsed
		     INTEGER
         }

         atmxAddressIndex OBJECT-TYPE
             SYNTAX   INTEGER (1..1023)
             ACCESS   read-only
             STATUS   mandatory
             DESCRIPTION
                "A unique value which identifies this address index."
             ::= { atmxAddressEntry 1 }

         atmxAddressAtmAddress OBJECT-TYPE
             SYNTAX   DisplayString (SIZE (0..40))
             ACCESS   read-write
             STATUS   mandatory
             DESCRIPTION
                "A unique value which identifies this address."
             ::= { atmxAddressEntry 2 }

 	 atmxAddressType OBJECT-TYPE
	     SYNTAX   INTEGER { arpServer(1), nonArpServer(2) }
             ACCESS   read-write
             STATUS   mandatory
             DESCRIPTION
                "The address type."
             ::= { atmxAddressEntry 3 }
	                        
	 atmxAddressVpi	OBJECT-TYPE
	     SYNTAX   INTEGER (0..0)
             ACCESS   read-only
             STATUS   mandatory
             DESCRIPTION
                "The virtual path identifier associated with this address."
             ::= { atmxAddressEntry 4 }

	 atmxAddressVci	OBJECT-TYPE
	     SYNTAX   INTEGER (1..1023)
             ACCESS   read-write
             STATUS   mandatory
             DESCRIPTION
                "The virtual channel identifier associated with this address."
             ::= { atmxAddressEntry 5 }

         atmxAddressDescription	OBJECT-TYPE
             SYNTAX   DisplayString (SIZE (0..31))
             ACCESS   read-write
             STATUS   mandatory
             DESCRIPTION
                "A description for this address."
             ::= { atmxAddressEntry 6 }

	 atmxAddressTransmitMaxSDU OBJECT-TYPE
	     SYNTAX   INTEGER (8..32678)
             ACCESS   read-write
             STATUS   mandatory
             DESCRIPTION
   	       	"The address maximum transmit SDU size in bytes for this SVC."
             ::= { atmxAddressEntry 7 }

	 atmxAddressReceiveMaxSDU OBJECT-TYPE
	     SYNTAX   INTEGER (8..32678)
             ACCESS   read-write
             STATUS   mandatory
             DESCRIPTION
	       	"The address maximun receive SDU size in bytes for this SVC."
             ::= { atmxAddressEntry 8 }

	 atmxAddressRequestedTransmitTrafficDescriptor OBJECT-TYPE
	     SYNTAX   AtmTrafficDescrTypes
             ACCESS   read-write
             STATUS   mandatory
             DESCRIPTION
	        "The address traffic descriptor for this SVC."
             ::= { atmxAddressEntry 9 }

	 atmxAddressRequestedTransmitTrafficDescriptorParam1 OBJECT-TYPE
	     SYNTAX   INTEGER (0..353208)
             ACCESS   read-write
             STATUS   mandatory
             DESCRIPTION
	        "The address transmit parameter 1 cell rate in cells/second for this SVC."
             ::= { atmxAddressEntry 10 }

	 atmxAddressRequestedTransmitTrafficDescriptorParam2 OBJECT-TYPE
 	     SYNTAX   INTEGER (0..353208)
             ACCESS   read-write
             STATUS   mandatory
             DESCRIPTION
	        "The address transmit parameter 2 cell rate in cells/second for this SVC."
             ::= { atmxAddressEntry 11 }

	 atmxAddressRequestedTransmitTrafficDescriptorParam3 OBJECT-TYPE
	     SYNTAX   INTEGER (0..353208)
             ACCESS   read-write
             STATUS   mandatory
             DESCRIPTION
	        "The address transmit parameter 3 cell rate in cells for this SVC."
             ::= { atmxAddressEntry 12 }

	 atmxAddressRequestedTransmitTrafficQoSClass	OBJECT-TYPE
	     SYNTAX   INTEGER (0..4)
             ACCESS   read-write
             STATUS   mandatory
             DESCRIPTION
	       "The address transmit traffic QOS Class for this SVC."
             ::= { atmxAddressEntry 13 }

	 atmxAddressRequestedTransmitTrafficBestEffort OBJECT-TYPE
	     SYNTAX   INTEGER { false(1), true(2) }
             ACCESS   read-write
             STATUS   mandatory
             DESCRIPTION
	       "The address transmit traffic best effort value for this SVC."
             ::= { atmxAddressEntry 14 }

	 atmxAddressRequestedReceiveTrafficDescriptor OBJECT-TYPE
	     SYNTAX   AtmTrafficDescrTypes
             ACCESS   read-write
             STATUS   mandatory
             DESCRIPTION
	       "The address receive traffic descriptor for this SVC."
             ::= { atmxAddressEntry 15 }

	 atmxAddressRequestedReceiveTrafficDescriptorParam1 OBJECT-TYPE
	     SYNTAX   INTEGER (0..353208)
             ACCESS   read-write
             STATUS   mandatory
             DESCRIPTION
	        "The address receive parameter 1 cell rate in cells/second for this SVC."
             ::= { atmxAddressEntry 16 }

	 atmxAddressRequestedReceiveTrafficDescriptorParam2 OBJECT-TYPE
 	     SYNTAX   INTEGER (0..353208)
             ACCESS   read-write
             STATUS   mandatory
             DESCRIPTION
	        "The address receive parameter 2 cell rate in cells/second for this SVC."
             ::= { atmxAddressEntry 17 }

	 atmxAddressRequestedReceiveTrafficDescriptorParam3 OBJECT-TYPE
	     SYNTAX   INTEGER (0..353208)
             ACCESS   read-write
             STATUS   mandatory
             DESCRIPTION
	        "The address receive parameter 2 cell rate in cells for this SVC."
             ::= { atmxAddressEntry 18 }

	 atmxAddressRequestedReceiveTrafficQoSClass OBJECT-TYPE
	     SYNTAX   INTEGER (0..4)
             ACCESS   read-write
             STATUS   mandatory
             DESCRIPTION
	       	"The address receive traffic QOS Class for this SVC."
             ::= { atmxAddressEntry 19 }

	 atmxAddressRequestedReceiveTrafficBestEffort OBJECT-TYPE
	     SYNTAX   INTEGER { false(1), true(2) }
             ACCESS   read-write
             STATUS   mandatory
             DESCRIPTION
	       	"The address receive traffic best effort value for this SVC."
             ::= { atmxAddressEntry 20 }
 
	 atmxAddressAcceptableTransmitTrafficDescriptor OBJECT-TYPE
	     SYNTAX   AtmTrafficDescrTypes
             ACCESS   read-write
             STATUS   mandatory
             DESCRIPTION
	        "The address traffic descriptor for this SVC."
             ::= { atmxAddressEntry 21 }

	 atmxAddressAcceptableTransmitTrafficDescriptorParam1 OBJECT-TYPE
	     SYNTAX   INTEGER (0..353208)
             ACCESS   read-write
             STATUS   mandatory
             DESCRIPTION
	        "The address transmit parameter 1 cell rate in cells/second for this SVC."
             ::= { atmxAddressEntry 22 }

	 atmxAddressAcceptableTransmitTrafficDescriptorParam2 OBJECT-TYPE
 	     SYNTAX   INTEGER (0..353208)
             ACCESS   read-write
             STATUS   mandatory
             DESCRIPTION
	        "The address transmit parameter 2 cell rate in cells/second for this SVC."
             ::= { atmxAddressEntry 23 }

	 atmxAddressAcceptableTransmitTrafficDescriptorParam3 OBJECT-TYPE
	     SYNTAX   INTEGER (0..353208)
             ACCESS   read-write
             STATUS   mandatory
             DESCRIPTION
	        "The address transmit parameter 3 cell rate in cells for this SVC."
             ::= { atmxAddressEntry 24 }

	 atmxAddressAcceptableTransmitTrafficQoSClass	OBJECT-TYPE
	     SYNTAX   INTEGER (0..4)
             ACCESS   read-write
             STATUS   mandatory
             DESCRIPTION
	       "The address transmit traffic QOS Class for this SVC."
             ::= { atmxAddressEntry 25 }

	 atmxAddressAcceptableTransmitTrafficBestEffort OBJECT-TYPE
	     SYNTAX   INTEGER { false(1), true(2) }
             ACCESS   read-write
             STATUS   mandatory
             DESCRIPTION
	       "The address transmit traffic best effort value for this SVC."
             ::= { atmxAddressEntry 26 }

	 atmxAddressAcceptableReceiveTrafficDescriptor OBJECT-TYPE
	     SYNTAX   AtmTrafficDescrTypes
             ACCESS   read-write
             STATUS   mandatory
             DESCRIPTION
	       "The address receive traffic descriptor for this SVC."
             ::= { atmxAddressEntry 27 }

	 atmxAddressAcceptableReceiveTrafficDescriptorParam1 OBJECT-TYPE
	     SYNTAX   INTEGER (0..353208)
             ACCESS   read-write
             STATUS   mandatory
             DESCRIPTION
	        "The address receive parameter 1 cell rate in cells/second for this SVC."
             ::= { atmxAddressEntry 28 }

	 atmxAddressAcceptableReceiveTrafficDescriptorParam2 OBJECT-TYPE
 	     SYNTAX   INTEGER (0..353208)
             ACCESS   read-write
             STATUS   mandatory
             DESCRIPTION
	        "The address receive parameter 2 cell rate in cells/second for this SVC."
             ::= { atmxAddressEntry 29 }

	 atmxAddressAcceptableReceiveTrafficDescriptorParam3 OBJECT-TYPE
	     SYNTAX   INTEGER (0..353208)
             ACCESS   read-write
             STATUS   mandatory
             DESCRIPTION
	        "The address receive parameter 2 cell rate in cells for this SVC."
             ::= { atmxAddressEntry 30 }

	 atmxAddressAcceptableReceiveTrafficQoSClass OBJECT-TYPE
	     SYNTAX   INTEGER (0..4)
             ACCESS   read-write
             STATUS   mandatory
             DESCRIPTION
	       	"The address receive traffic QOS Class for this SVC."
             ::= { atmxAddressEntry 31 }

	 atmxAddressAcceptableReceiveTrafficBestEffort OBJECT-TYPE
	     SYNTAX   INTEGER { false(1), true(2) }
             ACCESS   read-write
             STATUS   mandatory
             DESCRIPTION
	       	"The address receive traffic best effort value for this SVC."
             ::= { atmxAddressEntry 32 }

         atmxAddressAdmStatus OBJECT-TYPE
	     SYNTAX   AtmAdminStatCodes
             ACCESS   read-write
             STATUS   mandatory
             DESCRIPTION
                "The address adminstration status - used to delete an address."
             ::= { atmxAddressEntry 33 }

         atmxAddressServiceUsed OBJECT-TYPE
	     SYNTAX   INTEGER
             ACCESS   read-only
             STATUS   mandatory
             DESCRIPTION
                "The service number in which this address is used."
             ::= { atmxAddressEntry 34 }

         atmxAddressAddrUsed OBJECT-TYPE
	     SYNTAX   INTEGER
             ACCESS   read-only
             STATUS   mandatory
             DESCRIPTION
                "Address being used or not being used, currently not implemented."
             ::= { atmxAddressEntry 35 }

     
     --		The ATM Arp Group

     -- The ATM Arp Resolution Protocol Table

         atmxArpTable   OBJECT-TYPE
             SYNTAX   SEQUENCE OF AtmxArpEntry 
             ACCESS   not-accessible
             STATUS   mandatory
             DESCRIPTION
                "A table of ATM address to IP address information." 
             ::= { atmxArpGroup 1 }

         atmxArpEntry   OBJECT-TYPE
             SYNTAX   AtmxArpEntry
             ACCESS   not-accessible
             STATUS   mandatory
             DESCRIPTION
             	"An entry in the table, containing information about 
                the ATM address."
             INDEX   { atmxArpIndex }
             ::= { atmxArpTable 1 }

         AtmxArpEntry ::=
             SEQUENCE {
                 atmxArpIndex
                     INTEGER,
                 atmxArpIPAddress
                     IpAddress,
                 atmxArpAtmAddress
                     DisplayString,
		 atmxArpVci
		     INTEGER,
                 atmxArpTimeToLive
                     INTEGER,
		 atmxArpType
		     INTEGER
         }

         atmxArpIndex OBJECT-TYPE
             SYNTAX   INTEGER (1..128)
             ACCESS   read-only
             STATUS   mandatory
             DESCRIPTION
                "A unique value which identifies this arp entry."
             ::= { atmxArpEntry 1 }

         atmxArpIPAddress OBJECT-TYPE
             SYNTAX   IpAddress
             ACCESS   read-only
             STATUS   mandatory
             DESCRIPTION
                "The IP address for this atm address."
             ::= { atmxArpEntry 2 }

         atmxArpAtmAddress OBJECT-TYPE
             SYNTAX   DisplayString (SIZE (0..40))
             ACCESS   read-only
             STATUS   mandatory
             DESCRIPTION
                "A unique value which identifies this address."
             ::= { atmxArpEntry 3 }

	 atmxArpVci OBJECT-TYPE
	     SYNTAX   INTEGER (1..1023)
             ACCESS   read-only
             STATUS   mandatory
             DESCRIPTION
                "The virtual channel identifier associated with this address."
             ::= { atmxArpEntry 4 }

 	 atmxArpTimeToLive OBJECT-TYPE
	     SYNTAX   INTEGER
             ACCESS   read-only
             STATUS   mandatory
             DESCRIPTION
                "The address time to live."
             ::= { atmxArpEntry 5 }
	                        
 	 atmxArpType OBJECT-TYPE
	     SYNTAX   INTEGER { static(1), dynamic(2) }
             ACCESS   read-only
             STATUS   mandatory
             DESCRIPTION
                "The address type, statically or dynamically created."
             ::= { atmxArpEntry 6 }
	                        
     --
     --		The ATM LAN Emulation Group
     --

     -- ------------------------------------------------------------- --


     --
     --  LAN Emulation Client configuration group
     --

         atmLecConfigTable OBJECT-TYPE
             SYNTAX       SEQUENCE OF AtmLecConfigEntry
             ACCESS       not-accessible
             STATUS       mandatory
             DESCRIPTION
                     "This table contains all the configuration
                      parameters for a LAN Emulation client. "
             ::= { atmxLaneGroup 1 }

         atmLecConfigEntry OBJECT-TYPE
             SYNTAX       AtmLecConfigEntry
             ACCESS       not-accessible
             STATUS       mandatory
             DESCRIPTION
                     "Each table entry contains configuration information
                      for one LAN Emulation Client.

                      Most of the objects are derived from Initial State
                      Parameters in the LAN Emulation specification."
             INDEX   { atmxLecConfigIndex }
             ::= { atmLecConfigTable 1 }

         AtmLecConfigEntry ::=
             SEQUENCE {

                 --
                 --  Table index
                 --
                 atmxLecConfigIndex             INTEGER,
                 atmLecConfigLecsAtmAddress     XylanAtmLaneAddress,
                 atmLecConfigUseDefaultLecsAddr INTEGER,
                 atmLecRowStatus                INTEGER,
                 atmLecRowInUse                 INTEGER,
                 atmLecConfigMode               INTEGER,
                 atmLecConfigLanType            LecDataFrameFormat,
                 atmLecConfigMaxDataFrameSize   LecDataFrameSize,
                 atmLecConfigLanName            DisplayString,
                 atmLecConfigLesAtmAddress      XylanAtmLaneAddress,
                 atmLecControlTimeout           INTEGER,
                 atmLecMaxUnknownFrameCount     INTEGER,
                 atmLecMaxUnknownFrameTime      INTEGER,
                 atmLecVccTimeoutPeriod         INTEGER,
                 atmLecMaxRetryCount            INTEGER,
                 atmLecAgingTime                INTEGER,
                 atmLecForwardDelayTime         INTEGER,
                 atmLecExpectedArpResponseTime  INTEGER,
                 atmLecFlushTimeOut             INTEGER,
                 atmLecPathSwitchingDelay       INTEGER,
                 atmLecUseForwardDelay          INTEGER,
                 atmLecUseTranslation           INTEGER,
                 atmLecSrBridgeNum              INTEGER,
                 atmLecSrRingNum                INTEGER

             }

      atmxLecConfigIndex OBJECT-TYPE
             SYNTAX      INTEGER
             ACCESS      read-only
             STATUS      mandatory
             DESCRIPTION
                     "Index to identify an instance of this table."
             ::= { atmLecConfigEntry 1 }
 
         atmLecConfigLecsAtmAddress OBJECT-TYPE
             SYNTAX      XylanAtmLaneAddress
             ACCESS      read-write
             STATUS      mandatory
             DESCRIPTION
                     "The LAN Emulation Configuration Server which this client
                      can use if the Well Known LECS address is not used."
             ::= { atmLecConfigEntry 2 }

         atmLecConfigUseDefaultLecsAddr OBJECT-TYPE
             SYNTAX      INTEGER
             ACCESS      read-write
             STATUS      mandatory
             DESCRIPTION
                     "This is to specify if this client is to use the 
                      Well Know LECS address or user supplied address.
                     
                      This object alone with atmLecConfigLecsAtmAddress 
                      is meaningless if the atmLecConfigMode is setted to
                      manual(2) mode.

                        1 = TRUE
                        2 = FALSE  "
             ::= { atmLecConfigEntry 3 }

         atmLecRowStatus OBJECT-TYPE
             SYNTAX      INTEGER
             ACCESS      read-write
             STATUS      mandatory
             DESCRIPTION
                     "This object lets network managers create and delete
                      an instance for this table.
                      
                        1 = Create,
                        2 = Delete,   
                        3 = Modify."
             ::= { atmLecConfigEntry 4 }

         atmLecRowInUse OBJECT-TYPE
             SYNTAX      INTEGER
             ACCESS      read-only
             STATUS      mandatory
             DESCRIPTION
                     "This object returns a value to indicate if this
                      instance is used by an ATM service.
  
                        1 = In use
                        2 = Free.      "
             ::= { atmLecConfigEntry 5 }

         atmLecConfigMode OBJECT-TYPE
             SYNTAX      INTEGER {
                                  automatic(1),
                                  manual(2)
                                 }
             ACCESS      read-write
             STATUS      mandatory
             DESCRIPTION
                     "Indicates whether this LAN Emulation Client should
                      auto-configure the next time it is (re)started.

                      In automatic(1) mode, a client uses a LAN Emulation
                      Configuration Server to learn the ATM address of its
                      LAN Emulation Server, and to obtain other parameters.

                      atmLecConfig{ LanType, MaxDataFrameSize, LanName } are
                      used in the Configure request.  
                      atmLecConfigLesAtmAddress is ignored.

                      In manual(2) mode, management tells the client the
                      ATM address of its LAN Emulation Server and the
                      values of other parameters.

                      atmLecConfig{ LanType, MaxDataFrameSize, LanName } are
                      used in the Join request.  atmLecConfigLesAtmAddress
                      tells the client which LES to call."
             REFERENCE
                     "ATM Forum LAN Emulation Over ATM Specification, V1.0,
                      Sections 3.4.1.1 and 5.3"
             DEFVAL   { automatic }
             ::= { atmLecConfigEntry 6 }

         atmLecConfigLanType OBJECT-TYPE
             SYNTAX      LecDataFrameFormat
             ACCESS      read-write
             STATUS      mandatory
             DESCRIPTION
                     "C2  LAN Type.

                      The data frame format which this client will use the
                      next time it returns to the Initial State.

                      Auto-configuring clients use this parameter in their
                      Configure requests.  Manually-configured clients use
                      it in their Join requests.

                      This MIB object will not be overwritten with the new
                      value from a LE_{JOIN,CONFIGURE}_RESPONSE.  Instead,
                      atmLecActualLanType will be."
             REFERENCE
                     "ATM Forum LAN Emulation Over ATM Specification, V1.0,
                      Section 5.1.1"
             DEFVAL   { aflane8023 }
             ::= { atmLecConfigEntry 7 }

         atmLecConfigMaxDataFrameSize OBJECT-TYPE
             SYNTAX      LecDataFrameSize
             ACCESS      read-write
             STATUS      mandatory
             DESCRIPTION
                     "C3  Maximum Data Frame Size.

                      The maximum data frame size which this client will
                      use the next time it returns to the Initial State.

                      Auto-configuring clients use this parameter in their
                      Configure requests.  Manually-configured clients use
                      it in their Join requests.

                      This MIB object will not be overwritten with the new
                      value from a LE_{JOIN,CONFIGURE}_RESPONSE.  Instead,
                      atmLecActualMaxDataFrameSize will be."
             REFERENCE
                     "ATM Forum LAN Emulation Over ATM Specification, V1.0,
                      Section 5.1.1"
             DEFVAL   { max4544 }
             ::= { atmLecConfigEntry 8 }

         atmLecConfigLanName OBJECT-TYPE
             SYNTAX      DisplayString (SIZE( 0..32 ))
             ACCESS      read-write
             STATUS      mandatory
             DESCRIPTION
                     "C5  ELAN Name.

                      The ELAN Name this client will use the next time it
                      returns to the Initial State.

                      Auto-configuring clients use this parameter in their
                      Configure requests.  Manually-configured clients use
                      it in their Join requests.

                      This MIB object will not be overwritten with the new
                      value from a LE_{JOIN,CONFIGURE}_RESPONSE.  Instead,
                      atmLecActualLanName will be."
             REFERENCE
                     "ATM Forum LAN Emulation Over ATM Specification, V1.0,
                      Section 5.1.1"
             ::= { atmLecConfigEntry 9 }

         atmLecConfigLesAtmAddress OBJECT-TYPE
             SYNTAX      XylanAtmLaneAddress
             ACCESS      read-write
             STATUS      mandatory
             DESCRIPTION
                     "C9  LE Server ATM Address.
 
                      The LAN Emulation Server which this client will use
                      the next time it is started in manual configuration
                      mode.
 
                      When atmLecConfigMode is 'automatic', there is no need
                     to set this address, and no advantage to doing so.
                      The client will use the LECS to find a LES, putting
                      the auto-configured address in atmLecActualLesAtmAddress
                      while leaving atmLecConfigLesAtmAddress alone."
             REFERENCE
                     "ATM Forum LAN Emulation Over ATM Specification, V1.0,
                      Section 5.1.1"
             ::= { atmLecConfigEntry 10 }
 
         atmLecControlTimeout OBJECT-TYPE
             SYNTAX      INTEGER ( 10..300 )
             ACCESS      read-write
             STATUS      mandatory
             DESCRIPTION
                     "C7  Control Time-out.  Time out period used for
                          timing out most request/response control frame
                          interactions, as specified elsewhere [in the
                          LAN Emulation specification].

                      This time value is expressed in seconds."
             REFERENCE
                     "ATM Forum LAN Emulation Over ATM Specification, V1.0,
                      Section 5.1.1"
             DEFVAL   { 10 }
             ::= { atmLecConfigEntry 11 }

         atmLecMaxUnknownFrameCount OBJECT-TYPE
             SYNTAX      INTEGER ( 0..10 )
             ACCESS      read-write
             STATUS      mandatory
             DESCRIPTION
                     "C10 Maximum Unknown Frame Count.  See the description
                          of atmLecMaxUnknownFrameTime below."
             REFERENCE
                     "ATM Forum LAN Emulation Over ATM Specification, V1.0,
                      Section 5.1.1"
             DEFVAL   { 10 }
             ::= { atmLecConfigEntry 12 }

         atmLecMaxUnknownFrameTime OBJECT-TYPE
             SYNTAX      INTEGER ( 1..60 )
             ACCESS      read-write
             STATUS      mandatory
             DESCRIPTION
                     "C11 Maximum Unknown Frame Time.  Within the period of
                          time defined by the Maximum Unknown Frame Time, a
                          LE Client will send no more than Maximum Unknown
                          Frame Count frames to the BUS for a given unicast
                          LAN Destination, and it must also initiate the
                          address resolution protocol to resolve that LAN
                          Destination.

                      This time value is expressed in seconds."
             REFERENCE
                     "ATM Forum LAN Emulation Over ATM Specification, V1.0,
                      Section 5.1.1"
             DEFVAL   { 1 }
             ::= { atmLecConfigEntry 13 }

         atmLecVccTimeoutPeriod OBJECT-TYPE
             SYNTAX      INTEGER
             ACCESS      read-write
             STATUS      mandatory
             DESCRIPTION
                     "C12 VCC Time-out Period.  A LE Client SHOULD release
                          any Data Direct VCC that it has not used to
                          transmit or receive any data frames for the
                          length of the VCC Time-out Period.  This parameter
                          is only meaningful for SVC Data Direct VCCs.

                      This time value is expressed in seconds.  The default
                      value is 20 minutes.  A value of 0 seconds means that
                      the timeout period is infinite.  Negative values will
                      be rejected by the agent."
             REFERENCE
                     "ATM Forum LAN Emulation Over ATM Specification, V1.0,
                      Section 5.1.1"
             DEFVAL   { 1200 }
             ::= { atmLecConfigEntry 14 }

         atmLecMaxRetryCount OBJECT-TYPE
             SYNTAX      INTEGER( 0..2 )
             ACCESS      read-write
             STATUS      mandatory
             DESCRIPTION
                     "C13 Maximum Retry Count.  A LE CLient MUST not retry
                          a LE_ARP_REQUEST for a given frame's LAN
                          destination more than Maximum Retry Count times,
                          after the first LE_ARP_REQUEST for that same
                          frame's LAN destination."
             REFERENCE
                     "ATM Forum LAN Emulation Over ATM Specification, V1.0,
                      Section 5.1.1"
             DEFVAL   { 2 }
             ::= { atmLecConfigEntry 15 }

         atmLecAgingTime OBJECT-TYPE
             SYNTAX      INTEGER ( 10..300 )
             ACCESS      read-write
             STATUS      mandatory
             DESCRIPTION
                     "C17 Aging Time.  The maximum time that a LE Client
                          will maintain an entry in its LE_ARP cache in
                          the absence of a verification of that
                          relationship.

                      This time value is expressed in seconds."
             REFERENCE
                     "ATM Forum LAN Emulation Over ATM Specification, V1.0,
                      Section 5.1.1"
             DEFVAL  { 300 }
             ::= { atmLecConfigEntry 16 }

         atmLecForwardDelayTime OBJECT-TYPE
             SYNTAX      INTEGER ( 4..30 )
             ACCESS      read-write
             STATUS      mandatory
             DESCRIPTION
                     "C18 Forward Delay Time.  The maximum time that a LE
                          Client will maintain an entry for a non-local MAC
                          address in its LE_ARP cache in the absence of a
                          verification of that relationship, as long as the
                          Topology Change flag C19 is true.

                      atmLecForwardDelayTime SHOULD BE less than atmLecAgingTime.
                      When it is not, atmLecAgingTime governs LE_ARP aging.

                      This time value is expressed in seconds."
             REFERENCE
                     "ATM Forum LAN Emulation Over ATM Specification, V1.0,
                      Section 5.1.1"
             DEFVAL  { 15 }
             ::= { atmLecConfigEntry 17 }

         atmLecExpectedArpResponseTime OBJECT-TYPE
             SYNTAX      INTEGER ( 1..30 )
             ACCESS      read-write
             STATUS      mandatory
             DESCRIPTION
                     "C20 Expected LE_ARP Reponse Time.  The maximum time
                          that the LEC expects an LE_ARP_REQUEST/
                          LE_ARP_RESPONSE cycle to take.  Used for retries
                          and verifies.

                      This time value is expressed in seconds."
             REFERENCE
                     "ATM Forum LAN Emulation Over ATM Specification, V1.0,
                      Section 5.1.1"
             DEFVAL   { 1 }
             ::= { atmLecConfigEntry 18 }

         atmLecFlushTimeOut OBJECT-TYPE
             SYNTAX      INTEGER ( 1..4 )
             ACCESS      read-write
             STATUS      mandatory
             DESCRIPTION
                     "C21 Flush Time-out.  Time limit to wait to receive a
                          LE_FLUSH_RESPONSE after the LE_FLUSH_REQUEST has
                          been sent before taking recovery action.

                      This time value is expressed in seconds."
             REFERENCE
                     "ATM Forum LAN Emulation Over ATM Specification, V1.0,
                      Section 5.1.1"
             DEFVAL   { 4 }
             ::= { atmLecConfigEntry 19 }

         atmLecPathSwitchingDelay OBJECT-TYPE
             SYNTAX      INTEGER ( 1..8 )
             ACCESS      read-write
             STATUS      mandatory
             DESCRIPTION
                     "C22 Path Switching Delay.  The time since sending a
                          frame to the BUS after which the LE Client may
                          assume that the frame has been either discarded
                          or delivered to the recipient.  May be used to
                          bypass the Flush protocol.

                      This time value is expressed in seconds."
             REFERENCE
                     "ATM Forum LAN Emulation Over ATM Specification, V1.0,
                      Section 5.1.1"
             DEFVAL   { 6 }
             ::= { atmLecConfigEntry 20 }

         atmLecUseForwardDelay OBJECT-TYPE
             SYNTAX      INTEGER ( 1..2 )
             ACCESS      read-write
             STATUS      mandatory
             DESCRIPTION
                     " This is specify whether to use Forward delay or arp cache 
                       aging time

                           1 = No,
                           2 = Yes."
             DEFVAL   { 1 }
             ::= { atmLecConfigEntry 21 }

         atmLecUseTranslation OBJECT-TYPE
             SYNTAX      INTEGER ( 1..2 )
             ACCESS      read-write
             STATUS      mandatory
             DESCRIPTION
                     " Use translation option or not.
                       If set to yes, user must set the 
                       translation options by the swch 
                       command in UI or the vportSwitchTable
                       to set the translation option other
                       than the default defined for LANE.

                           1 = no, 
                           2 = yes."
             DEFVAL   { 2 }
             ::= { atmLecConfigEntry 23 }

         atmLecSrBridgeNum    OBJECT-TYPE
             SYNTAX      INTEGER ( 1..15 )
             ACCESS      read-write
             STATUS      mandatory
             DESCRIPTION
                     " SR bridge number for the LEC"
             ::= { atmLecConfigEntry 24 }

         atmLecSrRingNum    OBJECT-TYPE
             SYNTAX      INTEGER ( 1..4095 )
             ACCESS      read-write
             STATUS      mandatory
             DESCRIPTION
                     " SR Ring number for the LEC"
             ::= { atmLecConfigEntry 25 }

     --
     --  LAN Emulation Client status group
     --

         atmLecStatusTable OBJECT-TYPE
             SYNTAX       SEQUENCE OF AtmLecStatusEntry
             ACCESS       not-accessible
             STATUS       mandatory
             DESCRIPTION
                     "A read-only table containing identification, status,
                      and operational information about the LAN Emulation
                      Clients this agent manages."
             ::= { atmxLaneGroup 2 }

         atmLecStatusEntry OBJECT-TYPE
             SYNTAX       AtmLecStatusEntry
             ACCESS       not-accessible
             STATUS       mandatory
             DESCRIPTION
                     "Each table entry contains information about one LAN
                      Emulation Client."
             INDEX   { atmxLecStatusSlotIndex, 
                       atmxLecStatusPortIndex, 
                       atmxLecStatusServiceNum }
             ::= { atmLecStatusTable 1 }

         AtmLecStatusEntry ::=
             SEQUENCE {

                 --
                 --  Table index
                 --
                 atmxLecStatusSlotIndex         INTEGER,
                 atmxLecStatusPortIndex         INTEGER,
                 atmxLecStatusServiceNum        INTEGER,

                 --
                 --  Client identification
                 --
                 atmLecPrimaryAtmAddress        XylanAtmLaneAddress,
                 atmLecID                       INTEGER,

                 --
                 --  Client status and protocol version
                 --
                 atmLecInterfaceState           LecState,
                 atmLecLastFailureRespCode      INTEGER,
                 atmLecLastFailureState         LecState,
                 atmLecProtocol                 INTEGER,
                 atmLecVersion                  INTEGER,
                 atmLecTopologyChange           INTEGER,


                 --
                 --  Operational parameters and their source
                 --
                 atmLecConfigServerAtmAddress   XylanAtmLaneAddress,
                 atmLecConfigSource             INTEGER,
                 atmLecActualLanType            LecDataFrameFormat,
                 atmLecActualMaxDataFrameSize   LecDataFrameSize,
                 atmLecActualLanName            DisplayString,
                 atmLecActualLesAtmAddress      XylanAtmLaneAddress,
                 atmLecProxyClient              INTEGER

             }

        atmxLecStatusSlotIndex OBJECT-TYPE
             SYNTAX      INTEGER
             ACCESS      read-only
             STATUS      mandatory
             DESCRIPTION
                     "Slot index to identify an instance of this table."
             ::= { atmLecStatusEntry 1 }
 
         atmxLecStatusPortIndex OBJECT-TYPE
             SYNTAX      INTEGER
             ACCESS      read-only
             STATUS      mandatory
             DESCRIPTION
                     "Port index to identify an instance of this table."
             ::= { atmLecStatusEntry 2 }
 
         atmxLecStatusServiceNum OBJECT-TYPE
             SYNTAX      INTEGER
             ACCESS      read-only
             STATUS      mandatory
             DESCRIPTION
                     "Service number index to identify an instance of this
                      table."
             ::= { atmLecStatusEntry 3 }

         atmLecPrimaryAtmAddress OBJECT-TYPE
             SYNTAX      XylanAtmLaneAddress
             ACCESS      read-only
             STATUS      mandatory
             DESCRIPTION
                     "C1  LE Client's ATM Addresses.

                      The primary ATM address of this LAN Emulation Client.
                      This address is used to establish the Control Direct
                      and Multicast Send VCCs, and may also be used to set
                      up Data Direct VCCs.

                      A client may have additional ATM addresses for use
                      with Data Direct VCCs.  These addresses are readable
                      via the atmLecAtmAddressTable."
             REFERENCE
                     "ATM Forum LAN Emulation Over ATM Specification, V1.0,
                      Section 5.1.1"
             ::= { atmLecStatusEntry 4 }

         atmLecID OBJECT-TYPE
             SYNTAX      INTEGER( 0..65279 )
             ACCESS      read-only
             STATUS      mandatory
             DESCRIPTION
                     "C14 LE Client Identifier.  Each LE Client requires a
                          LE Client Identifier (LECID) assigned by the LE
                          Server during the Join phase.  The LECID is placed
                          in control requests by the LE Client and MAY be
                          used for echo suppression on multicast data frames
                          sent by that LE Client.  This value MUST NOT
                          change without terminating the LE Client and
                          returning to the Initial state.  A valid LECID
                          MUST be in the range X'0001' through X'FEFF'.

                      The value of this object is only meaningful for a LEC
                      that is connected to a LES.  For a LEC which does not
                      belong to an emulated LAN, the value of this object
                      is defined to be 0."
             REFERENCE
                     "ATM Forum LAN Emulation Over ATM Specification, V1.0,
                      Section 5.1.1"
             ::= { atmLecStatusEntry 5 }

         atmLecInterfaceState OBJECT-TYPE
             SYNTAX      LecState
             ACCESS      read-only
             STATUS      mandatory
             DESCRIPTION
                     "The mandatory state of the LAN Emulation Client.

                      Note that 'ifOperStatus' is defined to be 'up' when,
                      and only when, 'atmLecInterfaceState' is 'operational'."
             REFERENCE
                     "ATM Forum LAN Emulation Over ATM Specification, V1.0,
                      Section 2.3.1"
             ::= { atmLecStatusEntry 6 }

         atmLecLastFailureRespCode OBJECT-TYPE
             SYNTAX      INTEGER {
                                  none(1),
                                  timeout(2),
                                  undefinedError(3),
                                  versionNotSupported(4),
                                  invalidRequestParameters(5),
                                  duplicateLanDestination(6),
                                  duplicateAtmAddress(7),
                                  insufficientResources(8),
                                  accessDenied(9),
                                  invalidRequesterId(10),
                                  invalidLanDestination(11),
                                  invalidAtmAddress(12),
                                  noConfiguration(13),
                                  leConfigureError(14),
                                  insufficientInformation(15)
                                 }
             ACCESS      read-only
             STATUS      mandatory
             DESCRIPTION
                     "Status code from the last failed Configure response
                      or Join response.  Failed responses are those for
                      which the LE_CONFIGURE_RESPONSE / LE_JOIN_RESPONSE
                      frame contains a non-zero code, or fails to arrive
                      within a timeout period.

                      If none of this client's requests have failed, this
                      object has the value 'none'.

                      If the failed response contained a STATUS code that
                      is not defined in the LAN Emulation specification,
                      this object has the value 'undefinedError'.

                      The value 'timeout' is self-explanatory.

                      Other failure codes correspond to those defined in
                      the specification, although they may have different
                      numeric values."
             REFERENCE
                     "ATM Forum LAN Emulation Over ATM Specification, V1.0,
                      Section 4.2, Table 13"
             ::= { atmLecStatusEntry 7 }

         atmLecLastFailureState OBJECT-TYPE
             SYNTAX      LecState
             ACCESS      read-only
             STATUS      mandatory
             DESCRIPTION
                     "The state this client was in when it updated the
                      'atmLecLastFailureRespCode'.

                      If 'atmLecLastFailureRespCode' is 'none', this object
                      has the value initialState(1)."
             REFERENCE
                     "ATM Forum LAN Emulation Over ATM Specification, V1.0,
                      Section 2.3.1"
             ::= { atmLecStatusEntry 8 }

         atmLecProtocol OBJECT-TYPE
             SYNTAX      INTEGER ( 1..255 )
             ACCESS      read-only
             STATUS      mandatory
             DESCRIPTION
                     "The LAN Emulation protocol which this client supports,
                      and specifies in its LE_JOIN_REQUESTs."
             REFERENCE
                     "ATM Forum LAN Emulation Over ATM Specification, V1.0,
                      Section 4.2"
             ::= { atmLecStatusEntry 9 }

         atmLecVersion OBJECT-TYPE
             SYNTAX      INTEGER ( 1..255 )
             ACCESS      read-only
             STATUS      mandatory
             DESCRIPTION
                     "The LAN Emulation protocol version which this client
                      supports, and specifies in its LE_JOIN_REQUESTs."
             REFERENCE
                     "ATM Forum LAN Emulation Over ATM Specification, V1.0,
                      Section 4.2"
             ::= { atmLecStatusEntry 10 }

         atmLecTopologyChange OBJECT-TYPE
             SYNTAX      INTEGER
             ACCESS      read-only
             STATUS      mandatory
             DESCRIPTION
                     "C19 Topology Change.  Boolean indication that the LE
                          Client is using the Forward Delay Time C18,
                          instead of the Aging Time C17, to age non-local
                          entries in its LE_ARP cache C16.

                      For a client which is not connected to the LES, this
                      object is defined to have the value 'false'."
             REFERENCE
                     "ATM Forum LAN Emulation Over ATM Specification, V1.0,
                      Section 5.1.1"
             ::= { atmLecStatusEntry 11 }

         atmLecConfigServerAtmAddress OBJECT-TYPE
             SYNTAX      XylanAtmLaneAddress
             ACCESS      read-only
             STATUS      mandatory
             DESCRIPTION
                     "The ATM address of the LAN Emulation Configuration
                      Server (if known) or the empty string (otherwise)."
             ::= { atmLecStatusEntry 12 }

         atmLecConfigSource OBJECT-TYPE
             SYNTAX      INTEGER {
                                  gotAddressViaIlmi(1),
                                  usedWellKnownAddress(2),
                                  usedLecsPvc(3),
                                  didNotUseLecs(4)
                                 }
             ACCESS      read-only
             STATUS      mandatory
             DESCRIPTION
                     "Indicates whether this LAN Emulation Client used the
                      LAN Emulation Configuration Server, and, if so, what
                      method it used to establish the Configuration Direct
                      VCC."
             REFERENCE
                     "ATM Forum LAN Emulation Over ATM Specification, V1.0,
                      Section 5.2"
             ::= { atmLecStatusEntry 13 }


         atmLecActualLanType OBJECT-TYPE
             SYNTAX      LecDataFrameFormat
             ACCESS      read-only
             STATUS      mandatory
             DESCRIPTION
                     "C2  LAN Type.

                      The data frame format that this LAN Emulation Client
                      is using right now.  This may come from

                          *  atmLecConfigLanType,
                          *  the LAN Emulation Configuration Server, or
                          *  the LAN Emulation Server

                      This value is related to 'ifMtu' and 'ifType'.  See
                      the LEC management specification for more details."
             REFERENCE
                     "ATM Forum LAN Emulation Over ATM Specification, V1.0,
                      Section 5.1.1"
             ::= { atmLecStatusEntry 14 }

         atmLecActualMaxDataFrameSize OBJECT-TYPE
             SYNTAX      LecDataFrameSize
             ACCESS      read-only
             STATUS      mandatory
             DESCRIPTION
                     "C3  Maximum Data Frame Size.

                      The maximum data frame size that this LAN Emulation
                      client is using right now.  This may come from

                          *  atmLecConfigMaxDataFrameSize,
                          *  the LAN Emulation Configuration Server, or
                          *  the LAN Emulation Server                     "
             REFERENCE
                     "ATM Forum LAN Emulation Over ATM Specification, V1.0,
                      Section 5.1.1"
             ::= { atmLecStatusEntry 15 }

         atmLecActualLanName OBJECT-TYPE
             SYNTAX      DisplayString (SIZE( 0..32 ))
             ACCESS      read-only
             STATUS      mandatory
             DESCRIPTION
                     "C5  ELAN Name.

                      The identity of the emulated LAN which this client
                      last joined, or wishes to join.  This may come from

                          *  atmLecConfigLanName,
                          *  the LAN Emulation Configuration Server, or
                          *  the LAN Emulation Server                     "
             REFERENCE
                     "ATM Forum LAN Emulation Over ATM Specification, V1.0,
                   Section 5.1.1"
             ::= { atmLecStatusEntry 16 }

         atmLecActualLesAtmAddress OBJECT-TYPE
             SYNTAX      XylanAtmLaneAddress
             ACCESS      read-only
             STATUS      mandatory
             DESCRIPTION
                     "C9  LE Server ATM Address.

                      The LAN Emulation Server address currently in use or
                      most recently attempted.

                      If no LAN Emulation Server attachment has been tried,
                      this object's value is the zero-length string."
             REFERENCE
                     "ATM Forum LAN Emulation Over ATM Specification, V1.0,
                      Section 5.1.1"
             ::= { atmLecStatusEntry 17 }

         atmLecProxyClient OBJECT-TYPE
             SYNTAX      INTEGER
             ACCESS      read-only
             STATUS      mandatory
             DESCRIPTION
                     "C4  Proxy.

                      Indicates whether this client is acting as a proxy.

                      Proxy clients are allowed to represent unregistered
                      MAC addresses, and receive copies of LE_ARP_REQUEST
                      frames for such addresses."
             REFERENCE
                     "ATM Forum LAN Emulation Over ATM Specification, V1.0,
                      Section 5.1.1"
             ::= { atmLecStatusEntry 18 }

     -- ------------------------------------------------------------- --

     --
     --  LAN Emulation Client - Statistics table
     --

         atmLecStatisticsTable OBJECT-TYPE
             SYNTAX       SEQUENCE OF AtmLecStatisticsEntry
             ACCESS       not-accessible
             STATUS       mandatory
             DESCRIPTION
                     "An extension table containing traffic statistics for
                      all the LAN Emulation Clients this host implements."
             ::= { atmxLaneGroup 3 }

         atmLecStatisticsEntry OBJECT-TYPE
             SYNTAX       AtmLecStatisticsEntry
             ACCESS       not-accessible
             STATUS       mandatory
             DESCRIPTION
                     "Each row in this table contains traffic statistics
                      for one LAN Emulation client."
             INDEX   { atmxLecStatsSlotIndex, 
                       atmxLecStatsPortIndex,
                       atmxLecStatsServiceNum }
             ::= { atmLecStatisticsTable 1 }

         AtmLecStatisticsEntry ::=
             SEQUENCE {
                 atmxLecStatsSlotIndex          INTEGER,
                 atmxLecStatsPortIndex          INTEGER,
                 atmxLecStatsServiceNum         INTEGER,
                 atmLecArpRequestsOut           Counter,
                 atmLecArpRequestsIn            Counter,
                 atmLecArpRepliesOut            Counter,
                 atmLecArpRepliesIn             Counter,
                 atmLecControlFramesOut         Counter,
                 atmLecControlFramesIn          Counter,
                 atmLecSvcFailures              Counter
             }

         atmxLecStatsSlotIndex OBJECT-TYPE
             SYNTAX      INTEGER
             ACCESS      read-only
             STATUS      mandatory
             DESCRIPTION
                     "Slot index to identify an instance of this table."
             ::= { atmLecStatisticsEntry 1 }
 
         atmxLecStatsPortIndex OBJECT-TYPE
             SYNTAX      INTEGER
             ACCESS      read-only
             STATUS      mandatory
             DESCRIPTION
                     "Port index to identify an instance of this table."
             ::= { atmLecStatisticsEntry 2 }
 
         atmxLecStatsServiceNum OBJECT-TYPE
             SYNTAX      INTEGER
             ACCESS      read-only
             STATUS      mandatory
             DESCRIPTION
                     "Service number index to identify an instance of this
                      table."
             ::= { atmLecStatisticsEntry 3 }

         atmLecArpRequestsOut OBJECT-TYPE
             SYNTAX      Counter
             ACCESS      read-only
             STATUS      mandatory
             DESCRIPTION
                     "The number of LE_ARP_REQUESTs sent over the LUNI by
                      this LAN Emulation Client."
             ::= { atmLecStatisticsEntry 4 }

         atmLecArpRequestsIn OBJECT-TYPE
             SYNTAX      Counter
             ACCESS      read-only
             STATUS      mandatory
             DESCRIPTION
                     "The number of LE_ARP_REQUESTs received over the LUNI
                      by this LAN Emulation Client.

                      Requests may arrive on the Control Direct VCC or on
                      the Control Distribute VCC, depending upon how the
                      LES is implemented and the chances it has had for
                      learning.  This counter covers both VCCs."
             ::= { atmLecStatisticsEntry 5 }

         atmLecArpRepliesOut OBJECT-TYPE
             SYNTAX      Counter
             ACCESS      read-only
             STATUS      mandatory
             DESCRIPTION
                     "The number of LE_ARP_RESPONSEs sent over the LUNI by
                      this LAN Emulation Client."
             ::= { atmLecStatisticsEntry 6 }

         atmLecArpRepliesIn OBJECT-TYPE
             SYNTAX      Counter
             ACCESS      read-only
             STATUS      mandatory
             DESCRIPTION
                     "The number of LE_ARP_RESPONSEs received over the LUNI
                      by this LAN Emulation Client.  This count includes
                      all such replies, whether solicited or not.

                      Replies may arrive on the Control Direct VCC or on
                      the Control Distribute VCC, depending upon how the
                      LES is implemented.  This counter covers both VCCs."
             ::= { atmLecStatisticsEntry 7 }

         atmLecControlFramesOut OBJECT-TYPE
             SYNTAX      Counter
             ACCESS      read-only
             STATUS      mandatory
             DESCRIPTION
                     "The total number of control packets sent by this
                      LAN Emulation Client over the LUNI."
             ::= { atmLecStatisticsEntry 8 }

         atmLecControlFramesIn OBJECT-TYPE
             SYNTAX      Counter
             ACCESS      read-only
             STATUS      mandatory
             DESCRIPTION
                     "The total number of control packets received by this
                      LAN Emulation Client over the LUNI."
             ::= { atmLecStatisticsEntry 9 }

         atmLecSvcFailures OBJECT-TYPE
             SYNTAX      Counter
             ACCESS      read-only
             STATUS      mandatory
             DESCRIPTION
                     "The total number of

                          *  outgoing LAN Emulation SVCs which this client
                             tried, but failed, to open;

                          *  incoming LAN Emulation SVCs which this client
                             tried, but failed to establish; and

                          *  incoming LAN Emulation SVCs which this client
                             rejected for protocol or security reasons.   "
             ::= { atmLecStatisticsEntry 10 }

     -- ------------------------------------------------------------- --

     --
     --  LAN Emulation Client - Server VCC table
     --

         atmLecServerVccTable OBJECT-TYPE
             SYNTAX       SEQUENCE OF AtmLecServerVccEntry
             ACCESS       not-accessible
             STATUS       mandatory
             DESCRIPTION
                     "A table identifying the Control and Multicast VCCs
                      for each LAN Emulation Client this host implements."
             ::= { atmxLaneGroup 4 }

         atmLecServerVccEntry OBJECT-TYPE
             SYNTAX       AtmLecServerVccEntry
             ACCESS       not-accessible
             STATUS       mandatory
             DESCRIPTION
                     "Each row in this table describes the Control VCCs
                      and Multicast VCCs for one LAN Emulation client."
             INDEX   { atmxLecSlotIndex, 
                       atmxLecPortIndex,
                       atmxLecServiceNum }
             ::= { atmLecServerVccTable 1 }

         AtmLecServerVccEntry ::=
             SEQUENCE {

         --
         --  Note that the 'lec*Interface' objects double as 'connection
         --  exists' flags.
         --
                 atmxLecSlotIndex                  INTEGER,
                 atmxLecPortIndex                  INTEGER,
                 atmxLecServiceNum                 INTEGER,

                 atmLecConfigDirectVpi             VpiInteger,
                 atmLecConfigDirectVci             VciInteger,

                 atmLecControlDirectVpi            VpiInteger,
                 atmLecControlDirectVci            VciInteger,

                 atmLecControlDistributeVpi        VpiInteger,
                 atmLecControlDistributeVci        VciInteger,

                 atmLecMulticastSendVpi            VpiInteger,
                 atmLecMulticastSendVci            VciInteger,

                 atmLecMulticastForwardVpi         VpiInteger,
                 atmLecMulticastForwardVci         VciInteger
             }

         atmxLecSlotIndex OBJECT-TYPE
             SYNTAX      INTEGER
             ACCESS      read-only
             STATUS      mandatory
             DESCRIPTION
                    "index that uniquely identify an instance of 
                     the atmLecServerVccTable."
             ::= { atmLecServerVccEntry 1 }

         atmxLecPortIndex OBJECT-TYPE
             SYNTAX      INTEGER
             ACCESS      read-only
             STATUS      mandatory
             DESCRIPTION
                    "index that uniquely identify an instance of 
                     the atmLecServerVccTable."
             ::= { atmLecServerVccEntry 2 }

         atmxLecServiceNum OBJECT-TYPE
             SYNTAX      INTEGER
             ACCESS      read-only
             STATUS      mandatory
             DESCRIPTION
                    "Index that uniquely identify an instance of 
                     the atmLecServerVccTable."
             ::= { atmLecServerVccEntry 3 }

         atmLecConfigDirectVpi OBJECT-TYPE
             SYNTAX      VpiInteger
             ACCESS      read-only
             STATUS      mandatory
             DESCRIPTION
                     "If the Configuration Direct VCC exists, this object
                      contains the VPI which identifies that VCC at
                      the point where it connects to this LE client.

                      Otherwise, this object has the value 0."
             REFERENCE
                   "ATM Forum LAN Emulation Over ATM Specification, V1.0,
                    Section 2.2.2.1.1"
             ::= { atmLecServerVccEntry 4 }

         atmLecConfigDirectVci OBJECT-TYPE
             SYNTAX      VciInteger
             ACCESS      read-only
             STATUS      mandatory
             DESCRIPTION
                     "If the Configuration Direct VCC exists, this object
                      contains the VCI which identifies that VCC at
                      the point where it connects to this LE client.

                      Otherwise, this object has the value 0."
             REFERENCE
                   "ATM Forum LAN Emulation Over ATM Specification, V1.0,
                    Section 2.2.2.1.1"
             ::= { atmLecServerVccEntry 5 }

         atmLecControlDirectVpi OBJECT-TYPE
             SYNTAX      VpiInteger
             ACCESS      read-only
             STATUS      mandatory
             DESCRIPTION
                     "If the Control Direct VCC exists, this object
                      contains the VPI which identifies that VCC at
                      the point where it connects to this LE client.

                      Otherwise, this object has the value 0."
             REFERENCE
                   "ATM Forum LAN Emulation Over ATM Specification, V1.0,
                    Section 2.2.2.1.2"
             ::= { atmLecServerVccEntry 6 }

         atmLecControlDirectVci OBJECT-TYPE
             SYNTAX      VciInteger
             ACCESS      read-only
             STATUS      mandatory
             DESCRIPTION
                     "If the Control Direct VCC exists, this object
                      contains the VCI which identifies that VCC at
                      the point where it connects to this LE client.

                      Otherwise, this object has the value 0."
             REFERENCE
                   "ATM Forum LAN Emulation Over ATM Specification, V1.0,
                    Section 2.2.2.1.2"
             ::= { atmLecServerVccEntry 7 }

         atmLecControlDistributeVpi OBJECT-TYPE
             SYNTAX      VpiInteger
             ACCESS      read-only
             STATUS      mandatory
             DESCRIPTION
                     "If the Control Distribute VCC exists, this object
                      contains the VPI which identifies that VCC at the
                      point where it connects to this LE client.

                      Otherwise, this object has the value 0."
             REFERENCE
                   "ATM Forum LAN Emulation Over ATM Specification, V1.0,
                    Section 2.2.2.1.3"
             ::= { atmLecServerVccEntry 8 }

         atmLecControlDistributeVci OBJECT-TYPE
             SYNTAX      VciInteger
             ACCESS      read-only
             STATUS      mandatory
             DESCRIPTION
                     "If the Control Distribute VCC exists, this object
                      contains the VCI which identifies that VCC at the
                      point where it connects to this LE client.

                      Otherwise, this object contains the value 0."
             REFERENCE
                   "ATM Forum LAN Emulation Over ATM Specification, V1.0,
                    Section 2.2.2.1.3"
             ::= { atmLecServerVccEntry 9 }

         atmLecMulticastSendVpi OBJECT-TYPE
             SYNTAX      VpiInteger
             ACCESS      read-only
             STATUS      mandatory
             DESCRIPTION
                     "If the Multicast Send VCC exists, this object
                      contains the VPI which identifies that VCC at
                      the point where it connects to this LE client.

                      Otherwise, this object has the value 0."
             REFERENCE
                   "ATM Forum LAN Emulation Over ATM Specification, V1.0,
                    Section 2.2.2.2.2"
             ::= { atmLecServerVccEntry 10 }

         atmLecMulticastSendVci OBJECT-TYPE
             SYNTAX      VciInteger
             ACCESS      read-only
             STATUS      mandatory
             DESCRIPTION
                     "If the Multicast Send VCC exists, this object
                      contains the VCI which identifies that VCC at
                      the point where it connects to this LE client.

                      Otherwise, this object has the value 0."
             REFERENCE
                   "ATM Forum LAN Emulation Over ATM Specification, V1.0,
                    Section 2.2.2.2.2"
             ::= { atmLecServerVccEntry 11 }

         atmLecMulticastForwardVpi OBJECT-TYPE
             SYNTAX      VpiInteger
             ACCESS      read-only
             STATUS      mandatory
             DESCRIPTION
                     "If the Multicast Forward VCC exists, this object
                      contains the VPI which identifies that VCC at the
                      point where it connects to this LE client.

                      Otherwise, this object has the value 0."
             REFERENCE
                   "ATM Forum LAN Emulation Over ATM Specification, V1.0,
                    Section 2.2.2.2.3"
             ::= { atmLecServerVccEntry 12 }

         atmLecMulticastForwardVci OBJECT-TYPE
             SYNTAX      VciInteger
             ACCESS      read-only
             STATUS      mandatory
             DESCRIPTION
                     "If the Multicast Forward VCC exists, this object
                      contains the VCI which identifies that VCC at the
                      point where it connects to this LE client.

                      Otherwise, this object has the value 0."
             REFERENCE
                   "ATM Forum LAN Emulation Over ATM Specification, V1.0,
                    Section 2.2.2.2.3"
             ::= { atmLecServerVccEntry 13 }

     -- ------------------------------------------------------------- --

     --
     --  LAN Emulation Client ARP cache group - MAC addresses
     --

         atmLeArpTable OBJECT-TYPE
             SYNTAX      SEQUENCE OF AtmLeArpEntry
             ACCESS      not-accessible
             STATUS      mandatory
             DESCRIPTION
                     "This table provides access to an ATM LAN Emulation
                      Client's MAC-to-ATM ARP cache.  It contains entries
                      for unicast addresses and for the broadcast address,
                      but not for multicast MAC addresses.

                      C16 LE_ARP Cache.  A table of entries, each of which
                          establishes a relationship between a LAN
                          Destination external to the LE Client and the
                          ATM address to which data frames for that LAN
                          Destination will be sent."
             REFERENCE
                     "ATM Forum LAN Emulation Over ATM Specification,
                      Section 5.1.1"
             ::= { atmxLaneGroup 5 }

         atmLeArpEntry OBJECT-TYPE
             SYNTAX      AtmLeArpEntry
             ACCESS      not-accessible
             STATUS      mandatory
             DESCRIPTION
                     "An ATM LAN Emulation ARP cache entry containing
                      information about the binding of one MAC address
                      to one ATM address."
             INDEX   { atmxLeArpSlotIndex, 
                       atmxLeArpPortIndex,
                       atmxLeArpServiceNum,
                       atmLeArpIndex }
             ::= { atmLeArpTable 1 }

         AtmLeArpEntry ::=
             SEQUENCE {
                 atmxLeArpSlotIndex             INTEGER,
                 atmxLeArpPortIndex             INTEGER,
                 atmxLeArpServiceNum            INTEGER,
                 atmLeArpIndex                  INTEGER,
                 atmLeArpMacAddress             MacAddress,
                 atmLeArpAtmAddress             XylanAtmLaneAddress,
                 atmLeArpIsRemoteAddress        INTEGER,
                 atmLeArpEntryType              LeArpTableEntryType,
                 atmLeArpVpi                    VpiInteger,
                 atmLeArpVci                    VciInteger,
                 atmLeArpAge                    INTEGER,
                 atmLeArpType                   LeArpType
             }

         atmxLeArpSlotIndex OBJECT-TYPE
             SYNTAX      INTEGER
             ACCESS      read-only 
             STATUS      mandatory
             DESCRIPTION
                    "Slot index that uniquely identify an instance of 
                     the LeArp Table."
             ::= { atmLeArpEntry 1 }

         atmxLeArpPortIndex OBJECT-TYPE
             SYNTAX      INTEGER
             ACCESS      read-only
             STATUS      mandatory
             DESCRIPTION
                    "Port index that uniquely identify an instance of 
                     the LeArp Table."
             ::= { atmLeArpEntry 2 }

         atmxLeArpServiceNum OBJECT-TYPE
             SYNTAX      INTEGER
             ACCESS      read-only
             STATUS      mandatory
             DESCRIPTION
                    "Service number index that uniquely identify an instance of 
                     the LeArp Table."
             ::= { atmLeArpEntry 3 }

         atmLeArpIndex OBJECT-TYPE
             SYNTAX      INTEGER
             ACCESS      read-only
             STATUS      mandatory
             DESCRIPTION
                    "Index that uniquely identify an instance of 
                     the LeArp Table."
             ::= { atmLeArpEntry 4 }

         atmLeArpMacAddress OBJECT-TYPE
             SYNTAX      MacAddress
             ACCESS      read-only
             STATUS      mandatory
             DESCRIPTION
                     "The MAC address for which this cache entry provides
                      a translation.  Since ATM LAN Emulation uses an ARP
                      protocol to locate the Broadcast and Unknown Server,
                      the value of this object could be the broadcast MAC
                      address.

                      MAC addresses should be unique within any given ATM
                      Emulated LAN.  However, there's no requirement that
                      they be unique across disjoint emulated LANs."
             ::= { atmLeArpEntry 5 }

         atmLeArpAtmAddress OBJECT-TYPE
             SYNTAX      XylanAtmLaneAddress
             ACCESS      read-only
             STATUS      mandatory
             DESCRIPTION
                     "The ATM address of the Broadcast & Unknown Server
                      or LAN Emulation Client whose MAC address is stored
                      in 'atmLeArpMacAddress'.

                      This value may be determined through the use of the
                      LE_ARP procedure, through source address learning,
                      or through other mechanisms.

                      Some agents may provide write access to this object,
                      as part of their support for 'static' LE_ARP entries.
                      The effect of attempting to write an ATM address to
                      a 'learned' row is explicitly undefined.  Agents may
                      disallow the write, accept the write and change the
                      row's type, or even accept the write as-is."
             ::= { atmLeArpEntry 6 }

         atmLeArpIsRemoteAddress OBJECT-TYPE
             SYNTAX      INTEGER
             ACCESS      read-only
             STATUS      mandatory
             DESCRIPTION
                     "Indicates whether this entry is for a local or remote
                      MAC address.

                      In this context, 'local' means 'a MAC address that is
                      local to the remote client', as opposed to 'one of my
                      addresses'.

                          true(1)
                              The address is believed to be remote - or its
                              local/remote status is unknown.

                              For an entry created via the LE_ARP mechanism,
                              this corresponds to the 'Remote address' flag
                              being set in the LE_ARP_RESPONSE.

                              During Topology Change periods, remote LE_ARP
                              entries generally age out faster than others.
                              Specifically, they are subject to the Forward
                              Delay Time as well as to the Aging Time.

                          false(2)
                              The address is believed to be local - that is
                              to say, registered with the LES by the client
                              whose ATM address is atmLeArpAtmAddress.

                              For an entry created via the LE_ARP mechanism,
                              this corresponds to the 'Remote address' flag
                              being cleared in the LE_ARP_RESPONSE."
             ::= { atmLeArpEntry 7 }

         atmLeArpEntryType OBJECT-TYPE
             SYNTAX      LeArpTableEntryType
             ACCESS      read-only
             STATUS      mandatory
             DESCRIPTION
                     "Indicates how this LE_ARP table entry was created and
                      whether it is aged."
             ::= { atmLeArpEntry 8 }

         atmLeArpVpi OBJECT-TYPE
             SYNTAX      VpiInteger
             ACCESS      read-only
             STATUS      mandatory
             DESCRIPTION
                     "Indicates the vpi that this MAC is used to 
                      for it Data Direct VCC."
             ::= { atmLeArpEntry 9 }

         atmLeArpVci OBJECT-TYPE
             SYNTAX      VciInteger
             ACCESS      read-only
             STATUS      mandatory
             DESCRIPTION
                     "Indicates the vci that this MAC is used to 
                      for it Data Direct VCC."
             ::= { atmLeArpEntry 10 }

         atmLeArpAge OBJECT-TYPE
             SYNTAX      INTEGER
             ACCESS      read-only
             STATUS      mandatory
             DESCRIPTION
                     "Indicates the time in second that this entry
                      is being verified."
             ::= { atmLeArpEntry 11 }

         atmLeArpType OBJECT-TYPE
             SYNTAX      LeArpType
             ACCESS      read-only
             STATUS      mandatory
             DESCRIPTION
                     "Indicates if this entry represents a SR RD
                      or a ESI."
             ::= { atmLeArpEntry 12 }


     -- ------------------------------------------------------------- --

     --
     --  Supplementary Table for the lecConfigTable
     --

         xylanLecConfigTable OBJECT-TYPE
	     SYNTAX      SEQUENCE OF XylanLecConfigEntry
	     ACCESS      not-accessible
	     STATUS      mandatory
	     DESCRIPTION
	             "A supplementary table of the lecConfigTable in
		      ATM Forum MIB providing additional information
		      for creating and starting LEC service.
		      
		      This table is indexed by the lecIndex.  Each row
		      corresponding to the row with the same lecIndex
		      in the lecConfigTable."
	     ::= { atmxLaneGroup 6 }	      
		      
	 xylanLecConfigEntry OBJECT-TYPE
	     SYNTAX      XylanLecConfigEntry
	     ACCESS      not-accessible
	     STATUS      mandatory
	     DESCRIPTION
	             "Each row contains a slot number, a port number,
		      a service number and a group number for the LEC
		      service."
             INDEX   { lecIndex }
	     ::= { xylanLecConfigTable 1 }
	     
         XylanLecConfigEntry ::=
	     SEQUENCE {
	         xylanLecSlotNumber         INTEGER,
		 xylanLecPortNumber         INTEGER,
		 xylanLecServiceNumber      INTEGER,
		 xylanLecGroupNumber        INTEGER
	     }
 
	 xylanLecSlotNumber OBJECT-TYPE
	     SYNTAX       INTEGER
	     ACCESS       read-write
	     STATUS       mandatory
	     DESCRIPTION
	             "The slot on which the ASM/FCSM module is located.
		      The LEC service is to be created on that module.
		      When a row has just been created, the first slot
		      which has the ASM/FCSM module is assigned to this
		      instance.  If this number is not changed. The
		      service will be created based on this assigned slot
		      number."
	     ::= { xylanLecConfigEntry 1 }
	               
 	 xylanLecPortNumber OBJECT-TYPE
	     SYNTAX       INTEGER
	     ACCESS       read-write
	     STATUS       mandatory
	     DESCRIPTION
	             "The port of the ASM/FCSM module on which The LEC
		      service is to be created.  When a row has just
		      been created, the first available port of the ASM/FCSM
		      module is assigned to this instance.  If this number
		      is not changed. The service will be created based on
		      this assigned port number."
             ::= { xylanLecConfigEntry 2 }

	 xylanLecServiceNumber OBJECT-TYPE
	     SYNTAX       INTEGER
	     ACCESS       read-only
	     STATUS       mandatory
	     DESCRIPTION
	             "The service number which is assigned by the system."
             ::= { xylanLecConfigEntry 3 }
	 
	 xylanLecGroupNumber OBJECT-TYPE
	     SYNTAX       INTEGER
	     ACCESS       read-write
	     STATUS       mandatory
	     DESCRIPTION
	             "The group to which the LEC service belong. When a
		      row has just been created, the default group number
		      is assigned to this instance.  If this number is not
		      changed. The service will be created based on this
		      assigned group number."
             ::= { xylanLecConfigEntry 4 }
	       	      		          
     -- ------------------------------------------------------------- --

     --
     --  LAN Classical IP - Statistics table
     --

         atmCIPStatisticsTable OBJECT-TYPE
             SYNTAX       SEQUENCE OF AtmCIPStatisticsEntry
             ACCESS       not-accessible
             STATUS       mandatory
             DESCRIPTION
                     "An extension table containing traffic statistics for
                      all the Classical IP this host implements."
             ::= { atmxCIPstatsGroup 1 }

         atmCIPStatisticsEntry OBJECT-TYPE
             SYNTAX       AtmCIPStatisticsEntry
             ACCESS       not-accessible
             STATUS       mandatory
             DESCRIPTION
                     "Each row in this table contains traffic statistics
                      for one Classical IP Service."
             INDEX   { atmxCIPSlotIndex, 
                       atmxCIPPortIndex,
                       atmxCIPServiceNum }
             ::= { atmCIPStatisticsTable 1 }

         AtmCIPStatisticsEntry ::=
             SEQUENCE {
                 atmxCIPSlotIndex           INTEGER,
                 atmxCIPPortIndex           INTEGER,
                 atmxCIPServiceNum          INTEGER,
                 atmCIPpktsFromIP           Counter,
                 atmCIPBroadcastPktFromIP   Counter,
                 atmCIPPktsFromIPDiscard    Counter,
                 atmCIPPktsToIP             Counter,
                 atmCIPPktsFromNet          Counter,
                 atmCIPPktsFromNetDiscard   Counter,
                 atmCIPArpRespFromNet       Counter,
                 atmCIPArpReqFromNet        Counter,
                 atmCIPInvArpRespFromNet    Counter,
                 atmCIPInvArpReqFromNet     Counter,
                 atmCIPInvArpNakFromNet     Counter,
                 atmCIPPktsToNet            Counter,
                 atmCIPPktsToNetDiscard     Counter,
                 atmCIPArpRespToNet         Counter,
                 atmCIPArpReqToNet          Counter,
                 atmCIPInvArpRespToNet      Counter,
                 atmCIPInvArpReqToNet       Counter,
                 atmCIPInvArpNakToNet       Counter
             }

         atmxCIPSlotIndex OBJECT-TYPE
             SYNTAX      INTEGER
             ACCESS      read-only
             STATUS      mandatory
             DESCRIPTION
                     "Slot index to identify an instance of this table."
             ::= { atmCIPStatisticsEntry 1 }

         atmxCIPPortIndex OBJECT-TYPE
             SYNTAX      INTEGER
             ACCESS      read-only
             STATUS      mandatory
             DESCRIPTION
                     "Port index to identify an instance of this table."
             ::= { atmCIPStatisticsEntry 2 }

         atmxCIPServiceNum OBJECT-TYPE
             SYNTAX      INTEGER
             ACCESS      read-only
             STATUS      mandatory
             DESCRIPTION
                     "Service number index to identify an instance of this
                      table."
             ::= { atmCIPStatisticsEntry 3 }

         atmCIPpktsFromIP OBJECT-TYPE
             SYNTAX      Counter
             ACCESS      read-only
             STATUS      mandatory
             DESCRIPTION
                     "The number of packets received form IP."
             ::= { atmCIPStatisticsEntry 4 }

         atmCIPBroadcastPktFromIP OBJECT-TYPE
             SYNTAX      Counter
             ACCESS      read-only
             STATUS      mandatory
             DESCRIPTION
                     "The number of Broadcast packets received form IP."
             ::= { atmCIPStatisticsEntry 5 }

         atmCIPPktsFromIPDiscard OBJECT-TYPE
             SYNTAX      Counter
             ACCESS      read-only
             STATUS      mandatory
             DESCRIPTION
                     "The number of packets received form IP discarded."
             ::= { atmCIPStatisticsEntry 6 }

         atmCIPPktsToIP OBJECT-TYPE
             SYNTAX      Counter
             ACCESS      read-only
             STATUS      mandatory
             DESCRIPTION
                     "The number of packets sent to IP."
             ::= { atmCIPStatisticsEntry 7 }

         atmCIPPktsFromNet OBJECT-TYPE
             SYNTAX      Counter
             ACCESS      read-only
             STATUS      mandatory
             DESCRIPTION
                     "The number of packets received from the Network."
             ::= { atmCIPStatisticsEntry 8 }

         atmCIPPktsFromNetDiscard OBJECT-TYPE
             SYNTAX      Counter
             ACCESS      read-only
             STATUS      mandatory
             DESCRIPTION
                     "The number of packets sent to IP discarded."
             ::= { atmCIPStatisticsEntry 9 }

         atmCIPArpRespFromNet OBJECT-TYPE
             SYNTAX      Counter
             ACCESS      read-only
             STATUS      mandatory
             DESCRIPTION
                     "The number of Arp response packet received form the
                      network."
             ::= { atmCIPStatisticsEntry 10 }

         atmCIPArpReqFromNet OBJECT-TYPE
             SYNTAX      Counter
             ACCESS      read-only
             STATUS      mandatory
             DESCRIPTION
                     "The number of Arp request packet received form the
                      network."
             ::= { atmCIPStatisticsEntry 11 }

         atmCIPInvArpRespFromNet OBJECT-TYPE
             SYNTAX      Counter
             ACCESS      read-only
             STATUS      mandatory
             DESCRIPTION
                     "The number of Inverse Arp response packet received 
                      form the network."
             ::= { atmCIPStatisticsEntry 12 }

         atmCIPInvArpReqFromNet OBJECT-TYPE
             SYNTAX      Counter
             ACCESS      read-only
             STATUS      mandatory
             DESCRIPTION
                     "The number of Inverse Arp request packet received 
                      form the network."
             ::= { atmCIPStatisticsEntry 13 }

         atmCIPInvArpNakFromNet OBJECT-TYPE
             SYNTAX      Counter
             ACCESS      read-only
             STATUS      mandatory
             DESCRIPTION
                     "The number of Inverse Arp negative acknowledgement 
                      packet received form the network."
             ::= { atmCIPStatisticsEntry 14 }

         atmCIPPktsToNet OBJECT-TYPE
             SYNTAX      Counter
             ACCESS      read-only
             STATUS      mandatory
             DESCRIPTION
                     "The number of packets sent to the network."
             ::= { atmCIPStatisticsEntry 15 }

         atmCIPPktsToNetDiscard OBJECT-TYPE
             SYNTAX      Counter
             ACCESS      read-only
             STATUS      mandatory
             DESCRIPTION
                     "The number of packets sent to the network."
             ::= { atmCIPStatisticsEntry 16 }

         atmCIPArpRespToNet OBJECT-TYPE
             SYNTAX      Counter
             ACCESS      read-only
             STATUS      mandatory
             DESCRIPTION
                     "The number of Arp response packet sent to the 
                      network."
             ::= { atmCIPStatisticsEntry 17 }

         atmCIPArpReqToNet OBJECT-TYPE
             SYNTAX      Counter
             ACCESS      read-only
             STATUS      mandatory
             DESCRIPTION
                     "The number of Arp request packet sent to the 
                      network."
             ::= { atmCIPStatisticsEntry 18 }

         atmCIPInvArpRespToNet OBJECT-TYPE
             SYNTAX      Counter
             ACCESS      read-only
             STATUS      mandatory
             DESCRIPTION
                     "The number of Inverse Arp response packet sent to the 
                      network."
             ::= { atmCIPStatisticsEntry 19 }

         atmCIPInvArpReqToNet OBJECT-TYPE
             SYNTAX      Counter
             ACCESS      read-only
             STATUS      mandatory
             DESCRIPTION
                     "The number of Inverse Arp request packet sent to the 
                      network."
             ::= { atmCIPStatisticsEntry 20 }

         atmCIPInvArpNakToNet OBJECT-TYPE
             SYNTAX      Counter
             ACCESS      read-only
             STATUS      mandatory
             DESCRIPTION
                     "The number of Inverse Arp negative acknowledge 
                      packet sent to the network."
             ::= { atmCIPStatisticsEntry 21 }

     -- ------------------------------------------------------------- --

     --
     --  1483 Scaling Service   Group ID to virtual circuit Mapping table
     --

-- single entry

         atmGpToVcMappingTable OBJECT-TYPE
             SYNTAX       SEQUENCE OF AtmGpToVcMappingEntry
             ACCESS       not-accessible
             STATUS       mandatory
             DESCRIPTION
                     "An extension table containing mapping info for all 
                      group to VCI (and VPI) mapping for 1 Scaling service.
                      This table is for create, delete 1 mapping entry.

                      Utilize atmxServiceGroup to create or delete a
                      1483 Scaling Service.  Create 1483 Scaling Service 
                      only with 1 group and 1 vc thru the atmxServiceGroup. 
                      Adding or removing other group-to-vc mapping should 
                      then use this atmx1483ScaleGroup."

             ::= { atmx1483ScaleGroup 1 }

         atmGpToVcMappingEntry OBJECT-TYPE
             SYNTAX       AtmGpToVcMappingEntry
             ACCESS       not-accessible
             STATUS       mandatory
             DESCRIPTION
                     "Each row in this table contains mapping info  
                      for 1 group to 1 VCI (and 1 VPI) entry.
                      The value for VPI must be zero (0)."   
             INDEX   { atmxGpToVcSlotIndex, 
                       atmxGpToVcPortIndex,
                       atmxGpToVcServiceNum,
                       atmxGpToVcGroupId    
                     }
             ::= { atmGpToVcMappingTable 1 }

         AtmGpToVcMappingEntry ::=
             SEQUENCE {
                 atmxGpToVcSlotIndex           INTEGER,
                 atmxGpToVcPortIndex           INTEGER,
                 atmxGpToVcServiceNum          INTEGER,
		 atmxGpToVcGroupId             INTEGER,

		 atmxGpToVcVpi                 INTEGER,
		 atmxGpToVcVci                 INTEGER,
                 atmxGpToVcRowStatus           INTEGER
                              }

         atmxGpToVcSlotIndex OBJECT-TYPE
             SYNTAX      INTEGER
             ACCESS      read-only
             STATUS      mandatory
             DESCRIPTION
                     "Slot index to identify an instance of this table."
             ::= { atmGpToVcMappingEntry 1 }

         atmxGpToVcPortIndex OBJECT-TYPE
             SYNTAX      INTEGER
             ACCESS      read-only
             STATUS      mandatory
             DESCRIPTION
                     "Port index to identify an instance of this table."
             ::= { atmGpToVcMappingEntry 2 }

         atmxGpToVcServiceNum OBJECT-TYPE
             SYNTAX      INTEGER
             ACCESS      read-only
             STATUS      mandatory
             DESCRIPTION
                     "Service number index to identify an instance of this table."
             ::= { atmGpToVcMappingEntry 3 }


         atmxGpToVcGroupId OBJECT-TYPE
             SYNTAX      INTEGER
             ACCESS      read-only
             STATUS      mandatory
             DESCRIPTION
                     "Group number index to identify an instance of this table."
             ::= { atmGpToVcMappingEntry 4 }

         atmxGpToVcVpi OBJECT-TYPE
             SYNTAX      INTEGER
             ACCESS      read-write
             STATUS      mandatory
             DESCRIPTION
                     "The VPI for 1 Scaling Service. VPI can only be zero ."
             ::= { atmGpToVcMappingEntry 5 }

         atmxGpToVcVci OBJECT-TYPE
             SYNTAX      INTEGER
             ACCESS      read-write
             STATUS      mandatory
             DESCRIPTION
                     "The VCI for 1 Scaling Service. The range for VCI is
                      from 1 to 1000."
             ::= { atmGpToVcMappingEntry 6 }

         atmxGpToVcRowStatus OBJECT-TYPE
             SYNTAX    INTEGER { create (1),
                                 delete (2),
                                 active (3),
                                 inactive (4) }
             ACCESS      read-write
             STATUS      mandatory
             DESCRIPTION
                     "Row Status indicates the state of a entry of this
                      mapping table.  

                      For a Get-operation, the value to be returned 
                      values can be ACTIVE or INACTIVE.  This RowStatus will
                      return ACTIVE, if the atmxServiceAdminStatus (an object
                      in atmxSerivceGroup) is set to ENABLE.  RowStatus 
                      will be INACTIVE if atmxServiceAdminStatus is set to a 
                      value other than ENABLE.  
                      RowStatus can only set to CREATE or DELETE.  The values 
                      ACTIVE and INACTIVE are read only.

                      For a Set-operation, values to be set can be CREATE
                      or DELETE.

                      Utilize atmxServiceGroup to create or delete a
                      1483 Scaling Service.  Create 1483 Scaling Service 
                      only with 1 group and 1 vc thru the atmxServiceGroup. 
                      Adding or removing other group-to-vc mapping should 
                      then use this atmx1483ScaleGroup."


             ::= { atmGpToVcMappingEntry 7 }

-- Bulk 
    
         atmGpToVcBulkMappingTable OBJECT-TYPE
             SYNTAX       SEQUENCE OF AtmGpToVcBulkMappingEntry
             ACCESS       not-accessible
             STATUS       mandatory
             DESCRIPTION
                     "An extension table containing mapping (bulk) info for
                      all group to VCI (and VPI) mapping for 1 Scaling
                      service. This table can only have 1 row.
                      This table is for updating the whole mapping list
                      (ie. all mapping entries ) at one time. "
 
             ::= { atmx1483ScaleGroup 2 }

         atmGpToVcBulkMappingEntry OBJECT-TYPE
             SYNTAX       AtmGpToVcBulkMappingEntry
             ACCESS       not-accessible
             STATUS       mandatory
             DESCRIPTION
                     "There is only 1 row in this table. This row contains all
                      group to VCI (and VPI) mapping for 1 Scaling service. 
                      There are 3 indices for this table. 
                      The value for VPI must be zero (0)."   
             INDEX   { 
                       atmxGpToVcBulkSlotIndex, 
                       atmxGpToVcBulkPortIndex,
                       atmxGpToVcBulkServiceNum 
                     }
             ::= { atmGpToVcBulkMappingTable 1 }

         AtmGpToVcBulkMappingEntry ::=
             SEQUENCE {
                 atmxGpToVcBulkSlotIndex           INTEGER,
                 atmxGpToVcBulkPortIndex           INTEGER,
                 atmxGpToVcBulkServiceNum          INTEGER,

                 atmxGpToVcBulkNumOfNodes          INTEGER,
                 atmxGpToVcBulkMappingList         OCTET STRING (SIZE(8..8000))
                              }

         atmxGpToVcBulkSlotIndex OBJECT-TYPE
             SYNTAX      INTEGER
             ACCESS      read-only
             STATUS      mandatory
             DESCRIPTION
                     "Slot index to identify a Scaling service."
             ::= { atmGpToVcBulkMappingEntry 1 }

         atmxGpToVcBulkPortIndex OBJECT-TYPE
             SYNTAX      INTEGER
             ACCESS      read-only
             STATUS      mandatory
             DESCRIPTION
                     "Port index to identify a Scaling service."
             ::= { atmGpToVcBulkMappingEntry 2 }

         atmxGpToVcBulkServiceNum OBJECT-TYPE
             SYNTAX      INTEGER
             ACCESS      read-only
             STATUS      mandatory
             DESCRIPTION
                     "Service number index to identify a Scaling service."
             ::= { atmGpToVcBulkMappingEntry 3 }

         atmxGpToVcBulkNumOfNodes OBJECT-TYPE
             SYNTAX      INTEGER
             ACCESS      read-only 
             STATUS      mandatory
             DESCRIPTION
                     "Number of group to VCI (and VPI) mapping inside 
                      the bulk mapping list. "
             ::= { atmGpToVcBulkMappingEntry 4 }

         atmxGpToVcBulkMappingList OBJECT-TYPE
             SYNTAX      OCTET STRING(SIZE(8..8000))
             ACCESS      read-write
             STATUS      mandatory
             DESCRIPTION
                     "A list containing all group to VCI (and VPI) mapping
                      entries.  Each mapping entry has the following fields 
                      having the exact order :
                        a) Group Number (4 bytes)
                        b) VPI          (2 bytes) 
                        c) VCI          (2 bytes)
                      A total of 8 bytes for each mapping structure. There is 
                      no separator in between matching structures, nor is a 
                      end-of-string in this whole matching list.  The size 
                      of this whole mapping list must be a multiple of 8 bytes.
                      For Set-Operations, if a user wants to update the mapping
                      list, he must send the whole mapping list buffer. "
             ::= { atmGpToVcBulkMappingEntry 5 }

-- end 1483 scaling


     -- ------------------------------------------------------------- --
     
     --
     --  Sahi Traffic Shaping mib
     --  This table is applicable only for SAHI based HSM's

         atmxBwgTable   OBJECT-TYPE
	    SYNTAX   SEQUENCE OF AtmxBwgEntry 
            ACCESS   not-accessible
            STATUS   mandatory
            DESCRIPTION
            	"A table of Bandwidth group parameters for Traffic Shaping" 
            ::= { atmxSahiBWGroup 1 }

         atmxBwgEntry   OBJECT-TYPE
            SYNTAX   AtmxBwgEntry
            ACCESS   not-accessible
            STATUS   mandatory
            DESCRIPTION
            	"An entry in the table, containing information about 
                the Traffic parameters for each of the 8 bandwidth groups"
            INDEX   { atmxBwgSlotIndex, atmxBwgPortIndex, atmxBwgNum }
            ::= { atmxBwgTable 1 }

         AtmxBwgEntry ::= SEQUENCE {
                 atmxBwgSlotIndex	INTEGER,
                 atmxBwgPortIndex       INTEGER,
                 atmxBwgNum             INTEGER,
                 atmxBwgBE              INTEGER,
                 atmxBwgPcr             INTEGER,
                 atmxBwgScr             INTEGER,
                 atmxBwgMbs             INTEGER,
		 atmxBwgOperStatus	AtmOperStatCodes
         }

         atmxBwgSlotIndex OBJECT-TYPE
             SYNTAX   INTEGER (1..9)
             ACCESS   read-only
             STATUS   mandatory
             DESCRIPTION
                "A unique value which identifies this hsm board slot."
             ::= { atmxBwgEntry 1 }

         atmxBwgPortIndex OBJECT-TYPE
             SYNTAX   INTEGER (1..2)
             ACCESS   read-only
             STATUS   mandatory
             DESCRIPTION
                "A unique value which identifies this atm submodule port."
             ::= { atmxBwgEntry 2 }

         atmxBwgNum   OBJECT-TYPE
             SYNTAX   INTEGER (1..8)
             ACCESS   read-only
             STATUS   mandatory
             DESCRIPTION
                "A unique value that identifies the bwg"
             ::= { atmxBwgEntry 3 }

         atmxBwgBE OBJECT-TYPE
             SYNTAX   INTEGER {
		true(1),
		false(2) }
             ACCESS   read-write
             STATUS   mandatory
             DESCRIPTION
                "Whether to use Best Effort for tx data."
             ::= { atmxBwgEntry 4 }

         atmxBwgPcr   OBJECT-TYPE
             SYNTAX   INTEGER(535..150000)
             ACCESS   read-write
             STATUS   mandatory
             DESCRIPTION
                "The value of the Peak Cell Rate(Kbps) as defined in the Traffic
		 Management Specification Version 4.0.
		 atmxBwgPcr has no meaning when atmxBwgBE is equal to true."
             ::= { atmxBwgEntry 5 }

         atmxBwgScr   OBJECT-TYPE
             SYNTAX   INTEGER(35..150000)
             ACCESS   read-write
             STATUS   mandatory
             DESCRIPTION
                "The value of the Sustained Cell Rate(Kbps) as defined in the 
		 Traffic Management Specification Version 4.0.
		 atmxBwgScr must be less or equal to atmxBwgPcr.
		 atmxBwgScr has no meaning when atmxBwgBE is equal to true."
             ::= { atmxBwgEntry 6 }
                             
         atmxBwgMbs   OBJECT-TYPE
             SYNTAX   INTEGER(1..124)
             ACCESS   read-write
             STATUS   mandatory
             DESCRIPTION
                "The value of the max burst size when interleaving traffic
                 from multiple sources as defined in the 4.0 Traffic Management specification.
		 atmxBwgMbs has no meaning when atmxBwgBE is equal to true."
             ::= { atmxBwgEntry 7 }

         atmxBwgOperStatus   OBJECT-TYPE
             SYNTAX   AtmOperStatCodes
             ACCESS   read-only
             STATUS   mandatory
             DESCRIPTION
		"If the bwg is being used by any service we return inService(2)
		 , or we return outOfService(3)."
             ::= { atmxBwgEntry 8 }


    
         atmxBwgServiceTable   OBJECT-TYPE
	    SYNTAX   SEQUENCE OF AtmxBwgServiceEntry 
            ACCESS   not-accessible
            STATUS   mandatory
            DESCRIPTION
            	"A table of Service group parameters for Traffic Shaping" 
            ::= { atmxSahiBWGroup 2 }

         atmxBwgServiceEntry   OBJECT-TYPE
            SYNTAX   AtmxBwgServiceEntry
            ACCESS   not-accessible
            STATUS   mandatory
            DESCRIPTION
            	"Each entry represents an BandWidthGroup to Service mapping." 
            INDEX   { atmxBwgSlotIndex, atmxBwgPortIndex, atmxBwgNum, atmxBwgServiceNum }
            ::= { atmxBwgServiceTable 1 }

         AtmxBwgServiceEntry ::= SEQUENCE {
                 atmxBwgServiceNum		INTEGER
         }

         atmxBwgServiceNum OBJECT-TYPE
             SYNTAX   INTEGER
             ACCESS   read-only
             STATUS   mandatory
             DESCRIPTION
                "A unique value which identifies a service."
             ::= { atmxBwgServiceEntry 1 }

-- end Traffic Shaping

    END
