LAN-TUNNELING-MIB DEFINITIONS ::= BEGIN

IMPORTS
	MODULE-IDENTITY, OBJECT-TYPE
		FROM SNMPv2-SMI
	TEXTUAL-CONVENTION, RowStatus
		FROM SNMPv2-TC
	pgainDSLAM
		FROM PAIRGAIN-COMMON-HD-MIB;

pgLantMIB MODULE-IDENTITY
	LAST-UPDATED	"9712180000Z"
	ORGANIZATION	"Pairgain Technology"
        CONTACT-INFO	""
	DESCRIPTION	"The module defines MIB for LAN Tunneling configuration"
	::= {pgainDSLAM 2}


pgLantObjects OBJECT IDENTIFIER ::= {pgLantMIB 1}

PgLantEncapType ::=
	INTEGER {
		other (1),		-- None of the following
		llc-snap (2),		-- LLC/SNAP encapsulation
		vc-mux (3)		-- VC-based Multiplexing encapsulation
	}

pgLantTable OBJECT-TYPE
	SYNTAX		SEQUENCE OF PgLantEntry
	MAX-ACCESS	not-accessible
	STATUS		current
	DESCRIPTION	"A table of encapsulation and forwarding information
			for the LAN Tunneling service"
	::= {pgLantObjects 1}

pgLantEntry OBJECT-TYPE
	SYNTAX		PgLantEntry
	MAX-ACCESS	not-accessible
	STATUS		current
	DESCRIPTION	"The encapsulation and forwarding information for one
			the LAN Tunnel"
	INDEX		{pgLantChannelPortIfIndex}
	::= {pgLantTable 1}
 
PgLantEntry ::=
	SEQUENCE {
		pgLantChannelPortIfIndex	INTEGER,
		pgLantLinePortIfIndex		INTEGER,
		pgLantVpi			INTEGER,
		pgLantVci			INTEGER,
		pgLantEncapMode			PgLantEncapType,
                pgLantRowStatus			RowStatus
	}
 
pgLantChannelPortIfIndex OBJECT-TYPE
	SYNTAX		INTEGER (1..2047)
	MAX-ACCESS	read-only
	STATUS		current
	DESCRIPTION	"The Interface Index for the channel(xDSL) port that is
			to be connected to a PVC tunnel."
	::= {pgLantEntry 1}
 
pgLantLinePortIfIndex OBJECT-TYPE
	SYNTAX		INTEGER (1..2047)
	MAX-ACCESS	read-write
	STATUS		current
	DESCRIPTION	"The Interface Index for the line(OC3) port that the
			PVC is resided."
	::= {pgLantEntry 2}
 
pgLantVpi OBJECT-TYPE
	SYNTAX		INTEGER (0..255)
	MAX-ACCESS	read-write
	STATUS		current
	DESCRIPTION	"The internal VPI for the ATM PVC that is connected to
			the tunnel"
	::= {pgLantEntry 3}
 
pgLantVci OBJECT-TYPE
	SYNTAX		INTEGER (0..65535)
	MAX-ACCESS	read-write
	STATUS		current
	DESCRIPTION	"The internal VCI for the ATM PVC that is connected to
			the tunnel"
	::= {pgLantEntry 4}
 
pgLantEncapMode OBJECT-TYPE
	SYNTAX		PgLantEncapType
	MAX-ACCESS	read-write
	STATUS		current
	DESCRIPTION	"The encapsulation mode that is used by the tunnel"
	::= {pgLantEntry 5}

pgLantRowStatus OBJECT-TYPE
	SYNTAX		RowStatus
	MAX-ACCESS	read-create
	STATUS		current
	DESCRIPTION	"This object allows entries to be created and deleted
			in the pgLantTable. The RowStatus should be out of 
			the ACTIVE state for other columns to be modified."
	::= {pgLantEntry 6}

END
