------------------------------------------------------------------------------
--
-- File: MultiBridge.mib
--
-- Module Spec:
--
-- Contents:
--      Newbridge Extensions to the BRIDGE MIB for nodes that implement more
--      than one bridge.
--
-- History:
--      48A0003 / 97.03.19 / M. Dubois  / Creation
--      48A0003 / 97.03.20 / M. Dubois  / moved bridge to before MAC in index
--      48A0003 / 97.03.25 / M. Dubois  / update after review
--      48A0003 / 97.0x.xx / M. Dubois  / extensions number is xx
-- 
-- %%history-start%%
-- 1999.05.26 dylans 31A1284: atm.van2 trib merge 
-- %%history-end%%
--
-- Copyright 1995,96,97 Newbridge Networks Corporation.  All rights reserved.
--
--------------------------------------------------------------------------------
MULTIBRIDGE-MIB DEFINITIONS ::= BEGIN

          IMPORTS
             MODULE-IDENTITY, OBJECT-TYPE, TimeTicks, Counter32   
                                             FROM SNMPv2-SMI
             TEXTUAL-CONVENTION            FROM SNMPv2-TC
             nncExtensions                 FROM NNCGNI0001-SMI;
--           TRAP-TYPE                       FROM RFC1215-MIB;

        nncExtMultiBridge MODULE-IDENTITY
            LAST-UPDATED    "9703251140Z"
            ORGANIZATION    "Newbridge Networks Corporation"
            CONTACT-INFO    "Newbridge Networks Corporation
                             Postal: 600 March Road
                                     Kanata, Ontario
                                     Canada K2K 2E6

                             Phone:  +1 613 591 3600
                             Fax:    +1 613 591 3680"
            DESCRIPTION     "Newbridge's multi-BRIDGE MIB Module.
                             for nodes which implements more than
                             one bridge entity."
            ::= { nncExtensions 43 }

          -- taken from BRIDGE-MIB
          MacAddress ::= OCTET STRING (SIZE (6))
          BridgeId ::= OCTET STRING (SIZE (8))
          Timeout ::= INTEGER

          mBrdgBase     OBJECT IDENTIFIER ::= { nncExtMultiBridge 1 }

          mBrdgStp      OBJECT IDENTIFIER ::= { nncExtMultiBridge 2 }

          mBrdgTp       OBJECT IDENTIFIER ::= { nncExtMultiBridge 3 }

          mBrdgStatic   OBJECT IDENTIFIER ::= { nncExtMultiBridge 4 }

          mBrdgConfig   OBJECT IDENTIFIER ::= { nncExtMultiBridge 5 }

          -- the mBrdgBase TABLE group

          mBrdgBaseTable     OBJECT-TYPE
              SYNTAX  SEQUENCE OF MBrdgBaseEntry
              MAX-ACCESS  not-accessible
              STATUS  current
              DESCRIPTION
                      "This table contains scalar values defined under
                       dot1dBase in BRIDGE-MIB.  Rows cannot be added to
                       nor deleted from this table."
              ::= { mBrdgBase 1 }

          mBrdgBaseEntry OBJECT-TYPE
              SYNTAX  MBrdgBaseEntry
              MAX-ACCESS  not-accessible
              STATUS  current
              DESCRIPTION
                      "A list of information for each bridge of the
                      Node."
              REFERENCE
                      "IEEE 802.1D-1990: Section 6.4.2, 6.6.1"
              INDEX  { mBrdgBaseBridgeAddress }
              ::= { mBrdgBaseTable 1 }
 
          MBrdgBaseEntry ::=
              SEQUENCE {
                  mBrdgBaseBridgeAddress
                      MacAddress,
                  mBrdgBaseNumPorts
                      INTEGER,
                  mBrdgBaseType
                      INTEGER
              }

          mBrdgBaseBridgeAddress OBJECT-TYPE
              SYNTAX  MacAddress
              MAX-ACCESS  read-only
              STATUS  current
              DESCRIPTION
                      "The MAC address used by this bridge when it must
                      be referred to in a unique fashion.   It is
                      recommended that this be the numerically smallest
                      MAC address of all ports that belong to this
                      bridge.  However it is only required to be unique.
                      When concatenated with mBrdgStpPriority a unique
                      BridgeIdentifier is formed which is used in the
                      Spanning Tree Protocol."
              REFERENCE
                      "IEEE 802.1D-1990: Sections 6.4.1.1.3 and 3.12.5"
              ::= { mBrdgBaseEntry 1 }

          mBrdgBaseNumPorts OBJECT-TYPE
              SYNTAX  INTEGER
              MAX-ACCESS  read-only
              STATUS  current
              DESCRIPTION
                      "The number of ports controlled by this bridging
                      entity."
              REFERENCE
                      "IEEE 802.1D-1990: Section 6.4.1.1.3"
              ::= { mBrdgBaseEntry 2 }

          mBrdgBaseType OBJECT-TYPE
              SYNTAX  INTEGER {
                          unknown(1),
                          transparentOnly(2),
                          sourcerouteOnly(3),
                          srt(4)
                      }
              MAX-ACCESS  read-only
              STATUS  current
              DESCRIPTION
                      "Indicates what type of bridging this bridge can
                      perform.  If a bridge is actually performing a
                      certain type of bridging this will be indicated by
                      entries in the port table for the given type."
              ::= { mBrdgBaseEntry 3 }

          -- The Generic Bridge Port Table

          mBrdgBasePortTable OBJECT-TYPE
              SYNTAX  SEQUENCE OF MBrdgBasePortEntry
              MAX-ACCESS  not-accessible
              STATUS  current
              DESCRIPTION
                      "A table that contains generic information about
                      every port that is associated with this bridge.
                      Transparent, source-route, and srt ports are
                      included. Rows cannot be added to nor deleted from
                      this table."
              ::= { mBrdgBase 2 }

          mBrdgBasePortEntry OBJECT-TYPE
              SYNTAX  MBrdgBasePortEntry
              MAX-ACCESS  not-accessible
              STATUS  current
              DESCRIPTION
                      "A list of information for each port of the
                      bridge."
              REFERENCE
                      "IEEE 802.1D-1990: Section 6.4.2, 6.6.1"
              INDEX  { mBrdgBasePortBridgeIndex, mBrdgBasePort }
              ::= { mBrdgBasePortTable 1 }

          MBrdgBasePortEntry ::=
              SEQUENCE {
                  mBrdgBasePort
                      INTEGER,
                  mBrdgBasePortIfIndex
                      INTEGER,
                  mBrdgBasePortCircuit
                      OBJECT IDENTIFIER,
                  mBrdgBasePortDelayExceededDiscards
                      Counter32,
                  mBrdgBasePortMtuExceededDiscards
                      Counter32,
                  mBrdgBasePortBridgeIndex
                      INTEGER
              }

          mBrdgBasePort OBJECT-TYPE
              SYNTAX  INTEGER (1..65535)
              MAX-ACCESS  read-only
              STATUS  current
              DESCRIPTION
                      "The port number of the port for which this entry
                      contains bridge management information."
              ::= { mBrdgBasePortEntry 1 }

          mBrdgBasePortIfIndex OBJECT-TYPE
              SYNTAX  INTEGER
              MAX-ACCESS  read-only
              STATUS  current
              DESCRIPTION
                      "The value of the instance of the ifIndex object,
                      defined in MIB-II, for the interface corresponding
                      to this port."
              ::= { mBrdgBasePortEntry 2 }

          mBrdgBasePortCircuit OBJECT-TYPE
              SYNTAX  OBJECT IDENTIFIER
              MAX-ACCESS  read-only
              STATUS  current
              DESCRIPTION
                      "For a port which (potentially) has the same value
                      of mBrdgBasePortIfIndex as another port on the
                      same bridge, this object contains the name of an
                      object instance unique to this port.  For example,
                      in the case where mBrdgple ports correspond one-
                      to-one with mBrdgple X.25 virtual circuits, this
                      value might identify an (e.g., the first) object
                      instance associated with the X.25 virtual circuit
                      corresponding to this port.

                      For a port which has a unique value of
                      mBrdgBasePortIfIndex, this object can have the
                      value { 0 0 }."
              ::= { mBrdgBasePortEntry 3 }

          mBrdgBasePortDelayExceededDiscards OBJECT-TYPE
              SYNTAX  Counter32


              MAX-ACCESS  read-only
              STATUS  current
              DESCRIPTION
                      "The number of frames discarded by this port due
                      to excessive transit delay through the bridge.  It
                      is incremented by both transparent and source
                      route bridges."
              REFERENCE
                       "IEEE 802.1D-1990: Section 6.6.1.1.3"
              ::= { mBrdgBasePortEntry 4 }

          mBrdgBasePortMtuExceededDiscards OBJECT-TYPE
              SYNTAX  Counter32
              MAX-ACCESS  read-only
              STATUS  current
              DESCRIPTION
                      "The number of frames discarded by this port due
                      to an excessive size.  It is incremented by both
                      transparent and source route bridges."
              REFERENCE
                      "IEEE 802.1D-1990: Section 6.6.1.1.3"
              ::= { mBrdgBasePortEntry 5 }

          mBrdgBasePortBridgeIndex OBJECT-TYPE
              SYNTAX  INTEGER (1..65535)
              MAX-ACCESS  read-only
              STATUS  current
              DESCRIPTION
                      "The bridge number for which this entry
                      contains bridge management information."
              ::= { mBrdgBasePortEntry 6 }

          -- the mBrdgStp TABLE group

          mBrdgStpTable     OBJECT-TYPE
              SYNTAX  SEQUENCE OF MBrdgStpEntry
              MAX-ACCESS  not-accessible
              STATUS  current
              DESCRIPTION
                      "This table contains scalar values defined under
                       dot1dStp in BRIDGE-MIB.  Rows cannot be added to
                       nor deleted from this table."
              ::= { mBrdgStp 1 }

          mBrdgStpEntry OBJECT-TYPE
              SYNTAX  MBrdgStpEntry
              MAX-ACCESS  not-accessible
              STATUS  current
              DESCRIPTION
                      "A list of information for each bridge of the
                      Node."
              REFERENCE
                      "IEEE 802.1D-1990: Section 6.4.2, 6.6.1"
              INDEX  { mBrdgStpBridgeIndex }
              ::= { mBrdgStpTable 1 }
 
          MBrdgStpEntry ::=
              SEQUENCE {
                  mBrdgStpProtocolSpecification
                      INTEGER,
                  mBrdgStpPriority
                      INTEGER,
                  mBrdgStpTimeSinceTopologyChange
                      TimeTicks,
                  mBrdgStpTopChanges
                      Counter32,
                  mBrdgStpDesignatedRoot
                      BridgeId,
                  mBrdgStpRootCost
                      INTEGER,
                  mBrdgStpRootPort
                      INTEGER,
                  mBrdgStpMaxAge
                      Timeout,
                  mBrdgStpHelloTime
                      Timeout,
                  mBrdgStpHoldTime
                      INTEGER,
                  mBrdgStpForwardDelay
                      Timeout,
                  mBrdgStpBridgeMaxAge
                      Timeout,
                  mBrdgStpBridgeHelloTime
                      Timeout,
                  mBrdgStpBridgeForwardDelay
                      Timeout,
                  mBrdgStpEnable
                      INTEGER,
                  mBrdgStpBridgeIndex
                      INTEGER
              }

          -- Implementation of the mBrdgStp group is optional.  It is
          -- implemented by those bridges that support the Spanning Tree
          -- Protocol.

          mBrdgStpProtocolSpecification OBJECT-TYPE
              SYNTAX  INTEGER {
                          unknown(1),
                          decLb100(2),
                          ieee8021d(3)
                      }
              MAX-ACCESS  read-only
              STATUS  current
              DESCRIPTION
                      "An indication of what version of the Spanning
                      Tree Protocol is being run.  The value
                      'decLb100(2)' indicates the DEC LANbridge 100
                      Spanning Tree protocol.  IEEE 802.1d
                      implementations will return 'ieee8021d(3)'.  If
                      future versions of the IEEE Spanning Tree Protocol
                      are released that are incompatible with the
                      current version a new value will be defined."
              ::= { mBrdgStpEntry 1 }

          mBrdgStpPriority OBJECT-TYPE
              SYNTAX  INTEGER (0..65535)
              MAX-ACCESS  read-write
              STATUS  current
              DESCRIPTION
                      "The value of the write-able portion of the Bridge
                      ID, i.e., the first two octets of the (8 octet
                      long) Bridge ID.  The other (last) 6 octets of the
                      Bridge ID are given by the value of
                      mBrdgBaseTableBridgeAddress."
              REFERENCE
                      "IEEE 802.1D-1990: Section 4.5.3.7"
              ::= { mBrdgStpEntry 2 }

          mBrdgStpTimeSinceTopologyChange OBJECT-TYPE
              SYNTAX  TimeTicks
              MAX-ACCESS  read-only
              STATUS  current
              DESCRIPTION
                      "The time (in hundredths of a second) since the
                      last time a topology change was detected by the
                      bridge entity."
              REFERENCE
                      "IEEE 802.1D-1990: Section 6.8.1.1.3"
              ::= { mBrdgStpEntry 3 }

          mBrdgStpTopChanges OBJECT-TYPE
              SYNTAX  Counter32
              MAX-ACCESS  read-only
              STATUS  current
              DESCRIPTION
                      "The total number of topology changes detected by
                      this bridge since the management entity was last
                      reset or initialized."
              REFERENCE
                      "IEEE 802.1D-1990: Section 6.8.1.1.3"
              ::= { mBrdgStpEntry 4 }

          mBrdgStpDesignatedRoot OBJECT-TYPE
              SYNTAX  BridgeId
              MAX-ACCESS  read-only
              STATUS  current
              DESCRIPTION
                      "The bridge identifier of the root of the spanning
                      tree as determined by the Spanning Tree Protocol
                      as executed by this node.  This value is used as
                      the Root Identifier parameter in all Configuration
                      Bridge PDUs originated by this node."
              REFERENCE
                      "IEEE 802.1D-1990: Section 4.5.3.1"
              ::= { mBrdgStpEntry 5 }

          mBrdgStpRootCost OBJECT-TYPE
              SYNTAX  INTEGER
              MAX-ACCESS  read-only
              STATUS  current
              DESCRIPTION
                      "The cost of the path to the root as seen from
                      this bridge."
              REFERENCE
                      "IEEE 802.1D-1990: Section 4.5.3.2"
              ::= { mBrdgStpEntry 6 }

          mBrdgStpRootPort OBJECT-TYPE
              SYNTAX  INTEGER
              MAX-ACCESS  read-only
              STATUS  current
              DESCRIPTION
                      "The port number of the port which offers the
                      lowest cost path from this bridge to the root
                      bridge."
              REFERENCE
                      "IEEE 802.1D-1990: Section 4.5.3.3"
              ::= { mBrdgStpEntry 7 }

          mBrdgStpMaxAge OBJECT-TYPE
              SYNTAX  Timeout
              MAX-ACCESS  read-only
              STATUS  current
              DESCRIPTION
                      "The maximum age of Spanning Tree Protocol
                      information learned from the network on any port
                      before it is discarded, in units of hundredths of
                      a second.  This is the actual value that this
                      bridge is currently using."
              REFERENCE
                      "IEEE 802.1D-1990: Section 4.5.3.4"
              ::= { mBrdgStpEntry 8 }

          mBrdgStpHelloTime OBJECT-TYPE
              SYNTAX  Timeout
              MAX-ACCESS  read-only
              STATUS  current
              DESCRIPTION
                      "The amount of time between the transmission of
                      Configuration bridge PDUs by this node on any port
                      when it is the root of the spanning tree or trying
                      to become so, in units of hundredths of a second.
                      This is the actual value that this bridge is
                      currently using."
              REFERENCE
                      "IEEE 802.1D-1990: Section 4.5.3.5"
              ::= { mBrdgStpEntry 9 }

          mBrdgStpHoldTime OBJECT-TYPE
              SYNTAX  INTEGER
              MAX-ACCESS  read-only
              STATUS  current
              DESCRIPTION
                      "This time value determines the interval length
                      during which no more than two Configuration bridge
                      PDUs shall be transmitted by this node, in units
                      of hundredths of a second."
              REFERENCE
                      "IEEE 802.1D-1990: Section 4.5.3.14"
              ::= { mBrdgStpEntry 10 }

          mBrdgStpForwardDelay OBJECT-TYPE
              SYNTAX  Timeout
              MAX-ACCESS  read-only
              STATUS  current
              DESCRIPTION
                      "This time value, measured in units of hundredths
                      of a second, controls how fast a port changes its
                      spanning state when moving towards the Forwarding
                      state.  The value determines how long the port
                      stays in each of the Listening and Learning
                      states, which precede the Forwarding state.  This
                      value is also used, when a topology change has
                      been detected and is underway, to age all dynamic
                      entries in the Forwarding Database.  [Note that
                      this value is the one that this bridge is
                      currently using, in contrast to
                      mBrdgStpBridgeForwardDelay which is the value that
                      this bridge and all others would start using
                      if/when this bridge were to become the root.]"
              REFERENCE
                      "IEEE 802.1D-1990: Section 4.5.3.6"
              ::= { mBrdgStpEntry 11 }

          mBrdgStpBridgeMaxAge OBJECT-TYPE
              SYNTAX  Timeout (600..4000)
              MAX-ACCESS  read-write
              STATUS  current
              DESCRIPTION
                      "The value that all bridges use for MaxAge when
                      this bridge is acting as the root.  Note that
                      802.1D-1990 specifies that the range for this
                      parameter is related to the value of
                      mBrdgStpBridgeHelloTime. The granularity of this
                      timer is specified by 802.1D-1990 to be 1 second.
                      An agent may return a badValue error if a set is
                      attempted to a value which is not a whole number
                      of seconds."
              REFERENCE
                      "IEEE 802.1D-1990: Section 4.5.3.8"
              ::= { mBrdgStpEntry 12 }

          mBrdgStpBridgeHelloTime OBJECT-TYPE
              SYNTAX  Timeout (100..1000)
              MAX-ACCESS  read-write
              STATUS  current
              DESCRIPTION
                      "The value that all bridges use for HelloTime when
                      this bridge is acting as the root.  The
                      granularity of this timer is specified by 802.1D-
                      1990 to be 1 second.  An agent may return a
                      badValue error if a set is attempted to a value
                      which is not a whole number of seconds."
              REFERENCE
                      "IEEE 802.1D-1990: Section 4.5.3.9"
              ::= { mBrdgStpEntry 13 }

          mBrdgStpBridgeForwardDelay OBJECT-TYPE
              SYNTAX  Timeout (400..3000)
              MAX-ACCESS  read-write
              STATUS  current
              DESCRIPTION
                      "The value that all bridges use for ForwardDelay
                      when this bridge is acting as the root.  Note that
                      802.1D-1990 specifies that the range for this
                      parameter is related to the value of
                      mBrdgStpBridgeMaxAge.  The granularity of this
                      timer is specified by 802.1D-1990 to be 1 second.
                      An agent may return a badValue error if a set is
                      attempted to a value which is not a whole number
                      of seconds."
              REFERENCE
                      "IEEE 802.1D-1990: Section 4.5.3.10"
              ::= { mBrdgStpEntry 14 }

            mBrdgStpEnable       OBJECT-TYPE
              SYNTAX  INTEGER {
                        enabled(1),
                        disabled(2),
                        unavailable(3)
                    }
              MAX-ACCESS  read-write
              STATUS  current
              DESCRIPTION
                      "Specifies if this bridge entity has an instance
                       of the Spanning Tree Protocol running."
              ::= {mBrdgStpEntry 15}

          mBrdgStpBridgeIndex OBJECT-TYPE
              SYNTAX  INTEGER (1..65535)
              MAX-ACCESS  read-only
              STATUS  current
              DESCRIPTION
                      "The bridge number for which this entry
                      contains bridge management information."
              ::= { mBrdgStpEntry 16 }

          -- The Spanning Tree Port Table

          mBrdgStpPortTable OBJECT-TYPE
              SYNTAX  SEQUENCE OF MBrdgStpPortEntry
              MAX-ACCESS  not-accessible
              STATUS  current
              DESCRIPTION
                      "A table that contains port-specific information
                      for the Spanning Tree Protocol.  Rows cannot be added
                      to nor deleted from this table."
              ::= { mBrdgStp 2 }

          mBrdgStpPortEntry OBJECT-TYPE
              SYNTAX  MBrdgStpPortEntry
              MAX-ACCESS  not-accessible
              STATUS  current
              DESCRIPTION
                      "A list of information maintained by every port
                      about the Spanning Tree Protocol state for that
                      port."
              INDEX   { mBrdgStpPortBridgeIndex, mBrdgStpPort }
              ::= { mBrdgStpPortTable 1 }

          MBrdgStpPortEntry ::=
              SEQUENCE {
                  mBrdgStpPort
                      INTEGER,
                  mBrdgStpPortPriority
                      INTEGER,
                  mBrdgStpPortState
                      INTEGER,
                  mBrdgStpPortEnable
                      INTEGER,
                  mBrdgStpPortPathCost
                      INTEGER,
                  mBrdgStpPortDesignatedRoot
                      BridgeId,
                  mBrdgStpPortDesignatedCost
                      INTEGER,
                  mBrdgStpPortDesignatedBridge
                      BridgeId,
                  mBrdgStpPortDesignatedPort
                      OCTET STRING,
                  mBrdgStpPortForwardTransitions
                      Counter32,
                  mBrdgStpPortStatsTxBPDUCount
                      Counter32,
                  mBrdgStpPortStatsRxBPDUCount
                      Counter32,
                  mBrdgStpPortBridgeIndex
                      INTEGER
              }

          mBrdgStpPort OBJECT-TYPE
              SYNTAX  INTEGER (1..65535)


              MAX-ACCESS  read-only
              STATUS  current
              DESCRIPTION
                      "The port number of the port for which this entry
                      contains Spanning Tree Protocol management
                      information."
              REFERENCE
                      "IEEE 802.1D-1990: Section 6.8.2.1.2"
              ::= { mBrdgStpPortEntry 1 }

          mBrdgStpPortPriority OBJECT-TYPE
              SYNTAX  INTEGER (0..255)
              MAX-ACCESS  read-write
              STATUS  current
              DESCRIPTION
                      "The value of the priority field which is
                      contained in the first (in network byte order)
                      octet of the (2 octet long) Port ID.  The other
                      octet of the Port ID is given by the value of
                      mBrdgStpPort."
              REFERENCE
                      "IEEE 802.1D-1990: Section 4.5.5.1"
              ::= { mBrdgStpPortEntry 2 }

          mBrdgStpPortState OBJECT-TYPE
              SYNTAX  INTEGER {
                          disabled(1),
                          blocking(2),
                          listening(3),
                          learning(4),
                          forwarding(5),
                          broken(6)
                      }
              MAX-ACCESS  read-only
              STATUS  current
              DESCRIPTION
                      "The port's current state as defined by
                      application of the Spanning Tree Protocol.  This
                      state controls what action a port takes on
                      reception of a frame.  If the bridge has detected
                      a port that is malfunctioning it will place that
                      port into the broken(6) state.  For ports which
                      are disabled (see mBrdgStpPortEnable), this object
                      will have a value of disabled(1)."
              REFERENCE
                      "IEEE 802.1D-1990: Section 4.5.5.2"
              ::= { mBrdgStpPortEntry 3 }


          mBrdgStpPortEnable OBJECT-TYPE
              SYNTAX  INTEGER {
                          enabled(1),
                          disabled(2)
                      }
              MAX-ACCESS  read-write
              STATUS  current
              DESCRIPTION
                      "The enabled/disabled status of the port."
              REFERENCE
                      "IEEE 802.1D-1990: Section 4.5.5.2"
              ::= { mBrdgStpPortEntry 4 }

          mBrdgStpPortPathCost OBJECT-TYPE
              SYNTAX  INTEGER (1..65535)
              MAX-ACCESS  read-write
              STATUS  current
              DESCRIPTION
                      "The contribution of this port to the path cost of
                      paths towards the spanning tree root which include
                      this port.  802.1D-1990 recommends that the
                      default value of this parameter be in inverse
                      proportion to the speed of the attached LAN."
              REFERENCE
                      "IEEE 802.1D-1990: Section 4.5.5.3"
              ::= { mBrdgStpPortEntry 5 }

          mBrdgStpPortDesignatedRoot OBJECT-TYPE
              SYNTAX  BridgeId
              MAX-ACCESS  read-only
              STATUS  current
              DESCRIPTION
                      "The unique Bridge Identifier of the Bridge
                      recorded as the Root in the Configuration BPDUs
                      transmitted by the Designated Bridge for the
                      segment to which the port is attached."
              REFERENCE
                      "IEEE 802.1D-1990: Section 4.5.5.4"
              ::= { mBrdgStpPortEntry 6 }

          mBrdgStpPortDesignatedCost OBJECT-TYPE
              SYNTAX  INTEGER
              MAX-ACCESS  read-only
              STATUS  current
              DESCRIPTION
                      "The path cost of the Designated Port of the
                      segment connected to this port.  This value is
                      compared to the Root Path Cost field in received
                      bridge PDUs."
              REFERENCE
                      "IEEE 802.1D-1990: Section 4.5.5.5"
              ::= { mBrdgStpPortEntry 7 }

          mBrdgStpPortDesignatedBridge OBJECT-TYPE
              SYNTAX  BridgeId
              MAX-ACCESS  read-only
              STATUS  current
              DESCRIPTION
                      "The Bridge Identifier of the bridge which this
                      port considers to be the Designated Bridge for
                      this port's segment."
              REFERENCE
                      "IEEE 802.1D-1990: Section 4.5.5.6"
              ::= { mBrdgStpPortEntry 8 }

          mBrdgStpPortDesignatedPort OBJECT-TYPE
              SYNTAX  OCTET STRING (SIZE (2))
              MAX-ACCESS  read-only
              STATUS  current
              DESCRIPTION
                      "The Port Identifier of the port on the Designated
                      Bridge for this port's segment."
              REFERENCE
                      "IEEE 802.1D-1990: Section 4.5.5.7"
              ::= { mBrdgStpPortEntry 9 }

          mBrdgStpPortForwardTransitions OBJECT-TYPE
              SYNTAX  Counter32
              MAX-ACCESS  read-only
              STATUS  current
              DESCRIPTION
                      "The number of times this port has transitioned
                      from the Learning state to the Forwarding state."
              ::= { mBrdgStpPortEntry 10 }

          mBrdgStpPortStatsTxBPDUCount  OBJECT-TYPE
              SYNTAX  Counter32
              MAX-ACCESS  read-write
              STATUS current
              DESCRIPTION
                      "The total number of BPDU's sent on this port.
                       Sets may only be done with a value of 0."
              ::= { mBrdgStpPortEntry 11 }
 
          mBrdgStpPortStatsRxBPDUCount  OBJECT-TYPE
              SYNTAX  Counter32
              MAX-ACCESS  read-write
              STATUS current
              DESCRIPTION
                      "The total number of BPDU's received on this port.
                       Sets may only be done with a value of 0."
              ::= { mBrdgStpPortEntry 12 }

          mBrdgStpPortBridgeIndex OBJECT-TYPE
              SYNTAX  INTEGER (1..65535)
              MAX-ACCESS  read-only
              STATUS  current
              DESCRIPTION
                      "The bridge number for which this entry
                      contains bridge management information."
              ::= { mBrdgStpPortEntry 13 }
 

          -- the mBrdgTp TABLE group

          -- Implementation of the mBrdgTp group is optional.  It is
          -- implemented by those bridges that support the transparent
          -- bridging mode.  A transparent or SRT bridge will implement
          -- this group.

          mBrdgTpTable     OBJECT-TYPE
              SYNTAX  SEQUENCE OF MBrdgTpEntry
              MAX-ACCESS  not-accessible
              STATUS  current
              DESCRIPTION
                      "This table contains scalar values defined under
                       dot1dTp in BRIDGE-MIB.  Rows cannot be added to
                       nor deleted from this table."
              ::= { mBrdgTp 1 }

          mBrdgTpEntry OBJECT-TYPE
              SYNTAX  MBrdgTpEntry
              MAX-ACCESS  not-accessible
              STATUS  current
              DESCRIPTION
                      "A list of information for each bridge of the
                      Node."
              REFERENCE
                      "IEEE 802.1D-1990: Section 6.4.2, 6.6.1"
              INDEX  { mBrdgTpBridgeIndex }
              ::= { mBrdgTpTable 1 }

          MBrdgTpEntry ::=
              SEQUENCE {
                  mBrdgTpLearnedEntryDiscards
                      Counter32,
                  mBrdgTpAgingTime
                      INTEGER,
                  mBrdgTpLearningEnable
                      INTEGER,
                  mBrdgTpFdbNumLearnedEntries
                      INTEGER,
                  mBrdgTpFdbNumEntries
                      INTEGER,
                  mBrdgTpBridgeIndex
                      INTEGER
              }

          mBrdgTpLearnedEntryDiscards OBJECT-TYPE
              SYNTAX  Counter32
              MAX-ACCESS  read-only
              STATUS  current
              DESCRIPTION
                      "The total number of Forwarding Database entries,
                      which have been or would have been learnt, but
                      have been discarded due to a lack of space to
                      store them in the Forwarding Database.  If this
                      counter is increasing, it indicates that the
                      Forwarding Database is regularly becoming full (a
                      condition which has unpleasant performance effects
                      on the subnetwork).  If this counter has a
                      significant value but is not presently increasing,
                      it indicates that the problem has been occurring
                      but is not persistent."
              REFERENCE
                      "IEEE 802.1D-1990: Section 6.7.1.1.3"
              ::= { mBrdgTpEntry 1 }

          mBrdgTpAgingTime OBJECT-TYPE
              SYNTAX   INTEGER (10..1000000)
              MAX-ACCESS   read-write
              STATUS   current
              DESCRIPTION
                      "The timeout period in seconds for aging out
                      dynamically learned forwarding information.
                      802.1D-1990 recommends a default of 300 seconds."
              REFERENCE
                      "IEEE 802.1D-1990: Section 6.7.1.1.3"
              ::= { mBrdgTpEntry 2 }

          mBrdgTpLearningEnable  OBJECT-TYPE
              SYNTAX  INTEGER {
                        enabled(1),
                        disabled(2)
                      }
              MAX-ACCESS  read-write
              STATUS  current
              DESCRIPTION
                      "Specifies if this bridge entity will learn new
                       MAC addresses."
              ::= { mBrdgTpEntry 3 }
 
          mBrdgTpFdbNumLearnedEntries  OBJECT-TYPE
              SYNTAX  INTEGER 
              MAX-ACCESS  read-write
              STATUS  current
              DESCRIPTION
                      "Returns the number of learned stations in the
                       filtering database.  Writing 0 clears all the
                       entries (learned entries only)."
              ::= { mBrdgTpEntry 4 }

          mBrdgTpFdbNumEntries  OBJECT-TYPE
              SYNTAX  INTEGER 
              MAX-ACCESS  read-write
              STATUS  current
              DESCRIPTION
                      "Returns the number of stations (static and learned)
                       in the filtering database.  Writing 0 clears all the
                       entries (static and learned)."
              ::= { mBrdgTpEntry 5 }

          mBrdgTpBridgeIndex OBJECT-TYPE
              SYNTAX  INTEGER (1..65535)
              MAX-ACCESS  read-only
              STATUS  current
              DESCRIPTION
                      "The bridge number for which this entry
                      contains bridge management information."
              ::= { mBrdgTpEntry 6 }

          --  The Forwarding Database for Transparent Bridges

          mBrdgTpFdbTable OBJECT-TYPE
              SYNTAX  SEQUENCE OF MBrdgTpFdbEntry
              MAX-ACCESS  not-accessible
              STATUS  current
              DESCRIPTION
                      "A table that contains information about unicast
                      entries for which the bridge has forwarding and/or
                      filtering information.  This information is used
                      by the transparent bridging function in
                      determining how to propagate a received frame.
                      Rows cannot be added to this table.  To delete
                      rows, see mBrdgTpFdbStatus."
              ::= { mBrdgTp 2 }

          mBrdgTpFdbEntry OBJECT-TYPE
              SYNTAX  MBrdgTpFdbEntry
              MAX-ACCESS  not-accessible
              STATUS  current
              DESCRIPTION
                      "Information about a specific unicast MAC address
                      for which the bridge has some forwarding and/or
                      filtering information."
              INDEX   { mBrdgTpFdbBridgeIndex, mBrdgTpFdbAddress }
              ::= { mBrdgTpFdbTable 1 }

          MBrdgTpFdbEntry ::=
              SEQUENCE {
                  mBrdgTpFdbAddress
                      MacAddress,
                  mBrdgTpFdbPort
                      INTEGER,
                  mBrdgTpFdbStatus
                      INTEGER,
                  mBrdgTpFdbBridgeIndex
                      INTEGER
              }

          mBrdgTpFdbAddress OBJECT-TYPE
              SYNTAX  MacAddress
              MAX-ACCESS  read-only
              STATUS  current
              DESCRIPTION
                      "A unicast MAC address for which the bridge has
                      forwarding and/or filtering information."
              REFERENCE
                      "IEEE 802.1D-1990: Section 3.9.1, 3.9.2"
              ::= { mBrdgTpFdbEntry 1 }

          mBrdgTpFdbPort OBJECT-TYPE
              SYNTAX  INTEGER
              MAX-ACCESS  read-only
              STATUS  current
              DESCRIPTION
                      "Either the value '0', or the port number of the
                      port on which a frame having a source address
                      equal to the value of the corresponding instance
                      of mBrdgTpFdbAddress has been seen.  A value of
                      '0' indicates that the port number has not been
                      learned but that the bridge does have some
                      forwarding/filtering information about this
                      address (e.g. in the mBrdgStaticTable).
                      Implementors are encouraged to assign the port
                      value to this object whenever it is learned even
                      for addresses for which the corresponding value of
                      mBrdgTpFdbStatus is not learned(3)."
              ::= { mBrdgTpFdbEntry 2 }


          mBrdgTpFdbStatus OBJECT-TYPE
              SYNTAX  INTEGER {
                          other(1),
                          invalid(2),
                          learned(3),
                          self(4),
                          mgmt(5)
                      }
              MAX-ACCESS  read-only
              STATUS  current
              DESCRIPTION
                      "The status of this entry.  The meanings of the
                      values are:

                        other(1)   : none of the following.  This would
                                     include the case where some other
                                     MIB object (not the corresponding
                                     instance of mBrdgTpFdbPort, nor an
                                     entry in the mBrdgStaticTable) is
                                     being used to determine if and how
                                     frames addressed to the value of
                                     the corresponding instance of
                                     mBrdgTpFdbAddress are being
                                     forwarded.

                        invalid(2) : this entry is not longer valid
                                     (e.g., it was learned but has since
                                     aged-out), but has not yet been
                                     flushed from the table.

                        learned(3) : the value of the corresponding
                                     instance of mBrdgTpFdbPort was
                                     learned, and is being used.

                        self(4)    : the value of the corresponding
                                     instance of mBrdgTpFdbAddress
                                     represents one of the bridge's
                                     addresses.  The corresponding
                                     instance of mBrdgTpFdbPort
                                     indicates which of the bridge's
                                     ports has this address.

                        mgmt(5)    : the value of the corresponding
                                     instance of mBrdgTpFdbAddress is
                                     also the value of an existing
                                     instance of mBrdgStaticAddress."
              ::= { mBrdgTpFdbEntry 3 }

          mBrdgTpFdbBridgeIndex OBJECT-TYPE
              SYNTAX  INTEGER (1..65535)
              MAX-ACCESS  read-only
              STATUS  current
              DESCRIPTION
                      "The bridge number for which this entry
                      contains bridge management information."
              ::= { mBrdgTpFdbEntry 4 }

          --  Port Table for Transparent Bridges

          mBrdgTpPortTable OBJECT-TYPE
              SYNTAX  SEQUENCE OF MBrdgTpPortEntry
              MAX-ACCESS  not-accessible
              STATUS  current
              DESCRIPTION
                      "A table that contains information about every
                      port that is associated with this transparent
                      bridge.  Rows cannot be added to nor deleted from
                      this table."
              ::= { mBrdgTp 3 }

          mBrdgTpPortEntry OBJECT-TYPE
              SYNTAX  MBrdgTpPortEntry
              MAX-ACCESS  not-accessible
              STATUS  current
              DESCRIPTION
                      "A list of information for each port of a
                      transparent bridge."
              INDEX   { mBrdgTpPortBridgeIndex, mBrdgTpPort }
              ::= { mBrdgTpPortTable 1 }

          MBrdgTpPortEntry ::=
              SEQUENCE {
                  mBrdgTpPort
                      INTEGER,
                  mBrdgTpPortMaxInfo
                      INTEGER,
                  mBrdgTpPortInFrames
                      Counter32,
                  mBrdgTpPortOutFrames
                      Counter32,
                  mBrdgTpPortInDiscards
                      Counter32,
                  mBrdgTpPortBridgeIndex
                      INTEGER
              }

          mBrdgTpPort OBJECT-TYPE
              SYNTAX  INTEGER (1..65535)
              MAX-ACCESS  read-only
              STATUS  current
              DESCRIPTION
                      "The port number of the port for which this entry
                      contains Transparent bridging management
                      information."
              ::= { mBrdgTpPortEntry 1 }

          -- It would be nice if we could use ifMtu as the size of the
          -- largest INFO field, but we can't because ifMtu is defined


          -- to be the size that the (inter-)network layer can use which
          -- can differ from the MAC layer (especially if several layers
          -- of encapsulation are used).

          mBrdgTpPortMaxInfo OBJECT-TYPE
              SYNTAX  INTEGER
              MAX-ACCESS  read-only
              STATUS  current
              DESCRIPTION
                      "The maximum size of the INFO (non-MAC) field that
                      this port will receive or transmit."
              ::= { mBrdgTpPortEntry 2 }

          mBrdgTpPortInFrames OBJECT-TYPE
              SYNTAX  Counter32
              MAX-ACCESS  read-only
              STATUS  current
              DESCRIPTION
                      "The number of frames that have been received by
                      this port from its segment. Note that a frame
                      received on the interface corresponding to this
                      port is only counted by this object if and only if
                      it is for a protocol being processed by the local
                      bridging function, including bridge management
                      frames."
              REFERENCE
                      "IEEE 802.1D-1990: Section 6.6.1.1.3"
              ::= { mBrdgTpPortEntry 3 }

          mBrdgTpPortOutFrames OBJECT-TYPE
              SYNTAX  Counter32
              MAX-ACCESS  read-only
              STATUS  current
              DESCRIPTION
                      "The number of frames that have been transmitted
                      by this port to its segment.  Note that a frame
                      transmitted on the interface corresponding to this
                      port is only counted by this object if and only if
                      it is for a protocol being processed by the local
                      bridging function, including bridge management
                      frames."
              REFERENCE
                      "IEEE 802.1D-1990: Section 6.6.1.1.3"
              ::= { mBrdgTpPortEntry 4 }

          mBrdgTpPortInDiscards OBJECT-TYPE
              SYNTAX   Counter32
              MAX-ACCESS   read-only


              STATUS   current
              DESCRIPTION
                      "Count of valid frames received which were
                      discarded (i.e., filtered) by the Forwarding
                      Process."
              REFERENCE
                      "IEEE 802.1D-1990: Section 6.6.1.1.3"
              ::= { mBrdgTpPortEntry 5 }

          mBrdgTpPortBridgeIndex OBJECT-TYPE
              SYNTAX  INTEGER (1..65535)
              MAX-ACCESS  read-only
              STATUS  current
              DESCRIPTION
                      "The bridge number for which this entry
                      contains bridge management information."
              ::= { mBrdgTpPortEntry 6 }

          -- The Static (Destination-Address Filtering) Database

          -- Implementation of this group is optional.

          mBrdgStaticTable OBJECT-TYPE
              SYNTAX  SEQUENCE OF MBrdgStaticEntry
              MAX-ACCESS  not-accessible
              STATUS  current
              DESCRIPTION
                      "A table containing filtering information
                      configured into the bridge by (local or network)
                      management specifying the set of ports to which
                      frames received from specific ports and containing
                      specific destination addresses are allowed to be
                      forwarded.  The value of zero in this table as the
                      port number from which frames with a specific
                      destination address are received, is used to
                      specify all ports for which there is no specific
                      entry in this table for that particular
                      destination address.  Entries are valid for
                      unicast and for group/broadcast addresses."
              REFERENCE
                      "IEEE 802.1D-1990: Section 6.7.2"
              ::= { mBrdgStatic 1 }

          mBrdgStaticEntry OBJECT-TYPE
              SYNTAX  MBrdgStaticEntry
              MAX-ACCESS  not-accessible
              STATUS  current
              DESCRIPTION
                      "Filtering information configured into the bridge
                      by (local or network) management specifying the
                      set of ports to which frames received from a
                      specific port and containing a specific
                      destination address are allowed to be forwarded."
              REFERENCE
                      "IEEE 802.1D-1990: Section 6.7.2"
              INDEX   { mBrdgStaticBridgeIndex, mBrdgStaticAddress, mBrdgStaticReceivePort }
              ::= { mBrdgStaticTable 1 }

          MBrdgStaticEntry ::=
              SEQUENCE {
                  mBrdgStaticAddress
                      MacAddress,
                  mBrdgStaticReceivePort
                      INTEGER,
                  mBrdgStaticAllowedToGoTo
                      OCTET STRING,
                  mBrdgStaticStatus
                      INTEGER,
                  mBrdgStaticBridgeIndex
                      INTEGER
              }

          mBrdgStaticAddress OBJECT-TYPE
              SYNTAX  MacAddress
              MAX-ACCESS  read-write
              STATUS  current
              DESCRIPTION
                      "The destination MAC address in a frame to which
                      this entry's filtering information applies.  This
                      object can take the value of a unicast address, a
                      group address or the broadcast address."
              REFERENCE
                      "IEEE 802.1D-1990: Section 3.9.1, 3.9.2"
              ::= { mBrdgStaticEntry 1 }

          mBrdgStaticReceivePort OBJECT-TYPE
              SYNTAX  INTEGER
              MAX-ACCESS  read-write
              STATUS  current
              DESCRIPTION
                      "Either the value '0', or the port number of the
                      port from which a frame must be received in order
                      for this entry's filtering information to apply.
                      A value of zero indicates that this entry applies
                      on all ports of the bridge for which there is no
                      other applicable entry."
              ::= { mBrdgStaticEntry 2 }

          mBrdgStaticAllowedToGoTo OBJECT-TYPE
              SYNTAX  OCTET STRING
              MAX-ACCESS  read-write
              STATUS  current
              DESCRIPTION
                      "The set of ports to which frames received from a
                      specific port and destined for a specific MAC


                      address, are allowed to be forwarded.  Each octet
                      within the value of this object specifies a set of
                      eight ports, with the first octet specifying ports
                      1 through 8, the second octet specifying ports 9
                      through 16, etc.  Within each octet, the most
                      significant bit represents the lowest numbered
                      port, and the least significant bit represents the
                      highest numbered port.  Thus, each port of the
                      bridge is represented by a single bit within the
                      value of this object.  If that bit has a value of
                      '1' then that port is included in the set of
                      ports; the port is not included if its bit has a
                      value of '0'.  (Note that the setting of the bit
                      corresponding to the port from which a frame is
                      received is irrelevant.)  The default value of
                      this object is a string of ones of appropriate
                      length."
              ::= { mBrdgStaticEntry 3 }

          mBrdgStaticStatus OBJECT-TYPE
              SYNTAX  INTEGER {
                          other(1),
                          invalid(2),
                          permanent(3),
                          deleteOnReset(4),
                          deleteOnTimeout(5)
                      }
              MAX-ACCESS  read-write
              STATUS  current
              DESCRIPTION
                      "This object indicates the status of this entry.
                      The default value is permanent(3).

                           other(1) - this entry is currently in use but
                                the conditions under which it will
                                remain so are different from each of the
                                following values.
                           invalid(2) - writing this value to the object
                                removes the corresponding entry.
                           permanent(3) - this entry is currently in use
                                and will remain so after the next reset
                                of the bridge.
                           deleteOnReset(4) - this entry is currently in
                                use and will remain so until the next
                                reset of the bridge.
                           deleteOnTimeout(5) - this entry is currently
                                in use and will remain so until it is
                                aged out."


              ::= { mBrdgStaticEntry 4 }

          mBrdgStaticBridgeIndex OBJECT-TYPE
              SYNTAX  INTEGER (1..65535)
              MAX-ACCESS  read-only
              STATUS  current
              DESCRIPTION
                      "The bridge number for which this entry
                      contains bridge management information."
              ::= { mBrdgStaticEntry 7 }

          -- the mBrdgConfig TABLE group

          mBrdgConfigTable     OBJECT-TYPE
              SYNTAX  SEQUENCE OF MBrdgConfigEntry
              MAX-ACCESS  not-accessible
              STATUS  current
              DESCRIPTION
                      "This table contains attributes for the different
                       bridges Rows cannot be added to nor deleted from
                       this table."
              ::= { mBrdgConfig 1 }

          mBrdgConfigEntry OBJECT-TYPE
              SYNTAX  MBrdgConfigEntry
              MAX-ACCESS  not-accessible
              STATUS  current
              DESCRIPTION
                      "A list of information for each bridge of the
                      Node."
              REFERENCE
                      "IEEE 802.1D-1990: Section 6.4.2, 6.6.1"
              INDEX  { mBrdgConfigBridgeIndex }
              ::= { mBrdgConfigTable 1 }

          MBrdgConfigEntry ::=
              SEQUENCE {
                  mBrdgConfigBridgeIndex
                      INTEGER,
                  mBrdgConfigBridgeName
                      OCTET STRING,
                  mBrdgConfigBridgePeakRate
                      INTEGER
              }

          mBrdgConfigBridgeIndex OBJECT-TYPE
              SYNTAX  INTEGER (1..65535)
              MAX-ACCESS  read-only
              STATUS  current
              DESCRIPTION
                      "The bridge number for which this entry
                      contains bridge management information."
              ::= { mBrdgConfigEntry 1 }

          mBrdgConfigBridgeName OBJECT-TYPE
              SYNTAX  OCTET STRING (SIZE (0..32))
              MAX-ACCESS  read-write
              STATUS  current
              DESCRIPTION
                      "The name given to this bridge entity."
              ::= { mBrdgConfigEntry 2 }
 
          mBrdgConfigBridgePeakRate  OBJECT-TYPE
              SYNTAX  INTEGER (1..100)
              MAX-ACCESS  read-write
              STATUS  current
              DESCRIPTION
                      "The maximum rate (in percentage) at which data
                       is accepted from ports on this bridge entity."
              ::= { mBrdgConfigEntry 3 }


          -- Traps for use by Bridges

          -- Traps for the Spanning Tree Protocol

--          newRoot TRAP-TYPE
--              ENTERPRISE  mBrdgBridge
--              DESCRIPTION
--                      "The newRoot trap indicates that the sending agent
--                      has become the new root of the Spanning Tree; the
--                      trap is sent by a bridge soon after its election
--                      as the new root, e.g., upon expiration of the
--                      Topology Change Timer immediately subsequent to
--                      its election.  Implementation of this trap is
--                      optional."
--              ::= 1

--          topologyChange TRAP-TYPE
--              ENTERPRISE  mBrdgBridge
--              DESCRIPTION
--                      "A topologyChange trap is sent by a bridge when
--                      any of its configured ports transitions from the
--                     Learning state to the Forwarding state, or from
--                      the Forwarding state to the Blocking state.  The
--                      trap is not sent if a newRoot trap is sent for the
--                      same transition.  Implementation of this trap is
--                      optional."
--              ::= 2

-------------------------------------------------------------------------------
--      Review Minutes
-------------------------------------------------------------------------------
--      MINUTES-BEGIN
--              REVIEW-DATE  "1997.03.24"
--              BODY  "
--
--      TO:     Kamil Buchler*, Wayne Burwell*, Rob de Vlugt,
--              Arun Chandrasekaran, Azaduer Kurkjian*, Andrew Rees
--      CC:     Numbers Admin, Louise Richardson, Tom Walton, Tom C. Wilson
--      FROM:   Martin Dubois
--
--      A meeting was held on 97.03.24 to review MultiBridge.mib, the area
--      interface definition for the Bridging area in the system region.
--      Attendees are marked with * in the TO and CC lists above.
--
--      Outcome
--
--      It was the consensus of the review team that this file is
--      acceptable with the indicated modifications.
--
--      Actions:
--      A1 -    M. Dubois to update the file as indicated in D1 below.
--              To be completed by 97.03.25
--              Response:
--                                              Status: CLOSED
--
--      A2 -    M. Dubois to remove port from index in Static table
--              proven unless proven useful.  RFC 1493 does have this
--              element in the index.
--              To be completed by 97.03.25
--              Response: the port id is part of the OID in order to add
--              new addresses by using one command:
--               mBrdgStaticAddress.<Bridge>.<MAC Address><PortId>, value=<MAC>
--              instead of
--               mBrdgStaticAddress.<Bridge>.<MAC Address>, value=<MAC>
--               mBrdgStaticReceivePort.<Bridge>.<MAC Address>, value=<PortId>
--                                              Status: CLOSED
--
--      Decisions:
--      D1 -    MultiBridge.mib shall be updated as follows:
--              a) tables descriptions should contain hints on how to
--                 how to add/remove rows.
--      "
--
--      END-MINUTES

END
