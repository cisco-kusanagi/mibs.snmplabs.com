-- $Id: it-character-mib.mib,v 1.19 2002/01/18 19:08:47 sse Exp $
                    ITOUCH-CHARACTER-MIB DEFINITIONS ::= BEGIN
            
                    IMPORTS
                            Counter, Gauge, TimeTicks, IpAddress
                                    FROM RFC1155-SMI
                            DisplayString, sysLocation
                                    FROM RFC1213-MIB
                           OBJECT-TYPE
                                    FROM RFC-1212
			   TRAP-TYPE
                                    FROM RFC-1215
                            iTouch, DateTime, AddressType
                                    FROM ITOUCH-MIB
                            charPortIndex
                                    FROM RFC1316-MIB
                            rs232InSigState, rs232OutSigState, rs232PortIndex
                                    FROM RFC1317-MIB;
            
            characterDep    OBJECT IDENTIFIER ::= { iTouch 2 }
            xCharacter      OBJECT IDENTIFIER ::= { iTouch 13 }
            
            -- ITouch Character subgroups
            
            xBasic          OBJECT IDENTIFIER ::= { xCharacter 1 }
            xQueue          OBJECT IDENTIFIER ::= { xCharacter 2 }
            xMenu           OBJECT IDENTIFIER ::= { xCharacter 3 }
            xNetLogin       OBJECT IDENTIFIER ::= { xCharacter 4 }
            xDial           OBJECT IDENTIFIER ::= { xCharacter 5 }
            xSessionLog     OBJECT IDENTIFIER ::= { xCharacter 6 }
            xCcl            OBJECT IDENTIFIER ::= { xCharacter 7 }
            xBroadcastGroup OBJECT IDENTIFIER ::= { xCharacter 8 }
            
            -- This is a MIB module for all iTouch systems that
            -- implement physical or logical character stream devices.
            -- It is also used by the in-Reach product line for alarm, sensor
            -- and power managment functions.
            
            -- Copyright 2000 iTouch Communications, Inc. All Rights Reserved.
            -- Reproduction of this document is authorized on
            -- condition that this copyright notice is included.
            -- This MIB document embodies iTouch Communications, Inc.'s 
            -- proprietary intellectual property.  iTouch Communications, Inc.
            -- retains all title and ownership in this MIB, including any
            -- revisions.
            --
            -- It is iTouch Communications, Inc.'s intent to encourage the
            -- widespread use of this MIB in connection with the management of
            -- iTouch Communications, Inc. products. iTouch Communications,
            -- Inc. grants vendors,end-users, and other interested parties a
            -- non-exclusive license to use this MIB in connection with the
            -- management of iTouch Communications, Inc. products.
            --
            -- This MIB document is supplied "AS IS," and iTouch 
            -- Communications, Inc. makes no warranty, either express or
            -- implied, as to the use operation, condition, or performance of
            -- the MIB.

            
            -- the Character Basic group
            
            -- Implementation of this group is mandatory for all iTouch
            -- systems that implement physical or logical character
            -- stream devices
            
            basicBroadcast OBJECT-TYPE
                SYNTAX INTEGER { disabled(1), enabled(2) }
                ACCESS read-write
                STATUS mandatory
                DESCRIPTION
                    "Control for user ability to broadcast messages to 
                    other local ports.  Corresponds directly to SERVER 
                    BROADCAST and the presence of the label 'Broadcast' 
                    following the label 'Enabled Characteristics:' in 
                    the SERVER CHARACTERISTICS display."
                ::= { xBasic 1 }
            
            basicErrorReport OBJECT-TYPE
                SYNTAX INTEGER { disabled(1), enabled(2) }
                ACCESS read-write
                STATUS mandatory
                DESCRIPTION
                    "Control for server display of an error when the 
                    user gives an unsupported command.  Corresponds 
                    directly to SERVER REPORT ERRORS and the presence of 
                    the label 'Report Errors' following the label 
                    'Enabled Characteristics:' in the SERVER 
                    CHARACTERISTICS display."
                ::= { xBasic 2 }
            
            basicLock OBJECT-TYPE
                SYNTAX INTEGER { disabled(1), enabled(2) }
                ACCESS read-write
                STATUS mandatory
                DESCRIPTION
                    "Control for user ability to use a password to 
                    protect a logged in terminal from other users.  
                    Corresponds directly to SERVER LOCK and the presence 
                    of the label 'Lock' following the label 'Enabled 
                    Characteristics:' in the SERVER CHARACTERISTICS 
                    display."
                ::= { xBasic 3 }
            
            basicInactivityTimer OBJECT-TYPE
                SYNTAX INTEGER (1..480)
                ACCESS read-write
                STATUS mandatory
                DESCRIPTION
                    "Number of minutes a terminal may remain logged in 
                    with no sessions, no input or output, and no modem 
                    transitions.  Corresponds directly to SERVER 
                    INACTIVITY TIMER and the value labeled 'Inactivity 
                    Timer:' in the SERVER CHARACTERISTICS display."
                ::= { xBasic 4 }
            
            basicPasswordRetryLimit OBJECT-TYPE
                SYNTAX INTEGER (0..250)
                ACCESS read-write
                STATUS mandatory
                DESCRIPTION
                    "Number of times the server allows a user to retry 
                    an incorrect password.  Corresponds directly to 
                    SERVER PASSWORD LIMIT and the value labeled 
                    'Password Limit:' in the SERVER CHARACTERISTICS 
                    display."
                ::= { xBasic 5 }
            
            basicPrivilegedPassword OBJECT-TYPE
                SYNTAX DisplayString (SIZE (0..16))
                ACCESS read-write
                STATUS mandatory
                DESCRIPTION
                    "The password a user must enter to become 
                    privileged.
                    For security reasons, reading this object always 
                    returns a zero-length value.  Corresponds directly 
                    to SERVER PRIVILEGED PASSWORD."
                ::= { xBasic 6 }
            
            basicLoginPassword OBJECT-TYPE
                SYNTAX DisplayString (SIZE (0..16))
                ACCESS read-write
                STATUS mandatory
                DESCRIPTION
                    "The password a user must enter to be given the 
                    opportunity to log in.  For security reasons, 
                    reading this object always returns a zero-length 
                    value. Corresponds directly to SERVER LOGIN 
                    PASSWORD."
                ::= { xBasic 7 }
            
            basicLoginPrompt OBJECT-TYPE
                SYNTAX DisplayString (SIZE (0..8))
                ACCESS read-write
                STATUS mandatory
                DESCRIPTION
                    "The text string the server displays to prompt a 
                    user for the login password.  Corresponds directly 
                    to SERVER LOGIN PROMPT."
                ::= { xBasic 8 }
            
            basicWelcome OBJECT-TYPE
                SYNTAX DisplayString (SIZE (0..80))
                ACCESS read-write
                STATUS mandatory
                DESCRIPTION
                    "The text string the server displays before 
                    attempting to log in a user.  Corresponds directly 
                    to SERVER WELCOME and the value labeled 'Welcome:' 
                    in the SERVER CHARACTERISTICS display."
                ::= { xBasic 9 }
            
            basicActivePorts OBJECT-TYPE
                SYNTAX Gauge
                ACCESS read-only
                STATUS mandatory
                DESCRIPTION
                    "The number of ports with connected sessions or 
                    logged in users.  Corresponds directly to the value 
                    labeled 'Active Ports:' and 'Cur' in the SERVER 
                    STATUS display."
                ::= { xBasic 10 }
            
            basicActivePortsHigh OBJECT-TYPE
                SYNTAX Gauge
                ACCESS read-only
                STATUS mandatory
                DESCRIPTION
                    "The highest value of basicActivePorts since system 
                    initialization.  Corresponds directly to the value 
                    labeled 'Active Ports:' and 'High' in the SERVER 
                    STATUS display."
                ::= { xBasic 11 }
            
            basicActiveUsers OBJECT-TYPE
                SYNTAX Gauge
                ACCESS read-only
                STATUS mandatory
                DESCRIPTION
                    "The number of logged in users.  Corresponds 
                    directly to the value labeled 'Active Users:' and 
                    'Cur' in the SERVER STATUS display."
                ::= { xBasic 12 }
            
            basicActiveUsersHigh OBJECT-TYPE
                SYNTAX Gauge
                ACCESS read-only
                STATUS mandatory
                DESCRIPTION
                    "The highest value of basicActiveUsers since system 
                    initialization.  Corresponds directly to the value 
                    labeled 'Active Users:' and 'High' in the SERVER 
                    STATUS display."
                ::= { xBasic 13 }
            
            basicSessions OBJECT-TYPE
                SYNTAX Gauge
                ACCESS read-only
                STATUS mandatory
                DESCRIPTION
                    "The total number of connected sessions.  
                    Corresponds directly to the value labeled 'Connected 
                    Sessions:' and 'Cur' in the SERVER STATUS display."
                ::= { xBasic 14 }
            
            basicSessionsHigh OBJECT-TYPE
                SYNTAX Gauge
                ACCESS read-only
                STATUS mandatory
                DESCRIPTION
                    "The highest value of basicSessions since system 
                    initialization.  Corresponds directly to the value 
                    labeled 'Connected Sessions:' and 'High' in the 
                    SERVER STATUS display."
                ::= { xBasic 15 }
            
            basicSessionsLimit OBJECT-TYPE
                SYNTAX INTEGER (-1..255)
                ACCESS read-write
                STATUS mandatory
                DESCRIPTION
                    "The maximum total number of sessions that can 
                    simultaneously be connected to the system.  A value 
                    of -1 indicates no limit up to available dynamic 
                    system memory.  Corresponds directly to SERVER 
                    SESSION LIMIT and the value labeled 'Connected 
                    Sessions:' and 'Max' in the SERVER STATUS display."
                ::= { xBasic 16 }
            
            -- Additional Basic group parameters follow the port tables

            -- the Basic Port table
            
            basicPortTable OBJECT-TYPE
                SYNTAX SEQUENCE OF BasicPortEntry
                ACCESS not-accessible
                STATUS mandatory
                DESCRIPTION
                    "A list of basic character port entries."
                ::= { xBasic 17 }
            
            basicPortEntry OBJECT-TYPE
                SYNTAX BasicPortEntry
                ACCESS not-accessible
                STATUS mandatory
                DESCRIPTION
                    "Basic parameter values for a port."
                INDEX { basicPortIndex }
                ::= { basicPortTable 1 }
            
            BasicPortEntry ::=
                SEQUENCE {
                    basicPortIndex
                        INTEGER,
                    basicPortDefaultDestAction
                        INTEGER,
                    basicPortDefaultDestProtocol
                        INTEGER,
                    basicPortDefaultDestName
                        DisplayString,
                    basicPortDefaultDestLATNodeName
                        DisplayString,
                    basicPortDefaultDestLATPortName
                        DisplayString,
                    basicPortAutoConnect
                        INTEGER,
                    basicPortAutoLogin
                        INTEGER,
                    basicPortBroadcast
                        INTEGER,
                    basicPortConnectResume
                        INTEGER,
                    basicPortDialup
                        INTEGER,
                    basicPortIdleTimeout
                        INTEGER,
                    basicPortInactivityLogout
                        INTEGER,
                    basicPortLossNotification
                        INTEGER,
                    basicPortMessageCodes
                        INTEGER,
                    basicPortMultisessions
                        INTEGER,
                    basicPortDefaultUserName
                        DisplayString,
                    basicPortVerification
                        INTEGER,
                    basicPortDefaultProtocol
                        INTEGER,
                    basicPortLogins
                        Counter,
                    basicPortRemoteSessions
                        Counter,
                    basicPortIdleTimeouts
                        Counter,
                    basicPortStatus
                        INTEGER,
                    basicPortLastInCharacter
                        INTEGER,
                    basicPortLastOutCharacter
                        INTEGER,
                    basicPortActiveUserName
                        DisplayString,
                    basicPortDefaultSessionMode
                        INTEGER,
                    basicPortZero
                        INTEGER,
                    basicPortZeroTime
                        TimeTicks,
                    basicPortUnixCommands
                        INTEGER,
                    basicPortSessionMode
                        INTEGER,
                    basicPortRemoteDisconnectNotify
                        INTEGER,
                    basicPortDefaultDestControlled
                        INTEGER,
                    basicPortControlledPortLogin
                        OCTET STRING, 
                    basicPortControlledPortLogout
                        OCTET STRING,
                    basicPortControlledSessionInitialize
                        OCTET STRING,
                    basicPortControlledSessionTerminate
                        OCTET STRING,
                    basicPortRloginTransparentMode
                        INTEGER,
                    basicPortLoginDuration
                        INTEGER,
                    basicPortOutboundSecurity
                        INTEGER,
                    basicPortXonTimer
                        INTEGER,
                    basicPortDefaultDedicatedSessionType
                        OCTET STRING,
                    basicPortIdleTimeReceive
                        INTEGER,
                    basicPortIdleTimeTransmit
                        INTEGER,
                    basicPortZeroDisconnectSession
                        INTEGER,
                    basicPortConsolePort
                        INTEGER,
                    basicPortLoginPassword
                        DisplayString,
                    basicPortSensor
                        INTEGER,
                    basicPortAlarmControl
                        INTEGER,
                    basicPortCommandLogging
                        INTEGER,
                    basicPortBreakSequence
                        OCTET STRING,
                    basicPortTl1Mode
			INTEGER,
                    basicPortTl1Console
			INTEGER,
                    basicPortFallThrough
			INTEGER,
                    basicPortCommandLoggingSuppressControlCharacters 
			INTEGER,
                    basicPortDataLogging 
			INTEGER,
                    basicPortDataLoggingSuppressControlCharacters 
			INTEGER,
                    basicPortOnboardSecurity
			INTEGER,
                    basicPortFallBack
			INTEGER,
		    basicPortAlarmMaster
			INTEGER,
		    basicPortAlarmMasterAccounting
			INTEGER,
		    basicPortAlarmMasterAudibleAlarm
			INTEGER,
		    basicPortAlarmMasterFixTime
			INTEGER,
		    basicPortAlarmMasterLcdDisplayString
			DisplayString,
		    basicPortAlarmMasterReboot
			INTEGER,
		    basicPortAlarmMasterUpdateFirmwareHost
			IpAddress,
		    basicPortAlarmMasterUpdateFirmwareFileName
			DisplayString,
		    basicPortAlarmMasterUpdateFirmware
			INTEGER,
		    basicPortAlarmMasterStatus 
			INTEGER,
		    basicPortAlarmMasterFaultSeverity
			INTEGER,
		    basicPortPowerMaster
			INTEGER,
		    basicPortPowerMasterTimeDelay
			INTEGER,
		    basicPortPowerMasterSwitch
			INTEGER,
		    basicPortPowerMasterModel
			DisplayString,
		    basicPortPowerMasterSerialNumber
			DisplayString,
		    basicPortPowerMasterFirmware
			DisplayString,
		    basicPortLockout
			INTEGER,
		    basicPortAsciiToTrapTranslation
			INTEGER,
		    basicPortAsciiToTrapTranslationTrapSeverity
			INTEGER,
		    basicPortAsciiToTrapTranslationMessages
			Counter,
		    basicPortAsciiToTrapTranslationLastMessage
			DisplayString,
                    basicPortPowerMasterAlarmSeverity
			INTEGER,
                    basicPortPowerMasterDeviceStatus
			INTEGER
		 }

	     basicPortIndex OBJECT-TYPE
		 SYNTAX INTEGER
		 ACCESS read-only
		 STATUS mandatory
		 DESCRIPTION
		     "An index value that uniquely identifies a port.  
		     The port identified by a particular value of this 
		     index is the same port as identified by 
		     charPortIndex in the standard Character MIB."
		 ::= { basicPortEntry 1 }

	     basicPortDefaultDestAction OBJECT-TYPE
		 SYNTAX INTEGER { dedicated(1), preferred(2) }
		 ACCESS read-write
		 STATUS mandatory
		 DESCRIPTION
		     "The action to take relative to 
		     basicPortDefaultDestName.  Corresponds directly to 
		     PORT DEDICATED/PREFERRED SERVICE and the label 
		     'Dedicated/Preferred Service:' in the PORT 
		     CHARACTERISTICS display."
		 ::= { basicPortEntry 2 }

	     basicPortDefaultDestProtocol OBJECT-TYPE
		 SYNTAX INTEGER { lat(1), telnet(2), any(3) }
		 ACCESS read-write
		 STATUS mandatory
		 DESCRIPTION
		     "The session protocol to use with 
		     basicPortDefaultDestName.  Corresponds directly to 
		     LAT/TELNET PORT DEDICATED/PREFERRED SERVICE."
		 ::= { basicPortEntry 3 }

	     basicPortDefaultDestName OBJECT-TYPE
		 SYNTAX DisplayString (SIZE (0..50))
		 ACCESS read-write
		 STATUS mandatory
		 DESCRIPTION
		     "The default name to use in forming a connection 
		     when no other name is specified.  Corresponds 
		     directly to PORT DEDICATED/PREFERRED SERVICE and the 
		     value labeled 'Dedicated/Preferred Service:' in the 
		     PORT CHARACTERISTICS display.  If the value of 
		     basicPortDefaultDestProtocol is 'telnet', an 
		     Internet port number may be included on the end of 
		     the name, delimited with a colon (':').  If the 
		     value of basicPortDefaultDestProtocol is not 
		     'telnet', then the maximum length is 16."
		 ::= { basicPortEntry 4 }

	     basicPortDefaultDestLATNodeName OBJECT-TYPE
		 SYNTAX DisplayString (SIZE (0..16))
		 ACCESS read-write
		 STATUS mandatory
		 DESCRIPTION
		     "A LAT node name to use with 
		     basicPortDefaultDestName.  Corresponds directly to 
		     PORT DEDICATED/PREFERRED SERVICE NODE and the value 
		     labeled 'Node:' following the label 
		     'Dedicated/Preferred Service:' in the PORT 
		     CHARACTERISTICS display.  This object can have a 
		     non- zero-length value only if the value of 
		     basicPortDefaultDestProtocol is 'lat'."
		 ::= { basicPortEntry 5 }

	     basicPortDefaultDestLATPortName OBJECT-TYPE
		 SYNTAX DisplayString (SIZE (0..16))
		 ACCESS read-write
		 STATUS mandatory
		 DESCRIPTION
		     "A LAT port name to use with 
		     basicPortDefaultDestName.  Corresponds directly to 
		     PORT DEDICATED/PREFERRED SERVICE NODE and the value 
		     labeled 'Node:' following the label 
		     'Dedicated/Preferred Service:' in the PORT 
		     CHARACTERISTICS display.  this object can hav a 
		     non-zero-length value only if the value if 
		     basicPortDefaultDestProtocol is 'lat'"
		 ::= { basicPortEntry 6 }

	     basicPortAutoConnect OBJECT-TYPE
		 SYNTAX INTEGER { disabled(1), enabled(2) }
		 ACCESS read-write
		 STATUS mandatory
		 DESCRIPTION
		     "Control for automatic session connection.  
		     Corresponds directly to PORT AUTOCONNECT and the 
		     presence of the label 'Autoconnect' following the 
		     label 'Enabled Characteristics:' in the PORT 
		     CHARACTERISTICS display."
		 ::= { basicPortEntry 7 }

	     basicPortAutoLogin OBJECT-TYPE
		 SYNTAX INTEGER { disabled(1), enabled(2) }
		 ACCESS read-write
		 STATUS mandatory
		 DESCRIPTION
		     "Control for automatic port login.  Corresponds 
		     directly to PORT AUTODEDICATED and the presence of 
		     the label 'Autodedicated' following the label 
		     'Enabled Characteristics:' in the PORT 
		     CHARACTERISTICS display."
		 ::= { basicPortEntry 8 }

	     basicPortBroadcast OBJECT-TYPE
		 SYNTAX INTEGER { disabled(1), enabled(2) }
		 ACCESS read-write
		 STATUS mandatory
		 DESCRIPTION
		     "Control for display of messages sent by users on 
		     other ports.  Corresponds directly to PORT BROADCAST 
		     and the presence of the label 'Broadcast' following 
		     the label 'Enabled Characteristics:' in the PORT 
		     CHARACTERISTICS display."
		 ::= { basicPortEntry 9 }

	     basicPortConnectResume OBJECT-TYPE
		 SYNTAX INTEGER { disabled(1), enabled(2) }
		 ACCESS read-write
		 STATUS mandatory
		 DESCRIPTION
		     "Control for behavior of a connection attempt to a 
		     destination where the port already has a connection.  
		     'disabled' causes a new connection.  'enabled' 
		     causes the existing connection to become the active 
		     connection.  Corresponds directly to PORT 
		     CONNECTRESUME and the presence of the label 
		     'Connectresume' following the label 'Enabled 
		     Characteristics:' in the PORT CHARACTERISTICS 
		     display."
		 ::= { basicPortEntry 10 }

	     basicPortDialup OBJECT-TYPE
		 SYNTAX INTEGER { disabled(1), enabled(2) }
		 ACCESS read-write
		 STATUS mandatory
		 DESCRIPTION
		     "Defines whether the port should be considered as 
		     connected to a dialup line.  'enabled' means that it 
		     is.  Corresponds directly to PORT DIALUP and the 
		     presence of the label 'Dial Up' following the label 
		     'Enabled Characteristics:' in the PORT 
		     CHARACTERISTICS display. This object is not available
		     on units that do not support modem signals (ie 2220)."
		 ::= { basicPortEntry 11 }

	     basicPortIdleTimeout OBJECT-TYPE
		 SYNTAX INTEGER (-1..480)
		 ACCESS read-write
		 STATUS mandatory
		 DESCRIPTION
		     "The number of minutes the system will allow a 
		     session to have no activity before automatically 
		     disconnecting it.  A value of -1 indicates no 
		     timeout.  Zero is not a valid value.  Corresponds 
		     directly to PORT IDLE TIMEOUT and the value labeled 
		     'Idle Timeout:' in the PORT ALTERNATE 
		     CHARACTERISTICS display."
		 ::= { basicPortEntry 12 }

	     basicPortInactivityLogout OBJECT-TYPE
		 SYNTAX INTEGER { disabled(1), enabled(2) }
		 ACCESS read-write
		 STATUS mandatory
		 DESCRIPTION
		     "Control for the system automatically logging the 
		     port out when it has no sessions, no local activity, 
		     and no modem signal changes for the time period 
		     specified by basicInactivityTimer.  Corresponds 
		     directly to PORT INACTIVITY LOGOUT and the presence 
		     of the label 'Inactivity Logout' following the label 
		     'Enabled Characteristics:' in the PORT 
		     CHARACTERISTICS display."
		 ::= { basicPortEntry 13 }

	     basicPortLossNotification OBJECT-TYPE
		 SYNTAX INTEGER { disabled(1), enabled(2) }
		 ACCESS read-write
		 STATUS mandatory
		 DESCRIPTION
		     "Control for the system sending a Bell character to 
		     the port when it looses an input character due to an 
		     overrun or data error.  Corresponds directly to PORT 
		     LOSS NOTIFICATION and the presence of the label 
		     'Loss Notification' following the label 'Enabled 
		     Characteristics:' in the PORT CHARACTERISTICS 
		     display."
		 ::= { basicPortEntry 14 }

	     basicPortMessageCodes OBJECT-TYPE
		 SYNTAX INTEGER { disabled(1), enabled(2) }
		 ACCESS read-write
		 STATUS mandatory
		 DESCRIPTION
		     "Control for including error numbers in error 
		     messages displayed on the port.  Corresponds 
		     directly to PORT MESSAGE CODES and the presence of 
		     the label 'Message Codes' following the label 
		     'Enabled Characteristics:' in the PORT 
		     CHARACTERISTICS display."
		 ::= { basicPortEntry 15 }

	     basicPortMultisessions OBJECT-TYPE
		 SYNTAX INTEGER { disabled(1), enabled(2) }
		 ACCESS read-write
		 STATUS mandatory
		 DESCRIPTION
		     "Control for running the multisession line protocol 
		     between the port and the locally-connected terminal.  
		     Corresponds directly to PORT MULTISESSIONS and the 
		     presence of the label 'Multisessions' following the 
		     label 'Enabled Characteristics:' in the PORT 
		     CHARACTERISTICS display."
		 ::= { basicPortEntry 16 }

	     basicPortDefaultUserName OBJECT-TYPE
		 SYNTAX DisplayString (SIZE (0..16))
		 ACCESS read-write
		 STATUS mandatory
		 DESCRIPTION
		     "Default user name to use for automatically logging 
		     in the port.  Corresponds directly to PORT USERNAME 
		     and the value labeled 'Port n:' in the PORT 
		     CHARACTERISTICS display."
		 ::= { basicPortEntry 17 }

	     basicPortVerification OBJECT-TYPE
		 SYNTAX INTEGER { disabled(1), enabled(2) }
		 ACCESS read-write
		 STATUS mandatory
		 DESCRIPTION
		     "Control for display of informational messages on 
		     the port when the user connects, disconnects, or 
		     switches a session.  Corresponds directly to PORT 
		     VERIFICATION and the presence of the label 
		     'Verification' following the label 'Enabled 
		     Characteristics:' in the PORT CHARACTERISTICS 
		     display."
		 ::= { basicPortEntry 18 }

	     basicPortDefaultProtocol OBJECT-TYPE
		 SYNTAX INTEGER { lat(1), telnet(2), anylat(3), anytelnet(13) }
		 ACCESS read-write
		 STATUS mandatory
		 DESCRIPTION
		     "The session protocol to use when not otherwise 
		     specified.  Corresponds directly to PORT RESOLVE 
		     SERVICE and the value labeled 'Resolve Service:' in 
		     the PORT ALTERNATE CHARACTERISTICS display."
		 ::= { basicPortEntry 19 }

	     basicPortLogins OBJECT-TYPE
		 SYNTAX Counter
		 ACCESS read-only
		 STATUS mandatory
		 DESCRIPTION
		     "The number of logins on the port since system 
		     initialization.  Corresponds directly to the value 
		     labeled 'Local Accesses:' in the PORT COUNTERS 
		     display."
		 ::= { basicPortEntry 20 }

	     basicPortRemoteSessions OBJECT-TYPE
		 SYNTAX Counter
		 ACCESS read-only
		 STATUS mandatory
		 DESCRIPTION
		     "The number of remotely originating sessions to the 
		     port since system initialization.  Corresponds 
		     directly to the value labeled 'Remote Accesses:' in 
		     the PORT COUNTERS display."
		 ::= { basicPortEntry 21 }

	     basicPortIdleTimeouts OBJECT-TYPE
		 SYNTAX Counter
		 ACCESS read-only
		 STATUS mandatory
		 DESCRIPTION
		     "The number of session disconnects due to expiration 
		     of basicPortIdleTimeout.  Corresponds directly to 
		     the value labeled 'Idle Timeouts:' in the PORT 
		     COUNTERS display."
		 ::= { basicPortEntry 22 }

	     basicPortStatus OBJECT-TYPE
		 SYNTAX INTEGER { idle(1), local(2), waitInput(3),
				  executingCommand(4), connecting(5),
				  checkConnect(6), waitOutput(7),
				  connected(8), disconnecting(9),
				  disconnect(10), suspended(11),
				  locked(12), permanent(13),
				  loginWait(14), retryConnect(15),
				  connectWait(16), logout(17),
				  login(18), waitSession(19),
				  reset(20), testServiceWait(21),
				  testServiceOut(22), 
				  connectPassword(23),
				  waitLogout(24), waitQueue(25),
				  cancelQueue(26), autobaud(27),
				  available(28), checkModem(29),
				  slip(30), signalWait(31),
				  scriptSearch(32), scriptLoad(33),
				  scriptRun(34), dialback1(35),
				  dialback2(36), dialback3(37),
				  xremote(38), ppp(39), cslip(40),
				  arapInit(41), cclAnswer(42),
				  cclOriginate(43), cclHangup(44),
				  kerberos(45), securID(46), arapUser(47),
				  arapDialback(48), arapSearch(49),
				  arapLoad(50), arapRead(51), arapDialDone(52),
				  arapExit(53), arapEnabling(54),
				  arapConnecting(55), cclLoading(56),
				  cclLoadError(57), cclLoadWaiting(58),
				  cclExecute(59), cclDone(60), apd(61) }
		 ACCESS read-only
		 STATUS mandatory
		 DESCRIPTION
		     "The current operational status of the port.  
		     Corresponds directly to the value labeled 'Status:' 
		     in the PORT STATUS display."
		 ::= { basicPortEntry 23 }

	     basicPortLastInCharacter OBJECT-TYPE
		 SYNTAX INTEGER (0..255)
		 ACCESS read-only
		 STATUS mandatory
		 DESCRIPTION
		     "The character that most recently came into the 
		     port.  Corresponds directly to the value labeled 
		     'Last Char Input:' in the PORT STATUS display."
		 ::= { basicPortEntry 24 }

	     basicPortLastOutCharacter OBJECT-TYPE
		 SYNTAX INTEGER (0..255)
		 ACCESS read-only
		 STATUS mandatory
		 DESCRIPTION
		     "The character that most recently went out of the 
		     port.  Corresponds directly to the value labeled 
		     'Last Char Output:' in the PORT STATUS display."
		 ::= { basicPortEntry 25 }

	     basicPortActiveUserName OBJECT-TYPE
		 SYNTAX DisplayString (SIZE (0..16))
		 ACCESS read-only
		 STATUS mandatory
		 DESCRIPTION
		     "The user name currently logged into the port.  
		     Corresponds directly to the value by the port number 
		     and labeled 'Username' in the USERS display."
		 ::= { basicPortEntry 26 }

	     basicPortDefaultSessionMode OBJECT-TYPE
		 SYNTAX INTEGER { interactive(1), binary(2),
				  binaryWithFlow(3), transparent(4)  }
		 ACCESS read-write
		 STATUS mandatory
		 DESCRIPTION 
		     "Data recognition mode when starting a session,
		     with the following meanings:

		     interactive      locally recognize all controls
		     binary           recognize only session protocol
				      (corresponds to PASSALL)
		     binaryWithFlow   recognize only XON and XOFF
				      (corresponds to PASTHRU
		     transparent      recognize no data

		     Corresponds directly to PORT DEFAULT SESSION MODE
		     and the value labeled 'Default Session Mode:' in
		     the PORT ALTERNATE CHARACTERISTICS display."
		 ::= { basicPortEntry 27 }

	     basicPortZero OBJECT-TYPE
		 SYNTAX INTEGER  { ready(1), execute(2) }
		 ACCESS read-write
		 STATUS mandatory
		 DESCRIPTION
		     "Control to zero counters for the port.  In response 
		     to a get-request or get-next-request, the agent 
		     always returns 'ready' for this value.  Setting the 
		     value to 'ready' has no effect.  Setting it to 
		     'execute' causes the port's counters to be zeroed.  
		     Corresponds to the ZERO PORT command."
		 ::= { basicPortEntry 28 }

	     basicPortZeroTime OBJECT-TYPE
		 SYNTAX TimeTicks
		 ACCESS read-only
		 STATUS mandatory
		 DESCRIPTION
		     "The number of hundredths of a second since the most 
		     recent zeroing of the port's counters, such as 
		     through execution of basicPortZero.  Corresponds 
		     directly to the value labeled 'Seconds Since 
		     Zeroed:' in the PORT COUNTERS display."
		 ::= { basicPortEntry 29 }

	     basicPortUnixCommands OBJECT-TYPE
		 SYNTAX INTEGER { disabled(1), enabled(2),
				  primary(3), only(4) }
		 ACCESS read-write
		 STATUS mandatory
		 DESCRIPTION
		     "Control to allow the user to use Unix-style 
		     commands the port."
		 ::= { basicPortEntry 30 }

	     basicPortSessionMode OBJECT-TYPE
		 SYNTAX INTEGER { interactive(1), binary(2),
				  binaryWithFlow(3), transparent(4),
				  noActiveSessions(5)  }
		 ACCESS read-write
		 STATUS mandatory
		 DESCRIPTION
		     "Data recognition mode for an active session, with
		     the following meanings:

		     interactive      locally recognize all controls
		     binary           recognize only session protocol
				      (corresponds to PASSALL)
		     binaryWithFlow   recognize only XON and XOFF
				      (corresponds to PASTHRU
		     transparent      recognize no data
		     noActiveSessions no sessions on this port.

		     This object can be set to values of 1 to 4, but
		     only if there is an active session on the port."
		 ::= { basicPortEntry 31 }

	     basicPortRemoteDisconnectNotify OBJECT-TYPE
		 SYNTAX INTEGER { disabled(1), enabled(2) }
		 ACCESS read-write
		 STATUS mandatory
		 DESCRIPTION
		     "If enabled, a BELL (ctrl G) will be sent out the
		     serial port when a remote session is disconnected
		     and the port is logged out."
		 ::= { basicPortEntry 32 }

	 basicPortDefaultDestControlled  OBJECT-TYPE
		SYNTAX INTEGER { disabled(1), enabled(2) }
		ACCESS read-write
		STATUS mandatory
		DESCRIPTION
		    "A control to send preconfigured controlled port session
		     strings when entering or exiting a session established to
		     the basicPortDefaultDestName. Corresponds directly to the
		     value labeled '(Controlled)' following the label
		     'Dedicated/Preferred Service:' in the PORT CHARACTERISTICS
		     display."
		     ::= { basicPortEntry 33 }

	 basicPortControlledPortLogin  OBJECT-TYPE
		SYNTAX OCTET STRING (SIZE (0..32))
		ACCESS read-write
		STATUS mandatory
		DESCRIPTION
		    "A control string to send out the serial port upon
		     port login. Corresponds to the hexadecimal code which is
		     represented in ASCII following the label
		     'Controlled Port Login:' in the PORT CONTROLLED display."

		    ::= { basicPortEntry 34 }

	 basicPortControlledPortLogout  OBJECT-TYPE
		SYNTAX OCTET STRING (SIZE (0..32))
		ACCESS read-write
		STATUS mandatory
		DESCRIPTION
		    "A control string to send out the serial port upon
		     port logout. Corresponds to the hexadecimal code which is
		     represented in ASCII following the label
		     'Controlled Port Logout:' in the PORT CONTROLLED display."
		    ::= { basicPortEntry 35 }

	 basicPortControlledSessionInitialize  OBJECT-TYPE
		SYNTAX OCTET STRING (SIZE (0..32)) 
		ACCESS read-write
		STATUS mandatory
		DESCRIPTION
		    "A control string to send out the serial port upon
		     entering a session. Corresponds to the hexadecimal code 
		     which represented in ASCII following the label
		     'Controlled Session Initialize:' in the PORT CONTROLLED 
		     display."
		    ::= { basicPortEntry 36 }

	 basicPortControlledSessionTerminate  OBJECT-TYPE
		SYNTAX OCTET STRING (SIZE (0..32)) 
		ACCESS read-write
		STATUS mandatory
		DESCRIPTION
		    "A control string to send out the serial port upon
		     exiting a session. Corresponds to the hexadecimal code 
		     which is represented in ASCII following the label
		     'Controlled Session Terminate:' in the PORT CONTROLLED 
		     display."
		    ::= { basicPortEntry 37 }

	 basicPortRloginTransparentMode OBJECT-TYPE
		SYNTAX INTEGER { disabled(1), enabled(2) }
		ACCESS read-write
		STATUS mandatory 
		DESCRIPTION
		     "A control to pass x'ff' as binary data, not doubling x'ff'.
		Similar to basicPortSessionMode = transparent but for
		a rlogin session."
		 DEFVAL  { disabled }
			 ::= { basicPortEntry 38 }

	 basicPortLoginDuration OBJECT-TYPE
	     SYNTAX INTEGER  (0..64800)
	     ACCESS read-write
	     STATUS mandatory
	     DESCRIPTION
		 "The amount of time in minutes that a port may remain logged in
		  regardless of the activity on the port. The value 0 indicates
		  that the timer is disabled. Corresponds directly to the value
		  labeled 'Login Duration:' in the PORT ALTERNATE CHARACTERISTICS
		  display."
	     DEFVAL { 0 }
	     ::= { basicPortEntry 39 }

	 basicPortOutboundSecurity OBJECT-TYPE
	     SYNTAX INTEGER { disabled(1), enabled(2) }
	     ACCESS read-write
	     STATUS mandatory
	     DESCRIPTION
		 "Control to disable  outbound security, which can be either
		  Kerberos or SecureID, on a per port basis.  Corresponds
		  directly to the presence of the value 'OutboundSecurity'
		  following the label 'Enabled Characteristics' in the PORT
		  CHARACTERISTICS display."
	     DEFVAL { enabled }
	     ::= { basicPortEntry 40 }

	 basicPortXonTimer OBJECT-TYPE
	     SYNTAX INTEGER ( 0..2550 )
	     ACCESS read-write
	     STATUS mandatory
	     DESCRIPTION
		 "Indicates the number of seconds between successive 'XON's sent
		  out a port. A zero signifies that the timer is disabled.
		  Corresponds directly to the value labeled 'Xon Send Timer:' in
		  the PORT ALTERNATE CHARACTERISTICS display."
	     DEFVAL { 0 }
	     ::= { basicPortEntry 41 }

	 basicPortDefaultDedicatedSessionType OBJECT-TYPE
	     SYNTAX OCTET STRING (SIZE (1))
	     ACCESS read-write
	     STATUS mandatory
	     DESCRIPTION
		"A bit mask that specifies the default session type for a 
		 dedicated service for this port. The bit numbers are:
		 1;service name, 2;node name, 3;port name, 4, telnet
		 console; 5, rlogin; 6, bridge console; 7, chassis console."
	     DEFVAL { '0'h } 
	     ::= { basicPortEntry 42 }

	 basicPortIdleTimeReceive OBJECT-TYPE
	     SYNTAX INTEGER { disabled(1), enabled(2) }
	     ACCESS read-write
	     STATUS mandatory
	     DESCRIPTION
		 "Control to restrict the basicPortIdleTimeout to apply to data
		  received from the network and transmitted out the serial port.
		  Data received by the serial port will not be considered
		  activity. Corresponds directly to the value labeled 'Idle
		  Time Receive Mode:' in the PORT ALTERNATE CHARACTERISTICS
		  display."
	     DEFVAL { disabled }
	     ::= { basicPortEntry 43 }

	 basicPortIdleTimeTransmit OBJECT-TYPE
	     SYNTAX INTEGER { disabled(1), enabled(2) }
	     ACCESS read-write
	     STATUS mandatory
	     DESCRIPTION
		 "Control to restrict the basicPortIdleTimeout to apply to data
		  received from the serial port and transmitted out the LAN.
		  Data received from the network will not count as activity.
		  Corresponds directly to the value labeled 'Idle Time Transmit
		  Mode:' in the PORT ALTERNATE CHARACTERISTICS display."
	     DEFVAL { disabled }
	     ::= { basicPortEntry 44 }

	 basicPortZeroDisconnectSession OBJECT-TYPE
	     SYNTAX INTEGER { disabled(1), enabled(2) }
	     ACCESS read-write
	     STATUS mandatory 
	     DESCRIPTION
		 "A control to disconnect a session at Port 0 when the
		  password limit is reached."
	     DEFVAL  { disabled }
	     ::= { basicPortEntry 45 } 

	 basicPortConsolePort OBJECT-TYPE
	     SYNTAX  INTEGER { disabled(1), enabled(2) }
	     ACCESS  read-write
	     STATUS  mandatory
	     DESCRIPTION
		 "Control to configure this port as a console port. This
		  control is only valid on those models with variable 
		  configuration ports. This object can only be set enabled;
		  and doing so will disable basicPortSensor
		  and basicPortAlarmControl.
		  A set will only update the permanent database. Use a 
		  charPortReset for this change to take effect."
	 DEFVAL { enabled }
	 ::= { basicPortEntry 46 }

	 basicPortLoginPassword OBJECT-TYPE
	     SYNTAX DisplayString (SIZE (0..16))
	     ACCESS read-write
	     STATUS mandatory
	     DESCRIPTION
		 "The password a user must enter to be given the 
		 opportunity to log in to a given port. For security
		 reasons reading this object always returns a zero-length 
		 value. Corresponds directly to PORT LOGIN PASSWORD."
	     ::= { basicPortEntry 47 }

	 basicPortSensor OBJECT-TYPE
	     SYNTAX  INTEGER { disabled(1), enabled(2) }
	     ACCESS  read-write
	     STATUS  mandatory
	     DESCRIPTION
		 "Control to configure this port as a temperature and humidity
		  sensor. This control is only valid on those models with 
		  variable configuration ports. This object can only be set
		  enabled; and doing so will disable basicPortConsolePort
		  and basicPortAlarmControl.
		  A set will only update the permanent database. Use a 
		  charPortReset for this change to take effect."
	 DEFVAL { disabled }
	 ::= { basicPortEntry 48 }

	 basicPortAlarmControl OBJECT-TYPE 
	     SYNTAX  INTEGER { disabled(1), enabled(2) }
	     ACCESS  read-write
	     STATUS  mandatory
	     DESCRIPTION
		 "Control to configure this port for alarm input and control
                  output. This control is
		  only valid on those models with variable configuration ports.
		  This object can only be set enabled; and doing so will 
                  disable basicPortConsolePort and basicPortSensor.
		  A set will only update the permanent database. Use a 
		  charPortReset for this change to take effect."
	 DEFVAL { disabled }
	 ::= { basicPortEntry 49 }

	 basicPortCommandLogging OBJECT-TYPE
	     SYNTAX INTEGER { disabled(1), enabled(2) }
	     ACCESS read-write
	     STATUS mandatory
	     DESCRIPTION
		 "A control to toggle logging of commands at this port. 
		  Command input may be logged from direct terminal 
		  connections, session input from the LAN, or session output 
		  to the LAN. Corresponds directly to the presence of 'Command
		  Logging' under the label 'Enabled Characteristics:' in the 
		  PORT CHARACTERISTICS display. The desired change will not 
		  take effect until the port is logged off."
	     DEFVAL { disabled  }
	     ::= { basicPortEntry 50 }                

          basicPortBreakSequence OBJECT-TYPE
              SYNTAX OCTET STRING (SIZE (4)) 
              ACCESS read-write
              STATUS mandatory
              DESCRIPTION
                  "A sequence of characters to be sent out the serial port on
                   receipt of a Break from the network in lieu of a hardware
                   break."
              ::= { basicPortEntry 51 }                

 	basicPortTl1Mode OBJECT-TYPE
		SYNTAX INTEGER { disabled(1), hml(2), mml(3), mmlNoEcho(4) }
		ACCESS read-write
		STATUS mandatory
		DESCRIPTION
	           "Controls the TL1 mode of a port. Valid TL1 modes are human-
                    to-machine language (hml), machine-to-machine language 
		    (mml), and MML without echo. MML is for direct connection
                    to another TL1 device whereas HML provides human prompts.
                    A change takes effect after logging out the port."
		DEFVAL { disabled } 
		::= { basicPortEntry 53 }

 	basicPortTl1Console OBJECT-TYPE
		SYNTAX INTEGER { disabled(1), enabled(2) }
		ACCESS read-write
		STATUS mandatory
		DESCRIPTION
		    "Controls whether this port becomes the TL1 console
		    receiving and displaying autonomous reports of alarm
		    events. A change takes effect after logging out the port."
		DEFVAL {disabled }
		::= { basicPortEntry 54 }
 
 	basicPortFallThrough OBJECT-TYPE
		SYNTAX INTEGER { disabled(1), enabled(2) }
		ACCESS read-write
		STATUS mandatory
		DESCRIPTION
                    "Control to allow a user to login to a port after RADIUS
                     or SecurID authentication fails because the RADIUS servers
                     or SecurID servers are unavailable. When a user is logged
                     in via 'fallthrough', he is logged in to the port as a  
                     non-privileged user. The change takes effect after logging
                     out the port."
		DEFVAL {disabled }
		::= { basicPortEntry 55 }

 	basicPortCommandLoggingSuppressControlCharacters OBJECT-TYPE
		SYNTAX INTEGER { disabled(1), enabled(2) }
		ACCESS read-write
		STATUS mandatory
		DESCRIPTION
                    "Control to toggle suppression of control characters in the
                     command log. This object can only be set to enabled
                     when command logging is enabled on that port."
		DEFVAL {disabled }
		::= { basicPortEntry 56 }

 	basicPortDataLogging OBJECT-TYPE
		SYNTAX INTEGER { disabled(1), enabled(2) }
		ACCESS read-write
		STATUS mandatory
		DESCRIPTION
                    "Control to toggle data logging on the specified port."
		DEFVAL {disabled }
		::= { basicPortEntry 57 }

 	basicPortDataLoggingSuppressControlCharacters OBJECT-TYPE
		SYNTAX INTEGER { disabled(1), enabled(2) }
		ACCESS read-write
		STATUS mandatory
		DESCRIPTION
                    "Control to toggle suppression of control characters in the
                     data log. This object can only be set to enabled
                     when data logging is enabled on that port."
		DEFVAL {disabled }
		::= { basicPortEntry 58 }

        basicPortOnboardSecurity OBJECT-TYPE
	        SYNTAX INTEGER { disabled(1), enabled(2) }
	        ACCESS read-write
	        STATUS mandatory
	        DESCRIPTION
                    "A control to toggle onboard security for this port where
                     the username and password are authenticated against an
                     internal access list. The desired change will not take
                     effect until the port is logged off."
                DEFVAL { disabled }
	        ::= { basicPortEntry 59 }

 	basicPortFallBack OBJECT-TYPE
		SYNTAX INTEGER { disabled(1), enabled(2) }
		ACCESS read-write
		STATUS mandatory
		DESCRIPTION
                    "Control to allow a 'fallback' authentication mechanism
                     after RADIUS or SecurID authentication fails because the
                     RADIUS or SecurID servers are unavailable. Onboard 
                     security, an internal security database, is
                     used for fallback authentication. The user in fallback
                     mode must enter a valid username and password to be
                     successfully logged in. The change takes effect after
                     logging out the port."
		DEFVAL {disabled }
		::= { basicPortEntry 60 }


 	basicPortAlarmMaster OBJECT-TYPE
		SYNTAX INTEGER { disabled(1), enabled(2) }
		ACCESS read-write
		STATUS mandatory
		DESCRIPTION
		 "Control to configure this port for high densitiy alarm 
                  input and control output management. This control is
		  only valid on those models with variable configuration ports.
		  This object can only be set enabled; and doing so will 
                  disable basicPortConsolePort, basicPortSensor and 
                  basicPortAlarmControl. A set will only update the permanent 
                  database. Use a charPortReset for this change to take effect."
		DEFVAL {disabled }
		::= { basicPortEntry 61 }

 	basicPortAlarmMasterAccounting OBJECT-TYPE
		SYNTAX INTEGER { disabled(1), enabled(2) }
		ACCESS read-write
		STATUS mandatory
		DESCRIPTION
                    "Control to toggle logging of alarm events on this port.
		     Use a charPortReset for this change to take effect."
		DEFVAL {disabled }
		::= { basicPortEntry 62 }

 	basicPortAlarmMasterAudibleAlarm OBJECT-TYPE
		SYNTAX INTEGER { disabled(1), enabled(2) }
		ACCESS read-write
		STATUS mandatory
		DESCRIPTION
                    "Control whether the alarm will have an audible sound for
                     all alarm points attached to this port."
		DEFVAL {disabled }
		::= { basicPortEntry 63 }

 	basicPortAlarmMasterFixTime OBJECT-TYPE 
		SYNTAX INTEGER ( 1 .. 720 )
		ACCESS read-write
		STATUS mandatory
		DESCRIPTION
                    "Time in minutes between audible alarm soundings for an alarm 
                     master port. This occurs after someone hits the master alarm 
                     reset button. If there is at least one alarm condition on an 
                     alarm point within the fix time, then the alarm will sound 
                     again at the end of that fix time."
		DEFVAL { 30 }
		::= { basicPortEntry 64 }

 	basicPortAlarmMasterLcdDisplayString OBJECT-TYPE
		SYNTAX DisplayString (SIZE (32))
		ACCESS read-write
		STATUS mandatory
		DESCRIPTION
                    "Updates the LCD display message for the high density
                    alarm unit attached to the port. Corresponds directly 
                    to the DISPLAY AMST command."
		::= { basicPortEntry 65 }

 	basicPortAlarmMasterReboot OBJECT-TYPE
		SYNTAX INTEGER { ready(1), execute(2) }
		ACCESS read-write
		STATUS mandatory
		DESCRIPTION
                    "Control to reboot the high density alarm unit attached
                     to the port when set to 'execute'. In response to a 
                    get-request or get-next-request, the agent always 
                    returns 'ready' for this value.  Setting the value 
                    to 'ready' has no effect. Corresponds directly to the
                    REBOOT AMST command."
		::= { basicPortEntry 66 }


 	basicPortAlarmMasterUpdateFirmwareHost OBJECT-TYPE
		SYNTAX IpAddress
		ACCESS read-write
		STATUS mandatory
		DESCRIPTION
                    "The internet address of the server to use when 
                    downloading a new firmware image for the high density
                    alarm unit attached to this port via TFTP. 

                    Corresponds directly to the UPDATE AMST FIRMWARE
                    command's INTERNET ADDRESS parameter."
		::= { basicPortEntry 67 }

 	basicPortAlarmMasterUpdateFirmwareFileName OBJECT-TYPE
		SYNTAX DisplayString (SIZE (0..64))
		ACCESS read-write
		STATUS mandatory
		DESCRIPTION
                    "The filename to request when downloading a
                    new firmware image for the high density alarm
                    unit attached to this port via TFTP. 

                    Corresponds directly to the UPDATE AMST FIRMWARE
                    command's FILE parameter."
		::= { basicPortEntry 68 }

 	basicPortAlarmMasterUpdateFirmware OBJECT-TYPE
		SYNTAX INTEGER { ready(1), execute(2) }
		ACCESS read-write
		STATUS mandatory
		DESCRIPTION
                    "Control to update firmware for the high density alarm unit 
                    attached to the port when set to 'execute'. In response to a 
                    get-request or get-next-request, the agent always 
                    returns 'ready' for this value.  Setting the value 
                    to 'ready' has no effect. 

                    The basicPortAlarmMasterUpdateFirmwareHost
                    and basicPortAlarmMasterUpdateFirmwareFileName must be set
                    prior to setting this object.

                    Corresponds directly to the UPDATE AMST FIRMWARE command."
		::= { basicPortEntry 69 }

 	basicPortAlarmMasterStatus OBJECT-TYPE
	       SYNTAX  INTEGER { cleared (1), indeterminate (2), warning (3), 
        	                 minor (4), major (5), critical (6) }
		ACCESS read-only
		STATUS mandatory
		DESCRIPTION
                    "Indicates the current status of the high density
                     alarm unit attached to the port. If no response is
                     obtained from this unit, the status is set to
                     basicPortAlarmMasterFaultSeverity. Otherwise it is cleared."
		::= { basicPortEntry 70 }

 	basicPortAlarmMasterFaultSeverity OBJECT-TYPE
	       SYNTAX  INTEGER { cleared (1), indeterminate (2), warning (3), 
        	                 minor (4), major (5), critical (6) }
		ACCESS read-write
		STATUS mandatory
		DESCRIPTION
        	   "Control to determine the severity level associated with the
	            trap sent out when a fault occurs when no response is
		    obtained from the high density alarm unit attached to this
                    port."
                DEFVAL { major }
		::= { basicPortEntry 71 }


        basicPortPowerMaster OBJECT-TYPE
               SYNTAX  INTEGER { disabled (1), enabled (2) }
                ACCESS read-write
                STATUS mandatory
                DESCRIPTION
                   "Control to configure this port as a power master port.
                    This control is only valid on those models with variable 
                    configuration ports and which support the power master.
                    This object can only be set enabled, and doing so will 
                    disable the previous port type, such as basicPortConsolePort.
                    A set will only update the permanent database. Use a 
                    charPortReset for this change to take effect."
                DEFVAL { disabled }
                ::= { basicPortEntry 72 }

        basicPortPowerMasterTimeDelay OBJECT-TYPE
               SYNTAX  INTEGER { none (1), oneHundred (100), twoHundred (200),
                                 threeHundred (300), fourHundred (400),
                                 fiveHundred (500), sixHundred (600), 
                                 sevenHundred (700), eightHundred (800), 
                                 nineHundred (900) }
                ACCESS read-write
                STATUS mandatory
                DESCRIPTION
                   "Control to set the power up delay interval in milliseconds for
                    the power device attached to this port."
                DEFVAL { none }
                ::= { basicPortEntry 73 }

        basicPortPowerMasterSwitch OBJECT-TYPE
               SYNTAX  INTEGER { ready (1), off (2), on (3) }
                ACCESS read-write
                STATUS mandatory
                DESCRIPTION
                   "Control to power on or off all of the outlets in the power
                    device attached to this port. A get-request always returns ready."
                ::= { basicPortEntry 74 }

        basicPortPowerMasterModel OBJECT-TYPE
               SYNTAX  DisplayString (SIZE (0..20))
                ACCESS read-only
                STATUS mandatory
                DESCRIPTION
                   "The model number of the power master device, which
                    is connected to this port."
                ::= { basicPortEntry 75 }

        basicPortPowerMasterSerialNumber OBJECT-TYPE
               SYNTAX  DisplayString (SIZE (0..17))
                ACCESS read-only
                STATUS mandatory
                DESCRIPTION
                   "The serial number of the power master device, which
                    is connected to this port."
                ::= { basicPortEntry 76 }

       basicPortPowerMasterFirmware OBJECT-TYPE
               SYNTAX  DisplayString (SIZE (0..12))
                ACCESS read-only
                STATUS mandatory
                DESCRIPTION
                   "The firmware version of the power master device,
                    which is connected to this port."
                ::= { basicPortEntry 77 }

        basicPortLockout OBJECT-TYPE
               SYNTAX  INTEGER { disabled (1), enabled (2) }
                ACCESS read-write
                STATUS mandatory
                DESCRIPTION
                   "Control to prohibit access to this port and send a trap
                    when login authentication fails.
                    One must log out the port for this change to take effect."
                DEFVAL { disabled }
                ::= { basicPortEntry 78 }
 
        basicPortAsciiToTrapTranslation OBJECT-TYPE
               SYNTAX  INTEGER { disabled (1), enabled (2) }
                ACCESS read-write
                STATUS mandatory
                DESCRIPTION
                   "Control to configure the port as an ascii-to-trap translator.
                    One must log out the port for this change to take effect."
                DEFVAL { disabled }
                ::= { basicPortEntry 79 }
 
        basicPortAsciiToTrapTranslationTrapSeverity OBJECT-TYPE
               SYNTAX  INTEGER { cleared (1), indeterminate (2), warning (3),
                                 minor (4), major (5), critical (6) }
                ACCESS read-write
                STATUS mandatory
                DESCRIPTION
                   "Control to determine the severity level associated with the
                    trap sent out from this port. One must log out the port
                    for this change to take effect."
                DEFVAL { cleared }
                ::= { basicPortEntry 80 }
 
        basicPortAsciiToTrapTranslationMessages OBJECT-TYPE
               SYNTAX  Counter
                ACCESS read-only
                STATUS mandatory
                DESCRIPTION
                   "Count of number of trap messages sent from this port."
                ::= { basicPortEntry 81 }
 
        basicPortAsciiToTrapTranslationLastMessage OBJECT-TYPE
               SYNTAX  DisplayString  (SIZE(0..255))
                ACCESS read-only
                STATUS mandatory
                DESCRIPTION
                   "The last message or partial message sent out by this port."
                ::= { basicPortEntry 82 }
 
        basicPortPowerMasterAlarmSeverity OBJECT-TYPE
               SYNTAX  INTEGER { cleared (1), indeterminate (2), warning (3), minor (4), major (5), 
	                         critical (6) }
                ACCESS read-write
                STATUS mandatory
                DESCRIPTION
                   "Control to determine the severity level associated with the trap sent out when
                    the power device is not responding to this port."
                DEFVAL { major } 
                ::= { basicPortEntry 83 }

        basicPortPowerMasterDeviceStatus OBJECT-TYPE
               SYNTAX  INTEGER { cleared (1), indeterminate (2), warning (3), minor (4), major (5), 
	                         critical (6) }
                ACCESS read-only
                STATUS mandatory
                DESCRIPTION
                   "Indicates the current status of the power device controlled by this port. If 
                    the device is responding, the status is cleared. Otherwise the status matches
                    the basicPortPowerMasterAlarmSeverity."
                ::= { basicPortEntry 84 }

            -- the Basic Serial Port table
            
            basicSerialPortTable OBJECT-TYPE
                SYNTAX SEQUENCE OF BasicSerialPortEntry
                ACCESS not-accessible
                STATUS mandatory
                DESCRIPTION
                    "A list of basic character serial port entries."
                ::= { xBasic 18 }
            
            basicSerialPortEntry OBJECT-TYPE
                SYNTAX BasicSerialPortEntry
                ACCESS not-accessible
                STATUS mandatory
                DESCRIPTION
                    "Basic parameter values for a serial port."
                INDEX { basicSerialPortIndex }
                ::= { basicSerialPortTable 1 }
            
            BasicSerialPortEntry ::=
                SEQUENCE {
                    basicSerialPortIndex
                        INTEGER,
                    basicSerialPortBreak
                        INTEGER,
                    basicSerialPortInterrupts
                        INTEGER,
                    basicSerialPortNoLoss
                        INTEGER,
                    basicSerialPortPause
                        INTEGER,
                    basicSerialPortPrompt
                        DisplayString,
                    basicSerialPortTerminalType
                        INTEGER,
                    basicSerialPortTypeaheadLimit
                        INTEGER,
                    basicSerialPortBackwardSwitch
                        INTEGER,
                    basicSerialPortForwardSwitch
                        INTEGER,
                    basicSerialPortLocalSwitch
                        INTEGER,
                    basicSerialPortModemControl
                        INTEGER,
                    basicSerialPortSignalCheck
                        INTEGER,
                    basicSerialPortDSRLogout
                        INTEGER,
                    basicSerialPortDSRObserve
                        INTEGER,
                    basicSerialPortDCDTimeout
                        INTEGER,
                    basicSerialPortDTRAssert
                        INTEGER,
                    basicSerialPortLimitedCommands
                        INTEGER,
                    basicSerialPortLimitedView
                        INTEGER,
                    basicSerialPortPassword
                        INTEGER,
                    basicSerialPortLineEditor
                        INTEGER,
                    basicSerialPortLineEditorBackspace
                        INTEGER,
                    basicSerialPortLineEditorBeginning
                        INTEGER,
                    basicSerialPortLineEditorCancel
                        INTEGER,
                    basicSerialPortLineEditorDeleteBeginning
                        INTEGER,
                    basicSerialPortLineEditorDeleteLine
                        INTEGER,
                    basicSerialPortLineEditorEnd
                        INTEGER,
                    basicSerialPortLineEditorForward
                        INTEGER,
                    basicSerialPortLineEditorInsertToggle
                        INTEGER,
                    basicSerialPortLineEditorNextLine
                        INTEGER,
                    basicSerialPortLineEditorPreviousLine
                        INTEGER,
                    basicSerialPortLineEditorQuotingCharacter
                        INTEGER,
                    basicSerialPortLineEditorRedisplay
                        INTEGER,
                    basicSerialPortQuadartReceiveDiscard
                        INTEGER,
                    basicSerialPortAPDProtocols 
                        OCTET STRING,
                    basicSerialPortAPDTimeout 
                        INTEGER,
                    basicSerialPortAPDDefaultProtocol 
                        OCTET STRING,
                    basicSerialPortUsernameCharSet
                        INTEGER,
                    basicSerialPortAutoHangup
                        INTEGER,
                    basicSerialPortCommandSize
                        INTEGER,
                    basicSerialPortAutoProtocolDetectPrompt
                        INTEGER,
                    basicSerialPortUsernamePrompt
                        DisplayString,
                    basicSerialPortPasswordPrompt
                        DisplayString,
                    basicSerialPortAutoProtocolDetectSecurityInteractiveOnly
                        INTEGER,
                    basicSerialPortDedicatedUserData
                        DisplayString,
                    basicSerialPortIpAutoDiscovery 
                        INTEGER,
                    basicSerialPortDedicatedKickStartData
                        DisplayString,
                    basicSerialPortBreakLength
                        INTEGER,
                    basicSerialPortRotaryRoundRobin
                        INTEGER,
                    basicSerialPortWelcomeBeforeAuthentication
                        INTEGER,
                    basicSerialPortGatewayAutoDiscovery 
                        INTEGER,
                    basicSerialPortSubnetAutoDiscovery 
                        INTEGER,
                    basicSerialPortRaiseLowerDtr
                        INTEGER,
                    basicSerialPortRaiseControlDtr
                        INTEGER,
	            basicSerialPortIpConfigureBootp 
                        INTEGER
                     }
            
            basicSerialPortIndex OBJECT-TYPE
                SYNTAX INTEGER
                ACCESS read-only
                STATUS mandatory
                DESCRIPTION
                    "An index value that uniquely identifies a port.  
                    The port identified by a particular value of this 
                    index is the same port as identified by 
                    charPortIndex in the standard Character MIB."
                ::= { basicSerialPortEntry 1 }
            
            basicSerialPortBreak OBJECT-TYPE
                SYNTAX INTEGER { ignore(1), localSwitch(2),
                                 sendRemote(3) }
                ACCESS read-write
                STATUS mandatory
                DESCRIPTION
                    "Action to take on a BREAK condition from the port.  
                    Corresponds directly to PORT BREAK and the value 
                    labeled 'Break:' in the PORT CHARACTERISTICS 
                    display."
                ::= { basicSerialPortEntry 2 }
            
            basicSerialPortInterrupts OBJECT-TYPE
                SYNTAX INTEGER { disabled(1), enabled(2) }
                ACCESS read-write
                STATUS mandatory
                DESCRIPTION
                    "Control for recognizing BREAK or local switch to 
                    interrupt a session.  Corresponds directly to PORT 
                    INTERRUPTS and the presence of the label 
                    'Interrupts' following the label 'Enabled 
                    Characteristics:' in the PORT CHARACTERISTICS 
                    display."
                ::= { basicSerialPortEntry 3 }
            
            basicSerialPortNoLoss OBJECT-TYPE
                SYNTAX INTEGER { disabled(1), enabled(2) }
                ACCESS read-write
                STATUS mandatory
                DESCRIPTION
                    "Control for storing port input locally in 
                    anticipation of session startup.  Corresponds 
                    directly to PORT NOLOSS and the presence of the 
                    label 'Noloss' following the label 'Enabled 
                    Characteristics:' in the PORT CHARACTERISTICS 
                    display."
                ::= { basicSerialPortEntry 4 }
            
            basicSerialPortPause OBJECT-TYPE
                SYNTAX INTEGER { disabled(1), enabled(2) }
                ACCESS read-write
                STATUS mandatory
                DESCRIPTION
                    "Control for pausing after each screenful of 
                    locally-originated output to the port.  Corresponds 
                    directly to PORT PAUSE and the presence of the label 
                    'Pause' following the label 'Enabled 
                    Characteristics:' in the PORT CHARACTERISTICS 
                    display."
                ::= { basicSerialPortEntry 5 }
            
            basicSerialPortPrompt OBJECT-TYPE
                SYNTAX DisplayString (SIZE (0..20))
                ACCESS read-write
                STATUS mandatory
                DESCRIPTION
                    "Prompt for the system to use on the port.  
                    Corresponds directly to PORT PROMPT and the value 
                    labeled 'Prompt:' in the PORT ALTERNATE 
                    CHARACTERISTICS display."
                ::= { basicSerialPortEntry 6 }
            
            basicSerialPortTerminalType OBJECT-TYPE
                SYNTAX INTEGER { ansi(1), hardcopy(2), softcopy(3) }
                ACCESS read-write
                STATUS mandatory
                DESCRIPTION
                    "Type of terminal attached to the port, for 
                    formatting local output.  Corresponds directly to 
                    PORT TYPE and the value labeled 'Type:' in the PORT 
                    CHARACTERISTICS display."
                ::= { basicSerialPortEntry 7 }
            
            basicSerialPortTypeaheadLimit OBJECT-TYPE
                SYNTAX INTEGER (80..16384)
                ACCESS read-write
                STATUS mandatory
                DESCRIPTION
                    "Maximum number of input characters to hold pending 
                    tranmission on a session.  Corresponds directly to 
                    PORT TYPEAHEAD SIZE and the value labeled 'Typeahead 
                    Size:' in the PORT ALTERNATE CHARACTERISTICS 
                    display."
                ::= { basicSerialPortEntry 8 }
            
            basicSerialPortBackwardSwitch OBJECT-TYPE
                SYNTAX INTEGER (0..255)
                ACCESS read-write
                STATUS mandatory
                DESCRIPTION
                    "Character input from the character port to cause a 
                    switch to the previous, lower numbered session.  The 
                    value 0 indicates no character has this effect.  
                    Corresponds directly to PORT BACKWARD SWITCH and the 
                    value labeled 'Backwards Switch:' in the PORT 
                    CHARACTERISTICS display."
                ::= { basicSerialPortEntry 9 }
            
            basicSerialPortForwardSwitch OBJECT-TYPE
                SYNTAX INTEGER (0..255)
                ACCESS read-write
                STATUS mandatory
                DESCRIPTION
                    "Character input from the character port to cause a 
                    switch to the next, higher numbered session.  The 
                    value 0 indicates no character has this effect.  
                    Corresponds directly to PORT FORWARD SWITCH and the 
                    value labeled 'Forwards Switch:' in the PORT 
                    CHARACTERISTICS display."
                ::= { basicSerialPortEntry 10 }
            
            basicSerialPortLocalSwitch OBJECT-TYPE
                SYNTAX INTEGER (0..255)
                ACCESS read-write
                STATUS mandatory
                DESCRIPTION
                    "Character input from the character port to cause a 
                    switch to local command mode.  The value 0 indicates 
                    no character has this effect.  Corresponds directly 
                    to PORT LOCAL SWITCH and the value labeled 'Local 
                    Switch:' in the PORT CHARACTERISTICS display."
                ::= { basicSerialPortEntry 11 }
            
            basicSerialPortModemControl OBJECT-TYPE
                SYNTAX INTEGER { disabled(1), enabled(2) }
                ACCESS read-write
                STATUS mandatory
                DESCRIPTION
                    "Control for observing hardware modem control 
                    signals.  Corresponds directly to PORT MODEM CONTROL 
                    and the value labeled 'Modem Control:' in the PORT 
                    CHARACTERISTICS display. This object is not available
                    on units that do not support modem signals (ie 2220)."
                ::= { basicSerialPortEntry 12 }
            
            basicSerialPortSignalCheck OBJECT-TYPE
                SYNTAX INTEGER { disabled(1), enabled(2) }
                ACCESS read-write
                STATUS mandatory
                DESCRIPTION
                    "Control for observing DSR and DCD to bound allowing 
                    sessions.  Corresponds directly to PORT SIGNAL CHECK 
                    and the presence of the label 'Signal Check' 
                    following the label 'Enabled Characteristics:' in 
                    the PORT CHARACTERISTICS display. This object is not 
                    available on units that do not support modem signals 
                    (ie 2220)."
                ::= { basicSerialPortEntry 13 }
            
            basicSerialPortDSRLogout OBJECT-TYPE
                SYNTAX INTEGER { disabled(1), enabled(2) }
                ACCESS read-write
                STATUS mandatory
                DESCRIPTION
                    "Control for logging out the port when DCD is 
                    deasserted.  Corresponds directly to PORT DSRLOGOUT 
                    and the presence of the label 'DSRlogout' following 
                    the label 'Enabled Characteristics:' in the PORT 
                    CHARACTERISTICS display. This object is not available
                    on units that do not support modem signals (ie 2220)."
                ::= { basicSerialPortEntry 14 }
            
            basicSerialPortDSRObserve OBJECT-TYPE
                SYNTAX INTEGER { disabled(1), enabled(2) }
                ACCESS read-write
                STATUS mandatory
                DESCRIPTION
                    "Control for beginning the login sequence on the 
                    port when DCD is asserted.  Corresponds directly to 
                    PORT DSRWAIT and the presence of the label 'DSRwait' 
                    following the label 'Enabled Characteristics:' in 
                    the PORT CHARACTERISTICS display. This object is not 
                    available on units that do not support modem signals
                    (ie 2220)."
                ::= { basicSerialPortEntry 15 }
            
            basicSerialPortDCDTimeout OBJECT-TYPE
                SYNTAX INTEGER (0..10000)
                ACCESS read-write
                STATUS mandatory
                DESCRIPTION
                    "The number of milleseconds that DCD may be asserted 
                    before disconnecting the port.  Corresponds directly 
                    to PORT DCD TIMEOUT and the value labeled 'DCD 
                    Timeout:' in the PORT ALTERNATE CHARACTERISTICS 
                    display. This object is not available
                    on units that do not support modem signals (ie 2220)."
                ::= { basicSerialPortEntry 16 }
            
            basicSerialPortDTRAssert OBJECT-TYPE
                SYNTAX INTEGER { always(1), onConnectionOrRing(2),
                                 onConnection(3), onRing(4) }
                ACCESS read-write
                STATUS mandatory
                DESCRIPTION
                    "Control when the system asserts DTR on the port.
            
                    always               unconditional(DISABLED)
                    onConnectionOrRing   connection formed or RING
                                         asserted(ENABLED)
                    onConnection         connection formed
                                         (FORCONNECTION)
                    onRing               RING asserted (FORRING)
            
                    Corresponds directly to PORT DTRWAIT and the value 
                    labeled 'DTR Wait:' in the PORT ALTERNATE 
                    CHARACTERISTICS display. This object is not available
                    on units that do not support modem signals (ie 2220)."
                ::= { basicSerialPortEntry 17 }
            
            basicSerialPortLimitedCommands OBJECT-TYPE
                SYNTAX INTEGER { disabled(1), enabled(2) }
                ACCESS read-write
                STATUS mandatory
                DESCRIPTION
                    "Control for limiting the commands available to the 
                    user on the port.  Corresponds directly to PORT 
                    SECURITY and the presence of the label 'Security' 
                    following the label 'Enabled Characteristics:' in 
                    the PORT CHARACTERISTICS display. This object is not
                    available on units that do not support modem signals 
                    (ie 2220)."
                ::= { basicSerialPortEntry 18 }
            
            basicSerialPortLimitedView OBJECT-TYPE
                SYNTAX INTEGER { disabled(1), enabled(2) }
                ACCESS read-write
                STATUS mandatory
                DESCRIPTION
                    "Control for restricting what a user may display.  
                    Corresponds directly to PORT LIMITED VIEW and the 
                    presence of the label 'Limited View' following the 
                    label 'Enabled Characteristics:' in the PORT 
                    CHARACTERISTICS display."
                ::= { basicSerialPortEntry 19 }
            
            basicSerialPortPassword OBJECT-TYPE
                SYNTAX INTEGER { disabled(1), enabled(2) }
                ACCESS read-write
                STATUS mandatory
                DESCRIPTION
                    "Control for requiring the user to supply the login 
                    password to log in on the port.  Corresponds 
                    directly to PORT PASSWORD and the presence of the 
                    label 'Password' following the label 'Enabled 
                    Characteristics:' in the PORT CHARACTERISTICS 
                    display."
                ::= { basicSerialPortEntry 20 }
            
            basicSerialPortLineEditor OBJECT-TYPE
                SYNTAX INTEGER { disabled(1), enabled(2) }
                ACCESS read-write
                STATUS mandatory
                DESCRIPTION
                    "Control for allowing the user to use local mode 
                    command line editing.  Corresponds directly to PORT 
                    LINE EDITOR and the presence of the label 'Line 
                    Editor' following the label 'Enabled 
                    Characteristics:' in the PORT CHARACTERISTICS 
                    display."
                ::= { basicSerialPortEntry 21 }
            
            -- Note that the values for the switching and 
            -- line editing characters are mutally exclusive
            
            basicSerialPortLineEditorBackspace OBJECT-TYPE
                SYNTAX INTEGER (0..255)
                ACCESS read-write
                STATUS mandatory
                DESCRIPTION
                    "Character input from the character port to move the 
                    cursor to the left.  The value 0 indicates no 
                    character has this effect.  Corresponds directly to 
                    PORT LINE EDITOR BACKSPACE and the value labeled 
                    'Backspace Character:' in the PORT ALTERNATE 
                    CHARACTERISTICS display."
                ::= { basicSerialPortEntry 22 }
            
            basicSerialPortLineEditorBeginning OBJECT-TYPE
                SYNTAX INTEGER (0..255)
                ACCESS read-write
                STATUS mandatory
                DESCRIPTION
                    "Character input from the character port to move the 
                    cursor to the beginning of the line.  The value 0 
                    indicates no character has this effect.  Corresponds 
                    directly to PORT LINE EDITOR BEGINNING and the value 
                    labeled 'Begin Line Character:' in the PORT 
                    ALTERNATE CHARACTERISTICS display."
                ::= { basicSerialPortEntry 23 }
            
            basicSerialPortLineEditorCancel OBJECT-TYPE
                SYNTAX INTEGER (0..255)
                ACCESS read-write
                STATUS mandatory
                DESCRIPTION
                    "Character input from the character port to cancel 
                    an interactive dialog or delete the current line.  
                    The value 0 indicates no character has this effect.  
                    Corresponds directly to PORT LINE EDITOR CANCEL and 
                    the value labeled 'Cancel Character:' in the PORT 
                    ALTERNATE CHARACTERISTICS display."
                ::= { basicSerialPortEntry 24 }
            
            basicSerialPortLineEditorDeleteBeginning OBJECT-TYPE
                SYNTAX INTEGER (0..255)
                ACCESS read-write
                STATUS mandatory
                DESCRIPTION
                    "Character input from the character port to delete 
                    the current line from the cursor to the beginning.  
                    The value 0 indicates no character has this effect.  
                    Corresponds directly to PORT LINE EDITOR DELETE 
                    BEGINNING and the value labeled 'Delete Begin 
                    Character:' in the PORT ALTERNATE CHARACTERISTICS 
                    display."
                ::= { basicSerialPortEntry 25 }
            
            basicSerialPortLineEditorDeleteLine OBJECT-TYPE
                SYNTAX INTEGER (0..255)
                ACCESS read-write
                STATUS mandatory
                DESCRIPTION
                    "Character input from the character port to delete 
                    the current line.  The value 0 indicates no 
                    character has this effect.  Corresponds directly to 
                    PORT LINE EDITOR DELETE LINE and the value labeled 
                    'Delete Line Character:' in the PORT ALTERNATE 
                    CHARACTERISTICS display."
                ::= { basicSerialPortEntry 26 }
            
            basicSerialPortLineEditorEnd OBJECT-TYPE
                SYNTAX INTEGER (0..255)
                ACCESS read-write
                STATUS mandatory
                DESCRIPTION
                    "Character input from the character port to move the 
                    cursor to the end of the line.  The value 0 
                    indicates no character has this effect.  Corresponds 
                    directly to PORT LINE EDITOR END and the value 
                    labeled 'End of Line Character:' in the PORT 
                    ALTERNATE CHARACTERISTICS display."
                ::= { basicSerialPortEntry 27 }
            
            basicSerialPortLineEditorForward OBJECT-TYPE
                SYNTAX INTEGER (0..255)
                ACCESS read-write
                STATUS mandatory
                DESCRIPTION
                    "Character input from the character port to move the 
                    cursor to the right.  The value 0 indicates no 
                    character has this effect.  Corresponds directly to 
                    PORT LINE EDITOR FORWARDS and the value labeled 
                    'Forwards Character:' in the PORT ALTERNATE 
                    CHARACTERISTICS display."
                ::= { basicSerialPortEntry 28 }
            
            basicSerialPortLineEditorInsertToggle OBJECT-TYPE
                SYNTAX INTEGER (0..255)
                ACCESS read-write
                STATUS mandatory
                DESCRIPTION
                    "Character input from the character port to toggle 
                    between insert and overwrite modes.  The value 0 
                    indicates no character has this effect.  Corresponds 
                    directly to PORT LINE EDITOR INSERT TOGGLE and the 
                    value labeled 'Insert Character:' in the PORT 
                    ALTERNATE CHARACTERISTICS display."
                ::= { basicSerialPortEntry 29 }
            
            basicSerialPortLineEditorNextLine OBJECT-TYPE
                SYNTAX INTEGER (0..255)
                ACCESS read-write
                STATUS mandatory
                DESCRIPTION
                    "Character input from the character port to recall 
                    the next, newer line in the command history.  The 
                    value -1 indicates no character has this effect.  
                    Corresponds directly to PORT LINE EDITOR NEXT LINE 
                    and the value labeled 'Next Line Character:' in the 
                    PORT ALTERNATE CHARACTERISTICS display."
                ::= { basicSerialPortEntry 30 }
            
            basicSerialPortLineEditorPreviousLine OBJECT-TYPE
                SYNTAX INTEGER (0..255)
                ACCESS read-write
                STATUS mandatory
                DESCRIPTION
                    "Character input from the character port to recall 
                    the previous, older line in the command history.  
                    The value 0 indicates no character has this effect.  
                    Corresponds directly to PORT LINE EDITOR PREVIOUS 
                    LINE and the value labeled 'Previous Line 
                    Character:' in the PORT ALTERNATE CHARACTERISTICS 
                    display."
                ::= { basicSerialPortEntry 31 }
            
            basicSerialPortLineEditorQuotingCharacter OBJECT-TYPE
                SYNTAX INTEGER (0..255)
                ACCESS read-write
                STATUS mandatory
                DESCRIPTION
                    "Character input from the character port to inhibit 
                    interpretation of the next input character.  The 
                    value 0 indicates no character has this effect.  
                    Corresponds directly to PORT LINE EDITOR QUOTING 
                    CHARACTER and the value labeled 'Quoting Character:' 
                    in the PORT ALTERNATE CHARACTERISTICS display."
                ::= { basicSerialPortEntry 32 }
            
            basicSerialPortLineEditorRedisplay OBJECT-TYPE
                SYNTAX INTEGER (0..255)
                ACCESS read-write
                STATUS mandatory
                DESCRIPTION
                    "Character input from the character port to 
                    redisplay the current command line.  The value 0 
                    indicates no character has this effect.  Corresponds 
                    directly to PORT LINE EDITOR REDISPLAY CHARACTER and 
                    the value labeled 'Redisplay Character:' in the PORT 
                    ALTERNATE CHARACTERISTICS display."
                ::= { basicSerialPortEntry 33 }
            
            basicSerialPortQuadartReceiveDiscard OBJECT-TYPE
                SYNTAX INTEGER { disabled(1), enabled(2) }
                ACCESS read-write
                STATUS mandatory
                DESCRIPTION
                    "Control for discard of received errors from quadart 
                    hardware."
                ::= { basicSerialPortEntry 34 }

            basicSerialPortAPDProtocols OBJECT-TYPE
                SYNTAX OCTET STRING (SIZE (2))
                ACCESS read-write
                STATUS mandatory
                DESCRIPTION
                    "A bit map that specifies the protocols
                      that this port will attempt to detect
                     using the Auto Protocol Detection
                     function. The bit numbers for the
                     protocols are: 1;ARAP, 3;Interactive, 4;SLIP, 5;PPP.
                     Bits 6-16 are reserved for future use.
                     More than one of these protocols may
                     be ORed together. The default is 0 (zero)
                     no protocols."
                DEFVAL { '00'h }  -- the null string
                ::= { basicSerialPortEntry 35 }
            
            basicSerialPortAPDTimeout OBJECT-TYPE
                SYNTAX INTEGER (0..255)
                ACCESS read-write
                STATUS mandatory
                DESCRIPTION
                    "A time value, in seconds, that 
                    specifies how long the port will
                    attempt to determine which
                    protocol is coming into the port.
                    When basicSerialPortAPDTimeout seconds
                    have expired, the port will assume the
                    protocol to use is that specified by
                    basicSerialPortAPDDefaultProtocol.
                    A value of 0 (zero provides an unlimited timeout."
                DEFVAL { 0 }
                ::= { basicSerialPortEntry 36 }
            
            basicSerialPortAPDDefaultProtocol OBJECT-TYPE
                SYNTAX OCTET STRING (SIZE (2))
                ACCESS read-write
                STATUS mandatory
                DESCRIPTION
                    "A bit map that specifies the protocol
                     that this port will use when the time
                     specified by basicSerialPortAPDTimeout
                     has expired without sucessfully
                     identifying the incoming porotocol.
                     The bit numbers for the protocols are:
                     None;Logout the port, 1;ARAP, 2;CSLIP,
                     3;Interactive, 4;SLIP, 5;PPP. Bits 6-16
                     are reserved for future use. Only
                     one protocol may be specified for this
                     object"
                DEFVAL { '00'h }  -- the null string
                ::= { basicSerialPortEntry 37 }
            
            basicSerialPortUsernameCharSet OBJECT-TYPE
                SYNTAX INTEGER {none(1), seven-bit(2)}
                ACCESS read-write
                STATUS mandatory
                DESCRIPTION
                    "A control, that if set to seven-bit, will
                    allow only the ASCII printable characters
                    in the range SP (X20) to ~ (X7E) in the username
                    field. A value of none allows any character"
                DEFVAL { none}
                ::= { basicSerialPortEntry 38 }
            
            basicSerialPortAutoHangup OBJECT-TYPE
                SYNTAX INTEGER { disabled(1), enabled(2) }
                ACCESS read-write
                STATUS mandatory
                DESCRIPTION 
                    "A control that, if enabled,  will cause the port to be
                    logged off when the last session on that port is destroyed"
                DEFVAL {disabled}
                ::= {basicSerialPortEntry 39}
            
            basicSerialPortCommandSize OBJECT-TYPE
                SYNTAX INTEGER (80..16384)
                ACCESS read-write
                STATUS mandatory 
                DESCRIPTION
                    "Maximum number of input characters to hold in the command
                    buffer. Corresponds directly to the PORT COMMAND SIZE
                    and the value labeled 'Command Size:' in the PORT 
                    ALTERNATE CHARACTERISTICS display." 	
                DEFVAL { 80 }
                ::= { basicSerialPortEntry 40 }

            basicSerialPortAutoProtocolDetectPrompt OBJECT-TYPE
                SYNTAX INTEGER { disabled(1), enabled(2) }
                ACCESS read-write
                STATUS mandatory
                DESCRIPTION
                    "Controls whether to send the basicAutoProtocolDetectMessage
                     out the serial port at the beginning of auto protocol
                     detection mode. Corresponds to the value labeled 'APD
                     Prompt' in the PORT ALTERNATE CHARACTERISTICS display."
                DEFVAL { enabled }
                ::= { basicSerialPortEntry 41 }

            basicSerialPortUsernamePrompt OBJECT-TYPE
                SYNTAX DisplayString (SIZE (0..25))
                ACCESS read-write
                STATUS mandatory
                DESCRIPTION
                    "The text string used to prompt for a user's name. 
                     Corresponds directly to the value labeled 'Username 
                     Prompt:' in the PORT ALTERNATE CHARACTERISTICS display."
                DEFVAL { "Enter username>"  }
                ::= { basicSerialPortEntry 42 }
 
            basicSerialPortPasswordPrompt OBJECT-TYPE
                SYNTAX DisplayString (SIZE (0..25))
                ACCESS read-write
                STATUS mandatory
                DESCRIPTION
                    "The text string used to prompt for a user's password.
                     Corresponds directly to the value labeled 'Password 
                     Prompt:' in the PORT ALTERNATE CHARACTERISTICS display."
                DEFVAL { "Enter user password>"  }
                ::= { basicSerialPortEntry 43 }
 
            basicSerialPortAutoProtocolDetectSecurityInteractiveOnly OBJECT-TYPE
                SYNTAX INTEGER { disabled(1), enabled(2) }
                ACCESS read-write
                STATUS mandatory
                DESCRIPTION
                    "Controls whether Auto Protocol Detect (APD) authentication 
                     applies only to interactive users, and not to other APD 
                     protocols such as PPP. Corresponds directly to the value 
                     labeled 'APD Authentication Interactive Only:' in the PORT
                     CHARACTERISTICS display."
                DEFVAL { disabled }
                ::= { basicSerialPortEntry 44 }
 
            basicSerialPortDedicatedUserData OBJECT-TYPE
                SYNTAX DisplayString (SIZE (0..16))
                ACCESS read-write
                STATUS mandatory
                DESCRIPTION
                    "The text string to send at the beginning of a connection
                     to a Telnet dedicated service. Corresponds to the value
                     labeled 'UserData:' in the PORT CHARACTERISTICS display."
                DEFVAL { "" }  -- the null string
                ::= { basicSerialPortEntry 45 }
 
           basicSerialPortIpAutoDiscovery OBJECT-TYPE
                SYNTAX INTEGER { disabled(1), enabled(2) }
                ACCESS read-write
                STATUS deprecated
                DESCRIPTION
                    "Control to enable a non-standard method of acquiring the
                     IP address after boot completes via the BOOTP protocol.
                     Corresponds to the value labeled 'IP Address
                     Auto Discovery' in the SERVER CHARACTERISTICS display."
                DEFVAL { disabled }
                ::= { basicSerialPortEntry 47 }
 
           basicSerialPortDedicatedKickStartData OBJECT-TYPE
                SYNTAX DisplayString (SIZE (0..16))
                ACCESS read-write
                STATUS mandatory
                DESCRIPTION
                    "A text string which is used to compare at login time to
                     incoming serial data. A match will initiate a telnet
                     session to a dedicated service. Corresponds to the value
                     labeled 'KickStart:' in the PORT CHARACTERISTICS display."
                DEFVAL { "" }  -- the null string
                ::= { basicSerialPortEntry 48 }
 
 
           basicSerialPortBreakLength OBJECT-TYPE
                SYNTAX INTEGER { ms250(1), ms500(2), ms750(3) }
                ACCESS read-write
                STATUS mandatory
                DESCRIPTION
                    "Specifies the duration in milliseconds of a remote serial
                     break which is sent via the Telnet Break command. 
                     Corresponds directly to the value labeled 'Break Length:'
                     in the PORT CHARACTERISTIC display."
                ::= { basicSerialPortEntry 50 }

           basicSerialPortRotaryRoundRobin OBJECT-TYPE
                SYNTAX INTEGER  { disabled(1), enabled(2) }
                ACCESS read-write
                STATUS mandatory
                DESCRIPTION
                    "Controls whether a port which participates in an internet
                     rotary is selected in round robin or fixed priority order.
                     Corresponds directly to the value labeled 'Round Robin
                     search:' in the SERVER INTERNET ROTARY display."
                DEFVAL { enabled }
                ::= { basicSerialPortEntry 51 }
 
           basicSerialPortWelcomeBeforeAuthentication OBJECT-TYPE
                SYNTAX INTEGER  { disabled(1), enabled(2) }
                ACCESS read-write
                STATUS mandatory
                DESCRIPTION
                    "Control to display the basicWelcome message prior to
                     authenticating the user. Corresponds to the presence of the
                     value 'Welcome-Banner-Pre-Authentication' following the 
                     label 'Enabled Characteristics' in the PORT CHARACTERISTICS
                     display."
                DEFVAL { disabled }
                ::= { basicSerialPortEntry 52 }

           basicSerialPortGatewayAutoDiscovery OBJECT-TYPE
                SYNTAX INTEGER { disabled(1), enabled(2) }
                ACCESS read-write
                STATUS deprecated
                DESCRIPTION
                    "Control to enable a non-standard method of acquiring the
                     gateway address after boot completes via the bootp
                     protocol."
                DEFVAL { disabled  }
                ::= { basicSerialPortEntry 53 }
           
           basicSerialPortSubnetAutoDiscovery OBJECT-TYPE
                SYNTAX INTEGER  { disabled(1), enabled(2) }  
                ACCESS read-write
                STATUS deprecated
                DESCRIPTION
                    "Control to enable a non-standard method of acquiring the 
                     subnet mask after boot completes via the bootp protocol."
                DEFVAL { disabled  }
                ::= { basicSerialPortEntry 54 }
          
           basicSerialPortRaiseLowerDtr OBJECT-TYPE
                SYNTAX INTEGER { low(1), high(2) } 
                ACCESS read-write
                STATUS mandatory
                DESCRIPTION
                    "A control to to raise or lower the DTR signal from this
                     port by setting it to high or low, respectively. This
                     request will have no effect unless 
                     basicSerialPortRaiseControlDtr is enabled. In response 
                     to a get-request or get-next-request the agent always 
                     returns low for this object."
                ::= { basicSerialPortEntry 55 }                

           basicSerialPortRaiseControlDtr  OBJECT-TYPE
                SYNTAX INTEGER { disabled(1), enabled(2) }
                ACCESS read-write
                STATUS mandatory
                DESCRIPTION
                    "Controls the ability to change the state of DTR using 
                     basicSerialPortRaiseLowerDTR. This characteristic is not
                     intended for use with modem ports. Corresponds directly
                     to the presence of 'Control DTR' under the label 
                     'Enabled Characteristics' in the PORT CHARACTERISTICS 
                     display. The desired change will not take effect until 
                     the port is logged off."
                DEFVAL { disabled }
                ::= { basicSerialPortEntry 56 }                
 
            basicSerialPortIpConfigureBootp OBJECT-TYPE
                SYNTAX INTEGER { disabled(1), enabled(2) }
                ACCESS read-write
                STATUS deprecated
                DESCRIPTION
		    "Control to use the BOOTP protocol upon startup to learn
                     the unit's own internet address, subnet mask, primary and 
                     secondary gateway servers, domain name servers, time 
                     server and domain name. This object was moved to the 
                     ITOUCH-INTERNET-MIB for InReach agent software version V2.4."
                DEFVAL { enabled }
                ::= { basicSerialPortEntry 57 }                

            -- the Basic group continued
            
            basicConsoleLogoutDisconnect OBJECT-TYPE
                SYNTAX INTEGER { disabled(1), enabled(2) }
                ACCESS read-write
                STATUS mandatory
                DESCRIPTION
                    "Control for automatic session disconnection when a 
                    console port user logs out.  Corresponds directly to 
                    SERVER CONSOLE LOGOUT and the presence of the label 
                    'Console Logout' following the label 'Enabled 
                    Characteristics:' in the SERVER CHARACTERISTICS 
                    display."
                ::= { xBasic 19 }
            
        basicControlledPorts OBJECT-TYPE
               SYNTAX INTEGER { disabled(1), enabled(2) }
               ACCESS read-write
               STATUS mandatory
               DESCRIPTION
		    "Status of Controlled Ports feature. Corresponds directly
		     to the 'Controlled Ports' following the label 'Enabled
		     Characteristics:' in the SERVER CHARACTERISTICS display.
             Enabling this feature causes strings of control characters
             to be sent out on a port upon starting and/or stopping a session"
                    ::= { xBasic 20 }
     
            -- the Basic Port Session table
 
            basicPortSessionTable OBJECT-TYPE
                SYNTAX SEQUENCE OF BasicPortSessEntry
                ACCESS not-accessible
                STATUS mandatory
                DESCRIPTION
                    "A list of port session entries."
                ::= { xBasic 21}

 

            basicPortSessEntry OBJECT-TYPE
                SYNTAX BasicPortSessEntry
                ACCESS not-accessible
                STATUS mandatory
                DESCRIPTION
                    "Status and parameter values for a basic port
                    session."
                INDEX { basicPortPortIndex, basicPortSessIndex }
                ::= { basicPortSessionTable 1 }
 
            BasicPortSessEntry ::=
                SEQUENCE {
                    basicPortPortIndex
                        INTEGER,
                    basicPortSessIndex
                        INTEGER,
		            basicSessControlled
			            INTEGER
		            }
       
 
            basicPortPortIndex OBJECT-TYPE
                SYNTAX INTEGER
                ACCESS read-only
                STATUS mandatory
                DESCRIPTION
                    "The value of basicPortIndex for the port to which
                    this session belongs.
                    The port identified by a particular value of this 
                    index is the same port as identified by 
                    charPortIndex in the standard Character MIB."
                ::= { basicPortSessEntry 1 }
 
            basicPortSessIndex OBJECT-TYPE
                SYNTAX INTEGER
                ACCESS read-only
                STATUS mandatory
                DESCRIPTION
                    "The session index in the context of the port, a
                    non-zero positive integer.  Session indexes within a
                    port need not be sequential.  Session indexes may be
                    reused for different ports.  For example, port 1 and
                    port 3 may both have a session 2 at the same time.
                    Session indexes may have any valid integer value,
                    with any meaning convenient to the agent
                    implementation.
                    The session identified by a particular value of this 
                    index is the same session as identified by 
                    charSessIndex in the standard Character MIB."
                ::= { basicPortSessEntry 2 }
	
            basicSessControlled OBJECT-TYPE
               SYNTAX INTEGER { disabled(1), enabled(2) }
               ACCESS read-only
               STATUS mandatory
               DESCRIPTION
		     "A control to send preconfigured controlled port session
		      strings out the serial port when entering or exiting
		      this session. Corresponds directly to the value labeled
		      'Controlled' under the Service Mode header in the 
		      SESSION display."
                    ::= { basicPortSessEntry 3 }

           basicPortSessEncryption OBJECT-TYPE
                SYNTAX INTEGER { disabled(1), enabled(2) }
                ACCESS read-write
                STATUS mandatory
                DESCRIPTION
                    "Status of the default encryption value to be set
                     for each session.  Corresponds directly to Console
					 Security on SHOW SERVER screen."
                ::= { xBasic 22}


basicTemperatureUnits OBJECT-TYPE
        SYNTAX  INTEGER { fahrenheit  (1), celcius (2) }
        ACCESS  read-write
        STATUS  mandatory
        DESCRIPTION
            "Indicates the units of measurement for the temperature sensors."
	DEFVAL {fahrenheit }
        ::= { xBasic 23 }

basicEnvironmentalManagerCircuitBreaker OBJECT-TYPE
        SYNTAX  INTEGER { disabled  (1), enabled (2) }
        ACCESS  read-only
        STATUS  mandatory
        DESCRIPTION
            "Indicates whether the circuit breaker is activated."
        ::= { xBasic 24 }

-- Contact Closure or Alarm Input Table

basicContactClosureOrAlarmInputTable OBJECT-TYPE
        SYNTAX  SEQUENCE OF BasicContactClosureOrAlarmInputEntry
        ACCESS  not-accessible
        STATUS  mandatory
        DESCRIPTION
            "Information about contact closures or alarm inputs."
        ::= { xBasic 25 }

basicContactClosureOrAlarmInputEntry OBJECT-TYPE
        SYNTAX  BasicContactClosureOrAlarmInputEntry
        ACCESS  not-accessible
        STATUS  mandatory
        DESCRIPTION
            "An entry in the basicContactClosureOrAlarmInputTable."
        INDEX { basicContactClosureOrAlarmInputIndex }
        ::= { basicContactClosureOrAlarmInputTable 1 }


BasicContactClosureOrAlarmInputEntry ::=
    SEQUENCE {
        basicContactClosureOrAlarmInputValue
       	    INTEGER,
        basicContactClosureOrAlarmInputName
            DisplayString,
        basicContactClosureOrAlarmInputTrapEnable
            INTEGER,
        basicContactClosureOrAlarmInputFaultSeverity 
            INTEGER,
        basicContactClosureOrAlarmInputFaultState
            INTEGER,
        basicContactClosureOrAlarmInputStatus 
            INTEGER,
        basicContactClosureOrAlarmInputZone 
            DisplayString,
        basicContactClosureOrAlarmInputRelatedEquipment 
            DisplayString,
        basicContactClosureOrAlarmInputSiteId 
            DisplayString,
        basicContactClosureOrAlarmInputIndex
            INTEGER,
        basicContactClosureOrAlarmInputManufacturer 
            DisplayString,
        basicContactClosureOrAlarmInputModel
            DisplayString
             }

 basicContactClosureOrAlarmInputValue  OBJECT-TYPE
        SYNTAX  INTEGER { open (1), closed (2) }
        ACCESS  read-only
        STATUS  mandatory
        DESCRIPTION
            "Indicates the state of the contact closure or alarm input."
        ::= { basicContactClosureOrAlarmInputEntry 1 }

 basicContactClosureOrAlarmInputName OBJECT-TYPE
        SYNTAX  DisplayString (SIZE (0..32 ))
        ACCESS  read-write
        STATUS  mandatory
        DESCRIPTION
            "The name used to identify this contact closure or alarm input."
       ::= { basicContactClosureOrAlarmInputEntry 2 }
 
 basicContactClosureOrAlarmInputTrapEnable OBJECT-TYPE
       SYNTAX  INTEGER { disabled (1), enabled (2) }
       ACCESS  read-write
       STATUS  mandatory
       DESCRIPTION
           "Control to send trap when contact closure or alarm input changes
            state."
       DEFVAL { enabled  }
       ::= { basicContactClosureOrAlarmInputEntry 3 }

 basicContactClosureOrAlarmInputFaultSeverity OBJECT-TYPE
       SYNTAX  INTEGER { cleared (1), indeterminate (2), warning (3), 
                         minor (4), major (5), critical (6) }
       ACCESS  read-write
       STATUS  mandatory
       DESCRIPTION
           "Control to determine the severity level associated with the
            trap sent out when a fault occurs for a given contact  
            closure or alarm input."
       DEFVAL { minor  }
       ::= { basicContactClosureOrAlarmInputEntry 4 }

 basicContactClosureOrAlarmInputFaultState OBJECT-TYPE
       SYNTAX  INTEGER { open (1), closed (2) }
       ACCESS  read-write
       STATUS  mandatory
       DESCRIPTION
           "Control to indicate which state, open or closed, represents the 
            fault condition. The other state is the cleared condition."
       DEFVAL { open  }
       ::= { basicContactClosureOrAlarmInputEntry 5 }

 basicContactClosureOrAlarmInputStatus OBJECT-TYPE
       SYNTAX  INTEGER { cleared (1), indeterminate (2), warning (3), 
                         minor (4), major (5), critical (6) }
       ACCESS  read-only
       STATUS  mandatory
       DESCRIPTION
           "Indicates the current status of the contact closure or alarm input.
            If the basicContactClosureOrAlarmInputValue matches the fault 
            state, then the status is equal to the fault severity. Otherwise
            the status is cleared."
       ::= { basicContactClosureOrAlarmInputEntry 6 }

        basicContactClosureOrAlarmInputZone OBJECT-TYPE
               SYNTAX  DisplayString (SIZE(0..32))
                ACCESS read-write
                STATUS mandatory
                DESCRIPTION
                   "The name used to identify the zone where the equipment
                    resides."
                ::= { basicContactClosureOrAlarmInputEntry 7 }
 
        basicContactClosureOrAlarmInputRelatedEquipment OBJECT-TYPE
               SYNTAX  DisplayString (SIZE(0..32))
                ACCESS read-write
                STATUS mandatory
                DESCRIPTION
                   "The name used to identify related equipment."
                ::= { basicContactClosureOrAlarmInputEntry 8 }
                   
        basicContactClosureOrAlarmInputSiteId OBJECT-TYPE
               SYNTAX  DisplayString (SIZE(0..32))
                ACCESS read-write
                STATUS mandatory
                DESCRIPTION
                   "The name used to identify the site where the unit resides."
                ::= { basicContactClosureOrAlarmInputEntry 9 }
           
 basicContactClosureOrAlarmInputIndex OBJECT-TYPE
        SYNTAX  INTEGER
        ACCESS  read-only
        STATUS  mandatory
        DESCRIPTION
            "An index which uniquely identifies the contact closure or alarm
             input."
        ::= { basicContactClosureOrAlarmInputEntry 10 }

        basicContactClosureOrAlarmInputManufacturer OBJECT-TYPE
               SYNTAX  DisplayString (SIZE(0..32))
                ACCESS read-write
                STATUS mandatory
                DESCRIPTION
                   "The name used to identify the manufacturer of this equipment."
                ::= { basicContactClosureOrAlarmInputEntry 11 }
 
        basicContactClosureOrAlarmInputModel OBJECT-TYPE
               SYNTAX  DisplayString (SIZE(0..32))
                ACCESS read-write
                STATUS mandatory
                DESCRIPTION
                   "The model name of this equipment."
                ::= { basicContactClosureOrAlarmInputEntry 12 }
 


-- Power Outlet Table

basicPowerOutletTable OBJECT-TYPE
        SYNTAX  SEQUENCE OF BasicPowerOutletEntry
        ACCESS  not-accessible
        STATUS  mandatory
        DESCRIPTION
                "Information about Environmental Manager Power Outlets."
        ::= { xBasic 26 }

basicPowerOutletEntry OBJECT-TYPE
        SYNTAX  BasicPowerOutletEntry
        ACCESS  not-accessible
        STATUS  mandatory
        DESCRIPTION
                "An entry in the basicPowerOutletTable."
        INDEX { basicPowerOutletIndex }
        ::= { basicPowerOutletTable 1 }

BasicPowerOutletEntry ::=
    SEQUENCE {
        basicPowerOutletOnOff
       	    INTEGER,
        basicPowerOutletReboot
            INTEGER,
        basicPowerOutletName
            DisplayString,
        basicPowerOutletRedundant
            INTEGER,
        basicPowerOutletConsoleName
            DisplayString,
        basicPowerOutletHighCurrent
            INTEGER,
        basicPowerOutletIndex
            INTEGER
	}


basicPowerOutletOnOff OBJECT-TYPE
        SYNTAX  INTEGER  { off(1), on(2) }
        ACCESS  read-write
        STATUS  mandatory
        DESCRIPTION
            "Controls turning on or off the power for the device connected to
             this power outlet."
        ::= { basicPowerOutletEntry 1 }

basicPowerOutletReboot OBJECT-TYPE
        SYNTAX  INTEGER  (1..1)
        ACCESS  read-write
        STATUS  mandatory
        DESCRIPTION
                "Controls rebooting of the device attached this power outlet."
        ::= { basicPowerOutletEntry 2 }

basicPowerOutletName OBJECT-TYPE 
        SYNTAX  DisplayString (SIZE (0..16 ))
        ACCESS  read-write
        STATUS  mandatory
        DESCRIPTION
            "A name used to identify this power outlet."
       ::= { basicPowerOutletEntry 3 }

basicPowerOutletRedundant OBJECT-TYPE
        SYNTAX INTEGER { disabled(1), enabled(2) }
        ACCESS  read-only
        STATUS  mandatory
        DESCRIPTION
            "Controls whether power outlets in bank A have redundant outlets
             in bank B. When enabled, powering on an outlet in bank A will
             simultaneously power on the corresponding outlet number in bank
             B."  
        DEFVAL { enabled }
        ::= { basicPowerOutletEntry 4 }

basicPowerOutletConsoleName OBJECT-TYPE
   SYNTAX DisplayString (SIZE (0..16))
   ACCESS read-write
   STATUS mandatory
   DESCRIPTION
      "A name used to identify a console port on a unit with power outlet 
       managment."
   ::= { basicPowerOutletEntry 5 }                

 basicPowerOutletHighCurrent OBJECT-TYPE
    SYNTAX INTEGER { disabled(1), enabled(2) }
    ACCESS read-write
    STATUS mandatory
    DESCRIPTION
       "A control to indicate a high current unit is attached to this 
        power outlet. When enabled the high current unit will provide current
        when it detects no power from the power outlet; and will stop the
        current when the outlet resumes power. This control only works on 
        those InReach devices which support the high current unit such as 
        the IRMGR0. Corresponds directly to the value labeled 'HCNC Setting'
        in the INREACH MANAGER OUTLET STATUS display."
    DEFVAL { disabled }
    ::= { basicPowerOutletEntry 6 }                

basicPowerOutletIndex OBJECT-TYPE
        SYNTAX  INTEGER
        ACCESS  read-only
        STATUS  mandatory
        DESCRIPTION
            "An index which uniquely identifies a power outlet."
        ::= { basicPowerOutletEntry 10 }

-- Temperature and Humidity Sensor Tables

basicTemperatureHumiditySensor OBJECT IDENTIFIER ::= { xBasic 27 }

-- Temperature Sensor Table

basicTemperatureSensorTable OBJECT-TYPE
        SYNTAX  SEQUENCE OF BasicTemperatureSensorEntry
        ACCESS  not-accessible
        STATUS  mandatory
        DESCRIPTION
            "Information about Environmental Manager Temperature Sensors."
        ::= { basicTemperatureHumiditySensor 1 }

basicTemperatureSensorEntry OBJECT-TYPE
        SYNTAX  BasicTemperatureSensorEntry
        ACCESS  not-accessible
        STATUS  mandatory
        DESCRIPTION
                "An entry in the basicTemperatureSensorTable."
        INDEX { basicTemperatureSensorIndex }
        ::= { basicTemperatureSensorTable 1 }

BasicTemperatureSensorEntry ::=
    SEQUENCE {
        basicTempTrapHighThreshold
            INTEGER,
        basicTempTrapLowThreshold
            INTEGER,
        basicTemperatureSensor
            INTEGER,
        basicTemperatureValue
            INTEGER,
        basicTemperatureAlarmSeverity
            INTEGER,
        basicTemperatureAlarmStatus
            INTEGER,
        basicTemperatureSensorIndex
	    INTEGER
	}

basicTempTrapHighThreshold OBJECT-TYPE
        SYNTAX  INTEGER
        ACCESS  read-write
        STATUS  mandatory
        DESCRIPTION
            "The temperature at or above which a sensorThresholdTrap is 
             generated."
        ::= { basicTemperatureSensorEntry 1 }

basicTempTrapLowThreshold OBJECT-TYPE
        SYNTAX  INTEGER
        ACCESS  read-write
        STATUS  mandatory
        DESCRIPTION
            "The temperature at or below which a sensorThresholdTrap is 
             generated."
        ::= { basicTemperatureSensorEntry 2 }

basicTemperatureSensor OBJECT-TYPE
        SYNTAX  INTEGER { disabled(1), enabled(2) }
        ACCESS  read-write
        STATUS  mandatory
        DESCRIPTION
                "Controls the enabling or disabling of a temperature sensor."
        ::= { basicTemperatureSensorEntry 3 }

basicTemperatureValue OBJECT-TYPE
        SYNTAX  INTEGER
        ACCESS  read-write
        STATUS  mandatory
        DESCRIPTION
				"The current temperature reading for this sensor."
        ::= { basicTemperatureSensorEntry 4 }

 basicTemperatureAlarmSeverity OBJECT-TYPE
       SYNTAX  INTEGER { cleared (1), indeterminate (2), warning (3), 
                         minor (4), major (5), critical (6) }
       ACCESS  read-write
       STATUS  mandatory
       DESCRIPTION
           "Control to determine the severity level associated with the
            trap sent out when the temperature reading is out-of-bounds."
       DEFVAL { minor  }
       ::= { basicTemperatureSensorEntry 5 }

 basicTemperatureAlarmStatus OBJECT-TYPE
       SYNTAX  INTEGER { cleared (1), indeterminate (2), warning (3), 
                         minor (4), major (5), critical (6) }
       ACCESS  read-only
       STATUS  mandatory
       DESCRIPTION
           "Indicates the current status of the temperature sensor.
            If the basicTemperatureValue falls within the normal range,
            the status is cleared. Otherwise the status matches the alarm
            severity level."
       ::= { basicTemperatureSensorEntry 6 }

basicTemperatureSensorIndex OBJECT-TYPE
        SYNTAX  INTEGER
        ACCESS  read-only
        STATUS  mandatory
        DESCRIPTION
                "An index which uniquely identifies a temperature sensor."
        ::= { basicTemperatureSensorEntry 10 }


basicHumiditySensorTable OBJECT-TYPE
        SYNTAX  SEQUENCE OF BasicHumiditySensorEntry
        ACCESS  not-accessible
        STATUS  mandatory
        DESCRIPTION
            "Information about Environmental Manager Humidity Sensors."
        ::= { basicTemperatureHumiditySensor 2 }

basicHumiditySensorEntry OBJECT-TYPE
        SYNTAX  BasicHumiditySensorEntry
        ACCESS  not-accessible
        STATUS  mandatory
        DESCRIPTION
            "An entry in the basicHumiditySensorTable."
        INDEX { basicHumiditySensorIndex }
        ::= { basicHumiditySensorTable 1 }

BasicHumiditySensorEntry ::=
    SEQUENCE {
        basicHumidityTrapHighThreshold
            INTEGER,
        basicHumidityTrapLowThreshold
            INTEGER,
        basicHumiditySensor
            INTEGER,
        basicHumidityValue
	    INTEGER,
        basicHumidityAlarmSeverity
            INTEGER,
        basicHumidityAlarmStatus
            INTEGER,
        basicHumiditySensorIndex
            INTEGER
	}


basicHumidityTrapHighThreshold OBJECT-TYPE
        SYNTAX  INTEGER
        ACCESS  read-write
        STATUS  mandatory
        DESCRIPTION
            "The humidity at or above which a sensorThresholdTrap is generated."
        ::= { basicHumiditySensorEntry 1 }

basicHumidityTrapLowThreshold OBJECT-TYPE
        SYNTAX  INTEGER
        ACCESS  read-write
        STATUS  mandatory
        DESCRIPTION
            "The humidity at or below which a sensorThresholdTrap is generated."
        ::= { basicHumiditySensorEntry 2 }

basicHumiditySensor OBJECT-TYPE
        SYNTAX  INTEGER { disabled(1), enabled(2) }
        ACCESS  read-write
        STATUS  mandatory
        DESCRIPTION
            "Controls the enabling or disabling of a humidity sensor."
        ::= { basicHumiditySensorEntry 3 }

basicHumidityValue OBJECT-TYPE
        SYNTAX  INTEGER
        ACCESS  read-write
        STATUS  mandatory
        DESCRIPTION
            "The current humidity reading for this sensor."
        ::= { basicHumiditySensorEntry 4 }

 basicHumidityAlarmSeverity OBJECT-TYPE
       SYNTAX  INTEGER { cleared (1), indeterminate (2), warning (3), 
                         minor (4), major (5), critical (6) }
       ACCESS  read-write
       STATUS  mandatory
       DESCRIPTION
           "Control to indicate the severity level associated with the
            trap sent out when the humidity reading is out-of-bounds."
       DEFVAL { minor  }
       ::= { basicHumiditySensorEntry 5 }

 basicHumidityAlarmStatus OBJECT-TYPE
       SYNTAX  INTEGER { cleared (1), indeterminate (2), warning (3), 
                         minor (4), major (5), critical (6) }
       ACCESS  read-only
       STATUS  mandatory
       DESCRIPTION
           "Indicates the current status of the humidity sensor.
            If the basicHumidityValue falls within the normal range,
            the status is cleared. Otherwise the status matches the alarm
            severity level."
       ::= { basicHumiditySensorEntry 6 }

basicHumiditySensorIndex OBJECT-TYPE
        SYNTAX  INTEGER
        ACCESS  read-only
        STATUS  mandatory
        DESCRIPTION
                "An index which uniquely identifies a humidity sensor."
        ::= { basicHumiditySensorEntry 10 }

basicControlSignalTable OBJECT-TYPE
	SYNTAX  SEQUENCE OF BasicControlSignalEntry
        ACCESS  not-accessible
        STATUS  mandatory
        DESCRIPTION
                "Information about Environmental Manager Control Signal points."
        ::= { xBasic 28 }

basicControlSignalEntry OBJECT-TYPE
	SYNTAX  BasicControlSignalEntry
        ACCESS  not-accessible
        STATUS  mandatory
        DESCRIPTION
                "An entry in the basicControlSignalTable."
        INDEX { basicControlSignalIndex }
        ::= { basicControlSignalTable 1 }

BasicControlSignalEntry ::=
    SEQUENCE {
        basicControlSignalValue
		    INTEGER,
		basicControlSignalIndex
  		    INTEGER
	}

basicControlSignalValue  OBJECT-TYPE
        SYNTAX  INTEGER { high (1), low(2) } 
        ACCESS  read-write
        STATUS  mandatory
        DESCRIPTION
                "Sets and reads the state of the control signal point."
	    DEFVAL { high }
        ::= { basicControlSignalEntry 1 }

basicControlSignalIndex OBJECT-TYPE
        SYNTAX  INTEGER
        ACCESS  read-only
        STATUS  mandatory
        DESCRIPTION
                "An index which uniquely identifies a control signal point."
        ::= { basicControlSignalEntry 10 }

basicPowerAlarmTimer OBJECT-TYPE
        SYNTAX  INTEGER (1..60)
        ACCESS  read-write
        STATUS  mandatory
        DESCRIPTION
                "The polling interval in seconds for the fuse and power supply
                 status. An alarm trap is issued on power failure."
        DEFVAL { 10 }
        ::= { xBasic 29 }

 -- Control Output Table
 
 basicControlOutputTable OBJECT-TYPE
        SYNTAX  SEQUENCE OF BasicControlOutputEntry
        ACCESS  not-accessible
        STATUS  mandatory
        DESCRIPTION
                "Information about controlled output distribution points."
        ::= { xBasic 30 }
 
 basicControlOutputEntry OBJECT-TYPE
        SYNTAX  BasicControlOutputEntry
        ACCESS  not-accessible
        STATUS  mandatory
        DESCRIPTION
                "An entry in the basicControlOutputTable."
        INDEX { basicControlOutputIndex }
        ::= { basicControlOutputTable 1 }
 
 BasicControlOutputEntry ::=
        SEQUENCE {
            basicControlOutputSignalDtrRts
                INTEGER,
            basicControlOutputName
                DisplayString,
            basicControlOutputIndex
                INTEGER
        }
 
basicControlOutputSignalDtrRts OBJECT-TYPE
        SYNTAX  INTEGER { low(1), high(2) }
        ACCESS  read-write
        STATUS  mandatory
        DESCRIPTION
            "Controls the raising or lowering of a signal on a distribution
             control signal point. The signal is DTR when the
             basicControlOutputIndex is odd, or RTS when the
             basicControlOutputIndex is even."
        DEFVAL { high }
        ::= { basicControlOutputEntry 1 }
 
basicControlOutputName OBJECT-TYPE
        SYNTAX  DisplayString (SIZE (0..32 ))
        ACCESS  read-write
        STATUS  mandatory
        DESCRIPTION
           "The name used to identify this distribution control signal point."
       ::= { basicControlOutputEntry 2 }
 
basicControlOutputIndex OBJECT-TYPE
        SYNTAX  INTEGER
        ACCESS  read-only
        STATUS  mandatory
        DESCRIPTION
            "An index which uniquely identifies a distribution control
             signal point."
        ::= { basicControlOutputEntry 10 }

basicPowerStatusFuseA OBJECT-TYPE 
        SYNTAX  INTEGER { off (1), on (2) }
        ACCESS  read-only
        STATUS  mandatory
        DESCRIPTION
            "Indicates the status of fuse bank A."
        ::= { xBasic 31 }

basicPowerStatusFuseB OBJECT-TYPE 
        SYNTAX  INTEGER { off (1), on (2) }
        ACCESS  read-only
        STATUS  mandatory
        DESCRIPTION
            "Indicates the status of fuse bank B."
        ::= { xBasic 32 }

basicPowerSupplyStatusA OBJECT-TYPE 
        SYNTAX  INTEGER { off (1), on (2) }
        ACCESS  read-only
        STATUS  mandatory
        DESCRIPTION
            "Indicates the status of power supply A."
        ::= { xBasic 33 }

basicPowerSupplyStatusB OBJECT-TYPE 
        SYNTAX  INTEGER { off (1), on (2) }
        ACCESS  read-only
        STATUS  mandatory
        DESCRIPTION
            "Indicates the status of power supply B."
        ::= { xBasic 34 }

basicPortTrapTable OBJECT-TYPE
	SYNTAX SEQUENCE OF BasicPortTrapEntry
	ACCESS not-accessible
     	STATUS mandatory
	DESCRIPTION
	   "A list of traps associated with signal control changes on ports."
	::= { xBasic 35 }

basicPortTrapEntry OBJECT-TYPE
	SYNTAX BasicPortTrapEntry
	ACCESS not-accessible
     	STATUS mandatory
	DESCRIPTION
	    "Administrative status of signal change traps for a hardware port."
	INDEX { basicPortTrapIndex, basicPortSignalName }
	::= { basicPortTrapTable 1 }

BasicPortTrapEntry ::=
 	SEQUENCE {
	    basicPortTrapIndex
		INTEGER,
	    basicPortSignalName
		INTEGER,
	    basicPortTrapStatus
		INTEGER
	}

basicPortTrapIndex OBJECT-TYPE
	SYNTAX INTEGER
	ACCESS read-only
     	STATUS mandatory
	DESCRIPTION
	     "An index value that uniquely identifies a port.  
	     The port identified by a particular value of this 
	     index is the same port as identified by rs232PortIndex
	     in the standard rs232 MIB."
	::= { basicPortTrapEntry 1 }

basicPortSignalName OBJECT-TYPE
	SYNTAX INTEGER { rts(1), cts(2), dsr(3), dtr(4), ri(5), dcd(6) }
	ACCESS read-only
     	STATUS mandatory
	DESCRIPTION
	    "Identification of the hardware signal as specified in RFC1659
             as follows:
		rts 	Request to Send
		cts	Clear to Send
		dsr	Data Set Ready
		dts	Data Terminal Ready	
		ri	Ring Indicator
		dcd	Received Line Signal Detector  
	    Some agents do not support DSR since its pin is shared with DCD."
	::= { basicPortTrapEntry 2 }

basicPortTrapStatus OBJECT-TYPE	
        SYNTAX  INTEGER { disabled(1), enabled(2) }	
	ACCESS read-write
     	STATUS mandatory
	DESCRIPTION
	    "Control to toggle the sending of a trap on a specific signal 
             change on a physical port. One must logout the port prior to this
             taking effect."
	::= { basicPortTrapEntry 3 }


-- Alarm Master Input Table

basicAlarmMasterInputTable OBJECT-TYPE
        SYNTAX  SEQUENCE OF BasicAlarmMasterInputEntry
        ACCESS  not-accessible
        STATUS  mandatory
        DESCRIPTION
            "Information about the high density alarm manager's alarm inputs."
        ::= { xBasic 36 }

basicAlarmMasterInputEntry OBJECT-TYPE
        SYNTAX  BasicAlarmMasterInputEntry
        ACCESS  not-accessible
        STATUS  mandatory
        DESCRIPTION
            "An entry in the basicAlarmMasterInputTable."
        INDEX { basicAlarmMasterInputPort, basicAlarmMasterInputSlot, 
                basicAlarmMasterInputPoint }
        ::= { basicAlarmMasterInputTable 1 }

BasicAlarmMasterInputEntry ::=
    SEQUENCE {
        basicAlarmMasterInputPort
       	    INTEGER,
        basicAlarmMasterInputSlot
            INTEGER,
        basicAlarmMasterInputPoint
            INTEGER,
        basicAlarmMasterInputName      
            DisplayString,
        basicAlarmMasterInputTrapEnable
            INTEGER,
        basicAlarmMasterControlOutputSignal 
            INTEGER,
        basicAlarmMasterInputEnable 
            INTEGER,
        basicAlarmMasterInputDebounceInterval 
            INTEGER,
        basicAlarmMasterInputFaultSeverity 
            INTEGER,
        basicAlarmMasterInputFaultState
            INTEGER,
        basicAlarmMasterInputStatus
            INTEGER,
        basicAlarmMasterInputValue
            INTEGER,
        basicAlarmMasterDisplay
            INTEGER
             }

	basicAlarmMasterInputPort OBJECT-TYPE
                SYNTAX INTEGER
                ACCESS read-only
                STATUS mandatory
                DESCRIPTION
                    "An index value that uniquely identifies a port.
                    The port identified by a particular value of this 
                    index is the same port as identified by 
                    charPortIndex in the standard Character MIB."
                ::= { basicAlarmMasterInputEntry 1 }

	basicAlarmMasterInputSlot OBJECT-TYPE
                SYNTAX INTEGER
                ACCESS read-only
                STATUS mandatory
                DESCRIPTION
                    "An index value that uniquely identifies a slot of
                    alarm points on a given high density alarm port."
                ::= { basicAlarmMasterInputEntry 2 }

	basicAlarmMasterInputPoint OBJECT-TYPE
                SYNTAX INTEGER
                ACCESS read-only
                STATUS mandatory
                DESCRIPTION
                    "An index value that uniquely identifies an alarm
                     point within an alarm slot on a high density
                     alarm port."
                ::= { basicAlarmMasterInputEntry 3 }

 basicAlarmMasterInputName OBJECT-TYPE
        SYNTAX  DisplayString (SIZE (0..32 ))
        ACCESS  read-write
        STATUS  mandatory
        DESCRIPTION
            "The name used to identify this alarm point."
        ::= { basicAlarmMasterInputEntry 4 }

 basicAlarmMasterInputTrapEnable OBJECT-TYPE
       SYNTAX  INTEGER { disabled (1), enabled (2) }
       ACCESS  read-write
       STATUS  mandatory
       DESCRIPTION
           "Control to send a trap when the alarm input changes state."
      DEFVAL { disabled  }
        ::= { basicAlarmMasterInputEntry 5 }

 basicAlarmMasterControlOutputSignal OBJECT-TYPE
       SYNTAX  INTEGER { open (1), closed (2) }
       ACCESS  read-write
       STATUS  mandatory
       DESCRIPTION
           "Control to toggle the output signal for an alarm point." 
       DEFVAL { open }
        ::= { basicAlarmMasterInputEntry 6 }

 basicAlarmMasterInputEnable OBJECT-TYPE
       SYNTAX  INTEGER { disabled (1), enabled (2) }
       ACCESS  read-write
       STATUS  mandatory
       DESCRIPTION
           "Control to toggle whether this alarm point is active."
       DEFVAL { enabled  }
        ::= { basicAlarmMasterInputEntry 7 }

 basicAlarmMasterInputDebounceInterval OBJECT-TYPE
      SYNTAX  INTEGER ( 0..30 )
       ACCESS  read-write
       STATUS  mandatory
       DESCRIPTION
          "Amount of time in seconds to debounce a signal change before 
           triggering an alarm."
       DEFVAL { 0  }
        ::= { basicAlarmMasterInputEntry 8 }

 basicAlarmMasterInputFaultSeverity OBJECT-TYPE
       SYNTAX  INTEGER { cleared (1), indeterminate (2), warning (3), 
                         minor (4), major (5), critical (6) }
       ACCESS  read-write
       STATUS  mandatory
       DESCRIPTION
           "Control to determine the severity level associated with the
            trap sent out when a fault occurs for this alarm input point."
       DEFVAL { minor  }
  ::= { basicAlarmMasterInputEntry 9 }

 basicAlarmMasterInputFaultState OBJECT-TYPE
       SYNTAX  INTEGER { open (1), closed (2) }
       ACCESS  read-write
       STATUS  mandatory
       DESCRIPTION
           "Control to indicate which state, open or closed, represents the 
            fault condition for this alarm input point. The other state is 
            the cleared condition."
      DEFVAL { closed  }
  ::= { basicAlarmMasterInputEntry 10 }

 basicAlarmMasterInputStatus OBJECT-TYPE
       SYNTAX  INTEGER { cleared (1), indeterminate (2), warning (3), 
                         minor (4), major (5), critical (6) }
       ACCESS  read-only
       STATUS  mandatory
       DESCRIPTION
           "Indicates the current status of the alarm input point.
            If the basicAlarmMasterInputValue matches the fault 
            state, then the status is equal to the fault severity. Otherwise
            the status is cleared."
       ::= { basicAlarmMasterInputEntry 11 }

 basicAlarmMasterInputValue OBJECT-TYPE   
       SYNTAX  INTEGER { open (1), closed (2) }
       ACCESS  read-only
       STATUS  mandatory
       DESCRIPTION
           "Indicates the current state of the alarm input point."
       ::= { basicAlarmMasterInputEntry 12 }

 basicAlarmMasterDisplay OBJECT-TYPE
       SYNTAX  INTEGER { disabled (1), enabled (2) }
       ACCESS  read-write
       STATUS  mandatory
       DESCRIPTION
           "Control to toggle the display of the alarm status for this point
            in the display window of the high density alarm unit."
       DEFVAL { disabled  }
        ::= { basicAlarmMasterInputEntry 13 }

 -- Power Master Table
 
 basicPowerMasterOutletTable OBJECT-TYPE
        SYNTAX  SEQUENCE OF BasicPowerMasterOutletEntry
        ACCESS  not-accessible
        STATUS  mandatory
        DESCRIPTION
                "Information about power master outlets."
        ::= { xBasic 37 }

 basicPowerMasterOutletEntry OBJECT-TYPE
        SYNTAX  BasicPowerMasterOutletEntry
        ACCESS  not-accessible
        STATUS  mandatory
        DESCRIPTION
                "An entry in the basicPowerMasterOutletTable."
        INDEX { basicPowerMasterPortIndex, basicPowerMasterOutletIndex }
        ::= { basicPowerMasterOutletTable 1 }

 BasicPowerMasterOutletEntry ::=
        SEQUENCE {
            basicPowerMasterPortIndex
                INTEGER,
            basicPowerMasterOutletIndex
                INTEGER,
            basicPowerMasterOutletName
                DisplayString,
            basicPowerMasterOutletState
                INTEGER,
            basicPowerMasterOutletAmperageStatus
                DisplayString
        }

basicPowerMasterPortIndex OBJECT-TYPE
        SYNTAX  INTEGER
        ACCESS  read-only
        STATUS  mandatory
        DESCRIPTION
            "An index value that uniquely identifies a port.
             The port identified by a particular value of this 
             index is the same port as identified by the 
             charPortIndex in the standard Character MIB."
        ::= { basicPowerMasterOutletEntry 1 }

basicPowerMasterOutletIndex OBJECT-TYPE
        SYNTAX  INTEGER
        ACCESS  read-only
        STATUS  mandatory
        DESCRIPTION
            "An index which uniquely identifies a power master outlet."
        ::= { basicPowerMasterOutletEntry 2 }

basicPowerMasterOutletName OBJECT-TYPE
        SYNTAX  DisplayString (SIZE (0..32 ))
        ACCESS  read-write
        STATUS  mandatory
        DESCRIPTION
           "The name used to identify this power master outlet."
       ::= { basicPowerMasterOutletEntry 3 }

basicPowerMasterOutletState OBJECT-TYPE
        SYNTAX  INTEGER { off(1), on(2) }
        ACCESS  read-write
        STATUS  mandatory
        DESCRIPTION
            "Switches the power master outlet on or off. There may be a 
             noticeable time delay while processing a get-request for this object."
        DEFVAL { on }
        ::= { basicPowerMasterOutletEntry 4 }

basicPowerMasterOutletAmperageStatus OBJECT-TYPE
        SYNTAX  DisplayString (SIZE (0..5))
        ACCESS  read-only
        STATUS  mandatory
        DESCRIPTION
            "Indicates the current amperage drawn at this outlet. There may
             be a noticeable time delay while processing a get-request for this object."
        ::= { basicPowerMasterOutletEntry 5 }

 -- Control Output Relay Table
 
 basicControlOutputRelayTable OBJECT-TYPE
        SYNTAX  SEQUENCE OF BasicControlOutputRelayEntry
        ACCESS  not-accessible
        STATUS  mandatory
        DESCRIPTION
                "Information about controlled output relays."
        ::= { xBasic 38 }
 
 basicControlOutputRelayEntry OBJECT-TYPE
        SYNTAX  BasicControlOutputRelayEntry
        ACCESS  not-accessible
        STATUS  mandatory
        DESCRIPTION
                "An entry in the basicControlOutputRelayTable."
        INDEX { basicControlOutputRelayIndex }
        ::= { basicControlOutputRelayTable 1 }
 
 BasicControlOutputRelayEntry ::=
        SEQUENCE {
            basicControlOutputRelayIndex
                INTEGER,
            basicControlOutputRelayName
                DisplayString,
            basicControlOutputRelayState
                INTEGER,
            basicControlOutputRelayStatus
                INTEGER
        }

basicControlOutputRelayIndex OBJECT-TYPE
        SYNTAX  INTEGER
        ACCESS  read-only
        STATUS  mandatory
        DESCRIPTION
            "An index which uniquely identifies a control output relay."
        ::= { basicControlOutputRelayEntry 1 }

basicControlOutputRelayName OBJECT-TYPE
        SYNTAX  DisplayString (SIZE (0..32 ))
        ACCESS  read-write
        STATUS  mandatory
        DESCRIPTION
           "The name used to identify this control output relay."
       ::= { basicControlOutputRelayEntry 2 }

basicControlOutputRelayState OBJECT-TYPE
        SYNTAX  INTEGER { open(1), close(2) }
        ACCESS  read-write
        STATUS  mandatory
        DESCRIPTION
            "Controls the opening or closing of the control output relay."
        DEFVAL { open }
        ::= { basicControlOutputRelayEntry 3 }

basicControlOutputRelayStatus OBJECT-TYPE
        SYNTAX  INTEGER { open(1), close(2) }
        ACCESS  read-only
        STATUS  mandatory
        DESCRIPTION
            "Indicates the current status of the control output relay."
        ::= { basicControlOutputRelayEntry 4 }
 

           basicAutoProtocolDetectMessage OBJECT-TYPE
               SYNTAX DisplayString (SIZE (0..80))
               ACCESS read-write
               STATUS mandatory
               DESCRIPTION
                   "The text string sent as a prompt message out the
                    port at the beginning of auto protocol detection mode.
                    Corresponds to the value labeled 'APD Message' in the
                    SERVER UNIT display."
               DEFVAL {"AutoProtocolDetect - Begin protocol or enter 4 returns for interactive mode." }
               ::= { xBasic 100 } 

             
            -- the Queue group
            
            -- Implementation of this group is mandatory for all iTouch
            -- systems that implement port queueing
            
            queueLimit OBJECT-TYPE
                SYNTAX INTEGER (-1..100)
                ACCESS read-write
                STATUS mandatory
                DESCRIPTION
                    "The maximum number of entries that can be made in 
                    the Queue table.  The value -1 indicates the imit is 
                    available memory.  Corresponds directly to SERVER 
                    QUEUE LIMIT and the value labeled 'Queue Limit:' in 
                    the SERVER CHARACTERISTICS display."
                ::= { xQueue 1 }
            
            queueHigh OBJECT-TYPE
                SYNTAX Gauge
                ACCESS read-only
                STATUS mandatory
                DESCRIPTION
                    "The highest value of queueNumber since system 
                    initialization.  Corresponds directly to the value 
                    labeled 'Queue Entries' and 'High' in the SERVER 
                    STATUS display."
                ::= { xQueue 2 }
            
            queueNumber OBJECT-TYPE
                SYNTAX Gauge
                ACCESS read-only
                STATUS mandatory
                DESCRIPTION
                    "The number of entries in the Queue table.  
                    Corresponds directly to the value labeled 'Queue 
                    Entries' and 'Cur' in the SERVER STATUS display."
                ::= { xQueue 3 }
            
            -- The Queue table
            
            queueTable OBJECT-TYPE
                SYNTAX SEQUENCE OF QueueEntry
                ACCESS not-accessible
                STATUS mandatory
                DESCRIPTION
                    "A list of queue entries."
                ::= { xQueue 4 }
            
            queueEntry OBJECT-TYPE
                SYNTAX QueueEntry
                ACCESS not-accessible
                STATUS mandatory
                DESCRIPTION
                    "Parameter values for a queue entry."
                INDEX { queueJob }
                ::= { queueTable 1 }
            
            QueueEntry ::=
                SEQUENCE {
                    queueJob
                        INTEGER,
                    queueStatus
                        INTEGER,
                    queueSourceName
                        DisplayString,
                    queueServiceName
                        DisplayString,
                    queueServicePortIndex
                        INTEGER,
                    queueServicePortName
                        DisplayString
                }
            
            queueJob OBJECT-TYPE
                SYNTAX INTEGER
                ACCESS read-only
                STATUS mandatory
                DESCRIPTION
                    "The job number of a queued request.  Corresponds 
                    directly to the value labeled 'Entry' in the QUEUE 
                    display."
                ::= { queueEntry 1 }
            
            queueStatus OBJECT-TYPE
                SYNTAX INTEGER { invalid(1), valid(2) }
                ACCESS read-write
                STATUS mandatory
                DESCRIPTION
                    "The status of a queue entry.  Set to 'invalid' to 
                    remove the entry, which corresponds directly to the 
                    REMOVE QUEUE ENTRY command.  Actual removal of the 
                    entry is implementation specific."
                ::= { queueEntry 2 }
            
            queueSourceName OBJECT-TYPE
                SYNTAX DisplayString (SIZE (0..50))
                ACCESS read-only
                STATUS mandatory
                DESCRIPTION
                    "The name of the system that originated the queue 
                    entry.  Corresponds directly to the value labeled 
                    'Source Node' in the QUEUE display."
                ::= { queueEntry 3 }
            
            queueServiceName OBJECT-TYPE
                SYNTAX DisplayString (SIZE (0..16))
                ACCESS read-only
                STATUS mandatory
                DESCRIPTION
                    "The name of the service for which the originator is 
                    waiting.  Corresponds directly to the value labeled 
                    'Service' in the QUEUE display."
                ::= { queueEntry 4 }
            
            queueServicePortIndex OBJECT-TYPE
                SYNTAX INTEGER
                ACCESS read-only
                STATUS mandatory
                DESCRIPTION
                    "The charPortIndex of the port for which the 
                    originator is waiting, if supplied by the 
                    originator.  As defined in the standard Character 
                    MIB.  Corresponds indirectly to the port number part 
                    of the value labeled 'Port Name' in the QUEUE 
                    display."
                ::= { queueEntry 5 }
            
            queueServicePortName OBJECT-TYPE
                SYNTAX DisplayString (SIZE (0..16))
                ACCESS read-only
                STATUS mandatory
                DESCRIPTION
                    "The name of the port for which the originator is 
                    waiting, if supplied by the originator.  Corresponds 
                    directly to the port name part of the value labeled 
                    'Port Name' in the SERVER QUEUE display."
                ::= { queueEntry 6 }
            
            
            -- the Queue Port table
            
            queuePortTable OBJECT-TYPE
                SYNTAX SEQUENCE OF QueuePortEntry
                ACCESS not-accessible
                STATUS mandatory
                DESCRIPTION
                    "A list of queuing-related character port entries."
                ::= { xQueue 5 }
            
            queuePortEntry OBJECT-TYPE
                SYNTAX QueuePortEntry
                ACCESS not-accessible
                STATUS mandatory
                DESCRIPTION
                    "Queuing parameter values for a port."
                INDEX { queuePortIndex }
                ::= { queuePortTable 1 }
            
            QueuePortEntry ::=
                SEQUENCE {
                    queuePortIndex
                        INTEGER,
                    queuePortQueuing
                        INTEGER
                }
            
            queuePortIndex OBJECT-TYPE
                SYNTAX INTEGER
                ACCESS read-only
                STATUS mandatory
                DESCRIPTION
                    "An index value that uniquely identifies a port.  
                    The port identified by a particular value of this 
                    index is the same port as identified by 
                    charPortIndex in the standard Character MIB."
                ::= { queuePortEntry 1 }
            
            queuePortQueuing OBJECT-TYPE
                SYNTAX INTEGER { disabled(1), enabled(2) }
                ACCESS read-write
                STATUS mandatory
                DESCRIPTION
                    "Control for allowing queued requests for using the 
                    port.  Corresponds directly to PORT QUEUING and the 
                    presence of the label 'Queuing' following the label 
                    'Enabled Characteristics:' in the PORT 
                    CHARACTERISTICS display."
                ::= { queuePortEntry 2 }

            
            -- the Menu group
            
            -- Implementation of this group is mandatory for all iTouch
            -- systems that implement user menus
            
            menuNumber OBJECT-TYPE
                SYNTAX Gauge
                ACCESS read-only
                STATUS mandatory
                DESCRIPTION
                    "The number of entries in the Menu table.  
                    Corresponds indirectly to SERVER MENU display."
                ::= { xMenu 1 }
            
            menuContinuePrompt OBJECT-TYPE
                SYNTAX DisplayString (SIZE (0..50))
                ACCESS read-write
                STATUS mandatory
                DESCRIPTION
                    "The text to use when prompting a menu user to press 
                    RETURN to continue. Corresponds directly to SERVER 
                    MENU CONTINUE PROMPT and the value labeled 'Menu 
                    Continue Prompt:' in the SERVER MENU display."
                ::= { xMenu 2 }
            
            menuSelectionPrompt OBJECT-TYPE
                SYNTAX DisplayString (SIZE (0..50))
                ACCESS read-write
                STATUS mandatory
                DESCRIPTION
                    "The text to use when prompting a menu user for a 
                    menu selection. Corresponds directly to SERVER MENU 
                    PROMPT and the value labeled 'Menu Prompt:' in the 
                    SERVER MENU display."
                ::= { xMenu 3 }

            
            -- The Menu table
            
            menuTable OBJECT-TYPE
                SYNTAX SEQUENCE OF MenuEntry
                ACCESS not-accessible
                STATUS mandatory
                DESCRIPTION
                    "A list of menu entries."
                ::= { xMenu 4 }
            
            menuEntry OBJECT-TYPE
                SYNTAX MenuEntry
                ACCESS not-accessible
                STATUS mandatory
                DESCRIPTION
                    "Parameter values for a menu entry."
                INDEX { menuIndex }
                ::= { menuTable 1 }
            
            MenuEntry ::=
                SEQUENCE {
                    menuIndex
                        INTEGER,
                    menuStatus
                        INTEGER,
                    menuText
                        DisplayString,
                    menuCommand
                        DisplayString
                }
            
            menuIndex OBJECT-TYPE
                SYNTAX INTEGER
                ACCESS read-only
                STATUS mandatory
                DESCRIPTION
                    "The index number of a menu entry.  Corresponds 
                    directly to the numbers down the left of the SERVER 
                    MENU display."
                ::= { menuEntry 1 }
            
            menuStatus OBJECT-TYPE
                SYNTAX INTEGER { invalid(1), valid(2) }
                ACCESS read-write
                STATUS mandatory
                DESCRIPTION
                    "The status of a the entry.  Set to 'invalid' to
                    remove the entry, which corresponds directly to the 
                    CLEAR SERVER MENU command.  Actual removal of the 
                    entry is implementation specific."
                DEFVAL { valid }
                ::= { menuEntry 2 }
            
            menuText OBJECT-TYPE
                SYNTAX DisplayString (SIZE (0..30))
                ACCESS read-write
                STATUS mandatory
                DESCRIPTION
                    "The text to be displayed in the menu.  Corresponds 
                    directly to the line next to the entry number in the 
                    SERVER MENU display."
                ::= { menuEntry 3 }
            
            menuCommand OBJECT-TYPE
                SYNTAX DisplayString (SIZE (0..64))
                ACCESS read-write
                STATUS mandatory
                DESCRIPTION
                    "The commands to execute when the user chooses the 
                    menu entry.  Corresponds directly second line 
                    following the entry number in the SERVER MENU 
                    display."
                ::= { menuEntry 4 }

            
            -- the Menu Port table
            
            menuPortTable OBJECT-TYPE
                SYNTAX SEQUENCE OF MenuPortEntry
                ACCESS not-accessible
                STATUS mandatory
                DESCRIPTION
                    "A list of menu-related character port entries."
                ::= { xMenu 5 }
            
            menuPortEntry OBJECT-TYPE
                SYNTAX MenuPortEntry
                ACCESS not-accessible
                STATUS mandatory
                DESCRIPTION
                    "Menu parameter values for a port."
                INDEX { menuPortIndex }
                ::= { menuPortTable 1 }
            
            MenuPortEntry ::=
                SEQUENCE {
                    menuPortIndex
                        INTEGER,
                    menuPortMenuStatus
                        INTEGER,
                    menuPortNestedMenuStatus
                        INTEGER,
                    menuPortNestedMenuPrivilege
                        INTEGER,
                    menuPortNestedTopLevel
                        INTEGER
                }
            
            menuPortIndex OBJECT-TYPE
                SYNTAX INTEGER
                ACCESS read-only
                STATUS mandatory
                DESCRIPTION
                    "An index value that uniquely identifies a port.  
                    The port identified by a particular value of this 
                    index is the same port as identified by 
                    charPortIndex in the standard Character MIB."
                ::= { menuPortEntry 1 }
            
            menuPortMenuStatus OBJECT-TYPE
                SYNTAX INTEGER { disabled(1), enabled(2), privileged(3) }
                ACCESS read-write
                STATUS mandatory
                DESCRIPTION
                    "Control for menu operation on the port.  
                    Corresponds indirectly to PORT MENU and PORT 
                    PRIVILEGED MENU and the presence of the labels 
                    'Menu' and 'Privileged Menu' following the label 
                    'Enabled Characteristics:' in the PORT 
                    CHARACTERISTICS display."
                ::= { menuPortEntry 2 }
            
            menuPortNestedMenuStatus OBJECT-TYPE
                SYNTAX INTEGER { disabled(1), enabled(2), required(3) }
                ACCESS read-write
                STATUS mandatory
                DESCRIPTION
                    "Control for nested menu operation on the port.  
                    Corresponds indirectly to PORT NESTED MENU and the 
                    presence of the label 'Nested Menu' following the 
                    label 'Enabled Characteristics:' in the PORT 
                    CHARACTERISTICS display."
                ::= { menuPortEntry 3 }
            
            menuPortNestedMenuPrivilege OBJECT-TYPE
                SYNTAX INTEGER { disabled(1), enabled(2) }
                ACCESS read-write
                STATUS mandatory
                DESCRIPTION
                    "Control for nested privileged menu operation on the 
                    port.  Corresponds indirectly to PORT NESTED 
                    PRIVILEGED MENU and the presence of the label 
                    'Nested Privileged Menu' following the label 
                    'Enabled Characteristics:' in the PORT 
                    CHARACTERISTICS display."
                ::= { menuPortEntry 4 }
            
            menuPortNestedTopLevel OBJECT-TYPE
                SYNTAX INTEGER (0..255)
                ACCESS read-write
                STATUS mandatory
                DESCRIPTION
                    "The top level nested menu to select from the menu 
                    definition file."
                ::= { menuPortEntry 5 }
            
            -- additional scalar objects
            
            menuNestedName OBJECT-TYPE
                SYNTAX DisplayString (SIZE (0..16))
                ACCESS read-write
                STATUS mandatory
                DESCRIPTION
                    "Name of the script file containing the nested 
                    menu."
                DEFVAL { "NESTMENU.TXT" }
                ::= { xMenu 6 }
            
            menuNestedScriptMaximum OBJECT-TYPE
                SYNTAX INTEGER (0..204800)
                ACCESS read-write
                STATUS mandatory
                DESCRIPTION
                    "Maximum number of temporary storage bytes for a 
                    nested menu script file.  If not zero, the nested 
                    menu function is enabled."
                DEFVAL { 16384 }
                ::= { xMenu 7 }

            menuNestedSystemName OBJECT-TYPE
                SYNTAX INTEGER { disabled(1), enabled(2) }
                ACCESS read-write
                STATUS mandatory
                DESCRIPTION
                    "Control to request to download a menu script which is 
                     unique for this unit by prepending the sysLocalName of 
                     this unit to the nestedMenuName."
                DEFVAL { disabled  }
                ::= { xMenu 8 }
        
            menuNestedEthernet OBJECT-TYPE
                SYNTAX INTEGER { disabled(1), enabled(2) }
                ACCESS read-write
                STATUS mandatory
                DESCRIPTION
                    "Control to request to download a menu script which is
                     unique for this unit by prepending the Ethernet address, 
                     or 802.3 MAC address, of this unit to the nestedMenuName."
                DEFVAL { disabled   }
                ::= { xMenu 9 }

            
            -- the Network Login group
            
            -- Implementation of this group is mandatory for all iTouch
            -- systems that implement network login
            
            netLoginNumber OBJECT-TYPE
                SYNTAX INTEGER
                ACCESS read-only
                STATUS mandatory
                DESCRIPTION
                    "The number of entries in the Network Login Server 
                    table."
                ::= { xNetLogin 1 }
            
            -- The Network Login Server table
            
            netLoginServerTable OBJECT-TYPE
                SYNTAX SEQUENCE OF NetLoginServerEntry
                ACCESS not-accessible
                STATUS mandatory
                DESCRIPTION
                    "A list of network login server entries."
                ::= { xNetLogin 2 }
            
            netLoginServerEntry OBJECT-TYPE
                SYNTAX NetLoginServerEntry
                ACCESS not-accessible
                STATUS mandatory
                DESCRIPTION
                    "Network login parameter values for a server 
                    entry."
                INDEX { netLoginServerName }
                ::= { netLoginServerTable 1 }
            
            NetLoginServerEntry ::=
                SEQUENCE {
                    netLoginServerName
                        DisplayString,
                    netLoginServerStatus
                        INTEGER,
                    netLoginServerPath
                        DisplayString,
                    netLoginServerSeparator
                        DisplayString
                }
            
            netLoginServerName OBJECT-TYPE
                SYNTAX DisplayString (SIZE (1..50))
                ACCESS read-only
                STATUS mandatory
                DESCRIPTION
                    "The name of a network login server, suitable for 
                    resolution to a network address.  Corresponds 
                    directly to host portion of SERVER SCRIPT SERVER and 
                    the value labeled 'Script Host' in the SERVER 
                    PARAMETER SERVER display."
                ::= { netLoginServerEntry 1 }
            
            netLoginServerStatus OBJECT-TYPE
                SYNTAX INTEGER { invalid(1), valid(2) }
                ACCESS read-write
                STATUS mandatory
                DESCRIPTION 
                 "Status of this entry.  Set to 'invalid' to remove
                 the entry, which corresponds directly to the CLEAR
                 SERVER SCRIPT SERVER command.  Actual removal of the
                 entry is implementation specific."
                DEFVAL { valid }
                ::= { netLoginServerEntry 2 }
            
            netLoginServerPath OBJECT-TYPE
                SYNTAX DisplayString (SIZE (0..40))
                ACCESS read-write
                STATUS mandatory
                DESCRIPTION
                    "The full path name to the script file that is 
                    identified by the user name.  Corresponds directly 
                    to path portion of SERVER SCRIPT SERVER and the 
                    value labeled 'Script Path' in the SERVER PARAMETER 
                    SERVER display.  Defaults to the NULL string when
                    a new entry is created."
                ::= { netLoginServerEntry 3 }
            
            netLoginServerSeparator OBJECT-TYPE
                SYNTAX DisplayString (SIZE (0..1))
                ACCESS read-write
                STATUS mandatory
                DESCRIPTION
                    "The single character string that will be inserted
                    between the components of a file's path on the
                    script server.  Defaults to the NULL string when
                    a new entry is created.  Corresponds directly to the
                    separator portion of  SERVER SCRIPT SERVER display."
                ::= { netLoginServerEntry 4 }
            
            -- the Network Login Port table
            
            netLoginPortTable OBJECT-TYPE
                SYNTAX SEQUENCE OF NetLoginPortEntry
                ACCESS not-accessible
                STATUS mandatory
                DESCRIPTION
                    "A list of network login character port entries."
                ::= { xNetLogin 3 }
            
            netLoginPortEntry OBJECT-TYPE
                SYNTAX NetLoginPortEntry
                ACCESS not-accessible
                STATUS mandatory
                DESCRIPTION
                    "Network login parameter values for a port."
                INDEX { netLoginPortIndex }
                ::= { netLoginPortTable 1 }
            
            NetLoginPortEntry ::=
                SEQUENCE {
                    netLoginPortIndex
                        INTEGER,
                    netLoginPortScriptUse
                        INTEGER,
                    netLoginPortScriptEcho
                        INTEGER,
                    netLoginPortLoaderAddressType
                        AddressType,
                    netLoginPortLoaderAddress
                        OCTET STRING,
                    netLoginPortLoaderFile
                        DisplayString,
                    netLoginPortExecuteFile
                        DisplayString
                }
            
            netLoginPortIndex OBJECT-TYPE
                SYNTAX INTEGER
                ACCESS read-only
                STATUS mandatory
                DESCRIPTION
                    "An index value that uniquely identifies a port.  
                    The port identified by a particular value of this 
                    index is the same port as identified by 
                    charPortIndex in the standard Character MIB."
                ::= { netLoginPortEntry 1 }
            
            netLoginPortScriptUse OBJECT-TYPE
                SYNTAX INTEGER { disabled(1), enabled(2), required(3) }
                ACCESS read-write
                STATUS mandatory
                DESCRIPTION
                    "Control for the script action taken when a user 
                    logs in on the port.  Corresponds directly to PORT 
                    SCRIPT LOGIN and the value labeled 'Script Login:' 
                    in the PORT ALTERNATE CHARACTERISTICS display."
                ::= { netLoginPortEntry 2 }
            
            netLoginPortScriptEcho OBJECT-TYPE
                SYNTAX INTEGER { disabled(1), enabled(2) }
                ACCESS read-write
                STATUS mandatory
                DESCRIPTION
                    "Control for display of script operation on the port 
                    when running a script.  Corresponds directly to PORT 
                    SCRIPT ECHO and the presence of the label 'Script 
                    Echo' following the label 'Enabled Characteristics:' 
                    in the PORT CHARACTERISTICS display."
                ::= { netLoginPortEntry 3 }
            
            netLoginPortLoaderAddressType OBJECT-TYPE
                SYNTAX AddressType
                ACCESS read-only
                STATUS mandatory
                DESCRIPTION
                    "The type of network address contained in 
                    netLoginPortLoaderAddress.  'unknown' means no 
                    address has been defined.  'other' means no other 
                    type value applies.  'ip' is an Internet IP address.  
                    'ethernet' is an 802.3 MAC address.  Corresponds 
                    indirectly to the address part of the value labeled 
                    'Script Loaded From:' in the PORT STATUS display."
                ::= { netLoginPortEntry 4 }
            
            netLoginPortLoaderAddress OBJECT-TYPE
                SYNTAX OCTET STRING
                ACCESS read-only
                STATUS mandatory
                DESCRIPTION
                    "The network address of the server that provided the 
                    script for the current port login.  Corresponds 
                    directly the address part of the value labeled 
                    'Script Loaded From:' in the PORT STATUS display."
                ::= { netLoginPortEntry 5 }
            
            netLoginPortLoaderFile OBJECT-TYPE
                SYNTAX DisplayString
                ACCESS read-only
                STATUS mandatory
                DESCRIPTION
                    "The path and file name of the script used for the 
                    current port login.  Corresponds directly the file 
                    name  part of the value labeled 'Script Loaded 
                    From:' in the PORT STATUS display."
                ::= { netLoginPortEntry 6 }
            
            netLoginPortExecuteFile OBJECT-TYPE
                SYNTAX DisplayString (SIZE (0..40))
                ACCESS read-write
                STATUS mandatory
                DESCRIPTION
                    "The path and file name of a script to be executed 
                    immediately on the port.  Corresponds directly the 
                    file name in the SCRIPT command."
                ::= { netLoginPortEntry 7 }
            
            
            -- the Dial group
            
            -- Implementation of this group is mandatory for all iTouch
            -- systems that implement automatic dialing
            
            dialPortTable OBJECT-TYPE
                SYNTAX SEQUENCE OF DialPortEntry
                ACCESS not-accessible
                STATUS mandatory
                DESCRIPTION
                    "A list of dial character port entries."
                ::= { xDial 1 }
            
            dialPortEntry OBJECT-TYPE
                SYNTAX DialPortEntry
                ACCESS not-accessible
                STATUS mandatory
                DESCRIPTION
                    "Dial parameter values for a port."
                INDEX { dialPortIndex }
                ::= { dialPortTable 1 }
            
            DialPortEntry ::=
                SEQUENCE {
                    dialPortIndex
                        INTEGER,
                    dialPortDialback
                        INTEGER,
                    dialPortDialbackTimeout
                        INTEGER,
                    dialPortDialout
                        INTEGER,
                    dialPortDialbackNoUsername 
                        INTEGER
                }
            
            dialPortIndex OBJECT-TYPE
                SYNTAX INTEGER
                ACCESS read-only
                STATUS mandatory
                DESCRIPTION
                    "An index value that uniquely identifies a port.  
                    The port identified by a particular value of this 
                    index is the same port as identified by 
                    charPortIndex in the standard Character MIB."
                ::= { dialPortEntry 1 }
            
            dialPortDialback OBJECT-TYPE
                SYNTAX INTEGER { disabled(1), enabled(2) }
                ACCESS read-write
                STATUS mandatory
                DESCRIPTION
                    "Control for use of dialback when a user logs in on 
                    the port.  Corresponds directly to PORT DIALBACK and 
                    the presence of the label 'Dialback' following the 
                    label 'Enabled Characteristics:' in the PORT 
                    CHARACTERISTICS display."
                ::= { dialPortEntry 2 }
            
            dialPortDialbackTimeout OBJECT-TYPE
                SYNTAX INTEGER (5..60)
                ACCESS read-write
                STATUS mandatory
                DESCRIPTION
                    "The number of seconds to wait for remote modem 
                    response when dialing back.  Corresponds directly to 
                    PORT DIALBACK TIMEOUT and the value labeled 
                    'Dialback Timeout:' in the PORT ALTERNATE 
                    CHARACTERISTICS display."
                ::= { dialPortEntry 3 }

            dialPortDialout OBJECT-TYPE
                SYNTAX INTEGER { none(1), query(2), slip(3), ppp(4) }
                ACCESS read-write
                STATUS mandatory 
                DESCRIPTION
                    "A control to determine the state of a remote port after
                     it has been logged out from the remote side of the
                     connection.  none will log out the port, query will ask
                     user what to do, slip and ppp will revert
                     to those protocols"
                DEFVAL  { none }
                ::= { dialPortEntry 4 }

 	dialPortDialbackNoUsername OBJECT-TYPE
		SYNTAX INTEGER { disabled(1), enabled(2) }
		ACCESS read-write
		STATUS mandatory
		DESCRIPTION
		    "Control which when enabled on a dialback port will not
                     prompt for a username upon dialing back. Instead the 
                     original username is reused."
		DEFVAL { disabled }
		::= { dialPortEntry 5 }

            -- the Session Log group
            
            -- Implementation of this group is mandatory for all iTouch
            -- systems that implement logging session information
            
            sessionLogLimit OBJECT-TYPE
                SYNTAX INTEGER (0..1000)
                ACCESS read-write
                STATUS mandatory
                DESCRIPTION
                    "The maximum number of entries allowed in the 
                    Session Log table.  Corresponds directly to SERVER 
                    ACCOUNTING ENTRIES and the value labeled 'Accounting 
                    Entries:' in the SERVER CHARACTERISTICS display."
                ::= { xSessionLog 1 }
            
            -- Additional scalars follow Session Log table
            
            -- The Session Log table
            
            sessionLogTable OBJECT-TYPE
                SYNTAX SEQUENCE OF SessionLogEntry
                ACCESS not-accessible
                STATUS mandatory
                DESCRIPTION
                    "A list of session log entries."
                ::= { xSessionLog 2 }
            
            sessionLogEntry OBJECT-TYPE
                SYNTAX SessionLogEntry
                ACCESS not-accessible
                STATUS mandatory
                DESCRIPTION
                    "Parameter values for a session log entry."
                INDEX { sessionLogIndex }
                ::= { sessionLogTable 1 }
            
            SessionLogEntry ::=
                SEQUENCE {
                    sessionLogIndex
                        INTEGER,
                    sessionLogConnectionID
                        INTEGER,
                    sessionLogPort
                        INTEGER,
                    sessionLogEvent
                        INTEGER,
                    sessionLogEventDetail
                        INTEGER,
                    sessionLogUserName
                        DisplayString,
                    sessionLogRemoteName
                        DisplayString,
                    sessionLogConnectTime
                        DateTime,
                    sessionLogDisconnectTime
                        DateTime,
                    sessionLogInCharacters
                        Counter,
                    sessionLogOutCharacters
                        Counter,
                    sessionLogVerboseEvent
                        INTEGER,
                    sessionLogX25Direction
                        INTEGER,
                    sessionLogVerboseMessage
                        DisplayString,
                    sessionLogX25CallerAddress
                        OCTET STRING,
                    sessionLogX25CalledAddress
                        OCTET STRING,
                    sessionLogX25DisconnectCause
                        INTEGER,
                    sessionLogX25DisconnectDiagnostic
                        INTEGER
                }
            
            sessionLogIndex OBJECT-TYPE
                SYNTAX INTEGER
                ACCESS read-only
                STATUS mandatory
                DESCRIPTION
                    "The index number of a session log entry.  
                    Corresponds directly to the order of the displayed 
                    records in the SERVER ACCOUNTING display.  The 
                    maximum value is sessionLogLimit."
                ::= { sessionLogEntry 1 }
            
            sessionLogConnectionID OBJECT-TYPE
                SYNTAX INTEGER (1..65535)
                ACCESS read-only
                STATUS mandatory
                DESCRIPTION
                    "An indentifying number for records relating to the 
                    same connection, that is, the connect and disconnect 
                    records, either of which can be missing.  
                    Corresponds directly to value labeled 'Entry' the 
                    SERVER ACCOUNTING display."
                ::= { sessionLogEntry 2 }
            
            sessionLogPort OBJECT-TYPE
                SYNTAX INTEGER
                ACCESS read-only
                STATUS mandatory
                DESCRIPTION
                    "An index value that uniquely identifies the port 
                    where the event took place.  The port identified by 
                    a particular value of this index is the same port as 
                    identified by charPortIndex in the standard 
                    Character MIB.  Corresponds directly to the value 
                    labeled 'Port' in the SERVER ACCOUNTING display."
                ::= { sessionLogEntry 3 }
            
            sessionLogEvent OBJECT-TYPE
                SYNTAX INTEGER { login(1), connectLocal(2),
                                 connectRemote(3), disconnect(4),
                                 rCPConnect(5), rCPDisconnect(6),
                                 x25Connect(13), x25Disconnect(14),
                                 processDefined(15) }
                ACCESS read-only
                STATUS mandatory
                DESCRIPTION
                    "The type of event.  Corresponds directly to the 
                    alphabetic part of the value labeled 'Type' in the 
                    SERVER ACCOUNTING display. Type 15 is used by internal
                    processes that call the session log function with an
                    already formatted message. "
                ::= { sessionLogEntry 4 }
            
            sessionLogEventDetail OBJECT-TYPE
                SYNTAX INTEGER { none(1), protocolBadCircuit(2),
                                 protocolBadCredits(3),
                                 protocolBadStartOrRun(4),
                                 protocolBadRange(5),
                                 duplicateQueueID(6), noUsers(7),
                                 noServiceResourced(8),
                                 serviceUserDisconnect(9),
                                 serviceUnavailable(10),
                                 serverUserDisconnect(11),
                                 noNodeResources(12),
                                 systemShutdown(13),
                                 nodeUserdisconnect(14),
                                 badCircuitTimer(15),
                                 badServiceClass(16),
                                 badMessageOrSlot(17),
                                 timeout(18), noProgress(19),
                                 serviceNotOnPort(20), noSuchPort(21),
                                 badPassword(22), serviceBusy(23),
                                 noSuchService(24), 
                                 serviceDisabled(25),
                                 notInQueue(26), noImmeditatAccess(27),
                                 accessDenied(28),
                                 protocolBadSolicit(29),
                                 protocolBadReasonCode(30),
                                 unsupportedTest(31),
                                 domainTooLong(32),
                                 noSuchNode(33),
                                 noSuchServiceOnNode(34),
                                 rejectService(35),
                                 internetConnectDisabled(36) }
                ACCESS read-only
                STATUS mandatory
                DESCRIPTION
                    "The detailed reason for the event.  Corresponds 
                    directly to the numeric part of the value labeled 
                    'Type' in the SERVER ACCOUNTING display."
                ::= { sessionLogEntry 5 }
            
            sessionLogUserName OBJECT-TYPE
                SYNTAX DisplayString (SIZE (0..16))
                ACCESS read-only
                STATUS mandatory
                DESCRIPTION
                    "The user name logged in on the port when the event 
                    occurred.  Corresponds directly to the value labeled 
                    'Username' in the SERVER ACCOUNTING display."
                ::= { sessionLogEntry 6 }
            
            sessionLogRemoteName OBJECT-TYPE
                SYNTAX DisplayString (SIZE (0..17))
                ACCESS read-only
                STATUS mandatory
                DESCRIPTION
                    "The name of the session remote partner.  
                    Corresponds directly to the value labeled 
                    'Destination' in the SERVER ACCOUNTING display."
                ::= { sessionLogEntry 7 }
            
            sessionLogConnectTime OBJECT-TYPE
                SYNTAX DateTime
                ACCESS read-only
                STATUS mandatory
                DESCRIPTION
                    "The date and time that session connection occurred.  
                    Corresponds directly to the value labeled 'Connect 
                    Time' in the SERVER ACCOUNTING display."
                ::= { sessionLogEntry 8 }
            
            sessionLogDisconnectTime OBJECT-TYPE
                SYNTAX DateTime
                ACCESS read-only
                STATUS mandatory
                DESCRIPTION
                    "The date and time that session disconnection 
                    occurred.  Corresponds directly to the value labeled 
                    'Disconnect Time' in the SERVER ACCOUNTING 
                    display."
                ::= { sessionLogEntry 9 }
            
            sessionLogInCharacters OBJECT-TYPE
                SYNTAX Counter
                ACCESS read-only
                STATUS mandatory
                DESCRIPTION
                    "The number of characters that came into the port 
                    for the session.  Corresponds directly to the value 
                    labeled 'Bytes In' in the SERVER ACCOUNTING 
                    display."
                ::= { sessionLogEntry 10 }
            
            sessionLogOutCharacters OBJECT-TYPE
                SYNTAX Counter
                ACCESS read-only
                STATUS mandatory
                DESCRIPTION
                    "The number of characters that went out of the port 
                    for the session.  Corresponds directly to the value 
                    labeled 'Bytes Out' in the SERVER ACCOUNTING 
                    display."
                ::= { sessionLogEntry 11 }
            
            sessionLogVerboseEvent OBJECT-TYPE
                SYNTAX INTEGER { login(1), connectLocal(2),
                                 connectRemote(3), disconnect(4),
                                 connectRcp(5),
                                 disconnectRcp(6),
                                 telnetMaint(7),
                                 xremote(8),
                                 xprinter(9),
                                 lpd(12),
                                 connectX25(13),
                                 disconnectX25(14),
                                 userDefined(15) }
                ACCESS read-only
                STATUS mandatory
                DESCRIPTION
                    "When logging in 'verbose' mode, the event that 
                    occured."
                ::= { sessionLogEntry 12 }
            
            sessionLogX25Direction OBJECT-TYPE
                SYNTAX INTEGER { inbound(1), outbound(2) }
                ACCESS read-only
                STATUS mandatory
                DESCRIPTION
                    "The initial direction for an X.25 connection.
                     A value of 0 is returned if the session is
                     not X25"
                ::= { sessionLogEntry 13 }
            
            sessionLogVerboseMessage OBJECT-TYPE
                SYNTAX DisplayString
                ACCESS read-only
                STATUS mandatory
                DESCRIPTION
                    "Text describing the event that was logged."
                ::= { sessionLogEntry 14 }
            
            sessionLogX25CallerAddress OBJECT-TYPE
                SYNTAX OCTET STRING (SIZE (0..20))
                ACCESS read-only
                STATUS mandatory
                DESCRIPTION
                    "For an X.25 connection, the X.121 source address."
                ::= { sessionLogEntry 15 }
            
            sessionLogX25CalledAddress OBJECT-TYPE
                SYNTAX OCTET STRING (SIZE (0..20))
                ACCESS read-only
                STATUS mandatory
                DESCRIPTION
                    "For an X.25 connection, the X.121 destination 
                    address."
                ::= { sessionLogEntry 16 }
            
            sessionLogX25DisconnectCause OBJECT-TYPE
                SYNTAX INTEGER
                ACCESS read-only
                STATUS mandatory
                DESCRIPTION
                    "For a terminated X.25 connection, the standard, 
                    X.25 cause code."
                ::= { sessionLogEntry 17 }
            
            sessionLogX25DisconnectDiagnostic OBJECT-TYPE
                SYNTAX INTEGER
                ACCESS read-only
                STATUS mandatory
                DESCRIPTION
                    "For a terminated X.25 connection, the standard, 
                    X.25 diagnostic code."
                ::= { sessionLogEntry 18 }
            
            
            -- Additional scalars
            
            sessionLogHostType OBJECT-TYPE
                SYNTAX INTEGER { none(1), unix(2) }
                ACCESS read-write
                STATUS mandatory
                DESCRIPTION
                    "The type of host to which session log events are to 
                    be sent."
                ::= { xSessionLog 3 }
            
            sessionLogHostAddress OBJECT-TYPE
                SYNTAX OCTET STRING (SIZE (0..4))
                ACCESS read-write
                STATUS mandatory
                DESCRIPTION
                    "The address of the host to receive events."
                ::= { xSessionLog 4 }
            
            sessionLogVerbose OBJECT-TYPE
                SYNTAX INTEGER { disabled(1), enabled(2) }
                ACCESS read-write
                STATUS mandatory
                DESCRIPTION
                    "Control for verbose logging."
                ::= { xSessionLog 5 }
            
            sessionLogPriority OBJECT-TYPE
                SYNTAX INTEGER (0..7)
                ACCESS read-write
                STATUS mandatory
                DESCRIPTION
                    "The largest priority number for the system to log.  
                    Higher numbered (lower priority) events will not be 
                    logged."
                ::= { xSessionLog 6 }
            
            sessionLogEmpty OBJECT-TYPE
                SYNTAX INTEGER  { ready(1), execute(2) }
                ACCESS read-write
                STATUS mandatory
                DESCRIPTION
                    "Control to empty the log.  In response to a 
                    get-request or get-next-request, the agent always 
                    returns 'ready' for this value.  Setting the value 
                    to 'ready' has no effect.  Setting it to 'execute' 
                    causes the log to be emptied."
                ::= { xSessionLog 7 }

            sessionLogFacility OBJECT-TYPE
                SYNTAX INTEGER { local0(1), local1(2), local2(3),
                                 local3(4), local4(5), local5(6),
                                 local6(7), local7(8), user(9) }
                ACCESS read-write
                STATUS mandatory
                DESCRIPTION
                    "The UNIX facility level that server originated 
                     accounting messages are logged to."
                DEFVAL { user }
                ::= { xSessionLog 8 }

            sessionLogReliable OBJECT-TYPE
                SYNTAX INTEGER { disabled (1), enabled (2) }
                ACCESS read-write
                STATUS mandatory
                DESCRIPTION
                    "Control for reliable logging. Corresponds directly to the 
                    presence of the label 'Reliable Accounting' following the  
                    label 'Enabled Characteristics:' in the SERVER 
                    CHARACTERISTICS display."
                DEFVAL { disabled }
                ::= { xSessionLog 9 }

            sessionLogHostSecondaryType OBJECT-TYPE
                SYNTAX INTEGER { none (1), unix(2) }
                ACCESS read-write
                STATUS mandatory
                DESCRIPTION
                    "The type of secondary host to which session log events are
                     to be sent. This value should be set to unix when
                     configuring a non-zero sessionLogHostSecondaryAddress.
                     Corresponds to the presence of the label 'SYSLOGD Host2'
                     following the label 'Daemon(s)' in the SERVER UNIT 
                     display."
                DEFVAL { none  }
                ::= { xSessionLog 10 }

            sessionLogHostSecondaryAddress OBJECT-TYPE
                SYNTAX OCTET STRING (SIZE (0..4))
                ACCESS read-write
                STATUS mandatory
                DESCRIPTION
                    "The address of a secondary host to receive events.
                     Corresponds directly to the value labeled 
                     'SYSLOGD Host2' in the SERVER UNIT display."
                ::= { xSessionLog 11 }

            sessionLogZeroAccountingAll OBJECT-TYPE
                SYNTAX INTEGER { ready(1), execute(2)}
                ACCESS read-write
                STATUS mandatory
                DESCRIPTION
                    "A control to clear all entries in the accounting log 
                     including command log entries. Corresponds directly to 
                     the command CLEAR SERVER ACCOUNTING ALL. In response to 
                     a get-request or get-next-request the agent always returns
                     ready for this value."
                ::= { xSessionLog 12 }                


            sessionLogZeroCommandLogging OBJECT-TYPE
                SYNTAX INTEGER { ready(1), execute(2)}
                ACCESS read-write
                STATUS mandatory
                DESCRIPTION
                    "A control to clear all command log entries. Corresponds
                     directly to the command CLEAR SERVER COMMAND LOGGING. In
                     response to a get-request or get-next-request the agent 
                     always returns ready for this value."
                ::= { xSessionLog 13 }                

 	sessionLogTl1AutonomousLogSize OBJECT-TYPE
		SYNTAX INTEGER ( 0..1000)
		ACCESS read-write
		STATUS mandatory
		DESCRIPTION
		    "The size in bytes of the TL1 autonomous log, which 
                     records alarms. A change in log size will not take effect
                     until rebooting the unit."
		DEFVAL { 0 }
		::= { xSessionLog 14 }

 	sessionLogTl1CommandLogSize OBJECT-TYPE
		SYNTAX INTEGER ( 0..1000)
		ACCESS read-write
		STATUS mandatory
		DESCRIPTION
		    "The size in bytes of the TL1 command log, which records
                     all TL1 commands entered on this server. A change in log
                     size will not take effect until rebooting the unit."
		DEFVAL { 0 }
		::= { xSessionLog 15 }

            sessionLogZeroDataLogging OBJECT-TYPE
                SYNTAX INTEGER { ready(1), execute(2)}
                ACCESS read-write
                STATUS mandatory
                DESCRIPTION
                    "A control to clear all data log entries. Corresponds
                     directly to the command CLEAR SERVER DATA LOGGING. In
                     response to a get-request or get-next-request the agent 
                     always returns ready for this value."
                ::= { xSessionLog 16 }                

            sessionLogZeroAlarmLogging OBJECT-TYPE
                SYNTAX INTEGER { ready(1), execute(2)}
                ACCESS read-write
                STATUS mandatory
                DESCRIPTION
            	    "Control to clear all alarm log entries. In response to a
             	    get-request or a get-next-request the agent always returns
             	    ready for this value."
                ::= { xSessionLog 17 }                
 

            -- The Loaded and Parsed CCL Table

            cclParsedScriptTable OBJECT-TYPE
                SYNTAX SEQUENCE OF CclParsedScriptEntry
                ACCESS not-accessible
                STATUS mandatory
                DESCRIPTION
                    "A list of parsed CCL scripts."
                ::= { xCcl 1 }

            cclParsedScriptEntry OBJECT-TYPE
                SYNTAX CclParsedScriptEntry
                ACCESS not-accessible
                STATUS mandatory
                DESCRIPTION
                    "Parsed CCL script information."
                INDEX { cclScriptName }
                ::= { cclParsedScriptTable 1 }

            CclParsedScriptEntry ::=
                SEQUENCE {
                    cclScriptName
                        DisplayString,
                    cclScriptControl
                        INTEGER
                }

            cclScriptName OBJECT-TYPE
                SYNTAX DisplayString (SIZE (1..32))
                ACCESS read-only
                STATUS mandatory
                DESCRIPTION
                    "The name of a CCL script file that has been
                    loaded from a script server.  Corresponds directly
                    to the name in a SERVER CCL command and the value
                    labeled 'CCL name:' in the PORT CHARACTERISTICS
                    display."
                ::= { cclParsedScriptEntry 1 }

            cclScriptControl OBJECT-TYPE
                SYNTAX INTEGER { refresh(1), delete(2) }
                ACCESS read-write
                STATUS mandatory
                DESCRIPTION
                    "Control for maintaining the CCL script.  The
                    refresh action consists of retrieving the script
                    by name from a script server and parsing it into
                    an executable format.  This may be used to add an
                    entry to the table or refresh an existing entry with
                    a new version of the CCL script from the server.
                    This command may take ten seconds or more to complete
                    and may fail if the script file cannot be retrieved or
                    an error is encountered in parsing the CCL script.
                    An error value of genErr is returned upon refresh
                    failure. The refresh action corresponds directly to
                    the commnd: REFRESH SERVER CCL.  Setting this field
                    to delete causes a script that is NOT being referenced
                    by any ports to be removed from the list and its
                    memory freed.  This action corresponds directly to
                    the command: DELETE SERVER CCL.  An error value of
                    badValue is returned upon delete failure."
                DEFVAL { refresh }
                ::= { cclParsedScriptEntry 2 }

            -- The CCL Port Table

            cclPortTable OBJECT-TYPE
                SYNTAX SEQUENCE OF CclPortEntry
                ACCESS not-accessible
                STATUS mandatory
                DESCRIPTION
                    "A list of ccl character port entries."
                ::= { xCcl 2 }
            
            cclPortEntry OBJECT-TYPE
                SYNTAX CclPortEntry
                ACCESS not-accessible
                STATUS mandatory
                DESCRIPTION
                    "CCL parameter values for a port."
                INDEX { charPortIndex }
                ::= { cclPortTable 1 }
            
            CclPortEntry ::=
                SEQUENCE {
                    cclPortCclName
                        DisplayString,
                    cclPortModemAudible
                        INTEGER
                }

            cclPortCclName OBJECT-TYPE
                SYNTAX DisplayString (SIZE (0..32))
                ACCESS read-write
                STATUS mandatory
                DESCRIPTION
                    "The name of the ARAP modem CCL script file."
                ::= { cclPortEntry 1 }

            cclPortModemAudible OBJECT-TYPE
                SYNTAX INTEGER { disabled(1), enabled(2) }
                ACCESS read-write
                STATUS mandatory
                DESCRIPTION
                    "This boolean indicates if the CCL script should put
                    the modem into audible mode."
            ::= { cclPortEntry 2 }

-- The Data Broadcast Group Table

    broadcastGroupTable OBJECT-TYPE
	SYNTAX SEQUENCE OF BroadcastGroupEntry
	ACCESS not-accessible
	STATUS mandatory
	DESCRIPTION
		"A list of broadcast groups."
    ::= { xBroadcastGroup 1 }

    broadcastGroupEntry OBJECT-TYPE
	SYNTAX BroadcastGroupEntry
	ACCESS not-accessible
	STATUS mandatory
	DESCRIPTION
		"Broadcast group information."
	INDEX { broadcastGroupIndex }
    ::= { broadcastGroupTable 1 }

    BroadcastGroupEntry ::=
	SEQUENCE {
		broadcastGroupIndex
			INTEGER,
		broadcastGroupStatus
			INTEGER,
		broadcastGroupMaster
			INTEGER,
		broadcastGroupSlaves
			OCTET STRING,
		broadcastGroupSlavesBroadcastOnly
			OCTET STRING,
		broadcastGroupSlaveTcpPort
			INTEGER,
		broadcastGroupSlaveTcpBroadcastOnly
			INTEGER
	}

    broadcastGroupIndex OBJECT-TYPE
	SYNTAX INTEGER ( 1..10)
	ACCESS read-only
	STATUS mandatory
	DESCRIPTION
            "An index value that uniquely identifies a broadcast group."
    ::= { broadcastGroupEntry 1 }

    broadcastGroupStatus OBJECT-TYPE
	SYNTAX INTEGER { disabled(1), enabled(2) }
	ACCESS read-write
	STATUS mandatory
	DESCRIPTION
            "A status value for the broadcast group. The value 'enabled' means
             that the group is active and broadcasting data whereas 'disabled'
             means that the group is not active."
        DEFVAL { disabled }
    ::= { broadcastGroupEntry 2 } 

    broadcastGroupMaster OBJECT-TYPE
	SYNTAX INTEGER 
	ACCESS read-write
	STATUS mandatory
	DESCRIPTION
            "An index value that uniquely identifies the Master Broadcast Port
             for this group. The port provided in this object is the same port
             as identified by charPortIndex in the standard Character MIB."
    ::= { broadcastGroupEntry 3 } 

    broadcastGroupSlaves OBJECT-TYPE
	SYNTAX OCTET STRING 
	ACCESS read-write
	STATUS mandatory
	DESCRIPTION
            "A bitmap representing the ports included in this broadcast group.
             A bit with a value of '1' means the corresponding port is included
             in the broadcast group whereas a value of '0' indicates that the
             port is not part of the broadcast group."
    ::= { broadcastGroupEntry 4 } 

    broadcastGroupSlavesBroadcastOnly OBJECT-TYPE
	SYNTAX OCTET STRING
	ACCESS read-write
	STATUS mandatory
	DESCRIPTION
            "A bitmap representing the ports set up to discard input data and
             transmit only the broadcast data on the line. A bit set to '1' 
             means that the corresponding port will only broadcast the data and
             discard any input."
    ::= { broadcastGroupEntry 5 } 

    broadcastGroupSlaveTcpPort OBJECT-TYPE
	SYNTAX INTEGER (0..65554)
	ACCESS read-write
	STATUS mandatory
	DESCRIPTION
            "A TCP port number on which the broadcast group process will listen
             for incoming TCP connections. A client connected to this
             particular port will receive the data broadcast by the Master
             Port. A value of '0' indicates that no TCP port is defined."
        DEFVAL { 0 }
    ::= { broadcastGroupEntry 6 } 

    broadcastGroupSlaveTcpBroadcastOnly OBJECT-TYPE
	SYNTAX INTEGER { disabled(1), enabled(2) }
	ACCESS read-write
	STATUS mandatory
	DESCRIPTION
            "Specifies whether the TCP port will discard input characters 
             for the Master port so that the Master port operates in broadcast 
             only mode."
        DEFVAL { disabled }
    ::= { broadcastGroupEntry 7 }




	    -- Trap definitions
            -- These traps apply to InReach agents running V2.4 and above. 
            -- Earlier traps are defined in the ITOUCH-TRAP-MIB.
	
           contactClosureChanged TRAP-TYPE
           ENTERPRISE iTouch
           VARIABLES {
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Indication that the contact closure transitioned to open or closed."
           ::= 30

           powerAlarmFuseBankA TRAP-TYPE
           ENTERPRISE iTouch
           VARIABLES  { 
		basicPowerStatusFuseA,
		sysLocation
		}
           DESCRIPTION
               "Indicates that a fuse from bank A tripped its breaker, or that
                it went operational. However, it is unlikely that a trap would
                be issued when the fuse starts working."
           ::= 31

 	   powerAlarmFuseBankB TRAP-TYPE
           ENTERPRISE iTouch
           VARIABLES  { 
		basicPowerStatusFuseB,
		sysLocation
		}
           DESCRIPTION
               "Indicates that a fuse from bank B tripped its breaker, or that
                it went operational. However, it is unlikely that a trap would
                be issued when the fuse starts working."
           ::= 32

 	   powerSupplyAlarmA TRAP-TYPE
           ENTERPRISE iTouch
           VARIABLES  { basicPowerSupplyStatusA,
		 sysLocation 
		}
           DESCRIPTION
               "Indicates that power supply A lost or regained power.
                However, it is unlikely that a trap would be issued when the
                power comes on."
           ::= 33

 	   powerSupplyAlarmB TRAP-TYPE
           ENTERPRISE iTouch
           VARIABLES  { basicPowerSupplyStatusB,
		sysLocation
		}
           DESCRIPTION
               "Indicates that power supply B lost or regained power.
                However, it is unlikely that a trap would be issued when the
                power comes on."
           ::= 34

           portInputSignalChange TRAP-TYPE
           ENTERPRISE iTouch
           VARIABLES { rs232InSigState, sysLocation, 	        
			rs232PortIndex }
           DESCRIPTION
              "Indicates that an input signal on a port has transitioned to
               the state indicated in the variable rs232InSigState."
           ::= 35

           portOutputSignalChange TRAP-TYPE
           ENTERPRISE iTouch
           VARIABLES { rs232OutSigState, sysLocation,
			rs232PortIndex }
           DESCRIPTION
              "Indicates that an output signal on a port has transitioned to
               the state indicated in the variable rs232OutSigState."
           ::= 36

           humidityThresholdExceeded TRAP-TYPE
           ENTERPRISE iTouch
           VARIABLES { basicHumidityValue,
  		       sysLocation,
	               basicHumiditySensorIndex,
                       basicHumidityAlarmStatus
                     }
           DESCRIPTION
               "Indication that the humidity exceeded a threshhold and
                the value of the currrent humidity."
           ::= 37

           temperatureThresholdExceeded TRAP-TYPE
           ENTERPRISE iTouch
           VARIABLES  { 
		basicTemperatureValue,
		sysLocation,
	        basicTemperatureSensorIndex,
                basicTemperatureAlarmStatus
		}
           DESCRIPTION
               "Indication that the temperature exceeded a threshhold and
                the value of the currrent temperature."
           ::= 38

           alarmMasterNotResponding TRAP-TYPE
           ENTERPRISE iTouch
           VARIABLES {
	        basicPortIndex, 
		sysLocation,
		basicPortAlarmMasterStatus
		 }
           DESCRIPTION
               "Indication that the high density alarm management device lost
                or regained contact with the inReach port to which it was 
                connected as indicated by the basicPortAlarmMasterStatus 
                variable."
          ::= 39

           alarmMasterInputStateChange TRAP-TYPE
           ENTERPRISE iTouch
           VARIABLES {
		basicAlarmMasterInputValue,
		basicAlarmMasterInputName,  
		sysLocation,
	        basicAlarmMasterInputPort,
                basicAlarmMasterInputStatus,
	        basicAlarmMasterInputSlot,
	        basicAlarmMasterInputPoint
		 }
           DESCRIPTION
               "Indication that the alarm input point within a high density alarm 
                management port transitioned to open or closed."
          ::= 41

           asciiToTrapTranslation  TRAP-TYPE
           ENTERPRISE iTouch
           VARIABLES {
                basicPortAsciiToTrapTranslationTrapSeverity,
                basicPortAsciiToTrapTranslationLastMessage
                 }
           DESCRIPTION
                "This trap contains ASCII data, which arrived at serial port,
                 was formatted as a trap, and sent out on the network."
           ::= 42
 
	powerMasterNotResponding TRAP-TYPE
        ENTERPRISE iTouch
        VARIABLES  {
           basicPortIndex,
           sysLocation,
	   basicPortPowerMasterDeviceStatus           
           }
	DESCRIPTION
	    "Indication that the power management port lost or regained 
             contact with the power unit to which it was connected as
             indicated by the basicPortPowerMasterDeviceStatus variable."
        ::= 43

END
