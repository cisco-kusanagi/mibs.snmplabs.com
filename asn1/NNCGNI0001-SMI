-- @(#)Newbridge.smi	2.3 1/12/94
--------------------------------------------------------------------------------
-- file: Newbridge.smi
--
-- contents:
--	This file contains the number assignments for the Newbridge MIB 
--	extensions.
--
-- Copyright 1992-1999 Newbridge Networks Corporation.  All Rights Reserved
--------------------------------------------------------------------------------
NNCGNI0001-SMI	DEFINITIONS ::= BEGIN
	
	IMPORTS	
		TEXTUAL-CONVENTION
			FROM SNMPv2-TC
		enterprises
			FROM RFC1155-SMI
			Gauge32 FROM SNMPv2-SMI;
		
-- Numbers which are in comments are assigned through the MODULE-IDENTITY
-- macro in the MIB modules (".mib" files).  They are recorded here in
-- order for there to be SOME central repository of numbers.

--
-- Top divisions in the Newbridge SMI
--
	newbridge     		 OBJECT IDENTIFIER ::= { enterprises 123 }
        nncDeviceIDs   		 OBJECT IDENTIFIER ::= { newbridge 1 }
        nncInterimMib		 OBJECT IDENTIFIER ::= { newbridge 2 }
	nncExtensions		 OBJECT IDENTIFIER ::= { newbridge 3 }
	nncLegacyModules	 OBJECT IDENTIFIER ::= { newbridge 4 }
		
--
-- MIB extension sub-trees
-- ****NOTE:  Sub-trees are to be added by Numbers Admin only.  ****
-- **** This section of the file may NOT be changed             ****
--
	nncExtSystem		OBJECT IDENTIFIER ::= { nncExtensions 1 }
	nncExtEnvironmental	OBJECT IDENTIFIER ::= { nncExtensions 2 }
	nncExtRestart		OBJECT IDENTIFIER ::= { nncExtensions 3 }
	nncExtCodeSpace		OBJECT IDENTIFIER ::= { nncExtensions 4 }
	nncExtNVM		OBJECT IDENTIFIER ::= { nncExtensions 5 }
	nncExtAlarm		OBJECT IDENTIFIER ::= { nncExtensions 6 }
	nncExtNetSynch		OBJECT IDENTIFIER ::= { nncExtensions 7 }
	nncExtPosition		OBJECT IDENTIFIER ::= { nncExtensions 8 }
	nncExtDevice		OBJECT IDENTIFIER ::= { nncExtensions 9 }
	nncExtDs1		OBJECT IDENTIFIER ::= { nncExtensions 10 }
	nncExtRptr		OBJECT IDENTIFIER ::= { nncExtensions 11 }
	nncExtProbe		OBJECT IDENTIFIER ::= { nncExtensions 12 }
	nncExtDiag		OBJECT IDENTIFIER ::= { nncExtensions 13 }
	nncExtSyncDataCct	OBJECT IDENTIFIER ::= { nncExtensions 14 }
	-- nncExtSNMP		OBJECT IDENTIFIER ::= { nncExtensions 15 }
	-- nncExtILMI		OBJECT IDENTIFIER ::= { nncExtensions 16 }
	-- nncExtAttachedDev	OBJECT IDENTIFIER ::= { nncExtensions 17 }
	-- nncExtVividRsTm      OBJECT IDENTIFIER ::= { nncExtensions 18 }
	-- nncExtVividRsTt      OBJECT IDENTIFIER ::= { nncExtensions 19 }
	-- nncExtVividRsWd      OBJECT IDENTIFIER ::= { nncExtensions 20 }
	-- nncExtVividRsStp     OBJECT IDENTIFIER ::= { nncExtensions 21 }
	-- nncExtServiceUser    OBJECT IDENTIFIER ::= { nncExtensions 22 }
	-- nncExtIfHistStats    OBJECT IDENTIFIER ::= { nncExtensions 23 }
	-- nncExtDs1HistStats   OBJECT IDENTIFIER ::= { nncExtensions 24 }
	-- nncExtFRNetServLport OBJECT IDENTIFIER ::= { nncExtensions 25 }
	-- nncExtFRPVCConfig    OBJECT IDENTIFIER ::= { nncExtensions 26 }
	-- nncExtFRPVCEndptStats OBJECT IDENTIFIER ::= { nncExtensions 27 }
	-- nncVividRsVnc	OBJECT IDENTIFIER ::= { nncExtensions 28 }
	nncAtmStatistics	OBJECT IDENTIFIER ::= { nncExtensions 29 }
	-- nncFRIntStatistics	OBJECT IDENTIFIER ::= { nncExtensions 30 }
	nncExtIntvlStats	OBJECT IDENTIFIER ::= { nncExtensions 31 }
	nncExtSVCSigStats	OBJECT IDENTIFIER ::= { nncExtensions 32 }
	-- nncExtAtmPVCConfig	OBJECT IDENTIFIER ::= { nncExtensions 33 }
	-- nncExtDataCct	OBJECT IDENTIFIER ::= { nncExtensions 34 }
	-- nncExtSXC		OBJECT IDENTIFIER ::= { nncExtensions 35 }
	-- nncExtOcu		OBJECT IDENTIFIER ::= { nncExtensions 36 }
	-- nncExtAnalog		OBJECT IDENTIFIER ::= { nncExtensions 37 }
	-- nncExtVividRsRelay	OBJECT IDENTIFIER ::= { nncExtensions 38 }
	-- nncExtVividRsRedund	OBJECT IDENTIFIER ::= { nncExtensions 39 }
	nncExtE3		OBJECT IDENTIFIER ::= { nncExtensions 40 }
	-- nncExtAtmAld		OBJECT IDENTIFIER ::= { nncExtensions 41 }
	-- nncExtBridge		OBJECT IDENTIFIER ::= { nncExtensions 42 }
	-- nncExtMultiBridge	OBJECT IDENTIFIER ::= { nncExtensions 43 }
	-- nncExtNotif		OBJECT IDENTIFIER ::= { nncExtensions 44 }
	-- nncExtVividRsUbfObjects OBJECT IDENTIFIER ::= { nncExtensions 45 }
	-- nncExtRsGeneral      OBJECT IDENTIFIER ::= { nncExtensions 46 }
	-- NncCEFillLevelStatistics OBJECT IDENTIFIER ::= { nncExtensions 47 }
 	-- nncExtTrafMgmnt OBJECT IDENTIFIER ::= { nncExtensions 48 }
	-- nncExtMNSCNotif       OBJECT IDENTIFIER ::= { nncExtensions 49 } 
	-- nncExtPktStatistics   OBJECT IDENTIFIER ::= { nncExtensions 50 } 
	-- nncExtCons		   OBJECT IDENTIFIER ::= { nncExtensions 51 }
	-- nncExtRsbgpcfg	 OBJECT IDENTIFIER ::= { nncExtensions 52 }
	-- nncExtRsrtPolicy	 OBJECT IDENTIFIER ::= { nncExtensions 53 }
	-- nncExtAtmProtoStatistics OBJECT IDENTIFIER ::= { nncExtensions 54 }
	-- nncExtCodeSpaceDownloadDate OBJECT IDENTIFIER ::= { nncExtensions 55 }
	-- nncExtCodeSpaceDownloadTime OBJECT IDENTIFIER ::= { nncExtensions 56 }
	-- nncExtAtmCES    	OBJECT IDENTIFIER ::= { nncExtensions 57}
	-- nncExtDs0		OBJECT IDENTIFIER ::= { nncExtensions 58}
	-- nncExtDs1		OBJECT IDENTIFIER ::= { nncExtensions 59}
	-- nncExtIF		OBJECT IDENTIFIER ::= { nncExtensions 60}
	-- nncExtWless		OBJECT IDENTIFIER ::= { nncExtensions 61}
	-- nncExtJ2		OBJECT IDENTIFIER ::= { nncExtensions 62}
	-- nncAtmCongestionStatistics  OBJECT IDENTIFIER ::= { nncExtensions 63}
	-- nncSdslStatistics  OBJECT IDENTIFIER ::= { nncExtensions 64}
	nncExtPmStatistics  OBJECT IDENTIFIER ::= { nncExtensions 65}
	-- nncExtVividRsPort  OBJECT IDENTIFIER ::= { nncExtensions 66}
	-- nncExtVividRsMcast  OBJECT IDENTIFIER ::= { nncExtensions 67}
	-- nncExtRsRipOspfcfg  OBJECT IDENTIFIER ::= { nncExtensions 68}
	-- nncExtNEInventory  OBJECT IDENTIFIER ::= { nncExtensions 69}
	-- nncBellcoreGR820Ds1Statistics  OBJECT IDENTIFIER ::= { nncExtensions 70}



--
-- Module IDs for legacy modules (i.e. old Newbridge modules which have
-- been v2ized).
--
	-- nncExtBasics OBJECT IDENTIFIER ::= { nncLegacyModules 1 }
	-- nncExt3620Alarm  OBJECT IDENTIFIER ::= { nncLegacyModules 2 }
        -- nncExtNetSynch OBJECT IDENTIFIER ::= { nncLegacyModules 3 }
        -- nncExtDS1Ext   OBJECT IDENTIFIER ::= { nncLegacyModules 4 }
        -- nncExtHubExt   OBJECT IDENTIFIER ::= { nncLegacyModules 5 }
        -- nncExtGenDev   OBJECT IDENTIFIER ::= { nncLegacyModules 6 }
        -- nncExtSynchCct OBJECT IDENTIFIER ::= { nncLegacyModules 7 }
        -- nncExtPosition OBJECT IDENTIFIER ::= { nncLegacyModules 8 }
        -- nncostMib	  OBJECT IDENTIFIER ::= { nncLegacyModules 9 }
        -- nnXcellysMib	  OBJECT IDENTIFIER ::= { nncLegacyModules 10 }
	-- nncLegacyExtAlarm OBJECT IDENTIFIER ::= { nncLegacyModules 11 }

-- 
-- The following defines temporary types to be used until we have SNMPv2.
--
	NncUnsigned32 ::= TEXTUAL-CONVENTION
		STATUS	current
		DESCRIPTION
		"Type to be used as Unsigned32 for compatibility with SNMPv1."
		SYNTAX	Gauge32 (0..4294967295)

	NncExtCounter64 ::= TEXTUAL-CONVENTION
		DISPLAY-HINT "8d"
		STATUS	current
		DESCRIPTION
		"This defines a type that allows a 64-bit integer to be used
	         by v1 managers and agents.  Its semantics are the same as
		 Counter64 in SNMPv2.  The octets are in network-byte order."
		SYNTAX	OCTET STRING (SIZE (8))
END
