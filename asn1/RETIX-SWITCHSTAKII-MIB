-- Title:       RETIX SwitchStakII MIB
-- Version:     1.2
-- Date:        Nov 20, 1995

-- Copyright Retix 1995 
-- All Rights Reserved.  

-- Reproduction of this document is authorized on condition 
-- that the foregoing copyright notice is included.

-- This is the MIB for the Retix SwitchStakII products.

-- Retix makes no warranty, either express or implied, as to the use,
-- operation, condition, or performance of this Specification.


RETIX-SWITCHSTAKII-MIB DEFINITIONS ::= BEGIN

IMPORTS
      NetworkAddress, IpAddress,
      Counter, Gauge, TimeTicks,
      enterprises
    FROM RFC1158-MIB
    OBJECT-TYPE
    FROM RFC1212;

-- enterprises  OBJECT IDENTIFIER ::= 
--             { iso org(3) dod(6) internet(1) private(4) 1 }

-- 
--  Defined Groups
--
retix         OBJECT IDENTIFIER ::= { enterprises  72 }
switchStakII  OBJECT IDENTIFIER ::= { retix        20 }
unitProfile   OBJECT IDENTIFIER ::= { switchStakII  1 }
baseUnit      OBJECT IDENTIFIER ::= { switchStakII  2 }
stakbus       OBJECT IDENTIFIER ::= { switchStakII  3 }
vlan          OBJECT IDENTIFIER ::= { switchStakII  4 }
vlanConfig    OBJECT IDENTIFIER ::= { vlan          1 }

--
--  switchStakII.unitProfile
-- 


baseModule  OBJECT-TYPE
        SYNTAX  INTEGER {
                tenPorts2AUI(1) 
        }
        ACCESS  read-only
        STATUS  mandatory
        DESCRIPTION
        " Identifies the type of main PCB installed."
        ::= { unitProfile 1 }

io1Module  OBJECT-TYPE
        SYNTAX  INTEGER {
                vacant(1),
                sixPort10BaseT(2),
                fastEthernet(3), 
                stakbus(4),
                atm(5)
        }
        ACCESS  read-only
        STATUS  mandatory
        DESCRIPTION
        " Identifies the type of card installed in the IO1 connector"
        ::= { unitProfile 2 }

io2Module  OBJECT-TYPE
        SYNTAX  INTEGER {
                vacant(1),
                sixPort10BaseT(2),
                fastEthernet(3), 
                stakbus(4),
                atm(5)
        }
        ACCESS  read-only
        STATUS  mandatory
        DESCRIPTION
        " Identifies the type of card installed in the IO2 connector"
        ::= { unitProfile 3 }

--
--  switchStakII.baseUnit
--

baseBootFirmwareVersion  OBJECT-TYPE
        SYNTAX  INTEGER
        ACCESS  read-only
        STATUS  mandatory
        DESCRIPTION
        " Version number of current boot firmware in decimal,
          (i.e. V01.00 is displayed as 256)"
        ::= { baseUnit 1}

baseSoftwareVersion  OBJECT-TYPE
        SYNTAX  INTEGER
        ACCESS  read-only
        STATUS  mandatory
        DESCRIPTION
        " Version number of current software in decimal,
          (i.e. V01.03 is displayed as 259)"
        ::= { baseUnit 2}

baseErrorLog  OBJECT-TYPE
        SYNTAX  INTEGER
        ACCESS  read-write
        STATUS  mandatory
        DESCRIPTION
        "A stored value indicating that the unit has experienced a fault.  
         Log information is formatted as a four digit hex number.  
         Set to zero to clear the logged fault.  Record this value and 
         call Retix technical support."
        ::= { baseUnit 3}

--
--  switchStakII.stakbus
--

stkbusIOPort  OBJECT-TYPE
        SYNTAX  INTEGER {
                io1(1),
                io2(2),
                notInstalled(3)
        }
        ACCESS  read-only
        STATUS  mandatory
        DESCRIPTION
        "Represents the IO port containing a StakbusII card.  
        Only one Stakbus card is permitted per unit"
        ::= { stakbus 1}


stkbusSpeed  OBJECT-TYPE
        SYNTAX  INTEGER 
        ACCESS  read-only
        STATUS  mandatory
        DESCRIPTION
        "Speed in Mbps of the installed Stakbus (StakbusII = 175Mbps)."
        ::= { stakbus 2}

stkbusNodeAddress  OBJECT-TYPE
        SYNTAX  INTEGER (0..15)
        ACCESS  read-only
        STATUS  mandatory
        DESCRIPTION
        "Address of the Stakbus interface as set on front panel dial
         (0..15)."
        ::= { stakbus 3}

stkbusRingOperationalStatus  OBJECT-TYPE
        SYNTAX  INTEGER {
                ringOperational(1),
                ringNotOperational(2),
                notInstalled(3)
        }
        ACCESS  read-only
        STATUS  mandatory
        DESCRIPTION
        "The status of the Retix Stakbus interface ring."
        ::= { stakbus 4}

--
--  switchStakII.VLAN.config
-- 

vlanEnableDisable  OBJECT-TYPE
        SYNTAX  INTEGER {
                disabled(1),
                enabled(2)
        }
        ACCESS  read-write
        STATUS  mandatory
        DESCRIPTION
        "Enables or Disables VLAN operation on this unit."
        ::= { vlanConfig  1 }

portVLANTable  OBJECT-TYPE
        SYNTAX  SEQUENCE OF PortVLANEntry
        ACCESS  not-accessible
        STATUS  mandatory
        DESCRIPTION
        "Table of port based VLAN configurations.  
         Entries (rows) are added to the table by issuing a 
         SET command with the EnableAdd value for the
         portVLANEntryEdit object.  The new row is created
         using the instantiations."
        ::= { vlanConfig  2 }

portVLANEntry  OBJECT-TYPE
        SYNTAX  PortVLANEntry
        ACCESS  not-accessible
        STATUS  mandatory
        DESCRIPTION
        "This is an entry in the portVLANTable."
        INDEX   { portVLANEntryPortID, portVLANEntryVLANID }
        ::= { portVLANTable 1 }

PortVLANEntry ::= SEQUENCE {
                portVLANEntryPortID  INTEGER,
                portVLANEntryVLANID  INTEGER,
                portVLANEntryEdit    INTEGER
        }

portVLANEntryPortID  OBJECT-TYPE
        SYNTAX  INTEGER 
        ACCESS  read-write
        STATUS  mandatory
        DESCRIPTION
        "Port number for this VLAN configuration."
        ::= { portVLANEntry  1 }

portVLANEntryVLANID  OBJECT-TYPE
        SYNTAX  INTEGER
        ACCESS  read-write
        STATUS  mandatory
        DESCRIPTION
        "VLAN number or ID."
        ::= { portVLANEntry 2 }


portVLANEntryEdit  OBJECT-TYPE
        SYNTAX  INTEGER {
                enableAdd(1),
                disable(2), 
                delete(3)
        }
        ACCESS  read-write
        STATUS  mandatory
        DESCRIPTION
        "When set to enableAdd(1) the instantiations will be used to 
         create a new table entry (row).  Existing entries can be 
         disabled(2) or deleted (3)."
        ::= { portVLANEntry  3 }

END
