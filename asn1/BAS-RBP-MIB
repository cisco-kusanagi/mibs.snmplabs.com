BAS-RBP-MIB DEFINITIONS ::= BEGIN

IMPORTS
	MODULE-IDENTITY, OBJECT-TYPE, 
	Counter32						FROM SNMPv2-SMI
	RowStatus						FROM SNMPv2-TC
	basRbp, BasChassisId, 
	BasSlotId, BasInterfaceId, 
	BasLogicalPortId				FROM BAS-MIB;

basRbpMib MODULE-IDENTITY
	LAST-UPDATED "9810071415Z"
	ORGANIZATION "Broadband Access Systems"
	CONTACT-INFO
		" Tech Support
		  Broadband Access Systems
		  201 Forest Street
		  Marlboro, MA  01752
		  U.S.A.
		  
		  508-485-8200
		  support@basystems.com"
	DESCRIPTION
		"This MIB module defines the configuration MIB objects
		 for a Broadband Access System Reliable Broadcast Protocol."
	::= { basRbp 1 }


basRbpConfig	OBJECT IDENTIFIER ::= { basRbpMib 1 }


--
-- ----------------------------------------------------------------------
--
-- Bas RBP Targets List of Slots accepting broadcasts
--
-- ----------------------------------------------------------------------
--
basRbpTargetTable OBJECT-TYPE
	SYNTAX		SEQUENCE OF BasRbpTargetEntry
	MAX-ACCESS	not-accessible
	STATUS		current
	DESCRIPTION
		"RBP target list MIB. List of slots that registered to
		 accept RBP broadcasts."
	::= { basRbpConfig 1 }

basRbpTargetEntry OBJECT-TYPE
	SYNTAX      BasRbpTargetEntry
	MAX-ACCESS  not-accessible
	STATUS      current
	DESCRIPTION
		"Slot receiving RBP broadcasts."
	INDEX		{ basRbpChassis,
				  basRbpSlot,
				  basRbpIf,
				  basRbpLPort,
				  basRbpTargetChassis,
				  basRbpTargetSlot,
				  basRbpTargetIf,
				  basRbpTargetLPort
				}
	::= { basRbpTargetTable 1 }

BasRbpTargetEntry ::= SEQUENCE {
		basRbpChassis		BasChassisId,
		basRbpSlot			BasSlotId,
		basRbpIf			BasInterfaceId,
		basRbpLPort			BasLogicalPortId,
		basRbpTargetChassis	BasChassisId,
		basRbpTargetSlot	BasSlotId,
		basRbpTargetIf		BasInterfaceId,
		basRbpTargetLPort	BasLogicalPortId,
		basRbpTargetStatus	RowStatus
	}

basRbpChassis OBJECT-TYPE
	SYNTAX		BasChassisId
	MAX-ACCESS	not-accessible
	STATUS		current
	DESCRIPTION
		"The BAS Chassis ID of the RBP host."
	::= { basRbpTargetEntry 1 }

basRbpSlot OBJECT-TYPE
	SYNTAX		BasSlotId
	MAX-ACCESS	not-accessible
	STATUS		current
	DESCRIPTION
		"The BAS Slot ID of the RBP host."
	::= { basRbpTargetEntry 2 }

basRbpIf OBJECT-TYPE
	SYNTAX		BasInterfaceId
	MAX-ACCESS	not-accessible
	STATUS		current
	DESCRIPTION
		"The BAS interface ID of the RBP host."
	::= { basRbpTargetEntry 3 }

basRbpLPort OBJECT-TYPE
	SYNTAX		BasLogicalPortId
	MAX-ACCESS	not-accessible
	STATUS		current
	DESCRIPTION
		"The BAS logical port ID of the RBP host."
	::= { basRbpTargetEntry 4 }

basRbpTargetChassis OBJECT-TYPE
	SYNTAX		BasChassisId
	MAX-ACCESS	read-create
	STATUS		current
	DESCRIPTION
		"The BAS Chassis ID of the target receiving RBP."
	::= { basRbpTargetEntry 5 }

basRbpTargetSlot OBJECT-TYPE
	SYNTAX		BasSlotId
	MAX-ACCESS	read-create
	STATUS		current
	DESCRIPTION
		"The BAS Slot ID of the target receiving RBP."
	::= { basRbpTargetEntry 6 }

basRbpTargetIf OBJECT-TYPE
	SYNTAX		BasInterfaceId
	MAX-ACCESS	read-create
	STATUS		current
	DESCRIPTION
		"The BAS interface ID of the target receiving RBP."
	::= { basRbpTargetEntry 7 }

basRbpTargetLPort OBJECT-TYPE
	SYNTAX		BasLogicalPortId
	MAX-ACCESS	read-create
	STATUS		current
	DESCRIPTION
		"The BAS logical port ID of the target receiving RBP."
	::= { basRbpTargetEntry 8 }

basRbpTargetStatus OBJECT-TYPE
	SYNTAX		RowStatus
	MAX-ACCESS	read-create
	STATUS		current
	DESCRIPTION
		"The row status object used to create and delete a 
		 conceptual row according to RowStatus conventions."
	::= { basRbpTargetEntry 9 }

--
-- ----------------------------------------------------------------------
--
-- Bas RBP Applications using RBP transport
--
-- ----------------------------------------------------------------------
--

basRbpAppTable OBJECT-TYPE
	SYNTAX      SEQUENCE OF BasRbpAppEntry
	MAX-ACCESS  not-accessible
	STATUS      current
	DESCRIPTION
		"Table of application using RBP."
	::= { basRbpConfig 2 }

basRbpAppEntry OBJECT-TYPE
	SYNTAX      BasRbpAppEntry
	MAX-ACCESS  not-accessible
	STATUS      current
	DESCRIPTION
		"Application using RBP."
	INDEX		{ 
				  basRbpAppChassis,
				  basRbpAppSlot,
				  basRbpAppIf,
				  basRbpAppLPort,
				  basRbpAppType
				}
	::= { basRbpAppTable 1 }

BasRbpAppEntry ::= SEQUENCE {
		basRbpAppChassis			BasChassisId,
		basRbpAppSlot				BasSlotId,
		basRbpAppIf					BasInterfaceId,
		basRbpAppLPort				BasLogicalPortId,
		basRbpAppType				INTEGER,
		basRbpAppBusy				INTEGER,
		basRbpAppBroadcastPktSent	Counter32,
		basRbpAppPktRcv				Counter32,
		basRbpAppUnicastPktSent		Counter32,
		basRbpAppAckRcv				Counter32,
		basRbpAppAckSent			Counter32,
		basRbpAppRetryCount			Counter32,
		basRbpAppRequestFailCount	Counter32
	}

basRbpAppChassis OBJECT-TYPE
	SYNTAX		BasChassisId
	MAX-ACCESS	not-accessible
	STATUS		current
	DESCRIPTION
		"The BAS Chassis ID of the RBP host."
	::= { basRbpAppEntry 1 }

basRbpAppSlot OBJECT-TYPE
	SYNTAX		BasSlotId
	MAX-ACCESS	not-accessible
	STATUS		current
	DESCRIPTION
		"The BAS Slot ID of the RBP host."
	::= { basRbpAppEntry 2 }

basRbpAppIf OBJECT-TYPE
	SYNTAX		BasInterfaceId
	MAX-ACCESS	not-accessible
	STATUS		current
	DESCRIPTION
		"The BAS interface ID of the RBP host."
	::= { basRbpAppEntry 3 }

basRbpAppLPort OBJECT-TYPE
	SYNTAX		BasLogicalPortId
	MAX-ACCESS	not-accessible
	STATUS		current
	DESCRIPTION
		"The BAS logical port ID of the RBP host."
	::= { basRbpAppEntry 4 }

basRbpAppType OBJECT-TYPE
	SYNTAX      INTEGER {
					rbpFwdType(1),
					rbpMcastType(2),
					rbpGFilterType(3)
				}
	MAX-ACCESS  read-only
	STATUS      current
	DESCRIPTION
		"Application sending/receiving the RBP updates."
	::= { basRbpAppEntry 5 }

basRbpAppBusy OBJECT-TYPE
	SYNTAX     INTEGER {
						busy(1),
						notBusy(2)
						}
	MAX-ACCESS  read-only
	STATUS      current
	DESCRIPTION
		"Is RBP busy sending a request for this application ?"
	DEFVAL { notBusy }
	::= { basRbpAppEntry 6 }

basRbpAppBroadcastPktSent OBJECT-TYPE
	SYNTAX   Counter32
	MAX-ACCESS  read-only
	STATUS      current
	DESCRIPTION
		"Broadcast RBPs sent for this application."
	::= { basRbpAppEntry 7 }

basRbpAppPktRcv OBJECT-TYPE
	SYNTAX   Counter32
	MAX-ACCESS  read-only
	STATUS      current
	DESCRIPTION
		"Counter of packets that RBP received for this application."
	::= { basRbpAppEntry 8 }

basRbpAppUnicastPktSent OBJECT-TYPE
	SYNTAX   Counter32
	MAX-ACCESS  read-only
	STATUS      current
	DESCRIPTION
		"Counter of unicast packets RBP sent fro this application."
	::= { basRbpAppEntry 9 }

basRbpAppAckRcv OBJECT-TYPE
	SYNTAX   Counter32
	MAX-ACCESS  read-only
	STATUS      current
	DESCRIPTION
		"Counter of acknowledgemenst RBP recieved for this application."
	::= { basRbpAppEntry 10 }

basRbpAppAckSent OBJECT-TYPE
	SYNTAX   Counter32
	MAX-ACCESS  read-only
	STATUS      current
	DESCRIPTION
		"Counter of acknowledgements sent for this application."
	::= { basRbpAppEntry 11 }

basRbpAppRetryCount OBJECT-TYPE
	SYNTAX      Counter32
	MAX-ACCESS  read-only
	STATUS      current
	DESCRIPTION
		"Counter of retries for this application."
	::= { basRbpAppEntry 12 }

basRbpAppRequestFailCount OBJECT-TYPE
	SYNTAX      Counter32
	MAX-ACCESS  read-only
	STATUS      current
	DESCRIPTION
		"Counter of failed requests for this application."
	::= { basRbpAppEntry 13 }

--
-- ----------------------------------------------------------------------
--
-- End
--
-- ----------------------------------------------------------------------
--

END
