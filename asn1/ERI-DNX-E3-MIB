ERI-DNX-E3-MIB DEFINITIONS ::= BEGIN

IMPORTS
	MODULE-IDENTITY, OBJECT-IDENTITY, OBJECT-TYPE, Integer32,
	Counter32, NOTIFICATION-TYPE
		FROM SNMPv2-SMI
    DisplayString
        FROM SNMPv2-TC
    eriMibs
        FROM ERI-ROOT-SMI
    devices, PortStatus, DecisionType, FunctionSwitch, 
    DataSwitch, LinkPortAddress, LinkCmdStatus, trapSequence, 
    OneByteField
        FROM ERI-DNX-SMC-MIB;

eriDNXE3MIB MODULE-IDENTITY 
      LAST-UPDATED    "200204080000Z"
      ORGANIZATION    "Eastern Research, Inc."
      CONTACT-INFO
                      "Customer Service
                Postal: Eastern Research, Inc.
                        225 Executive Drive
                        Moorestown, NJ 08057
                Phone:  +1-800-337-4374
                Email:  support@erinc.com"
      DESCRIPTION
              "The ERI Enterprise MIB Module for the DNX E3 Device."

  	::= { eriMibs 11 }

-- *************************************************************************
-- The enterprise OID will be { iso(1) org(3) dod(6) internet(1) private(4)
--                              enterprises(1) virent(644) eri(2) dnx (4) 
--                              devices(2), dnxE3(8) }

-- *************************************************************************
-- The E3 card is currently controlled via the Config or Diag groups.
-- The Configuration branch is used to perform all E3 Port and Link provisioning 
-- functions and the Diagnostic branch is used to run tests and view 
-- associated Statistics. 
-- *************************************************************************

dnxE3     OBJECT IDENTIFIER 	::= { devices 8 }
e3Config  OBJECT IDENTIFIER 	::= { dnxE3 1 }
e3Diag    OBJECT IDENTIFIER 	::= { dnxE3 2 }

-- *************************************************************************
-- This table is the E3 Port configuration table

e3PortConfigTable OBJECT-TYPE
        SYNTAX SEQUENCE OF E3PortConfigEntry
        MAX-ACCESS not-accessible
        STATUS current
        DESCRIPTION
            "This is the E3 Port Configuration table which consists
            of an entry for each of the E3 cards.  The total number of
            entries depends on the number of E3 cards in the Node."
        ::= { e3Config 1 }

e3PortConfigEntry OBJECT-TYPE
        SYNTAX E3PortConfigEntry
        MAX-ACCESS not-accessible
        STATUS current
        DESCRIPTION
            "The conceptual row of the E3 Port Configuration table. 
            A row in this table cannot be added or deleted, only modified."
        INDEX { e3PortCfgAddr }
        ::= { e3PortConfigTable 1 }

E3PortConfigEntry ::=
        SEQUENCE {
                e3PortCfgAddr       LinkPortAddress,  -- RO
                e3PortCfgResource   Integer32,        -- RO
                e3Timing            INTEGER,
                e3ShortCable        DecisionType,
                e3CmdStatus         LinkCmdStatus
                }

e3PortCfgAddr OBJECT-TYPE
        SYNTAX LinkPortAddress
        MAX-ACCESS read-only
        STATUS current
        DESCRIPTION
            "This number uniquely identifies a E3 port resource. 
            This number will be used throughout the system to identify 
            a unique resource."
        ::= { e3PortConfigEntry 1 }

e3PortCfgResource OBJECT-TYPE
        SYNTAX Integer32
        MAX-ACCESS read-only
        STATUS current
        DESCRIPTION
                "Uniquely identifies an E3 Port in the system.
                 This number is provided as key to allow the manager to 
                 map this entry to a corresponding Resource Table entry."
        ::= { e3PortConfigEntry 2 }

e3Timing OBJECT-TYPE
        SYNTAX INTEGER {
                internal(0),
                loop(1)
                }
        MAX-ACCESS read-write
        STATUS current
        DESCRIPTION
           "Determines the mode of E3 transmit timing provided by the 
           receive clock.  When internal, timing is provided by an on-board 
           oscillator."
        ::= { e3PortConfigEntry 3 }

e3ShortCable OBJECT-TYPE
        SYNTAX DecisionType
        MAX-ACCESS read-write
        STATUS current
        DESCRIPTION
           "Indicates the line build out of the E3 transmitter.  'Yes' when 
           attached to a cable less than 50 feet long."
        ::= { e3PortConfigEntry 4 }

e3CmdStatus OBJECT-TYPE
        SYNTAX LinkCmdStatus
        MAX-ACCESS read-write
        STATUS current
        DESCRIPTION
           "The command status for this link configuration row/record.
           The value used in a SET will be replaced by a response
           value in the GET RESPONSE indicating success or failure.
           		
            Default Response State used in GET RESPONSE Command
                ready-for-command (0)
                    initial default status for a row           
                    
            E3 Link Commands used in SET Command (1..199)            
                update-link-config(1),
                    Change existing Link Configuration
               		
            Response States used in GET RESPONSE Command (200..399)
                update-successful (201)
                    Link data has been successfully changed
                                		
            E3 Port Config Error Codes used in GET RESPONSE Command (400..699)
                err-general-link-config-error (400)
                    Unknown link configuration error occurred                
                err-invalid-link-command (403)
                    Unrecognized link command-action
                err-invalid-link-rem-loop (408)         
                    Remote Loop type not valid for e3 frame type
                err-invalid-link-ais (409)
                    Unrecognized e3 AIS selection
                err-device-in-standby (414)
                    Can't change config for designated Standby device
                err-data-locked-by-another-user (450)
                    Another administrative user is making changes to this
                    part of the system via a terminal session. Check Event
                    Log for user name.
                err-snmp-parse-failed (500)
                    Agent could not parse variable
                err-invalid-snmp-type (501)
                    Variable ASN type does not match Agent defined type 
                err-invalid-snmp-var-size (502)
                    Variable size is too big"                 		
        ::= { e3PortConfigEntry 5 }


-- *************************************************************************
-- This table is the E3 E1 Link configuration table

e3E1LinkConfigTable OBJECT-TYPE
        SYNTAX SEQUENCE OF E3E1LinkConfigEntry
        MAX-ACCESS not-accessible
        STATUS current
        DESCRIPTION
            "This is the E3 E1 Link Configuration table which consists
            of an entry for each of the card's 16 links.  The total number of
            entries depends on the number of E3 cards in the Node."
        ::= { e3Config 2 }

e3E1LinkConfigEntry OBJECT-TYPE
        SYNTAX E3E1LinkConfigEntry
        MAX-ACCESS not-accessible
        STATUS current
        DESCRIPTION
            "The conceptual row of the E3 E1 Link Configuration table. 
            A row in this table cannot be added or deleted, only modified."
        INDEX { e3E1CfgLinkAddr }
        ::= { e3E1LinkConfigTable 1 }

E3E1LinkConfigEntry ::=
        SEQUENCE {
                e3E1CfgLinkAddr     LinkPortAddress,  -- RO
                e3E1CfgResource     Integer32,        -- RO
                e3E1CfgLinkName     DisplayString,
                e3E1Status          PortStatus,
                e3E1Clear           INTEGER,                
                e3E1Framing         INTEGER,
                e3E1NetLoop         INTEGER,
                e3E1RAI             INTEGER,
                e3E1UnusedTSs       INTEGER,
                e3E1NationalBits    OneByteField,
                e3E1CfgCmdStatus    LinkCmdStatus,
                e3E1InterNational   OneByteField
                }

e3E1CfgLinkAddr OBJECT-TYPE
        SYNTAX LinkPortAddress
        MAX-ACCESS read-only
        STATUS current
        DESCRIPTION
            "This number uniquely identifies a E3 E1 link resource. 
            This number will be used throughout the system to identify 
            a unique resource."
        ::= { e3E1LinkConfigEntry 1 }

e3E1CfgResource OBJECT-TYPE
        SYNTAX Integer32
        MAX-ACCESS read-only
        STATUS current
        DESCRIPTION
                "Uniquely identifies an E3 E1 Channel in the system.
                 This number is provided as key to allow the manager to 
                 map this entry to a corresponding Resource Table entry."
        ::= { e3E1LinkConfigEntry 2 }

e3E1CfgLinkName OBJECT-TYPE
        SYNTAX DisplayString (SIZE(0..20))
        MAX-ACCESS read-write
        STATUS current
        DESCRIPTION
        	"This is the user friendly text name to identify the link."
        ::= { e3E1LinkConfigEntry 3 }

e3E1Status OBJECT-TYPE
        SYNTAX PortStatus
        MAX-ACCESS read-write
        STATUS current
        DESCRIPTION
           "Dictates the current status of the link, in-service or 
           out-of-service."
        ::= { e3E1LinkConfigEntry 4 }

e3E1Clear OBJECT-TYPE
        SYNTAX INTEGER {
        	disabled (0),
        	framed   (1),
        	unframed (2)
        	}
        MAX-ACCESS read-write
        STATUS current
        DESCRIPTION
           "Determines if the port supports E1 unframed clear mode."
        ::= { e3E1LinkConfigEntry 5 }

e3E1Framing OBJECT-TYPE
        SYNTAX INTEGER {
        	e1 (0),
        	e1Crc (1),
        	e1Cas (2),
        	e1CasCrc (3),
        	e1Unframed (4)
        	}
        MAX-ACCESS read-write
        STATUS current
        DESCRIPTION
           "Determines the type of framing used on the line.  
           When value of e3E1Clear is set to unframed (2), the only 
           valid framing option is: e1Unframed(4)."
        ::= { e3E1LinkConfigEntry 6 }

e3E1NetLoop OBJECT-TYPE
        SYNTAX FunctionSwitch
        MAX-ACCESS read-write
        STATUS current
        DESCRIPTION
           "Determines whether or not the module should respond to loop 
           diagnostic commands received from the network supplier. Select 
           'enable' unless the commands are to be passed to another E3 
           device."
        ::= { e3E1LinkConfigEntry 7 }

e3E1RAI OBJECT-TYPE
        SYNTAX DecisionType
        MAX-ACCESS read-write
        STATUS current
        DESCRIPTION
           "Causes the module to discard data and send a yellow alarm if it
           is in a red alarm condition after a 3 second period. 'Yes' must
           be chosen if the network supplier is a common carrier, such as a 
           telephone company."
        ::= { e3E1LinkConfigEntry 8 }

e3E1UnusedTSs OBJECT-TYPE
        SYNTAX INTEGER {
        	busy (0),
        	idle (1)
        	}
        MAX-ACCESS read-write
        STATUS current
        DESCRIPTION
           "Determines the whether the code that will be transmitted over 
           the unused links will be 'idle' or 'busy' (all 1's)."
        ::= { e3E1LinkConfigEntry 9 }

e3E1NationalBits OBJECT-TYPE
        SYNTAX OneByteField
        MAX-ACCESS read-write
        STATUS current
        DESCRIPTION
           "Enables E1 National S-bits to be set to zero or one.
           This single byte field can be changed to set the values 
           of the E1 NFA byte in odd frames as depicted below:
           
              sa8 sa7 sa6 sa5 sa4 reserved bits
              --- --- --- --- --- -------------
              1    1   1   1   1   0   0   0      = F8 (default)
              
           Values should be entered in Hex.  If reserved bits are changed,
           an error code (427) will be returned in the command status.
           "
        ::= { e3E1LinkConfigEntry 10 }

e3E1CfgCmdStatus OBJECT-TYPE
        SYNTAX LinkCmdStatus 
        MAX-ACCESS read-write
        STATUS current
        DESCRIPTION
           "The command status for this link configuration row/record.
           The value used in a SET will be replaced by a response
           value in the GET RESPONSE indicating success or failure.
           		
            Default Response State used in GET RESPONSE Command
                ready-for-command (0)
                    initial default status for a row           
                    
            E3-E1 Link Commands used in SET Command (1..199)            
                update(1)
                    Change existing Link Configuration
                inServiceAll (7)
                    Change Link Status to in-service for all 16 links.
                copyToAll (9)
                    Copy E1 Link configuration to all other links 
                    within the same device
                outOfServiceAll (12)
                    Change Link Status to out-of-service for all 16 links.
               		
            Response States used in GET RESPONSE Command (100..199)
                update-successful (101)
                    Link data has been successfully changed
                insvc-successful (107)
                    All Links have been successfully placed In Service
                copy-successful (109)
                    E1 Link data has been successfully copied to other links
                oos-successful (112)
                    All Links have been successfully placed Out of Service
                                		
            E3-E1 Link Config Error Codes used in GET RESPONSE Command (400..699)
                err-general-link-config-error (400)
                    Unknown link configuration error occurred                
                err-invalid-link-status (401)
                    Unrecognized link status setting
                err-invalid-link-framing (402)         
                    Line framing type not valid for link type
                err-invalid-link-command (403)
                    Unrecognized link command-action
                err-invalid-network-loop (410)
                    Unrecognized network loop setting
                err-invalid-yellow-alrm (411)
                    Unrecognized yellow alarm setting
                err-invalid-idle-code (413)
                    Unrecognized idle code
                err-device-in-standby (414)
                    Can't change config for designated Standby device
                err-invalid-link-bits (427)
                    Reserved E1 bits must be left at zero.
                err-data-locked-by-another-user (450)
                    Another administrative user is making changes to this
                    part of the system via a terminal session. Check Event
                    Log for user name           		
                err-snmp-parse-failed (500)
                    Agent could not parse variable
                err-invalid-snmp-type (501)
                    Variable ASN type does not match Agent defined type 
                err-invalid-snmp-var-size (502)
                    Variable size is too big"                 		
        ::= { e3E1LinkConfigEntry 11 }

e3E1InterNational OBJECT-TYPE
        SYNTAX OneByteField
        MAX-ACCESS read-write
        STATUS current
        DESCRIPTION
           "Enables InterNational S(i) Spare bit to be set to zero or one.
           This single byte field can be changed to set the values 
           of the Bit 1 of TS0 G.704 frame as depicted below:
           
                    reserved bits        S(i)
              -------------------------- -----
              0   0   0   0   0   0   0   1      = 01 (default)
              
           Values should be entered in Hex.  If reserved bits are changed,
           an error code (427) will be returned in the command status.
           "
        ::= { e3E1LinkConfigEntry 12 }
       
-- *************************************************************************
-- This table is the E3 Framer Status Display table

e3FramerStatusTable OBJECT-TYPE
        SYNTAX SEQUENCE OF E3FramerStatusEntry
        MAX-ACCESS not-accessible
        STATUS current
        DESCRIPTION
            "This is the E-3 Framer Status table which consists of a single
            entry for each card's Framer Display.  The total number of
            entries depends on the number of E3 cards in the nest."
        ::= { e3Diag 1 }

e3FramerStatusEntry OBJECT-TYPE
        SYNTAX E3FramerStatusEntry
        MAX-ACCESS not-accessible
        STATUS current
        DESCRIPTION
            "The conceptual row of the Framer table. 
            A row in this table cannot be added or deleted, only modified."
        INDEX { e3FramerStatusAddr }
        ::= { e3FramerStatusTable 1 }

E3FramerStatusEntry ::=
        SEQUENCE {
                e3FramerStatusAddr             LinkPortAddress,  -- RO
                e3FramerStatusResource         Integer32,        -- RO
                e3FramerStatusState            INTEGER,
                e3FramerStatusErrSecs		   Counter32,
                e3FramerStatusOOFErrs          Counter32,
                e3FramerStatusAISSecs		   Counter32,
                e3FramerStatusFramingErrs	   Counter32,
                e3FramerStatusLoop             INTEGER,			 --RW
                e3FramerStatusBertState        INTEGER,          --RW
                e3FramerStatusBertSecs         Counter32,
                e3FramerStatusBertErrSecs      Counter32,
                e3FramerStatusBertSync         DataSwitch,
                e3FramerStatusLiuRLOSs         Counter32,
                e3FramerStatusLiuRLOLs         Counter32,
                e3FramerStatusLiuLCVs          Counter32,
                e3FramerStatusInsErrMode       INTEGER,          -- RW              
              	e3FramerStatusCmdStatus        INTEGER           -- RW              
                }

e3FramerStatusAddr OBJECT-TYPE
        SYNTAX LinkPortAddress
        MAX-ACCESS read-only
        STATUS current
        DESCRIPTION
            "This number uniquely identifies an e3 Framer resource. 
            This number will be used throughout the system to identify 
            a unique resource."
        ::= { e3FramerStatusEntry 1 }

e3FramerStatusResource OBJECT-TYPE 
        SYNTAX Integer32
        MAX-ACCESS read-only
        STATUS current
        DESCRIPTION
            "This number uniquely identifies an e3 Framer link resource. 
            This number is provided as key to allow the manager to map this
            entry to a corresponding Resource Table Entry."
        ::= { e3FramerStatusEntry 2 }

e3FramerStatusState OBJECT-TYPE
        SYNTAX INTEGER {
                ok  (0),
                ais (8),              -- bit 3
                lof (32),             -- bit 5
                los (64),             -- bit 6
                errors (2147483647)   -- all
                }
        MAX-ACCESS read-only
        STATUS current
        DESCRIPTION
           "Determines the current line condition status of the Framer.
                ok       (0)          - No Alarm
                ais      (8)          - Sending All Ones
                lof      (32)         - Loss/Out of Frame
                los      (64)         - Loss of Signal
                errors   (2147483647) - Multiple Errors displays raw bit field value
           "
       ::= { e3FramerStatusEntry 3 }

e3FramerStatusErrSecs OBJECT-TYPE
        SYNTAX Counter32
        MAX-ACCESS read-only
        STATUS current
        DESCRIPTION
            "This is the total number of errored seconds."
        ::= { e3FramerStatusEntry 4 } 

e3FramerStatusOOFErrs OBJECT-TYPE
        SYNTAX Counter32
        MAX-ACCESS read-only
        STATUS current
        DESCRIPTION
            "This is the number of seconds an Out Of Frame alignment error was declared."
        ::= { e3FramerStatusEntry 5 } 

e3FramerStatusAISSecs OBJECT-TYPE
        SYNTAX Counter32
        MAX-ACCESS read-only
        STATUS current
        DESCRIPTION
            "This is the number of seconds an Alarm Indication Signal was declared."
        ::= { e3FramerStatusEntry 6 } 

e3FramerStatusFramingErrs OBJECT-TYPE
        SYNTAX Counter32
        MAX-ACCESS read-only
        STATUS current
        DESCRIPTION
            "Indicates the number of Framing Errors."
        ::= { e3FramerStatusEntry 7 } 

e3FramerStatusLoop OBJECT-TYPE
        SYNTAX INTEGER {
                off  (0),
                e3-local (1),              
                e3-line (3),             
                e3-payload (4),             
                liu-local(37),
                liu-line(38)
                }

        MAX-ACCESS read-write
        STATUS current
        DESCRIPTION
            "The Loop status for the Framer as well as the Line Interface Unit."
        ::= { e3FramerStatusEntry 8 } 

e3FramerStatusBertState OBJECT-TYPE
        SYNTAX INTEGER { 
                bertOff (50),
                framed-2047 (61),
                framed-2-15th-inv(62)
        }
        MAX-ACCESS read-write
        STATUS current
        DESCRIPTION
            " Indicates the Bert State.
                bertOff (50)      - Turns the BERT off
                framed-2047       - Framed 2047
                framed-2-15th     - Framed 2^15-1 Inverted 
            "
        ::= { e3FramerStatusEntry 9 } 

e3FramerStatusBertSecs OBJECT-TYPE
        SYNTAX Counter32
        MAX-ACCESS read-only
        STATUS current
        DESCRIPTION
            "Indicates the Bert Duration in Seconds."
        ::= { e3FramerStatusEntry 10 } 

e3FramerStatusBertErrSecs OBJECT-TYPE
        SYNTAX Counter32
        MAX-ACCESS read-only
        STATUS current
        DESCRIPTION
            "Indicates the number of errored seconds since the Bert is running."
        ::= { e3FramerStatusEntry 11 } 
    
e3FramerStatusBertSync OBJECT-TYPE
        SYNTAX DataSwitch
        MAX-ACCESS read-only
        STATUS current
        DESCRIPTION
            "Indicates the Bert Synchronization as being ON or OFF."
        ::= { e3FramerStatusEntry 12 }        

e3FramerStatusLiuRLOSs OBJECT-TYPE
        SYNTAX Counter32
        MAX-ACCESS read-only
        STATUS current
        DESCRIPTION
            "This is the number of seconds recorded for Receive Loss of Signal."
        ::= { e3FramerStatusEntry 13 } 

e3FramerStatusLiuRLOLs OBJECT-TYPE
        SYNTAX Counter32
        MAX-ACCESS read-only
        STATUS current
        DESCRIPTION
            "This is the number of seconds recorded for Receive Loss of Lock."
        ::= { e3FramerStatusEntry 14 } 

e3FramerStatusLiuLCVs OBJECT-TYPE
        SYNTAX Counter32
        MAX-ACCESS read-only
        STATUS current
        DESCRIPTION
            "This is the number of seconds recorded for the Line Code Violation."
        ::= { e3FramerStatusEntry 15 } 


e3FramerStatusInsErrMode OBJECT-TYPE
        SYNTAX INTEGER {
--                multiframe-align (1),
                frame-alignment (2)
--                loss-of-signal (3),
--                allErrors (4)
                }
        MAX-ACCESS read-write
        STATUS current
        DESCRIPTION
           "Determines the status of the current Insert Error mode associated 
           with the framer. In order to insert an error, the e3FramerStatusCmdStatus 
           must be sent in a SET PDU with a value of 'insertError'."
       ::= { e3FramerStatusEntry 16 }

e3FramerStatusCmdStatus OBJECT-TYPE
        SYNTAX INTEGER {
    -- Initial default status for a row
            ready-for-command (0),
    -- Action States used in SET Command (1..99)
            update (1),
            clearErrors (14),
            insertError (16),
                                
    -- Response States used in GET RESPONSE Command (100..199)
            update-successful (101),
            clear-successful (114),
            insert-successful (116),
                                
    -- Test Error Codes used in GET RESPONSE Command (200..799)
            err-general-framer-error (200),
            err-invalid-loop-type (202),
            err-invalid-bert-type (203),
            err-test-in-progress (205),
            err-field-cannot-be-set (206),
            err-invalid-command (208),
            err-snmp-parse-failed(500),
            err-invalid-snmp-type(501),
            err-invalid-snmp-var-size(502) 
            }
        MAX-ACCESS read-write
        STATUS current
        DESCRIPTION
            "This is the command status for the Framer Row.
           The value used in a SET will be replaced by a response
           value in the GET RESPONSE indicating success or failure.

            Default Response State used in GET RESPONSE Command
                ready-for-command (0)
                    initial default status for a row           
                    
            E3 Framer Action Commands used in SET Command (1..99)            
                update (1)
                    Can be used optionally when activating loops and berts
                    in order to get status code back in response
                clearErrors (14)
                    Resets all error counters and bert test time to zero
                insertError (16)
                    Inserts the current invalid bit pattern as indicated
                    by the value of e3FramerStatusCmdStatus. 
                                
            Response States used in GET RESPONSE Command (100..199)
                update-successful (101)
                    Test action has been successfully performed
                clear-successful (114)
                    Error counts have been successfully cleared
                insert-successful (116)
                    Errored bits have been successfully inserted
                                
            The Error Codes used in GET RESPONSE Command (200..799)
                err-general-framer-error (200)
                    Unknown request error occurred.
                err-invalid-loop-type (202)
                    Unrecognized loop selection
                err-invalid-bert-type (203)
                    Unrecognized bert selection
                err-test-in-progress (205)
                    Requested action cannot be performed during bert
                err-field-cannot-be-set (206)
                    Read-only field was included in SET request
                err-invalid-command (208)
                    Unrecognized framer Command requested                    
                err-snmp-parse-failed (500)
                    Agent could not parse variable
                err-invalid-snmp-type (501)
                    Variable ASN type does not match Agent defined type 
                err-invalid-snmp-var-size (502)
                    Variable size is too big" 
        ::= { e3FramerStatusEntry 17 } 
        
-- *************************************************************************

dnxE3Enterprise OBJECT-IDENTITY
      STATUS current
      DESCRIPTION "ERI DNX E3 Enterprise for Alarms/Events"
    ::= { dnxE3 0 }

e3PortConfigTrap NOTIFICATION-TYPE
        OBJECTS {
            trapSequence,
            e3PortCfgAddr,
            e3CmdStatus
            }
        STATUS current
        DESCRIPTION
              	"This trap is used to notify a NMS that a user has updated 
              	the configuration for a given E3 Port entry."
        ::= { dnxE3Enterprise 1 }

e3E1ConfigTrap NOTIFICATION-TYPE
        OBJECTS {
            trapSequence,
            e3E1CfgLinkAddr,
            e3E1CfgCmdStatus
            }
        STATUS current
        DESCRIPTION
              	"This trap is used to notify a NMS that a user has updated 
              	the Link configuration for a given E3-E1 channel entry."
        ::= { dnxE3Enterprise 2 }
               
END

-- *************************************************************************
--
--  MIB:     ERI-DNX-APS-MIB
--
--  Purpose: This is the Eastern Research Automatic Protection Switching (APS)
--           MIB for the DNX product. This supports APS Device level
--           configuration & status via SNMP.
--
--  Contact: Eastern Research Inc. 1-800-337-4374  Email: support@erinc.com
--
-- *************************************************************************
