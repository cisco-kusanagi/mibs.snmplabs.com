UMSAGENT-MIB DEFINITIONS ::= BEGIN

IMPORTS
   OBJECT-TYPE
      FROM RFC-1212

   TRAP-TYPE
      FROM RFC-1215

   ibmpsgAgent,
   Boolean, Uint8, Sint8, Uint16, Sint16, Uint32,
   Sint32, Uint64, Sint64, Real32, Real64, String, Datetime
      FROM UMS-MIB;

iBMPSGHTTPConfigurationTable OBJECT-TYPE
   SYNTAX         SEQUENCE OF IBMPSGHTTPConfigurationEntry
   ACCESS         not-accessible
   STATUS         mandatory
   DESCRIPTION    ""
   REFERENCE      "IBMPSG_HTTPConfiguration"
::= { ibmpsgAgent 2 }

iBMPSGHTTPConfigurationEntry OBJECT-TYPE
   SYNTAX         IBMPSGHTTPConfigurationEntry
   ACCESS         not-accessible
   STATUS         mandatory
   DESCRIPTION    ""
   INDEX          { iBMPSGHTTPConfigurationKeyIndex }
::= { iBMPSGHTTPConfigurationTable 1 }

IBMPSGHTTPConfigurationEntry ::= SEQUENCE
{
   iBMPSGHTTPConfigurationKeyIndex String,
   iBMPSGHTTPConfigurationSettingId String,
   iBMPSGHTTPConfigurationPort Uint16
}

iBMPSGHTTPConfigurationKeyIndex OBJECT-TYPE
   SYNTAX         String
   ACCESS         read-write
   STATUS         mandatory
   DESCRIPTION    ""
   REFERENCE      "IBMPSG_HTTPConfiguration.KeyIndex"
::= { iBMPSGHTTPConfigurationEntry 1 }

iBMPSGHTTPConfigurationSettingId OBJECT-TYPE
   SYNTAX         String
   ACCESS         read-write
   STATUS         mandatory
   DESCRIPTION    ""
   REFERENCE      "IBMPSG_HTTPConfiguration.SettingId"
::= { iBMPSGHTTPConfigurationEntry 2 }

iBMPSGHTTPConfigurationPort OBJECT-TYPE
   SYNTAX         Uint16
   ACCESS         read-write
   STATUS         mandatory
   DESCRIPTION    ""
   REFERENCE      "IBMPSG_HTTPConfiguration.Port"
::= { iBMPSGHTTPConfigurationEntry 3 }

END
