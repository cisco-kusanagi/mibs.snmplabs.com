-- *****************************************************************
-- ciscoWanVismRtpConnCapabilities MIB
--
-- AGENT-CAPABILITIES mib for CISCO-WAN-RTP-CONN-MIB in the VISM product
--
-- Copyright(c) 2001 by Cisco Systems,Inc.
--
-- Author: Siana Smith
-- *****************************************************************

CISCO-WAN-VISM-RTP-CONN-CAPABILITY DEFINITIONS ::= BEGIN

IMPORTS
        MODULE-IDENTITY,
        Integer32
                FROM SNMPv2-SMI
        AGENT-CAPABILITIES
                FROM SNMPv2-CONF
        ciscoWanAgentCapability
                FROM CISCOWAN-SMI;

cwVismRtpConnCapability MODULE-IDENTITY
        LAST-UPDATED    "200108220000Z"
        ORGANIZATION    "Cisco Systems, Inc."
        CONTACT-INFO
                "       Cisco Systems
                        Customer Service

                Postal: 170 W Tasman Drive
                        San Jose, CA  95134
                        USA

                        Tel: +1 800 553-NETS

                E-mail: cs-vism@cisco.com"
        DESCRIPTION
                "The Agent Capabilities for CISCO-WAN-RTP-CONN-MIB."

        REVISION        "200103150000Z"
        DESCRIPTION
                "Initial version of this MIB module"
        ::= { ciscoWanAgentCapability 337 }

cwVismRtpConnCapabilityV2R00 AGENT-CAPABILITIES
    PRODUCT-RELEASE      "VISM Release2.1"
    STATUS               current
    DESCRIPTION          "CISCO-WAN-RTP-CONN-MIB Capabilities"

    SUPPORTS CISCO-WAN-RTP-CONN-MIB
    INCLUDES { vismRtpConnGroup,
               vismRtpBearerStatsGroup }

        VARIATION   vismRtpConnNum
        SYNTAX      Integer32 (1..248)
        DESCRIPTION "Valid range is 1 - 248."

        VARIATION   vismRtpEndptNum
        SYNTAX      Integer32 (1..248)
        DESCRIPTION "Valid range is 1 - 248."

        VARIATION   vismRtpLocPort
        SYNTAX      Integer32 (49648..50142)
        DESCRIPTION "Valid range is 49648 - 50142."

        VARIATION   vismRtpRmtPort
        SYNTAX      Integer32 (49648..50142)
        DESCRIPTION "Valid range is 49648 - 50142."

        VARIATION   vismRtpVadTimer
        SYNTAX      Integer32 (255..65535)
        DESCRIPTION "Valid range is 255 - 65535."

        VARIATION   vismRtpRowStatus
        SYNTAX INTEGER {
                       active(1),
                       createAndGo(4), 
                       destroy(6)
                       }
        DESCRIPTION "only supports active, createAndGo and Destroy"

    ::= { cwVismRtpConnCapability 1 }

END
