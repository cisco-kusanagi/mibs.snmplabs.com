-- Copyright 1995 by 3Com Corporation.  All rights reserved.
-- MIB file name:  startek
-- available in these 3Com devices:  Startek Token Ring Hubs
-- For support or more info, check 3Com's web page at http://www.3com.com



        -- 3Com Startek Division private MIB 
        -- Date: May 25, 1994
	--
	-- 3Com, Inc.
	-- 71 Lyman Street
	-- Northboro, MA  01532
	-- (800) NET-3COM




          STARTEK-PRIVATE-MIB DEFINITIONS ::= BEGIN

	      IMPORTS
    		enterprises, OBJECT-TYPE, TimeTicks, Opaque, Counter, IpAddress
     			FROM RFC1155-SMI
			DisplayString FROM SNMPv2-TC;


	    startek       OBJECT IDENTIFIER ::= { enterprises 260 }
            products      OBJECT IDENTIFIER ::= { startek 1 }
            maintenance   OBJECT IDENTIFIER ::= { startek 2 }
            fSeries       OBJECT IDENTIFIER ::= { products 2 }
            stackable     OBJECT IDENTIFIER ::= { products 3 }




           m828Series    OBJECT IDENTIFIER ::= { products 1 }

           m828Hubs      OBJECT IDENTIFIER ::= { m828Series 1 }

           -- m828Hubs Group

          m828HubNumber OBJECT-TYPE
              SYNTAX  INTEGER
              ACCESS  read-only
              STATUS  mandatory
              DESCRIPTION
                      "The number of items in hub table."
              ::= { m828Hubs 1 }

          m828HubTable OBJECT-TYPE
              SYNTAX  SEQUENCE OF M828hubTableEntry
              ACCESS  not-accessible
              STATUS  mandatory
              DESCRIPTION     
                      "A table which maintains a list of all of the intelligent
                       m828 series hubs on the ring being managed by the 
                       addressed agent. This table is indexed by the RS485 OOB 
                       address of the m828 series intelligent hubs."
              ::= { m828Hubs 2 }

          m828HubTableEntry        OBJECT-TYPE
              SYNTAX  M828hubTableEntry
              ACCESS  not-accessible
              STATUS  mandatory
              DESCRIPTION
                     "An entry in the m828HubTable."
              INDEX   { m828HubTableIndex }
              ::= { m828HubTable 1 }

          M828hubTableEntry ::=
              SEQUENCE  {
                      m828HubTableIndex        INTEGER,
                      m828HubModel             INTEGER,
                      m828Hub485Address        OCTET STRING,
                      m828HubRiFTolSw          INTEGER,
                      m828HubRiFTolState       INTEGER,
                      m828HubRiMask            INTEGER,
                      m828HubRiPhDet           INTEGER,
                      m828HubRiNsrtStatus      INTEGER,
                      m828HubRiBcnRemStatus    INTEGER,
                      m828RiNeighborType       INTEGER,
                      m828RiNeighborAddr       OCTET STRING,
                      m828RiTimeStamp          TimeTicks,
                      m828HubRoFTolSw          INTEGER,
                      m828HubRoFTolState       INTEGER,
                      m828HubRoMask            INTEGER,
                      m828HubRoPhDet           INTEGER,
                      m828HubRoNsrtStatus      INTEGER,
                      m828HubRoBcnRemStatus    INTEGER,
                      m828RoNeighborType       INTEGER,
                      m828RoNeighborAddr       OCTET STRING,
                      m828RoTimeStamp          TimeTicks,
                      m828HubDataRateSwitch    INTEGER,
                      m828HubDataRateState     INTEGER,
                      m828HubDataRateTimeStamp TimeTicks,
                      m828HubMgmtStatus        INTEGER,
                      m828HubProxyAgentID      OCTET STRING,
                      m828HubCodeVersion       OCTET STRING,
                      m828HubRawCommandData    OCTET STRING
                      }

          m828HubTableIndex        OBJECT-TYPE
              SYNTAX  INTEGER
              ACCESS  read-only
              STATUS  mandatory
              DESCRIPTION
                      "The index for this hub entry."
              ::= { m828HubTableEntry 1 }

          m828HubModel     OBJECT-TYPE
              SYNTAX  INTEGER {
                      model-4(1),     -- Star-Tek m828AT model 4  
                      model-5(2),     -- Star-Tek m828AT model 5 
                      model-6(3),     -- Star-Tek m828AT model 6
                      model-7(4)      -- Star-Tek m828AT model 7
                      }
              ACCESS  read-only
              STATUS  mandatory
              DESCRIPTION     
                      "The model number of the m828 series hub being managed."
              ::= { m828HubTableEntry 2 }

          m828Hub485Address        OBJECT-TYPE
              SYNTAX  OCTET STRING (SIZE (2..2))
              ACCESS  read-only
              STATUS  mandatory
              DESCRIPTION
                      "The 4 hex digit address used on the RS485 serial OOB 
                       management channel."
              ::=     { m828HubTableEntry 3 }

          m828HubRiFTolSw  OBJECT-TYPE
              SYNTAX  INTEGER {
                          off(1),
                          on(2)
                  }
              ACCESS  read-only
              STATUS  mandatory
              DESCRIPTION
                      "The status of the Ring In fault tolerance switch on the 
                       front panel of the hub." 
              ::= { m828HubTableEntry 4 }

          m828HubRiFTolState       OBJECT-TYPE
              SYNTAX  INTEGER {
                          off(1),
                          on(2)
                  }
              ACCESS  read-write
              STATUS  mandatory
              DESCRIPTION
                      "This parameter controls the Ring In (RI) fault tolerance 
                       behavior. The default value for this parameter is the 
                       same setting as is present for m828HubRiFTolSw. SETTING 
                       this parameter overrides the value derived from 
                       m828HubRiFTolSw.  Off(1) means that phantom currentis not
                       used on the corresponding RI interface as a condition for
                       main ring link insertion. On (2) means that phantom 
                       current is used on the corresponding RI interface as a 
                       condition for main ring link insertion. The preffered 
                       setting for this parameter is on (2)."
              ::= { m828HubTableEntry 5 }

          m828HubRiMask    OBJECT-TYPE
              SYNTAX  INTEGER {
                          isolate(1),
                          enable(2)
                  }
              ACCESS  read-write
              STATUS  mandatory
              DESCRIPTION
                      "Administrative status for this Ring In port. By
                       setting this parameter, a remote manager can control
                       the partitioning of this port."
              ::= { m828HubTableEntry 6 }

          m828HubRiPhDet   OBJECT-TYPE
              SYNTAX  INTEGER {
                          noPhantom(1),
                          phantDetected(2)
                  }
              ACCESS  read-only
              STATUS  mandatory
              DESCRIPTION
                      "This parameter describes the phantom detect status for
                       this Ring In port."
              ::= { m828HubTableEntry 7 }

          m828HubRiNsrtStatus  OBJECT-TYPE
              SYNTAX  INTEGER {
                          bypassed(1),
                          inserted(2)
                  }
              ACCESS  read-only
              STATUS  mandatory
              DESCRIPTION
                      "Insertion status for this Ring In port."
              ::= { m828HubTableEntry 8 }

          m828HubRiBcnRemStatus    OBJECT-TYPE
              SYNTAX  INTEGER {
                          ok(1),
                          autoIsolated(2)
                  }
              ACCESS  read-only
              STATUS  mandatory
              DESCRIPTION
                      "This parameter describes the result of any automatic 
                       beacon removal operations performed by the agent on this
                       port. Automatic beacon removal operations consist of 
                       agent-initiated isolation of a lobe port in order to 
                       remove the cause of a persistent beaconing condition." 
              ::= { m828HubTableEntry 9 }

          m828RiNeighborType    OBJECT-TYPE
              SYNTAX  INTEGER {
                          series828(1),
                          fSeries(2),
                          tokenRingMAC(3),
                          none(4),
                          stackable(5)
                  }
              ACCESS  read-only
              STATUS  mandatory
              DESCRIPTION
                     "This parameter indicates the type of nearest neighbor
                      on the Ring In port."
              ::= { m828HubTableEntry 10 }

          m828RiNeighborAddr    OBJECT-TYPE
              SYNTAX  OCTET STRING (SIZE (2..6))
              ACCESS  read-only
              STATUS  mandatory
              DESCRIPTION
                     "The address of the nearest neighbor on the Ring In port."
              ::= { m828HubTableEntry 11 }

          m828RiTimeStamp    OBJECT-TYPE
              SYNTAX  TimeTicks
              ACCESS  read-only
              STATUS  mandatory
              DESCRIPTION
                      "The time the status of Ring In (was) last changed."
              ::= { m828HubTableEntry 12 }

          m828HubRoFTolSw  OBJECT-TYPE
              SYNTAX  INTEGER {
                          off(1),
                          on(2)
                   }
              ACCESS  read-only
              STATUS  mandatory
              DESCRIPTION
                      "The state of the Ring Out Fault Tolerance switch on
                       the front panel of the unit."
              ::= { m828HubTableEntry 13 }

          m828HubRoFTolState       OBJECT-TYPE
              SYNTAX  INTEGER {
                          off(1),
                          on(2)
                   }
              ACCESS  read-write
              STATUS  mandatory
              DESCRIPTION
                      "This parameter controls the Ring Out(RO) fault tolerance 
                       behavior. The default value for this parameter is the 
                       same setting as is present for m828HubRoFTolSw. SETTING 
                       this parameter overrides the value derived from 
                       m828HubRoFTolSw.  Off(1) means that phantom currentis not
                       used on the corresponding RO interface as a condition for
                       main ring link insertion. On (2) means that phantom 
                       current is used on the corresponding RO interface as a 
                       condition for main ring link insertion. The preffered 
                       setting for this parameter is on (2)."
              ::= { m828HubTableEntry 14 }

          m828HubRoMask    OBJECT-TYPE
              SYNTAX  INTEGER {
                          isolate(1),
                          enable(2)
                   }
              ACCESS  read-write
              STATUS  mandatory
              DESCRIPTION
                      "Administrative status for this Ring Out port. By
                       setting this parameter, a remote manager can control
                       the partitioning of this port."
              ::= { m828HubTableEntry 15 }

          m828HubRoPhDet   OBJECT-TYPE
              SYNTAX  INTEGER {
                          wireFault(1),
                          phantOk(2)      --corresponds to 
                                          --forward ok
                   }
              ACCESS  read-only
              STATUS  mandatory
              DESCRIPTION
                      "This parameter describes the phantom detect status for
                       this Ring Out port."
              ::= { m828HubTableEntry 16 }

          m828HubRoNsrtStatus      OBJECT-TYPE
              SYNTAX  INTEGER {
                          bypassed(1),
                          inserted(2)
                   }
              ACCESS  read-only
              STATUS  mandatory
              DESCRIPTION
                      "Insertion status for this Ring Out port."
              ::= { m828HubTableEntry 17 }

          m828HubRoBcnRemStatus    OBJECT-TYPE
              SYNTAX  INTEGER {
                          ok(1),
                          autoIsolated(2)
                   }
              ACCESS  read-only
              STATUS  mandatory
              DESCRIPTION
                      "This parameter describes the result of any automatic 
                       beacon removal operations performed by the agent on this
                       port. Automatic beacon removal operations consist of 
                       agent-initiated isolation of a lobe port in order to 
                       remove the cause of a persistent beaconing condition." 
              ::= { m828HubTableEntry 18 }

          m828RoNeighborType    OBJECT-TYPE
              SYNTAX  INTEGER {
                          series828(1),
                          fSeries(2),
                          tokenRingMAC(3),
                          none(4),
                          stackable(5)
                  }
              ACCESS  read-only
              STATUS  mandatory
              DESCRIPTION
                      "This parameter indicates the type of nearest neighbor
                     on the Ring Out port."
              ::= { m828HubTableEntry 19 }

          m828RoNeighborAddr    OBJECT-TYPE
              SYNTAX  OCTET STRING (SIZE (2..6))
              ACCESS  read-only
              STATUS  mandatory
              DESCRIPTION
                      "The address of the nearest neighbor on the Ring Out
                       port."
              ::= { m828HubTableEntry 20 }

          m828RoTimeStamp    OBJECT-TYPE
              SYNTAX  TimeTicks
              ACCESS  read-only
              STATUS  mandatory
              DESCRIPTION
                      "The time the status of Ring Out (was) last changed."
              ::= { m828HubTableEntry 21 }

          m828HubDataRateSwitch    OBJECT-TYPE
              SYNTAX  INTEGER {
                          s4Mbps(1),
                          s16Mbps(2),
                          noSwitch(3)
                   }
              ACCESS  read-only
              STATUS  mandatory
              DESCRIPTION
                      "Setting of this parameter changes the data rate of
                       this unit.  A value of noSwitch(3) indicates that the
                       setting of the data rate is not available on this unit."
              ::= { m828HubTableEntry 22 }

          m828HubDataRateState     OBJECT-TYPE
              SYNTAX  INTEGER {
                          s4Mbps(1),
                          s16Mbps(2),
                          autoConfig(3)
                   }
              ACCESS  read-write
              STATUS  mandatory
              DESCRIPTION
                      "This parameter indicates the current data rate of
                     this unit."
              ::= { m828HubTableEntry 23 }

          m828HubDataRateTimeStamp    OBJECT-TYPE
              SYNTAX  TimeTicks
              ACCESS  read-only
              STATUS  mandatory
              DESCRIPTION
                      "The time the data rate status (was) last changed."
              ::= { m828HubTableEntry 24 }

          m828HubMgmtStatus     OBJECT-TYPE
              SYNTAX  INTEGER {
                          operational(1),
                          down(2)
                   }
              ACCESS  read-only
              STATUS  mandatory
              DESCRIPTION
                      "The operational status of this unit."
              ::= { m828HubTableEntry 25 }

          m828HubProxyAgentID      OBJECT-TYPE
              SYNTAX  OCTET STRING (SIZE (6..6))  -- the MAC address of the
                                                  -- TR interface in the agent
              ACCESS  read-only
              STATUS  mandatory
              DESCRIPTION
                      "The physical layer MAC Address of the agent."
              ::= { m828HubTableEntry 26 }

          m828HubCodeVersion       OBJECT-TYPE
              SYNTAX  OCTET STRING (SIZE (2..2))
              ACCESS  read-only
              STATUS  mandatory
              DESCRIPTION
                      "The firmware version number of this unit."
              ::= { m828HubTableEntry 27 }

          m828HubRawCommandData    OBJECT-TYPE
              SYNTAX  OCTET STRING (SIZE (1..1))
              ACCESS  read-write
              STATUS  mandatory
              DESCRIPTION
                      "This is used to send raw 485 serial data to
                       this unit."
              ::= { m828HubTableEntry 28 }

          m828HubLobeNumber OBJECT-TYPE
              SYNTAX  INTEGER
              ACCESS  read-only
              STATUS  mandatory
              DESCRIPTION
                      "The number of items in the hub lobe table."
              ::= { m828Hubs 3 }


          -- Connections table for m828 hubs

          m828HubLobeTable OBJECT-TYPE
              SYNTAX  SEQUENCE OF M828hubLobeEntry
              ACCESS  not-accessible
              STATUS  mandatory
              DESCRIPTION     
                      "A table which contains the control and status 
                       information for the lobes."
              ::= { m828Hubs 4 }

          m828HubLobeEntry OBJECT-TYPE
              SYNTAX  M828hubLobeEntry
              ACCESS  not-accessible
              STATUS  mandatory
              DESCRIPTION
                      "A collection of control and status parameters kept for
                       each lobe."
              INDEX   { m828HubIndex, m828HubLobePort  }
              ::= { m828HubLobeTable 1 }

          M828hubLobeEntry ::=
                  SEQUENCE  {
                          m828HubIndex             INTEGER,
                          m828HubLobePort          INTEGER,
                          m828HubLobePhDet         INTEGER,
                          m828HubLobeMask          INTEGER,
                          m828HubLobeNsrtStatus    INTEGER,
                          m828HubLobeMacAddr       OCTET STRING,
                          m828HubLobeBcnRemStatus  INTEGER,
                          m828HubLobeTimeStamp     TimeTicks
                   }

          m828HubIndex OBJECT-TYPE
              SYNTAX  INTEGER
              ACCESS  read-only
              STATUS  mandatory
              DESCRIPTION
                      "The index into the m828HubTable of the mau this lobe is
                       on."
              ::=  { m828HubLobeEntry 1 }

          m828HubLobePort OBJECT-TYPE
              SYNTAX  INTEGER
              ACCESS  read-only
              STATUS  mandatory
              DESCRIPTION
                      "The port of the mau this lobe is on."
              ::=  { m828HubLobeEntry 2 }

          m828HubLobePhDet  OBJECT-TYPE
              SYNTAX  INTEGER {
                                  noPhantom(1),
                                  phantDetected(2)
                           }
              ACCESS  read-only
              STATUS  mandatory
              DESCRIPTION
                      "Phantom current status for this lobe port. A value of 1 
                       corresponds to no phantom current detected. A value of 2 
                       corresponds to phantom presence." 
              ::=  { m828HubLobeEntry 3 }

          m828HubLobeMask    OBJECT-TYPE
              SYNTAX  INTEGER {
                                  isolated(1),
                                  enabled(2)
                           }
              ACCESS  read-write
              STATUS  mandatory
              DESCRIPTION
                      "Administrative status for this lobe port. By setting 
                       this parameter, a remote manager can control access to 
                       the lobe port." 
              ::=  { m828HubLobeEntry 4 }

          m828HubLobeNsrtStatus    OBJECT-TYPE
              SYNTAX  INTEGER {
                                  bypassed(1),
                                  inserted(2)
                           }
              ACCESS  read-only
              STATUS  mandatory
              DESCRIPTION
                      "Actual insertion status for this lobe port. A 1 value 
                       means that the corresponding station is not connected to 
                       the ring. A 2 value means that the corresponding station 
                       is connected to the ring." 
              ::=  { m828HubLobeEntry 5 }

          m828HubLobeMacAddr       OBJECT-TYPE
              SYNTAX  OCTET STRING (SIZE (6..6))
              ACCESS  read-only
              STATUS  mandatory
              DESCRIPTION
                      "The MAC layer address of the station which is attached 
                       to the corresponding lobe port."
              ::=  { m828HubLobeEntry 6 }

          m828HubLobeBcnRemStatus  OBJECT-TYPE
              SYNTAX  INTEGER {
                          ok(1),
                          autoIsolated(2),
                          unknown(3)
                   }
              ACCESS  read-only
              STATUS  mandatory
              DESCRIPTION
                      "This parameter describes the result of any automatic 
                       beacon removal operations performed by the agent on this
                       port. Automatic beacon removal operations consist of 
                       agent-initiated isolation of a lobe port in order to 
                       remove the cause of a persistent beaconing condition." 
              ::=  { m828HubLobeEntry 7 }

          m828HubLobeTimeStamp      OBJECT-TYPE
              SYNTAX  TimeTicks
              ACCESS  read-only
              STATUS  mandatory
              DESCRIPTION
                      "The time the status of this lobe (was) last changed."
              ::=  { m828HubLobeEntry 8 }



--      The fSeries group encompasses the portion of the StarTek MIB which 
--      applies to the StarTek Focus Series intelligent modular wiring hub 
--      product line.


                  fChassis      OBJECT IDENTIFIER ::= { fSeries 1 }
                  fTRMainRing   OBJECT IDENTIFIER ::= { fSeries 2 }
                  fTRLobe       OBJECT IDENTIFIER ::= { fSeries 3 }
                  fEthernet     OBJECT IDENTIFIER ::= { fSeries 4 }
                  fFddi         OBJECT IDENTIFIER ::= { fSeries 5 }
                  fTwx          OBJECT IDENTIFIER ::= { fSeries 6 }

          --              fchassis Group

          fChassisNumber       OBJECT-TYPE
              SYNTAX  INTEGER
              ACCESS  read-only
              STATUS  mandatory
              DESCRIPTION
                      "The number of chassis in table"
              ::= { fChassis 1  }

          fChassisTable     OBJECT-TYPE
              SYNTAX  SEQUENCE OF FchassisTableEntry
              ACCESS  not-accessible
              STATUS  mandatory
              DESCRIPTION
                      "A table which describes which modules are plugged into 
                       which slots of the chassis."
              ::= { fChassis 2 }

          fChassisTableEntry        OBJECT-TYPE
              SYNTAX  FchassisTableEntry
              ACCESS  not-accessible
              STATUS  mandatory
              INDEX   { fChassisIndex  }
              ::= {  fChassisTable 1 }

          FchassisTableEntry ::=
          SEQUENCE {
                          fChassisIndex     INTEGER,
                          fChassisModel     INTEGER,
                          fChassisPowStatus INTEGER,
                          fChassisLocation  INTEGER
                   }

          fChassisIndex       OBJECT-TYPE
              SYNTAX  INTEGER
              ACCESS  read-only
              STATUS  mandatory
              DESCRIPTION
                      "Index of this entry"
              ::= {  fChassisTableEntry 1  }

          fChassisModel   OBJECT-TYPE     
              SYNTAX  INTEGER {
                                  twoslot-10100(1),                       
                                  fiveslot-10101(2),               
                                  fiveslotredundant-10102(3),              
                                  reserved4(4),    
                                  reserved5(5),             
                                  reserved6(6),
                                  reserved7(7),             
                                  reserved8(8)     
                           }
              ACCESS  read-only
              STATUS  mandatory
              DESCRIPTION
                      "The model number of the f series chassis in which the 
                       addressed management agent is installed."
              ::= {  fChassisTableEntry 2  }

          fChassisPowStatus       OBJECT-TYPE     
              SYNTAX  INTEGER {
                                  singleSupOK(1),                 
                                  dualSupOK(2),            
                                  dualSup-BSupBAD(3),
                                  dualSup-ASupBAD(4),
                                  illegal(5)
                           }
              ACCESS  read-only
              STATUS  mandatory
              DESCRIPTION
                      "The status of the power supply or supplies in the 
                       chassis."
              ::= {  fChassisTableEntry 3  }

          fChassisLocation       OBJECT-TYPE
              SYNTAX  INTEGER {
                                  local(1),
                                  external(2)
                           }
              ACCESS  read-only
              STATUS  mandatory
              DESCRIPTION
                      "The location of the chassis."
              ::= {  fChassisTableEntry 4  }


          --              fTokenRing Group

          fTRMainRingNumber OBJECT-TYPE
              SYNTAX  INTEGER
              ACCESS  read-only
              STATUS  mandatory
              DESCRIPTION
                      "The number of the ring."
              ::= { fTRMainRing 1 }

          fTRMainRingTable OBJECT-TYPE
              SYNTAX  SEQUENCE OF FTRMainRingTableEntry
              ACCESS  not-accessible
              STATUS  mandatory
              DESCRIPTION     
                      "A table which maintains a list of all of the intelligent
                       Focus series hubs on the ring being managed by the 
                       addressed agent. This table is INDEXed by the RS485 OOB 
                       address of the Focus series intelligent hubs."
              ::= { fTRMainRing 2 }

          fTRMainRingTableEntry        OBJECT-TYPE
              SYNTAX  FTRMainRingTableEntry
              ACCESS  not-accessible
              STATUS  mandatory
              DESCRIPTION
                      "An entry in the fTRMainRingTable"
              INDEX   { fTRMainRingTableIndex  }
              ::= { fTRMainRingTable 1 }

          FTRMainRingTableEntry ::=
                  SEQUENCE  {
                          fTRMainRingTableIndex         INTEGER,
                          fTRMainRingModel              INTEGER,
                          fTRMainRing485Address         OCTET STRING,
                          fTRMainRingSlotIndex          INTEGER,
                          fTRMainRingChassisIndex       INTEGER,
                          fTRMainRingRiFTolState        INTEGER,
                          fTRMainRingRiMask             INTEGER,
                          fTRMainRingRiPhDet            INTEGER,
                          fTRMainRingRiNsrtStatus       INTEGER,
                          fTRMainRingRiBcnRemStatus     INTEGER,
                          fTRMainRingRiCableType        INTEGER,
                          fTRMainRingRiNghbrType        INTEGER,
                          fTRMainRingRiNghbrAddr        OCTET STRING,
                          fTRMainRingRiTimeStamp        TimeTicks,
                          fTRMainRingRoFTolState        INTEGER,
                          fTRMainRingRoMask             INTEGER,
                          fTRMainRingRoPhDet            INTEGER,
                          fTRMainRingRoNsrtStatus       INTEGER,
                          fTRMainRingRoBcnRemStatus     INTEGER,
                          fTRMainRingRoCableType        INTEGER,
                          fTRMainRingRoNghbrType        INTEGER,
                          fTRMainRingRoNghbrAddr        OCTET STRING,
                          fTRMainRingRoTimeStamp        TimeTicks,
                          fTRMainRingDataRateState      INTEGER,
                          fTRMainRingDataRateTimeStamp  TimeTicks,
                          fTRMainRingBkPlnNsrtState     INTEGER,
                          fTRMainRingBkPlnTimeStamp     TimeTicks,
                          fTRMainRingLobePhDet          INTEGER,
                          fTRMainRingLobeMask           INTEGER,
                          fTRMainRingLobeNsrtStatus     INTEGER,
                          fTRMainRingLobeMacAddr        OCTET STRING,
                          fTRMainRingLobeBcnRemStatus   INTEGER,
                          fTRMainRingLobeTimeStamp      TimeTicks,
                          fTRMainRingMgmtStatus         INTEGER,
                          fTRMainRingProxyAgentID       OCTET STRING,
                          fTRMainRingAttachedAgentType  INTEGER,
                          fTRMainRingAttachedAgentState INTEGER,
                          fTRMainRingTemperatureStatus  INTEGER,
                          fTRMainRingAutoRecovControl   INTEGER,
                          fTRMainRingAutoRecovRetries   INTEGER,
                          fTRMainRingCodeVersion        OCTET STRING,
                          fTRMainRingAutoRecovState     INTEGER,
                          fTRMainRingRawCommandData     OCTET STRING,
                          fTRMainRingPowerStatus        INTEGER,
                          fTRMainRingCageType           INTEGER,
                          fTRMainRingAutoRecovMode      INTEGER
                       }

          fTRMainRingTableIndex        OBJECT-TYPE
              SYNTAX  INTEGER
              ACCESS  read-only
              STATUS  mandatory
              DESCRIPTION
                      "The index for this ring entry."
              ::= { fTRMainRingTableEntry 1 }

          fTRMainRingModel     OBJECT-TYPE
              SYNTAX  INTEGER {
                                  f10154RiRoExpModule(1),
                                  f10155RiRoFiberExpModule(2),
                                  f10150RiRoExpModuleAgent(3),
                                  f10151RiRoFiberExpModuleAgent(4)
                           }
              ACCESS  read-only
              STATUS  mandatory
              DESCRIPTION     
                      "The model number of the Focus series hub being managed."
              ::= {  fTRMainRingTableEntry 2 }

          fTRMainRing485Address        OBJECT-TYPE
              SYNTAX  OCTET STRING (SIZE (3..3))
              ACCESS  read-only
              STATUS  mandatory
              DESCRIPTION
                      "The 6 hex digit address used on the RS485 serial OOB
                       management channel."
              ::=  {  fTRMainRingTableEntry 3 }

          fTRMainRingSlotIndex       OBJECT-TYPE
              SYNTAX  INTEGER
              ACCESS  read-only
              STATUS  mandatory
              DESCRIPTION
                      "The slot id."
              ::= { fTRMainRingTableEntry 4 }

          fTRMainRingChassisIndex       OBJECT-TYPE
              SYNTAX  INTEGER
              ACCESS  read-only
              STATUS  mandatory
              DESCRIPTION
                      "The index of the chassis the card is in."
              ::= { fTRMainRingTableEntry 5 }

          fTRMainRingRiFTolState       OBJECT-TYPE
              SYNTAX  INTEGER {
                          off(1),
                          on(2)
                   }
              ACCESS  read-write
              STATUS  mandatory
              DESCRIPTION
                      "This parameter controls the Ring In (RI) fault tolerance 
                       behavior. Off(1) means that phantom current is not used
                       on the corresponding RI interface as a condition for main
                       ring link insertion. On (2) means that phantom current
                       is used on the corresponding RI interface as a condition
                       for main ring link insertion. The preferred setting for
                       this parameter is on (2)."
              ::= { fTRMainRingTableEntry 6 }

          fTRMainRingRiMask    OBJECT-TYPE
              SYNTAX  INTEGER {
                          isolate(1),
                          enable(2)
                   }
              ACCESS  read-write
              STATUS  mandatory
              DESCRIPTION
                      "Administrative status for this Ring In port. By
                       setting this parameter, a remote manager can control
                       the partitioning of this port."
              ::= { fTRMainRingTableEntry 7 }

          fTRMainRingRiPhDet   OBJECT-TYPE
              SYNTAX  INTEGER {
                          noPhantom(1),
                          phantDetected(2)
                   }
              ACCESS  read-only
              STATUS  mandatory
              DESCRIPTION
                      "This parameter describes the phantom detect status of
                       the Ring In port."
              ::= { fTRMainRingTableEntry 8 }

          fTRMainRingRiNsrtStatus      OBJECT-TYPE
              SYNTAX  INTEGER {
                          bypassed(1),
                          inserted(2)
                   }
              ACCESS  read-only
              STATUS  mandatory
              DESCRIPTION
                      "Insertion status for this Ring In port."
              ::= { fTRMainRingTableEntry 9 }

          fTRMainRingRiBcnRemStatus    OBJECT-TYPE
              SYNTAX  INTEGER {
                          ok(1),
                          autoIsolated(2)
                   }
              ACCESS  read-only
              STATUS  mandatory
              DESCRIPTION
                      "This parameter describes the result of any automatic 
                       beacon removal operations performed by the agent on this
                       port. Automatic beacon removal operations consist of 
                       agent-initiated isolation of a lobe port in order to 
                       remove the cause of a persistent beaconing condition." 
              ::= { fTRMainRingTableEntry 10 }

          fTRMainRingRiCableType    OBJECT-TYPE
              SYNTAX  INTEGER {
                          copper(1),
                          fiber(2)
                   }
              ACCESS  read-only
              STATUS  mandatory
              DESCRIPTION
                      "This parameter indicates the type of physical cabling
                       used for the network interface on the Ring In port."
              ::= { fTRMainRingTableEntry 11 }

          fTRMainRingRiNghbrType    OBJECT-TYPE
              SYNTAX  INTEGER {
                          series828(1),
                          fSeries(2),
                          tokenRingMAC(3),
                          none(4),
                          stackable(5)
                  }
              ACCESS  read-only
              STATUS  mandatory
              DESCRIPTION
                      "This parameter indicates the type of nearest neighbor
                       on the Ring In port."
              ::= { fTRMainRingTableEntry 12 }

          fTRMainRingRiNghbrAddr    OBJECT-TYPE
              SYNTAX  OCTET STRING (SIZE (2..6))
              ACCESS  read-only
              STATUS  mandatory
              DESCRIPTION
                      "The address of the nearest neighbor on the Ring In port."
              ::= { fTRMainRingTableEntry 13 }

          fTRMainRingRiTimeStamp    OBJECT-TYPE
              SYNTAX  TimeTicks
              ACCESS  read-only
              STATUS  mandatory
              DESCRIPTION
                      "The time the status of Ring In (was) last changed."
              ::= { fTRMainRingTableEntry 14 }

          fTRMainRingRoFTolState       OBJECT-TYPE
              SYNTAX  INTEGER {
                          off(1),
                          on(2)
                   }
              ACCESS  read-write
              STATUS  mandatory
              DESCRIPTION
                      "This controls the Ring Out (RO) fault tolerance 
                       behavior. Off(1) means that phantom current is not used
                       on the corresponding RO interface as a condition for main
                       ring link insertion. On (2) means tha phantom current is
                       used on the corresponding RO interface as a condition for
                       main ring link insertion. The preferred setting for this
                       parameter is on (2)."
              ::= { fTRMainRingTableEntry 15 }

          fTRMainRingRoMask    OBJECT-TYPE
              SYNTAX  INTEGER {
                          isolate(1),
                          enable(2)
                   }
              ACCESS  read-write
              STATUS  mandatory
              DESCRIPTION
                     "Administrative status for this Ring Out port. By
                      setting this parameter, a remote manager can control
                      the partitioning of this port."
              ::= { fTRMainRingTableEntry 16 }

          fTRMainRingRoPhDet   OBJECT-TYPE
              SYNTAX  INTEGER {
                          wireFault(1),
                          phantOk(2)      --corresponds to 
                                          --forward ok
                   }
              ACCESS  read-only
              STATUS  mandatory
              DESCRIPTION
                     "This parameter describes the phantom detect status for
                      this Ring Out port."
              ::= { fTRMainRingTableEntry 17 }

          fTRMainRingRoNsrtStatus      OBJECT-TYPE
              SYNTAX  INTEGER {
                          bypassed(1),
                          inserted(2)
                   }
              ACCESS  read-only
              STATUS  mandatory
              DESCRIPTION
                     "Insertion status for this Ring Out port."
              ::= { fTRMainRingTableEntry 18 }

          fTRMainRingRoBcnRemStatus    OBJECT-TYPE
              SYNTAX  INTEGER {
                          ok(1),
                          autoIsolated(2)
                   }
              ACCESS  read-only
              STATUS  mandatory
              DESCRIPTION
                      "This parameter describes the result of any automatic 
                       beacon removal operations performed by the agent on this
                       port. Automatic beacon removal operations consist of 
                       agent-initiated isolation of a lobe port in order to 
                       remove the cause of a persistent beaconing condition." 
              ::= { fTRMainRingTableEntry 19 }

          fTRMainRingRoCableType    OBJECT-TYPE
              SYNTAX  INTEGER {
                          copper(1),
                          fiber(2)
                   }
              ACCESS  read-only
              STATUS  mandatory
              DESCRIPTION
                      "This parameter indicates the type of physical cabling
                       used for the network interface on the Ring Out port."
              ::= { fTRMainRingTableEntry 20 }

          fTRMainRingRoNghbrType    OBJECT-TYPE
              SYNTAX  INTEGER {
                          series828(1),
                          fSeries(2),
                          tokenRingMAC(3),
                          none(4),
                          stackable(5)
                  }
              ACCESS  read-only
              STATUS  mandatory
              DESCRIPTION
                      "This parameter indicates the type of nearest neighbor
                       on the Ring Out port."
              ::= { fTRMainRingTableEntry 21 }

          fTRMainRingRoNghbrAddr    OBJECT-TYPE
              SYNTAX  OCTET STRING (SIZE (2..6))
              ACCESS  read-only
              STATUS  mandatory
              DESCRIPTION
                      "The address of the nearest neighbor on the Ring Out
                       port."
              ::= { fTRMainRingTableEntry 22 }

          fTRMainRingRoTimeStamp    OBJECT-TYPE
              SYNTAX  TimeTicks
              ACCESS  read-only
              STATUS  mandatory
              DESCRIPTION
                      "The time the status of Ring Out (was) last changed."
              ::= { fTRMainRingTableEntry 23 }

          fTRMainRingDataRateState     OBJECT-TYPE
              SYNTAX  INTEGER {
                          s4Mbps(1),
                          s16Mbps(2)
                   }
              ACCESS  read-write
              STATUS  mandatory
              DESCRIPTION
                      "This parameter indicates the current data rate of
                       this unit."
              ::= { fTRMainRingTableEntry 24 }

          fTRMainRingDataRateTimeStamp    OBJECT-TYPE
              SYNTAX  TimeTicks
              ACCESS  read-only
              STATUS  mandatory
              DESCRIPTION
                      "The time the data rate status (was) last changed."
              ::= { fTRMainRingTableEntry 25 }

          fTRMainRingBkPlnNsrtState     OBJECT-TYPE
              SYNTAX  INTEGER {
                          inserted(1),
                          bypassed(2)
                   }
              ACCESS  read-write
              STATUS  mandatory
              DESCRIPTION
                      "Backplane insertion status for this unit." 
              ::= { fTRMainRingTableEntry 26 }

          fTRMainRingBkPlnTimeStamp    OBJECT-TYPE
              SYNTAX  TimeTicks
              ACCESS  read-only
              STATUS  mandatory
              DESCRIPTION
                      "The time the backplane insert status (was) last changed."
              ::= { fTRMainRingTableEntry 27 }

          fTRMainRingLobePhDet  OBJECT-TYPE
              SYNTAX  INTEGER {
                                  noPhantom(1),
                                  phantDetected(2)
                           }
              ACCESS  read-only
              STATUS  mandatory
              DESCRIPTION
                      "Phantom current status for this lobe port. A value of 1 
                       corresponds to no phantom current detected. A value of 2 
                       corresponds to phantom presence." 
              ::=  { fTRMainRingTableEntry 28 }

          fTRMainRingLobeMask    OBJECT-TYPE
              SYNTAX  INTEGER {
                                  isolated(1),
                                  enabled(2)
                           }
              ACCESS  read-write
              STATUS  mandatory
              DESCRIPTION
                      "Administrative status for this lobe port. By setting 
                       this parameter, a remote manager can control access to 
                       the lobe port." 
              ::=  { fTRMainRingTableEntry 29 }

          fTRMainRingLobeNsrtStatus    OBJECT-TYPE
              SYNTAX  INTEGER {
                                  bypassed(1),
                                  inserted(2)
                           }
              ACCESS  read-only
              STATUS  mandatory
              DESCRIPTION
                      "Actual insertion status for this lobe port. A 1 value 
                       means that the corresponding station is not connected to 
                       the ring. A 2 value means that the corresponding station
                       is connected to the ring." 
              ::=  { fTRMainRingTableEntry 30 }

          fTRMainRingLobeMacAddr       OBJECT-TYPE
              SYNTAX  OCTET STRING (SIZE (6..6))
              ACCESS  read-only
              STATUS  mandatory
              DESCRIPTION
                      "The MAC layer address of the station which is attached 
                       to the corresponding lobe port."
              ::=  { fTRMainRingTableEntry 31 }

          fTRMainRingLobeBcnRemStatus  OBJECT-TYPE
              SYNTAX  INTEGER {
                          ok(1),
                          autoIsolated(2),
                          unknown(3)
                   }
              ACCESS  read-only
              STATUS  mandatory
              DESCRIPTION
                      "This parameter describes the result of any automatic 
                       beacon removal operations performed by the agent on this
                       port. Automatic beacon removal operations consist of 
                       agent-initiated isolation of a lobe port in order to 
                       remove the cause of a persistent beaconing condition." 
              ::=  { fTRMainRingTableEntry 32 }

          fTRMainRingLobeTimeStamp      OBJECT-TYPE
              SYNTAX  TimeTicks
              ACCESS  read-only
              STATUS  mandatory
              DESCRIPTION
                      "The time the status of this lobe (was) last changed."
              ::=  { fTRMainRingTableEntry 33 }

          fTRMainRingMgmtStatus     OBJECT-TYPE
              SYNTAX  INTEGER {
                              operational(1),
                              down(2)
                  }
              ACCESS  read-only
              STATUS  mandatory
              DESCRIPTION
                      "The operational status of this unit."
              ::=  { fTRMainRingTableEntry 34 }

          fTRMainRingProxyAgentID      OBJECT-TYPE
              SYNTAX  OCTET STRING (SIZE (6..6))  -- the MAC address of the
                                                  -- TR interface in the agent
              ACCESS  read-only
              STATUS  mandatory
              DESCRIPTION
                      "The physical layer MAC Address of the agent."
              ::= { fTRMainRingTableEntry 35 }

          fTRMainRingAttachedAgentType      OBJECT-TYPE
              SYNTAX  INTEGER {
                              tokenring(1),
                              tokenring-ethernet(2),
                              reserved(3),
                              none(4)
                  }
              ACCESS  read-only
              STATUS  mandatory
              DESCRIPTION
                      "The type of the attached agent."
              ::=  { fTRMainRingTableEntry 36 }

          fTRMainRingAttachedAgentState     OBJECT-TYPE
              SYNTAX  INTEGER {
                              enabled(1),
                              disabled(2),
                              not-applicable(3)
                  }
              ACCESS  read-write
              STATUS  mandatory
              DESCRIPTION
                      "The state of the attached agent."
              ::=  { fTRMainRingTableEntry 37 }

          fTRMainRingTemperatureStatus      OBJECT-TYPE
              SYNTAX  INTEGER {
                              ok(1),
                              bad(2)
                  }
              ACCESS  read-only
              STATUS  mandatory
              DESCRIPTION
                      "The temperature status of this unit."
              ::=  { fTRMainRingTableEntry 38 }

          fTRMainRingAutoRecovControl       OBJECT-TYPE
              SYNTAX  INTEGER {
                              enabled(1),
                              disabled(2),
                              reset(3), 
                              unknown(4)
                  }
              ACCESS  read-write
              STATUS  mandatory
              DESCRIPTION
                      "This parameter controls the auto recovery operation
                       of this unit."
              ::=  { fTRMainRingTableEntry 39 }

          fTRMainRingAutoRecovRetries       OBJECT-TYPE
              SYNTAX  INTEGER (1..255)
              ACCESS  read-write
              STATUS  mandatory
              DESCRIPTION
                      "The number of Auto Recoveries performed by this unit."
              ::=  { fTRMainRingTableEntry 40 }

          fTRMainRingCodeVersion      OBJECT-TYPE
              SYNTAX  OCTET STRING (SIZE (2..2))  
              ACCESS  read-only
              STATUS  mandatory
              DESCRIPTION
                      "The firmware version number of this unit."
              ::= { fTRMainRingTableEntry 41 }

          fTRMainRingAutoRecovState         OBJECT-TYPE
              SYNTAX  INTEGER {
                              in-recovery(1),
                              normal(2),
                              halted(3)
                  }
              ACCESS  read-only
              STATUS  mandatory
              DESCRIPTION
                      "The auto recovery state of this unit."
              ::=  { fTRMainRingTableEntry 42 }

          fTRMainRingRawCommandData      OBJECT-TYPE
              SYNTAX  OCTET STRING (SIZE (1..255))  
              ACCESS  read-write
              STATUS  mandatory
              DESCRIPTION
                      "This is used to send raw 485 serial data to
                       this unit."
              ::= { fTRMainRingTableEntry 43 }

          fTRMainRingPowerStatus    OBJECT-TYPE
              SYNTAX  INTEGER {
                                  singleSupOK(1),                 
                                  dualSupOK(2),            
                                  dualSup-BSupBAD(3),
                                  dualSup-ASupBAD(4),
                                  illegal(5)
                  }
              ACCESS  read-only
              STATUS  mandatory
              DESCRIPTION
                      "The status of the power supply as seen by this unit."
              ::=  { fTRMainRingTableEntry 44 }

          fTRMainRingCageType     OBJECT-TYPE
              SYNTAX  INTEGER {
                                  twoslot-10100(1),                       
                                  fiveslot-10101(2),               
                                  fiveslotredundant-10102(3),              
                                  reserved4(4),    
                                  reserved5(5),             
                                  reserved6(6),
                                  reserved7(7),             
                                  reserved8(8)     
                           }
              ACCESS  read-only
              STATUS  mandatory
              DESCRIPTION
                      "The model number of the f series chassis the card is is."
              ::= {  fTRMainRingTableEntry 45 }

          fTRMainRingAutoRecovMode     OBJECT-TYPE
              SYNTAX  INTEGER {
                          selfEnabling(1),
                          non-selfEnabling(2)
                   }
              ACCESS  read-write
              STATUS  mandatory
              DESCRIPTION
                      "This parameter describes the auto recovery mode."
              ::= { fTRMainRingTableEntry 46 }


          --         fTRLobe group

          fTRLobeNumber OBJECT-TYPE
              SYNTAX  INTEGER
              ACCESS  read-only
              STATUS  mandatory
              DESCRIPTION
                  "The number of items in the lobe table"
              ::= { fTRLobe 1 }

          fTRLobeTable OBJECT-TYPE
              SYNTAX  SEQUENCE OF FTRLobeTableEntry
              ACCESS  not-accessible
              STATUS  mandatory
              DESCRIPTION     
                      "A table which maintains a list of all of the intelligent
                       Focus series hubs on the ring being managed by the 
                       addressed agent. This table is INDEXed by the RS485 OOB 
                       address of the Focus series intelligent hubs."
              ::= { fTRLobe 2 }

          fTRLobeTableEntry        OBJECT-TYPE
              SYNTAX  FTRLobeTableEntry
              ACCESS  not-accessible
              STATUS  mandatory
              DESCRIPTION
                      "An entry in the fTRLobeTable"
              INDEX   { fTRLobeTableIndex  }
              ::= { fTRLobeTable 1 }

          FTRLobeTableEntry ::=
                  SEQUENCE  {
                          fTRLobeTableIndex        INTEGER,
                          fTRLobeModel             INTEGER,
                          fTRLobe485Address        OCTET STRING,
                          fTRLobeSlotIndex         INTEGER,
                          fTRLobeChassisIndex      INTEGER,
                          fTRLobeDataRateState     INTEGER,
                          fTRLobeDataRateTimeStamp TimeTicks,
                          fTRLobeBkPlnNsrtState    INTEGER,
                          fTRLobeBkPlnTimeStamp    TimeTicks,
                          fTRLobeMgmtStatus        INTEGER,
                          fTRLobeProxyAgentID      OCTET STRING,
                          fTRLobeTemperatureStatus INTEGER,
                          fTRLobeAutoRecovControl  INTEGER,
                          fTRLobeAutoRecovMode     INTEGER,
                          fTRLobeAutoRecovRetries  INTEGER,
                          fTRLobeCodeVersion       OCTET STRING,
                          fTRLobeAutoRecovState    INTEGER,
                          fTRLobeRawCommandData    OCTET STRING,
                          fTRLobePowerStatus       INTEGER,
                          fTRLobeCageType          INTEGER
                       }

          fTRLobeTableIndex        OBJECT-TYPE
              SYNTAX  INTEGER
              ACCESS  read-only
              STATUS  mandatory
              DESCRIPTION
                      "The index for this lobe entry"
              ::= {  fTRLobeTableEntry 1 }

          fTRLobeModel     OBJECT-TYPE
              SYNTAX  INTEGER {
                                  f10157trPassiveMau(1),
                                  f10158trActiveMau(2)
                           }
              ACCESS  read-only
              STATUS  mandatory
              DESCRIPTION     
                      "The Mau type of the Focus series lobe being managed."
              ::= {  fTRLobeTableEntry 2 }

          fTRLobe485Address        OBJECT-TYPE
              SYNTAX  OCTET STRING (SIZE (3..3))
              ACCESS  read-only
              STATUS  mandatory
              DESCRIPTION
                      "The 6 hex digit address used on the RS485 serial OOB 
                      management channel."
              ::=  {  fTRLobeTableEntry 3 }

          fTRLobeSlotIndex       OBJECT-TYPE
              SYNTAX  INTEGER
              ACCESS  read-only
              STATUS  mandatory
              DESCRIPTION
                  "The slot id."
              ::= { fTRLobeTableEntry 4 }

          fTRLobeChassisIndex       OBJECT-TYPE
              SYNTAX  INTEGER
              ACCESS  read-only
              STATUS  mandatory
              DESCRIPTION
                  "The index of the chassis the card is in."
              ::= { fTRLobeTableEntry 5 }

          fTRLobeDataRateState     OBJECT-TYPE
              SYNTAX  INTEGER {
                          s4Mbps(1),
                          s16Mbps(2)
                   }
              ACCESS  read-write
              STATUS  mandatory
              DESCRIPTION
                     "This parameter indicates the current data rate of
                     this unit."
              ::= { fTRLobeTableEntry 6 }

          fTRLobeDataRateTimeStamp    OBJECT-TYPE
              SYNTAX  TimeTicks
              ACCESS  read-only
              STATUS  mandatory
              DESCRIPTION
                     "The time the data rate status (was) last changed."
              ::= { fTRLobeTableEntry 7 }

          fTRLobeBkPlnNsrtState     OBJECT-TYPE
              SYNTAX  INTEGER {
                          inserted(1),
                          bypassed(2)
                   }
              ACCESS  read-write
              STATUS  mandatory
              DESCRIPTION
                      "Backplane insertion status for this unit." 
              ::= { fTRLobeTableEntry 8 }

          fTRLobeBkPlnTimeStamp    OBJECT-TYPE
              SYNTAX  TimeTicks
              ACCESS  read-only
              STATUS  mandatory
              DESCRIPTION
                     "The time the backplane insert status (was) last changed."
              ::= { fTRLobeTableEntry 9 }

          fTRLobeMgmtStatus     OBJECT-TYPE
              SYNTAX  INTEGER {
                          operational(1),
                          down(2)
                   }
              ACCESS  read-only
              STATUS  mandatory
              DESCRIPTION
                      "The operational status of this unit."
              ::= { fTRLobeTableEntry 10 }

          fTRLobeProxyAgentID      OBJECT-TYPE
              SYNTAX  OCTET STRING (SIZE (6..6))  -- the MAC address of the
                                                  -- TR interface in the agent
              ACCESS  read-only
              STATUS  mandatory
              DESCRIPTION
                      "The physical layer MAC Address of the agent."
              ::= { fTRLobeTableEntry 11 }

          fTRLobeTemperatureStatus     OBJECT-TYPE
              SYNTAX  INTEGER {
                          ok(1),
                          bad(2)
                   }
              ACCESS  read-only
              STATUS  mandatory
              DESCRIPTION
                      "The temperature status of this unit."
              ::= { fTRLobeTableEntry 12 }

          fTRLobeAutoRecovControl     OBJECT-TYPE
              SYNTAX  INTEGER {
                          enabled(1),
                          disabled(2),
                          reset(3)
                   }
              ACCESS  read-write
              STATUS  mandatory
              DESCRIPTION
                      "This parameter controls the auto recovery operation
                       of this unit."
              ::= { fTRLobeTableEntry 13 }

          fTRLobeAutoRecovMode     OBJECT-TYPE
              SYNTAX  INTEGER {
                          selfEnabling(1),
                          non-selfEnabling(2)
                   }
              ACCESS  read-write
              STATUS  mandatory
              DESCRIPTION
                      "This parameter describes the auto recovery mode."
              ::= { fTRLobeTableEntry 14 }

          fTRLobeAutoRecovRetries   OBJECT-TYPE
              SYNTAX  INTEGER (1..255)
              ACCESS  read-write
              STATUS  mandatory
              DESCRIPTION
                      "The number of Auto Recoveries performed by this unit."
              ::=  { fTRLobeTableEntry 15 }

          fTRLobeCodeVersion      OBJECT-TYPE
              SYNTAX  OCTET STRING (SIZE (2..2))  
              ACCESS  read-only
              STATUS  mandatory
              DESCRIPTION
                      "The firmware version number of this unit."
              ::= { fTRLobeTableEntry 16 }

          fTRLobeAutoRecovState     OBJECT-TYPE
              SYNTAX  INTEGER {
                          in-recovery(1),
                          normal(2),
                          halted(3)
                   }
              ACCESS  read-only
              STATUS  mandatory
              DESCRIPTION
                      "The auto recovery state of this unit."
              ::= { fTRLobeTableEntry 17 }

          fTRLobeRawCommandData      OBJECT-TYPE
              SYNTAX  OCTET STRING (SIZE (1..255))  
              ACCESS  read-write
              STATUS  mandatory
              DESCRIPTION
                      "This is used to send raw 485 serial data to
                       this unit."
              ::= { fTRLobeTableEntry 18 }

          fTRLobePowerStatus        OBJECT-TYPE
              SYNTAX  INTEGER {
                                  singleSupOK(1),                 
                                  dualSupOK(2),            
                                  dualSup-BSupBAD(3),
                                  dualSup-ASupBAD(4),
                                  illegal(5)
                  }
              ACCESS  read-only
              STATUS  mandatory
              DESCRIPTION
                      "The status of the power supply as seen by this unit."
              ::=  { fTRLobeTableEntry 19 }

          fTRLobeCageType OBJECT-TYPE
              SYNTAX  INTEGER {
                                  twoslot-10100(1),                       
                                  fiveslot-10101(2),               
                                  fiveslotredundant-10102(3),              
                                  reserved4(4),    
                                  reserved5(5),             
                                  reserved6(6),
                                  reserved7(7),             
                                  reserved8(8)     
                           }
              ACCESS  read-only
              STATUS  mandatory
              DESCRIPTION
                      "The model number of the fseries chassis the card is is."
              ::= {  fTRLobeTableEntry 20 }


          -- Connections table for focus hubs

          fTRLobeConnectNumber OBJECT-TYPE
              SYNTAX  INTEGER
              ACCESS  read-only
              STATUS  mandatory
              DESCRIPTION
                      "The number of items in connection table"
              ::= { fTRLobe 3 }

          fTRLobeConnectTable OBJECT-TYPE
              SYNTAX  SEQUENCE OF FTRLobeConnectEntry
              ACCESS  not-accessible
              STATUS  mandatory
              DESCRIPTION     
                      "A table which contains the control and status 
                       information for the lobes."
              ::= { fTRLobe 4 }

          fTRLobeConnectEntry OBJECT-TYPE
              SYNTAX  FTRLobeConnectEntry
              ACCESS  not-accessible
              STATUS  mandatory
              DESCRIPTION
                      "A collection of control and status parameters kept for 
                       each lobe."
              INDEX   { fTRLobeIndex, fTRLobeConnectPort      }
              ::= { fTRLobeConnectTable 1 }

          FTRLobeConnectEntry ::=
                  SEQUENCE  {
                          fTRLobeIndex                INTEGER,
                          fTRLobeConnectPort          INTEGER,
                          fTRLobeConnectPhDet         INTEGER,
                          fTRLobeConnectMask          INTEGER,
                          fTRLobeConnectNsrtStatus    INTEGER,
                          fTRLobeConnectMacAddr       OCTET STRING,
                          fTRLobeConnectBcnRemStatus  INTEGER,
                          fTRLobeConnectBcnRemCause   INTEGER,
                          fTRLobeConnectTimeStamp     TimeTicks
                   }

          fTRLobeIndex OBJECT-TYPE
              SYNTAX  INTEGER
              ACCESS  read-only
              STATUS  mandatory
              DESCRIPTION
                      "The index into the fTRLobeTable of the mau this lobe is
                       on."
              ::=  { fTRLobeConnectEntry 1 }

          fTRLobeConnectPort OBJECT-TYPE
              SYNTAX  INTEGER
              ACCESS  read-only
              STATUS  mandatory
              DESCRIPTION
                      "The port of the mau this lobe is on."
              ::=  { fTRLobeConnectEntry 2 }

          fTRLobeConnectPhDet  OBJECT-TYPE
              SYNTAX  INTEGER {
                                  noPhantom(1),
                                  phantDetected(2)
                           }
              ACCESS  read-only
              STATUS  mandatory
              DESCRIPTION
                      "Phantom current status for this lobe port. A value of 1 
                       corresponds to no phantom current detected. A value of 2 
                       corresponds to phantom presence." 
              ::=  { fTRLobeConnectEntry 3 }

          fTRLobeConnectMask    OBJECT-TYPE
              SYNTAX  INTEGER {
                                  isolated(1),
                                  enabled(2)
                           }
              ACCESS  read-write
              STATUS  mandatory
              DESCRIPTION
                      "Administrative status for this lobe port. By setting 
                       this parameter, a remote manager can control access to 
                       the lobe port." 
              ::=  { fTRLobeConnectEntry 4 }

          fTRLobeConnectNsrtStatus    OBJECT-TYPE
              SYNTAX  INTEGER {
                                  bypassed(1),
                                  inserted(2)
                           }
              ACCESS  read-only
              STATUS  mandatory
              DESCRIPTION
                      "Actual insertion status for this lobe port. A 1 value 
                       means that the corresponding station is not connected to
                       the ring. A 2 value means that the corresponding station
                       is connected to the ring." 
              ::=  { fTRLobeConnectEntry 5 }

          fTRLobeConnectMacAddr       OBJECT-TYPE
              SYNTAX  OCTET STRING (SIZE (6..6))
              ACCESS  read-only
              STATUS  mandatory
              DESCRIPTION
                      "The MAC layer address of the station which is attached 
                       to the corresponding lobe port."
              ::=  { fTRLobeConnectEntry 6 }

          fTRLobeConnectBcnRemStatus  OBJECT-TYPE
              SYNTAX  INTEGER {
                          ok(1),
                          autoIsolated(2),
                          unknown(3)
                   }
              ACCESS  read-only
              STATUS  mandatory
              DESCRIPTION
                      "This parameter describes the result of any automatic 
                       beacon removal operations performed by the agent on this 
                       port. Automatic beacon removal operations consist of 
                       agent-initiated isolation of a lobe port in order to 
                       remove the cause of a persistent beaconing condition." 
              ::=  { fTRLobeConnectEntry 7 }

          fTRLobeConnectBcnRemCause  OBJECT-TYPE
              SYNTAX  INTEGER {
                          no-removal(1),
                          phantom-error(2),
                          no-carrier(3),
                          bad-rate(4),
                          unknown(5)
                   }
              ACCESS  read-only
              STATUS  mandatory
              DESCRIPTION
                      "This parameter describes the cause of any automatic 
                      beacon removal" 
              ::=  { fTRLobeConnectEntry 8 }

          fTRLobeConnectTimeStamp      OBJECT-TYPE
              SYNTAX  TimeTicks
              ACCESS  read-only
              STATUS  mandatory
              DESCRIPTION
                      "The time the status of this lobe (was) last changed."
              ::=  { fTRLobeConnectEntry 9 }


          -- fEthernet group
          --
          -- This section is NOT supported by the Star-Tek
          -- LinkBuilder TRi Model 1.
          --

          fEthernetNumber OBJECT-TYPE
              SYNTAX  INTEGER
              ACCESS  read-only
              STATUS  mandatory
              DESCRIPTION
                      "The number of items in concentrator table"
              ::= { fEthernet 1 }

          fEthernetTable OBJECT-TYPE
              SYNTAX  SEQUENCE OF FEthernetTableEntry
              ACCESS  not-accessible
              STATUS  mandatory
              DESCRIPTION     
                      "A table which maintains a list of all of the Focus
                       series ethernet concentrators in the repeater being 
                       managed by the addressed agent. This table is INDEXed 
                       by the repeater group id of the Focus series
                       ethernet concentrators."
              ::= { fEthernet 2 }

          fEthernetTableEntry        OBJECT-TYPE
              SYNTAX  FEthernetTableEntry
              ACCESS  not-accessible
              STATUS  mandatory
              DESCRIPTION
                      "An entry in the fEthernetTable"
              INDEX   { fEthernetTableIndex  }
              ::= { fEthernetTable 1 }

          FEthernetTableEntry ::=
                  SEQUENCE  {
                          fEthernetTableIndex        INTEGER,
                          fEthernetModel             INTEGER,
                          fEthernet485Address        OCTET STRING,
                          fEthernetSlotIndex         INTEGER,
                          fEthernetChassisIndex      INTEGER,
                          fEthernetBkPlnNsrtState    INTEGER,
                          fEthernetBkPlnTimeStamp    TimeTicks,
                          fEthernetMgmtStatus        INTEGER,
                          fEthernetProxyAgentID      OCTET STRING,
                          fEthernetTemperatureStatus INTEGER,
                          fEthernetCodeVersion       OCTET STRING,
                          fEthernetRawCommandData    OCTET STRING,
                          fEthernetPowerStatus       INTEGER,
                          fEthernetCageType          INTEGER
                       }

          fEthernetTableIndex        OBJECT-TYPE
              SYNTAX  INTEGER
              ACCESS  read-only
              STATUS  mandatory
              DESCRIPTION
                      "The index for this hub entry."
              ::= {  fEthernetTableEntry 1 }

          fEthernetModel     OBJECT-TYPE
              SYNTAX  INTEGER {
                                  f10160(1),
                                  f10161(2)
                           }
              ACCESS  read-only
              STATUS  mandatory
              DESCRIPTION     
                      "The model number of the Focus series ethernet 
                       concentrator being managed."
              ::= {  fEthernetTableEntry 2 }

          fEthernet485Address        OBJECT-TYPE
              SYNTAX  OCTET STRING (SIZE (3..3))
              ACCESS  read-only
              STATUS  mandatory
              DESCRIPTION
                      "The 6 hex digit address used on the RS485 serial OOB 
                       management channel."
              ::=  {  fEthernetTableEntry 3 }

          fEthernetSlotIndex       OBJECT-TYPE
              SYNTAX  INTEGER
              ACCESS  read-only
              STATUS  mandatory
              DESCRIPTION
                      "The slot id."
              ::= { fEthernetTableEntry 4 }

          fEthernetChassisIndex       OBJECT-TYPE
              SYNTAX  INTEGER
              ACCESS  read-only
              STATUS  mandatory
              DESCRIPTION
                      "The index of the chassis the card is in."
              ::= { fEthernetTableEntry 5 }

          fEthernetBkPlnNsrtState     OBJECT-TYPE
              SYNTAX  INTEGER {
                          inserted(1),
                          bypassed(2)
                   }
              ACCESS  read-write
              STATUS  mandatory
              DESCRIPTION
                      "Backplane insertion status for this unit." 
              ::= { fEthernetTableEntry 6 }

          fEthernetBkPlnTimeStamp    OBJECT-TYPE
              SYNTAX  TimeTicks
              ACCESS  read-only
              STATUS  mandatory
              DESCRIPTION
                     "The time the backplane insert status (was) last changed."
              ::= { fEthernetTableEntry 7 }

          fEthernetMgmtStatus     OBJECT-TYPE
              SYNTAX  INTEGER {
                          operational(1),
                          down(2)
                   }
              ACCESS  read-only
              STATUS  mandatory
              DESCRIPTION
                      "The operational status of this unit."
              ::= { fEthernetTableEntry 8 }

          fEthernetProxyAgentID      OBJECT-TYPE
              SYNTAX  OCTET STRING (SIZE (6..6))  -- the MAC address of the
                                                  -- interface in the agent
              ACCESS  read-only
              STATUS  mandatory
              DESCRIPTION
                      "The physical layer MAC Address of the agent."
              ::= { fEthernetTableEntry 9 }

          fEthernetTemperatureStatus     OBJECT-TYPE
              SYNTAX  INTEGER {
                          ok(1),
                          bad(2)
                   }
              ACCESS  read-only
              STATUS  mandatory
              DESCRIPTION
                      "The temperature status of this unit."
              ::= { fEthernetTableEntry 10 }

          fEthernetCodeVersion      OBJECT-TYPE
              SYNTAX  OCTET STRING (SIZE (2..2))  
              ACCESS  read-only
              STATUS  mandatory
              DESCRIPTION
                      "The firmware version number of this unit."
              ::= { fEthernetTableEntry 11 }

          fEthernetRawCommandData      OBJECT-TYPE
              SYNTAX  OCTET STRING (SIZE (1..255))  
              ACCESS  read-write
              STATUS  mandatory
              DESCRIPTION
                      "This is used to send raw 485 serial data to
                       this unit."
              ::= { fEthernetTableEntry 12 }

          fEthernetPowerStatus        OBJECT-TYPE
              SYNTAX  INTEGER {
                                  singleSupOK(1),                 
                                  dualSupOK(2),            
                                  dualSup-BSupBAD(3),
                                  dualSup-ASupBAD(4),
                                  illegal(5)
                  }
              ACCESS  read-only
              STATUS  mandatory
              DESCRIPTION
                      "The status of the power supply as seen by this unit."
              ::=  { fEthernetTableEntry 13 }

          fEthernetCageType OBJECT-TYPE
              SYNTAX  INTEGER {
                                  twoslot-10100(1),  
                                  fiveslot-10101(2),
                                  fiveslotredundant-10102(3),
                                  reserved4(4),    
                                  reserved5(5),             
                                  reserved6(6),
                                  reserved7(7),             
                                  reserved8(8)
                           }
              ACCESS  read-only
              STATUS  mandatory
              DESCRIPTION
                      "The model number of the fseries chassis the card is is."
              ::= {  fEthernetTableEntry 14 }

--
-- This is the beginning of the Star-Tek enterprise specific MIB.
-- This is implemented by all Star-Tek products which support
-- management via SNMP.
-- 
--         STARTEK-MIB DEFINTIONS ::= BEGIN
--
--           IMPORTS
--             enterprises            FROM RFC1155-SMI;


          rmonAgent     OBJECT IDENTIFIER ::= { fSeries 7 }

          -- Agent group

          rmonAgentDescription      OBJECT-TYPE
              SYNTAX  DisplayString    (SIZE (0..255))
              ACCESS  read-write
              STATUS  mandatory
              DESCRIPTION
                      "The text name for this agent."
              ::=  { rmonAgent 1 }

          rmonAgentID      OBJECT-TYPE
              SYNTAX  OCTET STRING (SIZE (6..6))
              ACCESS  read-only
              STATUS  mandatory
              DESCRIPTION
                      "The text name for this agent."
              ::=  { rmonAgent 2 }

          rmonAgentOOBNumber OBJECT-TYPE
              SYNTAX  INTEGER
              ACCESS  read-only
              STATUS  mandatory
              DESCRIPTION
                      "The number of items in connection table"
              ::= { rmonAgent 3 }

          rmonAgentOOBTable OBJECT-TYPE
              SYNTAX  SEQUENCE OF RmonAgentOOBTableEntry
              ACCESS  not-accessible
              STATUS  mandatory
              ::= { rmonAgent 4 }

          rmonAgentOOBTableEntry      OBJECT-TYPE
              SYNTAX  RmonAgentOOBTableEntry
              ACCESS  not-accessible
              STATUS  mandatory
              DESCRIPTION
                      "An entry in the rmonAgentOOBTable."
              INDEX   { rmonAgentOOBTableIndex }
              ::= { rmonAgentOOBTable 1 }

          RmonAgentOOBTableEntry ::=
                  SEQUENCE  {
                          rmonAgentOOBTableIndex             INTEGER,
                          rmonAgentOOBTableDescription       DisplayString,
                          rmonAgentOOBTableData              Opaque,
			  rmonAgentOOBRawDataCommand	     OCTET STRING
                       }

          rmonAgentOOBTableIndex      OBJECT-TYPE
              SYNTAX  INTEGER
              ACCESS  read-only
              STATUS  mandatory
              DESCRIPTION
                      "The index of this entry."
              ::=  { rmonAgentOOBTableEntry 1 }

          rmonAgentOOBTableDescription      OBJECT-TYPE
              SYNTAX  DisplayString    (SIZE (0..255))
              ACCESS  read-write
              STATUS  mandatory
              DESCRIPTION
                      "The text description of this OOB (Out Of Band) table."
              ::=  { rmonAgentOOBTableEntry 2 }

          rmonAgentOOBTableData         OBJECT-TYPE
              SYNTAX  Opaque
              ACCESS  read-only
              STATUS  mandatory
              DESCRIPTION
                      "An opaque data structure used for management."
              ::=  { rmonAgentOOBTableEntry 3 }

          rmonAgentOOBRawDataCommand      OBJECT-TYPE
              SYNTAX  OCTET STRING (SIZE (1..255))  
              ACCESS  read-write
              STATUS  mandatory
              DESCRIPTION
                      "Raw method of sending data on channel."
              ::=  { rmonAgentOOBTableEntry 4 }

          rmonAgentIBNumber OBJECT-TYPE
              SYNTAX  INTEGER
              ACCESS  read-only
              STATUS  mandatory
              DESCRIPTION
                      "The number of items in the connection table."
              ::= { rmonAgent 5 }

          rmonAgentIBTable OBJECT-TYPE
              SYNTAX  SEQUENCE OF RmonAgentIBTableEntry
              ACCESS  not-accessible
              STATUS  mandatory
              ::= { rmonAgent 6 }

          rmonAgentIBTableEntry      OBJECT-TYPE
              SYNTAX  RmonAgentIBTableEntry
              ACCESS  not-accessible
              STATUS  mandatory
              DESCRIPTION
                      "An entry in the rmonAgentIBTable."
              INDEX   { rmonAgentIBTableIndex }
              ::= { rmonAgentIBTable 1 }

          RmonAgentIBTableEntry ::=
                  SEQUENCE  {
                          rmonAgentIBTableIndex             INTEGER,
                          rmonAgentIBTableDescription       DisplayString,
                          rmonAgentIBNetworkType            INTEGER,
                          rmonAgentIBSampleInterval         INTEGER,
                          rmonAgentIBMacFrames              INTEGER,
                          rmonAgentIBDataFrames             INTEGER,
                          rmonAgentIBMacBytes               INTEGER,
                          rmonAgentIBDataBytes              INTEGER,
                          rmonAgentIBUtilization            INTEGER,
                          rmonAgentIBMACUtilization         INTEGER,
                          rmonAgentIBNonMACUtilization      INTEGER,
                          rmonAgentIBMACData0               Opaque,
                          rmonAgentIBMACData1               Opaque,
                          rmonAgentIBMACData2               Opaque,
                          rmonAgentIBMACData3               Opaque,
                          rmonAgentIBMACData4               Opaque,
                          rmonAgentIBMACData5               Opaque,
                          rmonAgentIBMACData6               Opaque,
                          rmonAgentIBMACData7               Opaque,
                          rmonAgentIBMACData8               Opaque,
                          rmonAgentIBMACData9               Opaque,
                          rmonAgentIBMACData10              Opaque,
                          rmonAgentIBMACData11              Opaque
                       }

          rmonAgentIBTableIndex      OBJECT-TYPE
              SYNTAX  INTEGER
              ACCESS  read-only
              STATUS  mandatory
              ::=  { rmonAgentIBTableEntry 1 }

          rmonAgentIBTableDescription      OBJECT-TYPE
              SYNTAX  DisplayString    (SIZE (0..255))
              ACCESS  read-write
              STATUS  mandatory
              DESCRIPTION
                      "The text description of this IB (In Band) Table."
              ::=  { rmonAgentIBTableEntry 2 }

          rmonAgentIBNetworkType      OBJECT-TYPE
              SYNTAX  INTEGER {
                          tokenring(1),
                          ethernet(2),
                          fddi(3)
                   }
              ACCESS  read-only
              STATUS  mandatory
              ::=  { rmonAgentIBTableEntry 3 }

          rmonAgentIBSampleInterval      OBJECT-TYPE
              SYNTAX  Counter
              ACCESS  read-write
              STATUS  mandatory
              ::=  { rmonAgentIBTableEntry 4 }

          rmonAgentIBMacFrames     OBJECT-TYPE
              SYNTAX  Counter
              ACCESS  read-only
              STATUS  mandatory
              ::=  { rmonAgentIBTableEntry 5 }

          rmonAgentIBDataFrames      OBJECT-TYPE
              SYNTAX  Counter
              ACCESS  read-only
              STATUS  mandatory
              ::=  { rmonAgentIBTableEntry 6 }

          rmonAgentIBMacBytes      OBJECT-TYPE
              SYNTAX  Counter
              ACCESS  read-only
              STATUS  mandatory
              ::=  { rmonAgentIBTableEntry 7 }

          rmonAgentIBDataBytes      OBJECT-TYPE
              SYNTAX  Counter
              ACCESS  read-only
              STATUS  mandatory
              ::=  { rmonAgentIBTableEntry 8 }

          rmonAgentIBUtilization      OBJECT-TYPE
              SYNTAX  Counter
              ACCESS  read-only
              STATUS  mandatory
              ::=  { rmonAgentIBTableEntry 9 }

          rmonAgentIBMACUtilization      OBJECT-TYPE
              SYNTAX  Counter
              ACCESS  read-only
              STATUS  mandatory
              ::=  { rmonAgentIBTableEntry 10 }

          rmonAgentIBNonMACUtilization      OBJECT-TYPE
              SYNTAX  Counter
              ACCESS  read-only
              STATUS  mandatory
              ::=  { rmonAgentIBTableEntry 11 }

          rmonAgentIBMACData0          OBJECT-TYPE
              SYNTAX  Opaque
              ACCESS  read-only
              STATUS  mandatory
              DESCRIPTION
                      "An opaque data structure used for management."
              ::=  { rmonAgentIBTableEntry 12 }

          rmonAgentIBMACData1          OBJECT-TYPE
              SYNTAX  Opaque
              ACCESS  read-only
              STATUS  mandatory
              DESCRIPTION
                      "An opaque data structure used for management."
              ::=  { rmonAgentIBTableEntry 13 }

          rmonAgentIBMACData2          OBJECT-TYPE
              SYNTAX  Opaque
              ACCESS  read-only
              STATUS  mandatory
              DESCRIPTION
                      "An opaque data structure used for management."
              ::=  { rmonAgentIBTableEntry 14 }

          rmonAgentIBMACData3          OBJECT-TYPE
              SYNTAX  Opaque
              ACCESS  read-only
              STATUS  mandatory
              DESCRIPTION
                      "An opaque data structure used for management."
              ::=  { rmonAgentIBTableEntry 15 }

          rmonAgentIBMACData4          OBJECT-TYPE
              SYNTAX  Opaque
              ACCESS  read-only
              STATUS  mandatory
              DESCRIPTION
                      "An opaque data structure used for management."
              ::=  { rmonAgentIBTableEntry 16 }

          rmonAgentIBMACData5          OBJECT-TYPE
              SYNTAX  Opaque
              ACCESS  read-only
              STATUS  mandatory
              DESCRIPTION
                      "An opaque data structure used for management."
              ::=  { rmonAgentIBTableEntry 17 }

          rmonAgentIBMACData6          OBJECT-TYPE
              SYNTAX  Opaque
              ACCESS  read-only
              STATUS  mandatory
              DESCRIPTION
                      "An opaque data structure used for management."
              ::=  { rmonAgentIBTableEntry 18 }

          rmonAgentIBMACData7          OBJECT-TYPE
              SYNTAX  Opaque
              ACCESS  read-only
              STATUS  mandatory
              DESCRIPTION
                      "An opaque data structure used for management."
              ::=  { rmonAgentIBTableEntry 19 }

          rmonAgentIBMACData8          OBJECT-TYPE
              SYNTAX  Opaque
              ACCESS  read-only
              STATUS  mandatory
              DESCRIPTION
                      "An opaque data structure used for management."
              ::=  { rmonAgentIBTableEntry 20 }

          rmonAgentIBMACData9          OBJECT-TYPE
              SYNTAX  Opaque
              ACCESS  read-only
              STATUS  mandatory
              DESCRIPTION
                      "An opaque data structure used for management."
              ::=  { rmonAgentIBTableEntry 21 }

          rmonAgentIBMACData10          OBJECT-TYPE
              SYNTAX  Opaque
              ACCESS  read-only
              STATUS  mandatory
              DESCRIPTION
                      "An opaque data structure used for management."
              ::=  { rmonAgentIBTableEntry 22 }

          rmonAgentIBMACData11          OBJECT-TYPE
              SYNTAX  Opaque
              ACCESS  read-only
              STATUS  mandatory
              DESCRIPTION
                      "An opaque data structure used for management."
              ::=  { rmonAgentIBTableEntry 23 }

          rmonAgentMonitorCommand      OBJECT-TYPE
              SYNTAX  DisplayString   (SIZE (0..255))
              ACCESS  read-write
              STATUS  mandatory
              DESCRIPTION
                      "A method of sending raw commands to the agent monitor."
              ::=  { rmonAgent 7 }

          rmonAgentMonitorResponse      OBJECT-TYPE
              SYNTAX  DisplayString   (SIZE (0..1024))
              ACCESS  read-only
              STATUS  mandatory
              DESCRIPTION
                      "This parameter contains the text response to an
                       agent monitor command."
              ::=  { rmonAgent 8 }

          rmonAgentDownloadData      OBJECT-TYPE
              SYNTAX  OCTET STRING  (SIZE (0..255))
              ACCESS  read-write
              STATUS  mandatory
              ::=  { rmonAgent 9 }

          rmonAgentNoMapOid      OBJECT-TYPE
              SYNTAX  OBJECT IDENTIFIER 
              ACCESS  read-write
              STATUS  mandatory
              ::=  { rmonAgent 10 }

          rmonAgentMACStatTable OBJECT-TYPE
              SYNTAX  SEQUENCE OF RmonAgentMACStatTableEntry
              ACCESS  not-accessible
              STATUS  mandatory
              ::= { rmonAgent 11 }

          rmonAgentMACStatTableEntry      OBJECT-TYPE
              SYNTAX  RmonAgentMACStatTableEntry
              ACCESS  not-accessible
              STATUS  mandatory
              DESCRIPTION
                      "An entry in the rmonAgentIBTable."
              INDEX   { INTEGER,  -- Network Interface
                        INTEGER } -- Index Number
              ::= { rmonAgentMACStatTable 1 }

          RmonAgentMACStatTableEntry ::=
                  SEQUENCE  {
                          rmonAgentMACStatTableData          Opaque
                       }

          rmonAgentMACStatTableData          OBJECT-TYPE
              SYNTAX  Opaque
              ACCESS  read-only
              STATUS  mandatory
              DESCRIPTION
                      "An opaque data structure used for management."
              ::=  { rmonAgentMACStatTableEntry 1 }

          rmonAgentIPAdressControl      OBJECT-TYPE
              SYNTAX  Opaque 
              ACCESS  read-write
              STATUS  mandatory
              DESCRIPTION
                      "An opaque data structure used for management."
              ::=  { rmonAgent 12 }




          -- Stackable group
          --
          -- This group supports the LinkBuilder TRi series of
          -- stackable hubs.
          --

          stackableHubs      OBJECT IDENTIFIER ::= { stackable 1 }


          stackableHubNumber OBJECT-TYPE
              SYNTAX  INTEGER
              ACCESS  read-only
              STATUS  mandatory
              DESCRIPTION
                      "The number of items in hub table"
              ::= { stackableHubs 1 }

          stackableHubTable OBJECT-TYPE
              SYNTAX  SEQUENCE OF StackablehubTableEntry
              ACCESS  not-accessible
              STATUS  mandatory
              DESCRIPTION     
                      "A table which maintains a list of all of the intelligent
                       stackable series hubs on the ring being managed by the 
                       addressed agent. This table is indexed by the RS485 OOB 
                       address of the stackable series intelligent hubs."
              ::= { stackableHubs 2 }

          stackableHubTableEntry        OBJECT-TYPE
              SYNTAX  StackablehubTableEntry
              ACCESS  not-accessible
              STATUS  mandatory
              DESCRIPTION
                      "An entry in the stackableHubTable."
              INDEX   { stackableHubTableIndex }
              ::= { stackableHubTable 1 }

          StackablehubTableEntry ::=
              SEQUENCE  {
                      stackableHubTableIndex           INTEGER,
                      stackableHubModel                INTEGER,
                      stackableHub485Address           OCTET STRING,
                      stackableHubRiFTolState          INTEGER,
                      stackableHubRiMask               INTEGER,
                      stackableHubRiPhDet              INTEGER,
                      stackableHubRiNsrtStatus         INTEGER,
                      stackableHubRiBcnRemStatus       INTEGER,
                      stackableHubRiNeighborType       INTEGER,
                      stackableHubRiNeighborAddr       OCTET STRING,
                      stackableHubRiTimeStamp          TimeTicks,
                      stackableHubRoFTolState          INTEGER,
                      stackableHubRoMask               INTEGER,
                      stackableHubRoPhDet              INTEGER,
                      stackableHubRoNsrtStatus         INTEGER,
                      stackableHubRoBcnRemStatus       INTEGER,
                      stackableHubRoNeighborType       INTEGER,
                      stackableHubRoNeighborAddr       OCTET STRING,
                      stackableHubRoTimeStamp          TimeTicks,
                      stackableHubDataRateState        INTEGER,
                      stackableHubDataRateTimeStamp    TimeTicks,
                      stackableHubMgmtStatus           INTEGER,
                      stackableHubProxyAgentID         OCTET STRING,
                      stackableHubAttachedAgentType    INTEGER,
                      stackableHubAttachedAgentState   INTEGER,
                      stackableHubTemperatureStatus    INTEGER,
                      stackableHubAutoRecovControl     INTEGER,
                      stackableHubAutoRecovRetries     INTEGER,
                      stackableHubCodeVersion          OCTET STRING,
                      stackableHubAutoRecovState       INTEGER,
                      stackableHubRawCommandData       OCTET STRING,
                      stackableHubAutoRecovMode        INTEGER
                      }

          stackableHubTableIndex        OBJECT-TYPE
              SYNTAX  INTEGER
              ACCESS  read-only
              STATUS  mandatory
              DESCRIPTION
                      "The index for this hub entry"
              ::= { stackableHubTableEntry 1 }

          stackableHubModel     OBJECT-TYPE
              SYNTAX  INTEGER {
                      standard-issue(1)     -- Star-Tek stackable unit  
                      }
              ACCESS  read-only
              STATUS  mandatory
              DESCRIPTION     
                      "The model number of the stackable series hub being
                       managed."
              ::= { stackableHubTableEntry 2 }

          stackableHub485Address        OBJECT-TYPE
              SYNTAX  OCTET STRING (SIZE (3..3))
              ACCESS  read-only
              STATUS  mandatory
              DESCRIPTION
                      "The 6 hex digit address used on the RS485 serial OOB 
                       management channel."
              ::=     { stackableHubTableEntry 3 }

          stackableHubRiFTolState       OBJECT-TYPE
              SYNTAX  INTEGER {
                          off(1),
                          on(2)
                  }
              ACCESS  read-write
              STATUS  mandatory
              DESCRIPTION
                     "This parameter controls the Ring In (RI) fault tolerance 
                      behavior. Off(1) means that phantom current is not used
                      on the corresponding RI interface as a condition for main
                      ring link insertion. On (2) means tha phantom current is
                      used on the corresponding RI interface as a condition for
                      main ring link insertion. The preferred setting for this
                      parameter is on (2)."
              ::= { stackableHubTableEntry 4 }

          stackableHubRiMask    OBJECT-TYPE
              SYNTAX  INTEGER {
                          isolate(1),
                          enable(2)
                  }
              ACCESS  read-write
              STATUS  mandatory
              DESCRIPTION
                      "Administrative status for this Ring In port. By
                       setting this parameter, a remote manager can control
                       the partitioning of this port."
              ::= { stackableHubTableEntry 5 }

          stackableHubRiPhDet   OBJECT-TYPE
              SYNTAX  INTEGER {
                          noPhantom(1),
                          phantDetected(2)
                  }
              ACCESS  read-only
              STATUS  mandatory
              DESCRIPTION
                      "This parameter describes the phantom detect status for
                       this Ring In port."
              ::= { stackableHubTableEntry 6 }

          stackableHubRiNsrtStatus  OBJECT-TYPE
              SYNTAX  INTEGER {
                          bypassed(1),
                          inserted(2)
                  }
              ACCESS  read-only
              STATUS  mandatory
              DESCRIPTION
                      "Insertion status for this Ring In port."
              ::= { stackableHubTableEntry 7 }

          stackableHubRiBcnRemStatus    OBJECT-TYPE
              SYNTAX  INTEGER {
                          ok(1),
                          autoIsolated(2)
                  }
              ACCESS  read-only
              STATUS  mandatory
              DESCRIPTION
                      "This parameter describes the result of any automatic 
                       beacon removal operations performed by the agent on this
                       port. Automatic beacon removal operations consist of 
                       agent-initiated isolation of a lobe port in order to 
                       remove the cause of a persistent beaconing condition." 
              ::= { stackableHubTableEntry 8 }

          stackableHubRiNeighborType    OBJECT-TYPE
              SYNTAX  INTEGER {
                          series828(1),
                          fSeries(2),
                          tokenRingMAC(3),
                          none(4),
                          stackable(5)
                  }
              ACCESS  read-only
              STATUS  mandatory
              DESCRIPTION
                      "This parameter indicates the type of nearest neighbor
                       on the Ring In port."
              ::= { stackableHubTableEntry 9 }

          stackableHubRiNeighborAddr    OBJECT-TYPE
              SYNTAX  OCTET STRING (SIZE (2..6))
              ACCESS  read-only
              STATUS  mandatory
              DESCRIPTION
                      "The address of the nearest neighbor on the Ring In port."
              ::= { stackableHubTableEntry 10 }

          stackableHubRiTimeStamp    OBJECT-TYPE
              SYNTAX  TimeTicks
              ACCESS  read-only
              STATUS  mandatory
              DESCRIPTION
                      "The time the status of Ring In (was) last changed."
              ::= { stackableHubTableEntry 11 }

          stackableHubRoFTolState       OBJECT-TYPE
              SYNTAX  INTEGER {
                          off(1),
                          on(2)
                   }
              ACCESS  read-write
              STATUS  mandatory
              DESCRIPTION
                      "This parameter controls the Ring Out(RO) fault tolerance 
                       behavior. Off(1) means that phantom current is not used
                       on the corresponding RO interface as a condition for main
                       ring link insertion. On (2) means tha phantom current is
                       used on the corresponding RO interface as a condition for
                       main ring link insertion. The preferred setting for this
                       parameter is on (2)."
              ::= { stackableHubTableEntry 12 }

          stackableHubRoMask    OBJECT-TYPE
              SYNTAX  INTEGER {
                          isolate(1),
                          enable(2)
                   }
              ACCESS  read-write
              STATUS  mandatory
              DESCRIPTION
                      "Administrative status for this Ring Out port. By
                       setting this parameter, a remote manager can control
                       the partitioning of this port."
              ::= { stackableHubTableEntry 13 }

          stackableHubRoPhDet   OBJECT-TYPE
              SYNTAX  INTEGER {
                          wireFault(1),
                          phantOk(2)      --corresponds to 
                                          --forward ok
                   }
              ACCESS  read-only
              STATUS  mandatory
              DESCRIPTION
                      "This parameter describes the phantom detect status for
                       this Ring Out port."
              ::= { stackableHubTableEntry 14 }

          stackableHubRoNsrtStatus      OBJECT-TYPE
              SYNTAX  INTEGER {
                          bypassed(1),
                          inserted(2)
                   }
              ACCESS  read-only
              STATUS  mandatory
              DESCRIPTION
                      "Insertion status for this Ring Out port."
              ::= { stackableHubTableEntry 15 }

          stackableHubRoBcnRemStatus    OBJECT-TYPE
              SYNTAX  INTEGER {
                          ok(1),
                          autoIsolated(2)
                   }
              ACCESS  read-only
              STATUS  mandatory
              DESCRIPTION
                      "This parameter describes the result of any automatic 
                       beacon removal operations performed by the agent on this
                       port. Automatic beacon removal operations consist of 
                       agent-initiated isolation of a lobe port in order to 
                       remove the cause of a persistent beaconing condition." 
              ::= { stackableHubTableEntry 16 }

          stackableHubRoNeighborType    OBJECT-TYPE
              SYNTAX  INTEGER {
                          series828(1),
                          fSeries(2),
                          tokenRingMAC(3),
                          none(4),
                          stackable(5)
                  }
              ACCESS  read-only
              STATUS  mandatory
              DESCRIPTION
                      "This parameter indicates the type of nearest neighbor
                       on the Ring Out port."
              ::= { stackableHubTableEntry 17 }

          stackableHubRoNeighborAddr    OBJECT-TYPE
              SYNTAX  OCTET STRING (SIZE (2..6))
              ACCESS  read-only
              STATUS  mandatory
              DESCRIPTION
                      "The address of the nearest neighbor on the Ring Out
                       port."
              ::= { stackableHubTableEntry 18 }

          stackableHubRoTimeStamp    OBJECT-TYPE
              SYNTAX  TimeTicks
              ACCESS  read-only
              STATUS  mandatory
              DESCRIPTION
                      "The time the status of Ring Out (was) last changed."
              ::= { stackableHubTableEntry 19 }

          stackableHubDataRateState     OBJECT-TYPE
              SYNTAX  INTEGER {
                          s4Mbps(1),
                          s16Mbps(2),
                          autoConfig(3)
                   }
              ACCESS  read-write
              STATUS  mandatory
              DESCRIPTION
                      "This parameter indicates the current data rate of
                       this unit."
              ::= { stackableHubTableEntry 20 }

          stackableHubDataRateTimeStamp    OBJECT-TYPE
              SYNTAX  TimeTicks
              ACCESS  read-only
              STATUS  mandatory
              DESCRIPTION
                      "The time the data rate status (was) last changed."
              ::= { stackableHubTableEntry 21 }

          stackableHubMgmtStatus     OBJECT-TYPE
              SYNTAX  INTEGER {
                          operational(1),
                          down(2)
                   }
              ACCESS  read-only
              STATUS  mandatory
              DESCRIPTION
                      "The operational status of this unit."
              ::= { stackableHubTableEntry 22 }

          stackableHubProxyAgentID      OBJECT-TYPE
              SYNTAX  OCTET STRING (SIZE (6..6))  -- the MAC address of the
                                                  -- TR interface in the agent
              ACCESS  read-only
              STATUS  mandatory
              DESCRIPTION
                      "The physical layer MAC Address of the agent."
              ::= { stackableHubTableEntry 23 }

          stackableHubAttachedAgentType      OBJECT-TYPE
              SYNTAX  INTEGER {
                              tokenring(1),
                              tokenring-ethernet(2),
                              reserved(3),
                              none(4)
                  }
              ACCESS  read-only
              STATUS  mandatory
              DESCRIPTION
                      "The type of the attached agent."
              ::=  { stackableHubTableEntry 24 }

          stackableHubAttachedAgentState     OBJECT-TYPE
              SYNTAX  INTEGER {
                              enabled(1),
                              disabled(2),
                              not-applicable(3)
                  }
              ACCESS  read-write
              STATUS  mandatory
              DESCRIPTION
                      "The state of the attached agent."
              ::=  { stackableHubTableEntry 25 }

          stackableHubTemperatureStatus      OBJECT-TYPE
              SYNTAX  INTEGER {
                              ok(1),
                              bad(2)
                  }
              ACCESS  read-only
              STATUS  mandatory
              DESCRIPTION
                      "The temperature status of this unit."
              ::=  { stackableHubTableEntry 26 }

          stackableHubAutoRecovControl       OBJECT-TYPE
              SYNTAX  INTEGER {
                              enabled(1),
                              disabled(2),
                              reset(3), 
                              unknown(4)
                  }
              ACCESS  read-write
              STATUS  mandatory
              DESCRIPTION
                      "This parameter controls the auto recovery operation
                       of this unit."
              ::=  { stackableHubTableEntry 27 }

          stackableHubAutoRecovRetries       OBJECT-TYPE
              SYNTAX  INTEGER (1..255)
              ACCESS  read-write
              STATUS  mandatory
              DESCRIPTION
                      "The number of Auto Recoveries performed by this unit."
              ::=  { stackableHubTableEntry 28 }

          stackableHubCodeVersion      OBJECT-TYPE
              SYNTAX  OCTET STRING (SIZE (2..2))  
              ACCESS  read-only
              STATUS  mandatory
              DESCRIPTION
                      "The firmware version number of this unit."
              ::= { stackableHubTableEntry 29 }

          stackableHubAutoRecovState         OBJECT-TYPE
              SYNTAX  INTEGER {
                              in-recovery(1),
                              normal(2),
                              halted(3)
                  }
              ACCESS  read-only
              STATUS  mandatory
              DESCRIPTION
                      "The auto recovery state of this unit."
              ::=  { stackableHubTableEntry 30 }

          stackableHubRawCommandData      OBJECT-TYPE
              SYNTAX  OCTET STRING (SIZE (1..255))  
              ACCESS  read-write
              STATUS  mandatory
              DESCRIPTION
                      "This is used to send raw 485 serial data to
                       this unit."
              ::= { stackableHubTableEntry 31 }

          stackableHubAutoRecovMode     OBJECT-TYPE
              SYNTAX  INTEGER {
                          selfEnabling(1),
                          non-selfEnabling(2)
                   }
              ACCESS  read-write
              STATUS  mandatory
              DESCRIPTION
                      "This parameter describes the auto recovery mode."
              ::= { stackableHubTableEntry 32 }


          --- 

          stackableHubLobeNumber OBJECT-TYPE
              SYNTAX  INTEGER
              ACCESS  read-only
              STATUS  mandatory
              DESCRIPTION
                      "The number of items in the hub lobe table."
              ::= { stackableHubs 3 }


          -- Connections table for stackable hubs

          stackableHubLobeTable OBJECT-TYPE
              SYNTAX  SEQUENCE OF StackablehubLobeEntry
              ACCESS  not-accessible
              STATUS  mandatory
              DESCRIPTION     
                      "A table which contains the control and status 
                       information for the lobes."
              ::= { stackableHubs 4 }

          stackableHubLobeEntry OBJECT-TYPE
              SYNTAX  StackablehubLobeEntry
              ACCESS  not-accessible
              STATUS  mandatory
              DESCRIPTION
                      "A collection of control and status parameters kept for
                       each lobe."
              INDEX   { stackableHubIndex, stackableHubLobePort  }
              ::= { stackableHubLobeTable 1 }

          StackablehubLobeEntry ::=
                  SEQUENCE  {
                          stackableHubIndex             INTEGER,
                          stackableHubLobePort          INTEGER,
                          stackableHubLobePhDet         INTEGER,
                          stackableHubLobeMask          INTEGER,
                          stackableHubLobeNsrtStatus    INTEGER,
                          stackableHubLobeMacAddr       OCTET STRING,
                          stackableHubLobeBcnRemStatus  INTEGER,
                          stackableHubLobeBcnRemCause   INTEGER,
                          stackableHubLobeTimeStamp     TimeTicks
                   }

          stackableHubIndex OBJECT-TYPE
              SYNTAX  INTEGER
              ACCESS  read-only
              STATUS  mandatory
              DESCRIPTION
                      "The index into the stackableHubTable of the mau
                       this lobe is on."
              ::=  { stackableHubLobeEntry 1 }

          stackableHubLobePort OBJECT-TYPE
              SYNTAX  INTEGER
              ACCESS  read-only
              STATUS  mandatory
              DESCRIPTION
                      "The port of the mau this lobe is on."
              ::=  { stackableHubLobeEntry 2 }

          stackableHubLobePhDet  OBJECT-TYPE
              SYNTAX  INTEGER {
                                  noPhantom(1),
                                  phantDetected(2)
                           }
              ACCESS  read-only
              STATUS  mandatory
              DESCRIPTION
                      "Phantom current status for this lobe port. A value of 1 
                       corresponds to no phantom current detected. A value of 2 
                       corresponds to phantom presence." 
              ::=  { stackableHubLobeEntry 3 }

          stackableHubLobeMask    OBJECT-TYPE
              SYNTAX  INTEGER {
                                  isolated(1),
                                  enabled(2)
                           }
              ACCESS  read-write
              STATUS  mandatory
              DESCRIPTION
                      "Administrative status for this lobe port. By setting 
                      this parameter, a remote manager can control access to 
                      the lobe port." 
              ::=  { stackableHubLobeEntry 4 }

          stackableHubLobeNsrtStatus    OBJECT-TYPE
              SYNTAX  INTEGER {
                                  bypassed(1),
                                  inserted(2)
                           }
              ACCESS  read-only
              STATUS  mandatory
              DESCRIPTION
                      "Actual insertion status for this lobe port. A 1 value 
                       means that the corresponding station is not connected to 
                       the ring. A 2 value means that the corresponding station 
                       is connected to the ring." 
              ::=  { stackableHubLobeEntry 5 }

          stackableHubLobeMacAddr       OBJECT-TYPE
              SYNTAX  OCTET STRING (SIZE (6..6))
              ACCESS  read-only
              STATUS  mandatory
              DESCRIPTION
                      "The MAC layer address of the station which is attached 
                       to the corresponding lobe port."
              ::=  { stackableHubLobeEntry 6 }

          stackableHubLobeBcnRemStatus  OBJECT-TYPE
              SYNTAX  INTEGER {
                          ok(1),
                          autoIsolated(2),
                          unknown(3)
                   }
              ACCESS  read-only
              STATUS  mandatory
              DESCRIPTION
                      "This parameter describes the result of any automatic 
                       beacon removal operations performed by the agent on this
                       port. Automatic beacon removal operations consist of 
                       agent-initiated isolation of a lobe port in order to 
                       remove the cause of a persistent beaconing condition." 
              ::=  { stackableHubLobeEntry 7 }

          stackableHubLobeBcnRemCause  OBJECT-TYPE
              SYNTAX  INTEGER {
                          no-removal(1),
                          phantom-error(2),
                          no-carrier(3),
                          bad-rate(4),
                          unknown(5)
                   }
              ACCESS  read-only
              STATUS  mandatory
              DESCRIPTION
                      "This parameter describes the cause of any automatic 
                       beacon removal operations performed by the agent on this
                       port." 
              ::=  { stackableHubLobeEntry 8 }

          stackableHubLobeTimeStamp      OBJECT-TYPE
              SYNTAX  TimeTicks
              ACCESS  read-only
              STATUS  mandatory
              DESCRIPTION
                      "The time the status of this lobe (was) last changed."
              ::=  { stackableHubLobeEntry 9 }

--  END



          -- SuperStack group
          --
          -- This group supports the SuperStack series of 
          -- stackable hubs.
          --

          superStackHubs      OBJECT IDENTIFIER ::= { stackable 2 }


          superStackHubNumber OBJECT-TYPE
              SYNTAX  INTEGER
              ACCESS  read-only
              STATUS  mandatory
              DESCRIPTION
                      "The number of items in hub table"
              ::= { superStackHubs 1 }

          superStackHubTable OBJECT-TYPE
              SYNTAX  SEQUENCE OF SuperStackHubTableEntry
              ACCESS  not-accessible
              STATUS  mandatory
              DESCRIPTION     
                      "A table which maintains a list of all of the intelligent
                       superStack series hubs on the ring being managed by the 
                       addressed agent. This table is indexed by the RS485 OOB 
                       address of the superStack series intelligent hubs."
              ::= { superStackHubs 2 }

          superStackHubTableEntry        OBJECT-TYPE
              SYNTAX  SuperStackHubTableEntry
              ACCESS  not-accessible
              STATUS  mandatory
              DESCRIPTION
                      "An entry in the superStackHubTable."
              INDEX   { superStackHubTableIndex }
              ::= { superStackHubTable 1 }

          SuperStackHubTableEntry ::=
              SEQUENCE  {
                      superStackHubTableIndex              INTEGER,                -- 1
                      superStackHubModel                   INTEGER,                -- 2
                      superStackHub485Address              OCTET STRING,           -- 3
                      superStackHubStackPosition           INTEGER,                -- 4
                      superStackHubRiConfiguration         INTEGER,                -- 5
                      superStackHubRiFTolState             INTEGER,                -- 6
                      superStackHubRiMask                  INTEGER,                -- 7
                      superStackHubRiPhDet                 INTEGER,                -- 8
                      superStackHubRiNsrtStatus            INTEGER,                -- 9
                      superStackHubRiBcnRemStatus          INTEGER,                -- 10
                      superStackHubRoConfiguration         INTEGER,                -- 11
                      superStackHubRoFTolState             INTEGER,                -- 12
                      superStackHubRoMask                  INTEGER,                -- 13
                      superStackHubRoPhDet                 INTEGER,                -- 14
                      superStackHubRoNsrtStatus            INTEGER,                -- 15
                      superStackHubRoBcnRemStatus          INTEGER,                -- 16
                      superStackHubCascadeUpMask           INTEGER,                -- 17
                      superStackHubCascadeUpPhDet          INTEGER,                -- 18
                      superStackHubCascadeUpNsrtStatus     INTEGER,                -- 19
                      superStackHubCascadeUpBcnRemStatus   INTEGER,                -- 20
                      superStackHubCascadeDownMask         INTEGER,                -- 21
                      superStackHubCascadeDownPhDet        INTEGER,                -- 22
                      superStackHubCascadeDownNsrtStatus   INTEGER,                -- 23
                      superStackHubCascadeDownBcnRemStatus INTEGER,                -- 24
                      superStackHubDataRateState           INTEGER,                -- 25
                      superStackHubDataDeviceTimeStamp     TimeTicks,              -- 26
                      superStackHubMgmtStatus              INTEGER,                -- 27
                      superStackHubProxyAgentID            OCTET STRING,           -- 28
                      superStackHubAttachedAgentType       INTEGER,                -- 29
                      superStackHubAttachedAgentState      INTEGER,                -- 30
                      superStackHubAttachedAgentControl    INTEGER,                -- 31
                      superStackHubTemperatureStatus       INTEGER,                -- 32
                      superStackHubPowerStatus             INTEGER,                -- 33
                      superStackHubAutoRecovControl        INTEGER,                -- 34
                      superStackHubAutoRecovRetries        INTEGER,                -- 35
                      superStackHubCodeVersion             OCTET STRING,           -- 36
                      superStackHubAutoRecovState          INTEGER,                -- 37
                      superStackHubRawCommandData          OCTET STRING,           -- 38
                      superStackHubAutoRecovMode           INTEGER,                -- 39
                      superStackHubRouterPortPhDet         INTEGER,                -- 40
                      superStackHubRouterPortMask          INTEGER,                -- 41
                      superStackHubRouterPortNsrtStatus    INTEGER,                -- 42
                      superStackHubRouterPortMacAddr       OCTET STRING,           -- 43
                      superStackHubRouterPortBcnRemStatus  INTEGER,                -- 44
                      superStackHubRouterPortBcnRemCause   INTEGER                 -- 45
                      }

          superStackHubTableIndex        OBJECT-TYPE
              SYNTAX  INTEGER
              ACCESS  read-only
              STATUS  mandatory
              DESCRIPTION
                      "The index for this hub entry"
              ::= { superStackHubTableEntry 1 }

          superStackHubModel     OBJECT-TYPE
              SYNTAX  INTEGER {
                      active-12-port-base-mau(1),         -- 3Com superStack base unit  
                      active-24-port-expansion-mau(2)     -- 3Com superStack expansion unit  
                      }
              ACCESS  read-only
              STATUS  mandatory
              DESCRIPTION     
                      "The model number of the superStack series hub being
                       managed."
              ::= { superStackHubTableEntry 2 }

          superStackHub485Address        OBJECT-TYPE
              SYNTAX  OCTET STRING (SIZE (3..3))
              ACCESS  read-only
              STATUS  mandatory
              DESCRIPTION
                      "The 6 hex digit address used on the RS485 serial OOB 
                       management channel."
              ::=     { superStackHubTableEntry 3 }

          superStackHubStackPosition     OBJECT-TYPE
              SYNTAX  INTEGER 
              ACCESS  read-only
              STATUS  mandatory
              DESCRIPTION     
                      "The integer position in a stack of units.  The top position
                       is 1."
              ::= { superStackHubTableEntry 4 }

          superStackRiConfiguration     OBJECT-TYPE
              SYNTAX  INTEGER {
                      no-ring-in-configured(1),
                      copper-ring-in-configured(2),
                      fiber-ring-in-configured(3),
                      copper-ring-in-disabled(4),
                      fiber-ring-in-disabled(5)
                      }
              ACCESS  read-only
              STATUS  mandatory
              DESCRIPTION     
                      "This parameter describes the physical configured
                       state of Ring In.  Ring In is disabled if there is
                       another Ring In within the cascaded stack of hubs."
              ::= { superStackHubTableEntry 5 }

          superStackHubRiFTolState       OBJECT-TYPE
              SYNTAX  INTEGER {
                          off(1),
                          on(2)
                  }
              ACCESS  read-write
              STATUS  mandatory
              DESCRIPTION
                     "This parameter controls the Ring In (RI) fault tolerance 
                      behavior. Off(1) means that phantom current is not used
                      on the corresponding RI interface as a condition for main
                      ring link insertion. On (2) means tha phantom current is
                      used on the corresponding RI interface as a condition for
                      main ring link insertion. The preferred setting for this
                      parameter is on (2)."
              ::= { superStackHubTableEntry 6 }

          superStackHubRiMask    OBJECT-TYPE
              SYNTAX  INTEGER {
                          isolate(1),
                          enable(2)
                  }
              ACCESS  read-write
              STATUS  mandatory
              DESCRIPTION
                      "Administrative status for this Ring In port. By
                       setting this parameter, a remote manager can control
                       the partitioning of this port."
              ::= { superStackHubTableEntry 7 }

          superStackHubRiPhDet   OBJECT-TYPE
              SYNTAX  INTEGER {
                          noPhantom(1),
                          phantDetected(2)
                  }
              ACCESS  read-only
              STATUS  mandatory
              DESCRIPTION
                      "This parameter describes the phantom detect status for
                       this Ring In port."
              ::= { superStackHubTableEntry 8 }

          superStackHubRiNsrtStatus  OBJECT-TYPE
              SYNTAX  INTEGER {
                          bypassed(1),
                          inserted(2)
                  }
              ACCESS  read-only
              STATUS  mandatory
              DESCRIPTION
                      "Insertion status for this Ring In port."
              ::= { superStackHubTableEntry 9 }

          superStackHubRiBcnRemStatus    OBJECT-TYPE
              SYNTAX  INTEGER {
                          ok(1),
                          autoIsolated(2)
                  }
              ACCESS  read-only
              STATUS  mandatory
              DESCRIPTION
                      "This parameter describes the result of any automatic 
                       beacon removal operations performed by the agent on this
                       port. Automatic beacon removal operations consist of 
                       agent-initiated isolation of a lobe port in order to 
                       remove the cause of a persistent beaconing condition." 
              ::= { superStackHubTableEntry 10 }

          superStackRoConfiguration     OBJECT-TYPE
              SYNTAX  INTEGER {
                      no-ring-out-configured(1),
                      copper-ring-out-configured(2),
                      fiber-ring-out-configured(3),
                      copper-ring-out-disabled(4),
                      fiber-ring-out-disabled(5)
                      }
              ACCESS  read-only
              STATUS  mandatory
              DESCRIPTION     
                      "This parameter describes the physical configured
                       state of Ring Out.  Ring Out is disabled if there is
                       another Ring Out within the cascaded stack of hubs."
              ::= { superStackHubTableEntry 11 }

          superStackHubRoFTolState       OBJECT-TYPE
              SYNTAX  INTEGER {
                          off(1),
                          on(2)
                   }
              ACCESS  read-write
              STATUS  mandatory
              DESCRIPTION
                      "This parameter controls the Ring Out(RO) fault tolerance 
                       behavior. Off(1) means that phantom current is not used
                       on the corresponding RO interface as a condition for main
                       ring link insertion. On (2) means tha phantom current is
                       used on the corresponding RO interface as a condition for
                       main ring link insertion. The preferred setting for this
                       parameter is on (2)."
              ::= { superStackHubTableEntry 12 }

          superStackHubRoMask    OBJECT-TYPE
              SYNTAX  INTEGER {
                          isolate(1),
                          enable(2)
                   }
              ACCESS  read-write
              STATUS  mandatory
              DESCRIPTION
                      "Administrative status for this Ring Out port. By
                       setting this parameter, a remote manager can control
                       the partitioning of this port."
              ::= { superStackHubTableEntry 13 }

          superStackHubRoPhDet   OBJECT-TYPE
              SYNTAX  INTEGER {
                          noPhantom(1),
                          phantDetected(2)
                   }
              ACCESS  read-only
              STATUS  mandatory
              DESCRIPTION
                      "This parameter describes the phantom detect status for
                       this Ring Out port."
              ::= { superStackHubTableEntry 14 }

          superStackHubRoNsrtStatus      OBJECT-TYPE
              SYNTAX  INTEGER {
                          bypassed(1),
                          inserted(2)
                   }
              ACCESS  read-only
              STATUS  mandatory
              DESCRIPTION
                      "Insertion status for this Ring Out port."
              ::= { superStackHubTableEntry 15 }

          superStackHubRoBcnRemStatus    OBJECT-TYPE
              SYNTAX  INTEGER {
                          ok(1),
                          autoIsolated(2)
                   }
              ACCESS  read-only
              STATUS  mandatory
              DESCRIPTION
                      "This parameter describes the result of any automatic 
                       beacon removal operations performed by the agent on this
                       port. Automatic beacon removal operations consist of 
                       agent-initiated isolation of a lobe port in order to 
                       remove the cause of a persistent beaconing condition." 
              ::= { superStackHubTableEntry 16 }

          superStackHubCascadeUpMask    OBJECT-TYPE
              SYNTAX  INTEGER {
                          isolate(1),
                          enable(2)
                   }
              ACCESS  read-write
              STATUS  mandatory
              DESCRIPTION
                      "Administrative status for this Cascade Up connection. By
                       setting this parameter, a remote manager can control
                       the partitioning of this port."
              ::= { superStackHubTableEntry 17 }

          superStackHubCascadeUpPhDet   OBJECT-TYPE
              SYNTAX  INTEGER {
                          noPhantom(1),
                          phantDetected(2)
                   }
              ACCESS  read-only
              STATUS  mandatory
              DESCRIPTION
                      "This parameter describes the phantom detect status for
                       this Cascade Up connection."
              ::= { superStackHubTableEntry 18 }

          superStackHubCascadeUpNsrtStatus      OBJECT-TYPE
              SYNTAX  INTEGER {
                          bypassed(1),
                          inserted(2)
                   }
              ACCESS  read-only
              STATUS  mandatory
              DESCRIPTION
                      "Insertion status for this Cascade Up connection."
              ::= { superStackHubTableEntry 19 }

          superStackHubCascadeUpBcnRemStatus    OBJECT-TYPE
              SYNTAX  INTEGER {
                          ok(1),
                          autoIsolated(2)
                   }
              ACCESS  read-only
              STATUS  mandatory
              DESCRIPTION
                      "This parameter describes the result of any automatic 
                       beacon removal operations performed by the agent on this
                       connection. Automatic beacon removal operations consist of 
                       agent-initiated isolation of a lobe port in order to 
                       remove the cause of a persistent beaconing condition." 
              ::= { superStackHubTableEntry 20 }

          superStackHubCascadeDownMask    OBJECT-TYPE
              SYNTAX  INTEGER {
                          isolate(1),
                          enable(2)
                   }
              ACCESS  read-write
              STATUS  mandatory
              DESCRIPTION
                      "Administrative status for this Cascade Down connection. By
                       setting this parameter, a remote manager can control
                       the partitioning of this port."
              ::= { superStackHubTableEntry 21 }

          superStackHubCascadeDownPhDet   OBJECT-TYPE
              SYNTAX  INTEGER {
                          noPhantom(1),
                          phantDetected(2)
                   }
              ACCESS  read-only
              STATUS  mandatory
              DESCRIPTION
                      "This parameter describes the phantom detect status for
                       this Cascade Down connection."
              ::= { superStackHubTableEntry 22 }

          superStackHubCascadeDownNsrtStatus      OBJECT-TYPE
              SYNTAX  INTEGER {
                          bypassed(1),
                          inserted(2)
                   }
              ACCESS  read-only
              STATUS  mandatory
              DESCRIPTION
                      "Insertion status for this Cascade Down connection."
              ::= { superStackHubTableEntry 23 }

          superStackHubCascadeDownBcnRemStatus    OBJECT-TYPE
              SYNTAX  INTEGER {
                          ok(1),
                          autoIsolated(2)
                   }
              ACCESS  read-only
              STATUS  mandatory
              DESCRIPTION
                      "This parameter describes the result of any automatic 
                       beacon removal operations performed by the agent on this
                       connection. Automatic beacon removal operations consist of 
                       agent-initiated isolation of a lobe port in order to 
                       remove the cause of a persistent beaconing condition." 
              ::= { superStackHubTableEntry 24 }

          superStackHubDataRateState     OBJECT-TYPE
              SYNTAX  INTEGER {
                          s4Mbps(1),
                          s16Mbps(2),
                          autoConfig(3)
                   }
              ACCESS  read-write
              STATUS  mandatory
              DESCRIPTION
                      "This parameter indicates the current data rate of
                       this unit."
              ::= { superStackHubTableEntry 25 }

          superStackHubDeviceTimeStamp    OBJECT-TYPE
              SYNTAX  TimeTicks
              ACCESS  read-only
              STATUS  mandatory
              DESCRIPTION
                      "The time the data rate status (was) last changed."
              ::= { superStackHubTableEntry 26 }

          superStackHubMgmtStatus     OBJECT-TYPE
              SYNTAX  INTEGER {
                          operational(1),
                          down(2)
                   }
              ACCESS  read-only
              STATUS  mandatory
              DESCRIPTION
                      "The operational status of this unit."
              ::= { superStackHubTableEntry 27 }

          superStackHubProxyAgentID      OBJECT-TYPE
              SYNTAX  OCTET STRING (SIZE (6..6))  -- the MAC address of the
                                                  -- TR interface in the agent
              ACCESS  read-only
              STATUS  mandatory
              DESCRIPTION
                      "The physical layer MAC Address of the agent."
              ::= { superStackHubTableEntry 28 }

          superStackHubAttachedAgentType      OBJECT-TYPE
              SYNTAX  INTEGER {
                              none(1),
                              unknown(2),
                              basic-68000(3),
                              advanced-960(4),
                              reserved1(5),
                              reserved2(6),
                              reserved3(7),
                              reserved4(8),
                              reserved5(9)
                  }
              ACCESS  read-only
              STATUS  mandatory
              DESCRIPTION
                      "The type of the attached agent."
              ::=  { superStackHubTableEntry 29 }

          superStackHubAttachedAgentState     OBJECT-TYPE
              SYNTAX  INTEGER {
                              not-applicable(1),
                              normal(2),
                              duplicate-detected(3),
                              management-disabled(4),
                              hardware-faulted(5),
                              agent-MAC-auto-isolated(6),
                              agent-MAC-mgmt-isolated(7),
                              reserved1(8),
                              reserved2(9),
                              reserved3(10),
                              reserved4(11),
                              reserved5(12)
                  }
              ACCESS  read-only
              STATUS  mandatory
              DESCRIPTION
                      "The state of the attached agent."
              ::=  { superStackHubTableEntry 30 }

          superStackHubAttachedAgentControl     OBJECT-TYPE
              SYNTAX  INTEGER {
                          enable(1),
                          disable(2),
                          enable-MAC-insertion(3),
                          isolate-MAC-insertion(4),
                          read-value(5)
                   }
              ACCESS  read-write
              STATUS  mandatory
              DESCRIPTION
                      "This parameter allows control of the agent.  Disabling the agent
                       causes it to stop communicating (via the cascade) with other devices
                       but it still allows for insertion of the MAC. The enable/isolate-MAC-insertion
                       commands cause the agents MAC to be inserted or looped back respectively.
                       this unit."
              ::= { superStackHubTableEntry 31 }

          superStackHubTemperatureStatus      OBJECT-TYPE
              SYNTAX  INTEGER {
                              ok(1),
                              bad(2)
                  }
              ACCESS  read-only
              STATUS  mandatory
              DESCRIPTION
                      "The temperature status of this unit."
              ::=  { superStackHubTableEntry 32 }

          superStackHubPowerStatus      OBJECT-TYPE
              SYNTAX  INTEGER {
                              normal-AC-power(1),
                              normal-redundant-DC-power(2),
                              non-redundant-DC-power(3)
                  }
              ACCESS  read-only
              STATUS  mandatory
              DESCRIPTION
                      "The power status of this unit."
              ::=  { superStackHubTableEntry 33 }

          superStackHubAutoRecovControl       OBJECT-TYPE
              SYNTAX  INTEGER {
                              enabled(1),
                              disabled(2),
                              reset(3), 
                              unknown(4)
                  }
              ACCESS  read-write
              STATUS  mandatory
              DESCRIPTION
                      "This parameter controls the auto recovery operation
                       of this unit."
              ::=  { superStackHubTableEntry 34 }

          superStackHubAutoRecovRetries       OBJECT-TYPE
              SYNTAX  INTEGER (1..255)
              ACCESS  read-write
              STATUS  mandatory
              DESCRIPTION
                      "The number of Auto Recoveries performed by this unit."
              ::=  { superStackHubTableEntry 35 }

          superStackHubCodeVersion      OBJECT-TYPE
              SYNTAX  OCTET STRING (SIZE (2..2))  
              ACCESS  read-only
              STATUS  mandatory
              DESCRIPTION
                      "The firmware version number of this unit."
              ::=  { superStackHubTableEntry 36 }

          superStackHubAutoRecovState         OBJECT-TYPE
              SYNTAX  INTEGER {
                              in-recovery(1),
                              normal(2),
                              halted(3)
                  }
              ACCESS  read-only
              STATUS  mandatory
              DESCRIPTION
                      "The current auto recovery state of this unit."
              ::=  { superStackHubTableEntry 37 }

          superStackHubRawCommandData      OBJECT-TYPE
              SYNTAX  OCTET STRING (SIZE (1..255))  
              ACCESS  read-write
              STATUS  mandatory
              DESCRIPTION
                      "This is used to send raw 485 serial data to
                       this unit."
              ::=  { superStackHubTableEntry 38 }

          superStackHubAutoRecovMode     OBJECT-TYPE
              SYNTAX  INTEGER {
                          selfEnabling(1),
                          non-selfEnabling(2)
                   }
              ACCESS  read-write
              STATUS  mandatory
              DESCRIPTION
                      "This parameter describes the auto recovery mode."
              ::=  { superStackHubTableEntry 39 }

          superStackHubRouterPortPhDet  OBJECT-TYPE
              SYNTAX  INTEGER {
                                  noPhantom(1),
                                  phantDetected(2)
                           }
              ACCESS  read-only
              STATUS  mandatory
              DESCRIPTION
                      "Phantom current status for the router port on rear. A value of 1 
                       corresponds to no phantom current detected. A value of 2 
                       corresponds to phantom presence." 
              ::=  { superStackHubTableEntry 40 }

          superStackHubRouterPortMask    OBJECT-TYPE
              SYNTAX  INTEGER {
                                  isolated(1),
                                  enabled(2)
                           }
              ACCESS  read-write
              STATUS  mandatory
              DESCRIPTION
                      "Administrative status for the router port on rear. By setting 
                      this parameter, a remote manager can control access to 
                      the lobe port." 
              ::=  { superStackHubTableEntry 41 }

          superStackHubRouterPortNsrtStatus    OBJECT-TYPE
              SYNTAX  INTEGER {
                                  bypassed(1),
                                  inserted(2)
                           }
              ACCESS  read-only
              STATUS  mandatory
              DESCRIPTION
                      "Actual insertion status for the router port on rear. A 1 value 
                       means that the corresponding station is not connected to 
                       the ring. A 2 value means that the corresponding station 
                       is connected to the ring." 
              ::=  { superStackHubTableEntry 42 }

          superStackHubRouterPortMacAddr       OBJECT-TYPE
              SYNTAX  OCTET STRING (SIZE (6..6))
              ACCESS  read-only
              STATUS  mandatory
              DESCRIPTION
                      "The MAC layer address of the station which is attached 
                       to the router port on rear."
              ::=  { superStackHubTableEntry 43 }

          superStackHubRouterPortBcnRemStatus  OBJECT-TYPE
              SYNTAX  INTEGER {
                          ok(1),
                          autoIsolated(2),
                          unknown(3)
                   }
              ACCESS  read-only
              STATUS  mandatory
              DESCRIPTION
                      "This parameter describes the result of any automatic 
                       beacon removal operations performed by the agent on the
                       router port. Automatic beacon removal operations consist of 
                       agent-initiated isolation of a lobe port in order to 
                       remove the cause of a persistent beaconing condition." 
              ::=  { superStackHubTableEntry 44 }

          superStackHubRouterPortBcnRemCause  OBJECT-TYPE
              SYNTAX  INTEGER {
                          no-removal(1),
                          phantom-error(2),
                          no-carrier(3),
                          bad-rate(4),
                          unknown(5)
                   }
              ACCESS  read-only
              STATUS  mandatory
              DESCRIPTION
                      "This parameter describes the cause of any automatic 
                       beacon removal operations performed by the agent on this
                       port." 
              ::=  { superStackHubTableEntry 45 }

          --- 

          superStackHubLobeNumber OBJECT-TYPE
              SYNTAX  INTEGER
              ACCESS  read-only
              STATUS  mandatory
              DESCRIPTION
                      "The number of items in the hub lobe table."
              ::= { superStackHubs 3 }


          -- Connections table for superStack hubs

          superStackHubLobeTable OBJECT-TYPE
              SYNTAX  SEQUENCE OF SuperStackHubLobeEntry
              ACCESS  not-accessible
              STATUS  mandatory
              DESCRIPTION     
                      "A table which contains the control and status 
                       information for the lobes."
              ::= { superStackHubs 4 }

          superStackHubLobeEntry OBJECT-TYPE
              SYNTAX  SuperStackHubLobeEntry
              ACCESS  not-accessible
              STATUS  mandatory
              DESCRIPTION
                      "A collection of control and status parameters kept for
                       each lobe."
              INDEX   { superStackHubIndex, superStackHubLobePort  }
              ::= { superStackHubLobeTable 1 }

          SuperStackHubLobeEntry ::=
                  SEQUENCE  {
                          superStackHubIndex             INTEGER,
                          superStackHubLobePort          INTEGER,
                          superStackHubLobeConfig        INTEGER,
                          superStackHubLobePhDet         INTEGER,
                          superStackHubLobeMask          INTEGER,
                          superStackHubLobeNsrtStatus    INTEGER,
                          superStackHubLobeMacAddr       OCTET STRING,
                          superStackHubLobeBcnRemStatus  INTEGER,
                          superStackHubLobeBcnRemCause   INTEGER
                   }

          superStackHubIndex OBJECT-TYPE
              SYNTAX  INTEGER
              ACCESS  read-only
              STATUS  mandatory
              DESCRIPTION
                      "The index into the superStackHubTable of the mau
                       this lobe is on."
              ::=  { superStackHubLobeEntry 1 }

          superStackHubLobePort OBJECT-TYPE
              SYNTAX  INTEGER
              ACCESS  read-only
              STATUS  mandatory
              DESCRIPTION
                      "The port of the mau this lobe is on."
              ::=  { superStackHubLobeEntry 2 }

           superStackHubLobeConfig OBJECT-TYPE
              SYNTAX  INTEGER {
                              user-normal(1),
                              ring-out-unused(2),
                              ring-in-unused(3),
                              unknown(4)
              }

              ACCESS  read-only
              STATUS  mandatory
              DESCRIPTION
                      "The hardware configuration of the port."
              ::=  { superStackHubLobeEntry 3 }

          superStackHubLobePhDet  OBJECT-TYPE
              SYNTAX  INTEGER {
                              noPhantom(1),
                              phantDetected(2)
                           }
              ACCESS  read-only
              STATUS  mandatory
              DESCRIPTION
                      "Phantom current status for this lobe port. A value of 1 
                       corresponds to no phantom current detected. A value of 2 
                       corresponds to phantom presence." 
              ::=  { superStackHubLobeEntry 4 }

          superStackHubLobeMask    OBJECT-TYPE
              SYNTAX  INTEGER {
                                  isolated(1),
                                  enabled(2)
                           }
              ACCESS  read-write
              STATUS  mandatory
              DESCRIPTION
                      "Administrative status for this lobe port. By setting 
                      this parameter, a remote manager can control access to 
                      the lobe port." 
              ::=  { superStackHubLobeEntry 5 }

          superStackHubLobeNsrtStatus    OBJECT-TYPE
              SYNTAX  INTEGER {
                                  bypassed(1),
                                  inserted(2)
                           }
              ACCESS  read-only
              STATUS  mandatory
              DESCRIPTION
                      "Actual insertion status for this lobe port. A 1 value 
                       means that the corresponding station is not connected to 
                       the ring. A 2 value means that the corresponding station 
                       is connected to the ring." 
              ::=  { superStackHubLobeEntry 6 }

          superStackHubLobeMacAddr       OBJECT-TYPE
              SYNTAX  OCTET STRING (SIZE (6..6))
              ACCESS  read-only
              STATUS  mandatory
              DESCRIPTION
                      "The MAC layer address of the station which is attached 
                       to the corresponding lobe port."
              ::=  { superStackHubLobeEntry 7 }

          superStackHubLobeBcnRemStatus  OBJECT-TYPE
              SYNTAX  INTEGER {
                          ok(1),
                          autoIsolated(2),
                          unknown(3)
                   }
              ACCESS  read-only
              STATUS  mandatory
              DESCRIPTION
                      "This parameter describes the result of any automatic 
                       beacon removal operations performed by the agent on this
                       port. Automatic beacon removal operations consist of 
                       agent-initiated isolation of a lobe port in order to 
                       remove the cause of a persistent beaconing condition." 
              ::=  { superStackHubLobeEntry 8 }

          superStackHubLobeBcnRemCause  OBJECT-TYPE
              SYNTAX  INTEGER {
                          no-removal(1),
                          phantom-error(2),
                          no-carrier(3),
                          bad-rate(4),
                          unknown(5)
                   }
              ACCESS  read-only
              STATUS  mandatory
              DESCRIPTION
                      "This parameter describes the cause of any automatic 
                       beacon removal operations performed by the agent on this
                       port." 
              ::=  { superStackHubLobeEntry 9 }

--  END

--
-- This is the beginning of the Star-Tek enterprise specific MIB.
-- This is implemented by all Star-Tek products which support
-- management via SNMP.
-- 
--         STARTEK-MIB DEFINTIONS ::= BEGIN
--

           managers      OBJECT IDENTIFIER ::= { maintenance 1 }

          -- Manager section

          mgrNumber OBJECT-TYPE
              SYNTAX  INTEGER
              ACCESS  read-only
              STATUS  mandatory
              DESCRIPTION
                      "The number of managers in the manager table."
              ::= {  managers 1  }

          mgrAutoAdd OBJECT-TYPE
              SYNTAX  INTEGER { enabled(1), disabled(2)  }
              ACCESS  read-write
              STATUS  mandatory
              DESCRIPTION
                      "This variable indicates whether any manager that
                       communicates with the agent should be added to the
                       manager table."
              ::= {  managers 2  }

          mgrAutoAge OBJECT-TYPE
              SYNTAX  INTEGER { enabled(1), disabled(2)  }
              ACCESS  read-write
              STATUS  mandatory
              DESCRIPTION
                      "When mgrAutoAdd is enabled, this variable then 
                       indicates whether manager entries should 
                       be deleted after 'mgrAgeInterval' ticks.  This
                       variable has no effect when mgrAutoAdd is disabled."
              ::= {  managers 3  }

          mgrAgeInterval OBJECT-TYPE
              SYNTAX  TimeTicks
              ACCESS  read-write
              STATUS  mandatory
              DESCRIPTION
                      "This is the aging interval."
              ::= {  managers 4  }


          -- the Manager table

          mgrTable OBJECT-TYPE
              SYNTAX  SEQUENCE OF MgrEntry
              ACCESS  not-accessible
              STATUS  mandatory
              DESCRIPTION
                      "A list of managers."
              ::= {  managers 5  }

          mgrEntry OBJECT-TYPE
              SYNTAX  MgrEntry
              ACCESS  not-accessible
              STATUS  mandatory
              DESCRIPTION
                      "A manager entry."
              INDEX   { mgrIndex  }
              ::= {  mgrTable 1  }

          MgrEntry ::=
              SEQUENCE {
                  mgrIndex      
                      INTEGER,
                  mgrIpAddr
                      IpAddress,
                  mgrCommunity
                      DisplayString,
                  mgrTimeStamp
                      TimeTicks,
                  mgrStatus
                      INTEGER,
                  mgrPhysAddr
                      OCTET STRING (SIZE(6..6)),
                  mgrInterfaceIndex
                      INTEGER
               }

          mgrIndex OBJECT-TYPE
              SYNTAX  INTEGER 
              ACCESS  read-write
              STATUS  mandatory
              DESCRIPTION
                      "The Index number of the Manager Entry."
              ::= {  mgrEntry 1  }

          mgrIpAddr OBJECT-TYPE
              SYNTAX  IpAddress
              ACCESS  read-write
              STATUS  mandatory
              DESCRIPTION
                      "The IP address of the manager."
              ::= {  mgrEntry 2  }

          mgrCommunity OBJECT-TYPE
              SYNTAX  DisplayString     (SIZE (0..255))
              ACCESS  read-write
              STATUS  mandatory
              DESCRIPTION
                      "The Community of the manager."
              ::= {  mgrEntry 3  }

          mgrTimeStamp OBJECT-TYPE
              SYNTAX  TimeTicks
              ACCESS  read-write
              STATUS  mandatory
              DESCRIPTION
                      "Time of last communication with the manager."
              ::= {  mgrEntry 4  }

          mgrStatus OBJECT-TYPE
              SYNTAX  INTEGER { valid(1), invalid(2)  }
              ACCESS  read-write
              STATUS  mandatory
              DESCRIPTION
                      "The Status of this Entry."
              ::= {  mgrEntry 5  }

          mgrPhysAddr OBJECT-TYPE
              SYNTAX    OCTET STRING (SIZE (6..6))
              ACCESS  read-write
              STATUS  mandatory
              DESCRIPTION
                      "The physical address of the manager entry."
              ::= {  mgrEntry 6  }

          mgrInterfaceIndex OBJECT-TYPE
              SYNTAX  INTEGER 
              ACCESS  read-write
              STATUS  mandatory
              DESCRIPTION
                      "The Interface Index of the manager entry."
              ::= {  mgrEntry 7  }



--
-- This is the beginning of the Star-Tek enterprise specific MIB.
-- This is implemented by all Star-Tek products which support
-- management via SNMP.
-- 
--         STARTEK-MIB DEFINTIONS ::= BEGIN
--
--           IMPORTS
--             enterprises            FROM RFC1155-SMI;


           versions      OBJECT IDENTIFIER ::= { maintenance 2 }
           configuration OBJECT IDENTIFIER ::= { maintenance 3 }



          -- Version section 

          versionHardware OBJECT-TYPE
              SYNTAX    OCTET STRING (SIZE (2..2))
              ACCESS  read-only
              STATUS  mandatory
              DESCRIPTION
                      "The Version of hardware release."
              ::= {  versions 1  }

          versionEPROMFirmware OBJECT-TYPE
              SYNTAX    OCTET STRING (SIZE (2..2))
              ACCESS  read-only
              STATUS  mandatory
              DESCRIPTION
                      "The Version of EPROM release."
              ::= {  versions 2  }

          versionFLASHFirmware OBJECT-TYPE
              SYNTAX    OCTET STRING (SIZE (2..2))
              ACCESS  read-only
              STATUS  mandatory
              DESCRIPTION
                      "The Version of FLASH release."
              ::= {  versions 3  }


          -- Configuration section 

          configEPROMSize OBJECT-TYPE
              SYNTAX  INTEGER
              ACCESS  read-only
              STATUS  mandatory
              DESCRIPTION
                      "The Quantity of EPROM installed (number of bytes)."
              ::= {  configuration 1  }

          configFLASHSize OBJECT-TYPE
              SYNTAX  INTEGER
              ACCESS  read-only
              STATUS  mandatory
              DESCRIPTION
                      "The Quantity of FLASH installed (number of bytes)."
              ::= {  configuration 2  }

          configFLASHCount OBJECT-TYPE
              SYNTAX  INTEGER
              ACCESS  read-only
              STATUS  mandatory
              DESCRIPTION
                      "The Quantity of FLASH installed (number of ICs)."
              ::= {  configuration 3  }

          configDRAMSize OBJECT-TYPE
              SYNTAX  INTEGER
              ACCESS  read-only
              STATUS  mandatory
              DESCRIPTION
                      "The Quantity of DRAM installed (number of bytes)."
              ::= {  configuration 4  }

          configDRAMCount OBJECT-TYPE
              SYNTAX  INTEGER
              ACCESS  read-only
              STATUS  mandatory
              DESCRIPTION
                      "The Quantity of DRAM installed (number of SIMMs)."
              ::= {  configuration 5  }

          configRS232Number OBJECT-TYPE
              SYNTAX  INTEGER
              ACCESS  read-only
              STATUS  mandatory
              DESCRIPTION
                      "The Number of RS-232 ports in the RS-232 port table."
              ::= { configuration 6  }  

          configRS232PortTable OBJECT-TYPE
              SYNTAX  SEQUENCE OF ConfigRS232PortEntry
              ACCESS  not-accessible
              STATUS  mandatory
              DESCRIPTION 
                      "A list of port entries. The number of entries is 
                       given by the value of configRS232Number."
              ::= { configuration 7 }

          configRS232PortEntry OBJECT-TYPE
              SYNTAX  ConfigRS232PortEntry
              ACCESS  not-accessible
              STATUS  mandatory
              DESCRIPTION
                      "Status and parameter values for a port."
              INDEX { configRS232PortIndex }
              ::= { configRS232PortTable 1 }

          ConfigRS232PortEntry ::=
              SEQUENCE {
                  configRS232PortIndex            INTEGER,
                  configRS232PortName             DisplayString,
                  configRS232BaudRate             INTEGER,
                  configRS232ModemStatus          INTEGER,
                  configRS232ConnectionStatus     INTEGER,
                  configRS232ModemConfigString    DisplayString,
                  configRS232OutputData           OCTET STRING (SIZE (0..42)),
                  configRS232InputData            OCTET STRING (SIZE (0..100)),
                  configRS232HardwareFlowControl  INTEGER
              }

          configRS232PortIndex OBJECT-TYPE
              SYNTAX  INTEGER
              ACCESS  read-only
              STATUS  mandatory
              DESCRIPTION
                      "A unique value for each port."
              ::= { configRS232PortEntry 1 }

          configRS232PortName OBJECT-TYPE
              SYNTAX  DisplayString
              ACCESS  read-only
              STATUS  mandatory
              DESCRIPTION
                      "A text description of the port, i.e. COM1."
              ::= { configRS232PortEntry 2 }

          configRS232BaudRate OBJECT-TYPE
              SYNTAX  INTEGER {
                      b1200(1),
                      b2400(2),
                      b4800(3),
                      b9600(4),
                      b19200(5),
                      b38400(6)
              }
              ACCESS  read-write
              STATUS  mandatory
              DESCRIPTION
                      "The baudrate at which the port is operating."
              ::= { configRS232PortEntry 3 }

          configRS232ModemStatus OBJECT-TYPE
              SYNTAX  INTEGER {
                      modemDetected(1),
                      autobauding(2),
                      noModemDetected(3)
              }
              ACCESS  read-only
              STATUS  mandatory
              DESCRIPTION
                      "The current status of the modem port connection."
              ::= { configRS232PortEntry 4 }

          configRS232ConnectionStatus OBJECT-TYPE
              SYNTAX  INTEGER {
                      connected(1),
                      connectionWait(2),
                      unknown(3)
              }
              ACCESS  read-only
              STATUS  mandatory
              DESCRIPTION
                      "The current status of the modem data connection."
              ::= { configRS232PortEntry 5 }

          configRS232ModemConfigString OBJECT-TYPE
              SYNTAX  DisplayString (SIZE (0..40))
              ACCESS  read-write
              STATUS  mandatory
              DESCRIPTION
                      "A user-configurable ASCII string used to initialize
                       a modem on this port. If this string is set to Z, the 
                       Star-Tek Agent sends ATZ<CR> to the modem during 
                       configuration."
              ::= { configRS232PortEntry 6 }

          configRS232OutputData OBJECT-TYPE
              SYNTAX  OCTET STRING (SIZE (0..42))
              ACCESS  read-write
              STATUS  mandatory
              DESCRIPTION
                      "Raw data to be sent out this port. Data can only 
                       be sent if the ConnectionStatus is connectionWait."
              ::= { configRS232PortEntry 7 }

          configRS232InputData OBJECT-TYPE
              SYNTAX  OCTET STRING (SIZE (0..100))
              ACCESS  read-only
              STATUS  mandatory
              DESCRIPTION
                      "The response, if any, to the output data."
              ::= { configRS232PortEntry 8 }

          configRS232HardwareFlowControl OBJECT-TYPE
              SYNTAX  INTEGER {
                      disabled(1),
                      enabled(2)
              }
              ACCESS  read-write
              STATUS  mandatory
              DESCRIPTION
                      "Controls the use of RTS-CTS hardware flow control during
                       modem connections."
              ::= { configRS232PortEntry 9 }

          configMonitorMode OBJECT-TYPE
              SYNTAX  INTEGER {
                      monitor(1),
                      slip(2)
              }
              ACCESS  read-write
              STATUS  mandatory
              DESCRIPTION
                      "The mode of operation of the monitor port. The monitor
                       port is COM2 (if present, COM1 if not)."
              ::= { configuration 8 }

          configMonitorInput OBJECT-TYPE
              SYNTAX  INTEGER {
                      enabled(1),
                      disabled(2)
              }
              ACCESS  read-write
              STATUS  mandatory
              DESCRIPTION
                      "Controls whether the monitor function will accept
                       input."
              ::= { configuration 9 }

          configMonitorDiags OBJECT-TYPE
              SYNTAX  INTEGER {
                      enabled(1),
                      disabled(2)
              }
              ACCESS  read-write
              STATUS  mandatory
              DESCRIPTION
                      "Controls whether the monitor function will produce
                       diagnostic output."
              ::= { configuration 10 }

          configParseControl OBJECT-TYPE
              SYNTAX  INTEGER {
                      parseAll(1),
                      parseMost(2),
                      parseLess(3),
                      parseNone(4)
              }
              ACCESS  read-write
              STATUS  mandatory
              DESCRIPTION
                      "Controls the degree to which frames are copied and
                       parsed. Under high network loads this control can be 
                       used to prevent agent overload."
              ::= { configuration 11 }

          configBootSource OBJECT-TYPE
              SYNTAX  INTEGER {
                      eprom(1),
                      flash(2)
              }
              ACCESS  read-only
              STATUS  mandatory
              DESCRIPTION
                      "Describes where the agent is executing code from."
              ::= { configuration 12 }



--
-- This is the beginning of the Star-Tek enterprise specific MIB.
-- This is implemented by all Star-Tek products which support
-- management via SNMP.
-- 
--         STARTEK-MIB DEFINTIONS ::= BEGIN
--
--           IMPORTS
--             enterprises            FROM RFC1155-SMI;


           security      OBJECT IDENTIFIER ::= { maintenance 4 }



          -- Security section 

          securityControl OBJECT-TYPE
              SYNTAX  INTEGER {
                      enabled(1),
                      disabled(2)
              }
              ACCESS  read-write
              STATUS  mandatory
              DESCRIPTION
                      "This controls whether security is enabled or disabled." 
              ::= {  security 1 }

          securityMacAddressTable OBJECT-TYPE
              SYNTAX  SEQUENCE OF SecurityMacAddressTableEntry
              ACCESS  not-accessible
              STATUS  mandatory
              DESCRIPTION
                      "A table which maintains a list of MacAddresses which
                       are from the local ring, along with a control field
                       which specifies whether it is allowed or disallowed
                       access to the local ring and a counter which tracks
                       the number of times that address has been disallowed
                       access to the ring."
              ::= { security 2 }

            securityMacAddressTableEntry OBJECT-TYPE
              SYNTAX  SecurityMacAddressTableEntry
              ACCESS  not-accessible
              STATUS  mandatory
              DESCRIPTION
                      "An entry in the securityMacAddressTable."
              INDEX { INTEGER }
              ::= { securityMacAddressTable 1 }

          SecurityMacAddressTableEntry ::=
              SEQUENCE  {
                      securityMacAddress         OCTET STRING,
                      securityStatus             INTEGER,
                      securityLockoutCount       Counter
                      }

          securityMacAddress  OBJECT-TYPE
              SYNTAX  OCTET STRING (SIZE (6..6))
              ACCESS  read-write
              STATUS  mandatory
              DESCRIPTION
                      "The Token Ring Mac Address for this entry."
              ::= { securityMacAddressTableEntry 1 }

          securityStatus  OBJECT-TYPE
              SYNTAX  INTEGER {
                      allowed(1),
                      disallowed(2)
              }
              ACCESS  read-write
              STATUS  mandatory
              DESCRIPTION
                      "Specifies whether this address is allowed or disallowed
                       to be on the local ring."
              ::= { securityMacAddressTableEntry 2 }

          securityLockoutCount OBJECT-TYPE
              SYNTAX  Counter
              ACCESS  read-only
              STATUS  mandatory
              DESCRIPTION
                      "The number of times this address was disallowed on the
                       local ring."
              ::= { securityMacAddressTableEntry 3 }




--
-- This is the beginning of the Star-Tek enterprise specific MIB.
-- This is implemented by all Star-Tek products which support
-- management via SNMP.
-- 
--         STARTEK-MIB DEFINTIONS ::= BEGIN
--
--           IMPORTS
--             enterprises            FROM RFC1155-SMI;


           recovery      OBJECT IDENTIFIER ::= { maintenance 5 }

           -- Recovery Group

          recoveryControl OBJECT-TYPE
              SYNTAX  INTEGER {
                      disabled(1),
                      enabled(2)
              }
              ACCESS  read-write
              STATUS  mandatory
              DESCRIPTION
                      "This variable controls whether or not this 
                       agent will Accelerate the token-ring recovery
                       process.  Enabled by default.  "
              ::= { recovery 1 }

          recovery828Support OBJECT-TYPE
              SYNTAX  INTEGER {
                      disabled(1),
                      enabled(2)
              }
              ACCESS  read-write
              STATUS  mandatory
              DESCRIPTION
                      "This variable controls whether this agent will
                       perform Accelerated Recovery on model 828 devices.
                       Disabled by default.  "
              ::= { recovery 2 }

          recoveryRetryLimit OBJECT-TYPE
              SYNTAX  INTEGER
              ACCESS  read-write
              STATUS  mandatory
              DESCRIPTION
                      "This variable controls the maximum number of 
                       Accelerated Recovery events that will be attempted 
                       within recoveryRetryTimePeriod seconds of each other."
              ::= { recovery 3 }

          recoveryRetryTimePeriod OBJECT-TYPE
              SYNTAX  INTEGER
              ACCESS  read-write
              STATUS  mandatory
              DESCRIPTION
                      "The number of seconds which must elapse between 
                       Recovery events in order for them to be considered
                       non-related and non-limited."
              ::= { recovery 4 }



           rmonextns         OBJECT IDENTIFIER ::= { startek 4 }
           stationstatistics OBJECT IDENTIFIER ::= { rmonextns 1 }
           stationhistory    OBJECT IDENTIFIER ::= { rmonextns 2 }

          -- Private Remote Network Monitoring MIB
          -- This group currently has statistics defined only for
          -- Token Ring interfaces.  Each TrStatsEntry contains statistics
          -- for one Token Ring station.  The probe must create one
          -- trStats entry for each monitored Token Ring station
          -- on the ring.
          --
          -- These groups are used to implement history on a station
          -- by station basis. 
          --
          -- The stationstatistics group is no longer used.

          -- Token Ring History table (per station)


          trHistoryTable OBJECT-TYPE
              SYNTAX SEQUENCE OF TrHistoryEntry
              ACCESS not-accessible
              STATUS mandatory
              DESCRIPTION
                      "A list of Token Ring history entries."
              ::= { stationhistory 1 }

          trHistoryEntry OBJECT-TYPE
              SYNTAX TrHistoryEntry
              ACCESS not-accessible
              STATUS mandatory
              DESCRIPTION
                      "An historical sample of Token Ring statistics on a
                       particular Token Ring interface (on a per station basis).
                       This sample is associated with the historyControlEntry
                       which set up the parameters for a regular collection
                       of these samples."
              INDEX { trHistoryIndex , trHistorySampleIndex }
              ::= { trHistoryTable 1 }

          TrHistoryEntry ::= SEQUENCE {
              trHistoryIndex                    INTEGER (1..65535),
              trHistorySampleIndex              INTEGER,
              trHistoryIntervalStart            TimeTicks,
              trHistoryInPkts                   Counter,
              trHistoryOutPkts                  Counter,
              trHistoryInOctets                 Counter,
              trHistoryOutOctets                Counter,
              trHistoryOutBroadcastPkts         Counter,
              trHistoryOutMulticastPkts         Counter,
              trHistoryClaimTokenPkts           Counter,
              trHistoryInLineErrors             Counter,
              trHistoryOutLineErrors            Counter,
              trHistoryInternalErrors           Counter,
              trHistoryInBurstErrors            Counter,
              trHistoryOutBurstErrors           Counter,
              trHistoryACErrors                 Counter,
              trHistoryAbortErrors              Counter,
              trHistoryLostFrameErrors          Counter,
              trHistoryCongestionErrors         Counter,
              trHistoryFrameCopiedErrors        Counter,
              trHistoryFrequencyErrors          Counter,
              trHistoryTokenErrors              Counter,
              trHistoryInBeaconErrors           Counter,
              trHistoryOutBeaconErrors          Counter,
              trHistoryInsertions               Counter,
              trHistorySoftErrors               Counter
          }

          trHistoryIndex OBJECT-TYPE
              SYNTAX  INTEGER (1..65535)
              ACCESS  read-only
              STATUS  mandatory
              DESCRIPTION
                      "The history of which this entry is a part.  The
                       history identified by a particular value of this
                       index is the same history as identified by the
                       same value of historyControlIndex."
              ::= { trHistoryEntry 1 }

          trHistorySampleIndex OBJECT-TYPE
              SYNTAX  INTEGER
              ACCESS  read-only
              STATUS  mandatory
              DESCRIPTION
                      "An index that uniquely identifies the particular
                       sample this entry represents among all samples
                       associated with the same historyControlEntry.
                       This index starts at 1 and increases by one as
                       each new sample is taken."
              ::= { trHistoryEntry 2 }

          trHistoryIntervalStart OBJECT-TYPE
              SYNTAX  TimeTicks
              ACCESS  read-only
              STATUS  mandatory
              DESCRIPTION
                      "The value of sysUpTime at the start of the interval
                       over which this sample was measured.  If the probe
                       keeps track of the time of day, it should start
                       the first sample of the history at a time such that
                       when the next hour of the day begins, a sample is
                       started at that instant.  Note that following this
                       rule may require the probe to delay collecting the
                       first sample of the history, as each sample must be
                       of the same interval.  Also note that the sample which
                       is currently being collected is not accessible in this
                       table until the end of its interval."
              ::= { trHistoryEntry 3 }

          trHistoryInPkts OBJECT-TYPE
              SYNTAX  Counter
              ACCESS  read-only
              STATUS  mandatory
              DESCRIPTION
                      "The number of packets (including error packets)
                       received by this station, during this sampling interval."
              ::= { trHistoryEntry 4 }

          trHistoryOutPkts OBJECT-TYPE
              SYNTAX  Counter
              ACCESS  read-only
              STATUS  mandatory
              DESCRIPTION
                      "The number of packets (including error packets)
                       transmitted by this station, during this sampling
                       interval."
              ::= { trHistoryEntry 5 }

          trHistoryInOctets OBJECT-TYPE
              SYNTAX  Counter
              ACCESS  read-only
              STATUS  mandatory
              DESCRIPTION
                      "The total number of octets of data (including
                       those in bad packets) received on the
                       network (excluding framing bits but including
                       FCS octets) by this station, during this
                       sampling interval."
              ::= { trHistoryEntry 6 }

          trHistoryOutOctets OBJECT-TYPE
              SYNTAX  Counter
              ACCESS  read-only
              STATUS  mandatory
              DESCRIPTION
                      "The total number of octets of data (including
                       those in bad packets) transmitted on the
                       network (excluding framing bits but including
                       FCS octets) by this station, during this
                       sampling interval."
              ::= { trHistoryEntry 7 }

          trHistoryOutBroadcastPkts OBJECT-TYPE
              SYNTAX  Counter
              ACCESS  read-only
              STATUS  mandatory
              DESCRIPTION
                      "The total number of good packets transmitted
                       on the network that were directed to the
                       broadcast address by this station, during this
                       sampling interval."
              ::= { trHistoryEntry 8 }

          trHistoryOutMulticastPkts OBJECT-TYPE
              SYNTAX  Counter
              ACCESS  read-only
              STATUS  mandatory
              DESCRIPTION
                      "The total number of good packets transmitted
                       on the network that were directed to a
                       multicast address by this station, during this
                       sampling interval.  Note that this number does
                       not include packets addressed to the broadcast
                       address."
              ::= { trHistoryEntry 9 }

          trHistoryClaimTokenPkts OBJECT-TYPE
              SYNTAX  Counter
              ACCESS  read-only
              STATUS  mandatory
              DESCRIPTION
                      "The total number of Claim Token MAC packets
                       detected by this station during this sampling
                       interval."
              ::= { trHistoryEntry 10 }

          trHistoryInLineErrors OBJECT-TYPE
              SYNTAX  Counter
              ACCESS  read-only
              STATUS  mandatory
              DESCRIPTION
                      "The total number of line errors reported by this
                       station in error reporting packets detected by the
                       probe during this sampling interval."
              ::= { trHistoryEntry 11 }

          trHistoryOutLineErrors OBJECT-TYPE
              SYNTAX  Counter
              ACCESS  read-only
              STATUS  mandatory
              DESCRIPTION
                      "The total number of line errors reported in error
                       reporting packets sent by the nearest active
                       downstream neighbor of this station and detected
                       by the probe during this sampling interval."
              ::= { trHistoryEntry 12 }

          trHistoryInternalErrors OBJECT-TYPE
              SYNTAX  Counter
              ACCESS  read-only
              STATUS  mandatory
              DESCRIPTION
                      "The total number of adapter internal errors
                       reported by this station in error reporting
                       packets detected by the probe during this
                       sampling interval."
              ::= { trHistoryEntry 13 }

          trHistoryInBurstErrors OBJECT-TYPE
              SYNTAX  Counter
              ACCESS  read-only
              STATUS  mandatory
              DESCRIPTION
                      "The total number of burst errors reported by this
                       station in error reporting packets detected by the
                       probe during this sampling interval."
              ::= { trHistoryEntry 14 }

          trHistoryOutBurstErrors OBJECT-TYPE
              SYNTAX  Counter
              ACCESS  read-only
              STATUS  mandatory
              DESCRIPTION
                      "The total number of burst errors reported in
                       error reporting packets sent by the nearest active
                       downstream neighbor of this station and detected
                       by the probe, during this sampling interval."
              ::= { trHistoryEntry 15 }

          trHistoryACErrors OBJECT-TYPE
              SYNTAX  Counter
              ACCESS  read-only
              STATUS  mandatory
              DESCRIPTION
                      "The total number of AC (Address Copied) errors
                       reported in error reporting packets sent by the
                       nearest active downstream neighbor of this station
                       and detected by the probe during this sampling
                       interval."
              ::= { trHistoryEntry 16 }

          trHistoryAbortErrors OBJECT-TYPE
              SYNTAX  Counter
              ACCESS  read-only
              STATUS  mandatory
              DESCRIPTION
                      "The total number of abort delimiters reported by
                       this station in error reporting packets detected
                       by the probe during this sampling interval."
               ::= { trHistoryEntry 17 }

          trHistoryLostFrameErrors OBJECT-TYPE
              SYNTAX  Counter
              ACCESS  read-only
              STATUS  mandatory
              DESCRIPTION
                      "The total number of lost frame errors reported by
                       this station in error reporting packets detected
                       by the probe during this sampling interval."
              ::= { trHistoryEntry 18 }

          trHistoryCongestionErrors OBJECT-TYPE
              SYNTAX  Counter
              ACCESS  read-only
              STATUS  mandatory
              DESCRIPTION
                      "The total number of receive congestion errors 
                       reported by this station in error reporting
                       packets detected by the probe during this
                       sampling interval."
              ::= { trHistoryEntry 19 }

          trHistoryFrameCopiedErrors OBJECT-TYPE
              SYNTAX  Counter
              ACCESS  read-only
              STATUS  mandatory
              DESCRIPTION
                      "The total number of frame copied errors reported
                       by this station in error reporting packets
                       detected by the probe during this sampling
                       interval."
              ::= { trHistoryEntry 20 }

          trHistoryFrequencyErrors OBJECT-TYPE
              SYNTAX  Counter
              ACCESS  read-only
              STATUS  optional
              DESCRIPTION
                      "The total number of frequency errors reported by
                       this station in error reporting packets detected
                       by the probe during this sampling interval."
              ::= { trHistoryEntry 21 }

          trHistoryTokenErrors OBJECT-TYPE
              SYNTAX  Counter
              ACCESS  read-only
              STATUS  mandatory
              DESCRIPTION
                      "The total number of token errors reported by this
                       station in error reporting packets detected by the
                       probe during this sampling interval."
              ::= { trHistoryEntry 22 }

          trHistoryInBeaconErrors OBJECT-TYPE
              SYNTAX  Counter
              ACCESS  read-only
              STATUS  mandatory
              DESCRIPTION
                      "The total number of beacon frames sent by this
                       station and detected by the probe, during this
                       sampling interval."
              ::= { trHistoryEntry 23 }

          trHistoryOutBeaconErrors OBJECT-TYPE
              SYNTAX  Counter
              ACCESS  read-only
              STATUS  mandatory
              DESCRIPTION
                      "The total number of beacon frames detected by the
                       probe, that name this station as the NAUN, during
                       this sampling interval."
              ::= { trHistoryEntry 24 }

          trHistoryInsertions OBJECT-TYPE
              SYNTAX  Counter
              ACCESS  read-only
              STATUS  mandatory
              DESCRIPTION
                      "The number of times the probe detected this
                       station inserting onto the ring during this
                       sampling interval."
              ::= { trHistoryEntry 25 }

          trHistorySoftErrors OBJECT-TYPE
              SYNTAX  Counter
              ACCESS  read-only
              STATUS  mandatory
              DESCRIPTION
                      "The number of soft errors reported by this
                       station in error reporting packets detected by the
                       probe during this sampling interval."
              ::= { trHistoryEntry 26 }



          -- Token Ring History Opaque table (per station)

          trHistoryOpaqueTable OBJECT-TYPE
              SYNTAX  SEQUENCE OF TrHistoryOpaqueEntry
              ACCESS  not-accessible
              STATUS  mandatory
              DESCRIPTION
                      "A list of Token Ring history entries."
             ::= { stationhistory 2 }

          trHistoryOpaqueEntry OBJECT-TYPE
              SYNTAX  TrHistoryOpaqueEntry
              ACCESS  not-accessible
              STATUS  mandatory
              DESCRIPTION
                      "An historical sample of Token Ring statistics on a
                       particular Token Ring interface.  This sample is
                       associated with the historyControlEntry which set
                       up the parameters for a regular collection of these
                       samples."
              INDEX { INTEGER,  -- History Control Index
                      INTEGER } -- Station Index
              ::= { trHistoryOpaqueTable 1 }

          TrHistoryOpaqueEntry ::= SEQUENCE {
                trHistoryTableData  Opaque
             }

          trHistoryTableData OBJECT-TYPE
              SYNTAX  Opaque
              ACCESS  read-only
              STATUS  mandatory
              DESCRIPTION
                      "An opaque data structure used for management."
              ::=  { trHistoryOpaqueEntry 1 }


           protocolstatistics OBJECT IDENTIFIER ::= { rmonextns 3 }

           protocolData OBJECT-TYPE
                SYNTAX  Opaque
                ACCESS  read-only
                STATUS  mandatory
                DESCRIPTION
                        "An opaque data structure used for data retrival."
                ::= { protocolstatistics 1 }

           protocolStatsTable OBJECT-TYPE
                SYNTAX  SEQUENCE OF ProtocolStatsEntry
                ACCESS  not-accessible
                STATUS  mandatory
                DESCRIPTION
                        "A list of protocol statistics entries."
                ::= { protocolstatistics 2 }

           protocolStatsEntry OBJECT-TYPE
                SYNTAX  ProtocolStatsEntry
                ACCESS  not-accessible
                STATUS  mandatory
                DESCRIPTION
                        "An entry in the protocolStatsTable."
                INDEX { protocolIfIndex , protocolID }
                ::= { protocolStatsTable 1 }

           ProtocolStatsEntry ::= SEQUENCE {
                protocolIfIndex       INTEGER (1..65535),
                protocolID            INTEGER (1..65535),
                protocolPkts          Counter,
                protocolOctets        Counter
           }

           protocolIfIndex OBJECT-TYPE
                SYNTAX  INTEGER (1..65535)
                ACCESS  read-only
                STATUS  mandatory
                DESCRIPTION
                        "The value of this object uniquely identifies the
                         interface on this remote network monitoring device
                         on which this station was detected.  The interface
                         identified by a particular value of this object is
                         the same interface as identified by the same value
                         of the ifindex object, defined in [4,6]."
                ::= { protocolStatsEntry 1 }

           protocolID OBJECT-TYPE
                SYNTAX  INTEGER {
                        all-packets(1),
                        unknown-protocols(2),
                        ieee8025-mac-protocol(3),
                        ieee8025-source-routed-packets(4),
                        ieee8025-nonsource-routed-packets(5),
                        dix-ethernet-packets(6),
                        ieee8022-llc-protocol(7),
                        ieee8022-llc-snap(8),
                        ip(9),
                        ip-icmp(10),
                        ip-gcp(11),
                        ip-tcp(12),
                        ip-egp(13),
                        ip-igp(14),
                        ip-chaos(15),
                        ip-udp(16),
                        ip-tp4(17),
                        ip-other(18),
                        arp(19),
                        netware-ipx(20),
                        llc-null-sap(21),
                        llc-individual-mgmt-sap(22),
                        llc-group-mgmt-sap(23),
                        llc-individual-sna-path-ctrl-sap(24),
                        llc-group-sna-path-ctrl-sap(25),
                        llc-arpanet-ip-sap(26),
                        llc-3com-xns-sap(27),
                        llc-netbios-sap(28),
                        llc-individual-lan-mgmt-sap(29),
                        llc-group-lan-mgmt-sap(30),
                        llc-remote-program-load-sap(31),
                        llc-iso-network-layer-sap(32),
                        llc-global-sap(33),
                        other-llc-sap(34),
                        chaosnet(35),
                        banyan-vines(36),
                        decnet(37),
                        dec-lat(38),
                        dec-lanbridge(39),
                        appletalk(40),
                        xerox-3com(41),
                        ipx-uknown(42),
                        ipx-routinginformationpacket(43),
                        ipx-echopacket(44),
                        ipx-errorpacket(45),
                        ipx-packetexchangeprotocol(46),
                        ipx-sequencedpacketprotocol(47),
                        ipx-netwarecoreprotocol(48),
                        ipx-other(49),
                        ncp(50),
                        ncp-create(51),
                        ncp-request(52),
                        ncp-reply(53),
                        ncp-destroyserviceconnection(54),
                        ncp-requestinprogressresponse(55),
                        ncp-other(56),
                        sap-generalservicequery(57),
                        sap-generalserviceresponse(58),
                        sap-nearestserverquery(59),
                        sap-nearestserverresponse(60),
                        llc-startekdiscovery(61),
                        reserved62(62),
                        reserved63(63),
                        reserved64(64),
                        reserved65(65),
                        reserved66(66),
                        reserved67(67),
                        reserved68(68),
                        reserved69(69),
                        reserved70(70),
                        reserved71(71),
                        reserved72(72),
                        reserved73(73),
                        reserved74(74),
                        reserved75(75),
                        reserved76(76),
                        reserved77(77),
                        reserved78(78),
                        reserved79(79),
                        reserved80(80),
                        reserved81(81),
                        reserved82(82)
                }
                ACCESS  read-only
                STATUS  mandatory
                DESCRIPTION
                        "The value of this object uniquely identifies the
                         protocol whose counters are tracked by this table
                         entry."
                ::= { protocolStatsEntry 2 }

           protocolPkts OBJECT-TYPE
                SYNTAX  Counter
                ACCESS  read-only
                STATUS  mandatory
                DESCRIPTION
                        "The number of packets received for this protocol."
                ::= { protocolStatsEntry 3 }

           protocolOctets OBJECT-TYPE
                SYNTAX  Counter
                ACCESS  read-only
                STATUS  mandatory
                DESCRIPTION
                        "The number of octets received for this protocol."
                ::= { protocolStatsEntry 4 }


	END
