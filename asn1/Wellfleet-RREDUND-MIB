Wellfleet-RREDUND-MIB DEFINITIONS ::= BEGIN

-- Created by mdl2asn version 3.1
-- Creation date: Wed Aug 30 16:47:08 EDT 1995


    IMPORTS

      IpAddress, Counter, Gauge
        FROM RFC1155-SMI
      OBJECT-TYPE
        FROM RFC-1212
      DisplayString
        FROM RFC1213-MIB
      wfRRedGroup
        FROM Wellfleet-COMMON-MIB;


    wfRRedundGroup	OBJECT IDENTIFIER ::= { wfRRedGroup 1 }

    wfRRedundDelete OBJECT-TYPE
        SYNTAX	INTEGER {
    		    created(1),
    		    deleted(2)
    		}
        ACCESS	read-write
        STATUS	mandatory
        DESCRIPTION
                "Create/Delete parameter"
        DEFVAL	{ created }
        ::= { wfRRedundGroup 1 }

    wfRRedundDisable OBJECT-TYPE
        SYNTAX	INTEGER {
    		    enabled(1),
    		    disabled(2)
    		}
        ACCESS	read-write
        STATUS	mandatory
        DESCRIPTION
                "Enable/Disable parameter"
        DEFVAL	{ enabled }
        ::= { wfRRedundGroup 2 }

    wfRRedundState OBJECT-TYPE
        SYNTAX	INTEGER {
                    up(1),
                    waitnewpri(2),
                    rcvdprigdby(3),
                    waitprigdby(4),
                    waitsosrply(5),
                    bidding(6),
                    init(7),
                    down(8),
                    notpresent(9)
    		}
        ACCESS	read-only
        STATUS	mandatory
        DESCRIPTION
                "State parameter"
        DEFVAL	{ init }
        ::= { wfRRedundGroup 3 }

    wfRRedundGroupId OBJECT-TYPE
        SYNTAX	INTEGER(1..128)
        ACCESS	read-write
        STATUS	mandatory
        DESCRIPTION
                "Group ID parameter"
        DEFVAL	{ 1 }
        ::= { wfRRedundGroup 4 }

    wfRRedundMemberId OBJECT-TYPE
        SYNTAX	INTEGER(1..128)
        ACCESS	read-write
        STATUS	mandatory
        DESCRIPTION
                "Member ID parameter"
        DEFVAL	{ 1 }
        ::= { wfRRedundGroup 5 }

    wfRRedundRole OBJECT-TYPE
        SYNTAX	INTEGER {
    		    primary(1),
    		    secondary(2)
    		}
        ACCESS	read-write
        STATUS	mandatory
        DESCRIPTION
                "Role parameter"
        DEFVAL	{ secondary }
        ::= { wfRRedundGroup 6 }

    wfRRedundRefNum OBJECT-TYPE
        SYNTAX	INTEGER
        ACCESS	read-only
        STATUS	mandatory
        DESCRIPTION
                "Reference Number parameter, a 32 bit unsigned number."
        ::= { wfRRedundGroup 7 }

    wfRRedundGoodIFCount OBJECT-TYPE
        SYNTAX	INTEGER
        ACCESS	read-only
        STATUS	mandatory
        DESCRIPTION
                "Good Interface Count parameter, a 32 bit unsigned number."
        ::= { wfRRedundGroup 8 }

    wfRRedundGoodRESCount OBJECT-TYPE
        SYNTAX	INTEGER
        ACCESS	read-only
        STATUS	mandatory
        DESCRIPTION
                "Good Resource Count parameter, a 32 bit unsigned number."
        ::= { wfRRedundGroup 9 }

    wfRRedundSwitch OBJECT-TYPE
        SYNTAX	INTEGER {
    		    dontswitch(1),
    		    switch(2)
    		}
        ACCESS	read-write
        STATUS	mandatory
        DESCRIPTION
                "Router software clears to indicate receive of role switch command"
        DEFVAL	{ dontswitch }
        ::= { wfRRedundGroup 10 }

    wfRRedundAuto OBJECT-TYPE
        SYNTAX	INTEGER {
    		    manual(1),
    		    auto(2),
                    oneshotauto(3),
                    failureonlyauto(4)
    		}
        ACCESS	read-write
        STATUS	mandatory
        DESCRIPTION
                "Auto Role Switching parameter - Options for Auto Role Switching."
        DEFVAL	{ auto }
        ::= { wfRRedundGroup 11 }

    wfRRedundGoodBidCount OBJECT-TYPE
        SYNTAX	INTEGER(1..10)
        ACCESS	read-write
        STATUS	mandatory
        DESCRIPTION
                "same router prior to kicking in Auto Role Switching."
        DEFVAL	{ 3 }
        ::= { wfRRedundGroup 12 }

    wfRRedundVersion OBJECT-TYPE
        SYNTAX	INTEGER
        ACCESS	read-only
        STATUS	mandatory
        DESCRIPTION
                "Version parameter - Redundancy Protocol Version Number"
        DEFVAL	{ 1 }
        ::= { wfRRedundGroup 13 }

    wfRRedundPriority OBJECT-TYPE
        SYNTAX	INTEGER(1..128)
        ACCESS	read-write
        STATUS	mandatory
        DESCRIPTION
                "Priority parameter - Priority level to be the Primary router"
        DEFVAL	{ 1 }
        ::= { wfRRedundGroup 14 }

    wfRRedundHelloTimer OBJECT-TYPE
        SYNTAX	INTEGER(1..86400)
        ACCESS	read-write
        STATUS	mandatory
        DESCRIPTION
                "Secondary Keep Alives"
        DEFVAL	{ 2 }
        ::= { wfRRedundGroup 15 }

    wfRRedundBidDuration OBJECT-TYPE
        SYNTAX	INTEGER(1..65535)
        ACCESS	read-write
        STATUS	mandatory
        DESCRIPTION
                "the Bidding Period"
        DEFVAL	{ 45 }
        ::= { wfRRedundGroup 16 }

    wfRRedundTimeoutCounters OBJECT-TYPE
        SYNTAX	INTEGER(1..100)
        ACCESS	read-write
        STATUS	mandatory
        DESCRIPTION
                "receiving Primary Hellos before Secondaries enter the bidding process."
        DEFVAL	{ 5 }
        ::= { wfRRedundGroup 17 }

    wfRRedundNPrimaryCounters OBJECT-TYPE
        SYNTAX	Counter
        ACCESS	read-only
        STATUS	mandatory
        DESCRIPTION
                "any design flaws."
        ::= { wfRRedundGroup 18 }

    wfRRedundRoleSwitchDelayTimer OBJECT-TYPE
        SYNTAX	INTEGER(1..86400)
        ACCESS	read-write
        STATUS	mandatory
        DESCRIPTION
                "message to adjacent routers on the non-backed-up interfaces."
        DEFVAL	{ 5 }
        ::= { wfRRedundGroup 19 }

    wfRRedundPriConfigFilePath OBJECT-TYPE
        SYNTAX	DisplayString
        ACCESS	read-write
        STATUS	mandatory
        DESCRIPTION
                "Pathname of Primary's configuration file."
        ::= { wfRRedundGroup 20 }

    wfRRedundPriMemberID OBJECT-TYPE
        SYNTAX	INTEGER(1..128)
        ACCESS	read-only
        STATUS	mandatory
        DESCRIPTION
                "Primary Member's Member ID"
        DEFVAL	{ 1 }
        ::= { wfRRedundGroup 21 }

    wfRRedundPriState OBJECT-TYPE
        SYNTAX	INTEGER {
                    up(1),
                    waitnewpri(2),
                    rcvdprigdby(3),
                    waitprigdby(4),
                    waitsosrply(5),
                    bidding(6),
                    init(7),
                    down(8),
                    notpresent(9)
    		}
        ACCESS	read-only
        STATUS	mandatory
        DESCRIPTION
                "Primary Member's State"
        DEFVAL	{ init }
        ::= { wfRRedundGroup 22 }

    wfRRedundPriRefNum OBJECT-TYPE
        SYNTAX	INTEGER
        ACCESS	read-only
        STATUS	mandatory
        DESCRIPTION
                "Primary Member's Reference Number, a 32 bit unsigned value."
        ::= { wfRRedundGroup 23 }

    wfRRedundPriGoodIFCount OBJECT-TYPE
        SYNTAX	INTEGER
        ACCESS	read-only
        STATUS	mandatory
        DESCRIPTION
                "Primary Member's Good Interface Count, a 32 bit unsigned value."
        ::= { wfRRedundGroup 24 }

    wfRRedundPriGoodRESCount OBJECT-TYPE
        SYNTAX	INTEGER
        ACCESS	read-only
        STATUS	mandatory
        DESCRIPTION
                "Primary Member's Good Resource Count, a 32 bit unsigned value."
        ::= { wfRRedundGroup 25 }

    wfRRedundBSecMemberID OBJECT-TYPE
        SYNTAX	INTEGER(1..128)
        ACCESS	read-only
        STATUS	mandatory
        DESCRIPTION
                "Best Secondary Member's Member ID"
        DEFVAL	{ 1 }
        ::= { wfRRedundGroup 26 }

    wfRRedundBSecState OBJECT-TYPE
        SYNTAX	INTEGER {
                    up(1),
                    waitnewpri(2),
                    rcvdprigdby(3),
                    waitprigdby(4),
                    waitsosrply(5),
                    bidding(6),
                    init(7),
                    down(8),
                    notpresent(9)
    		}
        ACCESS	read-only
        STATUS	mandatory
        DESCRIPTION
                "Best Secondary Member's State"
        DEFVAL	{ init }
        ::= { wfRRedundGroup 27 }

    wfRRedundBSecRefNum OBJECT-TYPE
        SYNTAX	INTEGER
        ACCESS	read-only
        STATUS	mandatory
        DESCRIPTION
                "Best Secondary Member's Reference Number, a 32 bit unsigned value."
        ::= { wfRRedundGroup 28 }

    wfRRedundBSecGoodIFCount OBJECT-TYPE
        SYNTAX	INTEGER
        ACCESS	read-only
        STATUS	mandatory
        DESCRIPTION
                "Best Secondary Member's Good Interface Count, a 32 bit unsigned value."
        ::= { wfRRedundGroup 29 }

    wfRRedundBSecGoodRESCount OBJECT-TYPE
        SYNTAX	INTEGER
        ACCESS	read-only
        STATUS	mandatory
        DESCRIPTION
                "Best Secondary Member's Good Resource Count, a 32 bit unsigned value."
        ::= { wfRRedundGroup 30 }

    wfRRedundWarmBoot OBJECT-TYPE
        SYNTAX  INTEGER {
                    enabled(1),
                    disabled(2)
    		}
        ACCESS  read-write
        STATUS  mandatory
        DESCRIPTION
                "Flag to indiacte mode of role switch.  enabled is Warm-reboot 
                 vs. disabled is hot-non-reboot"
        DEFVAL	{ disabled }
        ::= { wfRRedundGroup 31 }

    wfRRedundSlot OBJECT-TYPE
        SYNTAX  INTEGER(1..14)
        ACCESS  read-only
        STATUS  mandatory
        DESCRIPTION
                "The rredund gate's local Slot ID"
        ::= { wfRRedundGroup 32 }

    wfRRedundSlotMask OBJECT-TYPE
        SYNTAX  Gauge
        ACCESS  read-write
        STATUS  mandatory
        DESCRIPTION
                "Slot mask for which slots RREDUND is eligible
                to run on.  The MSBit represents slot 1, the
                next most significant bit represents slot 2,
                and so on...  Slots can be 1-14.
                Default is all slots on a BCN."
        DEFVAL  { 4294705152 }
        ::= { wfRRedundGroup 33 }

    wfRRedundAtmDeathTimer OBJECT-TYPE
        SYNTAX  INTEGER(1..65535)
        ACCESS  read-write
        STATUS  mandatory
        DESCRIPTION
                "Time (in milliseconds) we want to wait for the ATM driver
                 gate to come back up, before we role-switch."
        DEFVAL  { 3000 }
        ::= { wfRRedundGroup 34 }

    wfRRedundCctTable OBJECT-TYPE
        SYNTAX	SEQUENCE OF WfRRedundCctEntry
        ACCESS	not-accessible
        STATUS	mandatory
        DESCRIPTION
                "This tabulates the circuit specific Router Redundancy parameters."
        ::= { wfRRedGroup 2 }

    wfRRedundCctEntry OBJECT-TYPE
        SYNTAX	WfRRedundCctEntry
        ACCESS	not-accessible
        STATUS	mandatory
        DESCRIPTION
                "Entry summary."
        INDEX	{ wfRRedundCctCct }
        ::= { wfRRedundCctTable 1 }

    WfRRedundCctEntry ::= SEQUENCE {
    	    wfRRedundCctDelete
    		INTEGER,
    	    wfRRedundCctDisable
    		INTEGER,
    	    wfRRedundCctCct
    		INTEGER,
    	    wfRRedundCctPrimaryMACAddr
    		OCTET STRING,
            wfRRedundCctMonitor
                INTEGER,
            wfRRedundCctRSwitchOnFailure
                INTEGER,
    	    wfRRedundCctSendPduDisable
    		INTEGER,
            wfRRedundCctStatus
                INTEGER,
    	    wfRRedundCctSONMPXmtCount
    		INTEGER,
    	    wfRRedundCctSONMPRcvCount
    		INTEGER,
    	    wfRRedundCctSONMPRcvErrorCount
    		INTEGER
        }

    wfRRedundCctDelete OBJECT-TYPE
        SYNTAX	INTEGER {
    		    created(1),
    		    deleted(2)
    		}
        ACCESS	read-write
        STATUS	mandatory
        DESCRIPTION
                "Create/Delete parameter"
        DEFVAL	{ created }
        ::= { wfRRedundCctEntry 1 }

    wfRRedundCctDisable OBJECT-TYPE
        SYNTAX	INTEGER {
    		    enabled(1),
    		    disabled(2)
    		}
        ACCESS	read-write
        STATUS	mandatory
        DESCRIPTION
                "Enable/Disable parameter"
        DEFVAL	{ enabled }
        ::= { wfRRedundCctEntry 2 }

    wfRRedundCctCct OBJECT-TYPE
        SYNTAX	INTEGER
        ACCESS	read-only
        STATUS	mandatory
        DESCRIPTION
                "Circuit Number, used as Instance ID."
        ::= { wfRRedundCctEntry 3 }

    wfRRedundCctPrimaryMACAddr OBJECT-TYPE
        SYNTAX	OCTET STRING
        ACCESS	read-write
        STATUS	mandatory
        DESCRIPTION
                "This attribute is used for Site Manager Router Redundancy Configuration."
        ::= { wfRRedundCctEntry 4 }

     wfRRedundCctMonitor OBJECT-TYPE
         SYNTAX  INTEGER {
                     circuit(1),
                     link(2)
                 }
         ACCESS  read-write
         STATUS  mandatory
         DESCRIPTION
              "To indicate what element of the interface is being monitored for role switching, the circuit or the link."
         DEFVAL  { circuit }
         ::= { wfRRedundCctEntry 5 }

    wfRRedundCctRSwitchOnFailure OBJECT-TYPE
        SYNTAX  INTEGER {
                    enabled(1),
                    disabled(2)
                }
        ACCESS  read-write
        STATUS  mandatory
        DESCRIPTION
                "For select triggering of role switching when interface fails ona per CCT basis."
        DEFVAL  { enabled }
        ::= { wfRRedundCctEntry 6 }

    wfRRedundCctSendPduDisable OBJECT-TYPE
        SYNTAX	INTEGER {
    		    enabled(1),
    		    disabled(2)
    		}
        ACCESS	read-write
        STATUS	mandatory
        DESCRIPTION
                "For enabling/disabling sending of Router Redundancy PDU per CCT basis."
        DEFVAL	{ enabled }
        ::= { wfRRedundCctEntry 7 }

    wfRRedundCctStatus OBJECT-TYPE
        SYNTAX  INTEGER {
                    up(1),
                    down(2)
                }
        ACCESS  read-only
        STATUS  mandatory
        DESCRIPTION
                "Status of the interface from Router Redundancy prospective."
        DEFVAL  { down }
        ::= { wfRRedundCctEntry 8 }

    wfRRedundCctSONMPXmtCount OBJECT-TYPE
        SYNTAX	INTEGER
        ACCESS	read-only
        STATUS	mandatory
        DESCRIPTION
                "Used for counting SONMP PDU transmitted on this circuit."
        ::= { wfRRedundCctEntry 9 }

    wfRRedundCctSONMPRcvCount OBJECT-TYPE
        SYNTAX	INTEGER
        ACCESS	read-only
        STATUS	mandatory
        DESCRIPTION
                "Used for counting good SONMP PDU received on this circuit."
        ::= { wfRRedundCctEntry 10 }

    wfRRedundCctSONMPRcvErrorCount OBJECT-TYPE
        SYNTAX	INTEGER
        ACCESS	read-only
        STATUS	mandatory
        DESCRIPTION
                "Used for counting bad SONMP PDU received on this circuit."
        ::= { wfRRedundCctEntry 11 }

    wfRRedundResourceTable OBJECT-TYPE
        SYNTAX	SEQUENCE OF WfRRedundResourceEntry
        ACCESS	not-accessible
        STATUS	mandatory
        DESCRIPTION
                "for Router Redundancy."
        ::= { wfRRedGroup 3 }

    wfRRedundResourceEntry OBJECT-TYPE
        SYNTAX	WfRRedundResourceEntry
        ACCESS	not-accessible
        STATUS	mandatory
        DESCRIPTION
                "Entry summary."
        INDEX	{ wfRRedundResourceCircuitNumber,
    		  wfRRedundResourceNetAddr }
        ::= { wfRRedundResourceTable 1 }

    WfRRedundResourceEntry ::= SEQUENCE {
    	    wfRRedundResourceDelete
    		INTEGER,
    	    wfRRedundResourceDisable
    		INTEGER,
    	    wfRRedundResourceCircuitNumber
    		INTEGER,
    	    wfRRedundResourceNetAddr
    		IpAddress,
    	    wfRRedundResourceStatus
    		INTEGER,
    	    wfRRedundResourceStatusUpdateDisable
    		INTEGER,
    	    wfRRedundResourcePingIntervalTimer
    		INTEGER,
    	    wfRRedundResourcePingRetryCount
    		INTEGER,
    	    wfRRedundResourcePingTimeOut
    		INTEGER
        }

    wfRRedundResourceDelete OBJECT-TYPE
        SYNTAX	INTEGER {
    		    created(1),
    		    deleted(2)
    		}
        ACCESS	read-write
        STATUS	mandatory
        DESCRIPTION
                "Create/Delete parameter"
        DEFVAL	{ created }
        ::= { wfRRedundResourceEntry 1 }

    wfRRedundResourceDisable OBJECT-TYPE
        SYNTAX	INTEGER {
    		    enabled(1),
    		    disabled(2)
    		}
        ACCESS	read-write
        STATUS	mandatory
        DESCRIPTION
                "Enable/Disable parameter"
        DEFVAL	{ enabled }
        ::= { wfRRedundResourceEntry 2 }

    wfRRedundResourceCircuitNumber OBJECT-TYPE
        SYNTAX	INTEGER
        ACCESS	read-only
        STATUS	mandatory
        DESCRIPTION
                "Circuit owner of this interface."
        ::= { wfRRedundResourceEntry 3 }

    wfRRedundResourceNetAddr OBJECT-TYPE
        SYNTAX	IpAddress
        ACCESS	read-only
        STATUS	mandatory
        DESCRIPTION
                "Resource's Network Address, i.e. IP Address."
        ::= { wfRRedundResourceEntry 4 }

    wfRRedundResourceStatus OBJECT-TYPE
        SYNTAX	INTEGER {
    		    reachable(1),
    		    unreachable(2),
    		    unknown(3)
    		}
        ACCESS	read-only
        STATUS	mandatory
        DESCRIPTION
                "Resource Status."
        DEFVAL	{ unknown }
        ::= { wfRRedundResourceEntry 5 }

    wfRRedundResourceStatusUpdateDisable OBJECT-TYPE
        SYNTAX	INTEGER {
    		    enabled(1),
    		    disabled(2)
    		}
        ACCESS	read-write
        STATUS	mandatory
        DESCRIPTION
                "Resource Status Update Enable."
        DEFVAL	{ enabled }
        ::= { wfRRedundResourceEntry 6 }

    wfRRedundResourcePingIntervalTimer OBJECT-TYPE
        SYNTAX	INTEGER(1..86399)
        ACCESS	read-write
        STATUS	mandatory
        DESCRIPTION
                "Frequency timer for Pings in sec"
        DEFVAL	{ 600 }
        ::= { wfRRedundResourceEntry 7 }

    wfRRedundResourcePingRetryCount OBJECT-TYPE
        SYNTAX	INTEGER(1..9)
        ACCESS	read-write
        STATUS	mandatory
        DESCRIPTION
                "Number of missed Pings before Resouce is unreachable"
        DEFVAL	{ 3 }
        ::= { wfRRedundResourceEntry 8 }

    wfRRedundResourcePingTimeOut OBJECT-TYPE
        SYNTAX	INTEGER(1..10)
        ACCESS	read-write
        STATUS	mandatory
        DESCRIPTION
                "Ping TimeOut in sec (wait this long before increment retry)"
        DEFVAL	{ 5 }
        ::= { wfRRedundResourceEntry 9 }

    wfRRedundRemoteMemberTable OBJECT-TYPE
        SYNTAX	SEQUENCE OF WfRRedundRemoteMemberEntry
        ACCESS	not-accessible
        STATUS	mandatory
        DESCRIPTION
                "This tabulates the remote members for Router Redundancy."
        ::= { wfRRedGroup 4 }

    wfRRedundRemoteMemberEntry OBJECT-TYPE
        SYNTAX	WfRRedundRemoteMemberEntry
        ACCESS	not-accessible
        STATUS	mandatory
        DESCRIPTION
                "Entry summary."
        INDEX	{ wfRRedundRemoteMemberGroupId,
    		  wfRRedundRemoteMemberId }
        ::= { wfRRedundRemoteMemberTable 1 }

    WfRRedundRemoteMemberEntry ::= SEQUENCE {
    	    wfRRedundRemoteMemberDelete
    		INTEGER,
    	    wfRRedundRemoteMemberGroupId
    		INTEGER,
    	    wfRRedundRemoteMemberId
    		INTEGER,
    	    wfRRedundRemoteMemberNetAddr
    		IpAddress,
    	    wfRRedundRemoteMemberRole
    		INTEGER,
    	    wfRRedundRemoteMemberState
    		INTEGER,
    	    wfRRedundRemoteMemberRefNum
    		INTEGER,
    	    wfRRedundRemoteMemberPriority
    		INTEGER,
    	    wfRRedundRemoteMemberGoodIfCnt
    		INTEGER,
    	    wfRRedundRemoteMemberGoodResCnt
    		INTEGER,
    	    wfRRedundRemoteMemberIfCnt
    		INTEGER,
    	    wfRRedundRemoteMemberLocalIfReachCnt
    		INTEGER
        }

    wfRRedundRemoteMemberDelete OBJECT-TYPE
        SYNTAX	INTEGER {
    		    created(1),
    		    deleted(2)
    		}
        ACCESS	read-write
        STATUS	mandatory
        DESCRIPTION
                "Create/Delete parameter"
        DEFVAL	{ created }
        ::= { wfRRedundRemoteMemberEntry 1 }

    wfRRedundRemoteMemberGroupId OBJECT-TYPE
        SYNTAX	INTEGER
        ACCESS	read-only
        STATUS	mandatory
        DESCRIPTION
                "Group Member ID parameter"
        ::= { wfRRedundRemoteMemberEntry 2 }

    wfRRedundRemoteMemberId OBJECT-TYPE
        SYNTAX	INTEGER
        ACCESS	read-only
        STATUS	mandatory
        DESCRIPTION
                "Member ID parameter"
        ::= { wfRRedundRemoteMemberEntry 3 }

    wfRRedundRemoteMemberNetAddr OBJECT-TYPE
        SYNTAX	IpAddress
        ACCESS	read-only
        STATUS	mandatory
        DESCRIPTION
                "Member Net Address"
        ::= { wfRRedundRemoteMemberEntry 4 }

    wfRRedundRemoteMemberRole OBJECT-TYPE
        SYNTAX	INTEGER {
    		    primary(1),
    		    secondary(2)
    		}
        ACCESS	read-only
        STATUS	mandatory
        DESCRIPTION
                "Role parameter"
        DEFVAL	{ secondary }
        ::= { wfRRedundRemoteMemberEntry 5 }

    wfRRedundRemoteMemberState OBJECT-TYPE
        SYNTAX	INTEGER {
                    up(1),
                    waitnewpri(2),
                    rcvdprigdby(3),
                    waitprigdby(4),
                    waitsosrply(5),
                    bidding(6),
                    init(7),
                    down(8),
                    notpresent(9)
    		}
        ACCESS	read-only
        STATUS	mandatory
        DESCRIPTION
                "State parameter"
        DEFVAL	{ init }
        ::= { wfRRedundRemoteMemberEntry 6 }

    wfRRedundRemoteMemberRefNum OBJECT-TYPE
        SYNTAX	INTEGER
        ACCESS	read-only
        STATUS	mandatory
        DESCRIPTION
                "Reference Number parameter, a 32 bit unsigned value."
        ::= { wfRRedundRemoteMemberEntry 7 }

    wfRRedundRemoteMemberPriority OBJECT-TYPE
        SYNTAX	INTEGER(1..128)
        ACCESS	read-only
        STATUS	mandatory
        DESCRIPTION
                "Priority parameter - Priority level to be the Primary router"
        DEFVAL	{ 1 }
        ::= { wfRRedundRemoteMemberEntry 8 }

    wfRRedundRemoteMemberGoodIfCnt OBJECT-TYPE
        SYNTAX	INTEGER
        ACCESS	read-only
        STATUS	mandatory
        DESCRIPTION
                "Good interfaces count, a 32 bit unsigned value."
        ::= { wfRRedundRemoteMemberEntry 9 }

    wfRRedundRemoteMemberGoodResCnt OBJECT-TYPE
        SYNTAX	INTEGER
        ACCESS	read-only
        STATUS	mandatory
        DESCRIPTION
                "Good resources count, a 32 bit unsigned value."
        ::= { wfRRedundRemoteMemberEntry 10 }

    wfRRedundRemoteMemberIfCnt OBJECT-TYPE
        SYNTAX	INTEGER
        ACCESS	read-only
        STATUS	mandatory
        DESCRIPTION
                "Interface count"
        ::= { wfRRedundRemoteMemberEntry 11 }

    wfRRedundRemoteMemberLocalIfReachCnt OBJECT-TYPE
        SYNTAX	INTEGER
        ACCESS	read-only
        STATUS	mandatory
        DESCRIPTION
                "Local Interface reachable count"
        ::= { wfRRedundRemoteMemberEntry 12 }

    END  -- Wellfleet-RREDUND-MIB
