VERILINK-ENTERPRISE-NCMISDN-MIB


--              FORCE-INCLUDE <stdio.h>
--              FORCE-INCLUDE <prepc.h>
--              FORCE-INCLUDE <snmp/asn1.h>
--              FORCE-INCLUDE <snmp/mib.h>
--              FORCE-INCLUDE <snmp/snmp.h>
--              FORCE-INCLUDE <snmp/snmpstat.h>
--              FORCE-INCLUDE <snmp/buildpkt.h>
--              FORCE-INCLUDE "vl.h"
--              FORCE-INCLUDE "vkmib.h"
--              FORCE-INCLUDE "vktrap.h"
--              FORCE-INCLUDE "mib2.h"
--

	-- Created:  Stanley Lui in June, 1996.
	-- set up MIB-wide defaults
	-- all functions can use %n for object name and
	-- %t for object type, %p for parent name,
	-- %d for name of default-bearing node and %% for %

	  DEFINITIONS ::= BEGIN

     IMPORTS
	     DisplayString
		     FROM RFC1213-MIB
	     OBJECT-TYPE
		     FROM RFC-1212
	     ncm-isdn
		     FROM 
             VERILINK-ENTERPRISE-NCMALARM-MIB;

	     
 
     --  This MIB module uses the extended OBJECT-TYPE macro as
     --  defined in RFC 1212.
     --  This MIB module uses the TRAP-TYPE macro as
     --  defined in RFC 1215.
     --  enterprises{iso(1).org(3).dod(6).intrnet(1).pvt(4).entrprs(1).
     --                                                    vlnk(321).as2000(1).x }

     --  Please update verilink.mib whenever a new entry is added
     --  or deleted

     


     --  PRI Port Configuration Table


        ncmPRIPortConfigTable OBJECT-TYPE
        SYNTAX  SEQUENCE OF NcmPRIPortConfigEntry
        ACCESS  not-accessible
        STATUS  mandatory
	DESCRIPTION
        "The PRI Port Configuration table  ."

        --DEFAULT test-function    isdn-test
        --DEFAULT next-function    isdn-next


         ::= { ncm-isdn 8000 }


        ncmPRIPortConfigEntry OBJECT-TYPE
        SYNTAX  NcmPRIPortConfigEntry
        ACCESS  not-accessible
        STATUS  mandatory
        DESCRIPTION
        "An entry in the PRI Port Configuration table  ."
         INDEX   { ncmPRIPortNIDIndex, ncmPRIPortLineIndex }
         ::= { ncmPRIPortConfigTable 1 }


         NcmPRIPortConfigEntry ::=
         SEQUENCE {
	
	   ncmPRIPortNIDIndex
		 INTEGER,
           ncmPRIPortLineIndex
                 INTEGER,
           ncmPRIPortInService 
                 INTEGER,
           ncmPRIPortNFASMode 
                 INTEGER,
           ncmPRIPortDChanMode				
                 INTEGER,
           ncmPRIPortDChanBits				
                 INTEGER,
	   ncmPRIPortTimeslotMap
		 DisplayString,
           ncmPRIPortSwitchType				
                INTEGER,
           ncmPRIPortOwnNumPlan				
                INTEGER,
           ncmPRIPortOwnNumType				
                INTEGER,
           ncmPRIPortSecurityLevel				
                INTEGER,
	   ncmPRIPortConfigStatus
		INTEGER,
           ncmPRIPortSetConfig
		INTEGER,
	   ncmPRICallProfCallRefCount
		INTEGER,
	   ncmPRIL2AutoEstablish
		 INTEGER,
	   ncmPRIResetCard
		 INTEGER
                }


	 ncmPRIPortNIDIndex OBJECT-TYPE
          SYNTAX  INTEGER (1..'7fffffff'h)
          ACCESS  read-only
          STATUS  mandatory
          DESCRIPTION
         "The object specifies the node id of the node."
           
          ::= { ncmPRIPortConfigEntry 1 }



	 ncmPRIPortLineIndex OBJECT-TYPE
          SYNTAX  INTEGER (1..'7fffffff'h)
          ACCESS  read-only
          STATUS  mandatory
          DESCRIPTION
         "The index value which uniquely identifies  the
          interface to which this entry is applicable."
           
          ::= { ncmPRIPortConfigEntry 2 }
 
 
         ncmPRIPortInService OBJECT-TYPE
          SYNTAX INTEGER {
           
                       no(1),
                       yes(2)
 
               } 
          ACCESS read-write
          STATUS mandatory
          DESCRIPTION
          "The object specifies whether the PRI Port is in service 
           or not."
 
          ::= { ncmPRIPortConfigEntry 3 }
 
 

         ncmPRIPortNFASMode OBJECT-TYPE
          SYNTAX INTEGER {
           
                       no-nFas(1),
                       nFas(2),
		       nFas-on-4(3),	
		       nFas-w-D(4)	
 
               } 
          ACCESS read-write
          STATUS mandatory
          DESCRIPTION
          "The variable specifies the Pri NFAS mode.
           For DPRI card, it has selections of 1)No Nfas, 2)Nfas
           For QPRI card, it has selections of 1)No Nfas, 2)Nfas on 4, 3)Nfas w/D 
           WARNING: The card must be reset for this change to take effect !" 

 
          ::= { ncmPRIPortConfigEntry 4 }
 
 
         ncmPRIPortDChanMode OBJECT-TYPE
          SYNTAX INTEGER {
           
                       normal(1),
                       inverted(2)
 
               } 
          ACCESS read-write
          STATUS mandatory
          DESCRIPTION
          "The variable specifies the pri D-channel mode." 
 
          ::= { ncmPRIPortConfigEntry 5 }
 

         ncmPRIPortDChanBits OBJECT-TYPE
          SYNTAX INTEGER {
           
			chan-8-Bit(1),
			chan-7-Bit(2),
			chan-6-Bit(3)
               } 
          ACCESS read-write
          STATUS mandatory
          DESCRIPTION
          "The variable specifies the pri D-channel bits." 
 
          ::= { ncmPRIPortConfigEntry 6 }
 

         ncmPRIPortTimeslotMap OBJECT-TYPE
          SYNTAX DisplayString 
          ACCESS read-write
          STATUS mandatory
          DESCRIPTION
          "The variable specifies the timeslot map." 
 
          ::= { ncmPRIPortConfigEntry 7 }
 


         ncmPRIPortSwitchType OBJECT-TYPE
          SYNTAX INTEGER {
           
			sw-Unspecified(1),
			sw-Att-4Ess(2),
			sw-Att-5Ess(3),
			sw-Att-Reserved(4),
			sw-Nti-Dms100(5),
			sw-Ni-2(6)
	--		sw-ni-2(6),
	--		sw-1tr6(11),
	--		sw-ccitt(12),
	--		sw-dass2(13),
	--		sw-net5(14),
	--		sw-vn(16)
 
               } 
          ACCESS read-write
          STATUS mandatory
          DESCRIPTION
          "The variable specifies the pri switch type." 
 
          ::= { ncmPRIPortConfigEntry 8 }
 

         ncmPRIPortOwnNumPlan OBJECT-TYPE
          SYNTAX INTEGER {
           
		       unkn-NumPlan(1),
		       isdn-E164(2),
		       telephony-E163(3),	
                       private(10)
 
               } 
          ACCESS read-write
          STATUS mandatory
          DESCRIPTION
          "The variable specifies the pri own numbering plan." 
 
          ::= { ncmPRIPortConfigEntry 9 }
 

         ncmPRIPortOwnNumType OBJECT-TYPE
          SYNTAX INTEGER {
           
		       unkn-NumType(1),
		       international(2),
		       national(3),	
                       local(5)
               } 
          ACCESS read-write
          STATUS mandatory
          DESCRIPTION
          "The variable specifies the pri own numbering type." 
 
          ::= { ncmPRIPortConfigEntry 10 }
 

         ncmPRIPortSecurityLevel OBJECT-TYPE
          SYNTAX INTEGER {
           
                       no-Checks(1),
                       own-Numbers(2),
                       ext-Numbers(3),
		       both-Numbers(4)	
 
               } 
          ACCESS read-write
          STATUS mandatory
          DESCRIPTION
          "The variable specifies the fdl mode which is bit 0 of  fdl
           Parameter1."
 
          ::= { ncmPRIPortConfigEntry 11 }
 

         ncmPRIPortConfigStatus OBJECT-TYPE
          SYNTAX INTEGER {
           
		       configuration-OK(1),
		       configuration-Error(2)
 
               } 
          ACCESS read-only
          STATUS mandatory
          DESCRIPTION
          "The variable specifies the configuration result." 
 
          ::= { ncmPRIPortConfigEntry 12 }
 

         ncmPRIPortSetConfig OBJECT-TYPE
          SYNTAX INTEGER {
           
		       set-Config(1),
		       not-in-use(2)
 
               } 
          ACCESS read-write
          STATUS mandatory
          DESCRIPTION
          "The set configuration operation that involves sending out
           the ACP message to set the configuration with the setup parameters" 
 
          ::= { ncmPRIPortConfigEntry 13 }
 

         ncmPRICallProfCallRefCount OBJECT-TYPE
           SYNTAX INTEGER 
           ACCESS read-only
           STATUS mandatory
           DESCRIPTION
           "The variable specifies the number of valid call reference numbers"

          ::= { ncmPRIPortConfigEntry 14 }


         ncmPRIL2AutoEstablish OBJECT-TYPE
          SYNTAX INTEGER {
           
                       no(1),
                       yes(2)
 
               } 
          ACCESS read-write
          STATUS mandatory
          DESCRIPTION
          "The object specifies whether the PRI Port has an Auto
           establishment for Layer-2 or not." 
 
          ::= { ncmPRIPortConfigEntry 15 }
 
 
         ncmPRIResetCard OBJECT-TYPE
          SYNTAX INTEGER {
           
		       reset-Card(1),
		       not-in-use(2)
 
               } 
          ACCESS read-write
          STATUS mandatory
          DESCRIPTION
          "The reset card operation that involves sending out the ACP 
           message to reset the card" 
 
          ::= { ncmPRIPortConfigEntry 16 }
 


	--   ncm PRI Call Profile Table

        ncmPRICallProfileTable OBJECT-TYPE
        SYNTAX  SEQUENCE OF NcmPRICallProfEntry
        ACCESS  not-accessible
        STATUS  mandatory
	DESCRIPTION
        "The PRI Call Profile table  ."


        --DEFAULT test-function    isdn-test
        --DEFAULT next-function    isdn-callprof-next

         ::= { ncm-isdn 8001 }


        ncmPRICallProfEntry OBJECT-TYPE
        SYNTAX  NcmPRICallProfEntry
        ACCESS  not-accessible
        STATUS  mandatory
        DESCRIPTION
        "An entry in the PRI Call Profile table  ."
         INDEX   { ncmPRICallProfNIDIndex, ncmPRICallProfLineIndex, ncmPRICPCallProfileRef }
         ::= { ncmPRICallProfileTable 1 }


         NcmPRICallProfEntry ::=
         SEQUENCE {
	
	   ncmPRICallProfNIDIndex
		 INTEGER,
           ncmPRICallProfLineIndex
                 INTEGER,
	   ncmPRICPCallProfileRef
		 INTEGER,
	   ncmPRICallProfCallDir
		 INTEGER,
	   ncmPRICallProfNumOwnDigit
		 INTEGER,
           ncmPRICallProfOwnCallNum
	         DisplayString, 
	   ncmPRICallProfExtNumPlan
                 INTEGER,
	   ncmPRICallProfExtNumType
		 INTEGER,
	   ncmPRICallProfExtNumDigit
		 INTEGER,
	   ncmPRICallProfExtCallNum
	         DisplayString, 
           ncmPRICallProfTransferMode
                 INTEGER,
           ncmPRICallProfCallBandWth
                 INTEGER,
	   ncmPRICallProfMultiRateCnt
		 INTEGER,
	   ncmPRICallProfRateAdaptn
		 INTEGER,
	   ncmPRICallProfTestCallIntvl
       	 	 INTEGER,
           ncmPRICallProfCallStatus
		 INTEGER,
           ncmPRICallProfCallAction
		 INTEGER,
	   ncmPRICPSetCallProf
		 INTEGER,
	   ncmPRICPSetCallProfResp
		 INTEGER,
	   ncmPRICPCallActionResp
		 INTEGER

                }


	 ncmPRICallProfNIDIndex OBJECT-TYPE
          SYNTAX  INTEGER (1..'7fffffff'h)
          ACCESS  read-only
          STATUS  mandatory
          DESCRIPTION
         "The object specifies the node id of the node."
           
          ::= { ncmPRICallProfEntry 1 }


	 ncmPRICallProfLineIndex OBJECT-TYPE
          SYNTAX  INTEGER (1..'7fffffff'h)
          ACCESS  read-only
          STATUS  mandatory
          DESCRIPTION
         "The index value which uniquely identifies  the
          interface to which this entry is applicable."
           
          ::= { ncmPRICallProfEntry 2 }
 
         
         ncmPRICPCallProfileRef OBJECT-TYPE
           SYNTAX INTEGER 
           ACCESS read-write
           STATUS mandatory
           DESCRIPTION
           "The variable specifies the number of the call profile in the
            list (starting from one, then two and so on)."

          ::= { ncmPRICallProfEntry 3 }


         ncmPRICallProfCallDir OBJECT-TYPE
          SYNTAX INTEGER {

		       no-Direction(1),
		       incoming(2),
	               outgoing(3),	
                       both-Directions(4)

                   }
           ACCESS read-write
           STATUS mandatory
           DESCRIPTION
           "The variable specifies the call direction."

           ::= { ncmPRICallProfEntry 4 }


        ncmPRICallProfNumOwnDigit OBJECT-TYPE
           SYNTAX INTEGER 
           ACCESS read-write
           STATUS mandatory
           DESCRIPTION
           "The variable specifies the number of own digits."

           ::= { ncmPRICallProfEntry 5 }


         ncmPRICallProfOwnCallNum OBJECT-TYPE
           SYNTAX DisplayString 
           ACCESS read-write
           STATUS mandatory
           DESCRIPTION
           "The variable specifies the own call number."

           ::= { ncmPRICallProfEntry 6 }


         ncmPRICallProfExtNumPlan OBJECT-TYPE
          SYNTAX INTEGER {

		       unkn-NumPlan(1),
		       isdn-E164(2),
		       telephony-E163(3),	
                       private(10)

                   }
           ACCESS read-write
           STATUS mandatory
           DESCRIPTION
           "The variable specifies the external numbering plan."

           ::= { ncmPRICallProfEntry 7 }


         ncmPRICallProfExtNumType OBJECT-TYPE
          SYNTAX INTEGER {

		       unkn-NumType(1),
		       international(2),
		       national(3),	
                       local(5)

                   }
           ACCESS read-write
           STATUS mandatory
           DESCRIPTION
           "The variable specifies the external numbering type."

           ::= { ncmPRICallProfEntry 8 }


         ncmPRICallProfExtNumDigit OBJECT-TYPE
           SYNTAX INTEGER 
           ACCESS read-write
           STATUS mandatory
           DESCRIPTION
           "The variable specifies the external number of digits."

           ::= { ncmPRICallProfEntry 9 }


         ncmPRICallProfExtCallNum OBJECT-TYPE
           SYNTAX DisplayString 
           ACCESS read-write
           STATUS mandatory
           DESCRIPTION
           "The variable specifies the external call number."

           ::= { ncmPRICallProfEntry 10 }


         ncmPRICallProfTransferMode OBJECT-TYPE
           SYNTAX INTEGER {

                       unrestricted-digital(8),
                       restricted-digital(9)

                   }
           ACCESS read-write
           STATUS mandatory
           DESCRIPTION
           "The variable specifies the transfer mode."

           ::= { ncmPRICallProfEntry 11 }


         ncmPRICallProfCallBandWth OBJECT-TYPE
          SYNTAX INTEGER {

		       b1-64K(16),
		       h0-6X64K(19),	
		       h11-24X64K(21),	
		       h12-30X64K(23),	
                       multiRate(24)
 
                   }
           ACCESS read-write
           STATUS mandatory
           DESCRIPTION
           "The variable specifies the call bandwidth."

           ::= { ncmPRICallProfEntry 12 }


         ncmPRICallProfMultiRateCnt OBJECT-TYPE
          SYNTAX INTEGER {

		       mR-2(2),
		       mR-4(4),
		       mR-6(6),	
		       mR-8(8),	
		       mR-12(12),	
                       mR-23(23),
		       mR-24(24),
		       mR-30(30),
		       mR-31(31)			
 
                   }
           ACCESS read-write
           STATUS mandatory
           DESCRIPTION
           "The variable specifies the multirate count."

           ::= { ncmPRICallProfEntry 13 }


         ncmPRICallProfRateAdaptn OBJECT-TYPE
           SYNTAX INTEGER {

                       no-Adapt(1),
                       adapt-56K(2)

                   }
           ACCESS read-write
           STATUS mandatory
           DESCRIPTION
           "The variable specifies the rate adaptation."

           ::= { ncmPRICallProfEntry 14 }


         ncmPRICallProfTestCallIntvl OBJECT-TYPE
           SYNTAX INTEGER 
           ACCESS read-write
           STATUS mandatory
           DESCRIPTION
           "The variable specifies the test call interval."

           ::= { ncmPRICallProfEntry 15 }


         ncmPRICallProfCallStatus OBJECT-TYPE
           SYNTAX INTEGER {

                       fail-Takedown-Idle(1),
                       successful-Setup(2),
		       unknown(3)	

                   }
           ACCESS read-only
           STATUS mandatory
           DESCRIPTION
           "The variable specifies the get call profile call status."

           ::= { ncmPRICallProfEntry 16 }


         ncmPRICallProfCallAction OBJECT-TYPE
           SYNTAX INTEGER {

                       setup-Call(1),
		       takedown-Call(2)	

                   }
           ACCESS read-write
           STATUS mandatory
           DESCRIPTION
           "The variable specifies the call profile call action."

           ::= { ncmPRICallProfEntry 17 }



	 ncmPRICPSetCallProf OBJECT-TYPE
	   SYNTAX INTEGER {
			
			set-CallProf(1),
			not-in-use(2)
	           }		
           ACCESS read-write
           STATUS mandatory
           DESCRIPTION
           "The variable specifies the call profile call action."

           ::= { ncmPRICallProfEntry 18 }


	 ncmPRICPSetCallProfResp OBJECT-TYPE
           SYNTAX INTEGER {

                       configuration-OK(1),
                       configuration-Error(2)

                   }
           ACCESS read-only
           STATUS mandatory
           DESCRIPTION
           "The variable specifies the set call profile result"

           ::= { ncmPRICallProfEntry 19 }


	 ncmPRICPCallActionResp OBJECT-TYPE
           SYNTAX INTEGER {

                       configuration-OK(1),
                       configuration-Error(2)

                   }
           ACCESS read-only
           STATUS mandatory
           DESCRIPTION
           "The variable specifies the call action result"

           ::= { ncmPRICallProfEntry 20 }




	-- ncm  PRI Call Profile List Table


        ncmPRICallProfListTable OBJECT-TYPE
        SYNTAX  SEQUENCE OF NcmPRICallProfListEntry
        ACCESS  not-accessible
        STATUS  mandatory
	DESCRIPTION
        "The PRI Call Profile List table  ."


        --DEFAULT test-function    isdn-callprof-test
        --DEFAULT next-function    isdn-callprof-next
	         ::= { ncm-isdn 8002 }


        ncmPRICallProfListEntry OBJECT-TYPE
        SYNTAX  NcmPRICallProfListEntry
        ACCESS  not-accessible
        STATUS  mandatory
        DESCRIPTION
        "An entry in the PRI Call Profile List table  ."
         INDEX   { ncmPRICPListNIDIndex, ncmPRICPListLineIndex, ncmPRICPListIndex }
         ::= { ncmPRICallProfListTable 1 }


         NcmPRICallProfListEntry ::=
         SEQUENCE {
	
	   ncmPRICPListNIDIndex
		 INTEGER,
           ncmPRICPListLineIndex
                 INTEGER,
	   ncmPRICPListIndex
		 INTEGER,
	   ncmPRICPListValidCPRefNum
		 INTEGER

	 }


	 ncmPRICPListNIDIndex OBJECT-TYPE
          SYNTAX  INTEGER (1..'7fffffff'h)
          ACCESS  read-only
          STATUS  mandatory
          DESCRIPTION
         "The object specifies the node id of the node of the 
          call profile list group."
           
          ::= { ncmPRICallProfListEntry 1 }


	 ncmPRICPListLineIndex OBJECT-TYPE
          SYNTAX  INTEGER (1..'7fffffff'h)
          ACCESS  read-only
          STATUS  mandatory
          DESCRIPTION
         "The index value which uniquely identifies the
          interface to which this entry is applicable."
           
          ::= { ncmPRICallProfListEntry 2 }
 
         
         ncmPRICPListIndex OBJECT-TYPE
          SYNTAX  INTEGER 
             ACCESS  read-only
             STATUS  mandatory
             DESCRIPTION
                "The call profile list call reference index." 

          ::= { ncmPRICallProfListEntry 3 }
 

         ncmPRICPListValidCPRefNum OBJECT-TYPE
           SYNTAX INTEGER 
           ACCESS read-only
           STATUS mandatory
           DESCRIPTION
           "The variable is the valid call reference number."

          ::= { ncmPRICallProfListEntry 4 }



     -- ncm PRI Current Table


        ncmPRICurrentTable OBJECT-TYPE
        SYNTAX  SEQUENCE OF NcmPRICurrentEntry
        ACCESS  not-accessible
        STATUS  mandatory
	DESCRIPTION
        "The PRI Current Interval table  ."

        --DEFAULT test-function    isdn-test
        --DEFAULT next-function    isdn-next
	 

         ::= { ncm-isdn 8003 }


        ncmPRICurrentEntry OBJECT-TYPE
        SYNTAX  NcmPRICurrentEntry
        ACCESS  not-accessible
        STATUS  mandatory
        DESCRIPTION
        "An entry in the PRI Current Interval table  ."
         INDEX   { ncmPRICurrNIDIndex, ncmPRICurrLineIndex, ncmPRICurrEndType }
         ::= { ncmPRICurrentTable 1 }


         NcmPRICurrentEntry ::=
         SEQUENCE {
	
	   ncmPRICurrNIDIndex
		 INTEGER,
           ncmPRICurrLineIndex
                 INTEGER,
           ncmPRICurrEndType 
                 INTEGER,
	   ncmPRICurrTimestamp
	         INTEGER,
	   ncmPRICurrSecsInCurrIntvl
		 INTEGER,
	   ncmPRICurrInfoRx
	         INTEGER,
	   ncmPRICurrInfoTx
	         INTEGER,
	   ncmPRICurrCRCErrRx
	         INTEGER,
	   ncmPRICurrInvalidFrameRx
	         INTEGER,
	   ncmPRICurrFrameAbortRx
	         INTEGER,
	   ncmPRICurrDISCSRx
	         INTEGER,
	   ncmPRICurrDISCSTx
	         INTEGER,
	   ncmPRICurrFramerRx
	         INTEGER,
	   ncmPRICurrFramerTx
	         INTEGER,
	   ncmPRICurrLyr3ProtErr
	         INTEGER,
	   ncmPRICurrCallSetupSent
	         INTEGER,
	   ncmPRICurrCallSetupSentnFail
	         INTEGER,
	   ncmPRICurrCallSetupRx
	         INTEGER,
	   ncmPRICurrCallSetupRxnFail
	         INTEGER,
	   ncmPRICurrUnSupportMsgRx
	         INTEGER,
	   ncmPRICurrTstCalSetupSentnFail
	         INTEGER,
	   ncmPRICurrValidIntvls
		 INTEGER,
	   ncmPRICurrStatisticReset
		 INTEGER

                }


	 ncmPRICurrNIDIndex OBJECT-TYPE
          SYNTAX  INTEGER (1..'7fffffff'h)
          ACCESS  read-only
          STATUS  mandatory
          DESCRIPTION
         "The object specifies the node id of the node."
           
          ::= { ncmPRICurrentEntry 1 }



	 ncmPRICurrLineIndex OBJECT-TYPE
          SYNTAX  INTEGER (1..'7fffffff'h)
          ACCESS  read-only
          STATUS  mandatory
          DESCRIPTION
         "The index value which uniquely identifies  the
          interface to which this entry is applicable."
           
          ::= { ncmPRICurrentEntry 2 }
 

         ncmPRICurrEndType OBJECT-TYPE
          SYNTAX INTEGER {

                       near-End(1),
                       far-End(2)

                   }
           ACCESS read-only
           STATUS mandatory
           DESCRIPTION
           "The variable specifies the End Type   ."

          ::= { ncmPRICurrentEntry 3 }


	 ncmPRICurrTimestamp OBJECT-TYPE
          SYNTAX  INTEGER 
          ACCESS  read-only
          STATUS  mandatory
          DESCRIPTION
         "The object specifies the timestamp in seconds."
           
          ::= { ncmPRICurrentEntry 4 }


	 ncmPRICurrSecsInCurrIntvl OBJECT-TYPE
          SYNTAX  INTEGER 
          ACCESS  read-only
          STATUS  mandatory
          DESCRIPTION
         "The object specifies the seconds in current interval."
           
          ::= { ncmPRICurrentEntry 5 }


	 ncmPRICurrInfoRx OBJECT-TYPE
          SYNTAX  INTEGER 
          ACCESS  read-only
          STATUS  mandatory
          DESCRIPTION
         "The object specifies the current INFOs received."
           
          ::= { ncmPRICurrentEntry 6 }


	 ncmPRICurrInfoTx OBJECT-TYPE
          SYNTAX  INTEGER 
          ACCESS  read-only
          STATUS  mandatory
          DESCRIPTION
         "The object specifies the current INFOs transmitted."
           
          ::= { ncmPRICurrentEntry 7 }


	 ncmPRICurrCRCErrRx OBJECT-TYPE
          SYNTAX  INTEGER 
          ACCESS  read-only
          STATUS  mandatory
          DESCRIPTION
         "The object specifies the current CRC errors received."
           
          ::= { ncmPRICurrentEntry 8 }


	 ncmPRICurrInvalidFrameRx OBJECT-TYPE
          SYNTAX  INTEGER 
          ACCESS  read-only
          STATUS  mandatory
          DESCRIPTION
         "The object specifies the current invalid frames received."
           
          ::= { ncmPRICurrentEntry 9 }


	 ncmPRICurrFrameAbortRx OBJECT-TYPE
          SYNTAX  INTEGER 
          ACCESS  read-only
          STATUS  mandatory
          DESCRIPTION
         "The object specifies the current frame aborts received."
           
          ::= { ncmPRICurrentEntry 10 }


	 ncmPRICurrDISCSRx OBJECT-TYPE
          SYNTAX  INTEGER 
          ACCESS  read-only
          STATUS  mandatory
          DESCRIPTION
         "The object specifies the current DISCs received."
           
          ::= { ncmPRICurrentEntry 11 }


	 ncmPRICurrDISCSTx OBJECT-TYPE
          SYNTAX  INTEGER 
          ACCESS  read-only
          STATUS  mandatory
          DESCRIPTION
         "The object specifies the current DISCs transmitted."
           
          ::= { ncmPRICurrentEntry 12 }


	 ncmPRICurrFramerRx OBJECT-TYPE
          SYNTAX  INTEGER 
          ACCESS  read-only
          STATUS  mandatory
          DESCRIPTION
         "The object specifies the current framer received."
           
          ::= { ncmPRICurrentEntry 13 }


	 ncmPRICurrFramerTx OBJECT-TYPE
          SYNTAX  INTEGER 
          ACCESS  read-only
          STATUS  mandatory
          DESCRIPTION
         "The object specifies the current framer transmitted."
           
          ::= { ncmPRICurrentEntry 14 }


	 ncmPRICurrLyr3ProtErr OBJECT-TYPE
          SYNTAX  INTEGER 
          ACCESS  read-only
          STATUS  mandatory
          DESCRIPTION
         "The object specifies the current Layer 3 protocol errors."
           
          ::= { ncmPRICurrentEntry 15 }


	 ncmPRICurrCallSetupSent OBJECT-TYPE
          SYNTAX  INTEGER 
          ACCESS  read-only
          STATUS  mandatory
          DESCRIPTION
         "The object specifies the current call setup sent."
           
          ::= { ncmPRICurrentEntry 16 }


	 ncmPRICurrCallSetupSentnFail OBJECT-TYPE
          SYNTAX  INTEGER 
          ACCESS  read-only
          STATUS  mandatory
          DESCRIPTION
         "The object specifies the current call setup sent and failed."
           
          ::= { ncmPRICurrentEntry 17 }


	 ncmPRICurrCallSetupRx OBJECT-TYPE
          SYNTAX  INTEGER 
          ACCESS  read-only
          STATUS  mandatory
          DESCRIPTION
         "The object specifies the current call setup received."
           
          ::= { ncmPRICurrentEntry 18 }


	 ncmPRICurrCallSetupRxnFail OBJECT-TYPE
          SYNTAX  INTEGER 
          ACCESS  read-only
          STATUS  mandatory
          DESCRIPTION
         "The object specifies the current call setup received and failed."
           
          ::= { ncmPRICurrentEntry 19 }


	 ncmPRICurrUnSupportMsgRx OBJECT-TYPE
          SYNTAX  INTEGER 
          ACCESS  read-only
          STATUS  mandatory
          DESCRIPTION
         "The object specifies the current unsupported message received."
           
          ::= { ncmPRICurrentEntry 20 }


	 ncmPRICurrTstCalSetupSentnFail OBJECT-TYPE
          SYNTAX  INTEGER 
          ACCESS  read-only
          STATUS  mandatory
          DESCRIPTION
         "The object specifies the current test call setups sent and failed."
           
          ::= { ncmPRICurrentEntry 21 }


         ncmPRICurrValidIntvls OBJECT-TYPE
          SYNTAX  INTEGER 
             ACCESS  read-only
             STATUS  mandatory
             DESCRIPTION
                "A number between 1 and 96" 

          ::= { ncmPRICurrentEntry 22 }
 

	 ncmPRICurrStatisticReset OBJECT-TYPE
	   SYNTAX INTEGER {
			
			statistic-Reset(1)

	           }		
           ACCESS read-write
           STATUS mandatory
           DESCRIPTION
           "The variable specifies the statistic reset operation."

          ::= { ncmPRICurrentEntry 23 }




     --  PRI Interval Table


        ncmPRIIntervalTable OBJECT-TYPE
        SYNTAX  SEQUENCE OF NcmPRIIntervalEntry
        ACCESS  not-accessible
        STATUS  mandatory
	DESCRIPTION
        "The PRI Interval table  ."
        --DEFAULT test-function    isdn-interval-test
        --DEFAULT next-function    isdn-interval-next
	


         ::= { ncm-isdn 8004 }


        ncmPRIIntervalEntry OBJECT-TYPE
        SYNTAX  NcmPRIIntervalEntry
        ACCESS  not-accessible
        STATUS  mandatory
        DESCRIPTION
        "An entry in the PRI Interval table  ."
         INDEX   { ncmPRIntvlNIDIndex, ncmPRIntvlLineIndex, ncmPRIntvlEndType, ncmPRIntvlIndex }
         ::= { ncmPRIIntervalTable 1 }


         NcmPRIIntervalEntry ::=
         SEQUENCE {
	
	   ncmPRIntvlNIDIndex
		 INTEGER,
           ncmPRIntvlLineIndex
                 INTEGER,
           ncmPRIntvlEndType 
                 INTEGER,
	   ncmPRIntvlIndex
		 INTEGER,
	   ncmPRIntvlTimestamp
	         INTEGER,
	   ncmPRIntvlSecsInCurrIntvl
		 INTEGER,
	   ncmPRIntvlInfoRx
	         INTEGER,
	   ncmPRIntvlInfoTx
	         INTEGER,
	   ncmPRIntvlCRCErrRx
	         INTEGER,
	   ncmPRIntvlInvalidFrameRx
	         INTEGER,
	   ncmPRIntvlFrameAbortRx
	         INTEGER,
	   ncmPRIntvlDISCSRx
	         INTEGER,
	   ncmPRIntvlDISCSTx
	         INTEGER,
	   ncmPRIntvlFramerRx
	         INTEGER,
	   ncmPRIntvlFramerTx
	         INTEGER,
	   ncmPRIntvlLyr3ProtErr
	         INTEGER,
	   ncmPRIntvlCallSetupSent
	         INTEGER,
	   ncmPRIntvlCallSetupSentnFail
	         INTEGER,
	   ncmPRIntvlCallSetupRx
	         INTEGER,
	   ncmPRIntvlCallSetupRxnFail
	         INTEGER,
	   ncmPRIntvlUnSupportMsgRx
	         INTEGER,
	   ncmPRIntvlTstCalSetupSentnFail
	         INTEGER
                }


	 ncmPRIntvlNIDIndex OBJECT-TYPE
          SYNTAX  INTEGER (1..'7fffffff'h)
          ACCESS  read-only
          STATUS  mandatory
          DESCRIPTION
         "The object specifies the node id of the node."
           
          ::= { ncmPRIIntervalEntry 1 }



	 ncmPRIntvlLineIndex OBJECT-TYPE
          SYNTAX  INTEGER (1..'7fffffff'h)
          ACCESS  read-only
          STATUS  mandatory
          DESCRIPTION
         "The index value which uniquely identifies  the
          interface to which this entry is applicable."
           
          ::= { ncmPRIIntervalEntry 2 }
 

         ncmPRIntvlEndType OBJECT-TYPE
          SYNTAX INTEGER {

                       near-End(1),
                       far-End(2)

                   }
           ACCESS read-only
           STATUS mandatory
           DESCRIPTION
           "The variable specifies the End Type   ."

          ::= { ncmPRIIntervalEntry 3 }


         ncmPRIntvlIndex OBJECT-TYPE
          SYNTAX  INTEGER 
             ACCESS  read-only
             STATUS  mandatory
             DESCRIPTION
                "The interval index." 

          ::= { ncmPRIIntervalEntry 4 }
 

	 ncmPRIntvlTimestamp OBJECT-TYPE
          SYNTAX  INTEGER 
          ACCESS  read-only
          STATUS  mandatory
          DESCRIPTION
         "The object specifies the interval timestamp in seconds."
           
          ::= { ncmPRIIntervalEntry 5 }


	 ncmPRIntvlSecsInCurrIntvl OBJECT-TYPE
          SYNTAX  INTEGER 
          ACCESS  read-only
          STATUS  mandatory
          DESCRIPTION
         "The object specifies the interval seconds in current interval."
           
          ::= { ncmPRIIntervalEntry 6 }


	 ncmPRIntvlInfoRx OBJECT-TYPE
          SYNTAX  INTEGER 
          ACCESS  read-only
          STATUS  mandatory
          DESCRIPTION
         "The object specifies the interval INFOs received."
           
          ::= { ncmPRIIntervalEntry 7 }


	 ncmPRIntvlInfoTx OBJECT-TYPE
          SYNTAX  INTEGER 
          ACCESS  read-only
          STATUS  mandatory
          DESCRIPTION
         "The object specifies the interval INFOs transmitted."
           
          ::= { ncmPRIIntervalEntry 8 }


	 ncmPRIntvlCRCErrRx OBJECT-TYPE
          SYNTAX  INTEGER 
          ACCESS  read-only
          STATUS  mandatory
          DESCRIPTION
         "The object specifies the interval CRC errors received."
           
          ::= { ncmPRIIntervalEntry 9 }


	 ncmPRIntvlInvalidFrameRx OBJECT-TYPE
          SYNTAX  INTEGER 
          ACCESS  read-only
          STATUS  mandatory
          DESCRIPTION
         "The object specifies the interval invalid frames received."
           
          ::= { ncmPRIIntervalEntry 10 }


	 ncmPRIntvlFrameAbortRx OBJECT-TYPE
          SYNTAX  INTEGER 
          ACCESS  read-only
          STATUS  mandatory
          DESCRIPTION
         "The object specifies the interval frame aborts received."
           
          ::= { ncmPRIIntervalEntry 11 }


	 ncmPRIntvlDISCSRx OBJECT-TYPE
          SYNTAX  INTEGER 
          ACCESS  read-only
          STATUS  mandatory
          DESCRIPTION
         "The object specifies the interval DISCs received."
           
          ::= { ncmPRIIntervalEntry 12 }


	 ncmPRIntvlDISCSTx OBJECT-TYPE
          SYNTAX  INTEGER 
          ACCESS  read-only
          STATUS  mandatory
          DESCRIPTION
         "The object specifies the interval DISCs transmitted."
           
          ::= { ncmPRIIntervalEntry 13 }


	 ncmPRIntvlFramerRx OBJECT-TYPE
          SYNTAX  INTEGER 
          ACCESS  read-only
          STATUS  mandatory
          DESCRIPTION
         "The object specifies the interval framer received."
           
          ::= { ncmPRIIntervalEntry 14 }


	 ncmPRIntvlFramerTx OBJECT-TYPE
          SYNTAX  INTEGER 
          ACCESS  read-only
          STATUS  mandatory
          DESCRIPTION
         "The object specifies the interval framer transmitted."
           
          ::= { ncmPRIIntervalEntry 15 }


	 ncmPRIntvlLyr3ProtErr OBJECT-TYPE
          SYNTAX  INTEGER 
          ACCESS  read-only
          STATUS  mandatory
          DESCRIPTION
         "The object specifies the interval Layer 3 protocol errors."
           
          ::= { ncmPRIIntervalEntry 16 }


	 ncmPRIntvlCallSetupSent OBJECT-TYPE
          SYNTAX  INTEGER 
          ACCESS  read-only
          STATUS  mandatory
          DESCRIPTION
         "The object specifies the interval call setup sent."
           
          ::= { ncmPRIIntervalEntry 17 }


	 ncmPRIntvlCallSetupSentnFail OBJECT-TYPE
          SYNTAX  INTEGER 
          ACCESS  read-only
          STATUS  mandatory
          DESCRIPTION
         "The object specifies the interval call setup sent and failed."
           
          ::= { ncmPRIIntervalEntry 18 }


	 ncmPRIntvlCallSetupRx OBJECT-TYPE
          SYNTAX  INTEGER 
          ACCESS  read-only
          STATUS  mandatory
          DESCRIPTION
         "The object specifies the interval call setup received."
           
          ::= { ncmPRIIntervalEntry 19 }


	 ncmPRIntvlCallSetupRxnFail OBJECT-TYPE
          SYNTAX  INTEGER 
          ACCESS  read-only
          STATUS  mandatory
          DESCRIPTION
         "The object specifies the interval call setup received and failed."
           
          ::= { ncmPRIIntervalEntry 20 }


	 ncmPRIntvlUnSupportMsgRx OBJECT-TYPE
          SYNTAX  INTEGER 
          ACCESS  read-only
          STATUS  mandatory
          DESCRIPTION
         "The object specifies the interval unsupported message received."
           
          ::= { ncmPRIIntervalEntry 21 }


	 ncmPRIntvlTstCalSetupSentnFail OBJECT-TYPE
          SYNTAX  INTEGER 
          ACCESS  read-only
          STATUS  mandatory
          DESCRIPTION
         "The object specifies the interval test call setups sent and failed."
           
          ::= { ncmPRIIntervalEntry 22 }



END
