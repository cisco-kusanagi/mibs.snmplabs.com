-- extracted from draft-cha-gsmp-service-mib-00.txt
-- at Wed Nov  6 06:11:20 2002

                       GSMP-SERVICE-MIB  DEFINITIONS ::= BEGIN 
                                      draft-cha-gsmp-service-mib-00.txt      October 2002 
                     
                     
                       IMPORTS 
                        
                          MODULE-IDENTITY, OBJECT-TYPE, NOTIFICATION-TYPE, 
                          Unsigned32, Integer32, zeroDotZero, Counter64, mib-2 
                             FROM  SNMPv2-SMI                          -- [RFC2578] 
                          TEXTUAL-CONVENTION, RowStatus, StorageType,  
                          TruthValue, RowPointer 
                             FROM  SNMPv2-TC                           -- [RFC2579] 
                          OBJECT-GROUP, NOTIFICATION-GROUP, MODULE-COMPLIANCE 
                             FROM  SNMPv2-CONF                         -- [RFC2580] 
                          InterfaceIndex, InterfaceIndexOrZero 
                             FROM IF-MIB                               -- [RFC2863] 
                          ; 
                        
                       gsmpServiceMIB MODULE-IDENTITY 
                          LAST-UPDATED 
                             "200210230000Z" 
                          ORGANIZATION 
                             "Andong National University (ANU)" 
                          CONTACT-INFO    
                             "Editor: YoungWook Cha 
                              Email:  ywcha@andong.ac.kr 
                        
                              Editor: TaeHyun Kwon 
                              Email:  freeman@comeng.andong.ac.kr" 
                          DESCRIPTION  
                             "This MIB contains managed object definitions for network  
                             management services in General Switch Management Protocol  
                             (GSMP) Interface." 
                          -- Revision history 
                          REVISION 
                             "200210230000Z" 
                          DESCRIPTION 
                             "Initial revision, published as part of RFC XXXX." 
                          ::= { mib-2 XXX } 
                        
                       -- Top Level Componets of the MIB 
                       gsmpServiceObjects   OBJECT IDENTIFIER ::={ gsmpServiceMIB 1} 
                        
                       -- Textural Conventions -- 
                       Label ::= TEXTUAL-CONVENTION 
                          STATUS        current 
                          DESCRIPTION 
                             "This value represents an label as defined in [RFC3292]." 
                          SYNTAX  Unsigned32 (0..4294967295) 
                        
                       Owner ::= TEXTUAL-CONVENTION 
                          STATUS      current 
                                      draft-cha-gsmp-service-mib-00.txt      October 2002 
                     
                     
                          DESCRIPTION 
                             "The entity that originally created the object in question. 
                             The values of this enumeration are defined as follows: 
                             other(1) - This is used when an entity which has not been 
                             enumerated in this textual convention but which is known by the 
                             agent. 
                             snmp(2) - The Simple Network Management Protocol was used to 
                             configure this object initially. 
                             ldp(3) - The Label Distribution Protocol was used to configure 
                             this object initially. 
                             rsvp(4) - The Resource Reservation Protocol was used to  
                             configure this object initially. 
                             crldp(5) - The Constraint-Based Label Distribution Protocol was 
                             used to configure this object initially. 
                             policyAgent(6) - A policy agent (perhaps in combination with  
                             one of the above protocols) was used to configure this object  
                             initially. 
                             unknown(7) - the agent cannot discern which component created 
                             the object." 
                          SYNTAX   INTEGER { 
                                      other(1), 
                                      snmp(2), 
                                      ldp(3), 
                                      rsvp(4), 
                                      crldp(5), 
                                      policyAgent(6), 
                                      unknown(7) 
                                   } 
                       -- End of Textural Conventions -- 
                        
                       -- Entity Objects -- 
                        
                       -- Switch Config Table 
                       gsmpSwitchConfTable OBJECT-TYPE 
                          SYNTAX         SEQUENCE OF GsmpSwitchConfEntry 
                          MAX-ACCESS     not-accessible 
                          STATUS         current 
                          DESCRIPTION 
                             "This table represents the information of switch  
                             configuration." 
                          ::= { gsmpServiceObjects 1 } 
                        
                       gsmpSwitchConfEntry OBJECT-TYPE 
                          SYNTAX         GsmpSwitchConfEntry 
                          MAX-ACCESS     not-accessible 
                          STATUS         current 
                          DESCRIPTION 
                             "The entry of this table is mapped with the each switch  
                                      draft-cha-gsmp-service-mib-00.txt      October 2002 
                     
                     
                             partition." 
                          INDEX  { gsmpSwitchPartitionIndex } 
                          ::= { gsmpSwitchConfTable 1 } 
                        
                       GsmpSwitchConfEntry ::= SEQUENCE { 
                          gsmpSwitchPartitionIndex      Integer32,  
                          gsmpSwitchConfMtype1          Integer32,  
                          gsmpSwitchConfMtype2          Integer32,  
                          gsmpSwitchConfMtype3          Integer32,  
                          gsmpSwitchConfMtype4          Integer32,  
                          gsmpSwitchConfFirmVer         OCTET STRING, 
                          gsmpSwitchConfWindowSize      Integer32, 
                          gsmpSwitchConfSwitchType      OCTET STRING, 
                          gsmpSwitchConfSwitchName      OCTET STRING, 
                          gsmpSwitchConfMaxReservation  Integer32 
                       } 
                        
                       gsmpSwitchPartitionIndex OBJECT-TYPE 
                          SYNTAX         Integer32 (0..255) 
                          MAX-ACCESS     not-accessible 
                          STATUS         current 
                          DESCRIPTION  
                             "This is unique index for an entry in the gsmpSwitchConfEntry." 
                          ::= { gsmpSwitchConfEntry 1} 
                              
                       gsmpSwitchConfMtype1 OBJECT-TYPE 
                          SYNTAX         Integer32 (0..255) 
                          MAX-ACCESS     read-write 
                          STATUS         current 
                          DESCRIPTION  
                             "In the request, this object contains the requested QoS  
                             configuration type. In the response, this object contains the  
                             accepted QoS configuration type.  
                                0     : Indicates use of the default GSMP model 
                                1     : Indicates use of IEEE qGSMP model 
                                2-200 : Reserved 
                                201-255 : Experimental" 
                          DEFVAL {0} 
                          ::= { gsmpSwitchConfEntry 2} 
                        
                       gsmpSwitchConfMtype2 OBJECT-TYPE 
                          SYNTAX         Integer32 (0..255) 
                          MAX-ACCESS     read-only 
                          STATUS         current 
                          DESCRIPTION  
                             "If the switch can not support the requested OoS configuration  
                             type in gsmpSwitchConfMtype1, it negotiates the QoS model with 
                             the manager by offering up to three additional MType" 
                                      draft-cha-gsmp-service-mib-00.txt      October 2002 
                     
                     
                          ::= { gsmpSwitchConfEntry 3} 
                        
                       gsmpSwitchConfMtype3 OBJECT-TYPE 
                          SYNTAX         Integer32 (0..255) 
                          MAX-ACCESS     read-only 
                          STATUS         current 
                          DESCRIPTION  
                             "If the switch can not support the requested OoS configuration  
                             type in gsmpSwitchConfMtype1, it negotiates the QoS model with 
                             the manager by offering up to three additional Mtype" 
                          ::= { gsmpSwitchConfEntry 4} 
                        
                       gsmpSwitchConfMtype4 OBJECT-TYPE 
                          SYNTAX         Integer32 (0..255) 
                          MAX-ACCESS     read-only 
                          STATUS         current 
                          DESCRIPTION  
                             "If the switch can not support the requested OoS configuration  
                             type in gsmpSwitchConfMtype1, it negotiates the QoS model with  
                             the manager by offering up to three additional Mtype" 
                          ::= { gsmpSwitchConfEntry 5} 
                        
                       gsmpSwitchConfFirmVer OBJECT-TYPE 
                          SYNTAX         OCTET STRING (SIZE(2)) 
                          MAX-ACCESS     read-only 
                          STATUS         current 
                          DESCRIPTION  
                             "The version number of the switch control firmware installed." 
                          ::= { gsmpSwitchConfEntry 6}   
                        
                       gsmpSwitchConfWindowSize OBJECT-TYPE 
                          SYNTAX         Integer32 (1..65535) 
                          MAX-ACCESS     read-write 
                          STATUS         current 
                          DESCRIPTION  
                             "The maximum number of unacknowledged request messages that may  
                             be transmitted by the controller without the possibility of  
                             loss."    
                          ::= { gsmpSwitchConfEntry 7} 
                        
                       gsmpSwitchConfSwitchType OBJECT-TYPE 
                          SYNTAX         OCTET STRING (SIZE(2)) 
                          MAX-ACCESS     read-only 
                          STATUS         current 
                          DESCRIPTION  
                             "A 16-bit value allocated by the manufacturer of the switch. 
                             When this value is combined with the OUI from the  
                             gsmpSwitchConfSwitchName, the product is uniquely identified." 
                                      draft-cha-gsmp-service-mib-00.txt      October 2002 
                     
                     
                          ::= { gsmpSwitchConfEntry 8} 
                        
                       gsmpSwitchConfSwitchName OBJECT-TYPE 
                          SYNTAX         OCTET STRING (SIZE(6)) 
                          MAX-ACCESS     read-only 
                          STATUS         current 
                          DESCRIPTION  
                             "This object is a 48-bit quantity. A 48-bit IEEE 802 MAC  
                             address, if available, may be used." 
                          ::= { gsmpSwitchConfEntry 9} 
                     
                       gsmpSwitchConfMaxReservation OBJECT-TYPE 
                          SYNTAX         Integer32 (0..2147483647) 
                          MAX-ACCESS     read-only 
                          STATUS         current 
                          DESCRIPTION  
                           "The maximum number of reservations that the switch can support. 
                             A value of 0 indicates that the switch does not support  
                             reservations."  
                          ::= { gsmpSwitchConfEntry 10} 
                        
                       -- End of gsmpSwitchConfTable 
                        
                       -- Interface Confing Table 
                       gsmpInterfaceConfTable OBJECT-TYPE 
                          SYNTAX         SEQUENCE OF GsmpInterfaceConfEntry 
                          MAX-ACCESS     not-accessible 
                          STATUS         current 
                          DESCRIPTION 
                             "This table represents the configuration information of a  
                             single switch port." 
                          ::= { gsmpServiceObjects 2 } 
                        
                       gsmpInterfaceConfEntry OBJECT-TYPE 
                          SYNTAX         GsmpInterfaceConfEntry 
                          MAX-ACCESS     not-accessible 
                          STATUS         current 
                          DESCRIPTION 
                             "An entry in this table represents the configuration  
                             information of a single switch port." 
                          INDEX { gsmpInterfaceConfIndex } 
                          ::= { gsmpInterfaceConfTable 1 } 
                        
                       GsmpInterfaceConfEntry ::= SEQUENCE { 
                          gsmpInterfaceConfIndex     InterfaceIndexOrZero, 
                          gsmpPortType               INTEGER, 
                          gsmpPortStatus             INTEGER, 
                          gsmpLineType               INTEGER, 
                                      draft-cha-gsmp-service-mib-00.txt      October 2002 
                     
                     
                          gsmpFunctionType           INTEGER, 
                          gsmpLineStatus             INTEGER, 
                          gsmpPriorties              Integer32, 
                          gsmpPhysicalSlotNumber     Integer32, 
                          gsmpPhysicalPortNumber     Integer32, 
                          gsmpMinLabel               Label, 
                          gsmpMaxLabel               Label, 
                          gsmpRemainingLabels        Unsigned32, 
                          gsmpConnectionReplace      TruthValue, 
                          gsmpDuration               Integer32, 
                          gsmpEventSequenceNumber    Integer32, 
                          gsmpEventFlags             BITS, 
                          gsmpFlowControlFlags       BITS, 
                          gsmpReceiveDataRate        Unsigned32, 
                          gsmpTransmitDataRate       Unsigned32 
                       } 
                        
                       gsmpInterfaceConfIndex OBJECT-TYPE 
                          SYNTAX         InterfaceIndexOrZero 
                          MAX-ACCESS     not-accessible 
                          STATUS         current 
                          DESCRIPTION 
                             "This is a unique index for an entry in the  
                             gsmpInterfaceConfTable." 
                          ::= { gsmpInterfaceConfEntry 1 } 
                        
                       gsmpPortType OBJECT-TYPE 
                          SYNTAX         INTEGER  { 
                                                     atm(1), 
                                                     frameRelay(2), 
                                                     mpls(3) 
                                         } 
                          MAX-ACCESS     read-only 
                          STATUS         current 
                          DESCRIPTION 
                             "This object represents the port type." 
                          ::= { gsmpInterfaceConfEntry 2 } 
                        
                       gsmpPortStatus OBJECT-TYPE 
                          SYNTAX         INTEGER  { 
                                                     available(1), 
                                                     unavailable(2), 
                                                     internalLoopback(3), 
                                                     externalLoopback(4), 
                                                     bothwayLoopback(5) 
                                         } 
                          MAX-ACCESS     read-write 
                          STATUS         current 
                                      draft-cha-gsmp-service-mib-00.txt      October 2002 
                     
                     
                          DESCRIPTION 
                             "This object indicates the port status." 
                          ::= { gsmpInterfaceConfEntry 3 } 
                        
                       gsmpLineType OBJECT-TYPE 
                          SYNTAX         INTEGER  { 
                                                     other(1), 
                                                     ethernetCsmacd(2), 
                                                     ppp(3), 
                                                     atm(4), 
                                                     frameRelayService(5) 
                                         } 
                          MAX-ACCESS     read-only 
                          STATUS         current 
                          DESCRIPTION 
                             "This object represents the type of physical transmission  
                             interface for this port. 
                                PortType = Unknown: other(1) 
                                PortType = MPLS:    ethernetCsmacd(2), 
                                                    ppp(3) 
                                PortType = ATM:     atm(4) 
                                PortType = FR:      frameRelayService(5)" 
                          ::= { gsmpInterfaceConfEntry 4 } 
                        
                       gsmpFunctionType OBJECT-TYPE 
                          SYNTAX         INTEGER { 
                                                     bringUp(1), 
                                                     takeDown(2), 
                                                     internalLoopback(3), 
                                                     externelLoopback(4), 
                                                     bothwayLoopback(5), 
                                                     resetInputPort(6), 
                                                     resetFlags(7), 
                                                     setTransimtDataRate(8) 
                                         } 
                          MAX-ACCESS     read-write 
                          STATUS         current 
                          DESCRIPTION 
                             "It specifies the action to be taken by the switch. 
                             The specified action will be taken regardless of the current 
                             status of the port." 
                          ::= { gsmpInterfaceConfEntry 5} 
                        
                       gsmpLineStatus OBJECT-TYPE 
                          SYNTAX         INTEGER  { 
                                                     up(1), 
                                                     down(2), 
                                                     test(3) 

                                      draft-cha-gsmp-service-mib-00.txt      October 2002 
                     
                     
                                         } 
                          MAX-ACCESS     read-write 
                          STATUS         current 
                          DESCRIPTION 
                             "It defines the status of the physical transmission medium 
                             connected to the port. The defined values of the Line Status  
                             field are: 
                                up(1): 
                                   The line is able to both send and receive. When the line  
                                   status changes to Up from either the down or test states, 
                                   a new port session number MUST be generated. 
                                down(2): 
                                   The line is unable either to send or receive or both. 
                                Test(3): 
                                   The port or line is in a test mode, for example, power-on 
                                   test." 
                          ::= { gsmpInterfaceConfEntry 6 } 
                     
                       gsmpPriorties OBJECT-TYPE 
                          SYNTAX         Integer32 
                          MAX-ACCESS     read-write 
                          STATUS         current 
                          DESCRIPTION 
                             "This object represents the number of different priority levels 
                             that this output port can assign to connections. Zero is  
                             invalid in this field." 
                          ::= { gsmpInterfaceConfEntry 7 } 
                        
                       gsmpPhysicalSlotNumber OBJECT-TYPE 
                          SYNTAX         Integer32 
                          MAX-ACCESS     read-only 
                          STATUS         current 
                          DESCRIPTION 
                             "The physical location of the slot in which the port is  
                             located." 
                          ::= { gsmpInterfaceConfEntry 8 } 
                        
                       gsmpPhysicalPortNumber OBJECT-TYPE 
                          SYNTAX         Integer32 
                          MAX-ACCESS     read-only 
                          STATUS         current 
                          DESCRIPTION 
                             "The physical location of the port within the slot in which the 
                             port is located. The Physical Port Number is not used by the  
                             GSMP protocol. It is provided to assist network management 
                             in functions such as logging, port naming, and graphical  
                             representation." 
                          ::= { gsmpInterfaceConfEntry 9 } 
                                      draft-cha-gsmp-service-mib-00.txt      October 2002 
                     
                     
                       gsmpMinLabel OBJECT-TYPE 
                          SYNTAX         Label 
                          MAX-ACCESS     read-write 
                          STATUS         current 
                          DESCRIPTION 
                             "The minimum label value in the range." 
                          ::= { gsmpInterfaceConfEntry 10 } 
                        
                       gsmpMaxLabel OBJECT-TYPE 
                          SYNTAX         Label 
                          MAX-ACCESS     read-write 
                          STATUS         current 
                          DESCRIPTION 
                             "The maximum label value in the range." 
                          ::= { gsmpInterfaceConfEntry 11 } 
                        
                       gsmpRemainingLabels OBJECT-TYPE 
                          SYNTAX         Unsigned32 
                        
                          MAX-ACCESS     read-only 
                          STATUS         current 
                          DESCRIPTION 
                             "The maximum number of remaining labels that could be requested 
                             for allocation on the specified port." 
                          ::= { gsmpInterfaceConfEntry 12 } 
                        
                       gsmpConnectionReplace OBJECT-TYPE 
                          SYNTAX         TruthValue 
                          MAX-ACCESS     read-write 
                          STATUS         current 
                          DESCRIPTION 
                             "It indicates that a switch controller requests the switch port  
                             to support the mechanism of connection replacement." 
                          DEFVAL { false } 
                          ::= { gsmpInterfaceConfEntry 13 } 
                        
                       gsmpDuration OBJECT-TYPE 
                          SYNTAX         Integer32 
                          UNITS          "second" 
                          MAX-ACCESS     read-write 
                          STATUS         current 
                          DESCRIPTION 
                             "It is the length of time in seconds, that any of the loopback 
                             states remain in operation." 
                          ::= { gsmpInterfaceConfEntry 14 } 
                        
                       gsmpEventSequenceNumber OBJECT-TYPE 
                          SYNTAX         Integer32 
                                      draft-cha-gsmp-service-mib-00.txt      October 2002 
                     
                     
                          MAX-ACCESS     read-only 
                          STATUS         current 
                          DESCRIPTION 
                             "This object represents the current value of the event sequence  
                             number of the switch port. This number is set to zero when the  
                             port is initialed." 
                          ::= { gsmpInterfaceConfEntry 15 } 
                        
                       gsmpEventFlags OBJECT-TYPE 
                          SYNTAX         BITS  { 
                                                  portUp(0), 
                                                  portDown(1), 
                                                  invalidLabel(2), 
                                                  newPort(3), 
                                                  deadPort(4), 
                                                  adjacencyEvent(5), 
                                         } 
                          MAX-ACCESS     read-write 
                          STATUS         current 
                          DESCRIPTION 
                             "It is used to reset the event flags." 
                          ::= { gsmpInterfaceConfEntry 16 } 
                        
                       gsmpFlowControlFlags OBJECT-TYPE 
                          SYNTAX         BITS  { 
                                                  portUp(0), 
                                                  portDown(1), 
                                                  invalidLabel(2), 
                                                  newPort(3), 
                                                  deadPort(4), 
                                                  adjacencyEvent(5), 
                                         }         
                          MAX-ACCESS     read-write 
                          STATUS         current 
                          DESCRIPTION 
                             "It is used to indicate whether the flow control mechanism  
                             is turned on or not." 
                          ::= { gsmpInterfaceConfEntry 17 } 
                        
                       gsmpTransmitDataRate OBJECT-TYPE 
                          SYNTAX         Unsigned32 
                          MAX-ACCESS     read-write 
                          STATUS         current 
                          DESCRIPTION 
                             "It is used to set the output data rate of the output port. 
                                cells/s          for PortType = ATM 
                                bytes/s          for PortType = FR 
                                bytes/s          for PortType = MPLS" 
                                      draft-cha-gsmp-service-mib-00.txt      October 2002 
                     
                     
                          ::= { gsmpInterfaceConfEntry 18 } 
                        
                       gsmpReceiveDataRate OBJECT-TYPE 
                          SYNTAX         Unsigned32 
                          MAX-ACCESS     read-write 
                          STATUS         current 
                          DESCRIPTION 
                             "The maximum rate of data that may arrive at the input port. 
                                cells/s for PortType = ATM 
                                bytes/s for PortType = FR 
                                bytes/s for PortType = MPLS" 
                          ::= { gsmpInterfaceConfEntry 19 } 
                        
                       -- End of gsmpIntferfaceConfTable 
                        
                       -- Service Table 
                       gsmpServiceTable OBJECT-TYPE 
                          SYNTAX         SEQUENCE OF GsmpServiceEntry 
                          MAX-ACCESS     not-accessible 
                          STATUS         current 
                          DESCRIPTION 
                             "This table represents the list of services and their  
                             associated parameters, which are supported by the switch." 
                          ::= { gsmpServiceObjects 3 } 
                        
                       gsmpServiceEntry OBJECT-TYPE 
                          SYNTAX         GsmpServiceEntry 
                          MAX-ACCESS     not-accessible 
                          STATUS         current 
                          DESCRIPTION 
                             "The entry of this table represents the list of services  
                             and their associated parameters, which are supported by the  
                             switch." 
                          INDEX { gsmpServiceId, gsmpCapSetId } 
                          ::= { gsmpServiceTable 1 } 
                        
                       GsmpServiceEntry ::= SEQUENCE { 
                          gsmpServiceId           Integer32, 
                          gsmpCapSetId            Integer32, 
                          gsmpTrafficControls     BITS, 
                          gsmpCellLossRatio       Integer32, 
                          gsmpCellTransferDelay   Unsigned32, 
                          gsmpCellDelayVariation  Unsigned32, 
                          gsmpFrequency           Unsigned32, 
                       } 
                        
                       gsmpServiceId OBJECT-TYPE 
                          SYNTAX         Integer32 
                                      draft-cha-gsmp-service-mib-00.txt      October 2002 
                     
                     
                          MAX-ACCESS     not-accessible 
                          STATUS         current 
                          DESCRIPTION 
                             "This object represents the identifier of the service supported  
                             by the switch." 
                          ::= { gsmpServiceEntry 1 } 
                        
                       gsmpCapSetId OBJECT-TYPE 
                          SYNTAX         Integer32 
                          MAX-ACCESS     not-accessible 
                          STATUS         current 
                          DESCRIPTION 
                             "A capability set contains a set of parameters that describe  
                             the QoS parameter values and traffic controls that apply to an  
                             instance of the service." 
                          ::= { gsmpServiceEntry 2 } 
                        
                       gsmpTrafficControls OBJECT-TYPE 
                          SYNTAX         BITS { 
                                                  usageParameterControl(0), 
                                                  packetDiscard(1), 
                                                  ingressShaping(2), 
                                                  egressShaping(3), 
                                                  egressTrafficShaping(4), 
                                                  vcMerge(5), 
                                         } 
                          MAX-ACCESS     read-only 
                          STATUS         current 
                          DESCRIPTION 
                             "Identifies the availability of traffic controls within the  
                             capability set. 
                                U: Usage Parameter Control 
                                D: Packet Discard 
                                I: Ingress Shaping 
                                E: Egress Shaping, Peak Rate 
                                S: Egress Traffic Shaping, Sustainable Rate 
                                V: VC Merge" 
                          ::= { gsmpServiceEntry 3 } 
                        
                       gsmpCellLossRatio OBJECT-TYPE 
                          SYNTAX         Integer32 
                          MAX-ACCESS     read-only 
                          STATUS         current 
                          DESCRIPTION 
                             "It indicates the cell loss ratio parameter guaranteed by  
                             the switch for the specified service." 
                          ::= { gsmpServiceEntry 4 } 
                                      draft-cha-gsmp-service-mib-00.txt      October 2002 
                     
                     
                       gsmpCellTransferDelay OBJECT-TYPE 
                          SYNTAX         Unsigned32 
                          UNITS          "micro-second" 
                          MAX-ACCESS     read-only 
                          STATUS         current 
                          DESCRIPTION 
                             "The value of this object is expressed in units of  
                             microseconds." 
                          ::= { gsmpServiceEntry 5 } 
                        
                       gsmpCellDelayVariation OBJECT-TYPE 
                          SYNTAX         Unsigned32 
                          UNITS          "micro-second" 
                          MAX-ACCESS     read-only 
                          STATUS         current 
                          DESCRIPTION 
                             "It represents the peak-to-peak cell delay variation. 
                             The CDV value is expressed in units of microseconds." 
                          ::= { gsmpServiceEntry 6 } 
                        
                       gsmpFrequency OBJECT-TYPE 
                          SYNTAX         Unsigned32 
                          MAX-ACCESS     read-only 
                          STATUS         current 
                          DESCRIPTION 
                             "Frequency applies to the MPLS CR-LDP service. Valid values of  
                             this object are: 
                                0 - Very frequent 
                                1 - Frequent 
                                2 - Unspecified" 
                          ::= { gsmpServiceEntry 7 } 
                        
                       -- End of gsmpServiceTable 
                        
                       -- Port Service Map Table 
                       gsmpPortServiceMapTable OBJECT-TYPE 
                          SYNTAX         SEQUENCE OF GsmpPortServiceMapEntry 
                          MAX-ACCESS     not-accessible 
                          STATUS         current 
                          DESCRIPTION 
                             "This table represents the service lists, which are supported  
                             by the specific port." 
                          ::= { gsmpServiceObjects 4 } 
                        
                       gsmpPortServiceMapEntry OBJECT-TYPE 
                          SYNTAX         GsmpPortServiceMapEntry 
                          MAX-ACCESS     not-accessible 
                          STATUS         current 
                                      draft-cha-gsmp-service-mib-00.txt      October 2002 
                     
                     
                          DESCRIPTION 
                             "The entry of this table represents the service lists, which  
                             are supported by the specific port." 
                          INDEX { gsmpInterfaceConfIndex } 
                          ::= { gsmpPortServiceMapTable 1 } 
                        
                       GsmpPortServiceMapEntry ::= SEQUENCE { 
                          gsmpMapServiceId     Integer32, 
                          gsmpMapCapSetId      Integer32 
                       } 
                        
                       gsmpMapServiceId OBJECT-TYPE 
                          SYNTAX         Integer32 
                          MAX-ACCESS     read-only 
                          STATUS         current 
                          DESCRIPTION 
                             "This object represents the identifier of the service supported  
                             by the switch." 
                          ::= { gsmpPortServiceMapEntry 1 } 
                        
                       gsmpMapCapSetId OBJECT-TYPE 
                          SYNTAX         Integer32 
                          MAX-ACCESS     read-only 
                          STATUS         current 
                          DESCRIPTION 
                             "A capability set contains a set of parameters that describe  
                             the QoS parameter values and traffic controls that apply to an  
                             instance of the Service." 
                          ::= { gsmpPortServiceMapEntry 2 } 
                        
                       -- End of gsmpPortServiceMapTable 
                        
                       -- Traffic Parameter Table 
                       gsmpTrafficParamIndexNext OBJECT-TYPE 
                          SYNTAX         Unsigned32 (0..4294967295) 
                          MAX-ACCESS     read-only 
                          STATUS         current 
                          DESCRIPTION 
                             "This object contains an appropriate value which will be used  
                             for gsmpTrafficParamIndex." 
                          ::= { gsmpServiceObjects 5 } 
                        
                       gsmpTrafficParamTable OBJECT-TYPE 
                          SYNTAX         SEQUENCE OF GsmpTrafficParamEntry 
                          MAX-ACCESS     not-accessible 
                          STATUS         current 
                          DESCRIPTION 
                             "This table contains objects, which specify the traffic  
                                      draft-cha-gsmp-service-mib-00.txt      October 2002 
                     
                     
                             parameters of in-segments and out-segments." 
                          ::= { gsmpServiceObjects 6 } 
                        
                       gsmpTrafficParamEntry OBJECT-TYPE 
                          SYNTAX         GsmpTrafficParamEntry 
                          MAX-ACCESS     not-accessible 
                          STATUS         current 
                          DESCRIPTION 
                             "An entry in this table represents the gsmpTrafficParam objects  
                             for one or more in or out segments." 
                          INDEX { gsmpTrafficParamIndex } 
                          ::= { gsmpTrafficParamTable 1 } 
                        
                       GsmpTrafficParamEntry ::= SEQUENCE { 
                          gsmpTrafficParamIndex         Unsigned32, 
                          gsmpTrafficParamMaxRate       Integer32, 
                          gsmpTrafficParamMeanRate      Integer32, 
                          gsmpTrafficParamMaxBurstSize  Unsigned32, 
                          gsmpTrafficControlsFlags      BITS, 
                          gsmpTrafficParamRowStatus     RowStatus, 
                          gsmpTrafficParamStorageType   StorageType 
                       } 
                     
                       gsmpTrafficParamIndex OBJECT-TYPE 
                          SYNTAX        Unsigned32 (1..2147483647) 
                        
                          MAX-ACCESS    not-accessible 
                          STATUS        current 
                          DESCRIPTION 
                             "Uniquely identifies this row of this table. Note that zero  
                             represents an invalid index." 
                          ::= { gsmpTrafficParamEntry 1 } 
                        
                       gsmpTrafficParamMaxRate OBJECT-TYPE 
                          SYNTAX         Integer32 (1..2147483647) 
                          UNITS          "kilobits per second" 
                          MAX-ACCESS     read-create 
                          STATUS         current 
                          DESCRIPTION 
                             "Maximum rate in kilobits/second." 
                          ::= { gsmpTrafficParamEntry 2 } 
                        
                       gsmpTrafficParamMeanRate OBJECT-TYPE 
                          SYNTAX         Integer32 (1..2147483647) 
                          UNITS          "kilobits per second" 
                          MAX-ACCESS     read-create 
                          STATUS         current 
                          DESCRIPTION 
                                      draft-cha-gsmp-service-mib-00.txt      October 2002 
                     
                     
                             "Mean rate in kilobits/second." 
                          ::= { gsmpTrafficParamEntry 3 } 
                        
                       gsmpTrafficParamMaxBurstSize OBJECT-TYPE 
                          SYNTAX         Unsigned32 (1..4294967295) 
                          UNITS          "bytes" 
                          MAX-ACCESS     read-create 
                          STATUS         current 
                          DESCRIPTION 
                             "Maximum burst size in bytes." 
                          ::= { gsmpTrafficParamEntry 4 } 
                        
                       gsmpTrafficControlsFlags OBJECT-TYPE 
                          SYNTAX         BITS { 
                                                  usageParameterControl(0), 
                                                  packetDiscard(1), 
                                                  ingressShaping(2), 
                                                  egressShaping(3), 
                                                  egressTrafficShaping(4), 
                                                  vcMerge(5), 
                                                  port(6) 
                                         } 
                          MAX-ACCESS     read-create                                                      
                          STATUS         current 
                          DESCRIPTION 
                             "This object is used to indicate that specific traffic controls  
                             are requested for the requested connection. 
                                0 1 2 3 4 5 6 7 
                                +-+-+-+-+-+-+-+-+ 
                                |U|D|I|E|S|V|P|x| 
                                +-+-+-+-+-+-+-+-+ 
                                U: Usage Parameter Control 
                                D: Packet Discard 
                                I: Ingress Shaping 
                                E: Egress Shaping, Peak Rate 
                                S: Egress Traffic Shaping, Sustainable Rate 
                                V: VC Merge 
                                P: Port 
                                x: Reserved" 
                          ::= { gsmpTrafficParamEntry 5 } 
                       gsmpTrafficParamRowStatus OBJECT-TYPE 
                          SYNTAX         RowStatus 
                          MAX-ACCESS     read-create 
                          STATUS         current 
                          DESCRIPTION 
                             "For creating, modifying, and deleting this row." 
                          ::= { gsmpTrafficParamEntry 6 } 
                                      draft-cha-gsmp-service-mib-00.txt      October 2002 
                     
                     
                       gsmpTrafficParamStorageType OBJECT-TYPE 
                          SYNTAX         StorageType 
                          MAX-ACCESS     read-create 
                          STATUS         current 
                          DESCRIPTION 
                             "Defines the storage type support provided for this object by  
                             the agent." 
                          ::= { gsmpTrafficParamEntry 7 } 
                        
                       --End of Traffic Parameter Table 
                        
                       -- In-Segment Table  
                       gsmpInSegmentTable OBJECT-TYPE 
                          SYNTAX         SEQUENCE OF GsmpInSegmentEntry 
                          MAX-ACCESS     not-accessible 
                          STATUS         current 
                          DESCRIPTION 
                             "This table contains a description of the incoming GSMP  
                             segments and their associated parameters." 
                          ::= { gsmpServiceObjects 7 } 
                        
                       gsmpInSegmentEntry OBJECT-TYPE 
                          SYNTAX         GsmpInSegmentEntry 
                          MAX-ACCESS     not-accessible 
                          STATUS         current 
                          DESCRIPTION 
                             "An entry in this table represents one incoming GSMP segment." 
                          INDEX { gsmpInSegmentIfIndex, gsmpInSegmentLabel } 
                          ::=  { gsmpInSegmentTable 1} 
                        
                       GsmpInSegmentEntry ::= SEQUENCE { 
                          gsmpInSegmentIfIndex          InterfaceIndexOrZero, 
                          gsmpInSegmentLabel            Label, 
                          gsmpInSegmentXCIndex          Unsigned32, 
                          gsmpInSegmentOwner            Owner, 
                          gsmpInSegmentTrafficParamPtr  RowPointer, 
                          gsmpInQoSModelSelector        INTEGER, 
                          gsmpInServiceSelector         Integer32, 
                          gsmpInAdaptationMethodType    INTEGER, 
                          gsmpInSegmentRowStatus        RowStatus, 
                          gsmpInSegmentStorageType      StorageType 
                       } 
                       gsmpInSegmentIfIndex OBJECT-TYPE 
                          SYNTAX         InterfaceIndexOrZero 
                          MAX-ACCESS     not-accessible 
                          STATUS         current 
                          DESCRIPTION 
                             "This is a unique index for an entry in the gsmpInSegmentTable. 
                                      draft-cha-gsmp-service-mib-00.txt      October 2002 
                     
                     
                             This value represents the interface index for the incoming GSMP 
                             interface. A value of zero represents an incoming label from  
                             the per-platform label space." 
                          ::= { gsmpInSegmentEntry 1 } 
                        
                       gsmpInSegmentLabel OBJECT-TYPE 
                          SYNTAX         Label 
                          MAX-ACCESS     not-accessible 
                          STATUS         current 
                          DESCRIPTION 
                             "The incoming label for this segment." 
                          ::= { gsmpInSegmentEntry 2 } 
                        
                       gsmpInSegmentXCIndex OBJECT-TYPE 
                          SYNTAX         Unsigned32 (0..4294967295) 
                          MAX-ACCESS     read-only 
                          STATUS         current 
                          DESCRIPTION 
                             "Index into gsmpXCTable which identifies which cross-connect  
                             entry this segment is part of.  A value of zero indicates that  
                             this entry is not referred to by any cross-connect entry. When  
                             a cross-connect entry is created which this in-segment is a  
                             part of, this object is automatically updated to reflect the 
                             value of gsmpXCIndex of that cross-connect entry." 
                          ::= { gsmpInSegmentEntry 3 } 
                        
                       gsmpInSegmentOwner OBJECT-TYPE 
                          SYNTAX         Owner 
                          MAX-ACCESS     read-only 
                          STATUS         current 
                          DESCRIPTION 
                             "This object denotes the entity that created and is responsible  
                             for managing this segment." 
                          ::= { gsmpInSegmentEntry 4 } 
                        
                       gsmpInSegmentTrafficParamPtr OBJECT-TYPE 
                          SYNTAX         RowPointer 
                          MAX-ACCESS     read-create 
                          STATUS         current 
                          DESCRIPTION 
                             "This variable represents a pointer to the traffic parameter  
                             specification for this in-segment.  This value may point at an  
                             entry in the gsmpTrafficParamTable to indicate which  
                             gsmpTrafficParamEntry is to be assigned to this segment. 
                             This value may optionally point at an externally defined  
                             traffic parameter specification table." 
                          DEFVAL { zeroDotZero } 
                          ::= { gsmpInSegmentEntry 5 } 
                                      draft-cha-gsmp-service-mib-00.txt      October 2002 
                     
                     
                     
                       gsmpInQoSModelSelector OBJECT-TYPE 
                          SYNTAX         INTEGER  { 
                                                     simplePriorityModel(1), 
                                                     serviceProfileModel(2), 
                                                     serviceModel(3), 
                                                     armModel(4) 
                                         } 
                          MAX-ACCESS     read-create 
                          STATUS         current 
                          DESCRIPTION 
                             "simplePriorityModel(1):  
                                The input service selector indicates a simple priority. 
                             serviceProfileModel(2):  
                                The input service selector is an opaque service profile  
                                identifier. Service profiles can be used to indicate pre- 
                                defined differentiated service per hop behaviors. 
                             serviceModel(3):  
                                The input service selector corresponds to a service  
                                specification. When the value of this object is  
                                serviceModel(3), then a traffic parameters block is appended 
                                to this entry. 
                             armModel(4):  
                                The input service selector corresponds to an ARM service  
                                specification. ARM model is defined in qGSMP specification." 
                          ::= { gsmpInSegmentEntry 6 } 
                        
                       gsmpInServiceSelector OBJECT-TYPE 
                          SYNTAX         Integer32 
                          MAX-ACCESS     read-create 
                          STATUS         current 
                          DESCRIPTION 
                             "This object identifies details of the service specification  
                             being used for connection. The interpretation depends upon the  
                             gsmpInQoSModelSelector object." 
                          ::= { gsmpInSegmentEntry 7 } 
                        
                       gsmpInAdaptationMethodType OBJECT-TYPE 
                          SYNTAX         INTEGER { 
                                                     ppp(1), 
                                                     frf5(2), 
                                                     frf8(3) 
                                         }  
                          MAX-ACCESS     read-create 
                          STATUS         current 
                          DESCRIPTION 
                             "The adaptation method is used to define the adaptation framing 
                             that may be in use when moving traffic from one port type to 
                                      draft-cha-gsmp-service-mib-00.txt      October 2002 
                     
                     
                             another port type; e.g., from a frame relay port to an ATM  
                             port." 
                          ::= { gsmpInSegmentEntry 8 } 
                        
                       gsmpInSegmentRowStatus OBJECT-TYPE 
                          SYNTAX         RowStatus 
                          MAX-ACCESS     read-create 
                          STATUS         current 
                          DESCRIPTION 
                             "This variable is used to create, modify, and/or delete a row  
                                                           in this table." 
                          ::= { gsmpInSegmentEntry 9 } 
                           
                       gsmpInSegmentStorageType OBJECT-TYPE 
                          SYNTAX         StorageType 
                          MAX-ACCESS     read-create 
                          STATUS         current 
                          DESCRIPTION 
                             "This variable indicates the storage type for this object." 
                          ::= { gsmpInSegmentEntry 10 } 
                        
                       -- END of gsmpInSegmentTable 
                        
                       -- GSMP Out-Segment Table 
                       gsmpOutSegmentTable  OBJECT-TYPE 
                          SYNTAX         SEQUENCE OF GsmpOutSegmentEntry 
                          MAX-ACCESS     not-accessible 
                          STATUS         current 
                          DESCRIPTION  
                             "This table contains a description of the outgoing GSMP  
                             segments to a connection and their associated parameters." 
                          ::= { gsmpServiceObjects 8 } 
                           
                       gsmpOutSegmentEntry  OBJECT-TYPE 
                          SYNTAX         GsmpOutSegmentEntry 
                          MAX-ACCESS     not-accessible 
                          STATUS         current 
                          DESCRIPTION 
                             "An entry in this table represents one outgoing GSMP segment." 
                          INDEX {  gsmpOutSegmentIfIndex, gsmpOutSegmentLabel } 
                          ::=  { gsmpOutSegmentTable 1} 
                        
                       GsmpOutSegmentEntry ::= SEQUENCE { 
                          gsmpOutSegmentIfIndex         InterfaceIndexOrZero, 
                          gsmpOutSegmentLabel           Label, 
                          gsmpOutSegmentXCIndex         Unsigned32, 
                          gsmpOutSegmentOwner           Owner, 
                          gsmpOutSegmentTrafficParamPtr RowPointer, 
                                      draft-cha-gsmp-service-mib-00.txt      October 2002 
                     
                     
                          gsmpOutQoSModelSelector       INTEGER, 
                          gsmpOutServiceSelector        Integer32, 
                          gsmpOutAdaptationMethodType   INTEGER, 
                          gsmpOutSegmentRowStatus       RowStatus, 
                          gsmpOutSegmentStorageType     StorageType 
                       } 
                        
                       gsmpOutSegmentIfIndex OBJECT-TYPE 
                          SYNTAX         InterfaceIndex 
                          MAX-ACCESS     read-create 
                          STATUS         current 
                          DESCRIPTION 
                             "This is a unique index for an entry in the  
                             gsnmpOutSegmentTable. This value represents the interface index  
                             for the outgoing GSMP interface. A value of zero represents an  
                             outgoing label from  the per-platform label space." 
                          ::= { gsmpOutSegmentEntry 1 } 
                        
                       gsmpOutSegmentLabel OBJECT-TYPE 
                          SYNTAX         Label 
                          MAX-ACCESS     read-create 
                          STATUS         current 
                          DESCRIPTION 
                             "The outgoing label for this segment." 
                          ::= { gsmpOutSegmentEntry 2 } 
                        
                       gsmpOutSegmentXCIndex OBJECT-TYPE 
                          SYNTAX         Unsigned32 (0..4294967295) 
                          MAX-ACCESS     read-only 
                          STATUS         current 
                          DESCRIPTION 
                             "Index into gsmpXCTable which identifies which cross-connect  
                             entry this segment is part of.  A value of zero indicates that  
                             this entry is not referred to by any cross-connect entry. When  
                             a cross-connect entry is created which this out-segment is a  
                             part of, this object is automatically updated to reflect the 
                             value of gsmpXCIndex of that cross-connect entry." 
                          ::= { gsmpOutSegmentEntry 3 } 
                        
                       gsmpOutSegmentOwner OBJECT-TYPE 
                          SYNTAX         Owner 
                          MAX-ACCESS     read-only 
                          STATUS         current 
                          DESCRIPTION 
                             "This object denotes the entity that created and is responsible  
                             for managing this segment." 
                          ::= { gsmpOutSegmentEntry 4 } 
                                      draft-cha-gsmp-service-mib-00.txt      October 2002 
                     
                     
                       gsmpOutSegmentTrafficParamPtr OBJECT-TYPE 
                          SYNTAX         RowPointer 
                          MAX-ACCESS     read-create 
                          STATUS         current 
                          DESCRIPTION 
                             "This variable represents a pointer to the traffic parameter  
                             specification for this out-segment. This value may point at an  
                             entry in the gsmpTrafficParamTable to indicate which  
                             gsmpTrafficParamEntry is to be assigned to this segment. 
                             This value may optionally point at an externally defined  
                             traffic parameter specification table." 
                          DEFVAL { zeroDotZero } 
                          ::= { gsmpOutSegmentEntry 5 } 
                        
                       gsmpOutQoSModelSelector OBJECT-TYPE 
                          SYNTAX         INTEGER  { 
                                                     simplePriorityModel(1), 
                                                     serviceProfileModel(2), 
                                                     serviceModel(3), 
                                                     armModel(4) 
                                         } 
                          MAX-ACCESS     read-create 
                          STATUS         current 
                          DESCRIPTION 
                             "simplePriorityModel(1):  
                                The output service selector indicates a simple priority. 
                             serviceProfileModel(2):  
                                The output service selector is an opaque service profile  
                                identifier. Service profiles can be used to indicate pre- 
                                defined differentiated service per hop behaviors. 
                             serviceModel(3):  
                                The output service selector corresponds to a service  
                                specification. When the value of this object is  
                                serviceModel(3), then a traffic parameters block is appended 
                                to this entry. 
                             armModel(4):  
                                The output service selector corresponds to an ARM service  
                                specification. ARM model is defined in qGSMP specification." 
                          ::= { gsmpOutSegmentEntry 6 } 
                        
                       gsmpOutAdaptationMethodType OBJECT-TYPE 
                          SYNTAX         INTEGER { 
                                                     ppp(1), 
                                                     frf5(2), 
                                                     frf8(3) 
                                         }  
                          MAX-ACCESS     read-create 
                          STATUS         current 
                                      draft-cha-gsmp-service-mib-00.txt      October 2002 
                     
                     
                          DESCRIPTION 
                             "The adaptation method is used to define the adaptation framing 
                             that may be in use when moving traffic from one port type to 
                             another port type; e.g., from a frame relay port to an ATM  
                             port." 
                          ::= { gsmpOutSegmentEntry 8 } 
                        
                       gsmpOutSegmentRowStatus OBJECT-TYPE 
                          SYNTAX         RowStatus 
                          MAX-ACCESS     read-create 
                          STATUS         current 
                          DESCRIPTION 
                             "This variable is used to create, modify, and/or delete a row  
                                                           in this table." 
                          ::= { gsmpOutSegmentEntry 9 } 
                           
                       gsmpOutSegmentStorageType OBJECT-TYPE 
                          SYNTAX         StorageType 
                          MAX-ACCESS     read-create 
                          STATUS         current 
                          DESCRIPTION 
                             "This variable indicates the storage type for this object." 
                          ::= { gsmpOutSegmentEntry 10 } 
                        
                       -- END of gsmpOutSegmentTable 
                        
                       -- Cross-Connect Table 
                       gsmpXCIndexNext OBJECT-TYPE 
                          SYNTAX         Unsigned32 (0..4294967295) 
                          MAX-ACCESS     read-only 
                          STATUS         current 
                          DESCRIPTION 
                             "This object contains an appropriate value to be used for  
                             gsmpXCIndex when creating entries in the gsmpXCTable." 
                          ::= { gsmpServiceObjects 9 } 
                        
                       gsmpXCTable OBJECT-TYPE 
                          SYNTAX         SEQUENCE OF GsmpXCEntry 
                          MAX-ACCESS     not-accessible 
                          STATUS         current 
                          DESCRIPTION 
                             "A connection is modeled as a cross-connect consisting of one  
                             or more incoming segments(in-segments) and/or one or more  
                             outgoing segments(out-segments) at a switch. The association or  
                             interconnection of the in-segments and out-segments is  
                             accomplished by using the gsmpXCTable." 
                          ::= { gsmpServiceObjects 10 } 
                                      draft-cha-gsmp-service-mib-00.txt      October 2002 
                     
                     
                       gsmpXCEntry    OBJECT-TYPE 
                          SYNTAX      GsmpXCEntry 
                          MAX-ACCESS  not-accessible 
                          STATUS      current 
                          DESCRIPTION 
                             "A row in this table represents one cross-connect entry." 
                          INDEX {  
                                   gsmpXCIndex, 
                                   gsmpXCInSegmentIfIndex, 
                                   gsmpXCInSegmentLabel, 
                                   gsmpXCOutSegmentIfIndex, 
                                   gsmpXCOutSegmentLabel 
                          } 
                          ::= { gsmpXCTable 1 } 
                        
                       GsmpXCEntry ::= SEQUENCE { 
                          gsmpXCIndex             Unsigned32, 
                          gsmpXCInSegmentIfIndex  InterfaceIndexOrZero, 
                          gsmpXCInSegmentLabel    Label, 
                          gsmpXCOutSegmentIfIndex InterfaceIndexOrZero, 
                          gsmpXCOutSegmentLabel   Label, 
                          gsmpXCIsPersistent      TruthValue, 
                          gsmpXCOwner             Owner, 
                          gsmpConnectType         INTEGER, 
                          gsmpBiDirection         TruthValue, 
                          gsmpXCAdminStatus       INTEGER, 
                          gsmpXCOperStatus        INTEGER, 
                          gsmpXCRowStatus         RowStatus, 
                          gsmpXCStorageType       StorageType, 
                       } 
                        
                       gsmpXCIndex OBJECT-TYPE 
                          SYNTAX         Unsigned32 (1..2147483647) 
                          MAX-ACCESS     not-accessible 
                          STATUS         current 
                          DESCRIPTION 
                             "Primary index for the conceptual row identifying cross-connect  
                             segments." 
                          ::= { gsmpXCEntry 1 } 
                        
                       gsmpXCInSegmentIfIndex OBJECT-TYPE 
                          SYNTAX         InterfaceIndexOrZero 
                          MAX-ACCESS     not-accessible 
                          STATUS         current 
                          DESCRIPTION 
                             "Interface index of the in-segment."  
                          ::= { gsmpXCEntry 2 } 
                                      draft-cha-gsmp-service-mib-00.txt      October 2002 
                     
                     
                       gsmpXCInSegmentLabel OBJECT-TYPE 
                          SYNTAX         Label 
                          MAX-ACCESS     not-accessible 
                          STATUS         current 
                          DESCRIPTION 
                             ôIncoming label." 
                          ::= { gsmpXCEntry 3 } 
                        
                       gsmpXCOutSegmentIfIndex OBJECT-TYPE 
                          SYNTAX         InterfaceIndexOrZero 
                          MAX-ACCESS     not-accessible 
                          STATUS         current 
                          DESCRIPTION 
                             "Interface index of the out-segment."  
                          ::= { gsmpXCEntry 4 } 
                        
                       gsmpXCOutSegmentLabel OBJECT-TYPE 
                          SYNTAX         Label 
                          MAX-ACCESS     not-accessible 
                          STATUS         current 
                          DESCRIPTION 
                             "Outgoing label." 
                          ::= { gsmpXCEntry 5 } 
                        
                       gsmpXCIsPersistent OBJECT-TYPE 
                          SYNTAX         TruthValue 
                          MAX-ACCESS     read-create 
                          STATUS         current 
                          DESCRIPTION 
                             "This object denotes whether or not this cross-connect entry  
                             and associated in- and out-segments should be restored  
                             automatically after failures. This value MUST be set to false  
                             in cases where this cross-connect entry was created by a  
                             signaling protocol." 
                          DEFVAL { false } 
                          ::= { gsmpXCEntry 6 } 
                        
                       gsmpXCOwner OBJECT-TYPE 
                          SYNTAX         Owner 
                          MAX-ACCESS     read-only 
                          STATUS         current 
                          DESCRIPTION 
                             "It denotes the entity that created and is responsible for  
                             managing this cross-connect." 
                          ::= { gsmpXCEntry 7 } 
                        
                       gsmpXCAdminStatus OBJECT-TYPE 
                          SYNTAX         INTEGER { 
                                      draft-cha-gsmp-service-mib-00.txt      October 2002 
                     
                     
                                            up(1), 
                                            down(2), 
                                            testing(3) 
                                         } 
                          MAX-ACCESS     read-create 
                          STATUS         current 
                          DESCRIPTION 
                             "The desired operational status of this segment. 
                                up(1) = ready to pass packets 
                                testing(3) = in some test mode" 
                          ::= { gsmpXCEntry  8 } 
                        
                       gsmpXCOperStatus OBJECT-TYPE 
                          SYNTAX         INTEGER { 
                                            up(1), 
                                            down(2), 
                                            testing(3), 
                                            unknown(4), 
                                            dormant(5), 
                                            notPresent(6), 
                                            lowerLayerDown(7) 
                                         } 
                          MAX-ACCESS     read-only 
                          STATUS         current 
                          DESCRIPTION 
                             "The actual operational status of this cross-connect. 
                                up(1) = ready to pass packets 
                                testing(3) = in some test mode 
                                unknown(4) = status cannot be determined for some reason 
                                notPresent(6) = some component is missing 
                                lowerLayerDown(7) = down due to the state of lower layer  
                                interfaces" 
                          ::= { gsmpXCEntry 9 } 
                        
                       gsmpConnectType OBJECT-TYPE 
                          SYNTAX         INTEGER  { 
                                            point-to-point(1), 
                                            point-to-multipoint(2), 
                                            multipoint-to-point(3), 
                                            multipoint-to-multipoint(4) 
                                         } 
                          MAX-ACCESS     read-create 
                          STATUS         current 
                          DESCRIPTION 
                             "This object is used to define connection types." 
                          ::= { gsmpXCEntry 10 } 
                        
                       gsmpBiDirection OBJECT-TYPE 
                                      draft-cha-gsmp-service-mib-00.txt      October 2002 
                     
                     
                          SYNTAX         TruthValue 
                          MAX-ACCESS     read-create 
                          STATUS         current 
                          DESCRIPTION 
                             "If this flag is true, then the connection should be  
                             established to be bi-direction." 
                          DEFVAL { false } 
                          ::= { gsmpXCEntry 11 } 
                        
                       gsmpXCRowStatus OBJECT-TYPE 
                          SYNTAX         RowStatus 
                          MAX-ACCESS     read-create 
                          STATUS         current 
                          DESCRIPTION 
                             "This variable is used to create, modify, and/or delete a row  
                                                           in this table." 
                          ::= { gsmpXCEntry 12 } 
                        
                       gsmpXCStorageType OBJECT-TYPE 
                          SYNTAX         StorageType 
                          MAX-ACCESS     read-only 
                          STATUS         current 
                          DESCRIPTION 
                             "This variable indicates the storage type for this object." 
                          ::= { gsmpXCEntry 13 } 
                        
                       -- End of gsmpXCTable 
                        
                        
                       -- Label stack table is the next step for study. 
                       -- The gsmpLabelStackTable specifies the label stack to be pushed 
                       -- onto a packet, beneath the top label. Entries on this table are  
                       -- referred to from gsmpXCTable. This table is not supported in this  
                       -- version. 
                        
                        
                       -- Interface Performance Table 
                       gsmpInterfacePerfTable OBJECT-TYPE 
                          SYNTAX         SEQUENCE OF GsmpInterfacePerfEntry 
                          MAX-ACCESS     not-accessible 
                          STATUS         current 
                          DESCRIPTION 
                             "This table contains objects to measure the performance of GSMP  
                             interfaces and is an AUGMENT to gsmpInterfaceConfTable." 
                          ::= { gsmpServiceObjects 11 } 
                        
                       gsmpInterfacePerfEntry OBJECT-TYPE 
                          SYNTAX         GsmpInterfacePerfEntry 
                                      draft-cha-gsmp-service-mib-00.txt      October 2002 
                     
                     
                          MAX-ACCESS     not-accessible 
                          STATUS         current 
                          DESCRIPTION 
                             "The Entry of this table contains objects to measure the  
                             performance of GSMP  interfaces and is an AUGMENT to  
                             gsmpInterfaceConfTable." 
                          AUGMENTS { gsmpInterfaceConfEntry } 
                          ::= { gsmpInterfacePerfTable 1 } 
                        
                       GsmpInterfacePerfEntry ::= SEQUENCE { 
                          gsmpInterfaceInFrameCount           Counter64, 
                          gsmpInterfaceInInvalidLabelCount    Counter64, 
                          gsmpInterfaceInFrameDiscardCount    Counter64, 
                          gsmpInterfaceOutFrameCount          Counter64, 
                          gsmpInterfaceOutFrameDiscardCount   Counter64, 
                       } 
                        
                       gsmpInterfaceInFrameCount OBJECT-TYPE 
                          SYNTAX         Counter64 
                          MAX-ACCESS     read-only 
                          STATUS         current 
                          DESCRIPTION 
                             "This object counts frames arriving at the input. It is  
                             relevant for label types = FR and MPLS." 
                          ::= { gsmpInterfacePerfEntry 1 } 
                        
                       gsmpInterfaceInInvalidLabelCount OBJECT-TYPE 
                          SYNTAX         Counter64 
                          MAX-ACCESS     read-only 
                          STATUS         current 
                          DESCRIPTION 
                             "This object counts frames discarded because their Label is  
                             invalid on arrival at an input port." 
                          ::= { gsmpInterfacePerfEntry 2 } 
                        
                       gsmpInterfaceInFrameDiscardCount OBJECT-TYPE 
                          SYNTAX         Counter64 
                          MAX-ACCESS     read-only 
                          STATUS         current 
                          DESCRIPTION 
                             "This object counts frames discarded due to congestion on an  
                             input port. It is relevant for label types = FR and MPLS." 
                          ::= { gsmpInterfacePerfEntry 3 } 
                        
                       gsmpInterfaceOutFrameCount OBJECT-TYPE 
                          SYNTAX         Counter64 
                          MAX-ACCESS     read-only 
                          STATUS         current 
                                      draft-cha-gsmp-service-mib-00.txt      October 2002 
                     
                     
                          DESCRIPTION 
                             "This object counts frames arriving at the output. It is  
                             relevant for label types = FR and MPLS." 
                          ::= { gsmpInterfacePerfEntry 4 } 
                        
                       gsmpInterfaceOutFrameDiscardCount OBJECT-TYPE 
                          SYNTAX         Counter64 
                          MAX-ACCESS     read-only 
                          STATUS         current 
                          DESCRIPTION 
                             "This object counts frames discarded due to congestion on an  
                             output port. It is relevant for label types = FR and MPLS." 
                          ::= { gsmpInterfacePerfEntry 5 } 
                        
                       -- End of gsmpInterfacePerfTable  
                        
                       -- Label Performance Table 
                       gsmpLabelPerfTable OBJECT-TYPE 
                          SYNTAX         SEQUENCE OF GsmpLabelPerfEntry 
                          MAX-ACCESS     not-accessible 
                          STATUS         current 
                          DESCRIPTION 
                             "This table has objects to measure the performance of  
                             connection." 
                          ::= { gsmpServiceObjects 12 } 
                        
                       gsmpLabelPerfEntry OBJECT-TYPE 
                          SYNTAX         GsmpLabelPerfEntry 
                          MAX-ACCESS     not-accessible 
                          STATUS         current 
                          DESCRIPTION 
                             "The Entry of this table contains objects to measure the  
                             performance of GSMP label." 
                          INDEX { gsmpInterfaceConfIndex, gsmpPerfLabel } 
                          ::= { gsmpLabelPerfTable 1 } 
                        
                       GsmpLabelPerfEntry ::= SEQUENCE { 
                          gsmpLabelIndex                   Label, 
                          gsmpLabelInFrameCount            Counter64, 
                          gsmpLabelInFrameDiscardCount     Counter64, 
                          gsmpLabelOutFrameCount           Counter64, 
                          gsmpLabelOutFrameDiscardCount    Counter64, 
                       } 
                        
                       gsmpLabelIndex OBJECT-TYPE 
                          SYNTAX         Label 
                          MAX-ACCESS     not-accessible 
                          STATUS         current 
                                      draft-cha-gsmp-service-mib-00.txt      October 2002 
                     
                     
                          DESCRIPTION 
                             "This is a unique index for an entry in the 
                             gsmpLabelPerfTable." 
                          ::= { gsmpLabelPerfEntry 1 } 
                        
                       gsmpLabelInFrameCount OBJECT-TYPE 
                          SYNTAX         Counter64 
                          MAX-ACCESS     read-only 
                          STATUS         current 
                          DESCRIPTION 
                             "This object counts frames arriving at the in-segment. It is  
                             relevant for label types = FR and MPLS." 
                          ::= { gsmpLabelPerfEntry 2 } 
                        
                       gsmpLabelInFrameDiscardCount OBJECT-TYPE 
                          SYNTAX         Counter64 
                          MAX-ACCESS     read-only 
                          STATUS         current 
                          DESCRIPTION 
                             "This object counts frames discarded due to congestion on the  
                             in-segment. It is relevant for label types = FR and MPLS." 
                          ::= { gsmpLabelPerfEntry 3 } 
                        
                       gsmpLabelOutFrameCount OBJECT-TYPE 
                          SYNTAX         Counter64 
                          MAX-ACCESS     read-only 
                          STATUS         current 
                          DESCRIPTION 
                             "This object counts frames departing from the out-segment. It  
                             is relevant for label types = FR and MPLS." 
                          ::= { gsmpLabelPerfEntry 4 } 
                        
                       gsmpLabelOutFrameDiscardCount OBJECT-TYPE 
                          SYNTAX         Counter64 
                          MAX-ACCESS     read-only 
                          STATUS         current 
                          DESCRIPTION 
                             "This object counts frames discarded due to congestion on the 
                             out-segment. It is relevant for label types = FR and MPLS." 
                          ::= { gsmpLabelPerfEntry 5 } 
                        
                       -- End of gsmpLabelPerfTable   
                        
                       -- Notifications will use notifications defined in GSMP-MIB[RFC3295]. 
                        
                       -- Module-Compliance is the next step for study. 
                        
                       END
