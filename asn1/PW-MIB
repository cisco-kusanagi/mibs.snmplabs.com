-- extracted from draft-ietf-pwe3-pw-mib-01.txt
-- at Fri May 14 06:21:09 2004

  PW-MIB DEFINITIONS ::= BEGIN 
   
  IMPORTS 
     MODULE-IDENTITY, OBJECT-TYPE, 
     experimental, Integer32, Unsigned32, 
     Counter64, TimeTicks 
        FROM SNMPv2-SMI 
   
     MODULE-COMPLIANCE, OBJECT-GROUP 
        FROM SNMPv2-CONF 
   
     TruthValue, RowStatus, StorageType, 
     TimeStamp 
        FROM SNMPv2-TC 
   
     SnmpAdminString 
        FROM SNMP-FRAMEWORK-MIB 
   
     PwVcIndexType, PwGroupID, PwVcIDType, PwOperStatus, 
     PwVcType 
        FROM PW-TC-MIB 
   
    InetAddressType, InetAddress 
        FROM INET-ADDRESS-MIB 
   
  ; 
   
  pwVcMIB MODULE-IDENTITY 
     LAST-UPDATED "200301301200Z"  -- 30 January 2003 12:00:00 EST 
     ORGANIZATION "Pseudo Wire Edge to Edge Emulation (PWE3) Working 
                   Group" 
     CONTACT-INFO 
         " 
          David Zelig 
          Postal: Corrigent Systems 
                  126, Yigal Alon St. 
                  Tel Aviv, ISRAEL 
                  Phone: +972-3-6945273 
          E-mail: davidz@corrigent.com 
   
          Thomas D. Nadeau 
          Postal: Cisco Systems, Inc. 
                  250 Apollo Drive 
                  Chelmsford, MA 01824 
          Tel:    +1-978-497-3051 
          Email:  tnadeau@cisco.com 
   
          Dave Danenberg 
          Postal: Litchfield Communications, Inc. 
                      Pseudo Wire (PW) Management           June 2003 
                            Information Base 


                  76 Westbury Park Rd 
                  Princeton Building East 
                  Watertown, CT 06795 
          Tel:    +1-860-945-1573 x3180 
          Email:  dave_danenberg@litchfieldcomm.com 
       
                  Andrew G. Malis  
          Postal: Vivace Networks, Inc.  
                  2730 Orchard Parkway  
                  San Jose, CA 95134  
          Email:  Andy.Malis@vivacenetworks.com 
           
                   Sharon Mantin 
          Postal:  AxONLink (Israel) Ltd  
                   9 Bareket St.  
                   Petah Tikva 49517, Israel  
          Tel:     +972-3-9263972  
          Email:   sharon.mantin@axonlink.com 
           
          The PWE3 Working Group (email distribution pwe3@ietf.org) 
          " 
   
     DESCRIPTION 
         "This MIB contains managed object definitions for Pseudo 
          Wire operation as in: Pate, P., et al, <draft-ietf-pwe3- 
          framework>, Xiao, X., et al, <draft-ietf-pwe3- 
          requirements>, Martini, L., et al, <draft-martini- 
          l2circuit-trans-mpls>, and Martini, L., et al, 
          <draft-martini-l2circuit-encap-mpls>. 
   
          The indexes for this MIB are also used to index the PSN- 
          specific tables and the VC-specific tables. The VC Type 
          dictates which VC-specific MIB to use. For example, a  
          'cep' VC Type requires the use the configuration and status  
          tables within the CEP-MIB. 
   
          This MIB enable the use of any underlying packet switched  
          network (PSN). Specific tables for the MPLS PSN is 
          currently defined in a separate PW-MPLS-MIB. Tables to 
          support other PSNs (IP, L2TP for example) will be added to 
          this MIB in future revisions. 
           
          At the time of publication of this version, there are no  
          PWE3 WG documents for all features and objects in this MIB, 
          and the MIB is therefore subject to change based on the WG  
          progress." 
      
     -- Revision history. 
     REVISION 
         "200305261200Z"  -- 26 May 2002 12:00:00 EST 
     DESCRIPTION 
                      Pseudo Wire (PW) Management           June 2003 
                            Information Base 


         "Moved to draft-ietf-00 status. Changes from previous draft: 
          1) Change name of pwVcPriority to pwVcSetUpPriority and  
             added pwVcHoldingPriority. 
          2) Add pwVcIdMappingTable and pwVcPeersMappingTable to help  
             ordered query of the MIB tables for EMS applications. 
          3) Clarification to work in progress objects. 
          4) Editorial and typos in descriptions. 
          5) Added pwVcPerfTotalDiscontinuityTime and  
             pwVcPerfIntervalTimeElapsed.  
          6) Remove 32 bit counters. 
         " 
     REVISION 
         "200201301200Z"  -- 30 January 2002 12:00:00 EST 
     DESCRIPTION 
         " Changes from -01 draft: 
           1) Inbound and outbound clarification and name changes. 
           2) Removing pwVcPeerIpv4Addr and pwVcPeerIpv6Addr,   
              replacing them with pwVcPeerAddr and adding type for  
              address type selection. 
           3) Adding type for VC OperStatus. 
           4) Adding pwVcTimeElapsed and pwVcValidIntervals. 
            
         " 
     REVISION 
         "200111071200Z"  -- 7 November 2001 12:00:00 EST 
     DESCRIPTION 
        "Changes from -00 draft: 
        1) Remove VcInstance from tables indexes in order to simplify 
           the MIB. 
        2) Removing APS 1+1 table. 
        3) Changing hdlcCisco to hdlc in pwVcType. 
        4) Add description of VC label at pending PW signaling stage. 
        5) Add interval valid object in interval performance tables. 
        6) Remove VC APS notification. 
        7) Change 'conservative'/'liberal' to 'strict'/'loose'. 
        8) Add objects for interface MTU, use of control word, 
           interface string. 
        9) Ordering of objects based on functionality. 
        10) Update operation of pwVcOperStatus.  
        " 
   
     REVISION 
         "200107111200Z"  -- 11 July 2001 12:00:00 EST 
     DESCRIPTION 
        "draft-00 version" 
   
     ::= { experimental xxx } -- To be assigned by IANA 
   
  -- Top-level components of this MIB. 
   
  -- Notifications 
                      Pseudo Wire (PW) Management           June 2003 
                            Information Base 


   
  -- Tables, Scalars 
  pwVcObjects       OBJECT IDENTIFIER 
                                ::= { pwVcMIB 1 } 
   
  -- Conformance 
  pwVcConformance   OBJECT IDENTIFIER  
                                ::= { pwVcMIB 2 } 
   
  -- PW Virtual Connection (VC) Table 
   
  pwVcIndexNext OBJECT-TYPE 
     SYNTAX            Unsigned32 
     MAX-ACCESS        read-only 
     STATUS            current 
     DESCRIPTION 
         "This object contains an appropriate value to be used 
          for pwVcIndex when creating entries in the 
          pwVcTable. The value 0 indicates that no 
          unassigned entries are available.  To obtain the 
          value of pwVcIndex for a new entry in the 
          pwVcTable, the manager issues a management 
          protocol retrieval operation to obtain the current 
          value of pwVcIndex.  After each retrieval 
          operation, the agent should modify the value to 
          reflect the next unassigned index.  After a manager 
          retrieves a value the agent will determine through 
          its local policy when this index value will be made 
          available for reuse." 
     ::= { pwVcObjects 1 } 
   
   
  pwVcTable   OBJECT-TYPE 
     SYNTAX        SEQUENCE OF PwVcEntry 
     MAX-ACCESS    not-accessible 
     STATUS        current 
     DESCRIPTION 
         "This table specifies information for connecting various 
          emulated services to various tunnel type." 
     ::= { pwVcObjects 2 } 
   
  pwVcEntry   OBJECT-TYPE 
     SYNTAX        PwVcEntry 
     MAX-ACCESS    not-accessible 
     STATUS        current 
     DESCRIPTION 
          "A row in this table represents an emulated virtual 
           connection (VC) across a packet network. It is indexed by 
           pwVcIndex, which uniquely identifying a singular  
           connection. 
          " 
                      Pseudo Wire (PW) Management           June 2003 
                            Information Base 


     INDEX  { pwVcIndex } 
   
        ::= { pwVcTable 1 } 
   
  PwVcEntry ::= SEQUENCE { 
        pwVcIndex               PwVcIndexType, 
        pwVcType                PwVcType, 
        pwVcOwner               INTEGER, 
        pwVcPsnType             INTEGER, 
        pwVcSetUpPriority       Integer32, 
        pwVcHoldingPriority     Integer32, 
        pwVcInboundMode         INTEGER,       
        pwVcPeerAddrType        InetAddressType, 
        pwVcPeerAddr            InetAddress, 
   
        pwVcID                  PwVcIDType, 
        pwVcLocalGroupID        PwGroupID, 
        pwVcControlWord         TruthValue, 
        pwVcLocalIfMtu          Unsigned32, 
        pwVcLocalIfString       TruthValue,  
        pwVcRemoteGroupID       PwGroupID, 
        pwVcRemoteControlWord   INTEGER, 
        pwVcRemoteIfMtu         Unsigned32, 
        pwVcRemoteIfString      SnmpAdminString,       
        pwVcOutboundVcLabel     Unsigned32, 
        pwVcInboundVcLabel      Unsigned32, 
   
        pwVcName                SnmpAdminString, 
        pwVcDescr               SnmpAdminString, 
        pwVcCreateTime          TimeStamp, 
        pwVcUpTime              TimeTicks, 
        pwVcAdminStatus         INTEGER, 
        pwVcOperStatus          PwOperStatus, 
        pwVcInboundOperStatus   PwOperStatus, 
        pwVcOutboundOperStatus  PwOperStatus, 
        pwVcTimeElapsed         Integer32, 
        pwVcValidIntervals      Integer32, 
        pwVcRowStatus           RowStatus, 
        pwVcStorageType         StorageType 
     } 
   
  pwVcIndex OBJECT-TYPE 
     SYNTAX        PwVcIndexType 
     MAX-ACCESS    not-accessible 
     STATUS        current 
     DESCRIPTION 
         "Index for the conceptual row identifying a VC within  
          this PW Emulation VC table." 
     ::= { pwVcEntry 1 } 
   
  pwVcType OBJECT-TYPE 
                      Pseudo Wire (PW) Management           June 2003 
                            Information Base 


     SYNTAX        PwVcType 
     MAX-ACCESS    read-create 
     STATUS        current 
     DESCRIPTION 
         "This value indicate the service to be carried over 
          this VC.  
          Note: the exact set of VC types is yet to be worked  
          out by the WG. 
         " 
     ::= { pwVcEntry 2 } 
   
  pwVcOwner OBJECT-TYPE  
     SYNTAX   INTEGER { 
            manual                (1),  
            maintenanceProtocol   (2), -- PW signaling 
            other                 (3) 
                      } 
     MAX-ACCESS    read-create 
     STATUS        current 
     DESCRIPTION 
          "Set by the operator to indicate the protocol responsible  
           for establishing this VC. Value 'manual' is used in all 
           cases where no maintenance protocol (PW signaling) is used  
           to set-up the VC, i.e. require configuration of entries in 
           the VC tables including VC labels, etc. The value  
           'maintenanceProtocol' is used in case of standard 
           signaling of the VC for the specific PSN, for example LDP 
           for MPLS PSN as specified in <draft- draft-martini- 
           l2circuit-trans-mpls> or L2TP control protocol.  
           Value 'other' is used for other types of signaling."  
     ::= { pwVcEntry 3 } 
   
   
  pwVcPsnType OBJECT-TYPE  
     SYNTAX   INTEGER { 
         mpls       (1),  
         l2tp       (2), 
         ip         (3), 
         mplsOverIp (4), -- May be combined with 'mpls' in the future 
         gre        (5), 
         other      (6) 
                      } 
     MAX-ACCESS    read-create 
     STATUS        current 
     DESCRIPTION 
          "Set by the operator to indicate the PSN type on which this  
           VC will be carried. Based on this object, the relevant PSN  
           table entries are created in the in the PSN specific MIB  
           modules. For example, if mpls(1) is defined, the agent  
           create an entry in pwVcMplsTable, which further define the  
           MPLS PSN configuration. 
                      Pseudo Wire (PW) Management           June 2003 
                            Information Base 


           Note: the exact set of PSN types is yet to be worked  
           out by the WG. 
           " 
     ::= { pwVcEntry 4 } 
   
  pwVcSetUpPriority  OBJECT-TYPE 
     SYNTAX         Integer32 (0..7) 
     MAX-ACCESS     read-create 
     STATUS         current 
     DESCRIPTION 
          "This object define the relative set-up priority of the VC   
           in a lowest-to-highest fashion, where 0 is the highest  
           priority. VCs with the same priority are treated with 
           equal priority. Dropped VC will be set 'dormant' (as 
           indicated in pwVcOperStatus). 
           This value is significant if there are competing resources 
           between VCs and the implementation support this feature. 
           If not supported or not relevant, the value of zero MUST 
           be used."  
     DEFVAL 
         { 0 } 
     ::= { pwVcEntry 5 } 
   
  pwVcHoldingPriority  OBJECT-TYPE 
     SYNTAX         Integer32 (0..7) 
     MAX-ACCESS     read-create 
     STATUS         current 
     DESCRIPTION 
          "This object define the relative holding priority of the VC   
           in a lowest-to-highest fashion, where 0 is the highest  
           priority. VCs with the same priority are treated with 
           equal priority. Dropped VC will be set 'dormant' (as 
           indicated in pwVcOperStatus). 
           This value is significant if there are competing resources 
           between VCs and the implementation support this feature. 
           If not supported or not relevant, the value of zero MUST 
           be used."  
     DEFVAL 
         { 0 } 
     ::= { pwVcEntry 6 } 
   
  pwVcInboundMode OBJECT-TYPE 
     SYNTAX        INTEGER { 
     loose (1), 
     strict (2) 
     } 
     MAX-ACCESS    read-create 
     STATUS        current 
     DESCRIPTION 
         "This object is used to enable greater security for  
          implementation that use per platform VC label space. In  
                      Pseudo Wire (PW) Management           June 2003 
                            Information Base 


          strict mode, packets coming from the PSN are accepted only  
          from tunnels that are associated to the same VC via the  
          inbound tunnel table in the case of MPLS, or as identified  
          by the source IP address in case of L2TP or IP PSN. The  
          entries in the inbound tunnel table are either explicitly  
          configured or implicitly known by the maintenance protocol  
          used for VC set-up. 
   
          If such association is not known, not configured or not  
          desired, loose mode should be configured, and the node  
          should accept the packet based on the VC label only  
          regardless of the outer tunnel used to carry the VC." 
     DEFVAL 
          { loose } 
     ::= { pwVcEntry 7 } 
   
  pwVcPeerAddrType OBJECT-TYPE 
     SYNTAX        InetAddressType 
     MAX-ACCESS    read-create 
     STATUS        current 
     DESCRIPTION 
          "Denotes the address type of the peer node maintenance 
           protocol (signaling) address if PW maintenance protocol is 
           used for the VC creation. It should be set to  
           'unknown' if PE/PW maintenance protocol is not used,  
           i.e. pwVcOwner is set to 'manual'. " 
     DEFVAL        { ipv4 } 
     ::= { pwVcEntry 8 } 
   
  pwVcPeerAddr OBJECT-TYPE 
     SYNTAX        InetAddress 
     MAX-ACCESS    read-create 
     STATUS        current 
     DESCRIPTION 
          "This object conatin the value of of the peer node address 
           of the PW/PE maintenance protocol entity. This object  
           should contain a value of 0 if not relevant (manual  
           configuration of the VC)." 
     ::= { pwVcEntry 9 } 
   
  pwVcID OBJECT-TYPE 
     SYNTAX        PwVcIDType 
     MAX-ACCESS    read-create 
     STATUS        current 
     DESCRIPTION 
         "Used in the outgoing VC ID field within the 'Virtual 
          Circuit FEC Element' when LDP signaling is used or PW ID  
          AVP for L2TP." 
     REFERENCE 
         "Martini, et al, <draft-martini-l2circuit-trans-mpls>. 
          and So, et al, <draft-so-pwe3-ethernet>.  
                      Pseudo Wire (PW) Management           June 2003 
                            Information Base 


          Note: as specified in l2circuit-trans: It is REQUIRED to 
          assign the same VC ID, and VC type for a given circuit in 
          both directions." 
     ::= { pwVcEntry 10 } 
   
  pwVcLocalGroupID OBJECT-TYPE 
     SYNTAX        PwGroupID 
     MAX-ACCESS    read-create 
     STATUS        current 
     DESCRIPTION 
         "Used in the Group ID field sent to the peer PWES  
         within the maintenance protocol used for VC setup,  
         zero if not used." 
     REFERENCE 
         "Martini, et al, <draft-martini-l2circuit-trans-mpls> 
         and So, et al, <draft-so-pwe3-ethernet.txt>." 
     ::= { pwVcEntry 11 } 
   
  pwVcControlWord OBJECT-TYPE 
     SYNTAX        TruthValue 
     MAX-ACCESS    read-create 
     STATUS        current 
     DESCRIPTION 
         "Define if the control word will be sent with each packet by  
          the local node." 
     REFERENCE 
         "Martini, et al, <draft-martini-l2circuit-trans-mpls>" 
     DEFVAL 
         { false } 
     ::= { pwVcEntry 12 } 
   
  pwVcLocalIfMtu OBJECT-TYPE 
     SYNTAX        Unsigned32 (0..65535) 
     MAX-ACCESS    read-create 
     STATUS        current 
     DESCRIPTION 
         "If not equal zero, the optional IfMtu object in the  
          maintenance protocol will be sent with this value,  
          representing the locally supported MTU size over the  
          interface (or the virtual interface) associated with the  
          VC." 
     REFERENCE 
         "Martini, et al, <draft-martini-l2circuit-trans-mpls> 
          and So, et al, <draft-so-pwe3-ethernet>." 
   
     DEFVAL 
         { 0 } 
     ::= { pwVcEntry 13 } 
   
  pwVcLocalIfString OBJECT-TYPE 
     SYNTAX        TruthValue 
                      Pseudo Wire (PW) Management           June 2003 
                            Information Base 


     MAX-ACCESS    read-create 
     STATUS        current 
     DESCRIPTION 
         "Each VC is associated to an interface (or a virtual  
          interface) in the ifTable of the node as part of the 
          service configuration. This object defines if the  
          maintenance protocol will send the interface's name as 
          appears on the ifTable in the name object as part of the 
          maintenance protocol. If set to false, the optional element 
          will not be sent." 
     REFERENCE 
         "Martini, et al, <draft-martini-l2circuit-trans-mpls> 
          and So, et al, <draft-so-pwe3-ethernet.txt>." 
     DEFVAL 
         { false } 
     ::= { pwVcEntry 14 } 
   
  pwVcRemoteGroupID OBJECT-TYPE 
     SYNTAX        PwGroupID 
     MAX-ACCESS    read-only 
     STATUS        current 
     DESCRIPTION 
         "Obtained from the Group ID field as received via the  
          maintenance protocol used for VC setup, zero if not used.  
          Value of 0xFFFF shall be used if the object is yet to be  
          defined by the VC maintenance protocol." 
     REFERENCE 
         "Martini, et al, <draft-martini-l2circuit-trans-mpls> 
          and So, et al, <draft-so-pwe3-ethernet.txt>." 
     ::= { pwVcEntry 15 } 
   
  pwVcRemoteControlWord OBJECT-TYPE 
     SYNTAX        INTEGER { 
                         noControlWord (1), 
                         withControlWord (2), 
                         notYetKnown(3) 
                       } 
     MAX-ACCESS    read-create 
     STATUS        current 
     DESCRIPTION 
         "If maintenance protocol is used for VC establishment, this  
          parameter indicates the received status of the control word  
          usage, i.e. if packets will be received with control word 
          or not. The value of 'notYetKnown' is used while the 
          maintenance protocol has not yet received the indication  
          from the remote node. 
          In manual configuration of the VC this parameters indicate  
          to the local node what is the expected encapsulation for 
          the received packets. 
         " 
                      Pseudo Wire (PW) Management           June 2003 
                            Information Base 


     REFERENCE 
         "Martini, et al, <draft-martini-l2circuit-trans-mpls> 
          and So, et al, <draft-so-pwe3-ethernet.txt>." 
     ::= { pwVcEntry 16 } 
   
  pwVcRemoteIfMtu OBJECT-TYPE 
     SYNTAX        Unsigned32  
     MAX-ACCESS    read-only 
     STATUS        current 
     DESCRIPTION 
         "The remote interface MTU as (optionally) received from the 
          remote node via the maintenance protocol. Should be zero if 
          this parameter is not available or not used." 
     REFERENCE 
         "Martini, et al, <draft-martini-l2circuit-trans-mpls> 
          and So, et al, <draft-so-pwe3-ethernet.txt>." 
     ::= { pwVcEntry 17 } 
   
  pwVcRemoteIfString OBJECT-TYPE 
     SYNTAX        SnmpAdminString (SIZE (0..80)) 
     MAX-ACCESS    read-only 
     STATUS        current 
     DESCRIPTION 
         "Indicate the interface description string as received by 
          the maintenance protocol, MUST be NULL string if not  
          applicable or not known yet." 
     REFERENCE 
         "Martini, et al, <draft-martini-l2circuit-trans-mpls> 
          and So, et al, <draft-so-pwe3-ethernet>." 
     ::= { pwVcEntry 18 } 
   
  pwVcOutboundVcLabel OBJECT-TYPE 
     SYNTAX        Unsigned32 
     MAX-ACCESS    read-create 
     STATUS        current 
     DESCRIPTION 
         "The VC label used in the outbound direction (i.e. toward  
          the PSN). It may be set up manually if owner is 'manual' or  
          automatically otherwise. Examples: For MPLS PSN, it  
          represents the 20 bits of VC tag, for L2TP it represent the 
          32 bits Session ID. 
          If the label is not yet known (signaling in process), the  
          object should return a value of 0xFFFF." 
     REFERENCE 
         "Martini, et al, <draft-martini-l2circuit-trans-mpls> 
          Townsley, et al, <draft-ietf-l2tpext-l2tp-base.txt>" 
     ::= { pwVcEntry 19 } 
   
  pwVcInboundVcLabel OBJECT-TYPE 
     SYNTAX        Unsigned32 
     MAX-ACCESS    read-create 
                      Pseudo Wire (PW) Management           June 2003 
                            Information Base 


     STATUS        current 
     DESCRIPTION 
         "The VC label used in the inbound direction (i.e. packets  
          received from the PSN. It may be set up manually if owner 
          is 'manual' or automatically otherwise.  
          Examples: For MPLS PSN, it represents the 20 bits of VC 
          tag, for L2TP it represent the 32 bits Session ID. 
          If the label is not yet known (signaling in process), the  
          object should return a value of 0xFFFF." 
     REFERENCE 
         "Martini, et al, <draft-martini-l2circuit-trans-mpls> 
          Townsley, et al, <draft-ietf-l2tpext-l2tp-base.txt>" 
     ::= { pwVcEntry 20 } 
   
  pwVcName  OBJECT-TYPE 
     SYNTAX        SnmpAdminString 
     MAX-ACCESS    read-create 
     STATUS        current 
     DESCRIPTION 
         "The canonical name assigned to the VC." 
     ::= { pwVcEntry 21 } 
   
  pwVcDescr OBJECT-TYPE 
     SYNTAX        SnmpAdminString 
     MAX-ACCESS    read-create 
     STATUS        current 
     DESCRIPTION 
         "A textual string containing information about the VC.  
          If there is no description this object contains a zero 
          length string." 
     ::= { pwVcEntry 22 } 
   
  pwVcCreateTime OBJECT-TYPE 
     SYNTAX        TimeStamp 
     MAX-ACCESS    read-only 
     STATUS        current 
     DESCRIPTION 
         "System time when this VC was created." 
     ::= { pwVcEntry 23 } 
   
  pwVcUpTime  OBJECT-TYPE 
     SYNTAX        TimeTicks 
     MAX-ACCESS    read-only 
     STATUS        current 
     DESCRIPTION 
         "Number of consecutive ticks this VC has been 'up' in 
          both directions together (i.e. 'up' is observed in  
          pwVcOperStatus.)" 
     ::= { pwVcEntry 24 } 
   
  pwVcAdminStatus OBJECT-TYPE 
                      Pseudo Wire (PW) Management           June 2003 
                            Information Base 


     SYNTAX   INTEGER { 
                  up(1),     -- ready to pass packets 
                  down(2), 
                  testing(3) -- in some test mode 
     } 
     MAX-ACCESS    read-create 
     STATUS        current 
     DESCRIPTION 
         "The desired operational status of this VC." 
     ::= { pwVcEntry 25 } 
   
  pwVcOperStatus OBJECT-TYPE 
     SYNTAX        PwOperStatus 
     MAX-ACCESS    read-only 
     STATUS        current 
     DESCRIPTION 
          "Indicates the actual combined operational status of this  
           VC. It is 'up' if both pwVcInboundOperStatus and  
           pwVcOutboundOperStatus are in 'up' state. For all other  
           values, if the VCs in both directions are of the same 
           value it reflects that value, otherwise it is set to the 
           most severe status out of the two statuses. The order of  
           severance from most severe to less severe is: unknown,  
           notPresent, down, lowerLayerDown, dormant, testing, up. 
           The operator may consult the per direction OperStatus for 
           fault isolation per direction." 
     ::= { pwVcEntry 26 } 
   
  pwVcInboundOperStatus OBJECT-TYPE 
     SYNTAX        PwOperStatus 
     MAX-ACCESS    read-only 
     STATUS        current 
     DESCRIPTION 
          "Indicates the actual operational status of this VC in the  
           inbound direction. 
   
           - down:           if PW signaling has not yet finished, or 
                             indications available at the service  
                             level indicate that the VC is not  
                             passing packets. 
           - testing:        if AdminStatus at the VC level is set to  
                             test. 
           - dormant:        The VC is not available because of the 
                             required resources are occupied VC with  
                             higher priority VCs . 
           - notPresent:     Some component is missing to accomplish  
                             the set up of the VC. 
           - lowerLayerDown: The underlying PSN is not in OperStatus  
                             'up'.  
           " 
     ::= { pwVcEntry 27 } 
                      Pseudo Wire (PW) Management           June 2003 
                            Information Base 


   
  pwVcOutboundOperStatus OBJECT-TYPE 
     SYNTAX        PwOperStatus 
     MAX-ACCESS    read-only 
     STATUS        current 
     DESCRIPTION 
          "Indicates the actual operational status of this VC in the  
           outbound direction 
           - down:           if PW signaling has not yet finished, or 
                             indications available at the service  
                             level indicate that the VC is not 
                             passing packets. 
           - testing:        if AdminStatus at the VC level is set to  
                             test. 
           - dormant:        The VC is not available because of the 
                             required resources are occupied VC with  
                             higher priority VCs . 
           - notPresent:     Some component is missing to accomplish  
                             the set up of the VC. 
           - lowerLayerDown: The underlying PSN is not in OperStatus  
                             'up'.  
           " 
     ::= { pwVcEntry 28 } 
   
  pwVcTimeElapsed OBJECT-TYPE 
      SYNTAX  Integer32 (1..900) 
      MAX-ACCESS  read-only 
      STATUS  current 
      DESCRIPTION 
         "The number of seconds, including partial seconds, 
         that have elapsed since the beginning of the current 
         measurement period. If, for some reason, such as an 
         adjustment in the system's time-of-day clock, the 
         current interval exceeds the maximum value, the 
         agent will return the maximum value." 
      ::= { pwVcEntry 29 } 
   
  pwVcValidIntervals OBJECT-TYPE 
      SYNTAX  Integer32 (0..96) 
      MAX-ACCESS  read-only 
      STATUS  current 
      DESCRIPTION 
         "The number of previous 15-minute intervals 
         for which data was collected.  
         An agent with PW capability must be capable of supporting at  
         least n intervals. The minimum value of n is 4, The default  
         of n is 32 and the maximum value of n is 96. 
         The value will be <n> unless the measurement was (re-)  
         started within the last (<n>*15) minutes, in which case the  
         value will be the number of complete 15 minute intervals for  
         which the agent has at least some data. In certain cases  
                      Pseudo Wire (PW) Management           June 2003 
                            Information Base 


         (e.g., in the case where the agent is a proxy) it is  
         possible that some intervals are unavailable.  In this case,  
         this interval is the maximum interval number for which data  
         is available. " 
      ::= { pwVcEntry 30 } 
   
  pwVcRowStatus OBJECT-TYPE 
     SYNTAX        RowStatus 
     MAX-ACCESS    read-create 
     STATUS        current 
     DESCRIPTION 
         "For creating, modifying, and deleting this row." 
     ::= { pwVcEntry 31 } 
   
  pwVcStorageType OBJECT-TYPE 
     SYNTAX        StorageType 
     MAX-ACCESS    read-create 
     STATUS        current 
     DESCRIPTION 
         "This variable indicates the storage type for this 
          object." 
     ::= { pwVcEntry 32 } 
   
  -- End of PW Virtual Connection (VC) Table 
   
  -- Vc Performance Table. 
   
  pwVcPerfCurrentTable  OBJECT-TYPE 
     SYNTAX        SEQUENCE OF PwVcPerfCurrentEntry 
     MAX-ACCESS    not-accessible 
     STATUS        current 
     DESCRIPTION 
          "This table provides per-VC performance information for the  
           current interval." 
     ::= { pwVcObjects 3 } 
   
  pwVcPerfCurrentEntry OBJECT-TYPE 
     SYNTAX        PwVcPerfCurrentEntry 
     MAX-ACCESS    not-accessible 
     STATUS        current 
     DESCRIPTION 
          "An entry in this table is created by the agent for 
           every VC." 
     INDEX  { pwVcIndex } 
     ::= { pwVcPerfCurrentTable 1 } 
      
  PwVcPerfCurrentEntry ::= SEQUENCE { 
        pwVcPerfCurrentInHCPackets          Counter64, 
        pwVcPerfCurrentInHCBytes            Counter64, 
        pwVcPerfCurrentOutHCBytes           Counter64, 
        pwVcPerfCurrentOutHCPackets         Counter64       
                      Pseudo Wire (PW) Management           June 2003 
                            Information Base 


        } 
   
  pwVcPerfCurrentInHCPackets OBJECT-TYPE 
     SYNTAX        Counter64 
     MAX-ACCESS    read-only 
     STATUS        current 
     DESCRIPTION 
          "High capacity counter for number of packets received 
           by the VC (from the PSN) in the current 15 minute 
  interval." 
     ::= { pwVcPerfCurrentEntry 1 } 
                                 
  pwVcPerfCurrentInHCBytes OBJECT-TYPE 
     SYNTAX        Counter64 
     MAX-ACCESS    read-only 
     STATUS        current 
     DESCRIPTION 
          "High capacity counter for number of bytes received 
           by the VC (from the PSN) in the current 15 minute 
  interval." 
     ::= { pwVcPerfCurrentEntry 2 } 
   
  pwVcPerfCurrentOutHCPackets OBJECT-TYPE 
     SYNTAX        Counter64 
     MAX-ACCESS    read-only 
     STATUS        current 
     DESCRIPTION 
          "High capacity counter for number of packets forwarded 
           by the VC (to the PSN) in the current 15 minute interval." 
     ::= { pwVcPerfCurrentEntry 3 } 
   
  pwVcPerfCurrentOutHCBytes OBJECT-TYPE 
     SYNTAX        Counter64 
     MAX-ACCESS    read-only 
     STATUS        current 
     DESCRIPTION 
          "High capacity counter for number of bytes forwarded 
           by the VC (to the PSN) in the current 15 minute interval." 
     ::= { pwVcPerfCurrentEntry 4 } 
   
  -- End of Vc Perf current Table 
   
  -- Vc Performance Interval Table. 
   
  pwVcPerfIntervalTable  OBJECT-TYPE 
     SYNTAX        SEQUENCE OF PwVcPerfIntervalEntry 
     MAX-ACCESS    not-accessible 
     STATUS        current 
     DESCRIPTION 
          "This table provides per-VC performance information for  
           each interval." 
                      Pseudo Wire (PW) Management           June 2003 
                            Information Base 


     ::= { pwVcObjects 4 } 
   
  pwVcPerfIntervalEntry OBJECT-TYPE 
     SYNTAX        PwVcPerfIntervalEntry 
     MAX-ACCESS    not-accessible 
     STATUS        current 
     DESCRIPTION 
          "An entry in this table is created agent for every VC." 
     INDEX  { pwVcIndex, pwVcPerfIntervalNumber } 
     ::= { pwVcPerfIntervalTable 1 } 
      
  PwVcPerfIntervalEntry ::= SEQUENCE { 
        pwVcPerfIntervalNumber               Integer32, 
        pwVcPerfIntervalValidData            TruthValue, 
        pwVcPerfIntervalTimeElapsed          Integer32, 
   
        pwVcPerfIntervalInHCPackets          Counter64, 
        pwVcPerfIntervalInHCBytes            Counter64, 
        pwVcPerfIntervalOutHCPackets         Counter64, 
        pwVcPerfIntervalOutHCBytes           Counter64 
                          } 
   
  pwVcPerfIntervalNumber OBJECT-TYPE 
      SYNTAX  Integer32 (1..96) 
      MAX-ACCESS  not-accessible 
      STATUS  current 
      DESCRIPTION 
          "A number N, between 1 and 96, which identifies the 
           interval for which the set of statistics is available. 
           The interval identified by 1 is the most recently 
           completed 15 minute interval, and the interval identified 
           by N is the interval immediately preceding the one 
           identified by N-1. 
           The minimum range of N is 1 through 4. The default range 
           is 1 to 32. The maximum range of N is 1 through 96. " 
     REFERENCE 
         "Tesink, K. 'Definitions of Managed Objects for the 
          SONET/SDH Interface Type', RFC 2558" 
     ::= { pwVcPerfIntervalEntry 1 } 
   
  pwVcPerfIntervalValidData OBJECT-TYPE 
     SYNTAX        TruthValue 
     MAX-ACCESS    read-only 
     STATUS        current 
     DESCRIPTION 
         "This variable indicates if the data for this interval 
          is valid." 
     ::= { pwVcPerfIntervalEntry 2 } 
   
  pwVcPerfIntervalTimeElapsed OBJECT-TYPE 
      SYNTAX      Integer32  
                      Pseudo Wire (PW) Management           June 2003 
                            Information Base 


      MAX-ACCESS  read-only 
      STATUS      current 
      DESCRIPTION 
        "The duration of a particular interval in seconds. 
         Adjustments in the system's time-of-day clock, may 
         cause the interval to be greater or less than the 
         normal value. Therefore this actual interval value 
         is provided." 
      ::= { pwVcPerfIntervalEntry 3 } 
   
  pwVcPerfIntervalInHCPackets OBJECT-TYPE 
     SYNTAX        Counter64 
     MAX-ACCESS    read-only 
     STATUS        current 
     DESCRIPTION 
          "High capacity counter for number of packets received by 
           the VC (from the PSN) in a particular 15-minute interval." 
     ::= { pwVcPerfIntervalEntry 4 } 
   
  pwVcPerfIntervalInHCBytes OBJECT-TYPE 
     SYNTAX        Counter64 
     MAX-ACCESS    read-only 
     STATUS        current 
     DESCRIPTION 
          "High capacity counter for number of bytes received by the  
           VC (from the PSN) in a particular 15-minute interval." 
   
     ::= { pwVcPerfIntervalEntry 5 } 
   
  pwVcPerfIntervalOutHCPackets OBJECT-TYPE 
     SYNTAX        Counter64 
     MAX-ACCESS    read-only 
     STATUS        current 
     DESCRIPTION 
          "High capacity counter for number of packets forwarded by  
           the VC (to the PSN) in a particular 15-minute interval." 
     ::= { pwVcPerfIntervalEntry 6 } 
   
  pwVcPerfIntervalOutHCBytes OBJECT-TYPE 
     SYNTAX        Counter64 
     MAX-ACCESS    read-only 
     STATUS        current 
     DESCRIPTION 
          "High capacity counter for number of bytes forwarded by the  
           VC (to the PSN) in a particular 15-minute interval." 
   
     ::= { pwVcPerfIntervalEntry 7 } 
   
  -- End of VC Performance Interval Table 
   
  -- VC Performance Total Table. 
                      Pseudo Wire (PW) Management           June 2003 
                            Information Base 


   
  pwVcPerfTotalTable  OBJECT-TYPE 
     SYNTAX        SEQUENCE OF PwVcPerfTotalEntry 
     MAX-ACCESS    not-accessible 
     STATUS        current 
     DESCRIPTION 
          "This table provides per-VC Performance information from VC  
           start time." 
     ::= { pwVcObjects 5 } 
   
  pwVcPerfTotalEntry OBJECT-TYPE 
     SYNTAX        PwVcPerfTotalEntry 
     MAX-ACCESS    not-accessible 
     STATUS        current 
     DESCRIPTION 
          "An entry in this table is created agent for every VC." 
   
     INDEX  { pwVcIndex } 
     ::= { pwVcPerfTotalTable 1 } 
      
  PwVcPerfTotalEntry ::= SEQUENCE { 
        pwVcPerfTotalInHCPackets          Counter64, 
        pwVcPerfTotalInHCBytes            Counter64, 
        pwVcPerfTotalOutHCPackets         Counter64, 
        pwVcPerfTotalOutHCBytes           Counter64, 
        pwVcPerfTotalDiscontinuityTime    TimeStamp 
                          } 
   
  pwVcPerfTotalInHCPackets OBJECT-TYPE 
     SYNTAX        Counter64 
     MAX-ACCESS    read-only 
     STATUS        current 
     DESCRIPTION 
         "High capacity counter for number of packets received by the  
          VC (from the PSN)." 
     ::= { pwVcPerfTotalEntry 1 } 
   
  pwVcPerfTotalInHCBytes OBJECT-TYPE 
     SYNTAX        Counter64 
     MAX-ACCESS    read-only 
     STATUS        current 
     DESCRIPTION 
          "High capacity counter for number of bytes received by the  
           VC (from the PSN)." 
     ::= { pwVcPerfTotalEntry 2 } 
   
  pwVcPerfTotalOutHCPackets OBJECT-TYPE 
     SYNTAX        Counter64 
     MAX-ACCESS    read-only 
     STATUS        current 
     DESCRIPTION 
                      Pseudo Wire (PW) Management           June 2003 
                            Information Base 


          "High capacity counter for number of packets forwarded by  
           the VC (to the PSN)." 
     ::= { pwVcPerfTotalEntry 3 } 
   
  pwVcPerfTotalOutHCBytes OBJECT-TYPE 
     SYNTAX        Counter64 
     MAX-ACCESS    read-only 
     STATUS        current 
     DESCRIPTION 
          "High capacity counter for number of bytes forwarded by the  
           VC (to the PSN)." 
     ::= { pwVcPerfTotalEntry 4 } 
   
  pwVcPerfTotalDiscontinuityTime OBJECT-TYPE 
     SYNTAX      TimeStamp 
     MAX-ACCESS  read-only 
     STATUS      current 
     DESCRIPTION 
         "The value of sysUpTime on the most recent occasion at 
          which any one or more of this row Counter32 or 
          Counter64 suffered a discontinuity. If no such 
          discontinuities have occurred since the last re- 
          initialization of the local management subsystem, then 
          this object contains a zero value." 
     ::= { pwVcPerfTotalEntry 5 } 
   
  -- End of VC Perf Total Table 
   
  -- Error counter scalar  
   
  pwVcPerfTotalErrorPackets OBJECT-TYPE 
     SYNTAX        Counter64 
     MAX-ACCESS    read-only 
     STATUS        current 
     DESCRIPTION 
          "Counter for number of error at VC level processing, for  
           example packets received with unknown VC label." 
     ::= { pwVcObjects 6 } 
   
  -- Reverse mapping tables 
   
  pwVcIdMappingTable  OBJECT-TYPE 
     SYNTAX        SEQUENCE OF PwVcIdMappingEntry 
     MAX-ACCESS    not-accessible 
     STATUS        current 
     DESCRIPTION 
          "This table provides reverse mapping of the existing VCs  
           based on vc type and VC ID ordering. This table is  
           typically useful for EMS ordered query of existing VCs." 
     ::= { pwVcObjects 7 } 
                      Pseudo Wire (PW) Management           June 2003 
                            Information Base 


  pwVcIdMappingEntry OBJECT-TYPE 
     SYNTAX        PwVcIdMappingEntry 
     MAX-ACCESS    not-accessible 
     STATUS        current 
     DESCRIPTION 
          "An entry in this table is created by the agent for every  
           VC configured by the pwVcTable." 
   
     INDEX  { pwVcIdMappingVcType,  pwVcIdMappingVcID, 
              pwVcIdMappingPeerAddrType, pwVcIdMappingPeerAddr, 
              pwVcIdMappingVcIndex} 
     ::= { pwVcIdMappingTable 1 } 
      
  PwVcIdMappingEntry ::= SEQUENCE { 
        pwVcIdMappingVcType               PwVcType, 
        pwVcIdMappingVcID                 PwVcIDType, 
        pwVcIdMappingPeerAddrType         InetAddressType, 
        pwVcIdMappingPeerAddr             InetAddress, 
        pwVcIdMappingVcIndex              PwVcIndexType 
                         } 
   
  pwVcIdMappingVcType OBJECT-TYPE 
     SYNTAX        PwVcType 
     MAX-ACCESS    not-accessible 
     STATUS        current 
     DESCRIPTION 
          "The VC type (indicate the service) of this VC." 
     ::= { pwVcIdMappingEntry 1 } 
   
  pwVcIdMappingVcID OBJECT-TYPE 
     SYNTAX        PwVcIDType 
     MAX-ACCESS    not-accessible 
     STATUS        current 
     DESCRIPTION 
          "The VC ID of this VC. Zero if the VC is configured  
           manually." 
     ::= { pwVcIdMappingEntry 2 } 
   
  pwVcIdMappingPeerAddrType OBJECT-TYPE 
     SYNTAX        InetAddressType 
     MAX-ACCESS    not-accessible 
     STATUS        current 
     DESCRIPTION 
          "IP address type of the peer node." 
     ::= { pwVcIdMappingEntry 3 } 
   
  pwVcIdMappingPeerAddr OBJECT-TYPE 
     SYNTAX        InetAddress 
     MAX-ACCESS    not-accessible 
     STATUS        current 
     DESCRIPTION 
                      Pseudo Wire (PW) Management           June 2003 
                            Information Base 


          "IP address type of the peer node." 
     ::= { pwVcIdMappingEntry 4 } 
   
  pwVcIdMappingVcIndex  OBJECT-TYPE 
     SYNTAX        PwVcIndexType 
     MAX-ACCESS    read-only 
     STATUS        current 
     DESCRIPTION 
         "The value that represent the VC in the pwVcTable." 
     ::= { pwVcIdMappingEntry 5 } 
   
  pwVcPeerMappingTable  OBJECT-TYPE 
     SYNTAX        SEQUENCE OF PwVcPeerMappingEntry 
     MAX-ACCESS    not-accessible 
     STATUS        current 
     DESCRIPTION 
          "This table provides reverse mapping of the existing VCs  
           based on vc type and VC ID ordering. This table is  
           typically useful for EMS ordered query of existing VCs." 
     ::= { pwVcObjects 8 } 
   
  pwVcPeerMappingEntry OBJECT-TYPE 
     SYNTAX        PwVcPeerMappingEntry 
     MAX-ACCESS    not-accessible 
     STATUS        current 
     DESCRIPTION 
          "An entry in this table is created by the agent for every  
           VC configured in pwVcTable." 
   
     INDEX  { pwVcPeerMappingPeerAddrType, pwVcPeerMappingPeerAddr, 
              pwVcPeerMappingVcType,  pwVcPeerMappingVcID, 
              pwVcPeerMappingVcIndex}  
   
     ::= { pwVcPeerMappingTable 1 } 
      
  PwVcPeerMappingEntry ::= SEQUENCE { 
        pwVcPeerMappingPeerAddrType         InetAddressType, 
        pwVcPeerMappingPeerAddr             InetAddress, 
        pwVcPeerMappingVcType               PwVcType, 
        pwVcPeerMappingVcID                 PwVcIDType, 
        pwVcPeerMappingVcIndex              PwVcIndexType 
                         } 
   
  pwVcPeerMappingPeerAddrType OBJECT-TYPE 
     SYNTAX        InetAddressType 
     MAX-ACCESS    not-accessible 
     STATUS        current 
     DESCRIPTION 
          "IP address type of the peer node." 
     ::= { pwVcPeerMappingEntry 1 } 
                      Pseudo Wire (PW) Management           June 2003 
                            Information Base 


  pwVcPeerMappingPeerAddr OBJECT-TYPE 
     SYNTAX        InetAddress 
     MAX-ACCESS    not-accessible 
     STATUS        current 
     DESCRIPTION 
          "IP address type of the peer node." 
     ::= { pwVcPeerMappingEntry 2 } 
   
  pwVcPeerMappingVcType OBJECT-TYPE 
     SYNTAX        PwVcType 
     MAX-ACCESS    not-accessible 
     STATUS        current 
     DESCRIPTION 
          "The VC type (indicate the service) of this VC." 
     ::= { pwVcPeerMappingEntry 3 } 
   
  pwVcPeerMappingVcID OBJECT-TYPE 
     SYNTAX        PwVcIDType 
     MAX-ACCESS    not-accessible 
     STATUS        current 
     DESCRIPTION 
          "The VC ID of this VC. Zero if the VC is configured  
           manually." 
     ::= { pwVcPeerMappingEntry 4 } 
   
  pwVcPeerMappingVcIndex  OBJECT-TYPE 
     SYNTAX        PwVcIndexType 
     MAX-ACCESS    read-only 
     STATUS        current 
     DESCRIPTION 
         "The value that represent the VC in the pwVcTable." 
     ::= { pwVcPeerMappingEntry 5 } 
   
   
  -- End of reverse mapping tables 
   
  -- Notifications - PW VCs 
   
  -- No notifications are defined. Notifications are generated in 
  -- the per service MIB modules and/or PSN specific modules.  
  -- Notification related to the maintenance protocol are FFS. 
   
  -- End of notifications. 
   
  -- conformance information 
   
   
     -- Note: Conformance at the object access and values level is  
     -- still FFS, therefore current conformance is defined at the 
     -- object existence level only. 
                      Pseudo Wire (PW) Management           June 2003 
                            Information Base 


  pwVcGroups      OBJECT IDENTIFIER ::= { pwVcConformance   1 } 
  pwVcCompliances OBJECT IDENTIFIER ::= { pwVcConformance   2 } 
   
   
  pwModuleCompliance MODULE-COMPLIANCE 
      STATUS  current 
      DESCRIPTION 
              "The compliance statement for agent that support PW  
               operation." 
   
      MODULE  -- this module 
          MANDATORY-GROUPS { pwVcGroup, 
                             pwVcPeformanceGroup } 
   
       ::= { pwVcCompliances 1 } 
   
  -- Units of conformance. 
   
  pwVcGroup   OBJECT-GROUP  
     OBJECTS { 
              pwVcIndexNext, 
              pwVcType, 
              pwVcOwner, 
              pwVcPsnType, 
              pwVcSetUpPriority, 
              pwVcHoldingPriority, 
              pwVcInboundMode, 
              pwVcPeerAddrType, 
              pwVcPeerAddr, 
              pwVcID, 
              pwVcLocalGroupID, 
              pwVcControlWord, 
              pwVcLocalIfMtu, 
              pwVcLocalIfString, 
              pwVcRemoteGroupID, 
              pwVcRemoteControlWord, 
              pwVcRemoteIfMtu, 
              pwVcRemoteIfString, 
              pwVcOutboundVcLabel, 
              pwVcInboundVcLabel, 
              pwVcName, 
              pwVcDescr, 
              pwVcCreateTime, 
              pwVcUpTime, 
              pwVcAdminStatus, 
              pwVcOperStatus, 
              pwVcOutboundOperStatus, 
              pwVcInboundOperStatus, 
              pwVcTimeElapsed, 
              pwVcValidIntervals, 
              pwVcRowStatus, 
                      Pseudo Wire (PW) Management           June 2003 
                            Information Base 


              pwVcStorageType 
            } 
                
     STATUS  current 
     DESCRIPTION 
            "Collection of objects needed for PW VC 
             configuration." 
     ::= { pwVcGroups 1 } 
   
   
   
  pwVcPeformanceGroup OBJECT-GROUP  
     OBJECTS { 
              pwVcPerfCurrentInHCPackets, 
              pwVcPerfCurrentInHCBytes, 
              pwVcPerfCurrentOutHCPackets, 
              pwVcPerfCurrentOutHCBytes, 
               
              pwVcPerfIntervalValidData, 
              pwVcPerfIntervalTimeElapsed, 
              pwVcPerfIntervalInHCPackets, 
              pwVcPerfIntervalInHCBytes, 
              pwVcPerfIntervalOutHCPackets, 
              pwVcPerfIntervalOutHCBytes, 
               
              pwVcPerfTotalInHCPackets, 
              pwVcPerfTotalInHCBytes, 
              pwVcPerfTotalOutHCPackets, 
              pwVcPerfTotalOutHCBytes, 
              pwVcPerfTotalDiscontinuityTime, 
   
              pwVcPerfTotalErrorPackets 
            } 
                
     STATUS  current 
     DESCRIPTION 
            "Collection of objects needed for PW VC 
             performance." 
     ::= { pwVcGroups 2 } 
   
  pwVcMappingTablesGroup OBJECT-GROUP  
     OBJECTS { 
              pwVcIdMappingVcIndex, 
              pwVcPeerMappingVcIndex 
            } 
                
     STATUS  current 
     DESCRIPTION 
            "Collection of objects contained in the reverse 
             mapping tables." 
     ::= { pwVcGroups 3 } 
                      Pseudo Wire (PW) Management           June 2003 
                            Information Base 


   
  -- END of PW-MIB 
   
  END 

-- 
--   Copyright (C) The Internet Society (2000).  All Rights Reserved. 
--   This document and translations of it may be copied and furnished to 
--   others, and derivative works that comment on or otherwise explain 
--   it or assist in its implementation may be prepared, copied, 
--   published and distributed, in whole or in part, without restriction 
--   of any kind, provided that the above copyright notice and this 
--   paragraph are included on all such copies and derivative works.  
--   However, this document itself may not be modified in any way, such 
--   as by removing the copyright notice or references to the Internet 
--   Society or other Internet organizations, except as needed for the 
--   purpose of developing Internet standards in which case the 
--   procedures for copyrights defined in the Internet Standards process 
--   must be followed, or as required to translate it into languages 
--   other than English. 
--   The limited permissions granted above are perpetual and will not be 
--   revoked by the Internet Society or its successors or assigns. This 
--   document and the information contained herein is provided on an "AS 
--   IS" basis and THE INTERNET SOCIETY AND THE INTERNET ENGINEERING 
--   TASK FORCE DISCLAIMS ALL WARRANTIES, EXPRESS OR IMPLIED, INCLUDING 
--   BUT NOT LIMITED TO ANY WARRANTY THAT THE USE OF THE INFORMATION 
--   HEREIN WILL NOT INFRINGE ANY RIGHTS OR ANY IMPLIED WARRANTIES OF 
--   MERCHANTABILITY OR FITNESS FOR A PARTICULAR PURPOSE.
