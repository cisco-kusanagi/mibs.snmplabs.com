-- TyLink NETWORK EXECUTIVE Enterprise MIB
-- Release version 5.00
-- Patch level     00
-- Release Date    December 13, 1995
-- For use with SNAC release version 1.06
--
-- This file contains MIB Definitions for extended management of
-- the TyLink NETWORK EXECUTIVE Product.

     NETEXEC-MIB DEFINITIONS ::= BEGIN

     IMPORTS

     DisplayString
               FROM RFC1213-MIB
     Counter, TimeTicks
               FROM RFC1155-SMI
     OBJECT-TYPE
               FROM RFC-1212
     TRAP-TYPE
               FROM RFC-1215;

-- This MIB module uses the extended OBJECT-TYPE macro.

     internet  OBJECT IDENTIFIER ::= { iso(1) org(3) dod(6) 1 }
     private  OBJECT IDENTIFIER ::= { internet 4 }
     enterprises  OBJECT IDENTIFIER ::= { private 1 }
     tylink  OBJECT IDENTIFIER ::= { enterprises 466 }
     netexec  OBJECT IDENTIFIER ::= { tylink 6 }
     dsucsu  OBJECT IDENTIFIER ::= { netexec 1 }
     tyview  OBJECT IDENTIFIER ::= { netexec 2 }

       -- textual conventions

       --DisplayString ::=
       --    OCTET STRING
       -- This data type is used to model textual information taken
       -- from the NVT ASCII character set.  By convention, objects
       -- with this syntax are declared as having
       --
       --      SIZE (0..255)

       --PhysAddress ::=
       --    OCTET STRING
       -- This data type is used to model media addresses.  For many
       -- types of media, this will be in a binary representation.
       -- For example, an ethernet address would be represented as
       -- a string of 6 octets.


-- *********************************************************************
--                     TYLINK ENTERPRISE SPECIFIC MIB
-- *********************************************************************
--
--      the DSU/CSU group
--

dsucsuSysTable      OBJECT-TYPE
                    SYNTAX      SEQUENCE OF DsucsuSysEntry
                    ACCESS      not-accessible
                    STATUS      mandatory
                    DESCRIPTION
                            "A list of system level attributes describing the
                            addressed node."
                    ::= { dsucsu 1 }

dsucsuSysEntry      OBJECT-TYPE
                    SYNTAX      DsucsuSysEntry
                    ACCESS      not-accessible
                    STATUS      mandatory
                    DESCRIPTION
                            "System Object for a DSU/CSU"
                    INDEX { dsucsuSysSlot, dsucsuSysNode }
                    ::= { dsucsuSysTable 1 }

DsucsuSysEntry ::=
                    SEQUENCE
                    {
                    dsucsuSysSlot
                        INTEGER (1..16),
                    dsucsuSysNode
                        INTEGER (1..255),
                    dsucsuSysName
                        DisplayString (SIZE (0..8)),
                    dsucsuSysType
                        INTEGER,
                    dsucsuSysSoftRev
                        DisplayString (SIZE (0..10)),
                    dsucsuSysHardRev
                        DisplayString (SIZE (0..1)),
                    dsucsuSysNumChan
                        INTEGER (0..4)
                    }

dsucsuSysSlot       OBJECT-TYPE
                    SYNTAX      INTEGER (1..16)
                    ACCESS      read-only
                    STATUS      mandatory
                    DESCRIPTION
                            "The PC port to which the TyView node is attached."
                    ::= { dsucsuSysEntry 1 }

dsucsuSysNode       OBJECT-TYPE
                    SYNTAX      INTEGER (1..255)
                    ACCESS      read-only
                    STATUS      mandatory
                    DESCRIPTION
                            "The node ID: unique per port ID."
                    ::= { dsucsuSysEntry 2 }

dsucsuSysName       OBJECT-TYPE
                    SYNTAX      DisplayString (SIZE (0..8))
                    ACCESS      read-only
                    STATUS      mandatory
                    DESCRIPTION
                            "The unique name of the node accessed"
                    ::= { dsucsuSysEntry 3 }

dsucsuSysType       OBJECT-TYPE
                    SYNTAX      INTEGER
		    {
                    unknown (1),
                    ons400 (2),
                    fns400 (3),
                    ons400e (4),
                    sns400 (5),
                    ons1000 (6),
                    ons232sp (7),
                    ons271sp (8),
                    ons200 (9),
                    ons400n (10),
                    sns256 (11),
                    sns4000 (12),
                    sns1000 (13),
                    ty3410 (14),
                    ty3210 (15),
                    ons1010n (16),
                    ty3250 (17),
                    ty3000n (18),
                    ty3450n (19)
		    }
                    ACCESS      read-only
                    STATUS      mandatory
                    DESCRIPTION
                            "A desciption of the system model: ie.
                            ONS400, FNS400, ONS1000X, BLACK BOX FT1-4"
                    ::= { dsucsuSysEntry 4 }

dsucsuSysSoftRev    OBJECT-TYPE
                    SYNTAX      DisplayString (SIZE (0..10))
                    ACCESS      read-only
                    STATUS      mandatory
                    DESCRIPTION
                            "Displays the Software Revision of the accessed
                            node."
                    ::= { dsucsuSysEntry 5 }

dsucsuSysHardRev    OBJECT-TYPE
                    SYNTAX      DisplayString (SIZE (0..1))
                    ACCESS      read-only
                    STATUS      mandatory
                    DESCRIPTION
                            "Displays the Hardware Revision of the accessed
                            node."
                    ::= { dsucsuSysEntry 6 }

dsucsuSysNumChan    OBJECT-TYPE
                    SYNTAX      INTEGER (0..4)
                    ACCESS      read-only
                    STATUS      mandatory
                    DESCRIPTION
                            "The number of channels that are installed on the
                            node."
                    ::= { dsucsuSysEntry 7 }


dsucsuCfgNetTable 	OBJECT-TYPE
                    SYNTAX      SEQUENCE OF DsucsuCfgNetEntry
                    ACCESS      not-accessible
                    STATUS      mandatory
                    DESCRIPTION
                            "Network Line Configuration"
                    ::= { dsucsu 2 }

dsucsuCfgNetEntry      OBJECT-TYPE
                    SYNTAX      DsucsuCfgNetEntry
                    ACCESS      not-accessible
                    STATUS      mandatory
                    DESCRIPTION
                            "Configuration Object for a DSU/CSU"
                    INDEX { dsucsuCfgNetSlot, dsucsuCfgNetNode, dsucsuCfgNetIndex }
                    ::= { dsucsuCfgNetTable 1 }

DsucsuCfgNetEntry ::=
                    SEQUENCE
                    {
                    dsucsuCfgNetSlot
                        INTEGER (1..16),
                    dsucsuCfgNetNode
                        INTEGER (1..255),
                    dsucsuCfgNetIndex
                        INTEGER (1..2),
                    dsucsuCfgNetInterface
                        INTEGER,     
                    dsucsuCfgNetType
                        INTEGER,
                    dsucsuCfgNetCoding
                        INTEGER,
                    dsucsuCfgNetClockSource
                        INTEGER,
                    dsucsuCfgNetCsuEnable
                        INTEGER,
                    dsucsuCfgNetCsuLBO
                        INTEGER,
                    dsucsuCfgNetCsuDensity
                        INTEGER,
                    dsucsuCfgNetRateMultiples
                        INTEGER,
                    dsucsuCfgNetOutputPulse
                        INTEGER,
                    dsucsuCfgNetTs0
                        INTEGER,
                    dsucsuCfgNetTs16
                        INTEGER
                    } 

dsucsuCfgNetSlot  OBJECT-TYPE
                    SYNTAX      INTEGER (1..16)
                    ACCESS      read-only
                    STATUS      mandatory
                    DESCRIPTION
                            "The NEST slot to which the TyLink card is attached."
                    ::= { dsucsuCfgNetEntry 1 }

dsucsuCfgNetNode  OBJECT-TYPE
                    SYNTAX      INTEGER (1..255)
                    ACCESS      read-only
                    STATUS      mandatory
                    DESCRIPTION
                            "The node ID: unique per port ID."
                    ::= { dsucsuCfgNetEntry 2 }

dsucsuCfgNetIndex OBJECT-TYPE
                    SYNTAX      INTEGER (1..2)
                    ACCESS      read-only
                    STATUS      mandatory
                    DESCRIPTION
                            "The network index."
                    ::= { dsucsuCfgNetEntry 3 }

dsucsuCfgNetInterface OBJECT-TYPE
                    SYNTAX      INTEGER
		    {
                    network (1),
                    dsx-1 (2)
		    }
                    ACCESS      read-write
                    STATUS      mandatory
                    DESCRIPTION
                            "The interface type for 3000N. For a T1 line,
 			     NETWORK or DSX-1 is valid."
                    ::= { dsucsuCfgNetEntry 4 }

dsucsuCfgNetType OBJECT-TYPE
                    SYNTAX      INTEGER
		    {
                    d4 (1),
                    esf-54016 (2),
                    esf-ansi (3),
                    nsms (4),
                    cept-2048 (5)
		    }
                    ACCESS      read-write
                    STATUS      mandatory
                    DESCRIPTION
                            "The aggregate line type."
                    ::= { dsucsuCfgNetEntry 5 }

dsucsuCfgNetCoding OBJECT-TYPE
                    SYNTAX      INTEGER
		    {
                    ami (1),
                    b8zs (2),
                    hdb3 (3)
		    }
                    ACCESS      read-write
                    STATUS      mandatory
                    DESCRIPTION
                            "The encoding scheme for the line. For a T1 line,
 			     AMI and B8ZS are valid. For an E1 line, AMI and
 			     HDB3 are valid."
                    ::= { dsucsuCfgNetEntry 6 }
 
dsucsuCfgNetClockSource OBJECT-TYPE
                    SYNTAX      INTEGER
		    {
                    internal (1),
                    loop (2),
                    external-ch1 (3),
                    external-ch3 (4),
                    station-clock (5)
		    }
                    ACCESS      read-write
                    STATUS      mandatory
                    DESCRIPTION
                            "The aggregate timing for the addressed node."
                    ::= { dsucsuCfgNetEntry 7 }
 
dsucsuCfgNetCsuEnable OBJECT-TYPE
                    SYNTAX      INTEGER
		    {
                    dsx1 (1),
                    csu (2)
		    }
                    ACCESS      read-write
                    STATUS      mandatory
                    DESCRIPTION
                            "Enable/Disable Internal CSU."
                    ::= { dsucsuCfgNetEntry 8 }
 
dsucsuCfgNetCsuLBO OBJECT-TYPE
                    SYNTAX      INTEGER
		    {
                    db-0 (1),
                    db-7-5 (2),
                    db-15 (3)
		    }
                    ACCESS      read-write
                    STATUS      mandatory
                    DESCRIPTION
                            "The setting of the Line Buildout switch. Setting
			    must be db_0 if network interface is DSX-1."
                    ::= { dsucsuCfgNetEntry 9 }
 
dsucsuCfgNetCsuDensity OBJECT-TYPE
                    SYNTAX      INTEGER
		    {
                    none (1),
                    d-1-in-8 (2),
                    d-1-in-16 (3),
                    d-1-in-64 (4),
                    d-12pt5-percent (5)
		    }
                    ACCESS      read-write
                    STATUS      mandatory
                    DESCRIPTION
                            "The setting of the one stuffing option. Inserts
			    a 1 into the 8th, 16th, or 64th bit position
			    (depending on the selection) if the previous 7
			    bits were 0's."
                    ::= { dsucsuCfgNetEntry 10 }
 
dsucsuCfgNetRateMultiples OBJECT-TYPE
                    SYNTAX      INTEGER
		    {
                    nx56 (1),
                    nx64 (2),
                    extended-mixed (3),
                    all-rates (4)
		    }
                    ACCESS      read-write
                    STATUS      mandatory
                    DESCRIPTION
                            "The channel rate multiples for each of the ports."
                    ::= { dsucsuCfgNetEntry 11 }
 
dsucsuCfgNetOutputPulse OBJECT-TYPE
                    SYNTAX      INTEGER
		    {
                    pulse-0-133-ft (1),
                    pulse-133-266-ft (2),
                    pulse-266-399-ft (3),
                    pulse-399-533-ft (4),
                    pulse-533-655-ft (5)
		    }
                    ACCESS      read-write
                    STATUS      mandatory
                    DESCRIPTION
                            "The distance to the CSU in feet."
                    ::= { dsucsuCfgNetEntry 12 }
 
dsucsuCfgNetTs0 OBJECT-TYPE
                    SYNTAX      INTEGER
		    {
                    crc4-enable (1),
                    crc4-disable (2)
		    }
                    ACCESS      read-write
                    STATUS      mandatory
                    DESCRIPTION
                            "The E1 Timeslot 0 value."
                    ::= { dsucsuCfgNetEntry 13 }
 
dsucsuCfgNetTs16 OBJECT-TYPE
                    SYNTAX      INTEGER
		    {
                    data (1),
                    multifr-align (2)
		    }
                    ACCESS      read-write
                    STATUS      mandatory
                    DESCRIPTION
                            "The E1 Timeslot 16 value. Valid values are
			     data and multiframe alignment."
                    ::= { dsucsuCfgNetEntry 14 }
 
-- dsucsuCfgNetCoTable { dsucsu 3 } not implemented

dsucsuCfgDteChanTable  OBJECT-TYPE
                    SYNTAX      SEQUENCE OF DsucsuCfgDteChanEntry
                    ACCESS      not-accessible
                    STATUS      mandatory
                    DESCRIPTION
                            "DTE Channel Configuration"
                    ::= { dsucsu 4 }

dsucsuCfgDteChanEntry      OBJECT-TYPE
                    SYNTAX      DsucsuCfgDteChanEntry
                    ACCESS      not-accessible
                    STATUS      mandatory
                    DESCRIPTION
                            "DTE Channel Configuration Object for a DSU/CSU"
                    INDEX { dsucsuCfgDteChanSlot, dsucsuCfgDteChanNode, dsucsuCfgDteChanIndex }
                    ::= { dsucsuCfgDteChanTable 1 }

DsucsuCfgDteChanEntry ::=
                    SEQUENCE
                    {
                    dsucsuCfgDteChanSlot
                        INTEGER (1..16),
                    dsucsuCfgDteChanNode
                        INTEGER (1..255),
                    dsucsuCfgDteChanIndex
                        INTEGER (1..4),
                    dsucsuCfgDteChanType
                        INTEGER,
                    dsucsuCfgDteChanRate
                        INTEGER,
                    dsucsuCfgDteChanEncoding
                        INTEGER,
                    dsucsuCfgDteChanStartDs0
                        INTEGER,
                    dsucsuCfgDteChanCtrlSignal
                        INTEGER,
                    dsucsuCfgDteChanTiming
                        INTEGER,
                    dsucsuCfgDteChanClockInvert
                        INTEGER,
                    dsucsuCfgDteChanDataInvert
                        INTEGER
                    } 

dsucsuCfgDteChanSlot  OBJECT-TYPE
                    SYNTAX      INTEGER (1..16)
                    ACCESS      read-only
                    STATUS      mandatory
                    DESCRIPTION
                            "The PC port to which the TyView node is attached."
                    ::= { dsucsuCfgDteChanEntry 1 }

dsucsuCfgDteChanNode  OBJECT-TYPE
                    SYNTAX      INTEGER (1..255)
                    ACCESS      read-only
                    STATUS      mandatory
                    DESCRIPTION
                            "The node ID: unique per port ID."
                    ::= { dsucsuCfgDteChanEntry 2 }

dsucsuCfgDteChanIndex OBJECT-TYPE
                    SYNTAX      INTEGER (1..4)
                    ACCESS      read-only
                    STATUS      mandatory
                    DESCRIPTION
                            "The channel index."
                    ::= { dsucsuCfgDteChanEntry 3 }

dsucsuCfgDteChanType OBJECT-TYPE
                    SYNTAX      INTEGER
		    {
                    rs232 (1),
                    v35 (2),
                    rs449 (3),
                    none (4)
		    }
                    ACCESS      read-write
                    STATUS      mandatory
                    DESCRIPTION
                            "The Dte channel type." 
                    ::= { dsucsuCfgDteChanEntry 4 }
 
dsucsuCfgDteChanRate OBJECT-TYPE
                    SYNTAX      INTEGER
                    ACCESS      read-write 
                    STATUS      mandatory
                    DESCRIPTION
                            "The Data rate in kilobits per second. The rate is
			    dependent on the setting of the Aggregate DTE
			    channel multiples."
                    ::= { dsucsuCfgDteChanEntry 5 }
 
dsucsuCfgDteChanEncoding OBJECT-TYPE
                    SYNTAX      INTEGER
		    {
                    b7s (1),
                    alt (2),
                    clr (3)
		    }
                    ACCESS      read-write
                    STATUS      mandatory
                    DESCRIPTION
                            "The Channel encoding."
                    ::= { dsucsuCfgDteChanEntry 6 }
 
dsucsuCfgDteChanStartDs0 OBJECT-TYPE
                    SYNTAX      INTEGER
                    ACCESS      read-write
                    STATUS      mandatory
                    DESCRIPTION
                            "The starting DS0 for the addressed channel's data."
                    ::= { dsucsuCfgDteChanEntry 7 }
 
dsucsuCfgDteChanCtrlSignal OBJECT-TYPE
                    SYNTAX      INTEGER
		    {
                    rts-on (1),
                    rts-switch (2),
                    cts-on (3),
                    cts-auto (4)
		    }
                    ACCESS      read-write
                    STATUS      mandatory
                    DESCRIPTION
                            "The control signal state."
                    ::= { dsucsuCfgDteChanEntry 8 }
 
dsucsuCfgDteChanTiming OBJECT-TYPE
                    SYNTAX      INTEGER
		    {
                    loop1 (1),
                    loop2 (2)
		    }
                    ACCESS      read-write
                    STATUS      mandatory
                    DESCRIPTION
                            "The DTE channel Timing."
                    ::= { dsucsuCfgDteChanEntry 9 }
 
dsucsuCfgDteChanClockInvert OBJECT-TYPE
                    SYNTAX      INTEGER
		    {
                    off (1),
                    on (2)
		    }
                    ACCESS      read-write
                    STATUS      mandatory
                    DESCRIPTION
                            "The DTE channel Clock Invert setting."
                    ::= { dsucsuCfgDteChanEntry 10 }
 
dsucsuCfgDteChanDataInvert OBJECT-TYPE
                    SYNTAX      INTEGER
		    {
                    off (1),
                    on (2)
		    }
                    ACCESS      read-write
                    STATUS      mandatory
                    DESCRIPTION
                            "The DTE channel Data Invert setting."
                    ::= { dsucsuCfgDteChanEntry 11 }
 
dsucsuCfgFrmChanTable  OBJECT-TYPE
                    SYNTAX      SEQUENCE OF DsucsuCfgFrmChanEntry
                    ACCESS      not-accessible
                    STATUS      mandatory
                    DESCRIPTION
                            "Framed Channel Configuration"
                    ::= { dsucsu 5 }

dsucsuCfgFrmChanEntry      OBJECT-TYPE
                    SYNTAX      DsucsuCfgFrmChanEntry
                    ACCESS      not-accessible
                    STATUS      mandatory
                    DESCRIPTION
                            "Framed Channel Configuration Object for a DSU/CSU"
                    INDEX { dsucsuCfgFrmChanSlot, dsucsuCfgFrmChanNode, dsucsuCfgFrmChanIndex }
                    ::= { dsucsuCfgFrmChanTable 1 }

DsucsuCfgFrmChanEntry ::=
                    SEQUENCE
                    {
                    dsucsuCfgFrmChanSlot
                        INTEGER (1..16),
                    dsucsuCfgFrmChanNode
                        INTEGER (1..255),
                    dsucsuCfgFrmChanIndex
                        INTEGER (1..4),
                    dsucsuCfgFrmChanType
                        INTEGER,
                    dsucsuCfgFrmChanNumDs0
                        INTEGER,
                    dsucsuCfgFrmChanEncoding
                        INTEGER,
                    dsucsuCfgFrmChanStartDs0
                        INTEGER,
                    dsucsuCfgFrmChanDteStartDs0
                        INTEGER,
                    dsucsuCfgFrmChanMapping
                        INTEGER,
                    dsucsuCfgFrmChanDs0Type
                        INTEGER,
                    dsucsuCfgFrmChanFrameType
                        INTEGER,
                    dsucsuCfgFrmChanOutputPulse
                        INTEGER,
                    dsucsuCfgFrmChanNetMapping
                        INTEGER
                    } 

dsucsuCfgFrmChanSlot  OBJECT-TYPE
                    SYNTAX      INTEGER (1..16)
                    ACCESS      read-only
                    STATUS      mandatory
                    DESCRIPTION
                            "The PC port to which the TyView node is attached."
                    ::= { dsucsuCfgFrmChanEntry 1 }

dsucsuCfgFrmChanNode  OBJECT-TYPE
                    SYNTAX      INTEGER (1..255)
                    ACCESS      read-only
                    STATUS      mandatory
                    DESCRIPTION
                            "The node ID: unique per port ID."
                    ::= { dsucsuCfgFrmChanEntry 2 }

dsucsuCfgFrmChanIndex OBJECT-TYPE
                    SYNTAX      INTEGER (1..4)
                    ACCESS      read-only
                    STATUS      mandatory
                    DESCRIPTION
                            "The channel index."
                    ::= { dsucsuCfgFrmChanEntry 3 }

dsucsuCfgFrmChanType OBJECT-TYPE
                    SYNTAX      INTEGER
		    {
                    pbx (1),
                    none (2)
		    }
                    ACCESS      read-only
                    STATUS      mandatory
                    DESCRIPTION
                            "The framed channel type." 
                    ::= { dsucsuCfgFrmChanEntry 4 }
 
dsucsuCfgFrmChanNumDs0 OBJECT-TYPE
                    SYNTAX      INTEGER
                    ACCESS      read-write
                    STATUS      mandatory
                    DESCRIPTION
                            "The number of DS0's on the network side."
                    ::= { dsucsuCfgFrmChanEntry 5 }
 
dsucsuCfgFrmChanEncoding OBJECT-TYPE
                    SYNTAX      INTEGER
		    {
                    ami (1),
                    b8zs (2)
		    }
                    ACCESS      read-write
                    STATUS      mandatory
                    DESCRIPTION
                            "The channel line code."
                    ::= { dsucsuCfgFrmChanEntry 6 }
 
dsucsuCfgFrmChanStartDs0 OBJECT-TYPE
                    SYNTAX      INTEGER
                    ACCESS      read-write
                    STATUS      mandatory
                    DESCRIPTION
                            "The starting DS0 on the network side."
                    ::= { dsucsuCfgFrmChanEntry 7 }
 
dsucsuCfgFrmChanDteStartDs0 OBJECT-TYPE
                    SYNTAX      INTEGER
                    ACCESS      read-write
                    STATUS      mandatory
                    DESCRIPTION
                            "The starting DS0 on the framed channel."
                    ::= { dsucsuCfgFrmChanEntry 8 }
 
dsucsuCfgFrmChanMapping OBJECT-TYPE
                    SYNTAX      INTEGER
		    {
                    ctg-ds0 (1),
                    alt-ds0 (2)
		    }
                    ACCESS      read-write
                    STATUS      mandatory
                    DESCRIPTION
                            "The Framed channel Mapping."
                    ::= { dsucsuCfgFrmChanEntry 9 }
 
dsucsuCfgFrmChanDs0Type OBJECT-TYPE
                    SYNTAX      INTEGER
		    {
                    data (1),
                    voice (2),
                    mixed (3)
		    }
                    ACCESS      read-write
                    STATUS      mandatory
                    DESCRIPTION
                            "The Framed channel DS0 Type."
                    ::= { dsucsuCfgFrmChanEntry 10 }
 
dsucsuCfgFrmChanFrameType OBJECT-TYPE
                    SYNTAX      INTEGER
		    {
                    d4 (1),
                    esf (2)
		    }
                    ACCESS      read-write
                    STATUS      mandatory
                    DESCRIPTION
                            "The Framed channel Frame Type."
                    ::= { dsucsuCfgFrmChanEntry 11 }
 
dsucsuCfgFrmChanOutputPulse OBJECT-TYPE
                    SYNTAX      INTEGER
		    {
                    pulse-0-133-ft (1),
                    pulse-133-266-ft (2),
                    pulse-266-399-ft (3),
                    pulse-399-533-ft (4),
                    pulse-533-655-ft (5)
		    }
                    ACCESS      read-write
                    STATUS      mandatory
                    DESCRIPTION
                            "The cabling distance from the PBX to the PBX
			    channel port in feet."
                    ::= { dsucsuCfgFrmChanEntry 12 }
 
dsucsuCfgFrmChanNetMapping OBJECT-TYPE
                    SYNTAX      INTEGER
		    {
                    ctg-ds0 (1),
                    alt-ds0 (2)
		    }
                    ACCESS      read-write
                    STATUS      mandatory
                    DESCRIPTION
                            "The Network Ds0 Mapping."
                    ::= { dsucsuCfgFrmChanEntry 13 }
 
-- dsucsuCfgSwChanTable { dsucsu 6 } not implemented

dsucsuConfigSupTable  OBJECT-TYPE
                    SYNTAX      SEQUENCE OF DsucsuConfigSupEntry
                    ACCESS      not-accessible
                    STATUS      mandatory
                    DESCRIPTION
                            "Inband Supervisory Channel Configuration"
                    ::= { dsucsu 7 }

dsucsuConfigSupEntry      OBJECT-TYPE
                    SYNTAX      DsucsuConfigSupEntry
                    ACCESS      not-accessible
                    STATUS      mandatory
                    DESCRIPTION
                            "Inband Supervisory Configuration Object for a DSU/CSU"
                    INDEX { dsucsuConfigSupSlot, dsucsuConfigSupNode, dsucsuConfigSupIndex }
                    ::= { dsucsuConfigSupTable 1 }

DsucsuConfigSupEntry ::=
                    SEQUENCE
                    {
                    dsucsuConfigSupSlot
                        INTEGER (1..16),
                    dsucsuConfigSupNode
                        INTEGER (1..255),
                    dsucsuConfigSupIndex
                        INTEGER (1..2),
                    dsucsuConfigSupDs0
                        INTEGER
                    } 

dsucsuConfigSupSlot  OBJECT-TYPE
                    SYNTAX      INTEGER (1..16)
                    ACCESS      read-only
                    STATUS      mandatory
                    DESCRIPTION
                            "The PC port to which the TyView node is attached."
                    ::= { dsucsuConfigSupEntry 1 }

dsucsuConfigSupNode  OBJECT-TYPE
                    SYNTAX      INTEGER (1..255)
                    ACCESS      read-only
                    STATUS      mandatory
                    DESCRIPTION
                            "The node ID: unique per port ID."
                    ::= { dsucsuConfigSupEntry 2 }

dsucsuConfigSupIndex OBJECT-TYPE
                    SYNTAX      INTEGER (1..2)
                    ACCESS      read-only
                    STATUS      mandatory
                    DESCRIPTION
                            "The Supervisory channel index.
			     Index 1 refers to supervisory channel A.
			     Index 2 refers to supervisory channel B."
                    ::= { dsucsuConfigSupEntry 3 }

dsucsuConfigSupDs0 OBJECT-TYPE
                    SYNTAX      INTEGER
                    ACCESS      read-write
                    STATUS      mandatory
                    DESCRIPTION
                            "The DS0 to place the Supervisory channel in."
                    ::= { dsucsuConfigSupEntry 4 }

dsucsuCfgSupAuxTable  OBJECT-TYPE
                    SYNTAX      SEQUENCE OF DsucsuCfgSupAuxEntry
                    ACCESS      not-accessible
                    STATUS      mandatory
                    DESCRIPTION
                            "Auxillary Supervisory Channel Configuration"
                    ::= { dsucsu 8 }

dsucsuCfgSupAuxEntry      OBJECT-TYPE
                    SYNTAX      DsucsuCfgSupAuxEntry
                    ACCESS      not-accessible
                    STATUS      mandatory
                    DESCRIPTION
                            "Auxilary Supervisory Configuration Object for a DSU/CSU"
                    INDEX { dsucsuCfgSupAuxSlot, dsucsuCfgSupAuxNode, dsucsuCfgSupAuxIndex }
                    ::= { dsucsuCfgSupAuxTable 1 }

DsucsuCfgSupAuxEntry ::=
                    SEQUENCE
                    {
                    dsucsuCfgSupAuxSlot
                        INTEGER (1..16),
                    dsucsuCfgSupAuxNode
                        INTEGER (1..255),
                    dsucsuCfgSupAuxIndex
                        INTEGER (1..2),
                     dsucsuCfgSupAuxFdl
                        INTEGER
                    } 

dsucsuCfgSupAuxSlot  OBJECT-TYPE
                    SYNTAX      INTEGER (1..16)
                    ACCESS      read-only
                    STATUS      mandatory
                    DESCRIPTION
                            "The PC port to which the TyView node is attached."
                    ::= { dsucsuCfgSupAuxEntry 1 }

dsucsuCfgSupAuxNode  OBJECT-TYPE
                    SYNTAX      INTEGER (1..255)
                    ACCESS      read-only
                    STATUS      mandatory
                    DESCRIPTION
                            "The node ID: unique per port ID."
                    ::= { dsucsuCfgSupAuxEntry 2 }

dsucsuCfgSupAuxIndex OBJECT-TYPE
                    SYNTAX      INTEGER (1..2)
                    ACCESS      read-only
                    STATUS      mandatory
                    DESCRIPTION
                            "Auxillary Supervisory Channel Configuration Index
			     Index 1 refers to FDL supervisory on PORT 1.
			     Index 2 refers to FDL supervisory on PORT 2."

                    ::= { dsucsuCfgSupAuxEntry 3 }

dsucsuCfgSupAuxFdl OBJECT-TYPE
                    SYNTAX      INTEGER
		    {
		    off (1),
		    on (2)
		    }
                    ACCESS      read-write
                    STATUS      mandatory
                    DESCRIPTION
                            "Places the supervisory link bits within the
			    Facility Data Link bits of the Extended Superframe."
                    ::= { dsucsuCfgSupAuxEntry 4 }

dsucsuActvConfTable OBJECT-TYPE
                    SYNTAX      SEQUENCE OF DsucsuActvConfEntry
                    ACCESS      not-accessible
                    STATUS      mandatory
                    DESCRIPTION
                            "Activate a stored configuration on the selected 
                            node."
                    ::= { dsucsu 9 }

dsucsuActvConfEntry OBJECT-TYPE
                    SYNTAX      DsucsuActvConfEntry
                    ACCESS      not-accessible
                    STATUS      mandatory
                    DESCRIPTION
                            "An activate configuration entry."
                    INDEX { dsucsuActvConfSlot, dsucsuActvConfNode }
                    ::= { dsucsuActvConfTable 1 }

DsucsuActvConfEntry ::=
                    SEQUENCE
                    {
                    dsucsuActvConfSlot
                        INTEGER (1..16),
                    dsucsuActvConfNode
                        INTEGER (1..255),
                    dsucsuActvConfIndex
                        INTEGER (1..4)
                    } 

dsucsuActvConfSlot  OBJECT-TYPE
                    SYNTAX      INTEGER (1..16)
                    ACCESS      read-only
                    STATUS      mandatory
                    DESCRIPTION
                            "The PC port to which the TyView node is attached."
                    ::= { dsucsuActvConfEntry 1 }

dsucsuActvConfNode  OBJECT-TYPE
                    SYNTAX      INTEGER (1..255)
                    ACCESS      read-only
                    STATUS      mandatory
                    DESCRIPTION
                            "The node ID: unique per port ID."
                    ::= { dsucsuActvConfEntry 2 }

dsucsuActvConfIndex OBJECT-TYPE
                    SYNTAX      INTEGER (1..4)
                    ACCESS      write-only
                    STATUS      mandatory
                    DESCRIPTION
                            "Activate one of the four stored configurations."
                    ::= { dsucsuActvConfEntry 3 }

dsucsuEventDesTable OBJECT-TYPE
                    SYNTAX      SEQUENCE OF DsucsuEventDesEntry
                    ACCESS      not-accessible
                    STATUS      mandatory
                    DESCRIPTION
                            "Table of event destinations. Events or alarms 
                            detected by a node can be reported to up to two 
                            destinations.  The operator can set or clear either 
                            or both of these destinations via this Table."
                    ::= { dsucsu 10 }

dsucsuEventDesEntry OBJECT-TYPE
                    SYNTAX      DsucsuEventDesEntry
                    ACCESS      not-accessible
                    STATUS      mandatory
                    DESCRIPTION
                            "Entry in the table of event destinations."
                    INDEX { dsucsuEventDesSlot, dsucsuEventDesNode }
                    ::= { dsucsuEventDesTable 1 }

DsucsuEventDesEntry ::=
                     SEQUENCE
                     {
                     dsucsuEventDesSlot
                         INTEGER (1..16),
                     dsucsuEventDesNode
                         INTEGER (1..255),
                     dsucsuEventNameIndx
                         DisplayString (SIZE (0..8)),
                     dsucsuEventDesName1
                         DisplayString (SIZE (0..8)),
                     dsucsuEventDesName2
                         DisplayString (SIZE (0..8)),
                     dsucsuEventClrDest
                         INTEGER
                     }

dsucsuEventDesSlot  OBJECT-TYPE
                    SYNTAX      INTEGER (1..16)
                    ACCESS      read-only
                    STATUS      mandatory
                    DESCRIPTION
                            "The PC port to which the TyView node is attached."
                    ::= { dsucsuEventDesEntry 1 }

dsucsuEventDesNode  OBJECT-TYPE
                    SYNTAX      INTEGER (1..255)
                    ACCESS      read-only
                    STATUS      mandatory
                    DESCRIPTION
                            "The node ID: unique per port ID."
                    ::= { dsucsuEventDesEntry 2 }

dsucsuEventNameIndx OBJECT-TYPE
                    SYNTAX      DisplayString (SIZE (0..8))
                    ACCESS      read-only
                    STATUS      mandatory
                    DESCRIPTION
                            "The unique name of the node accessed."
                    ::= { dsucsuEventDesEntry 3 }

dsucsuEventDesName1 OBJECT-TYPE
                    SYNTAX      DisplayString (SIZE (0..8))
                    ACCESS      read-write
                    STATUS      mandatory
                    DESCRIPTION
                            "The name of the node/PC where the alarms will be 
                            sent to."
                    ::= { dsucsuEventDesEntry 4 }

dsucsuEventDesName2 OBJECT-TYPE
                    SYNTAX      DisplayString (SIZE (0..8))
                    ACCESS      read-write
                    STATUS      mandatory
                    DESCRIPTION
                            "The name of the alternate node/PC where the alarms
                             will be sent to."
                    ::= { dsucsuEventDesEntry 5 }

dsucsuEventClrDest  OBJECT-TYPE
                    SYNTAX      INTEGER
                    {
                    clearDest1 (1),
                    clearDest2 (2),
                    clearBothDest (3)
                    }
                    ACCESS      write-only
                    STATUS      mandatory
                    DESCRIPTION
                            "Clears the destination(s) for the reporting of
                            alarms."
                    ::= { dsucsuEventDesEntry 6 }

dsucsuCfgMaintTable  OBJECT-TYPE
                    SYNTAX      SEQUENCE OF DsucsuCfgMaintEntry
                    ACCESS      not-accessible
                    STATUS      mandatory
                    DESCRIPTION
                            "Maint. Port Configuration"
                    ::= { dsucsu 11 }

dsucsuCfgMaintEntry      OBJECT-TYPE
                    SYNTAX      DsucsuCfgMaintEntry
                    ACCESS      not-accessible
                    STATUS      mandatory
                    DESCRIPTION
                            "Maint. Port Configuration Object"
                    INDEX { dsucsuCfgMaintSlot, dsucsuCfgMaintNode }
                    ::= { dsucsuCfgMaintTable 1 }

DsucsuCfgMaintEntry ::=
                    SEQUENCE
                    {
                    dsucsuCfgMaintSlot
                        INTEGER (1..16),
                    dsucsuCfgMaintNode
                        INTEGER (1..255),
                    dsucsuCfgMaintChanType
                        INTEGER,
                    dsucsuCfgMaintFlowCtrl
                        INTEGER,
                    dsucsuCfgMaintStopBits
                        INTEGER,
                    dsucsuCfgMaintParity
                        INTEGER,
                    dsucsuCfgMaintDataBits
                        INTEGER,
                    dsucsuCfgMaintBaud
                        INTEGER
                    } 

dsucsuCfgMaintSlot  OBJECT-TYPE
                    SYNTAX      INTEGER (1..16)
                    ACCESS      read-only
                    STATUS      mandatory
                    DESCRIPTION
                            "The PC port to which the TyView node is attached."
                    ::= { dsucsuCfgMaintEntry 1 }

dsucsuCfgMaintNode  OBJECT-TYPE
                    SYNTAX      INTEGER (1..255)
                    ACCESS      read-only
                    STATUS      mandatory
                    DESCRIPTION
                            "The node ID: unique per port ID."
                    ::= { dsucsuCfgMaintEntry 2 }

dsucsuCfgMaintChanType OBJECT-TYPE
                    SYNTAX      INTEGER
		    {
		    disabled (1),
		    nsms (2),
		    ascii (3),
		    alarm (4),
		    ext-event (5)
		    }
                    ACCESS      read-write
                    STATUS      mandatory
                    DESCRIPTION
                            "The type of data passed over the Maint. port."
                    ::= { dsucsuCfgMaintEntry 3 }

dsucsuCfgMaintFlowCtrl OBJECT-TYPE
                    SYNTAX      INTEGER
		    {
		    off (1),
		    on (2)
		    }
                    ACCESS      read-write
                    STATUS      mandatory
                    DESCRIPTION
                            "Flow Control for the Maint. port."
                    ::= { dsucsuCfgMaintEntry 4 }

dsucsuCfgMaintStopBits OBJECT-TYPE
                    SYNTAX      INTEGER
		    {
		    stopbits-1 (1),
		    stopbits-1-5 (2),
		    stopbits-2 (3)
		    }
                    ACCESS      read-write
                    STATUS      mandatory
                    DESCRIPTION
                            "Number of Stopbits for the Maint. port."
                    ::= { dsucsuCfgMaintEntry 5 }

dsucsuCfgMaintParity OBJECT-TYPE
                    SYNTAX      INTEGER
		    {
		    none (1),
		    odd (2),
		    even (3)
		    }
                    ACCESS      read-write
                    STATUS      mandatory
                    DESCRIPTION
                            "Parity for the Maint. port."
                    ::= { dsucsuCfgMaintEntry 6 }

dsucsuCfgMaintDataBits OBJECT-TYPE
                    SYNTAX      INTEGER
		    {
		    databits-7 (1),
		    databits-8 (2)
		    }
                    ACCESS      read-write
                    STATUS      mandatory
                    DESCRIPTION
                            "Databits for the Maint. port."
                    ::= { dsucsuCfgMaintEntry 7 }

dsucsuCfgMaintBaud OBJECT-TYPE
                    SYNTAX      INTEGER
		    {
		    baud-1200 (1),
		    baud-2400 (2),
		    baud-4800 (3),
		    baud-9600 (4)
		    }
                    ACCESS      read-write
                    STATUS      mandatory
                    DESCRIPTION
                            "Baud rate for the Maint. port."
                    ::= { dsucsuCfgMaintEntry 8 }

dsucsuCfgCommTable  OBJECT-TYPE
                    SYNTAX      SEQUENCE OF DsucsuCfgCommEntry
                    ACCESS      not-accessible
                    STATUS      mandatory
                    DESCRIPTION
                            "Communication Port Configuration"
                    ::= { dsucsu 12 }

dsucsuCfgCommEntry      OBJECT-TYPE
                    SYNTAX      DsucsuCfgCommEntry
                    ACCESS      not-accessible
                    STATUS      mandatory
                    DESCRIPTION
                            "Communication Port Configuration Object"
                    INDEX { dsucsuCfgCommSlot, dsucsuCfgCommNode }
                    ::= { dsucsuCfgCommTable 1 }

DsucsuCfgCommEntry ::=
                    SEQUENCE
                    {
                    dsucsuCfgCommSlot
                        INTEGER (1..16),
                    dsucsuCfgCommNode
                        INTEGER (1..255),
                    dsucsuCfgCommChanType
                        INTEGER,
                    dsucsuCfgCommFlowCtrl
                        INTEGER,
                    dsucsuCfgCommStopBits
                        INTEGER,
                    dsucsuCfgCommParity
                        INTEGER,
                    dsucsuCfgCommDataBits
                        INTEGER,
                    dsucsuCfgCommBaud
                        INTEGER
                    } 

dsucsuCfgCommSlot  OBJECT-TYPE
                    SYNTAX      INTEGER (1..16)
                    ACCESS      read-only
                    STATUS      mandatory
                    DESCRIPTION
                            "The PC port to which the TyView node is attached."
                    ::= { dsucsuCfgCommEntry 1 }

dsucsuCfgCommNode  OBJECT-TYPE
                    SYNTAX      INTEGER (1..255)
                    ACCESS      read-only
                    STATUS      mandatory
                    DESCRIPTION
                            "The node ID: unique per port ID."
                    ::= { dsucsuCfgCommEntry 2 }

dsucsuCfgCommChanType OBJECT-TYPE
                    SYNTAX      INTEGER
		    {
		    disabled (1),
		    nsms (2),
		    ascii (3),
		    alarm (4),
		    ext-event (5)
		    }
                    ACCESS      read-write
                    STATUS      mandatory
                    DESCRIPTION
                            "The type of data passed over the Communication port."
                    ::= { dsucsuCfgCommEntry 3 }

dsucsuCfgCommFlowCtrl OBJECT-TYPE
                    SYNTAX      INTEGER
		    {
		    off (1),
		    on (2)
		    }
                    ACCESS      read-write
                    STATUS      mandatory
                    DESCRIPTION
                            "Flow Control for the Communication port."
                    ::= { dsucsuCfgCommEntry 4 }

dsucsuCfgCommStopBits OBJECT-TYPE
                    SYNTAX      INTEGER
		    {
		    stopbits-1 (1),
		    stopbits-1-5 (2),
		    stopbits-2 (3)
		    }
                    ACCESS      read-write
                    STATUS      mandatory
                    DESCRIPTION
                            "Number of Stopbits for the Communication port."
                    ::= { dsucsuCfgCommEntry 5 }

dsucsuCfgCommParity OBJECT-TYPE
                    SYNTAX      INTEGER
		    {
		    none (1),
		    odd (2),
		    even (3)
		    }
                    ACCESS      read-write
                    STATUS      mandatory
                    DESCRIPTION
                            "Parity for the Communication port."
                    ::= { dsucsuCfgCommEntry 6 }

dsucsuCfgCommDataBits OBJECT-TYPE
                    SYNTAX      INTEGER
		    {
		    databits-7 (1),
		    databits-8 (2)
		    }
                    ACCESS      read-write
                    STATUS      mandatory
                    DESCRIPTION
                            "Databits for the Communication port."
                    ::= { dsucsuCfgCommEntry 7 }

dsucsuCfgCommBaud OBJECT-TYPE
                    SYNTAX      INTEGER
		    {
		    baud-1200 (1),
		    baud-2400 (2),
		    baud-4800 (3),
		    baud-9600 (4)
		    }
                    ACCESS      read-write
                    STATUS      mandatory
                    DESCRIPTION
                            "Baud rate for the Communication port."
                    ::= { dsucsuCfgCommEntry 8 }

dsucsuCfgBrdTable   OBJECT-TYPE
                    SYNTAX      SEQUENCE OF DsucsuCfgBrdEntry
                    ACCESS      not-accessible
                    STATUS      mandatory
                    DESCRIPTION
                            "Network timing for 3000N board."
                    ::= { dsucsu 13 }

dsucsuCfgBrdEntry   OBJECT-TYPE
                    SYNTAX      DsucsuCfgBrdEntry
                    ACCESS      not-accessible
                    STATUS      mandatory
                    DESCRIPTION
                            "Board Timing Configuration Object."
                    INDEX { dsucsuCfgBrdSlot, dsucsuCfgBrdNode }
                    ::= { dsucsuCfgBrdTable 1 }

DsucsuCfgBrdEntry ::=
                    SEQUENCE
                    {
                    dsucsuCfgBrdSlot
                        INTEGER (1..16),
                    dsucsuCfgBrdNode
                        INTEGER (1..255),
                    dsucsuCfgBrdTiming
                        INTEGER
                    }

dsucsuCfgBrdSlot      OBJECT-TYPE
                    SYNTAX      INTEGER (1..16)
                    ACCESS      read-only
                    STATUS      mandatory
                    DESCRIPTION
                            "The PC port to which the TyView node is attached."
                    ::= { dsucsuCfgBrdEntry 1 }

dsucsuCfgBrdNode      OBJECT-TYPE
                    SYNTAX      INTEGER (1..255)
                    ACCESS      read-only
                    STATUS      mandatory
                    DESCRIPTION
                            "The node ID: unique per port ID."
                    ::= { dsucsuCfgBrdEntry 2 }

dsucsuCfgBrdTiming     OBJECT-TYPE
                    SYNTAX      INTEGER
                    {
                    master (1),
                    port1 (2),
                    port2 (3),
                    port3 (4),
                    port4 (5)
                    }
                    ACCESS      read-write
                    STATUS      mandatory
                    DESCRIPTION
                            "The Board Level Timing for a 3000N."
                    ::= { dsucsuCfgBrdEntry 3 }

--
--       The Connection Configuration Table
--           The Connection Configuration table contains methods for
--           assigning T1 network bandwidth to ports. In auto entry mode
--           the user provides a starting DS0 and the node assigns
--           sequential, contiguous, DS0s; all of the same type (data or
--           voice). In manual entry the user configures each DS0 
--           seperately. In manual mode the DS0s may be assigned 
--           discontiguously and could be a mix of voice and data 
--           circuits. This table also includes deletion and
--           validation utilities.

dsucsuCfgDacsTable  OBJECT IDENTIFIER ::= { dsucsu 14 }

--              "Provides T1 network index, starting DS0 and DTE port number
--              for the node to automatically assign the proper amount of
--              bandwidth. Bandwidth requirements are defined by the DTE 
--              Data Rate and DTE Channel Density selections."

dsucsuCfgAutoAssignTable   OBJECT-TYPE
                    SYNTAX      SEQUENCE OF DsucsuCfgAutoAssignEntry
                    ACCESS      not-accessible
                    STATUS      mandatory
                    DESCRIPTION
                            "Automatically assign the proper amount of bandwidth."
                    ::= { dsucsuCfgDacsTable 1 }


dsucsuCfgAutoAssignEntry   OBJECT-TYPE
                    SYNTAX      DsucsuCfgAutoAssignEntry
                    ACCESS      not-accessible
                    STATUS      mandatory
                    DESCRIPTION
                            "DACS auto assign Configuration Object."
                    INDEX { dsucsuConnAutoSlot, dsucsuConnAutoNode, dsucsuConnAutoSrcPort }
                    ::= { dsucsuCfgAutoAssignTable 1 }

DsucsuCfgAutoAssignEntry ::=
                    SEQUENCE
                    {
                    dsucsuConnAutoSlot
                        INTEGER (1..16),
                    dsucsuConnAutoNode
                        INTEGER (1..255),
                    dsucsuConnAutoSrcPort
                        INTEGER (1..4),
                    dsucsuConnAutoStartDS0
                        INTEGER,
                    dsucsuConnAutoDestPort
                        INTEGER,
                    dsucsuConnAutoType
                        INTEGER,
                    dsucsuConnDteRate
                        INTEGER (0..1536000),
                    dsucsuConnDteDensity
                        INTEGER,
                    dsucsuConnDs0Required
                        INTEGER (0..24),
                    dsucsuConnAutoStatus
                        INTEGER,
                    dsucsuConnAutoUpdateCmd
                        INTEGER
                    }

dsucsuConnAutoSlot  OBJECT-TYPE
                    SYNTAX      INTEGER (1..16)
                    ACCESS      read-only
                    STATUS      mandatory
                    DESCRIPTION
                            "The PC port to which the TyView node is attached."
                    ::= { dsucsuCfgAutoAssignEntry 1 }

dsucsuConnAutoNode  OBJECT-TYPE
                    SYNTAX      INTEGER (1..255)
                    ACCESS      read-only
                    STATUS      mandatory
                    DESCRIPTION
                            "The node ID: unique per port ID."
                    ::= { dsucsuCfgAutoAssignEntry 2 }

dsucsuConnAutoSrcPort OBJECT-TYPE
                    SYNTAX      INTEGER (1..4)
                    ACCESS      read-only
                    STATUS      mandatory
                    DESCRIPTION
                            "Index to the 3000N source port of interest. 3000N supports
                             two DTE-V35/RS-499 DATA ports (P3-P4)."
                    ::= { dsucsuCfgAutoAssignEntry 3 }

dsucsuConnAutoStartDS0            OBJECT-TYPE
	  SYNTAX        INTEGER
			{
			ds0-01        (1),
			ds0-02        (2),
			ds0-03        (3),
			ds0-04        (4),
			ds0-05        (5),
			ds0-06        (6),
			ds0-07        (7),
			ds0-08        (8),
			ds0-09        (9),
			ds0-10        (10),
			ds0-11        (11),
			ds0-12        (12),
			ds0-13        (13),
			ds0-14        (14),
			ds0-15        (15),
			ds0-16        (16),
			ds0-17        (17),
			ds0-18        (18),
			ds0-19        (19),
			ds0-20        (20),
			ds0-21        (21),
			ds0-22        (22),
			ds0-23        (23),
			ds0-24        (24),
			no-current-connections (40),
			non-continuous-ds0s (41)
			}
	  ACCESS        read-write
	  STATUS        mandatory
	  DESCRIPTION
		"Port1/2 includes 24 DS0's. This value is the starting DS0  
		used by the node to allocate DS0s to meet port(3-4)-dte 
		requirements. Sequential, contiguous DS0s are assigned. 
		The number of DS0s required is based upon the DTE Data Rate 
		and DTE Channel Mapping. The node's response to an entry  
		may be gathered by querying dsucsuConnAutoStatus. To assign 
		DS0s in a non-contiguous format, use the CfgEditConnTable."
	  ::= { dsucsuCfgAutoAssignEntry 4 }

dsucsuConnAutoDestPort      OBJECT-TYPE
	  SYNTAX        INTEGER
			{
			port1         (1),
			port2         (2),
                        port3         (3),
                        port4         (4),
			not-connected (33)
			}
	  ACCESS        read-write
	  STATUS        mandatory
	  DESCRIPTION
		"Selects the port for which DS0s are automatically
		allocated to one of the T1 network ports. Node software may
		not allow connection of port1 to port1."
	  ::= { dsucsuCfgAutoAssignEntry 5 }

dsucsuConnAutoType            OBJECT-TYPE
	  SYNTAX        INTEGER
			{
			data (1),
			voice (2)
			}
	  ACCESS        read-write
	  STATUS        mandatory
	  DESCRIPTION
		"Defines the type of traffic being transported. The 3000N
		supports data (1) or voice (2).  The selected type will be
                assigned to all DS0s."

	  ::= { dsucsuCfgAutoAssignEntry 6 }


dsucsuConnDteRate             OBJECT-TYPE
	  SYNTAX        INTEGER (0..1536000)
	  ACCESS        read-only
	  STATUS        mandatory
	  DESCRIPTION
		"Data rate of the DTE port. Can be chaged from
		the CfgDteTable."

	  ::= { dsucsuCfgAutoAssignEntry 7 }

dsucsuConnDteDensity          OBJECT-TYPE
	  SYNTAX        INTEGER 
			{
			bit-7-stuff     (56),
			clear-channel   (64)
			}
	  ACCESS        read-only
	  STATUS        mandatory
	  DESCRIPTION
		"Channel/DS0 format for the DTE port. Can be 
		changed from the CfgDteTable."

	  ::= { dsucsuCfgAutoAssignEntry 8 }

dsucsuConnDs0Required         OBJECT-TYPE
	  SYNTAX        INTEGER (0..24)
	  ACCESS        read-only
	  STATUS        mandatory
	  DESCRIPTION
		"The number of DS0s required by the node's DTE port. 
		This is based upon the DTE data rate and channel density 
		selections."
		
		::= { dsucsuCfgAutoAssignEntry 9 }

dsucsuConnAutoStatus         OBJECT-TYPE  
	  SYNTAX       INTEGER
			{
			connections-valid (1),
			connections-not-valid (2),
			incorrect-bandwidth (3),
			bandwidth-conflict (4),
			no-current-connections(5),
                        port-type-valid(6),
                        port-type-invalid(7),
                        start-ds0-valid(8),
                        start-ds0-invalid(9),
                        port-valid(10),
                        port-invalid(11)
			}
	  ACCESS       read-only
	  STATUS       mandatory
	  DESCRIPTION
	  "Queries the node's connection status.  Code
	  will be returned when a connection set or update is rejected or accepted."
	  ::= { dsucsuCfgAutoAssignEntry 10 }             

dsucsuConnAutoUpdateCmd        OBJECT-TYPE
	  SYNTAX        INTEGER
			{
			update (1)
			}
	  ACCESS        write-only
	  STATUS        mandatory
	  DESCRIPTION
		"Updates the connections with the edit buffer. The edit buffer
		is comprised of any changes sent (set) from the dsucsuCfgAutoAssignEntry."
	  ::= { dsucsuCfgAutoAssignEntry 11 }             


dsucsuCfgCurrentConnTable OBJECT-TYPE
	  SYNTAX       SEQUENCE OF DsucsuCfgCurrentConnections
	  ACCESS       not-accessible
	  STATUS       mandatory
	  DESCRIPTION
	     "Retrieves node's active connections assignments for 
	     display only. To edit connections, use CfgConnAutoAssign  
	     or CfgEditConnTable."
	  ::= { dsucsuCfgDacsTable 2 }

dsucsuCfgCurrentConnections OBJECT-TYPE
	  SYNTAX  DsucsuCfgCurrentConnections
	  ACCESS  not-accessible
	  STATUS      mandatory
	  DESCRIPTION
		"An entry in the Current Connections Table."
	  INDEX { dsucsuSlot, dsucsuNode, dsucsuT1Index, dsucsuDs0 }
	  ::= { dsucsuCfgCurrentConnTable 1 }

DsucsuCfgCurrentConnections ::=
	  SEQUENCE 
	  {
                dsucsuSlot           INTEGER (1..16),
                dsucsuNode           INTEGER (1..255),
		dsucsuT1Index        INTEGER (1..4),
		dsucsuDs0            INTEGER (1..24),
		dsucsuDtePort        INTEGER,
		dsucsuType           INTEGER
	  }

dsucsuSlot  OBJECT-TYPE
                    SYNTAX      INTEGER (1..16)
                    ACCESS      read-only
                    STATUS      mandatory
                    DESCRIPTION
                            "The PC port to which the TyView node is attached."
                    ::= { dsucsuCfgCurrentConnections 1 }

dsucsuNode  OBJECT-TYPE
                    SYNTAX      INTEGER (1..255)
                    ACCESS      read-only
                    STATUS      mandatory
                    DESCRIPTION
                            "The node ID: unique per port ID."
                    ::= { dsucsuCfgCurrentConnections 2 }


dsucsuT1Index   OBJECT-TYPE
	  SYNTAX      INTEGER (1..4)
	  ACCESS      read-only
	  STATUS      mandatory
	  DESCRIPTION
		"Index to T1 network port of interest. The 3000N supports
		two NETWORK/DSX-1 ports."
	  ::= { dsucsuCfgCurrentConnections 3 }

dsucsuDs0       OBJECT-TYPE
	  SYNTAX        INTEGER (1..24)
	  ACCESS        read-only
	  STATUS        mandatory
	  DESCRIPTION
		"DS0 number 1 through 24 corresponding to the T1 network
		port index."
	  ::= { dsucsuCfgCurrentConnections 4 }

dsucsuDtePort   OBJECT-TYPE
	  SYNTAX        INTEGER
			{
			port1         (1),
			port2         (2),
                        port3         (3),
                        port4         (4),
			not-connected (33)
			}
	  ACCESS        read-only
	  STATUS        mandatory
	  DESCRIPTION
		"DS0 assignment for indexed T1 network port. After 
		making any adjustments to the connections, the 
		dsucsuCfgConnUpdateCmd must be sent. Node software 
		may not permit port 1 connections to itself."
	  ::= { dsucsuCfgCurrentConnections 5 }

dsucsuType                    OBJECT-TYPE
	  SYNTAX        INTEGER
			{
			data (1),
			voice (2)
			}
	  ACCESS        read-only
	  STATUS        mandatory
	  DESCRIPTION
		"Defines the type of traffic being transported. The 3000N
		supports data (1) or voice (2)."

	  ::= { dsucsuCfgCurrentConnections 6 }

dsucsuCfgEditConnTable   OBJECT-TYPE
                    SYNTAX      SEQUENCE OF DsucsuCfgEditConnEntry
                    ACCESS      not-accessible
                    STATUS      mandatory
                    DESCRIPTION
                            "Manually assign the proper amount of bandwidth."
                    ::= { dsucsuCfgDacsTable 3 }


dsucsuCfgEditConnEntry   OBJECT-TYPE
                    SYNTAX      DsucsuCfgEditConnEntry
                    ACCESS      not-accessible
                    STATUS      mandatory
                    DESCRIPTION
	     "Edits current DS0 assignment. After making any adjustments 
	     to the connections, the dsucsuCfgConnUpdateCmd must be sent."
                    INDEX { dsucsuConnSlot, dsucsuConnNode, dsucsuConnSrcPort, dsucsuConnSrcDs0 }
                    ::= { dsucsuCfgEditConnTable 1 }

DsucsuCfgEditConnEntry ::=
	  SEQUENCE 
		{
		dsucsuConnSlot INTEGER (1..16),
		dsucsuConnNode INTEGER (1..255),
		dsucsuConnSrcPort INTEGER (1..4),
		dsucsuConnSrcDs0 INTEGER (1..24),
		dsucsuConnDestPort INTEGER,
		dsucsuConnDestDs0 INTEGER,
		dsucsuConnType INTEGER,
                dsucsuConnNumDs0s INTEGER (1..24),
                dsucsuConnSetStatus INTEGER,
                dsucsuConnConnect INTEGER,
                dsucsuConnUpdateRequired INTEGER,
                dsucsuConnUpdateCmd INTEGER,
                dsucsuConnClearEditBuff INTEGER
		}
					    
dsucsuConnSlot  OBJECT-TYPE
                    SYNTAX      INTEGER (1..16)
                    ACCESS      read-only
                    STATUS      mandatory
                    DESCRIPTION
                            "The PC port to which the TyView node is attached."
                    ::= { dsucsuCfgEditConnEntry 1 }

dsucsuConnNode  OBJECT-TYPE
                    SYNTAX      INTEGER (1..255)
                    ACCESS      read-only
                    STATUS      mandatory
                    DESCRIPTION
                            "The node ID: unique per port ID."
                    ::= { dsucsuCfgEditConnEntry 2 }

dsucsuConnSrcPort OBJECT-TYPE
	  SYNTAX      INTEGER (1..4)
	  ACCESS      read-only
	  STATUS      mandatory
	  DESCRIPTION
		"Index to the source port of interest. The 3000N
                supports two NETWORK/DSX-1 and two DTE ports."
	  ::= { dsucsuCfgEditConnEntry 3 }

dsucsuConnSrcDs0        OBJECT-TYPE
	  SYNTAX        INTEGER (1..24)
	  ACCESS        read-only
	  STATUS        mandatory
	  DESCRIPTION
		"The source DS0 number 1 through 24 corresponding to the T1 network
		port index"
	  ::= { dsucsuCfgEditConnEntry 4 }

dsucsuConnDestPort OBJECT-TYPE
	  SYNTAX        INTEGER
                        {
			port1         (1),
			port2         (2),
                        port3         (3),
                        port4         (4),
			not-connected (33)
                        }
	  ACCESS      read-write
	  STATUS      mandatory
	  DESCRIPTION
		"Index to the destination port of interest. The 3000N
                supports two NETWORK/DSX-1 and two DTE ports."
	  ::= { dsucsuCfgEditConnEntry 5 }

dsucsuConnDestDs0        OBJECT-TYPE
	  SYNTAX        INTEGER 
			{
			ds0-01        (1),
			ds0-02        (2),
			ds0-03        (3),
			ds0-04        (4),
			ds0-05        (5),
			ds0-06        (6),
			ds0-07        (7),
			ds0-08        (8),
			ds0-09        (9),
			ds0-10        (10),
			ds0-11        (11),
			ds0-12        (12),
			ds0-13        (13),
			ds0-14        (14),
			ds0-15        (15),
			ds0-16        (16),
			ds0-17        (17),
			ds0-18        (18),
			ds0-19        (19),
			ds0-20        (20),
			ds0-21        (21),
			ds0-22        (22),
			ds0-23        (23),
			ds0-24        (24),
			no-current-connections (40),
			non-continuous-ds0s (41)
			}
	  ACCESS        read-write
	  STATUS        mandatory
	  DESCRIPTION
		"DS0 assignment for indexed T1 network port. After making 
		any adjustments to the connections, the dsucsuConnUpdateCmd 
		must be sent. Node software may not permit connections between
		the same port and itself."
	  ::= { dsucsuCfgEditConnEntry 6 }


dsucsuConnType       OBJECT-TYPE
	  SYNTAX        INTEGER
			{
			data (1),
			voice (2)
			}
	  ACCESS        read-write
	  STATUS        mandatory
	  DESCRIPTION
		"Defines the type of traffic being transported. The 3000N
		supports data (1) or voice (2)."
	  ::= { dsucsuCfgEditConnEntry 7 }

dsucsuConnNumDs0s       OBJECT-TYPE
	  SYNTAX        INTEGER (1..24)
	  ACCESS        read-write
	  STATUS        mandatory
	  DESCRIPTION
		"The total number of Ds0s to be connected.  The number of Ds0s
                must be between 1 and 24."
	  ::= { dsucsuCfgEditConnEntry 8 }

dsucsuConnSetStatus             OBJECT-TYPE
	  SYNTAX          INTEGER
			  {
			  connections-valid (1),
			  connections-not-valid (2),
			  incorrect-bandwidth (3),
			  bandwidth-conflict (4),
			  no-current-connections(5),
                          port-type-valid(6),
                          port-type-invalid(7),
                          destination-ds0-valid(8),
                          destination-ds0-invalid(9),
                          port-valid(10),
                          port-invalid(11),
                          num-ds0s-valid(12),
                          num-ds0s-invalid(13)
			  }
	  ACCESS        read-only
	  STATUS        mandatory
	  DESCRIPTION
		"Displays node status from the last SNMP issed set command."
	  ::= { dsucsuCfgEditConnEntry 9 }             

dsucsuConnConnect       OBJECT-TYPE
	  SYNTAX        INTEGER
			{
			connect (1),
                        disconnect (2)
			}
	  ACCESS        write-only
	  STATUS        mandatory
	  DESCRIPTION
		"Updates the connections with the edit buffer. The edit buffer
		is comprised of any changes sent (set) from the CfgEditConnTable."
	  ::= { dsucsuCfgEditConnEntry 10}             

dsucsuConnUpdateRequired  OBJECT-TYPE
	  SYNTAX          INTEGER
			  {
			  update-not-required (1),
			  update-required (2)
			  }
	  ACCESS        read-only
	  STATUS        mandatory
	  DESCRIPTION
		"Displays node status from the last connection update."
	  ::= { dsucsuCfgEditConnEntry 11 }             

dsucsuConnUpdateCmd        OBJECT-TYPE
	  SYNTAX        INTEGER
			{
			update (1)
			}
	  ACCESS        write-only
	  STATUS        mandatory
	  DESCRIPTION
		"Sends the updated connections from the edit buffer to the node.
                The edit buffer is comprised of any changes sent (set) from the CfgEditConnTable."
	  ::= { dsucsuCfgEditConnEntry 12}             

dsucsuConnClearEditBuff    OBJECT-TYPE
	  SYNTAX        INTEGER
			{
			clear-edit (1)
			}
	  ACCESS        write-only
	  STATUS        mandatory
	  DESCRIPTION
		"Removes all changes from edit buffer. The edit buffer is 
		comprised of any changes sent (set) from the CfgEditConnTable."
	  ::= { dsucsuCfgEditConnEntry 13 }             

dsucsuDiagNetTable  OBJECT-TYPE
                    SYNTAX      SEQUENCE OF DsucsuDiagNetEntry
                    ACCESS      not-accessible
                    STATUS      mandatory
                    DESCRIPTION
                            "A list of Network Diagnostic attributes. Loopbacks,
                            tests and their respective results can be initiated,
                            cancelled and examined."
                    ::= { dsucsu 15 }

dsucsuDiagNetEntry  OBJECT-TYPE
                    SYNTAX      DsucsuDiagNetEntry
                    ACCESS      not-accessible
                    STATUS      mandatory
                    DESCRIPTION
                            "A Network Diagnostic entry"
                    INDEX { dsucsuDiagNetSlot, dsucsuDiagNetNode, dsucsuDiagNetIndex }
                    ::= { dsucsuDiagNetTable 1 }

DsucsuDiagNetEntry ::=
                    SEQUENCE
                    {
                    dsucsuDiagNetSlot
                        INTEGER (1..16),
                    dsucsuDiagNetNode
                        INTEGER (1..255),
                    dsucsuDiagNetIndex
                        INTEGER (1..2),
                    dsucsuDiagNetLclNetAggLpbk
                        INTEGER,
                    dsucsuDiagNetLclNetLpbk
                        INTEGER,
                    dsucsuDiagNetLclNetPayload
                        INTEGER,
                    dsucsuDiagNetLclNetBiDir
                        INTEGER,
                    dsucsuDiagNetRemCsuLpbk
                        INTEGER,
                    dsucsuDiagNetRemDsuLpbk
                        INTEGER,
                    dsucsuDiagNetEvElapTime
                        TimeTicks,
                    dsucsuDiagNetEvCRC6Err
                        Counter,
                    dsucsuDiagNetEvOofErr
                        Counter,
                    dsucsuDiagNetErrEvents
                        Counter,
                    dsucsuDiagNetClearEvReg
                        INTEGER
                    }

dsucsuDiagNetSlot   OBJECT-TYPE
                    SYNTAX      INTEGER (1..16)
                    ACCESS      read-only
                    STATUS      mandatory
                    DESCRIPTION
                            "The PC port to which the TyView node is attached."
                    ::= { dsucsuDiagNetEntry 1 }

dsucsuDiagNetNode   OBJECT-TYPE
                    SYNTAX      INTEGER (1..255)
                    ACCESS      read-only
                    STATUS      mandatory
                    DESCRIPTION
                            "The node ID: unique per port ID."
                    ::= { dsucsuDiagNetEntry 2 }

dsucsuDiagNetIndex  OBJECT-TYPE
                    SYNTAX      INTEGER (1..2)
                    ACCESS      read-only
                    STATUS      mandatory
                    DESCRIPTION
                            "The network number to be examined for a particular
                            node (3000N only)."
                    ::= { dsucsuDiagNetEntry 3 }


dsucsuDiagNetLclNetAggLpbk  OBJECT-TYPE
                    SYNTAX      INTEGER
                    {
                    enableLoopbackMode (1),
                    disableLoopbackMode (2),
                    notApplicable (3)
                    }
                    ACCESS      read-write
                    STATUS      mandatory
                    DESCRIPTION
                            "Enables the operator to control and examine the 
                            local aggregate loopback.  This loopback occurs on
                            the net side of the local transmit and receive 
                            logic.  The unit continues to transmit data across
                            the network and also loops the data back to its own
                            receiver circuitry."
                    ::= { dsucsuDiagNetEntry 4 }

dsucsuDiagNetLclNetLpbk  OBJECT-TYPE
                    SYNTAX      INTEGER
                    {
                    enableLoopbackMode (1),
                    disableLoopbackMode (2),
                    notApplicable (3)
                    }
                    ACCESS      read-write
                    STATUS      mandatory
                    DESCRIPTION
                            "Enables the operator to control and examine the 
                            local network loopback.  This loopback allows the
                            operator to disconnect the side of the network by
                            transmitting the data recovered from the network."
                    ::= { dsucsuDiagNetEntry 5 }

dsucsuDiagNetLclNetPayload  OBJECT-TYPE
                    SYNTAX      INTEGER
                    {
                    enableLoopbackMode (1),
                    disableLoopbackMode (2),
                    notApplicable (3)
                    }
                    ACCESS      read-write
                    STATUS      mandatory
                    DESCRIPTION
                            "Enables the operator to control and examine the 
                            network payload loopback.  This loopback occurs on
                            the net side of the local transmit and receive 
                            logic.  The unit continues to transmit data across
                            the network and also loops the data back to its own
                            receiver circuitry."
                    ::= { dsucsuDiagNetEntry 6 }

dsucsuDiagNetLclNetBiDir  OBJECT-TYPE
                    SYNTAX      INTEGER
                    {
                    enableLoopbackMode (1),
                    disableLoopbackMode (2),
                    notApplicable (3)
                    }
                    ACCESS      read-write
                    STATUS      mandatory
                    DESCRIPTION
                            "Enables the operator to control and examine the 
                            local network loopback.  This loopback allows the
                            operator to disconnect the side of the network by
                            transmitting the data recovered from the network
                            in both directions."
                    ::= { dsucsuDiagNetEntry 7 }

dsucsuDiagNetRemCsuLpbk OBJECT-TYPE
                    SYNTAX      INTEGER
                    {
                    transmitLoopUpCode (1),
                    transmitLoopDownCode (2),
                    notApplicable (3)
                    }
                    ACCESS      read-write
                    STATUS      mandatory
                    DESCRIPTION
                            "Enables the operator to control and examine the 
                            remote CSU loopback. This loopback allows the
                            operator to test the operation of the local 
                            channel, the aggregate and the remote CSU."
                    ::= { dsucsuDiagNetEntry 8 }

dsucsuDiagNetRemDsuLpbk OBJECT-TYPE
                    SYNTAX      INTEGER
                    {
                    enableLoopbackMode (1),
                    disableLoopbackMode (2),
                    notApplicable (3)
                    }
                    ACCESS      read-write
                    STATUS      mandatory
                    DESCRIPTION
                            "Enables the operator to control and examine the 
                            remote aggregate loopback. This loopback allows the
                            operator to test the entire system from the local
                            unit through the network to the remote node's 
                            transmit and receive front end."
                    ::= { dsucsuDiagNetEntry 9 }

dsucsuDiagNetEvElapTime OBJECT-TYPE
                    SYNTAX      TimeTicks
                    ACCESS      read-only
                    STATUS      mandatory
                    DESCRIPTION
                            "The time elapsed since the Event Test started.  
                            The new Event Test commences as soon as the 
                            previous Event Test registers are cleared."
                    ::= { dsucsuDiagNetEntry 10 }

dsucsuDiagNetEvCRC6Err OBJECT-TYPE
                    SYNTAX      Counter
                    ACCESS      read-only
                    STATUS      mandatory
                    DESCRIPTION
                            "The number of CRC6 errors encountered during the
                            Event Test period."
                    ::= { dsucsuDiagNetEntry 11 }

dsucsuDiagNetEvOofErr  OBJECT-TYPE
                    SYNTAX      Counter
                    ACCESS      read-only
                    STATUS      mandatory
                    DESCRIPTION
                            "The number of Out-Of-Frame errors encountered 
                            during the Event Test period."
                    ::= { dsucsuDiagNetEntry 12 }

dsucsuDiagNetErrEvents OBJECT-TYPE
                    SYNTAX      Counter
                    ACCESS      read-only
                    STATUS      mandatory
                    DESCRIPTION
                            "The number of Errored Events encountered during 
                            the Event Test period."
                    ::= { dsucsuDiagNetEntry 13 }

dsucsuDiagNetClearEvReg OBJECT-TYPE
                    SYNTAX      INTEGER 
                    {
                    clearRegister (1)
                    }
                    ACCESS      write-only
                    STATUS      mandatory
                    DESCRIPTION
                            "Clear all the Event Test registers. Automatically
                            initiates a new Event Test."
                    ::= { dsucsuDiagNetEntry 14 }

dsucsuDiagDteTable     OBJECT-TYPE
                    SYNTAX      SEQUENCE OF DsucsuDiagDteEntry
                    ACCESS      not-accessible
                    STATUS      mandatory
                    DESCRIPTION
                            "A list of DTE channel diagnostics."
                    ::= { dsucsu 16 }

dsucsuDiagDteEntry     OBJECT-TYPE
                    SYNTAX      DsucsuDiagDteEntry
                    ACCESS      not-accessible
                    STATUS      mandatory
                    DESCRIPTION
                            "A DTE channel diagnostic entry"
                    INDEX { dsucsuDiagDteSlot, dsucsuDiagDteNode, dsucsuDiagDteIndex }
                    ::= { dsucsuDiagDteTable 1 }

DsucsuDiagDteEntry ::=
                    SEQUENCE
                    {
                    dsucsuDiagDteSlot
                        INTEGER (1..16),
                    dsucsuDiagDteNode
                        INTEGER (1..255),
                    dsucsuDiagDteIndex
                        INTEGER (1..4),
                    dsucsuDiagDteLocalBiDir
                        INTEGER,
                    dsucsuDiagDteLocalPayload
                        INTEGER,
                    dsucsuDiagDteRemLpbk
                        INTEGER,
                    dsucsuDiagDteBertTestAct
                        INTEGER,
                    dsucsuDiagDteBertHourStrt
                        INTEGER (0..23),
                    dsucsuDiagDteBertMinStrt
                        INTEGER (0..59),
                    dsucsuDiagDteBertTimeElaps
                        TimeTicks,
                    dsucsuDiagDteBertErrors
                        Counter
                    }

dsucsuDiagDteSlot      OBJECT-TYPE
                    SYNTAX      INTEGER (1..16)
                    ACCESS      read-only
                    STATUS      mandatory
                    DESCRIPTION
                            "The PC port to which the TyView node is attached."
                    ::= { dsucsuDiagDteEntry 1 }

dsucsuDiagDteNode      OBJECT-TYPE
                    SYNTAX      INTEGER (1..255)
                    ACCESS      read-only
                    STATUS      mandatory
                    DESCRIPTION
                            "The node ID: unique per port ID."
                    ::= { dsucsuDiagDteEntry 2 }

dsucsuDiagDteIndex     OBJECT-TYPE
                    SYNTAX      INTEGER (1..4)
                    ACCESS      read-only
                    STATUS      mandatory
                    DESCRIPTION
                            "The channel number to be examined for a particular
                            node."
                    ::= { dsucsuDiagDteEntry 3 }

dsucsuDiagDteLocalBiDir OBJECT-TYPE
                    SYNTAX      INTEGER
                    {
                    enableLoopbackMode (1),
                    disableLoopbackMode (2),
                    notApplicable (3)
                    }
                    ACCESS      read-write
                    STATUS      mandatory
                    DESCRIPTION
                            "This selection displays the status or controls the
                            Local Channel Loopback for the selected channel. 
                            This is a local turnaround and is bi-directional."
                    ::= { dsucsuDiagDteEntry 4 }

dsucsuDiagDteLocalPayload OBJECT-TYPE
                    SYNTAX      INTEGER
                    {
                    enableLoopbackMode (1),
                    disableLoopbackMode (2),
                    notApplicable (3)
                    }
                    ACCESS      read-write
                    STATUS      mandatory
                    DESCRIPTION
                            "This selection displays the status or controls the
                            Local Payload Channel Loopback for the selected channel."
                    ::= { dsucsuDiagDteEntry 5 }

dsucsuDiagDteRemLpbk   OBJECT-TYPE
                    SYNTAX      INTEGER
                    {
                    enableLoopbackMode (1),
                    disableLoopbackMode (2),
                    notApplicable (3)
                    }
                    ACCESS      read-write
                    STATUS      mandatory
                    DESCRIPTION
                            "This selection displays the status or controls the
                            Channel Remote Loopback for the selected channel.
                            This loopback transmits a code to the remote node
                            which will enable or disable a diagnostic loopback
                            at the addressed channel." 
                    ::= { dsucsuDiagDteEntry 6 }

dsucsuDiagDteBertTestAct   OBJECT-TYPE
                    SYNTAX      INTEGER
                    {
                    startBertTest (1),
                    stopBertTest (2),
                    injectErrorBertTest (3),
                    clearErrorBertTest (4)
                    }
                    ACCESS      read-write
                    STATUS      mandatory
                    DESCRIPTION
                            "BERT test related actions:
                                 a: Starts a BERT test on a channel,
                                 b: Stops a BERT test on a channel,
                                 c: Inject Errors while the BERT test is running,
                                 d: Clears BERT test errors."
                    ::= { dsucsuDiagDteEntry 7 }

dsucsuDiagDteBertHourStrt  OBJECT-TYPE
                    SYNTAX      INTEGER (0..23)
                    ACCESS      read-only
                    STATUS      mandatory
                    DESCRIPTION
                            "Displays the hour that the BERT test started."
                    ::= { dsucsuDiagDteEntry 8 }

dsucsuDiagDteBertMinStrt   OBJECT-TYPE
                    SYNTAX      INTEGER (0..59)
                    ACCESS      read-only
                    STATUS      mandatory
                    DESCRIPTION
                            "Displays th minute that BERT test started."
                    ::= { dsucsuDiagDteEntry 9 }

dsucsuDiagDteBertTimeElaps OBJECT-TYPE
                    SYNTAX      TimeTicks
                    ACCESS      read-only
                    STATUS      mandatory
                    DESCRIPTION
                            "Elapsed time since the BERT Test started"
                    ::= { dsucsuDiagDteEntry 10 }

dsucsuDiagDteBertErrors    OBJECT-TYPE
                    SYNTAX      Counter
                    ACCESS      read-only
                    STATUS      mandatory
                    DESCRIPTION
                            "Number of BERT test errors encountered during the 
                            BERT Test."
                    ::= { dsucsuDiagDteEntry 11 }

dsucsuDiagFrmTable     OBJECT-TYPE
                    SYNTAX      SEQUENCE OF DsucsuDiagFrmEntry
                    ACCESS      not-accessible
                    STATUS      mandatory
                    DESCRIPTION
                            "A list of framed channel diagnostics." 
                    ::= { dsucsu 17 }

dsucsuDiagFrmEntry     OBJECT-TYPE
                    SYNTAX      DsucsuDiagFrmEntry
                    ACCESS      not-accessible
                    STATUS      mandatory
                    DESCRIPTION
                            "A  framed channel diagnostic entry"
                    INDEX { dsucsuDiagFrmSlot, dsucsuDiagFrmNode, dsucsuDiagFrmIndex }
                    ::= { dsucsuDiagFrmTable 1 }

DsucsuDiagFrmEntry ::=
                    SEQUENCE
                    {
                    dsucsuDiagFrmSlot
                        INTEGER (1..16),
                    dsucsuDiagFrmNode
                        INTEGER (1..255),
                    dsucsuDiagFrmIndex
                        INTEGER (1..4),
                    dsucsuDiagFrmLclLpbk
                        INTEGER,
                    dsucsuDiagFrmLclPayload
                        INTEGER,
                    dsucsuDiagFrmLclBiDir
                        INTEGER,
                    dsucsuDiagFrmRemLpbk
                        INTEGER,
                    dsucsuDiagFrmLclDte
                        INTEGER,
                    dsucsuDiagFrmLclDte2
                        INTEGER,
                    dsucsuDiagFrmBertTestAct
                        INTEGER,
                    dsucsuDiagFrmEvElapTime
                        TimeTicks,
                    dsucsuDiagFrmEvBpvErr
                        Counter,
                    dsucsuDiagFrmEvOofErr
                        Counter,
                    dsucsuDiagFrmFrameErr
                        Counter,
                    dsucsuDiagFrmClearEvReg
                        INTEGER
                    }

dsucsuDiagFrmSlot      OBJECT-TYPE
                    SYNTAX      INTEGER (1..16)
                    ACCESS      read-only
                    STATUS      mandatory
                    DESCRIPTION
                            "The PC port to which the TyView node is attached."
                    ::= { dsucsuDiagFrmEntry 1 }

dsucsuDiagFrmNode      OBJECT-TYPE
                    SYNTAX      INTEGER (1..255)
                    ACCESS      read-only
                    STATUS      mandatory
                    DESCRIPTION
                            "The node ID: unique per port ID."
                    ::= { dsucsuDiagFrmEntry 2 }

dsucsuDiagFrmIndex     OBJECT-TYPE
                    SYNTAX      INTEGER (1..4)
                    ACCESS      read-only
                    STATUS      mandatory
                    DESCRIPTION
                            "The channel number to be examined for a particular
                            node."
                    ::= { dsucsuDiagFrmEntry 3 }

dsucsuDiagFrmLclLpbk OBJECT-TYPE
                    SYNTAX      INTEGER
                    {
                    enableLoopbackMode (1),
                    disableLoopbackMode (2),
                    notApplicable (3)
                    }
                    ACCESS      read-write
                    STATUS      mandatory
                    DESCRIPTION
                            "This selection displays the status or controls the
                            Local Channel Loopback for the selected channel. 
                            This is a local turnaround and is bi-directional."
                    ::= { dsucsuDiagFrmEntry 4 }

dsucsuDiagFrmLclPayload   OBJECT-TYPE
                    SYNTAX      INTEGER
                    {
                    enableLoopbackMode (1),
                    disableLoopbackMode (2),
                    notApplicable (3)
                    }
                    ACCESS      read-write
                    STATUS      mandatory
                    DESCRIPTION
                            "This selection displays the status or controls the
                            Channel Remote Loopback for the selected channel.
                            This loopback transmits a code to the remote node
                            which will enable or disable a diagnostic loopback
                            at the addressed channel. This selection is 
                            applicable only for DSX type channels."
                    ::= { dsucsuDiagFrmEntry 5 }

dsucsuDiagFrmLclBiDir       OBJECT-TYPE
                    SYNTAX      INTEGER
                    {
                    enableLoopbackMode (1),
                    disableLoopbackMode (2),
                    notApplicable (3)
                    }
                    ACCESS      read-write
                    STATUS      mandatory
                    DESCRIPTION
                            "This selection displays the status or controls the 
                            DSX Loopback for the selected channel. This 
                            selection is applicable only for DSX channels."
                    ::= { dsucsuDiagFrmEntry 6 }

dsucsuDiagFrmRemLpbk   OBJECT-TYPE
                    SYNTAX      INTEGER
                    {
                    transmitLoopUpCode (1),
                    transmitLoopDownCode (2),
                    notApplicable (3)
                    }
                    ACCESS      read-write
                    STATUS      mandatory
                    DESCRIPTION
                            "This selection displays the status or controls the
                            Local Channel Loopback for the selected channel. 
                            This loopback transmits a code to the remote node
                            which will enable or disable a diagnostic loopback
                            at the addressed channel. This selection is 
                            applicable only for DSX channels."
                    ::= { dsucsuDiagFrmEntry 7 }

dsucsuDiagFrmLclDte OBJECT-TYPE
                    SYNTAX      INTEGER
                    {
                    enableLoopbackMode (1),
                    disableLoopbackMode (2),
                    notApplicable (3)
                    }
                    ACCESS      read-write
                    STATUS      mandatory
                    DESCRIPTION
                            "This selection displays the status or controls the
                            Local Channel Loopback for the selected channel. 
                            This is a local turnaround and is bi-directional.
                            This selection is applicable only for CSU type channels."
                    ::= { dsucsuDiagFrmEntry 8 }

dsucsuDiagFrmLclDte2   OBJECT-TYPE
                    SYNTAX      INTEGER
                    {
                    enableLoopbackMode (1),
                    disableLoopbackMode (2),
                    notApplicable (3)
                    }
                    ACCESS      read-write
                    STATUS      mandatory
                    DESCRIPTION
                            "This selection displays the status or controls the
                            Channel Remote Loopback for the selected channel.
                            This loopback transmits a code to the remote node
                            which will enable or disable a diagnostic loopback
                            at the addressed channel. This selection is 
                            applicable only for CSU type channels."
                    ::= { dsucsuDiagFrmEntry 9 }

dsucsuDiagFrmBertTestAct   OBJECT-TYPE
                    SYNTAX      INTEGER
                    {
                    startBertTest (1),
                    stopBertTest (2),
                    injectErrorBertTest (3),
                    clearErrorBertTest (4)
                    }
                    ACCESS      read-write
                    STATUS      mandatory
                    DESCRIPTION
                            "BERT test related actions:
                                 a: Starts a BERT test on a channel,
                                 b: Stops a BERT test on a channel,
                                 c: Inject Errors while the BERT test is running,
                                 d: Clears BERT test errors."
                    ::= { dsucsuDiagFrmEntry 10 }

dsucsuDiagFrmEvElapTime  OBJECT-TYPE
                    SYNTAX      TimeTicks
                    ACCESS      read-only
                    STATUS      mandatory
                    DESCRIPTION
                            "The time elapsed since the PBX Event Test started. 
                            This selection is applicable only for PBX channels."
                    ::= { dsucsuDiagFrmEntry 11 }

dsucsuDiagFrmEvBpvErr OBJECT-TYPE
                    SYNTAX      Counter
                    ACCESS      read-only
                    STATUS      mandatory
                    DESCRIPTION
                            "The number of Bipolar Violations encountered 
                            during the Event Test. This selection is applicable
                            only for PBX channels."
                    ::= { dsucsuDiagFrmEntry 12 }

dsucsuDiagFrmEvOofErr OBJECT-TYPE
                    SYNTAX      Counter
                    ACCESS      read-only
                    STATUS      mandatory
                    DESCRIPTION
                            "The number of Out-Of-Frame Errors encountered 
                            during the Event Test.  This selection is applicable
                            only for PBX channels."
                    ::= { dsucsuDiagFrmEntry 13 }

dsucsuDiagFrmFrameErr   OBJECT-TYPE
                    SYNTAX      Counter
                    ACCESS      read-only
                    STATUS      mandatory
                    DESCRIPTION
                            "The number of Frame Errors encountered during the 
                            Event Test. This selection is applicable only for
                            PBX channels."
                    ::= { dsucsuDiagFrmEntry 14 }

dsucsuDiagFrmClearEvReg OBJECT-TYPE
                    SYNTAX      INTEGER 
                    {
                    clearRegister (1)
                    }
                    ACCESS      write-only
                    STATUS      mandatory
                    DESCRIPTION
                            "Clears all the PBX Event Test registers. This
                            selection is applicable only for PBX channels."
                    ::= { dsucsuDiagFrmEntry 15 }

dsucsuDiagAuxTable  OBJECT-TYPE
                    SYNTAX      SEQUENCE OF DsucsuDiagAuxEntry
                    ACCESS      not-accessible
                    STATUS      mandatory
                    DESCRIPTION
                            "Auxillary Channel Diagnostics"
                    ::= { dsucsu 18 }

dsucsuDiagAuxEntry     OBJECT-TYPE
                    SYNTAX      DsucsuDiagAuxEntry
                    ACCESS      not-accessible
                    STATUS      mandatory
                    DESCRIPTION
                            "Auxilary diagnostic entry"
                    INDEX { dsucsuDiagAuxSlot, dsucsuDiagAuxNode }
                    ::= { dsucsuDiagAuxTable 1 }

DsucsuDiagAuxEntry ::=
                    SEQUENCE
                    {
                    dsucsuDiagAuxSlot
                        INTEGER (1..16),
                    dsucsuDiagAuxNode
                        INTEGER (1..255),
                    dsucsuDiagAuxChAStatus
                        INTEGER,
                    dsucsuDiagAuxChBStatus
                        INTEGER,
                    dsucsuDiagAuxFdlStatus
                        INTEGER,
                    dsucsuDiagAuxFdl2Status
                        INTEGER,
                    dsucsuDiagAuxMaintStatus
                        INTEGER,
                    dsucsuDiagAuxCommStatus
                        INTEGER
                    } 

dsucsuDiagAuxSlot   OBJECT-TYPE
                    SYNTAX      INTEGER (1..16)
                    ACCESS      read-only
                    STATUS      mandatory
                    DESCRIPTION
                            "The PC port to which the TyView node is attached."
                    ::= { dsucsuDiagAuxEntry 1 }

dsucsuDiagAuxNode  OBJECT-TYPE
                    SYNTAX      INTEGER (1..255)
                    ACCESS      read-only
                    STATUS      mandatory
                    DESCRIPTION
                            "The node ID: unique per port ID."
                    ::= { dsucsuDiagAuxEntry 2 }

dsucsuDiagAuxChAStatus OBJECT-TYPE
                    SYNTAX      INTEGER
                    {
                    down (1),
                    sync (2),
                    off (3)
                    }
                    ACCESS      read-only
                    STATUS      mandatory
                    DESCRIPTION
			    "Status of Supervisory link channel A."
                    ::= { dsucsuDiagAuxEntry 3 }

dsucsuDiagAuxChBStatus OBJECT-TYPE
                    SYNTAX      INTEGER
                    {
                    down (1),
                    sync (2),
                    off (3)
                    }
                    ACCESS      read-only
                    STATUS      mandatory
                    DESCRIPTION
			    "Status of Supervisory Link Channel B."
                    ::= { dsucsuDiagAuxEntry 4 }

dsucsuDiagAuxFdlStatus OBJECT-TYPE
                    SYNTAX      INTEGER
                    {
                    down (1),
                    sync (2),
                    off (3)
                    }
                    ACCESS      read-only
                    STATUS      mandatory
                    DESCRIPTION
			    "Status of Facility Data Link (PORT1)."
                    ::= { dsucsuDiagAuxEntry 5 }

dsucsuDiagAuxFdl2Status OBJECT-TYPE
                    SYNTAX      INTEGER
                    {
                    down (1),
                    sync (2),
                    off (3)
                    }
                    ACCESS      read-only
                    STATUS      mandatory
                    DESCRIPTION
			    "Status of Facility Data Link (PORT2)."
                    ::= { dsucsuDiagAuxEntry 6 }


dsucsuDiagAuxMaintStatus OBJECT-TYPE
                    SYNTAX      INTEGER
                    {
                    down (1),
                    sync (2),
                    off (3)
                    }
                    ACCESS      read-only
                    STATUS      mandatory
                    DESCRIPTION
			     " The Maint. Port Supervisory link status."
                    ::= { dsucsuDiagAuxEntry 7 }

dsucsuDiagAuxCommStatus OBJECT-TYPE
                    SYNTAX      INTEGER
                    {
                    down (1),
                    sync (2),
                    off (3)
                    }
                    ACCESS      read-only
                    STATUS      mandatory
                    DESCRIPTION
                            "The Communications port Supervisory link status." 
                    ::= { dsucsuDiagAuxEntry 8 }

dsucsuDiagPortTable  OBJECT-TYPE
                    SYNTAX      SEQUENCE OF DsucsuDiagPortEntry
                    ACCESS      not-accessible
                    STATUS      mandatory
                    DESCRIPTION
                            "Port Specific Display only Diagnostics"
                    ::= { dsucsu 19 }

dsucsuDiagPortEntry     OBJECT-TYPE
                    SYNTAX      DsucsuDiagPortEntry
                    ACCESS      not-accessible
                    STATUS      mandatory
                    DESCRIPTION
                            "Port Specific Display only entry"
                    INDEX { dsucsuDiagPortSlot, dsucsuDiagPortNode, dsucsuDiagPortIndex }
                    ::= { dsucsuDiagPortTable 1 }

DsucsuDiagPortEntry ::=
                    SEQUENCE
                    {
                    dsucsuDiagPortSlot
                        INTEGER (1..16),
                    dsucsuDiagPortNode
                        INTEGER (1..255),
                    dsucsuDiagPortIndex
                        INTEGER (1..4),
                    dsucsuDiagPortType
                        INTEGER,
                    dsucsuDiagPortStatus
                        INTEGER
                    } 

dsucsuDiagPortSlot   OBJECT-TYPE
                    SYNTAX      INTEGER (1..16)
                    ACCESS      read-only
                    STATUS      mandatory
                    DESCRIPTION
                            "The PC port to which the TyView node is attached."
                    ::= { dsucsuDiagPortEntry 1 }

dsucsuDiagPortNode  OBJECT-TYPE
                    SYNTAX      INTEGER (1..255)
                    ACCESS      read-only
                    STATUS      mandatory
                    DESCRIPTION
                            "The node ID: unique per port ID."
                    ::= { dsucsuDiagPortEntry 2 }

dsucsuDiagPortIndex OBJECT-TYPE
                    SYNTAX      INTEGER (1..4)
                    ACCESS      read-only
                    STATUS      mandatory
                    DESCRIPTION
                            "The port index: unique per port."
                    ::= { dsucsuDiagPortEntry 3 }

dsucsuDiagPortType OBJECT-TYPE
                    SYNTAX      INTEGER
                    {
                    none (1),
                    network (2),
                    dsx (3),
                    pbx (4),
                    rs449 (5),
                    rs232 (6),
                    mil188 (7),
                    v35 (8),
                    dte (9),
                    tdm (10)
                    }
                    ACCESS      read-only
                    STATUS      mandatory
                    DESCRIPTION
			    "The port type (NET/DSX/PBX/V.35/RS-449)."
                    ::= { dsucsuDiagPortEntry 4 }

dsucsuDiagPortStatus OBJECT-TYPE
                    SYNTAX      INTEGER
                    {
                    clearOK (1),
                    redAlarm (2),
                    yellowAlarm (3),
                    syncLoss (4),
                    bpvAlarm (5),
                    blueAlarm (6),
                    test (7),
                    timeout (8),
                    notApplicable (9)
                    }
                    ACCESS      read-only
                    STATUS      mandatory
                    DESCRIPTION
			    "Current status condition of a particular port."
                    ::= { dsucsuDiagPortEntry 5 }

dsucsuIntervalTable OBJECT-TYPE
                    SYNTAX      SEQUENCE OF DsucsuIntervalEntry
                    ACCESS      not-accessible
                    STATUS      mandatory
                    DESCRIPTION
                            "The table contains various ESF stats collected over
                            the last 96 15-minute intervals (24 hours total 
                            time)."
                    ::= { dsucsu 20 }

dsucsuIntervalEntry OBJECT-TYPE
                    SYNTAX      DsucsuIntervalEntry
                    ACCESS      not-accessible
                    STATUS      mandatory
                    DESCRIPTION
                            "Entry in the table of ESF interval stats."
                    INDEX { dsucsuIntervalSlot, dsucsuIntervalNode,
                            dsucsuIntervalPort, dsucsuIntervalNum }
                    ::= { dsucsuIntervalTable 1 }

DsucsuIntervalEntry ::=
                     SEQUENCE
                     {
                     dsucsuIntervalSlot
                         INTEGER (1..16),
                     dsucsuIntervalNode
                         INTEGER (1..255),
                     dsucsuIntervalPort
                         INTEGER (1..2),
                     dsucsuIntervalNum
                         INTEGER (1..96),
                     dsucsuIntervalESs
                         Counter,
                     dsucsuIntervalSESs
                         Counter,
                     dsucsuIntervalBPVs
                         Counter,
                     dsucsuIntervalFSs
                         Counter
                     }

dsucsuIntervalSlot  OBJECT-TYPE
                    SYNTAX      INTEGER (1..16)
                    ACCESS      read-only
                    STATUS      mandatory
                    DESCRIPTION
                            "The PC port to which the TyView node is attached."
                    ::= { dsucsuIntervalEntry 1 }

dsucsuIntervalNode  OBJECT-TYPE
                    SYNTAX      INTEGER (1..255)
                    ACCESS      read-only
                    STATUS      mandatory
                    DESCRIPTION
                            "The node ID: unique per port ID."
                    ::= { dsucsuIntervalEntry 2 }

dsucsuIntervalPort OBJECT-TYPE
                    SYNTAX      INTEGER (1..2)
                    ACCESS      read-only
                    STATUS      mandatory
                    DESCRIPTION
                            "The port index: unique per port."
                    ::= { dsucsuIntervalEntry 3 }

dsucsuIntervalNum OBJECT-TYPE
                    SYNTAX      INTEGER (1..96)
                    ACCESS      read-only
                    STATUS      mandatory
                    DESCRIPTION
                            "The sequence number for the selected interval."
                    ::= { dsucsuIntervalEntry 4 }       

dsucsuIntervalESs OBJECT-TYPE
                    SYNTAX      Counter
                    ACCESS      read-only
                    STATUS      mandatory
                    DESCRIPTION
                            "The number of Errored Seconds (as defined in Bell
                            Publication 62411) encountered in the user
                            registers during the selected interval."
                    ::= { dsucsuIntervalEntry 5 }

dsucsuIntervalSESs OBJECT-TYPE
                    SYNTAX      Counter
                    ACCESS      read-only
                    STATUS      mandatory
                    DESCRIPTION
                            "The number of Severely Errored Seconds (as 
                            defined in Bell Publication 62411) encountered in
                            the user registers during the selected interval."
                    ::= { dsucsuIntervalEntry 6 }

dsucsuIntervalBPVs OBJECT-TYPE
                    SYNTAX      Counter
                    ACCESS      read-only
                    STATUS      mandatory
                    DESCRIPTION
                            "The number of Bipolar Violations (as defined in 
                            Bell Publication 62411) encountered in the user 
                            registers during the selected interval."
                    ::= { dsucsuIntervalEntry 7 }

dsucsuIntervalFSs OBJECT-TYPE
                    SYNTAX      Counter
                    ACCESS      read-write
                    STATUS      mandatory
                    DESCRIPTION
                            "The number of Failed Seconds (as defined in Bell
                            Publication 62411) encountered in the user 
                            registers during the selected interval."
                    ::= { dsucsuIntervalEntry 8 }

-- dsucsuIntervalCarrTable {dsucsu 21} not implemented

dsucsuCurrentTable OBJECT-TYPE
                    SYNTAX      SEQUENCE OF DsucsuCurrentEntry
                    ACCESS      not-accessible
                    STATUS      mandatory
                    DESCRIPTION
                            "The table contains various ESF stats collected 
                            over the current 15-minute interval."
                    ::= { dsucsu 22 }

dsucsuCurrentEntry OBJECT-TYPE
                    SYNTAX      DsucsuCurrentEntry
                    ACCESS      not-accessible
                    STATUS      mandatory
                    DESCRIPTION
                            "Entry in the table of the current ESF stats."
                    INDEX { dsucsuCurrentSlot, dsucsuCurrentNode,
                            dsucsuCurrentPort }
                    ::= { dsucsuCurrentTable 1 }

DsucsuCurrentEntry ::=
                     SEQUENCE
                     {
                     dsucsuCurrentSlot
                         INTEGER (1..16),
                     dsucsuCurrentNode
                         INTEGER (1..255),
                     dsucsuCurrentPort
                         INTEGER (1..2),
                     dsucsuCurrentESs
                         Counter,
                     dsucsuCurrentSESs
                         Counter,
                     dsucsuCurrentBPVs
                         Counter,
                     dsucsuCurrentSECs
                         Counter,
                     dsucsuCurrentStatus
                         INTEGER
                     }

dsucsuCurrentSlot  OBJECT-TYPE
                    SYNTAX      INTEGER (1..16)
                    ACCESS      read-only
                    STATUS      mandatory
                    DESCRIPTION
                            "The PC port to which the TyView node is attached."
                    ::= { dsucsuCurrentEntry 1 }

dsucsuCurrentNode  OBJECT-TYPE
                    SYNTAX      INTEGER (1..255)
                    ACCESS      read-only
                    STATUS      mandatory
                    DESCRIPTION
                            "The node ID: unique per port ID."
                    ::= { dsucsuCurrentEntry 2 }

dsucsuCurrentPort  OBJECT-TYPE
                    SYNTAX      INTEGER (1..2)
                    ACCESS      read-only
                    STATUS      mandatory
                    DESCRIPTION
                            "The port index: unique per port."
                    ::= { dsucsuCurrentEntry 3 }

dsucsuCurrentESs    OBJECT-TYPE
                    SYNTAX      Counter
                    ACCESS      read-only
                    STATUS      mandatory
                    DESCRIPTION
                            "The number of Errored Seconds (as defined in Bell
                            Publication 62411) encountered in the user 
                            registers during the current 15 minute interval."
                    ::= { dsucsuCurrentEntry 4 }

dsucsuCurrentSESs   OBJECT-TYPE
                    SYNTAX      Counter
                    ACCESS      read-only
                    STATUS      mandatory
                    DESCRIPTION
                            "The number of Severely Errored Seconds (as defined 
                            in Bell Publication 62411) encountered in the user 
                            registers during the current 15 minute interval."
                    ::= { dsucsuCurrentEntry 5 }

dsucsuCurrentBPVs   OBJECT-TYPE
                    SYNTAX      Counter
                    ACCESS      read-only
                    STATUS      mandatory
                    DESCRIPTION
                            "The number of Bipolar Violations (as defined in
                            Bell Publication 62411) encountered in the user 
                            registers during the current 15 minute interval."
                    ::= { dsucsuCurrentEntry 6 }

dsucsuCurrentSECs   OBJECT-TYPE
                    SYNTAX      Counter
                    ACCESS      read-only
                    STATUS      mandatory
                    DESCRIPTION
                            "Number of seconds elapsed in the current 15 minute
                            interval."
                    ::= { dsucsuCurrentEntry 7 }

dsucsuCurrentStatus OBJECT-TYPE
                    SYNTAX      INTEGER
                    {
                    frozen (1),
                    unfrozen (2)
                    }
                    ACCESS      read-write
                    STATUS      mandatory
                    DESCRIPTION
                            "Indication of whether statistics have been halted 
                            during current 15 minute interval."
                    ::= { dsucsuCurrentEntry 8 }

-- dsucsuCurCarrTable {dsucsu 23} not implemented

dsucsuTotalTable    OBJECT-TYPE
                    SYNTAX  SEQUENCE OF DsucsuTotalEntry
                    ACCESS  not-accessible
                    STATUS  mandatory
                    DESCRIPTION
                            "The table contains the cummulative sum of various 
                            ESF stats collected over the last 24 hour period."
                    ::= { dsucsu 24 }

dsucsuTotalEntry    OBJECT-TYPE
                    SYNTAX   DsucsuTotalEntry
                    ACCESS   not-accessible
                    STATUS   mandatory
                    DESCRIPTION
                            "Entry in the table of the total ESF stats."
                    INDEX { dsucsuTotalSlot, dsucsuTotalNode,
                            dsucsuTotalPort }
                    ::= { dsucsuTotalTable 1 }

DsucsuTotalEntry ::=
                     SEQUENCE
                     {
                     dsucsuTotalSlot
                         INTEGER (1..16),
                     dsucsuTotalNode
                         INTEGER (1..255),
                     dsucsuTotalPort
                         INTEGER (1..2),
                     dsucsuTotalESs
                         Counter,
                     dsucsuTotalSESs
                         Counter,
                     dsucsuTotalBPVs
                         Counter,
                     dsucsuTotalSECs
                         Counter,
                     dsucsuTotalStatus
                         INTEGER
                     }

dsucsuTotalSlot     OBJECT-TYPE
                    SYNTAX      INTEGER (1..16)
                    ACCESS      read-only
                    STATUS      mandatory
                    DESCRIPTION
                            "The PC port to which the TyView node is attached."
                    ::= { dsucsuTotalEntry 1 }

dsucsuTotalNode     OBJECT-TYPE
                    SYNTAX      INTEGER (1..255)
                    ACCESS      read-only
                    STATUS      mandatory
                    DESCRIPTION
                            "The node ID: unique per port ID."
                    ::= { dsucsuTotalEntry 2 }

dsucsuTotalPort     OBJECT-TYPE
                    SYNTAX      INTEGER (1..2)
                    ACCESS      read-only
                    STATUS      mandatory
                    DESCRIPTION
                            "The port index: unique per port."
                    ::= { dsucsuTotalEntry 3 }

dsucsuTotalESs      OBJECT-TYPE
                    SYNTAX      Counter
                    ACCESS      read-only
                    STATUS      mandatory
                    DESCRIPTION
                            "The number of Errored Seconds (as defined in Bell
                            Publication 62411) encountered in the user 
                            registers in the last 24 hour period (96 
                            intervals)."
                    ::= { dsucsuTotalEntry 4 }

dsucsuTotalSESs     OBJECT-TYPE
                    SYNTAX      Counter
                    ACCESS      read-only
                    STATUS      mandatory
                    DESCRIPTION
                            "The number of Severely Errored Seconds (as defined 
                            in Bell Publication 62411) encountered in the user 
                            registers in the last 24 hour period (96 
                            intervals)."
                    ::= { dsucsuTotalEntry 5 }

dsucsuTotalBPVs     OBJECT-TYPE
                    SYNTAX      Counter
                    ACCESS      read-only
                    STATUS      mandatory
                    DESCRIPTION
                            "The number of Bipolar Violations (as defined in 
                            Bell Publication 62411) encountered in the user 
                            registers in the last 24 hour period (96 
                            intervals)."
                    ::= { dsucsuTotalEntry 6 }

dsucsuTotalSECs     OBJECT-TYPE
                    SYNTAX      Counter
                    ACCESS      read-only
                    STATUS      mandatory
                    DESCRIPTION
                            "Number of seconds elapsed in the last 24 hours. 
                            This will be the maximum value of 86400 unless the 
                            addressed node was brought on-line with the this 
                            period."
                    ::= { dsucsuTotalEntry 7 }

dsucsuTotalStatus   OBJECT-TYPE
                    SYNTAX      INTEGER
                    {
                    frozen (1),
                    unfrozen (2)
                    }
                    ACCESS      read-write
                    STATUS      mandatory
                    DESCRIPTION
                            "Indication of whether statistics have been halted 
                            in the last 24 hours."
                    ::= { dsucsuTotalEntry 8 }

dsucsuAlarmType     OBJECT-TYPE
                    SYNTAX      INTEGER
                    {
		    yellow-Alarm (1),
		    sync-Alarm (2),
		    red-Alarm (3),
		    bpv-Alarm (4),
		    confg-Activated (5),
		    confg-Stored (6),
		    pbx1-Yellow-Alarm (7),
		    pbx1-Red-Alarm (8),
		    pbx1-Los-Alarm (9),
		    pbx3-Yellow-Alarm (10),
		    pbx3-Red-Alarm (11),
		    pbx3-Los-Alarm (12),
		    ais-Alarm (13),
		    node-communications-lost (14),
		    sync-ais-Alarm (15),
		    ts16-ais-Alarm (16),
		    ts16-Los-Alarm (17),
		    remote-Alarm (18),
		    remote-ts16-Alarm (19),
		    frame-Error-Alarm (20),
		    crc4-Error-Alarm (21),
		    port2-Yellow-Alarm (22),
		    port2-Sync-Alarm (23),
		    port2-Red-Alarm (24),
		    port2-Bpv-Alarm (25),
                    power-Supply-Alarm (26),
                    fan-one-Failure (27),
                    fan-two-Failure (28),
		    yellow-Alarm-Clear (29),
		    sync-Alarm-Clear (30),
		    red-Alarm-Clear (31),
		    bpv-Alarm-Clear (32),
		    pbx1-Yellow-Alarm-Clear (33),
		    pbx1-Red-Alarm-Clear (34),
		    pbx1-Los-Alarm-Clear (35),
		    pbx3-Yellow-Alarm-Clear (36),
		    pbx3-Red-Alarm-Clear (37),
		    pbx3-Los-Alarm-Clear (38),
		    ais-Alarm-Clear (39),
		    node-communications-restored (40),
		    sync-ais-Alarm-Clear (41),
		    ts16-ais-Alarm-Clear (42),
		    ts16-Los-Alarm-Clear (43),
		    remote-Alarm-Clear (44),
		    remote-ts16-Alarm-Clear (45),
		    frame-Error-Alarm-Clear (46),
		    crc4-Error-Alarm-Clear (47),
		    port2-Yellow-Alarm-Clear (48),
		    port2-Sync-Alarm-Clear (49),
		    port2-Red-Alarm-Clear (50),
		    port2-Bpv-Alarm-Clear (51),
                    power-Supply-Alarm-Clear (52),
                    fan-one-Failure-Clear (53),
                    fan-two-Failure-Clear (54)
                    }
                    ACCESS      read-only
                    STATUS      mandatory
                    DESCRIPTION
                            "The type of alarms that are generated on the node"
                    ::= { dsucsu 25 }

dsucsuAlarmSlot     OBJECT-TYPE
                    SYNTAX      INTEGER (1..16)
                    ACCESS      read-only
                    STATUS      mandatory
                    DESCRIPTION
                            "The PC port to which the TyView node is attached."
                    ::= { dsucsu 26 }

dsucsuAlarmNode     OBJECT-TYPE
                    SYNTAX      INTEGER (1..255)
                    ACCESS      read-only
                    STATUS      mandatory
                    DESCRIPTION
                            "The node ID: unique per port ID."
                    ::= { dsucsu 27 }

dsucsuAlarmName     OBJECT-TYPE
                    SYNTAX      DisplayString (SIZE (0..8))
                    ACCESS      read-only
                    STATUS      mandatory
                    DESCRIPTION
                            "The name of the node which triggered the alarm."
                    ::= { dsucsu 28 }

--
--	the TyView group
--

tyviewSysTable 	    OBJECT IDENTIFIER ::= { tyview 1 }

tyviewSysRevSw	    OBJECT-TYPE
                    SYNTAX      DisplayString (SIZE (0..10))
                    ACCESS      read-only
                    STATUS      mandatory
                    DESCRIPTION
                            "The TyView software revision."
                    ::= { tyviewSysTable 1 }

tyviewSysName	    OBJECT-TYPE
                    SYNTAX      DisplayString (SIZE (0..30))
                    ACCESS      read-write
                    STATUS      mandatory
                    DESCRIPTION
                            "The name given to TyView system."
                    ::= { tyviewSysTable 2 }

tyviewSysId	    OBJECT-TYPE
                    SYNTAX      INTEGER 
                    ACCESS      read-only
                    STATUS      mandatory
                    DESCRIPTION
                            "The TyView system ID."
                    ::= { tyviewSysTable 3 }

tyviewSysTimeOutFactor	    OBJECT-TYPE
                    SYNTAX      INTEGER 
                    ACCESS      read-write
                    STATUS      mandatory
                    DESCRIPTION
                            "The TyView timeout factor."
                    ::= { tyviewSysTable 4 }

tyviewSysObjectId   OBJECT-TYPE
                    SYNTAX      DisplayString (SIZE (0..30))
                    ACCESS      read-write
                    STATUS      mandatory
                    DESCRIPTION
                            "The Tyview Domain Object Identifier."
                    ::= { tyviewSysTable 5 }

tyviewSysSlotNumber	    OBJECT-TYPE
                    SYNTAX      INTEGER 
                    ACCESS      read-only
                    STATUS      mandatory
                    DESCRIPTION
                            "The Physical Slot Number the NETEXEC is installed in."
                    ::= { tyviewSysTable 6 }

tyviewSysClearDatabase OBJECT-TYPE
                    SYNTAX      INTEGER 
                    {
                    clearDatabase (1)
                    }
                    ACCESS      write-only
                    STATUS      mandatory
                    DESCRIPTION
                            "Clear the node database."
                    ::= { tyviewSysTable 7 }

tyviewSysGetCommName OBJECT-TYPE
                    SYNTAX      DisplayString (SIZE (0..32))
                    ACCESS      read-write
                    STATUS      mandatory
                    DESCRIPTION
                            "The GET community name."
                    ::= { tyviewSysTable 8 }

tyviewSysSetCommName OBJECT-TYPE
                    SYNTAX      DisplayString (SIZE (0..32))
                    ACCESS      read-write
                    STATUS      mandatory
                    DESCRIPTION
                            "The SET community name."
                    ::= { tyviewSysTable 9 }

tyviewSysTrapCommName OBJECT-TYPE
                    SYNTAX      DisplayString (SIZE (0..32))
                    ACCESS      read-write
                    STATUS      mandatory
                    DESCRIPTION
                            "The TRAP community name."
                    ::= { tyviewSysTable 10 }

tyviewSysN1TrapDest OBJECT-TYPE
                    SYNTAX      DisplayString (SIZE (0..15))
                    ACCESS      read-write
                    STATUS      mandatory
                    DESCRIPTION
                            "The first Trap IP Destination."
                    ::= { tyviewSysTable 11 }

tyviewSysN2TrapDest OBJECT-TYPE
                    SYNTAX      DisplayString (SIZE (0..15))
                    ACCESS      read-write
                    STATUS      mandatory
                    DESCRIPTION
                            "The second Trap IP Destination."
                    ::= { tyviewSysTable 12 }

tyviewSysDate       OBJECT-TYPE
                    SYNTAX      DisplayString (SIZE (0..8))
                    ACCESS      read-write
                    STATUS      mandatory
                    DESCRIPTION
                            "The NETEXEC date (mm/dd/yy)."
                    ::= { tyviewSysTable 13 }

tyviewSysTime       OBJECT-TYPE
                    SYNTAX      DisplayString (SIZE (0..5))
                    ACCESS      read-write
                    STATUS      mandatory
                    DESCRIPTION
                            "The NETEXEC time (hh:mm)."
                    ::= { tyviewSysTable 14 }

tyviewSysMjrMnrLED  OBJECT-TYPE
                    SYNTAX      INTEGER 
                    {
                    led-Off (1),
                    led-Red (2),
                    led-Green (3),
                    led-Yellow (4),
                    led-RedYellow (5)
                    }
                    ACCESS      read-only
                    STATUS      mandatory
                    DESCRIPTION
                            "The Major/Minor LED status."
                    ::= { tyviewSysTable 15 }

tyviewSysFanPSLED   OBJECT-TYPE
                    SYNTAX      INTEGER 
                    {
                    led-Off (1),
                    led-Red (2),
                    led-Green (3),
                    led-Yellow (4),
                    led-RedYellow (5)
                    }
                    ACCESS      read-only
                    STATUS      mandatory
                    DESCRIPTION
                            "The Fan / Power Supply LED status."
                    ::= { tyviewSysTable 16 }

tyviewSysCtlrLED    OBJECT-TYPE
                    SYNTAX      INTEGER 
                    {
                    led-Off (1),
                    led-Red (2),
                    led-Green (3),
                    led-Yellow (4),
                    led-RedYellow (5)
                    }
                    ACCESS      read-only
                    STATUS      mandatory
                    DESCRIPTION
                            "The Controller LED status."
                    ::= { tyviewSysTable 17 }

tyviewSysSlipLED    OBJECT-TYPE
                    SYNTAX      INTEGER 
                    {
                    led-Off (1),
                    led-Red (2),
                    led-Green (3),
                    led-Yellow (4),
                    led-RedYellow (5)
                    }
                    ACCESS      read-only
                    STATUS      mandatory
                    DESCRIPTION
                            "The SLIP LED status."
                    ::= { tyviewSysTable 18 }

tyviewSysCtlChLED   OBJECT-TYPE
                    SYNTAX      INTEGER 
                    {
                    led-Off (1),
                    led-Red (2),
                    led-Green (3),
                    led-Yellow (4),
                    led-RedYellow (5)
                    }
                    ACCESS      read-only
                    STATUS      mandatory
                    DESCRIPTION
                            "The Control Channel LED status."
                    ::= { tyviewSysTable 19 }

tyviewSysTDMLED     OBJECT-TYPE
                    SYNTAX      INTEGER 
                    {
                    led-Off (1),
                    led-Red (2),
                    led-Green (3),
                    led-Yellow (4),
                    led-RedYellow (5)
                    }
                    ACCESS      read-only
                    STATUS      mandatory
                    DESCRIPTION
                            "The TDM LED status."
                    ::= { tyviewSysTable 20 }

tyviewSysMaintUseage OBJECT-TYPE
                    SYNTAX      INTEGER 
                    {
                    none (1),
                    command (2),
                    slip (3),
                    tp-modem (4),
                    diagnostic (5),
                    ppp (6)
                    }
                    ACCESS      read-write
                    STATUS      mandatory
                    DESCRIPTION
                            "The Maintenance Port useage specification."
                    ::= { tyviewSysTable 21 }

tyviewSysMaintDataBits OBJECT-TYPE
                    SYNTAX      INTEGER 
                    {
                    databits-7 (1),
                    databits-8 (2)
                    }
                    ACCESS      read-write
                    STATUS      mandatory
                    DESCRIPTION
                            "The Maintenance Port databits specification."
                    ::= { tyviewSysTable 22 }

tyviewSysMaintRate  OBJECT-TYPE
                    SYNTAX      INTEGER 
                    {
                    rate-1200 (1),
                    rate-2400 (2),
                    rate-4800 (3),
                    rate-9600 (4),
                    rate-19200 (5)
                    }
                    ACCESS      read-write
                    STATUS      mandatory
                    DESCRIPTION
                            "The Maintenance Port rate specification."
                    ::= { tyviewSysTable 23 }

tyviewSysMaintStopBits OBJECT-TYPE
                    SYNTAX      INTEGER 
                    {
                    stopbits-1 (1),
                    stopbits-2 (2)
                    }
                    ACCESS      read-write
                    STATUS      mandatory
                    DESCRIPTION
                            "The Maintenance Port stopbits specification."
                    ::= { tyviewSysTable 24 }

tyviewSysMaintParity OBJECT-TYPE
                    SYNTAX      INTEGER 
                    {
                    none (1),
                    odd (2),
                    even (3)
                    }
                    ACCESS      read-write
                    STATUS      mandatory
                    DESCRIPTION
                            "The Maintenance Port parity specification."
                    ::= { tyviewSysTable 25 }

tyviewSysMaintMtu   OBJECT-TYPE
                    SYNTAX      INTEGER 
                    ACCESS      read-write
                    STATUS      mandatory
                    DESCRIPTION
                            "The Maintenance Port maximum trans unit size."
                    ::= { tyviewSysTable 26 }

tyviewSysMaintCompression OBJECT-TYPE
                    SYNTAX      INTEGER 
                    {
                    off (1),
                    on (2)
                    }
                    ACCESS      read-write
                    STATUS      mandatory
                    DESCRIPTION
                            "The Maintenance Port compression specification."
                    ::= { tyviewSysTable 27 }

tyviewSysMaintSubnetMask OBJECT-TYPE
                    SYNTAX      DisplayString (SIZE (0..15))
                    ACCESS      read-write
                    STATUS      mandatory
                    DESCRIPTION
                            "The Maintenance Port subnet mask."
                    ::= { tyviewSysTable 28 }

tyviewSysMaintLocalIP OBJECT-TYPE
                    SYNTAX      DisplayString (SIZE (0..15))
                    ACCESS      read-write
                    STATUS      mandatory
                    DESCRIPTION
                            "The Maintenance Port local IP address."
                    ::= { tyviewSysTable 29 }

tyviewSysMaintPeerIP OBJECT-TYPE
                    SYNTAX      DisplayString (SIZE (0..15))
                    ACCESS      read-write
                    STATUS      mandatory
                    DESCRIPTION
                            "The Maintenance Port peer IP address."
                    ::= { tyviewSysTable 30 }

tyviewSysComUseage  OBJECT-TYPE
                    SYNTAX      INTEGER 
                    {
                    none (1),
                    command (2),
                    slip (3),
                    tp-modem (4),
                    diagnostic (5),
                    ppp (6)
                    }
                    ACCESS      read-write
                    STATUS      mandatory
                    DESCRIPTION
                            "The Com Port useage specification."
                    ::= { tyviewSysTable 31 }

tyviewSysComDataBits OBJECT-TYPE
                    SYNTAX      INTEGER 
                    {
                    databits-7 (1),
                    databits-8 (2)
                    }
                    ACCESS      read-write
                    STATUS      mandatory
                    DESCRIPTION
                            "The Com Port databits specification."
                    ::= { tyviewSysTable 32 }

tyviewSysComRate    OBJECT-TYPE
                    SYNTAX      INTEGER 
                    {
                    rate-1200 (1),
                    rate-2400 (2),
                    rate-4800 (3),
                    rate-9600 (4),
                    rate-19200 (5)
                    }
                    ACCESS      read-write
                    STATUS      mandatory
                    DESCRIPTION
                            "The Com Port rate specification."
                    ::= { tyviewSysTable 33 }

tyviewSysComStopBits OBJECT-TYPE
                    SYNTAX      INTEGER 
                    {
                    stopbits-1 (1),
                    stopbits-2 (2)
                    }
                    ACCESS      read-write
                    STATUS      mandatory
                    DESCRIPTION
                            "The Com Port stopbits specification."
                    ::= { tyviewSysTable 34 }

tyviewSysComParity  OBJECT-TYPE
                    SYNTAX      INTEGER 
                    {
                    none (1),
                    odd (2),
                    even (3)
                    }
                    ACCESS      read-write
                    STATUS      mandatory
                    DESCRIPTION
                            "The Com Port parity specification."
                    ::= { tyviewSysTable 35 }

tyviewSysComMtu     OBJECT-TYPE
                    SYNTAX      INTEGER 
                    ACCESS      read-write
                    STATUS      mandatory
                    DESCRIPTION
                            "The Com Port maximum trans unit size."
                    ::= { tyviewSysTable 36 }

tyviewSysComCompression OBJECT-TYPE
                    SYNTAX      INTEGER 
                    {
                    off (1),
                    on (2)
                    }
                    ACCESS      read-write
                    STATUS      mandatory
                    DESCRIPTION
                            "The Com Port compression specification."
                    ::= { tyviewSysTable 37 }

tyviewSysComSubnetMask OBJECT-TYPE
                    SYNTAX      DisplayString (SIZE (0..15))
                    ACCESS      read-write
                    STATUS      mandatory
                    DESCRIPTION
                            "The Com Port subnet mask."
                    ::= { tyviewSysTable 38 }

tyviewSysComLocalIP OBJECT-TYPE
                    SYNTAX      DisplayString (SIZE (0..15))
                    ACCESS      read-write
                    STATUS      mandatory
                    DESCRIPTION
                            "The Com Port local IP address."
                    ::= { tyviewSysTable 39 }

tyviewSysComPeerIP  OBJECT-TYPE
                    SYNTAX      DisplayString (SIZE (0..15))
                    ACCESS      read-write
                    STATUS      mandatory
                    DESCRIPTION
                            "The Com Port peer IP address."
                    ::= { tyviewSysTable 40 }

tyviewSysTelnetEna  OBJECT-TYPE
                    SYNTAX      INTEGER 
                    {
                    disabled (1),
                    enabled (2)
                    }
                    ACCESS      read-write
                    STATUS      mandatory
                    DESCRIPTION
                            "The Telnet log-in enable."
                    ::= { tyviewSysTable 41 }

tyviewSysTelnetTO   OBJECT-TYPE
                    SYNTAX      INTEGER 
                    ACCESS      read-write
                    STATUS      mandatory
                    DESCRIPTION
                            "The Telnet auto-logout timeout (minutes)."
                    ::= { tyviewSysTable 42 }

tyviewSysClrMjrMin  OBJECT-TYPE
                    SYNTAX      INTEGER 
                    {
                    clearMajorMinor (1)
                    }
                    ACCESS      write-only
                    STATUS      mandatory
                    DESCRIPTION
                            "Clear major/minor alarm window / LED."
                    ::= { tyviewSysTable 43 }

tyviewDatabaseTable OBJECT-TYPE
                    SYNTAX      SEQUENCE OF TyviewDatabaseEntry
                    ACCESS      not-accessible
                    STATUS      mandatory
                    DESCRIPTION
                            "A list of tyview database entries." 
                    ::= { tyview 2 }

tyviewDatabaseEntry OBJECT-TYPE
                    SYNTAX      TyviewDatabaseEntry
                    ACCESS      not-accessible
                    STATUS      mandatory
                    DESCRIPTION
                            "System Object for TyView Database"
                    INDEX { tyviewDatabaseSlot, tyviewDatabaseNode }
                    ::= { tyviewDatabaseTable 1 }

TyviewDatabaseEntry ::=
                    SEQUENCE
                    {
                    tyviewDatabaseSlot
                        INTEGER(1..16),
                    tyviewDatabaseNode
                        INTEGER(1..255),
                    tyviewDatabaseName
                        DisplayString (SIZE (0..8)),
                    tyviewDatabaseStatus
                        INTEGER
		    }

tyviewDatabaseSlot  OBJECT-TYPE
                    SYNTAX      INTEGER (1..16)
                    ACCESS      read-only
                    STATUS      mandatory
                    DESCRIPTION
                            "The PC port to which the node is attached."
                    ::= { tyviewDatabaseEntry 1 }

tyviewDatabaseNode  OBJECT-TYPE
                    SYNTAX      INTEGER (1..255)
                    ACCESS      read-only
                    STATUS      mandatory
                    DESCRIPTION
                            "The node ID: unique per port ID."
                    ::= { tyviewDatabaseEntry 2 }

tyviewDatabaseName  OBJECT-TYPE
                    SYNTAX      DisplayString (SIZE (0..8))
                    ACCESS      read-write
                    STATUS      mandatory
                    DESCRIPTION
                            "The unique name of the node."
                    ::= { tyviewDatabaseEntry 3 }

tyviewDatabaseStatus OBJECT-TYPE
                    SYNTAX      INTEGER
                    {
                    ok (1),
                    timeout (2),
                    error (3)
                    }
                    ACCESS      read-only
                    STATUS      mandatory
                    DESCRIPTION
                            "The last comm status."
                    ::= { tyviewDatabaseEntry 4 }

tyviewBroadcastTable OBJECT IDENTIFIER ::= { tyview 3 }

tyviewBroadcastSetTime OBJECT-TYPE
                    SYNTAX      INTEGER
                    {
                    setTime (1)
                    }
                    ACCESS      write-only
                    STATUS      mandatory
                    DESCRIPTION
                            "Broadcast the time to all nodes."
                    ::= { tyviewBroadcastTable 1 }

tyviewBroadcastForwardAlarms OBJECT-TYPE
                    SYNTAX      INTEGER
                    {
                    forwardAlarms (1)
                    }
                    ACCESS      write-only
                    STATUS      mandatory
                    DESCRIPTION
                            "Broadcast alarm forwarding."
                    ::= { tyviewBroadcastTable 2 }

tyviewBroadcastClearLoopbacks OBJECT-TYPE
                    SYNTAX      INTEGER
                    {
                    clearNetLoopbacks (1),
                    clearChanLoopbacks (2)
                    }
                    ACCESS      write-only
                    STATUS      mandatory
                    DESCRIPTION
                            "Broadcast Clearing of loopbacks."
                    ::= { tyviewBroadcastTable 3 }

tyviewTPTable       OBJECT-TYPE
                    SYNTAX      SEQUENCE OF TyviewTPEntry
                    ACCESS      not-accessible
                    STATUS      mandatory
                    DESCRIPTION
                            "A list of Threshold Processing records." 
                    ::= { tyview 4 }

tyviewTPEntry       OBJECT-TYPE
                    SYNTAX      TyviewTPEntry
                    ACCESS      not-accessible
                    STATUS      mandatory
                    DESCRIPTION
                            "System Object for Threshold Processing"
                    INDEX { tyviewTPRecord }
                    ::= { tyviewTPTable 1 }

TyviewTPEntry      ::=
                    SEQUENCE
                    {
                    tyviewTPRecord
                        INTEGER(1..25),
                    tyviewTPMonNodeMode
                        INTEGER,
                    tyviewTPNode
                        DisplayString (SIZE (0..8)),
                    tyviewTPAlarmType
                        INTEGER,
                    tyviewTPTriggerEvent
                        INTEGER,
                    tyviewTPInstance
                        INTEGER,
                    tyviewTPInterval
                        INTEGER,
                    tyviewTPEventAction
                        DisplayString (SIZE (0..32)),
                    tyviewTPDryContact
                        INTEGER,
                    tyviewTPClearDryContact
                        INTEGER
                    }

tyviewTPRecord      OBJECT-TYPE
                    SYNTAX      INTEGER (1..25)
                    ACCESS      read-only
                    STATUS      mandatory
                    DESCRIPTION
                            "The Threshold Processing record referenced."
                    ::= { tyviewTPEntry 1 }
 
tyviewTPMonNodeMode OBJECT-TYPE
                    SYNTAX      INTEGER
                    {
                    none (1),
                    all-nodes (2),
                    node-specific (3)
                    }
                    ACCESS      read-write
                    STATUS      mandatory
                    DESCRIPTION
                            "The mode used for monitoring nodes."
                    ::= { tyviewTPEntry 2 }

tyviewTPNode        OBJECT-TYPE
                    SYNTAX      DisplayString (SIZE (0..8))
                    ACCESS      read-write
                    STATUS      mandatory
                    DESCRIPTION
                            "The node name for node-specific monitoring."
                    ::= { tyviewTPEntry 3 }

tyviewTPAlarmType   OBJECT-TYPE
                    SYNTAX      INTEGER
                    {
                    major (1),
                    minor (2),
                    all (3)
                    }
                    ACCESS      read-write
                    STATUS      mandatory
                    DESCRIPTION
                            "The alarm type used to trigger."
                    ::= { tyviewTPEntry 4 }

tyviewTPTriggerEvent OBJECT-TYPE
                    SYNTAX      INTEGER
                    {
                    alarm-on (1),
                    alarm-instance (2)
                    }
                    ACCESS      read-write
                    STATUS      mandatory
                    DESCRIPTION
                            "The event type used to trigger."
                    ::= { tyviewTPEntry 5 }

tyviewTPInstance    OBJECT-TYPE
                    SYNTAX      INTEGER
                    ACCESS      read-write
                    STATUS      mandatory
                    DESCRIPTION
                            "The alarm instance used to trigger."
                    ::= { tyviewTPEntry 6 }

tyviewTPInterval    OBJECT-TYPE
                    SYNTAX      INTEGER
                    ACCESS      read-write
                    STATUS      mandatory
                    DESCRIPTION
                            "The alarm interval used to trigger."
                    ::= { tyviewTPEntry 7 }

tyviewTPEventAction OBJECT-TYPE
                    SYNTAX      DisplayString (SIZE (0..32))
                    ACCESS      read-write
                    STATUS      mandatory
                    DESCRIPTION
                            "The phone number dialed when triggered."
                    ::= { tyviewTPEntry 8 }

tyviewTPDryContact  OBJECT-TYPE
                    SYNTAX      INTEGER
                    {
                    dry-contact-off (1),
                    dry-contact-major (2),
                    dry-contact-minor (3)
                    }
                    ACCESS      read-write
                    STATUS      mandatory
                    DESCRIPTION
                            "The type of Dry Contact when triggered."
                    ::= { tyviewTPEntry 9 }

tyviewTPClearDryContact  OBJECT-TYPE
                    SYNTAX      INTEGER
                    {
                    clear-major (1),
                    clear-minor (2)
                    }
                    ACCESS      write-only
                    STATUS      mandatory
                    DESCRIPTION
                            "Clear major/minor Dry Contact."
                    ::= { tyviewTPEntry 10 }

-- =========================
-- ==        TRAPS        ==
-- =========================
--
--       The Alarm (Trap) table for the NETEXEC.
--              This table contains definitions for enterprise specific traps
--              associated with the NETEXEC.
dsucsuTrap          TRAP-TYPE
                    ENTERPRISE  dsucsu
                    VARIABLES
                    { 
                    dsucsuAlarmType,
                    dsucsuAlarmSlot,
                    dsucsuAlarmNode,
                    dsucsuAlarmName
                    }
                    DESCRIPTION
                            "A dsucsuTrap trap signifies that the
                            sending node had its `dsucsuAlarmType`
                            variable modified."
                    ::= 0

END
