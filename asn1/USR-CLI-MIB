USR-CLI-MIB DEFINITIONS ::= BEGIN
	IMPORTS
        MODULE-IDENTITY, OBJECT-TYPE, Integer32
                  FROM SNMPv2-SMI
        DisplayString
                  FROM SNMPv2-TC
        UsrConfigStatus, common
                  FROM USR-DEFINITIONS-MIB;
    usrCli MODULE-IDENTITY
         LAST-UPDATED "200208231250Z"
         ORGANIZATION "CommWorks Corporation, a 3Com Company"
         CONTACT-INFO "Customer Support"
         DESCRIPTION
                 "The commWorks enterprise defined MIB objects
                   for the CLI"
--       REVISION    "200201091935Z"
--       DESCRIPTION "MODULE-IDENTITY created."
--       REVISION    "200208231350Z"
--       DESCRIPTION "Changed usrCliGlobalPageBreak from simple
--                    integer to enumerated integer."
     ::= { common 22 }
   -- Begin managed object definitions here...
usrCliVersion OBJECT-TYPE
	SYNTAX		DisplayString
	MAX-ACCESS	read-only
	STATUS		obsolete
	DESCRIPTION
		"The current software version of the Command Line Interpreter
	       process.."
::= { usrCli 1 }
usrCliConfigFileName OBJECT-TYPE
	SYNTAX		DisplayString
	MAX-ACCESS	read-only
	STATUS		current
	DESCRIPTION		
		  "The name of a ConfigFile to read/write permanent database
                   records."
	::= { usrCli 2 }
usrCliCFMStatusFlag OBJECT-TYPE
	SYNTAX		UsrConfigStatus
	MAX-ACCESS	read-write
	STATUS		current
	DESCRIPTION
		"This variable controls saving and loading of configuration
           information for the CLI process. The value can 
           be set to either save or load by a management station. The other
           values indicate if any configuration operation and what type
           is in progress."
::= { usrCli 3 }
usrCliHistoryDepth OBJECT-TYPE
     SYNTAX   Integer32
     MAX-ACCESS   read-write
     STATUS   current
     DESCRIPTION
            "The number of commands to be held in the History Array."
	--CONFIGURABLE
::= { usrCli 4 }
usrCliPrompt OBJECT-TYPE
     SYNTAX   DisplayString
     MAX-ACCESS   read-write
     STATUS   current
     DESCRIPTION
            "The specific prompt to be used for this CLI."
	--CONFIGURABLE
::= { usrCli 5 }
usrCliConsoleLogin OBJECT-TYPE
     SYNTAX   INTEGER {no(1),yes(2) }
     MAX-ACCESS   read-write
     STATUS   current
     DESCRIPTION
            "Whether the Console user will be required to log in.
		This defaults to Enabled and can only be changed by
		a privileged user."
	--CONFIGURABLE
::= { usrCli 6 }
usrCliConsoleIdleTimeout OBJECT-TYPE
     SYNTAX   Integer32 (0..60)
     MAX-ACCESS   read-write
     STATUS   current
     DESCRIPTION
            "If Console user is required to log in, there will be
		an idle timeout specified in minutes.  
		This will default to 5 minutes.
		There is a max of 60 minutes.  
		If this is set to 0, there will be no timeout. 
		This can only be modified by a privileged user."
	--CONFIGURABLE
::= { usrCli 7 }
usrCliGlobalPageBreak OBJECT-TYPE
     SYNTAX       INTEGER {
                    disabled(0),
                    enabled(1)
                    }
     MAX-ACCESS   read-write
     STATUS   current
     DESCRIPTION
        "This is a flag which says whether global page break is 
         enabled/disabled "
    --CONFIGURABLE
::= { usrCli 8 }
usrCliGlobalPageSize OBJECT-TYPE
     SYNTAX   Integer32
     MAX-ACCESS   read-write
     STATUS   current
     DESCRIPTION
        " This is a flag which says whether local page break is 
          enabled/disabled "
    --CONFIGURABLE
::= { usrCli 9 }
END         -- End CLI MIB definitions
-- ************************************************************************
--
--	usr_adsl.mib - ADSL Driver MIB
--
-- Author:         Jim Halpin
--
