Wellfleet-X25-MIB DEFINITIONS ::= BEGIN

-- Created by mdl2asn version 3.1
-- Creation date: Wed Aug 30 16:50:09 EDT 1995


    IMPORTS

      IpAddress, Counter, Gauge
        FROM RFC1155-SMI
      OBJECT-TYPE
        FROM RFC-1212
      DisplayString
        FROM RFC1213-MIB
      wfX25Group
        FROM Wellfleet-COMMON-MIB;


    wfX25		OBJECT IDENTIFIER ::= { wfX25Group 1 }

    wfX25Delete OBJECT-TYPE
        SYNTAX	INTEGER {
    		    created(1),
    		    deleted(2)
    		}
        ACCESS	read-write
        STATUS	mandatory
        DESCRIPTION
                "Create/Delete parameter. Default is created."
        DEFVAL	{ created }
        ::= { wfX25 1 }

    wfX25Disable OBJECT-TYPE
        SYNTAX	INTEGER {
    		    enabled(1),
    		    disabled(2)
    		}
        ACCESS	read-write
        STATUS	mandatory
        DESCRIPTION
                "Enable/Disable parameter. Default is enabled."
        DEFVAL	{ enabled }
        ::= { wfX25 2 }

    wfX25State OBJECT-TYPE
        SYNTAX	INTEGER {
    		    up(1),
    		    down(2),
    		    init(3),
    		    notpresent(4)
    		}
        ACCESS	read-only
        STATUS	mandatory
        DESCRIPTION
                "The current state of the entire X.25."
        DEFVAL	{ notpresent }
        ::= { wfX25 3 }

    wfX25ServiceTable OBJECT-TYPE
        SYNTAX	SEQUENCE OF WfX25ServiceEntry
        ACCESS	not-accessible
        STATUS	mandatory
        DESCRIPTION
                "This table describes the services of a circuit on an X.25 line."
        ::= { wfX25Group 2 }

    wfX25ServiceEntry OBJECT-TYPE
        SYNTAX	WfX25ServiceEntry
        ACCESS	not-accessible
        STATUS	mandatory
        DESCRIPTION
                "An entry in the X25 Service table."
        INDEX	{ wfX25ServiceSlot,
    		  wfX25ServiceConnector,
    		  wfX25ServiceLineNumber,
    		  wfX25ServiceLLIndex,
    		  wfX25ServiceCct,
    		  wfX25ServiceIndex }
        ::= { wfX25ServiceTable 1 }

    WfX25ServiceEntry ::= SEQUENCE {
    	    wfX25ServiceDelete
    		INTEGER,
    	    wfX25ServiceDisable
    		INTEGER,
    	    wfX25ServiceSlot
    		INTEGER,
    	    wfX25ServiceConnector
    		INTEGER,
    	    wfX25ServiceLineNumber
    		INTEGER,
    	    wfX25ServiceLLIndex
    		INTEGER,
    	    wfX25ServiceCct
    		INTEGER,
    	    wfX25ServiceIndex
    		INTEGER,
    	    wfX25ServiceType
    		INTEGER,
    	    wfX25ServiceConnRef
    		INTEGER,
    	    wfX25ServiceConnId
    		INTEGER,
    	    wfX25ServiceRemoteX121Addr
    		DisplayString,
    	    wfX25ServiceRemoteIpAddr
    		IpAddress,
    	    wfX25ServiceBCast
    		INTEGER,
    	    wfX25ServiceMaxConn
    		INTEGER,
    	    wfX25ServicePrecedence
    		INTEGER,
    	    wfX25ServiceMaxIdle
    		INTEGER,
    	    wfX25ServiceCallRetry
    		INTEGER,
    	    wfX25ServiceFlowFacility
    		INTEGER,
    	    wfX25ServiceWinSize
    		INTEGER,
    	    wfX25ServicePktSize
    		INTEGER,
    	    wfX25ServiceFastSelRequest
    		INTEGER,
    	    wfX25ServiceFastSelAccept
    		INTEGER,
    	    wfX25ServiceRevChRequest
    		INTEGER,
    	    wfX25ServiceRevChAccept
    		INTEGER,
    	    wfX25ServiceCugFormat
    		INTEGER,
    	    wfX25ServiceCugType
    		INTEGER,
    	    wfX25ServiceCugNum
    		INTEGER,
    	    wfX25ServiceUserFacility
    		OCTET STRING,
    	    wfX25ServiceValid
    		INTEGER,
    	    wfX25ServiceBFE
    		INTEGER,
    	    wfX25ServiceForceCugZero
    		INTEGER,
    	    wfX25ServiceWcpEnable
    		INTEGER,
    	    wfX25ServiceMUX
    		INTEGER,
            wfX25ServicePtopCallRequest
                INTEGER,
            wfX25ServiceVcType
                INTEGER,
            wfX25ServicePvcLcn
                INTEGER,
            wfX25ServiceMacPoolStart
                OCTET STRING,
            wfX25ServiceMacPoolSize
                INTEGER,
            wfX25ServiceWindowTimeout
                INTEGER,
            wfX25ServiceVcBurstThroughput
                INTEGER,
            wfX25ServiceVcBurstQDepth
                INTEGER,
            wfX25ServiceVcPriority
                INTEGER,
            wfX25ServiceVcBurstQClippedPkts
                Counter,
            wfX25ServiceVcBurstQPktCnt
                Counter,
            wfX25ServiceVcBurstQHighWaterPkts
                Gauge,
            wfX25ServiceVcPktDrops
                Counter,
            wfX25ServicePlpPktDrops
                Counter,
            wfX25ServiceBurstThrPerVc
                INTEGER,
	    wfX25ServiceBackupRecoveryDelay
		INTEGER,
	    wfX25ServiceSetupTime
		INTEGER,
	    wfX25ServiceRetryNumber
		INTEGER,
	    wfX25BackupInitiation
		INTEGER,
            wfX25ServiceEntryName
                DisplayString

        }

    wfX25ServiceDelete OBJECT-TYPE
        SYNTAX	INTEGER {
    		    created(1),
    		    deleted(2)
    		}
        ACCESS	read-write
        STATUS	mandatory
        DESCRIPTION
                "Create/Delete parameter, default = created."
        DEFVAL	{ created }
        ::= { wfX25ServiceEntry 1 }

    wfX25ServiceDisable OBJECT-TYPE
        SYNTAX	INTEGER {
    		    enabled(1),
    		    disabled(2)
    		}
        ACCESS	read-write
        STATUS	mandatory
        DESCRIPTION
                "Enable/Disable parameter, default = enabled."
        DEFVAL	{ enabled }
        ::= { wfX25ServiceEntry 2 }

    wfX25ServiceSlot OBJECT-TYPE
        SYNTAX	INTEGER(1..14)
        ACCESS	read-only
        STATUS	mandatory
        DESCRIPTION
                "Slot number and part of Instance Id."
        ::= { wfX25ServiceEntry 3 }

    wfX25ServiceConnector OBJECT-TYPE
        SYNTAX	INTEGER {
    		    one(1),
    		    two(2),
    		    three(3),
    		    four(4)
    		}
        ACCESS	read-only
        STATUS	mandatory
        DESCRIPTION
                "Connector number and instance ID member."
        ::= { wfX25ServiceEntry 4 }

    wfX25ServiceLineNumber OBJECT-TYPE
        SYNTAX	INTEGER
        ACCESS	read-only
        STATUS	mandatory
        DESCRIPTION
                "Instance identifier member. This is the line number assigned
                to the driver X.25 is running over.  No used in 7.60."
        ::= { wfX25ServiceEntry 5 }

    wfX25ServiceLLIndex OBJECT-TYPE
        SYNTAX	INTEGER
        ACCESS	read-only
        STATUS	mandatory
        DESCRIPTION
                "Instance identifier member. This is the lower layer index
                presented to X25 by the layer immediately below it on the
                protocol stack. If the lower layer is a driver, the index
                will be 0. Not used in 7.60."
        ::= { wfX25ServiceEntry 6 }

    wfX25ServiceCct OBJECT-TYPE
        SYNTAX	INTEGER(1..1024)
        ACCESS	read-only
        STATUS	mandatory
        DESCRIPTION
                "Circuit number and instance ID member."
        ::= { wfX25ServiceEntry 7 }

    wfX25ServiceIndex OBJECT-TYPE
        SYNTAX	INTEGER(1..4000)
        ACCESS	read-only
        STATUS	mandatory
        DESCRIPTION
                "X.25 service entry record ID for this instance."
        ::= { wfX25ServiceEntry 8 }

    wfX25ServiceType OBJECT-TYPE
        SYNTAX	INTEGER {
    		    pdntype(1),
    		    ddntype(2),
    		    ptoptype(4),
    		    npttype(8),
    		    ipextype(16),
        	    qllctype(32),
        	    defaulttype(64)
    		}
        ACCESS	read-write
        STATUS	mandatory
        DESCRIPTION
                "Type of Service."
        ::= { wfX25ServiceEntry 9 }

    wfX25ServiceConnRef OBJECT-TYPE
        SYNTAX	INTEGER {
    		    on(1),
    		    off(2)
    		}
        ACCESS	read-only
        STATUS	mandatory
        DESCRIPTION
                "Use of Connection Reference Numbers in Call Request
                For PDN only, if ON then use wfX25ServiceConnId as
                starting reference number for PDN."
        DEFVAL	{ off }
        ::= { wfX25ServiceEntry 10 }

    wfX25ServiceConnId OBJECT-TYPE
        SYNTAX	INTEGER(1..255)
        ACCESS	read-write
        STATUS	mandatory
        DESCRIPTION
                "Connection Id to be used in a PTOP Call request. For PDN this will
                be the starting number to be used as Connection Id in PDN."
        DEFVAL	{ 1 }
        ::= { wfX25ServiceEntry 11 }

    wfX25ServiceRemoteX121Addr OBJECT-TYPE
        SYNTAX	DisplayString
        ACCESS	read-write
        STATUS	mandatory
        DESCRIPTION
                "Remote X.121 address for this table entry instance."
        ::= { wfX25ServiceEntry 12 }

    wfX25ServiceRemoteIpAddr OBJECT-TYPE
        SYNTAX	IpAddress
        ACCESS	read-write
        STATUS	mandatory
        DESCRIPTION
                "Remote IP address for PDN and DDN only."
        ::= { wfX25ServiceEntry 13 }

    wfX25ServiceBCast OBJECT-TYPE
        SYNTAX	INTEGER {
    		    on(1),
    		    off(2)
    		}
        ACCESS	read-write
        STATUS	mandatory
        DESCRIPTION
                "Broadcast recipient status for this table entry instance."
        DEFVAL	{ off }
        ::= { wfX25ServiceEntry 14 }

    wfX25ServiceMaxConn OBJECT-TYPE
        SYNTAX	INTEGER(1..4)
        ACCESS	read-write
        STATUS	mandatory
        DESCRIPTION
                "Maximum connections per destination for this table entry instance."
        DEFVAL	{ 2 }
        ::= { wfX25ServiceEntry 15 }

    wfX25ServicePrecedence OBJECT-TYPE
        SYNTAX	INTEGER {
    		    negot(1),
    		    default(2)
    		}
        ACCESS	read-write
        STATUS	mandatory
        DESCRIPTION
                "Precedence value for this table entry instance. DDN only."
        DEFVAL	{ default }
        ::= { wfX25ServiceEntry 16 }

    wfX25ServiceMaxIdle OBJECT-TYPE
        SYNTAX	INTEGER(1..999)
        ACCESS	read-write
        STATUS	mandatory
        DESCRIPTION
                "Maximum Idle Time in Minutes for this table entry instance. If 0
                is entered the connection stays on forever."
        DEFVAL	{ 2 }
        ::= { wfX25ServiceEntry 17 }

    wfX25ServiceCallRetry OBJECT-TYPE
        SYNTAX	INTEGER(10..999)
        ACCESS	read-write
        STATUS	mandatory
        DESCRIPTION
                "Interval in seconds between Call Request to same the destination.
                Must be at least 2 times T11/T21 Timer for Packet Level."
        DEFVAL	{ 60 }
        ::= { wfX25ServiceEntry 18 }

    wfX25ServiceFlowFacility OBJECT-TYPE
        SYNTAX	INTEGER {
    		    negot(1),
    		    default(2)
    		}
        ACCESS	read-write
        STATUS	mandatory
        DESCRIPTION
                "Flow Control negotiation facility parameter for this instance."
        DEFVAL	{ default }
        ::= { wfX25ServiceEntry 19 }

    wfX25ServiceWinSize OBJECT-TYPE
        SYNTAX	INTEGER(1..127)
        ACCESS	read-write
        STATUS	mandatory
        DESCRIPTION
                "Packet window size parameter for this table entry instance."
        DEFVAL	{ 2 }
        ::= { wfX25ServiceEntry 20 }

    wfX25ServicePktSize OBJECT-TYPE
        SYNTAX	INTEGER {
    		    size16(4),
    		    size32(5),
    		    size64(6),
    		    size128(7),
    		    size256(8),
    		    size512(9),
    		    size1024(10),
    		    size2048(11),
    		    size4096(12)
    		}
        ACCESS	read-write
        STATUS	mandatory
        DESCRIPTION
                "Packet size parameter for this table entry instance."
        DEFVAL	{ size128 }
        ::= { wfX25ServiceEntry 21 }

    wfX25ServiceFastSelRequest OBJECT-TYPE
        SYNTAX	INTEGER {
    		    on(1),
    		    off(2)
    		}
        ACCESS	read-write
        STATUS	mandatory
        DESCRIPTION
                "Fast Select Request Facility for this table entry instance."
        DEFVAL	{ off }
        ::= { wfX25ServiceEntry 22 }

    wfX25ServiceFastSelAccept OBJECT-TYPE
        SYNTAX	INTEGER {
    		    on(1),
    		    off(2)
    		}
        ACCESS	read-write
        STATUS	mandatory
        DESCRIPTION
                "Fast Select Accept Facility for this table entry instance."
        DEFVAL	{ off }
        ::= { wfX25ServiceEntry 23 }

    wfX25ServiceRevChRequest OBJECT-TYPE
        SYNTAX	INTEGER {
    		    on(1),
    		    off(2)
    		}
        ACCESS	read-write
        STATUS	mandatory
        DESCRIPTION
                "Reverse Charge Request Facility for this table entry instance."
        DEFVAL	{ off }
        ::= { wfX25ServiceEntry 24 }

    wfX25ServiceRevChAccept OBJECT-TYPE
        SYNTAX	INTEGER {
    		    on(1),
    		    off(2)
    		}
        ACCESS	read-write
        STATUS	mandatory
        DESCRIPTION
                "Reverse charge Accept Facility for this table entry instance."
        DEFVAL	{ off }
        ::= { wfX25ServiceEntry 25 }

    wfX25ServiceCugFormat OBJECT-TYPE
        SYNTAX	INTEGER {
    		    none(1),
    		    basic(2),
    		    ext(3)
    		}
        ACCESS	read-write
        STATUS	mandatory
        DESCRIPTION
                "Closed User Group Facility Format."
        DEFVAL	{ none }
        ::= { wfX25ServiceEntry 26 }

    wfX25ServiceCugType OBJECT-TYPE
        SYNTAX	INTEGER {
    		    normal(1),
    		    oa(2),
    		    bilat(3)
    		}
        ACCESS	read-write
        STATUS	mandatory
        DESCRIPTION
                "Closed User Group Facility Type: Normal CUG,
                Bilateral CUG, or Outgoing Access CUG."
        DEFVAL	{ normal }
        ::= { wfX25ServiceEntry 27 }

    wfX25ServiceCugNum OBJECT-TYPE
        SYNTAX	INTEGER(1..9999)
        ACCESS	read-write
        STATUS	mandatory
        DESCRIPTION
                "Closed User Group (CUG) number."
        ::= { wfX25ServiceEntry 28 }

    wfX25ServiceUserFacility OBJECT-TYPE
        SYNTAX	OCTET STRING
        ACCESS	read-write
        STATUS	mandatory
        DESCRIPTION
                "Additional User Supplied Facilities. Must be in Hexadecimal form."
        ::= { wfX25ServiceEntry 29 }

    wfX25ServiceValid OBJECT-TYPE
        SYNTAX	INTEGER {
    		    valid(1),
    		    invalid(2)
    		}
        ACCESS	read-only
        STATUS	mandatory
        DESCRIPTION
                "Validity of the record - updated by X.25."
        DEFVAL	{ valid }
        ::= { wfX25ServiceEntry 30 }

    wfX25ServiceBFE OBJECT-TYPE
        SYNTAX	INTEGER {
    		    enabled(1),
    		    disabled(2)
    		}
        ACCESS	read-write
        STATUS	mandatory
        DESCRIPTION
                "Enabled if DDNX.25/BFE enabled."
        DEFVAL	{ disabled }
        ::= { wfX25ServiceEntry 31 }

    wfX25ServiceForceCugZero OBJECT-TYPE
        SYNTAX	INTEGER {
    		    enabled(1),
    		    disabled(2)
    		}
        ACCESS	read-write
        STATUS	mandatory
        DESCRIPTION
                "Force Closed User Group of Zero."
        DEFVAL	{ disabled }
        ::= { wfX25ServiceEntry 32 }

    wfX25ServiceWcpEnable OBJECT-TYPE
        SYNTAX	INTEGER {
    		    enabled(1),
    		    disabled(2)
    		}
        ACCESS	read-write
        STATUS	mandatory
        DESCRIPTION
                "Enable compression"
        DEFVAL	{ disabled }
        ::= { wfX25ServiceEntry 33 }

    wfX25ServiceMUX OBJECT-TYPE
        SYNTAX	INTEGER {
    		    enabled(1),
    		    disabled(2)
    		}
        ACCESS	read-write
        STATUS	mandatory
        DESCRIPTION
                "Set to Enabled to perform 1356 Multiplexing of protocols in the same Vc"
        DEFVAL	{ disabled }
        ::= { wfX25ServiceEntry 34 }

    wfX25ServicePtopCallRequest OBJECT-TYPE
        SYNTAX	INTEGER {
    		    default(1),
    		    local(2),
                    remote(3)
    		}
        ACCESS	read-write
        STATUS	mandatory
        DESCRIPTION
                "Select which side of PTOP circuit initiates the connection.
                (default = highest X.121 address initiates the call)"
        DEFVAL	{ default }
        ::= { wfX25ServiceEntry 35 }

    wfX25ServiceVcType OBJECT-TYPE
        SYNTAX	INTEGER {
    		    svc(1),
    		    pvc(2)
    		}
        ACCESS	read-write
        STATUS	mandatory
        DESCRIPTION
                "Determines whether this service record represents a
                 Switch Virtual Circuit (SVC) or Permanent Virtual
                 Circuit (PVC). (default = svc)"
        DEFVAL	{ svc }
        ::= { wfX25ServiceEntry 36 }

    wfX25ServicePvcLcn OBJECT-TYPE
        SYNTAX	INTEGER (0..4095)
        ACCESS	read-write
        STATUS	mandatory
        DESCRIPTION
                "PVC Logical Channel Number for this service record"
        DEFVAL	{ 1 }
        ::= { wfX25ServiceEntry 37 }

    wfX25ServiceMacPoolStart OBJECT-TYPE
        SYNTAX  OCTET STRING (SIZE (6))
        ACCESS  read-write
        STATUS  mandatory
        DESCRIPTION
                "Starting address of MAC address pool"
        ::= { wfX25ServiceEntry 38 }

    wfX25ServiceMacPoolSize OBJECT-TYPE
        SYNTAX  INTEGER
        ACCESS  read-write
        STATUS  mandatory
        DESCRIPTION
                "The size of MAC address pool"
        ::= { wfX25ServiceEntry 39 }

    wfX25ServiceWindowTimeout OBJECT-TYPE
        SYNTAX  INTEGER
        ACCESS  read-write
        STATUS  mandatory
        DESCRIPTION
                "Window Timeout to detect a dysfunctional VC."
        DEFVAL  { 0 }
        ::= { wfX25ServiceEntry 40 }

    wfX25ServiceVcBurstThroughput OBJECT-TYPE
        SYNTAX  INTEGER
        ACCESS  read-write
        STATUS  mandatory
        DESCRIPTION
                "Maximum number of bits of data allowed to be transmitted
                 for this service record in one second. This value is
                 divided equally amongst the VCs active for this service
                 record at any given point in time. A value of 0 indicates
                 Burst control is not to be applied. The default value is 0."
        DEFVAL  { 0 }
        ::= { wfX25ServiceEntry 41 }

    wfX25ServiceVcBurstQDepth OBJECT-TYPE
        SYNTAX  INTEGER (1..100)
        ACCESS  read-write
        STATUS  mandatory
        DESCRIPTION
                "Maximum number of buffers that can be held in the Burst
                 Queue while the VC gate pends."
        DEFVAL  { 10 }
        ::= { wfX25ServiceEntry 42 }

    wfX25ServiceVcPriority OBJECT-TYPE
        SYNTAX  INTEGER (1..9999)
        ACCESS  read-write
        STATUS  mandatory
        DESCRIPTION
                "Priority of the VCs associated with this service record.
                 This value is used to specify whether packets being
                 transmitted for this VC will be given preference over those
                 on another VC or not. In the range for this value, 1..9999,
                 1 signifies highest priority."
        DEFVAL  { 1 }
        ::= { wfX25ServiceEntry 43 }

    wfX25ServiceVcBurstQClippedPkts OBJECT-TYPE
        SYNTAX	Counter
        ACCESS	read-only
        STATUS	mandatory
        DESCRIPTION
                "Total Number of packets dropped for VCs of this service
                 record due to lack of buffers in their respective Burst
                 Queues."
        ::= { wfX25ServiceEntry 44 }

    wfX25ServiceVcBurstQPktCnt OBJECT-TYPE
        SYNTAX	Counter
        ACCESS	read-only
        STATUS	mandatory
        DESCRIPTION
                "Total Number of packets stored in the Burst Queues of VCs
                 of this service record between successive attempts to
                 forward to the PLP layer."
        ::= { wfX25ServiceEntry 45 }

    wfX25ServiceVcBurstQHighWaterPkts OBJECT-TYPE
        SYNTAX	Gauge
        ACCESS	read-only
        STATUS	mandatory
        DESCRIPTION
                "The Highest Water Packet Mark of the Burst Queues of VCs
                 of this service record."
        ::= { wfX25ServiceEntry 46 }

    wfX25ServiceVcPktDrops OBJECT-TYPE
        SYNTAX	Counter
        ACCESS	read-only
        STATUS	mandatory
        DESCRIPTION
                "Total Number of Packets Dropped for VCs of this service
                 record at the VC level."
        ::= { wfX25ServiceEntry 47 }

    wfX25ServicePlpPktDrops OBJECT-TYPE
        SYNTAX	Counter
        ACCESS	read-only
        STATUS	mandatory
        DESCRIPTION
                "Total Number of Packets Dropped by PLP for VCs of this
                 service record."
        ::= { wfX25ServiceEntry 48 }

    wfX25ServiceBurstThrPerVc OBJECT-TYPE
        SYNTAX	INTEGER
        ACCESS	read-only
        STATUS	mandatory
        DESCRIPTION
                "Burst Throughput per VC, dynamically computed as Burst
                 Throughput confiogured for the service record divided
                 by number of VCs for the service record in Data Transfer
                 State."
        ::= { wfX25ServiceEntry 49 }

    wfX25ServiceBackupRecoveryDelay OBJECT-TYPE
        SYNTAX	INTEGER
        ACCESS	read-write
        STATUS	mandatory
        DESCRIPTION
                "Delay in reverting back to a restored PDN service"
        DEFVAL	{ 0 }
        ::= { wfX25ServiceEntry 50 }

    wfX25ServiceSetupTime OBJECT-TYPE
        SYNTAX	INTEGER
        ACCESS	read-write
        STATUS	mandatory
        DESCRIPTION
                "Total time allowed for setting up a PDN SVC before
		 attempting a backup"
        DEFVAL	{ 60 }
        ::= { wfX25ServiceEntry 51 }

    wfX25ServiceRetryNumber OBJECT-TYPE
        SYNTAX	INTEGER
        ACCESS	read-write
        STATUS	mandatory
        DESCRIPTION
                "The number of times a PDN SVC setup will be attempted if
		 no response is received from the peer"
        DEFVAL	{ 1 }
        ::= { wfX25ServiceEntry 52 }

    wfX25BackupInitiation OBJECT-TYPE
        SYNTAX	INTEGER {
    		    any(1),
    		    last(2)
    		}
        ACCESS	read-write
        STATUS	mandatory
        DESCRIPTION
                "Determines whether to initiate PDN backup on failure of
		 any SVC or the last one"
        DEFVAL	{ any }
        ::= { wfX25ServiceEntry 53 }

   wfX25ServiceEntryName OBJECT-TYPE
        SYNTAX  DisplayString
        ACCESS  read-write
        STATUS  mandatory
        DESCRIPTION
                "name of the sevice entry"
        ::= { wfX25ServiceEntry 54 }

    wfX25VcTable OBJECT-TYPE
        SYNTAX	SEQUENCE OF WfX25VcEntry
        ACCESS	not-accessible
        STATUS	mandatory
        DESCRIPTION
                "This is a table of Statistic Entries is per Virtual Circuit."
        ::= { wfX25Group 4 }

    wfX25VcEntry OBJECT-TYPE
        SYNTAX	WfX25VcEntry
        ACCESS	not-accessible
        STATUS	mandatory
        DESCRIPTION
                "An entry in the X.25 VC table."
        INDEX	{ wfX25VcSlotNum,
    		  wfX25VcConnector,
    		  wfX25VcLineNumber,
    		  wfX25VcLLIndex,
    		  wfX25VcCct,
    		  wfX25VcNumber }
        ::= { wfX25VcTable 1 }

    WfX25VcEntry ::= SEQUENCE {
    	    wfX25VcSlotNum
    		INTEGER,
    	    wfX25VcConnector
    		INTEGER,
    	    wfX25VcLineNumber
    		INTEGER,
    	    wfX25VcLLIndex
    		INTEGER,
    	    wfX25VcCct
    		INTEGER,
    	    wfX25VcNumber
    		INTEGER,
    	    wfX25VcDataTxs
    		Counter,
    	    wfX25VcInterruptTxs
    		Counter,
    	    wfX25VcResetTxs
    		Counter,
    	    wfX25VcRrTxs
    		Counter,
    	    wfX25VcRnrTxs
    		Counter,
    	    wfX25VcRejectTxs
    		Counter,
    	    wfX25VcSegmentTxs
    		Counter,
    	    wfX25VcBytesTxs
    		Counter,
    	    wfX25VcIntBytesTxs
    		Counter,
    	    wfX25VcDataRxs
    		Counter,
    	    wfX25VcInterruptRxs
    		Counter,
    	    wfX25VcResetRxs
    		Counter,
    	    wfX25VcRrRxs
    		Counter,
    	    wfX25VcRnrRxs
    		Counter,
    	    wfX25VcRejectRxs
    		Counter,
    	    wfX25VcSegmentRxs
    		Counter,
    	    wfX25VcBytesRxs
    		Counter,
    	    wfX25VcIntBytesRxs
    		Counter,
    	    wfX25VcApPktsDropped
    		Counter,
    	    wfX25VcRemoteX121Addr
    		DisplayString,
    	    wfX25VcBurstQClippedPkts
    		Counter,
    	    wfX25VcBurstQPktCnt
    		Counter,
    	    wfX25VcBurstQHighWaterPkts
    		Gauge,
    	    wfX25VcPktsLargerThanBurstThrCnt
    		Counter,
    	    wfX25VcPktDrops
    		Counter,
    	    wfX25VcPlpPktDrops
    		Counter,
    	    wfX25VcMbsOutstanding
    		Counter,
    	    wfX25VcMbsOutstandingPostTx
    		Counter,
    	    wfX25VcMaxTx
    		Counter,
    	    wfX25VcMbsQueueCnt
    		Counter,
    	    wfX25VcMbsQueueCntPostTx
    		Counter,
    	    wfX25VcTxQueueCnt
    		Counter,
    	    wfX25VcTxQueueCntPostTx
    		Counter
        }

    wfX25VcSlotNum OBJECT-TYPE
        SYNTAX	INTEGER(1..14)
        ACCESS	read-only
        STATUS	mandatory
        DESCRIPTION
                "Instance ID and Slot number this VC is on."
        ::= { wfX25VcEntry 1 }

    wfX25VcConnector OBJECT-TYPE
        SYNTAX	INTEGER {
    		    one(1),
    		    two(2),
    		    three(3),
    		    four(4)
    		}
        ACCESS	read-only
        STATUS	mandatory
        DESCRIPTION
                "Instance ID and Connector number this VC is using"
        ::= { wfX25VcEntry 2 }

    wfX25VcLineNumber OBJECT-TYPE
        SYNTAX	INTEGER
        ACCESS	read-only
        STATUS	mandatory
        DESCRIPTION
                "Instance identifier member. This is the line number assigned
                to the driver X25 is running on top of and this VC is running
                on.  No used in 7.60"
        ::= { wfX25VcEntry 3 }

    wfX25VcLLIndex OBJECT-TYPE
        SYNTAX	INTEGER
        ACCESS	read-only
        STATUS	mandatory
        DESCRIPTION
                "Instance identifier member. This is the lower layer index
                presented to X25 by the layer immediately below it on the
                protocol stack. If the lower layer is a driver, the index
                will be 0. Not used in 7.60."
        ::= { wfX25VcEntry 4 }

    wfX25VcCct OBJECT-TYPE
        SYNTAX	INTEGER
        ACCESS	read-only
        STATUS	mandatory
        DESCRIPTION
                "Instance ID and CCT supporting these VCs. User determines this CCT
                via log."
        ::= { wfX25VcEntry 5 }

    wfX25VcNumber OBJECT-TYPE
        SYNTAX	INTEGER
        ACCESS	read-only
        STATUS	mandatory
        DESCRIPTION
                "Instance ID and VC number for this VC. This number corresponds to
                the LCN."
        ::= { wfX25VcEntry 6 }

    wfX25VcDataTxs OBJECT-TYPE
        SYNTAX	Counter
        ACCESS	read-only
        STATUS	mandatory
        DESCRIPTION
                "Number of Data Packets sent."
        ::= { wfX25VcEntry 7 }

    wfX25VcInterruptTxs OBJECT-TYPE
        SYNTAX	Counter
        ACCESS	read-only
        STATUS	mandatory
        DESCRIPTION
                "Number of Interrupt Packets sent."
        ::= { wfX25VcEntry 8 }

    wfX25VcResetTxs OBJECT-TYPE
        SYNTAX	Counter
        ACCESS	read-only
        STATUS	mandatory
        DESCRIPTION
                "Number of Reset Packets sent."
        ::= { wfX25VcEntry 9 }

    wfX25VcRrTxs OBJECT-TYPE
        SYNTAX	Counter
        ACCESS	read-only
        STATUS	mandatory
        DESCRIPTION
                "Number of Receiver Ready Packets sent."
        ::= { wfX25VcEntry 10 }

    wfX25VcRnrTxs OBJECT-TYPE
        SYNTAX	Counter
        ACCESS	read-only
        STATUS	mandatory
        DESCRIPTION
                "Number of Receiver Not Ready Packets sent."
        ::= { wfX25VcEntry 11 }

    wfX25VcRejectTxs OBJECT-TYPE
        SYNTAX	Counter
        ACCESS	read-only
        STATUS	mandatory
        DESCRIPTION
                "Number of Reject Packets sent."
        ::= { wfX25VcEntry 12 }

    wfX25VcSegmentTxs OBJECT-TYPE
        SYNTAX	Counter
        ACCESS	read-only
        STATUS	mandatory
        DESCRIPTION
                "Number of Charge Units sent."
        ::= { wfX25VcEntry 13 }

    wfX25VcBytesTxs OBJECT-TYPE
        SYNTAX	Counter
        ACCESS	read-only
        STATUS	mandatory
        DESCRIPTION
                "Number of Data Bytes sent."
        ::= { wfX25VcEntry 14 }

    wfX25VcIntBytesTxs OBJECT-TYPE
        SYNTAX	Counter
        ACCESS	read-only
        STATUS	mandatory
        DESCRIPTION
                "Number of Interrupt Data Bytes sent."
        ::= { wfX25VcEntry 15 }

    wfX25VcDataRxs OBJECT-TYPE
        SYNTAX	Counter
        ACCESS	read-only
        STATUS	mandatory
        DESCRIPTION
                "Number of Data Packets received."
        ::= { wfX25VcEntry 16 }

    wfX25VcInterruptRxs OBJECT-TYPE
        SYNTAX	Counter
        ACCESS	read-only
        STATUS	mandatory
        DESCRIPTION
                "Number of Interrupt Packets received."
        ::= { wfX25VcEntry 17 }

    wfX25VcResetRxs OBJECT-TYPE
        SYNTAX	Counter
        ACCESS	read-only
        STATUS	mandatory
        DESCRIPTION
                "Number of Reset Packets received."
        ::= { wfX25VcEntry 18 }

    wfX25VcRrRxs OBJECT-TYPE
        SYNTAX	Counter
        ACCESS	read-only
        STATUS	mandatory
        DESCRIPTION
                "Number of Receiver Ready Packets received."
        ::= { wfX25VcEntry 19 }

    wfX25VcRnrRxs OBJECT-TYPE
        SYNTAX	Counter
        ACCESS	read-only
        STATUS	mandatory
        DESCRIPTION
                "Number of Receiver Not Ready Packets received."
        ::= { wfX25VcEntry 20 }

    wfX25VcRejectRxs OBJECT-TYPE
        SYNTAX	Counter
        ACCESS	read-only
        STATUS	mandatory
        DESCRIPTION
                "Number of Reject Packets received."
        ::= { wfX25VcEntry 21 }

    wfX25VcSegmentRxs OBJECT-TYPE
        SYNTAX	Counter
        ACCESS	read-only
        STATUS	mandatory
        DESCRIPTION
                "Number of Charge Units received."
        ::= { wfX25VcEntry 22 }

    wfX25VcBytesRxs OBJECT-TYPE
        SYNTAX	Counter
        ACCESS	read-only
        STATUS	mandatory
        DESCRIPTION
                "Number of Data Bytes received."
        ::= { wfX25VcEntry 23 }

    wfX25VcIntBytesRxs OBJECT-TYPE
        SYNTAX	Counter
        ACCESS	read-only
        STATUS	mandatory
        DESCRIPTION
                "Number of Interrupt Data Bytes received."
        ::= { wfX25VcEntry 24 }

    wfX25VcApPktsDropped OBJECT-TYPE
        SYNTAX	Counter
        ACCESS	read-only
        STATUS	mandatory
        DESCRIPTION
                "Number of Application/redirector Packets Droped"
        ::= { wfX25VcEntry 25 }

    wfX25VcRemoteX121Addr OBJECT-TYPE
        SYNTAX	DisplayString
        ACCESS	read-only
        STATUS	mandatory
        DESCRIPTION
                "Remote DTE Address for this connection"
        ::= { wfX25VcEntry 26 }

    wfX25VcBurstQClippedPkts OBJECT-TYPE
        SYNTAX	Counter
        ACCESS	read-only
        STATUS	mandatory
        DESCRIPTION
                "Number of packets dropped for this VC due to lack of
                 buffers in the Burst Queue. Packets are only dropped
                 when the value of the statistic wfX25VcBurstQPktCnt is
                 equal to wfX25ServiceVcBurstQDepth."
        ::= { wfX25VcEntry 27 }

    wfX25VcBurstQPktCnt OBJECT-TYPE
        SYNTAX	Counter
        ACCESS	read-only
        STATUS	mandatory
        DESCRIPTION
                "Number of packets stored for this VC in the Burst Queue
                 between successive attempts to forward to the PLP layer.
                 This statistic is indicative of the transient loading of
                 buffering mechanism between the PLP layer and the upper
                 layers. The maximum value that this statistic can reach
                 is determined by the setting of wfX25ServiceVcMaxBufCnt.
                 When the value of this statistic is equal to
                 wfX25ServiceVcBurstQDepth, all subsequently arriving
                 packets are dropped."
        ::= { wfX25VcEntry 28 }

    wfX25VcBurstQHighWaterPkts OBJECT-TYPE
        SYNTAX	Gauge
        ACCESS	read-only
        STATUS	mandatory
        DESCRIPTION
                "High Water Packet Mark for the Burst Queue of this VC."
        ::= { wfX25VcEntry 29 }

    wfX25VcPktsLargerThanBurstThrCnt OBJECT-TYPE
        SYNTAX	Counter
        ACCESS	read-only
        STATUS	mandatory
        DESCRIPTION
                "Total Number of Packets serviced on this VC which are
                 larger than the computed burst throughput per VC.
                 The burst throughput per VC is computed as 
                 wfX25ServiceVcBurstThroughput / No. of Active VCs for the
                 service record."
        ::= { wfX25VcEntry 30 }

    wfX25VcPktDrops OBJECT-TYPE
        SYNTAX	Counter
        ACCESS	read-only
        STATUS	mandatory
        DESCRIPTION
                "Total Number of Packets Dropped on this VC.
                 These drops are caused by insufficient resources
                 being available to forward the packets to the PLP layer."
        ::= { wfX25VcEntry 31 }

    wfX25VcPlpPktDrops OBJECT-TYPE
        SYNTAX	Counter
        ACCESS	read-only
        STATUS	mandatory
        DESCRIPTION
                "Total Number of Packets Dropped by PLP on this VC.
                 These drops are due to either the line being disabled or the
                 lack of buffering to store packets for transmission."
        ::= { wfX25VcEntry 32 }

    wfX25VcMbsOutstanding OBJECT-TYPE
        SYNTAX	Counter
        ACCESS	read-only
        STATUS	mandatory
        DESCRIPTION
                "Number of packets sent to the PLP layer from the upper layer
                 that have not yet been added to the local assembly/deassembly
                 queue at the PLP layer. These packets will require additional
                 processing at a later time.  This value is set after the PLP
                 layer has completed processing of the maximum allowable number
                 of packets received from the upper layer."
        ::= { wfX25VcEntry 33 }

    wfX25VcMbsOutstandingPostTx OBJECT-TYPE
        SYNTAX	Counter
        ACCESS	read-only
        STATUS	mandatory
        DESCRIPTION
                "Number of buffers sent to the PLP layer that have not yet been
                 added to the local asembly/deassembly queue.  This value
                 is set after the PLP layer has completed transmission of the
                 maximum allowable number of packets from the local assembly/
                 deassembly queue to the lower layer."
        ::= { wfX25VcEntry 34 }

    wfX25VcMaxTx OBJECT-TYPE
        SYNTAX	Counter
        ACCESS	read-only
        STATUS	mandatory
        DESCRIPTION
                "Maximum Number of buffers that can be sent from the upper
                 layer to the PLP layer at any one time without overflowing
                 the local assembly/desasembly queue."
        ::= { wfX25VcEntry 35 }

    wfX25VcMbsQueueCnt OBJECT-TYPE
        SYNTAX	Counter
        ACCESS	read-only
        STATUS	mandatory
        DESCRIPTION
                "Number of buffers sent to the PLP layer that are currently
                 on the local assembly/deassembly queue at the PLP layer.
                 This value is set after the PLP layer has completed processing
                 of the maximum allowable number of packets received from the
                 upper layer."
        ::= { wfX25VcEntry 36 }

    wfX25VcMbsQueueCntPostTx OBJECT-TYPE
        SYNTAX	Counter
        ACCESS	read-only
        STATUS	mandatory
        DESCRIPTION
                "Number of buffers sent to the PLP layer that have not yet
                 been added to the local assembly/deassembly queue.  This value
                 is set after the PLP layer has completed transmission of the
                 maximum allowable number of packets from the local assembly/
                 deassembly queue to the lower layer."
        ::= { wfX25VcEntry 37 }

    wfX25VcTxQueueCnt OBJECT-TYPE
        SYNTAX	Counter
        ACCESS	read-only
        STATUS	mandatory
        DESCRIPTION
                "Number of buffers sent to the PLP layer that are currently
                 on the transmit queue at the PLP layer. This value is set
                 after the PLP layer has completed processing of the maximum
                 allowable number of packets received from upper layer."
        ::= { wfX25VcEntry 38 }

    wfX25VcTxQueueCntPostTx OBJECT-TYPE
        SYNTAX	Counter
        ACCESS	read-only
        STATUS	mandatory
        DESCRIPTION
                "Number of buffers sent to the PLP layer that are currently
                 on thequeue to transmit at the PLP layer.  This value is set
                 after the PLP layer has completed transmission of the maximum
                 allowable number of packets from the local assembly/deassembly
                 queue to the lower layer."
        ::= { wfX25VcEntry 39 }

    wfLapbPktTable OBJECT-TYPE
        SYNTAX	SEQUENCE OF WfLapbPktEntry
        ACCESS	not-accessible
        STATUS	mandatory
        DESCRIPTION
                "The table of LAPB PKT Level Parameters"
        ::= { wfX25Group 5 }

    wfLapbPktEntry OBJECT-TYPE
        SYNTAX	WfLapbPktEntry
        ACCESS	not-accessible
        STATUS	mandatory
        DESCRIPTION
                "An entry in the LAPB PKT table"
        INDEX	{ wfLapbPktSlotNum,
    		  wfLapbPktConnector,
    		  wfLapbPktLineNumber,
    		  wfLapbPktLLIndex }
        ::= { wfLapbPktTable 1 }

    WfLapbPktEntry ::= SEQUENCE {
    	    wfLapbPktDelete
    		INTEGER,
    	    wfLapbPktDisable
    		INTEGER,
    	    wfLapbPktSlotNum
    		INTEGER,
    	    wfLapbPktConnector
    		INTEGER,
    	    wfLapbPktLineNumber
    		INTEGER,
    	    wfLapbPktLLIndex
    		INTEGER,
    	    wfLapbPktLapbCct
    		INTEGER,
    	    wfLapbPktLinkId
    		INTEGER,
    	    wfLapbPktLineState
    		INTEGER,
    	    wfLapbPktSeqSize
    		INTEGER,
    	    wfLapbPktMaxWindow
    		INTEGER,
    	    wfLapbPktMaxLength
    		INTEGER,
    	    wfLapbPktMaxThroughput
    		INTEGER,
    	    wfLapbPktFlowCtl
    		INTEGER,
    	    wfLapbPktThroughput
    		INTEGER,
    	    wfLapbPktUserIdentity
    		INTEGER,
    	    wfLapbPktInCalls
    		INTEGER,
    	    wfLapbPktOutCalls
    		INTEGER,
    	    wfLapbPktFastAccept
    		INTEGER,
    	    wfLapbPktReverseAccept
    		INTEGER,
    	    wfLapbPktFastSelect
    		INTEGER,
    	    wfLapbPktReverseCharging
    		INTEGER,
    	    wfLapbPktCugSelection
    		INTEGER,
    	    wfLapbPktCugOA
    		INTEGER,
    	    wfLapbPktCugBilateral
    		INTEGER,
    	    wfLapbPktRpoaSelection
    		INTEGER,
    	    wfLapbPktChargeInform
    		INTEGER,
    	    wfLapbPktTransitDelay
    		INTEGER,
    	    wfLapbPktFullAddressing
    		INTEGER,
    	    wfLapbPktAccFormat
    		INTEGER,
    	    wfLapbPktRelFormat
    		INTEGER,
    	    wfLapbPktT1
    		INTEGER,
    	    wfLapbPktT2
    		INTEGER,
    	    wfLapbPktT3
    		INTEGER,
    	    wfLapbPktT4
    		INTEGER,
    	    wfLapbPktIwcCnt
    		INTEGER,
    	    wfLapbPktIwcId
    		INTEGER,
    	    wfLapbPktBwcCnt
    		INTEGER,
    	    wfLapbPktBwcId
    		INTEGER,
    	    wfLapbPktOwcCnt
    		INTEGER,
    	    wfLapbPktOwcId
    		INTEGER,
    	    wfLapbPktDefWindow
    		INTEGER,
    	    wfLapbPktDefLength
    		INTEGER,
    	    wfLapbPktDefClass
    		INTEGER,
    	    wfLapbPktDxe
    		INTEGER,
    	    wfLapbPktConformance
    		INTEGER,
    	    wfLapbPktStandard
    		INTEGER,
    	    wfLapbPktNetaddr
    		DisplayString,
    	    wfLapbPktStatistics
    		INTEGER,
    	    wfLapbPktNetaddrType
    		INTEGER,
    	    wfLapbPktDDNIpAddr
    		IpAddress,
    	    wfLapbPktPDNX121Addr
    		DisplayString,
    	    wfLapbPktTxT5
    		INTEGER,
	        wfLapbPktUseDfltService
		    INTEGER,
    	    wfLapbPktPVCCnt
    		INTEGER,
    	    wfLapbPktPVCLowLcn
    		INTEGER,
    	    wfLapbPktClientTimer
    		INTEGER,
            wfLapbPktPduSize
	        INTEGER,
	    wfLapbPktTranspacCauseCodeEnable
  		INTEGER,
	    wfLapbPktTxMbsQueueThreshold
                INTEGER,
	    wfLapbPktBackupDebugLvl
		INTEGER,
	    wfLapbPktBackupEnable
		INTEGER

        }

    wfLapbPktDelete OBJECT-TYPE
        SYNTAX	INTEGER {
    		    created(1),
    		    deleted(2)
    		}
        ACCESS	read-write
        STATUS	mandatory
        DESCRIPTION
                "Create/Delete parameter. Default is created."
        DEFVAL	{ created }
        ::= { wfLapbPktEntry 1 }

    wfLapbPktDisable OBJECT-TYPE
        SYNTAX	INTEGER {
    		    enabled(1),
    		    disabled(2)
    		}
        ACCESS	read-write
        STATUS	mandatory
        DESCRIPTION
                "Enable/Disable parameter"
        DEFVAL	{ enabled }
        ::= { wfLapbPktEntry 2 }

    wfLapbPktSlotNum OBJECT-TYPE
        SYNTAX	INTEGER
        ACCESS	read-only
        STATUS	mandatory
        DESCRIPTION
                "Instance identifier. This is the slot number where this X.25 packet
                layer is running."
        ::= { wfLapbPktEntry 3 }

    wfLapbPktConnector OBJECT-TYPE
        SYNTAX	INTEGER
        ACCESS	read-only
        STATUS	mandatory
        DESCRIPTION
                "Instance identifier. This is the Physical connector number for the Physical
                layer associated with this X25 Packet layer."
        ::= { wfLapbPktEntry 4 }

    wfLapbPktLineNumber OBJECT-TYPE
        SYNTAX	INTEGER
        ACCESS	read-only
        STATUS	mandatory
        DESCRIPTION
                "Instance identifier. This is the line number assigned to the LAPB Driver
                associated with this X25 Packet Layer.  Not used in 7.60"
        ::= { wfLapbPktEntry 5 }

    wfLapbPktLLIndex OBJECT-TYPE
        SYNTAX	INTEGER
        ACCESS	read-only
        STATUS	mandatory
        DESCRIPTION
                "Instance identifier. This is the lower layer index presented to X25 by
                the layer immediately below it on the protocol stack. If the lower layer
                is a driver, the index will be 0. Not used in 7.60."
        ::= { wfLapbPktEntry 6 }

    wfLapbPktLapbCct OBJECT-TYPE
        SYNTAX	INTEGER
        ACCESS	read-only
        STATUS	mandatory
        DESCRIPTION
                "Circuit number of Lapb (SYNC) driver associated with this X25 Packet Layer"
        ::= { wfLapbPktEntry 7 }

    wfLapbPktLinkId OBJECT-TYPE
        SYNTAX	INTEGER
        ACCESS	read-only
        STATUS	mandatory
        DESCRIPTION
                "Access Link identifier - index into  line information array."
        ::= { wfLapbPktEntry 8 }

    wfLapbPktLineState OBJECT-TYPE
        SYNTAX	INTEGER {
    		    up(1),
    		    down(2),
    		    init(3),
    		    notpresent(4)
    		}
        ACCESS	read-only
        STATUS	mandatory
        DESCRIPTION
                "Reflects the state of the X.25 packet layer that is associated with this
                network record. When the state of this parameter is set to Up, the router
                can transfer data between the line layer and the packet layer. Note that
                this parameter is used internally; it does NOT reflect the status of the
                underlying synchronous circuit."
        DEFVAL	{ notpresent }
        ::= { wfLapbPktEntry 9 }

    wfLapbPktSeqSize OBJECT-TYPE
        SYNTAX	INTEGER {
    		    mod8(8),
    		    mod128(128)
    		}
        ACCESS	read-write
        STATUS	mandatory
        DESCRIPTION
                "Sequence numbering scheme for the data packets. Modulo 8 or Modulo 128"
        DEFVAL	{ mod8 }
        ::= { wfLapbPktEntry 10 }

    wfLapbPktMaxWindow OBJECT-TYPE
        SYNTAX	INTEGER(1..127)
        ACCESS	read-write
        STATUS	mandatory
        DESCRIPTION
                "Maximum window size that can be negotiated on a per call basis, if the
                flow control facility is subscribed too.  Extended window size of 127
                can be used if wfLapbPktSeqSize is 128.  Otherwise the maximum is 7.
                This attribute is effective only if the attribute  wfLapbPktFloCtl is
                set to 'ON'."
        DEFVAL	{ 2 }
        ::= { wfLapbPktEntry 11 }

    wfLapbPktMaxLength OBJECT-TYPE
        SYNTAX	INTEGER {
    		    size16(4),
    		    size32(5),
    		    size64(6),
    		    size128(7),
    		    size256(8),
    		    size512(9),
    		    size1024(10),
    		    size2048(11),
    		    size4096(12)
    		}
        ACCESS	read-write
        STATUS	mandatory
        DESCRIPTION
                "Maximum packet length that can be negotiated on a per call basis, if
                the flow control facility is subscribed too. This attribute is effective
                only if the attribute wfLapbPktFloCtl is set to 'ON'. This attribute
                should not be greater than the wfSYNCEntry attribute wfSyncMtu."
        DEFVAL	{ size128 }
        ::= { wfLapbPktEntry 12 }

    wfLapbPktMaxThroughput OBJECT-TYPE
        SYNTAX	INTEGER {
    		    thrclass75(3),
    		    thrclass150(4),
    		    thrclass300(5),
    		    thrclass600(6),
    		    thrclass1200(7),
    		    thrclass2400(8),
    		    thrclass4800(9),
    		    thrclass9600(10),
    		    thrclass19200(11),
    		    thrclass48k(12),
    		    thrclass64k(13)
    		}
        ACCESS	read-write
        STATUS	mandatory
        DESCRIPTION
                "Maximum throughput class value that can be negotiated on a per call basis,
                if the throughput class negotiation facility is subscribed too. For this
                to be effective the attribute wfLapbPktThroughput must be set to ON."
        DEFVAL	{ thrclass19200 }
        ::= { wfLapbPktEntry 13 }

    wfLapbPktFlowCtl OBJECT-TYPE
        SYNTAX	INTEGER {
    		    on(1),
    		    off(2)
    		}
        ACCESS	read-write
        STATUS	mandatory
        DESCRIPTION
                "Flow control parameter negotiation facility subscription"
        DEFVAL	{ off }
        ::= { wfLapbPktEntry 14 }

    wfLapbPktThroughput OBJECT-TYPE
        SYNTAX	INTEGER {
    		    on(1),
    		    off(2)
    		}
        ACCESS	read-write
        STATUS	mandatory
        DESCRIPTION
                "Throughput class negotiation facility subscription"
        DEFVAL	{ off }
        ::= { wfLapbPktEntry 15 }

    wfLapbPktUserIdentity OBJECT-TYPE
        SYNTAX	INTEGER {
    		    on(1),
    		    off(2)
    		}
        ACCESS	read-write
        STATUS	mandatory
        DESCRIPTION
                "Network user identification (NUI) related facility subscription"
        DEFVAL	{ off }
        ::= { wfLapbPktEntry 16 }

    wfLapbPktInCalls OBJECT-TYPE
        SYNTAX	INTEGER {
    		    on(1),
    		    off(2)
    		}
        ACCESS	read-write
        STATUS	mandatory
        DESCRIPTION
                "Specifies whether or not (ON/OFF) incoming calls are permitted"
        DEFVAL	{ on }
        ::= { wfLapbPktEntry 17 }

    wfLapbPktOutCalls OBJECT-TYPE
        SYNTAX	INTEGER {
    		    on(1),
    		    off(2)
    		}
        ACCESS	read-write
        STATUS	mandatory
        DESCRIPTION
                "Specifies whether or not (ON/OFF) outgoing calls are permitted"
        DEFVAL	{ on }
        ::= { wfLapbPktEntry 18 }

    wfLapbPktFastAccept OBJECT-TYPE
        SYNTAX	INTEGER {
    		    on(1),
    		    off(2)
    		}
        ACCESS	read-write
        STATUS	mandatory
        DESCRIPTION
                "Specifies whether or not (ON/OFF) fast select acceptance facility is
                subscribed too."
        DEFVAL	{ off }
        ::= { wfLapbPktEntry 19 }

    wfLapbPktReverseAccept OBJECT-TYPE
        SYNTAX	INTEGER {
    		    on(1),
    		    off(2)
    		}
        ACCESS	read-write
        STATUS	mandatory
        DESCRIPTION
                "Specifies whether or not (ON/OFF) reverse charge aceptance facility is
                subscribed to.  If this is set this packet layer will simply accept calls
                with reverse charge facility.  But the packet layer (router) will not
                provide any charging information."
        DEFVAL	{ off }
        ::= { wfLapbPktEntry 20 }

    wfLapbPktFastSelect OBJECT-TYPE
        SYNTAX	INTEGER {
    		    on(1),
    		    off(2)
    		}
        ACCESS	read-write
        STATUS	mandatory
        DESCRIPTION
                "Specifies whether or not (ON/OFF) fast select facility is allowed on
                a per call basis."
        DEFVAL	{ off }
        ::= { wfLapbPktEntry 21 }

    wfLapbPktReverseCharging OBJECT-TYPE
        SYNTAX	INTEGER {
    		    on(1),
    		    off(2)
    		}
        ACCESS	read-write
        STATUS	mandatory
        DESCRIPTION
                "Specifies whether or not (ON/OFF) reverse charging facility is allowed
                on a per call basis."
        DEFVAL	{ off }
        ::= { wfLapbPktEntry 22 }

    wfLapbPktCugSelection OBJECT-TYPE
        SYNTAX	INTEGER {
		    off(2),
    		    basic(16),
    		    extended(32)
    		}
        ACCESS	read-write
        STATUS	mandatory
        DESCRIPTION
                "Format of the Closed User Group (CUG) related facilities supported."
        DEFVAL	{ off }
        ::= { wfLapbPktEntry 23 }

    wfLapbPktCugOA OBJECT-TYPE
        SYNTAX	INTEGER {
		    off(2),
    		    cugoa(64)
    		}
        ACCESS	read-write
        STATUS	mandatory
        DESCRIPTION
                "Specifies whether or not CUG with Outgoing access selection facility
                is supported."
        DEFVAL	{ off }
        ::= { wfLapbPktEntry 24 }

    wfLapbPktCugBilateral OBJECT-TYPE
        SYNTAX	INTEGER {
		    off(2),
    		    bilat(128)
    		}
        ACCESS	read-write
        STATUS	mandatory
        DESCRIPTION
                "Specifies whether or not Bilateral Closed User Group related facility
                is supported.  If this is set, then the wfLapbPktCugSelection should be
                set to EXTENDED."
        DEFVAL	{ off }
        ::= { wfLapbPktEntry 25 }

    wfLapbPktRpoaSelection OBJECT-TYPE
        SYNTAX	INTEGER {
    		    on(1),
    		    off(2)
    		}
        ACCESS	read-write
        STATUS	mandatory
        DESCRIPTION
                "Specifies whether or not RPOA related facility is supported. Outgoing
                calls will not contain any RPOA facility. But if set this packet layer
                will simply accept calls with RPOA related facility."
        DEFVAL	{ off }
        ::= { wfLapbPktEntry 26 }

    wfLapbPktChargeInform OBJECT-TYPE
        SYNTAX	INTEGER {
    		    on(1),
    		    off(2)
    		}
        ACCESS	read-write
        STATUS	mandatory
        DESCRIPTION
                "Specifies whether or not the charging information related facilities
                are supported.  Outgoing calls will not contain the charge information
                related facility. But if set this packet layer will simply accept calls
                with the charge information related facility.  No charging information
                will be collected."
        DEFVAL	{ off }
        ::= { wfLapbPktEntry 27 }

    wfLapbPktTransitDelay OBJECT-TYPE
        SYNTAX	INTEGER {
    		    on(1),
    		    off(2)
    		}
        ACCESS	read-write
        STATUS	mandatory
        DESCRIPTION
                "Transit delay indication facility. If set, accept calls with this
                facility."
        DEFVAL	{ off }
        ::= { wfLapbPktEntry 28 }

    wfLapbPktFullAddressing OBJECT-TYPE
        SYNTAX	INTEGER {
    		    on(1),
    		    off(2)
    		}
        ACCESS	read-write
        STATUS	mandatory
        DESCRIPTION
                "If this attribute is set, the full local X121 address (calling address)
                is supplied in the outgoing call request and the X.25 network also expected
                to provide the full called address in the incoming call packet."
        DEFVAL	{ on }
        ::= { wfLapbPktEntry 29 }

    wfLapbPktAccFormat OBJECT-TYPE
        SYNTAX	INTEGER {
    		    basic(2),
    		    allext(255),
    		    defbas(103)
    		}
        ACCESS	read-write
        STATUS	mandatory
        DESCRIPTION
                "Specifies the format of the call accepted packet."
        DEFVAL	{ basic }
        ::= { wfLapbPktEntry 30 }

    wfLapbPktRelFormat OBJECT-TYPE
        SYNTAX	INTEGER {
    		    basic(2),
    		    allext(255),
    		    defext(103)
    		}
        ACCESS	read-write
        STATUS	mandatory
        DESCRIPTION
                "Connection release format -  format of Clear Requests"
        DEFVAL	{ basic }
        ::= { wfLapbPktEntry 31 }

    wfLapbPktT1 OBJECT-TYPE
        SYNTAX	INTEGER(1..999)
        ACCESS	read-write
        STATUS	mandatory
        DESCRIPTION
                "Local confirmation timeouts in seconds. This timer represents the
                following CCITT timers.
                  If DCE: T10 (restart), T12 (reset), T13 (clear)
                  If DTE: T20 (restart), T22 (reset), T23 (clear)"
        DEFVAL	{ 60 }
        ::= { wfLapbPktEntry 32 }

    wfLapbPktT2 OBJECT-TYPE
        SYNTAX	INTEGER(1..999)
        ACCESS	read-write
        STATUS	mandatory
        DESCRIPTION
                "Call confirmation time out in seconds. This represent the CCITT T11
                timer for the DCE and T21 timer for the DTE."
        DEFVAL	{ 180 }
        ::= { wfLapbPktEntry 33 }

    wfLapbPktT3 OBJECT-TYPE
        SYNTAX	INTEGER(200..2000)
        ACCESS	read-write
        STATUS	mandatory
        DESCRIPTION
                "Congestion or busy condition watchdog timer in milliseconds. When system
                resources needed for packet assembly/deassembly depleted, this timer is
                set to reenter the PLP state machine to retry. User should use extreme
                caution in manipulating this timer."
        DEFVAL	{ 200 }
        ::= { wfLapbPktEntry 34 }

    wfLapbPktT4 OBJECT-TYPE
        SYNTAX	INTEGER(200..2000)
        ACCESS	read-write
        STATUS	mandatory
        DESCRIPTION
                "Data packet transmission watchdog timer in milliseconds. This is the
                delay for acknowledgement. It is used to reenter PLP state machine also.
                User should use extreme caution in manipulating this timer."
        DEFVAL	{ 200 }
        ::= { wfLapbPktEntry 35 }

    wfLapbPktIwcCnt OBJECT-TYPE
        SYNTAX	INTEGER(1..512)
        ACCESS	read-write
        STATUS	mandatory
        DESCRIPTION
                "Number of IWC (Incoming VC's) defined on this access link."
        ::= { wfLapbPktEntry 36 }

    wfLapbPktIwcId OBJECT-TYPE
        SYNTAX	INTEGER(0..4095)
        ACCESS	read-write
        STATUS	mandatory
        DESCRIPTION
                "Low LCN ID for IWC (Incoming VC's) defined on this access link."
        DEFVAL	{ 1 }
        ::= { wfLapbPktEntry 37 }

    wfLapbPktBwcCnt OBJECT-TYPE
        SYNTAX	INTEGER(1..512)
        ACCESS	read-write
        STATUS	mandatory
        DESCRIPTION
                "Number of BWC (Bidirectional VC's) defined on this access link."
        ::= { wfLapbPktEntry 38 }

    wfLapbPktBwcId OBJECT-TYPE
        SYNTAX	INTEGER(0..4095)
        ACCESS	read-write
        STATUS	mandatory
        DESCRIPTION
                "Low LCN ID for BWC (Bidirectional VC's) defined on this access link."
        DEFVAL	{ 1 }
        ::= { wfLapbPktEntry 39 }

    wfLapbPktOwcCnt OBJECT-TYPE
        SYNTAX	INTEGER(1..512)
        ACCESS	read-write
        STATUS	mandatory
        DESCRIPTION
                "Number of OWC (Outgoing VC's) defined on this access link."
        ::= { wfLapbPktEntry 40 }

    wfLapbPktOwcId OBJECT-TYPE
        SYNTAX	INTEGER(0..4095)
        ACCESS	read-write
        STATUS	mandatory
        DESCRIPTION
                "Low LCN ID for OWC (Outgoing VC's) defined on this access link."
        DEFVAL	{ 1 }
        ::= { wfLapbPktEntry 41 }

    wfLapbPktDefWindow OBJECT-TYPE
        SYNTAX	INTEGER(1..127)
        ACCESS	read-write
        STATUS	mandatory
        DESCRIPTION
                "Non standard default transmit/receive window size."
        DEFVAL	{ 2 }
        ::= { wfLapbPktEntry 42 }

    wfLapbPktDefLength OBJECT-TYPE
        SYNTAX	INTEGER {
    		    size16(4),
    		    size32(5),
    		    size64(6),
    		    size128(7),
    		    size256(8),
    		    size512(9),
    		    size1024(10),
    		    size2048(11),
    		    size4096(12)
    		}
        ACCESS	read-write
        STATUS	mandatory
        DESCRIPTION
                "Non standard default transmit/receive packet size. This attribute should
                not be greater than the wfSyncEntry attribute wfSyncMtu."
        DEFVAL	{ size128 }
        ::= { wfLapbPktEntry 43 }

    wfLapbPktDefClass OBJECT-TYPE
        SYNTAX	INTEGER(3..13)
        ACCESS	read-write
        STATUS	mandatory
        DESCRIPTION
                "Non standard default transmit/receive throughput class assignment."
        DEFVAL	{ 11 }
        ::= { wfLapbPktEntry 44 }

    wfLapbPktDxe OBJECT-TYPE
        SYNTAX	INTEGER {
    		    x25dtersta(1),
    		    x25dte(2),
    		    x25dce(3),
    		    x25dtedxe(4)
    		}
        ACCESS	read-write
        STATUS	mandatory
        DESCRIPTION
                "Specify type of local X25 interface and imply subsequent rules of X.25.
                DXE_X25DTERSTA ->DTE mode with Restart Procedure.
                DXE_X25DTE     ->DTE mode without any restart procedure
                DXE_X25DCE     ->DCE mode with restart procedure
                DXE_X25DTEDXE  ->DTE/DTE environment, unassigned roles."
        DEFVAL	{ x25dtersta }
        ::= { wfLapbPktEntry 45 }

    wfLapbPktConformance OBJECT-TYPE
        SYNTAX	INTEGER {
    		    dxe1980(257),
    		    fsel1980(258),
    		    dxe1984(513),
    		    fsel1984(514),
    		    dxe1988(1025),
    		    fsel1988(1026)
    		}
        ACCESS	read-write
        STATUS	mandatory
        DESCRIPTION
                "CCITT conformance recommendation used on each line."
        DEFVAL	{ dxe1988 }
        ::= { wfLapbPktEntry 46 }

    wfLapbPktStandard OBJECT-TYPE
        SYNTAX	INTEGER {
    		    stdiso(16),
    		    stddod(32),
    		    stdnone(1)
    		}
        ACCESS	read-write
        STATUS	mandatory
        DESCRIPTION
                "Network Standard to be used on each line."
        DEFVAL	{ stdnone }
        ::= { wfLapbPktEntry 47 }

    wfLapbPktNetaddr OBJECT-TYPE
        SYNTAX	DisplayString
        ACCESS	read-only
        STATUS	mandatory
        DESCRIPTION
                "This Link's Network address (X121 address)."
        ::= { wfLapbPktEntry 48 }

    wfLapbPktStatistics OBJECT-TYPE
        SYNTAX	INTEGER {
    		    statson(1),
    		    statsoff(2)
    		}
        ACCESS	read-write
        STATUS	mandatory
        DESCRIPTION
                "Gives the user the ability to Turn ON or Shut OFF statistics computation.
                This can be shut off for better performance on the line. Now it also
                provides a small packet trace function."
        DEFVAL	{ statsoff }
        ::= { wfLapbPktEntry 49 }

    wfLapbPktNetaddrType OBJECT-TYPE
        SYNTAX	INTEGER {
    		    pdntype(1),
    		    ddntype(2),
    		    bfetype(3)
    		}
        ACCESS	read-write
        STATUS	mandatory
        DESCRIPTION
                "This defines whether the Network connection is to a DDN network or
                PDN Network. This is used to decide how the Local X121 Network address is
                derived. If this attribute is set to DDN the Local X121 address used in
                the attribute wfLapbPktNetaddr will be derived from the user supplied
                IP address.  Otherwise the X121 address should be supplid by the user."
        DEFVAL	{ pdntype }
        ::= { wfLapbPktEntry 50 }

    wfLapbPktDDNIpAddr OBJECT-TYPE
        SYNTAX	IpAddress
        ACCESS	read-write
        STATUS	mandatory
        DESCRIPTION
                "If the wfLapbPktNetaddrType is DDNTYPE or DDN_BFE this is the user
                supplied local IP address. The router will convert this to the
                corresponding X121 address and the X121 address value will be put
                in wfLapbPktNetaddr attribute."
        ::= { wfLapbPktEntry 51 }

    wfLapbPktPDNX121Addr OBJECT-TYPE
        SYNTAX	DisplayString
        ACCESS	read-write
        STATUS	mandatory
        DESCRIPTION
                "If the wfLapbPktNetaddrType is PDNTYPE this is the user supplied local
                X.121 address.  The router will put this value in wfLapbPktNetaddr
                attribute."
        ::= { wfLapbPktEntry 52 }

    wfLapbPktTxT5 OBJECT-TYPE
        SYNTAX	INTEGER(1..8000)
        ACCESS	read-write
        STATUS	mandatory
        DESCRIPTION
                "Tx window size transmit delay timer"
        DEFVAL	{ 200 }
        ::= { wfLapbPktEntry 53 }

    wfLapbPktUseDfltService OBJECT-TYPE
        SYNTAX	INTEGER {
    		    on(1),
    		    off(2)
	}
        ACCESS	read-write
        STATUS	mandatory
        DESCRIPTION
                "Indicates whether or not to use the default ddn service."
	DEFVAL  { off }
        ::= { wfLapbPktEntry 54 }

    wfLapbPktPVCCnt OBJECT-TYPE
        SYNTAX	INTEGER(1..512)
        ACCESS	read-write
        STATUS	mandatory
        DESCRIPTION
                "Number of PVCs defined on this access link."
        ::= { wfLapbPktEntry 55 }

    wfLapbPktPVCLowLcn OBJECT-TYPE
        SYNTAX	INTEGER(0..4095)
        ACCESS	read-write
        STATUS	mandatory
        DESCRIPTION
                "Low LCN ID for PVCs defined on this access link."
        DEFVAL	{ 1 }
        ::= { wfLapbPktEntry 56 }

    wfLapbPktClientTimer OBJECT-TYPE
        SYNTAX	INTEGER(1..999)
        ACCESS	read-write
        STATUS	mandatory
        DESCRIPTION
                "Client application response timeout period in seconds.
                This timer allows for the extended delays that can occur
                negotiating with remote clients (e.g., IPEX or QLLC).
                This timer must be greater than the wfLapbPktT3 period
                and less than wfLapbPktT2."
        DEFVAL	{ 120 }
        ::= { wfLapbPktEntry 57 }

    wfLapbPktPduSize OBJECT-TYPE
        SYNTAX	INTEGER (1600..4096)
        ACCESS	read-write
        STATUS	mandatory
        DESCRIPTION
                "The X.25 PDU Size for this logical channel. This PDU size
                 represents the M_BUF_SIZE used for X.25 Fragmentation
                 and Reassembly in the packet layer. This is the largest
                 message size X.25 will handle from a client on a given
                 Logical Channel. Changing this attribute enables X.25
                 to handle client messages up to 4096 bytes in length"
        DEFVAL	{ 1600 }
        ::= { wfLapbPktEntry 58 }

    wfLapbPktTranspacCauseCodeEnable OBJECT-TYPE
      	SYNTAX  INTEGER {
	            enabled(1),
              	disabled(2)
         	}
	  	ACCESS  read-write
		STATUS  mandatory
		DESCRIPTION
			"Use Transpac Cause Codes , default = disabled."
		DEFVAL  { disabled }
		  ::= { wfLapbPktEntry 59 }

    wfLapbPktTxMbsQueueThreshold OBJECT-TYPE
        SYNTAX	INTEGER (0..128)
        ACCESS	read-write
        STATUS	mandatory
        DESCRIPTION
                "The maximum number of packets that TX mbs queue can hold.
                 If X.25 receives more packets and TX mbs queue count
                 reaches this maximum, it will open up another SVC connection.
                 The default is zero and the maximum queue count is equal to
                 wfLapbPktDefWindow + 1, which is three."
        DEFVAL	{ 0 }
        ::= { wfLapbPktEntry 60 }

    wfLapbPktBackupDebugLvl OBJECT-TYPE
        SYNTAX	INTEGER {
    		    one(1),
    		    debug(4)
    		}
        ACCESS	read-write
        STATUS	mandatory
        DESCRIPTION
                "Debug level for X.25 backup messages"
        DEFVAL	{ one }
        ::= { wfLapbPktEntry 61 }

    wfLapbPktBackupEnable OBJECT-TYPE
        SYNTAX	INTEGER {
    		    enabled(1),
    		    disabled(2)
    		}
        ACCESS	read-write
        STATUS	mandatory
        DESCRIPTION
                "Backup Enable/Disable parameter"
        DEFVAL	{ disabled }
        ::= { wfLapbPktEntry 62 }

    wfLapbPktStatsTable OBJECT-TYPE
        SYNTAX	SEQUENCE OF WfLapbPktStatsEntry
        ACCESS	not-accessible
        STATUS	mandatory
        DESCRIPTION
                "The table of LAPB PKT Level Statistics."
        ::= { wfX25Group 6 }

    wfLapbPktStatsEntry OBJECT-TYPE
        SYNTAX	WfLapbPktStatsEntry
        ACCESS	not-accessible
        STATUS	mandatory
        DESCRIPTION
                "Packet level statistics."
        INDEX	{ wfLapbPktStatsSlotNum,
    		  wfLapbPktStatsConnector,
    		  wfLapbPktStatsLineNumber,
    		  wfLapbPktStatsLLIndex }
        ::= { wfLapbPktStatsTable 1 }

    WfLapbPktStatsEntry ::= SEQUENCE {
    	    wfLapbPktStatsSlotNum
    		INTEGER,
    	    wfLapbPktStatsConnector
    		INTEGER,
    	    wfLapbPktStatsLineNumber
    		INTEGER,
    	    wfLapbPktStatsLLIndex
    		INTEGER,
    	    wfLapbPktStatsCct
    		INTEGER,
    	    wfLapbPktStatsLineAddress
    		DisplayString,
    	    wfLapbPktStatsMaxVcs
    		Counter,
    	    wfLapbPktStatsActiveVcs
    		Counter,
    	    wfLapbPktStatsActiveMax
    		Counter,
    	    wfLapbPktStatsTotalConnections
    		Counter,
    	    wfLapbPktStatsFailedConnections
    		Counter,
    	    wfLapbPktStatsNormalDisconnects
    		Counter,
    	    wfLapbPktStatsAbnormalDisconnects
    		Counter,
    	    wfLapbPktStatsDataTxs
    		Counter,
    	    wfLapbPktStatsInterruptTxs
    		Counter,
    	    wfLapbPktStatsResetTxs
    		Counter,
    	    wfLapbPktStatsRrTxs
    		Counter,
    	    wfLapbPktStatsRnrTxs
    		Counter,
    	    wfLapbPktStatsRejectTxs
    		Counter,
    	    wfLapbPktStatsRestartTxs
    		Counter,
    	    wfLapbPktStatsDiagTxs
    		Counter,
    	    wfLapbPktStatsSegmentTxs
    		Counter,
    	    wfLapbPktStatsBytesTxs
    		Counter,
    	    wfLapbPktStatsIntBytesTxs
    		Counter,
    	    wfLapbPktStatsDataRxs
    		Counter,
    	    wfLapbPktStatsInterruptRxs
    		Counter,
    	    wfLapbPktStatsResetRxs
    		Counter,
    	    wfLapbPktStatsRrRxs
    		Counter,
    	    wfLapbPktStatsRnrRxs
    		Counter,
    	    wfLapbPktStatsRejectRxs
    		Counter,
    	    wfLapbPktStatsRestartRxs
    		Counter,
    	    wfLapbPktStatsDiagRxs
    		Counter,
    	    wfLapbPktStatsSegmentRxs
    		Counter,
    	    wfLapbPktStatsBytesRxs
    		Counter,
    	    wfLapbPktStatsIntBytesRxs
    		Counter,
    	    wfLapbPktStatsOnOffSwitch
    		INTEGER
        }

    wfLapbPktStatsSlotNum OBJECT-TYPE
        SYNTAX	INTEGER
        ACCESS	read-only
        STATUS	mandatory
        DESCRIPTION
                "Slot number and instance ID for this Lapb Packet Layer Line instance."
        ::= { wfLapbPktStatsEntry 1 }

    wfLapbPktStatsConnector OBJECT-TYPE
        SYNTAX	INTEGER
        ACCESS	read-only
        STATUS	mandatory
        DESCRIPTION
                "Port number and instance ID for this Lapb Packet Layer Line instance."
        ::= { wfLapbPktStatsEntry 2 }

    wfLapbPktStatsLineNumber OBJECT-TYPE
        SYNTAX	INTEGER
        ACCESS	read-only
        STATUS	mandatory
        DESCRIPTION
                "Instance identifier member. This is the line number assigned to the
                driver X.25 is running over.  No used in 7.60"
        ::= { wfLapbPktStatsEntry 3 }

    wfLapbPktStatsLLIndex OBJECT-TYPE
        SYNTAX	INTEGER
        ACCESS	read-only
        STATUS	mandatory
        DESCRIPTION
                "Instance identifier member. This is the lower layer index
                presented to X25 by the layer immediately below it on the
                protocol stack. If the lower layer is a driver, the index
                will be 0. Not used in 7.60."
        ::= { wfLapbPktStatsEntry 4 }

    wfLapbPktStatsCct OBJECT-TYPE
        SYNTAX	INTEGER
        ACCESS	read-only
        STATUS	mandatory
        DESCRIPTION
                "Circuit number for this instance."
        ::= { wfLapbPktStatsEntry 5 }

    wfLapbPktStatsLineAddress OBJECT-TYPE
        SYNTAX	DisplayString
        ACCESS	read-only
        STATUS	mandatory
        DESCRIPTION
                "The local X.121 address of this line."
        ::= { wfLapbPktStatsEntry 6 }

    wfLapbPktStatsMaxVcs OBJECT-TYPE
        SYNTAX	Counter
        ACCESS	read-only
        STATUS	mandatory
        DESCRIPTION
                "Maximum number of Virtual Circuits allowed on this line."
        ::= { wfLapbPktStatsEntry 7 }

    wfLapbPktStatsActiveVcs OBJECT-TYPE
        SYNTAX	Counter
        ACCESS	read-only
        STATUS	mandatory
        DESCRIPTION
                "Number of Active Virtual Circuits on this line."
        ::= { wfLapbPktStatsEntry 8 }

    wfLapbPktStatsActiveMax OBJECT-TYPE
        SYNTAX	Counter
        ACCESS	read-only
        STATUS	mandatory
        DESCRIPTION
                "Highest number of active Virtual Circuits on this line."
        ::= { wfLapbPktStatsEntry 9 }

    wfLapbPktStatsTotalConnections OBJECT-TYPE
        SYNTAX	Counter
        ACCESS	read-only
        STATUS	mandatory
        DESCRIPTION
                "Number of Total Virtual Connections performed since start up."
        ::= { wfLapbPktStatsEntry 10 }

    wfLapbPktStatsFailedConnections OBJECT-TYPE
        SYNTAX	Counter
        ACCESS	read-only
        STATUS	mandatory
        DESCRIPTION
                "Number of unsuccessful Virtual Connections performed since start up."
        ::= { wfLapbPktStatsEntry 11 }

    wfLapbPktStatsNormalDisconnects OBJECT-TYPE
        SYNTAX	Counter
        ACCESS	read-only
        STATUS	mandatory
        DESCRIPTION
                "Number of Normal Virtual Circuit Disconnections."
        ::= { wfLapbPktStatsEntry 12 }

    wfLapbPktStatsAbnormalDisconnects OBJECT-TYPE
        SYNTAX	Counter
        ACCESS	read-only
        STATUS	mandatory
        DESCRIPTION
                "Number of Abnormal Virtual Circuit Disconnections."
        ::= { wfLapbPktStatsEntry 13 }

    wfLapbPktStatsDataTxs OBJECT-TYPE
        SYNTAX	Counter
        ACCESS	read-only
        STATUS	mandatory
        DESCRIPTION
                "Number of Data Packets Transmitted on this line."
        ::= { wfLapbPktStatsEntry 14 }

    wfLapbPktStatsInterruptTxs OBJECT-TYPE
        SYNTAX	Counter
        ACCESS	read-only
        STATUS	mandatory
        DESCRIPTION
                "Number of Interrupt Packets sent."
        ::= { wfLapbPktStatsEntry 15 }

    wfLapbPktStatsResetTxs OBJECT-TYPE
        SYNTAX	Counter
        ACCESS	read-only
        STATUS	mandatory
        DESCRIPTION
                "Number of Reset Requests sent."
        ::= { wfLapbPktStatsEntry 16 }

    wfLapbPktStatsRrTxs OBJECT-TYPE
        SYNTAX	Counter
        ACCESS	read-only
        STATUS	mandatory
        DESCRIPTION
                "Number of Receiver Ready Packets sent."
        ::= { wfLapbPktStatsEntry 17 }

    wfLapbPktStatsRnrTxs OBJECT-TYPE
        SYNTAX	Counter
        ACCESS	read-only
        STATUS	mandatory
        DESCRIPTION
                "Number of Receiver Not Ready Packets sent."
        ::= { wfLapbPktStatsEntry 18 }

    wfLapbPktStatsRejectTxs OBJECT-TYPE
        SYNTAX	Counter
        ACCESS	read-only
        STATUS	mandatory
        DESCRIPTION
                "Number of Reject Packets sent."
        ::= { wfLapbPktStatsEntry 19 }

    wfLapbPktStatsRestartTxs OBJECT-TYPE
        SYNTAX	Counter
        ACCESS	read-only
        STATUS	mandatory
        DESCRIPTION
                "Number of Restart Packets sent."
        ::= { wfLapbPktStatsEntry 20 }

    wfLapbPktStatsDiagTxs OBJECT-TYPE
        SYNTAX	Counter
        ACCESS	read-only
        STATUS	mandatory
        DESCRIPTION
                "Number of Diagnostic Packets sent."
        ::= { wfLapbPktStatsEntry 21 }

    wfLapbPktStatsSegmentTxs OBJECT-TYPE
        SYNTAX	Counter
        ACCESS	read-only
        STATUS	mandatory
        DESCRIPTION
                "Number of Charge Units sent."
        ::= { wfLapbPktStatsEntry 22 }

    wfLapbPktStatsBytesTxs OBJECT-TYPE
        SYNTAX	Counter
        ACCESS	read-only
        STATUS	mandatory
        DESCRIPTION
                "Number of Data Bytes sent."
        ::= { wfLapbPktStatsEntry 23 }

    wfLapbPktStatsIntBytesTxs OBJECT-TYPE
        SYNTAX	Counter
        ACCESS	read-only
        STATUS	mandatory
        DESCRIPTION
                "Number of Interrupt Data Bytes sent."
        ::= { wfLapbPktStatsEntry 24 }

    wfLapbPktStatsDataRxs OBJECT-TYPE
        SYNTAX	Counter
        ACCESS	read-only
        STATUS	mandatory
        DESCRIPTION
                "Number of Data Packets received on this line."
        ::= { wfLapbPktStatsEntry 25 }

    wfLapbPktStatsInterruptRxs OBJECT-TYPE
        SYNTAX	Counter
        ACCESS	read-only
        STATUS	mandatory
        DESCRIPTION
                "Number of Interrupt Packets received."
        ::= { wfLapbPktStatsEntry 26 }

    wfLapbPktStatsResetRxs OBJECT-TYPE
        SYNTAX	Counter
        ACCESS	read-only
        STATUS	mandatory
        DESCRIPTION
                "Number of Reset Requests received."
        ::= { wfLapbPktStatsEntry 27 }

    wfLapbPktStatsRrRxs OBJECT-TYPE
        SYNTAX	Counter
        ACCESS	read-only
        STATUS	mandatory
        DESCRIPTION
                "Number of Receiver Ready Packets received."
        ::= { wfLapbPktStatsEntry 28 }

    wfLapbPktStatsRnrRxs OBJECT-TYPE
        SYNTAX	Counter
        ACCESS	read-only
        STATUS	mandatory
        DESCRIPTION
                "Number of Receiver Not Ready Packets received."
        ::= { wfLapbPktStatsEntry 29 }

    wfLapbPktStatsRejectRxs OBJECT-TYPE
        SYNTAX	Counter
        ACCESS	read-only
        STATUS	mandatory
        DESCRIPTION
                "Number of Reject Packets received."
        ::= { wfLapbPktStatsEntry 30 }

    wfLapbPktStatsRestartRxs OBJECT-TYPE
        SYNTAX	Counter
        ACCESS	read-only
        STATUS	mandatory
        DESCRIPTION
                "Number of Restart Packets received."
        ::= { wfLapbPktStatsEntry 31 }

    wfLapbPktStatsDiagRxs OBJECT-TYPE
        SYNTAX	Counter
        ACCESS	read-only
        STATUS	mandatory
        DESCRIPTION
                "Number of Diagnostic Packets received."
        ::= { wfLapbPktStatsEntry 32 }

    wfLapbPktStatsSegmentRxs OBJECT-TYPE
        SYNTAX	Counter
        ACCESS	read-only
        STATUS	mandatory
        DESCRIPTION
                "Number of Charge Units received."
        ::= { wfLapbPktStatsEntry 33 }

    wfLapbPktStatsBytesRxs OBJECT-TYPE
        SYNTAX	Counter
        ACCESS	read-only
        STATUS	mandatory
        DESCRIPTION
                "Number of Data Bytes received."
        ::= { wfLapbPktStatsEntry 34 }

    wfLapbPktStatsIntBytesRxs OBJECT-TYPE
        SYNTAX	Counter
        ACCESS	read-only
        STATUS	mandatory
        DESCRIPTION
                "Number of Interrupt Data Bytes received."
        ::= { wfLapbPktStatsEntry 35 }

    wfLapbPktStatsOnOffSwitch OBJECT-TYPE
        SYNTAX	INTEGER
        ACCESS	read-only
        STATUS	mandatory
        DESCRIPTION
                "This tells the user if Statistics Computation is turned ON or OFF."
        ::= { wfLapbPktStatsEntry 36 }

    wfX25PvcServiceTable OBJECT-TYPE
        SYNTAX	SEQUENCE OF WfX25PvcServiceEntry
        ACCESS	not-accessible
        STATUS	mandatory
        DESCRIPTION
                "the table of Lapb Pvc Packet level parameters"
        ::= { wfX25Group 7 }

    wfX25PvcServiceEntry OBJECT-TYPE
        SYNTAX	WfX25PvcServiceEntry
        ACCESS	not-accessible
        STATUS	mandatory
        DESCRIPTION
                "An entry in the LAPB PKT table"
        INDEX	{ wfX25SlotNum,
    		  wfX25Connector,
    		  wfX25LineNumber,
    		  wfX25LLIndex,
    		  wfX25PvcServiceCct,
    		  wfX25PvcServiceIndex }
        ::= { wfX25PvcServiceTable 1 }

    WfX25PvcServiceEntry ::= SEQUENCE {
    	    wfX25PvcDelete
    		INTEGER,
    	    wfX25PvcDisable
    		INTEGER,
    	    wfX25SlotNum
    		INTEGER,
    	    wfX25Connector
    		INTEGER,
    	    wfX25LineNumber
    		INTEGER,
    	    wfX25LLIndex
    		INTEGER,
    	    wfX25PvcServiceCct
    		INTEGER,
    	    wfX25PvcServiceIndex
    		INTEGER,
    	    wfX25PvcServiceType
    		INTEGER,
    	    wfX25PvcRxDefWindow
    		INTEGER,
    	    wfX25PvcTxDefWindow
    		INTEGER,
    	    wfX25PvcRxDefLength
    		INTEGER,
    	    wfX25PvcTxDefLength
    		INTEGER,
    	    wfX25PvcRxDefClass
    		INTEGER,
    	    wfX25PvcTxDefClass
    		INTEGER
        }

    wfX25PvcDelete OBJECT-TYPE
        SYNTAX	INTEGER {
    		    created(1),
    		    deleted(2)
    		}
        ACCESS	read-write
        STATUS	mandatory
        DESCRIPTION
                "Create/Delete parameter, Default is created"
        DEFVAL	{ created }
        ::= { wfX25PvcServiceEntry 1 }

    wfX25PvcDisable OBJECT-TYPE
        SYNTAX	INTEGER {
    		    enabled(1),
    		    disabled(2)
    		}
        ACCESS	read-write
        STATUS	mandatory
        DESCRIPTION
                "Enable/Disable Parameter"
        DEFVAL	{ enabled }
        ::= { wfX25PvcServiceEntry 2 }

    wfX25SlotNum OBJECT-TYPE
        SYNTAX	INTEGER
        ACCESS	read-only
        STATUS	mandatory
        DESCRIPTION
                "Part of the Instance Identifier. This is the slot number where this
                X25 packet layer is running"
        ::= { wfX25PvcServiceEntry 3 }

    wfX25Connector OBJECT-TYPE
        SYNTAX	INTEGER
        ACCESS	read-only
        STATUS	mandatory
        DESCRIPTION
                "Part of the Instance Identifier. This is the physical connector number
                for the physical layer associated with this packet layer"
        ::= { wfX25PvcServiceEntry 4 }

    wfX25LineNumber OBJECT-TYPE
        SYNTAX	INTEGER
        ACCESS	read-only
        STATUS	mandatory
        DESCRIPTION
                "Part of the Instance Id. This is the line number assigned to the LAPB
                driver associated with the X25 Packet layer."
        ::= { wfX25PvcServiceEntry 5 }

    wfX25LLIndex OBJECT-TYPE
        SYNTAX	INTEGER
        ACCESS	read-only
        STATUS	mandatory
        DESCRIPTION
                "Instance identifier. This is the lower layer index presented to X25 by
                the layer immediately below it on the protocol stack. If the lower layer
                is a driver, the index will be 0. Not used in 7.60."
        ::= { wfX25PvcServiceEntry 6 }

    wfX25PvcServiceCct OBJECT-TYPE
        SYNTAX	INTEGER
        ACCESS	read-only
        STATUS	mandatory
        DESCRIPTION
                "Instance Id. This is the Circuit number"
        ::= { wfX25PvcServiceEntry 7 }

    wfX25PvcServiceIndex OBJECT-TYPE
        SYNTAX	INTEGER
        ACCESS	read-only
        STATUS	mandatory
        DESCRIPTION
                "Instace Id. This is the lcn on which this pvc is running"
        ::= { wfX25PvcServiceEntry 8 }

    wfX25PvcServiceType OBJECT-TYPE
        SYNTAX	INTEGER {
    		    pdntype(1),
    		    ddntype(2),
    		    ptoptype(4),
    		    npttype(8),
    		    ipextype(16),
                qllctype(32)
    		}
        ACCESS	read-write
        STATUS	mandatory
        DESCRIPTION
                "Type of Service for this PVC Service record"
        ::= { wfX25PvcServiceEntry 9 }

    wfX25PvcRxDefWindow OBJECT-TYPE
        SYNTAX	INTEGER(1..127)
        ACCESS	read-write
        STATUS	mandatory
        DESCRIPTION
                "This is the receive window size used for setting up the pvc."
        DEFVAL	{ 2 }
        ::= { wfX25PvcServiceEntry 10 }

    wfX25PvcTxDefWindow OBJECT-TYPE
        SYNTAX	INTEGER(1..127)
        ACCESS	read-write
        STATUS	mandatory
        DESCRIPTION
                "This is the transmit window size used for setting up the pvc."
        DEFVAL	{ 2 }
        ::= { wfX25PvcServiceEntry 11 }

    wfX25PvcRxDefLength OBJECT-TYPE
        SYNTAX	INTEGER {
    		    size16(4),
    		    size32(5),
    		    size64(6),
    		    size128(7),
    		    size256(8),
    		    size512(9),
    		    size1024(10),
    		    size2048(11),
    		    size4096(12)
    		}
        ACCESS	read-write
        STATUS	mandatory
        DESCRIPTION
                "This is the receive packet size."
        DEFVAL	{ size128 }
        ::= { wfX25PvcServiceEntry 12 }

    wfX25PvcTxDefLength OBJECT-TYPE
        SYNTAX	INTEGER {
    		    size16(4),
    		    size32(5),
    		    size64(6),
    		    size128(7),
    		    size256(8),
    		    size512(9),
    		    size1024(10),
    		    size2048(11),
    		    size4096(12)
    		}
        ACCESS	read-write
        STATUS	mandatory
        DESCRIPTION
                "This is the trasmit packet size"
        DEFVAL	{ size128 }
        ::= { wfX25PvcServiceEntry 13 }

    wfX25PvcRxDefClass OBJECT-TYPE
        SYNTAX	INTEGER {
    		    thrclass75(3),
    		    thrclass150(4),
    		    thrclass300(5),
    		    thrclass600(6),
    		    thrclass1200(7),
    		    thrclass2400(8),
    		    thrclass4800(9),
    		    thrclass9600(10),
    		    thrclass19200(11),
    		    thrclass48k(12),
    		    thrclass64k(13)
    		}
        ACCESS	read-write
        STATUS	mandatory
        DESCRIPTION
                "This is the receive througput class value that can be used on a per pvc
                basis. For this to be effective, the wfX25Throughput must be set
                ON"
        DEFVAL	{ thrclass19200 }
        ::= { wfX25PvcServiceEntry 14 }

    wfX25PvcTxDefClass OBJECT-TYPE
        SYNTAX	INTEGER {
    		    thrclass75(3),
    		    thrclass150(4),
    		    thrclass300(5),
    		    thrclass600(6),
    		    thrclass1200(7),
    		    thrclass2400(8),
    		    thrclass4800(9),
    		    thrclass9600(10),
    		    thrclass19200(11),
    		    thrclass48k(12),
    		    thrclass64k(13)
    		}
        ACCESS	read-write
        STATUS	mandatory
        DESCRIPTION
                "This is the transmit througput class value that can be used on a per pvc
                basis. For this to be effective, the wfX25Throughput must be set
                ON"
        DEFVAL	{ thrclass19200 }
        ::= { wfX25PvcServiceEntry 15 }

    wfX25QllcAddrMapTable OBJECT-TYPE
        SYNTAX  SEQUENCE OF WfX25QllcAddrMapEntry
        ACCESS  not-accessible
        STATUS  mandatory
        DESCRIPTION
                "table of X.121 address to LLC Mac address mappings."
        ::= { wfX25Group 8 }

    wfX25QllcAddrMapEntry OBJECT-TYPE
        SYNTAX  WfX25QllcAddrMapEntry
        ACCESS  not-accessible
        STATUS  mandatory
        DESCRIPTION
                "An entry in the QLLC Address Mapping table"
        INDEX   {  wfX25QllcAddrMapCct,
              wfX25QllcAddrMapIndex }
        ::= { wfX25QllcAddrMapTable 1 }

    WfX25QllcAddrMapEntry ::= SEQUENCE {
            wfX25QllcAddrMapDelete
            INTEGER,
            wfX25QllcAddrMapDisable
            INTEGER,
            wfX25QllcAddrMapState
            INTEGER,
            wfX25QllcAddrMapCct
            INTEGER,
            wfX25QllcAddrMapIndex
            INTEGER,
            wfX25QllcAddrMapPartnerX121
            DisplayString,
            wfX25QllcAddrMapAdjacentX121
            DisplayString,
            wfX25QllcAddrMapPid
            INTEGER,
            wfX25QllcAddrMapPartnerMac
            OCTET STRING,
            wfX25QllcAddrMapPartnerSap
            INTEGER,
            wfX25QllcAddrMapAdjacentMac
            OCTET STRING,
            wfX25QllcAddrMapAdjacentSap
            INTEGER,
            wfX25QllcAddrMapOptions
            INTEGER,
            wfX25QllcAddrMapTrace
            INTEGER,
            wfX25QllcAddrMapPuType
            INTEGER,
            wfX25QllcAddrMapGenXid
            INTEGER,
            wfX25QllcAddrMapNodeId
            OCTET STRING,
            wfX25QllcAddrMapName
            DisplayString
        }

    wfX25QllcAddrMapDelete OBJECT-TYPE
        SYNTAX  INTEGER {
                created(1),
                deleted(2)
            }
        ACCESS  read-write
        STATUS  mandatory
        DESCRIPTION
                "Create/Delete parameter."
        DEFVAL  { created }
        ::= { wfX25QllcAddrMapEntry 1 }

    wfX25QllcAddrMapDisable OBJECT-TYPE
        SYNTAX  INTEGER {
                enabled(1),
                disabled(2)
            }
        ACCESS  read-write
        STATUS  mandatory
        DESCRIPTION
                "Enable/Disable parameter."
        DEFVAL  { enabled }
        ::= { wfX25QllcAddrMapEntry 2 }

    wfX25QllcAddrMapState OBJECT-TYPE
        SYNTAX  INTEGER {
                active(1),
                notactive(2),
                notpresent(3)
            }
        ACCESS  read-only
        STATUS  mandatory
        DESCRIPTION
                "The current state of the QLLC Mapping."
        DEFVAL  { notpresent }
        ::= { wfX25QllcAddrMapEntry 3 }

    wfX25QllcAddrMapCct OBJECT-TYPE
        SYNTAX  INTEGER(1..1024)
        ACCESS  read-only
        STATUS  mandatory
        DESCRIPTION
                "Circuit number and instance ID member."
        ::= { wfX25QllcAddrMapEntry 4 }

    wfX25QllcAddrMapIndex OBJECT-TYPE
        SYNTAX  INTEGER(1..4000)
        ACCESS  read-only
        STATUS  mandatory
        DESCRIPTION
               "X.25 QLLC Address Map entry record ID for this instance."
        ::= { wfX25QllcAddrMapEntry 5 }

    wfX25QllcAddrMapPartnerX121 OBJECT-TYPE
        SYNTAX  DisplayString
        ACCESS  read-write
        STATUS  mandatory
        DESCRIPTION
                "The X.121 address of a X.25 device emulated by this
                 interface."
        ::= { wfX25QllcAddrMapEntry 6 }

    wfX25QllcAddrMapAdjacentX121 OBJECT-TYPE
        SYNTAX  DisplayString
        ACCESS  read-write
        STATUS  mandatory
        DESCRIPTION
                "The X.121 address of a X.25 device connecting thru this
                 interface. This address may contain wildcard characters."
        ::= { wfX25QllcAddrMapEntry 7 }

    wfX25QllcAddrMapPid OBJECT-TYPE
        SYNTAX  INTEGER(1..254)
        ACCESS  read-write
        STATUS  mandatory
        DESCRIPTION
                "QLLC Protocol ID used in the first byte of Call User
                 Data of the X.25 Call Request packet."
        DEFVAL  { 195 }
        ::= { wfX25QllcAddrMapEntry 8 }

    wfX25QllcAddrMapPartnerMac OBJECT-TYPE
        SYNTAX  OCTET STRING
        ACCESS  read-write
        STATUS  mandatory
        DESCRIPTION
                "The LLC MAC address of a LLC device connecting thru this
                 interface. The LLC MAC address may contain wildcard
                 characters, see wfX25QllcAddrMapOptions attribute below."
        ::= { wfX25QllcAddrMapEntry 9 }

    wfX25QllcAddrMapPartnerSap OBJECT-TYPE
        SYNTAX  INTEGER(1..254)
        ACCESS  read-write
        STATUS  mandatory
        DESCRIPTION
                "The SAP of a LLC device connecting thru this interface."
        DEFVAL  { 4 }
        ::= { wfX25QllcAddrMapEntry 10 }

    wfX25QllcAddrMapAdjacentMac OBJECT-TYPE
        SYNTAX  OCTET STRING (SIZE (6))
        ACCESS  read-write
        STATUS  mandatory
        DESCRIPTION
                "The  LLC MAC address of a LLC device emulated by this
                 interface. If set to nil, a LLC MAC address will be
                 dynamically assign by X.25 from an address pool defined
                 in the X.25 Service Record."
        ::= { wfX25QllcAddrMapEntry 11 }

    wfX25QllcAddrMapAdjacentSap OBJECT-TYPE
        SYNTAX  INTEGER (1..254)
        ACCESS  read-write
        STATUS  mandatory
        DESCRIPTION
                "The SAP of a LLC device emulated by this interface."
        DEFVAL  { 4 }
        ::= { wfX25QllcAddrMapEntry 12 }

    wfX25QllcAddrMapOptions OBJECT-TYPE
        SYNTAX  INTEGER
        ACCESS  read-write
        STATUS  mandatory
        DESCRIPTION
                "This object is a bitmask, setting individual bit postions
                 enable the option. Values may be added together to
                 enable multiple options.

                 Hex     Dec
                Value   Value     Options
                ---------------------------------------------------------
                0x0001     1  Do not wait for Adjacent DTE/DCE to send
                              an QXID before forwarding an QXID to it.
                0x0002     2  Enable when SDLC endstations are connecting
                              to QLLC hosts that do not support receipt of
                              XID polls and do not retransmit XIDs.
                0x0004     4  wfX25QllcAddrMapPartnerMac field contains
                              wildcard characters."
        DEFVAL  { 0 }
        ::= { wfX25QllcAddrMapEntry 13 }

    wfX25QllcAddrMapTrace OBJECT-TYPE
        SYNTAX  INTEGER
        ACCESS  read-write
        STATUS  mandatory
        DESCRIPTION
                "This object is a bitmask, setting individual bit postions
                 enable logging of internal QLLC messages and events.
                 Values may be added together to enable multiple message
                 groups.

                 Hex     Dec
                Value   Value     Message/Event
                ---------------------------------------------------------
                0x0001     1  Enable QLLC logging.
                0x0002     2  Data frames/packets.
                0x0004     4  Flow Control messages.
                0x0008     8  Client registration messages.

                0x0010    16  X.25 session establishment messages.
                0x0020    32  Test frames/packets.
                0x0040    64  XID frames/packes.
                0x0080   128  Set Mode frames/packets.

                0x0100   256  Disconnect frames/packets.
                0x0200   512  Configuration changes.
                0x0400  1024  Death of client (DLSw or APPN).
                0x0800  2048  Data Path (DP) messages."
        DEFVAL  { 0 }
        ::= { wfX25QllcAddrMapEntry 14 }

    wfX25QllcAddrMapPuType OBJECT-TYPE
        SYNTAX  INTEGER {
                pu21(1),
                pu20(2)
            }
        ACCESS  read-write
        STATUS  obsolete
        DESCRIPTION
                "PU type (T2.0 or T2.1) of the locally attached QLLC device."
        DEFVAL  { pu20 }
        ::= { wfX25QllcAddrMapEntry 15 }

    wfX25QllcAddrMapGenXid OBJECT-TYPE
        SYNTAX  INTEGER {
                enabled(1),
                disabled(2)
            }
        ACCESS  read-write
        STATUS  mandatory
        DESCRIPTION
                "Simulate receiving an XID command from the QLLC device.
                 This object should be enabled when an PU 2.0 QLLC
                 device is connecting thru DLSw to an non-X.25 host."
        DEFVAL  { disabled }
        ::= { wfX25QllcAddrMapEntry 16 }

    wfX25QllcAddrMapNodeId OBJECT-TYPE
        SYNTAX  OCTET STRING (SIZE (4))
        ACCESS  read-write
        STATUS  obsolete
        DESCRIPTION
                "The 8 hexadecimal digit Node Identification field of the
                 simulated XID (see wfX25QllcAddrMapGenXid object). This
                 field has two sub-fields, ID Block and ID Number. The
                 first 3 hexadecimal digits are the ID block value and the
                 last 5 hexadecimal digits are the ID Number value."
        ::= { wfX25QllcAddrMapEntry 17 }

    wfX25QllcAddrMapName OBJECT-TYPE
        SYNTAX  DisplayString
        ACCESS  read-write
        STATUS  mandatory
        DESCRIPTION
                "A informational name for this QLLC Mapping."
        ::= { wfX25QllcAddrMapEntry 18 }


    END  -- Wellfleet-X25-MIB
