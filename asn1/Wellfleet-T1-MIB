Wellfleet-T1-MIB DEFINITIONS ::= BEGIN

-- Created by mdl2asn version 3.1
-- Creation date: Wed Aug 30 16:49:06 EDT 1995


    IMPORTS

      IpAddress, Counter, Gauge, TimeTicks, Opaque, enterprises, mgmt
        FROM RFC1155-SMI
      OBJECT-TYPE
        FROM RFC-1212
      TRAP-TYPE
        FROM RFC-1215
      DisplayString, mib-2
        FROM RFC1213-MIB
      wfLine
        FROM Wellfleet-COMMON-MIB;


    wfT1Table OBJECT-TYPE
        SYNTAX	SEQUENCE OF WfT1Entry
        ACCESS	not-accessible
        STATUS	mandatory
        DESCRIPTION
                "T1 line record"
        ::= { wfLine 10 }

    wfT1Entry OBJECT-TYPE
        SYNTAX	WfT1Entry
        ACCESS	not-accessible
        STATUS	mandatory
        DESCRIPTION
                "An entry in the T1 table"
        INDEX	{ wfT1Slot,
    		  wfT1Connector }
        ::= { wfT1Table 1 }

    WfT1Entry ::= SEQUENCE {
    	    wfT1Delete
    		INTEGER,
    	    wfT1Disable
    		INTEGER,
    	    wfT1State
    		INTEGER,
    	    wfT1Slot
    		INTEGER,
    	    wfT1Connector
    		INTEGER,
    	    wfT1Madr
    		OCTET STRING,
    	    wfT1FrameType
    		INTEGER,
    	    wfT1LineBuildout
    		INTEGER,
    	    wfT1B8ZSSupport
    		INTEGER,
    	    wfT1ClockMode
    		INTEGER,
    	    wfT1MiniDacs
    		DisplayString,
    	    wfT1BipolarVios
    		Counter,
    	    wfT1FrameBitErrs
    		Counter,
    	    wfT1OutOfFrameErrs
    		Counter,
    	    wfT1SuperFrameErrs
    		Counter,
    	    wfT1RcvYelAlarms
    		Counter,
    	    wfT1RcvCarrierLoss
    		Counter,
    	    wfT1RcvRedAlarms
    		Counter
        }

    wfT1Delete OBJECT-TYPE
        SYNTAX	INTEGER {
    		    created(1),
    		    deleted(2)
    		}
        ACCESS	read-write
        STATUS	mandatory
        DESCRIPTION
                "create/delete parameter, dflt = created"
        DEFVAL	{ created }
        ::= { wfT1Entry 1 }

    wfT1Disable OBJECT-TYPE
        SYNTAX	INTEGER {
    		    enabled(1),
    		    disabled(2)
    		}
        ACCESS	read-write
        STATUS	mandatory
        DESCRIPTION
                "enable/disable parameter, dflt = enabled"
        DEFVAL	{ enabled }
        ::= { wfT1Entry 2 }

    wfT1State OBJECT-TYPE
        SYNTAX	INTEGER {
    		    up(1),
    		    init(3),
    		    notpresent(4)
    		}
        ACCESS	read-only
        STATUS	mandatory
        DESCRIPTION
                "line driver state variable, Not Present, Init, Up"
        DEFVAL	{ notpresent }
        ::= { wfT1Entry 3 }

    wfT1Slot OBJECT-TYPE
        SYNTAX	INTEGER(1..14)
        ACCESS	read-only
        STATUS	mandatory
        DESCRIPTION
                "instance ID Slot, filled in by driver"
        ::= { wfT1Entry 4 }

    wfT1Connector OBJECT-TYPE
        SYNTAX	INTEGER {
    		    one(1),
    		    two(2)
    		}
        ACCESS	read-only
        STATUS	mandatory
        DESCRIPTION
                "instance ID Connector, filled in by driver"
        ::= { wfT1Entry 5 }

    wfT1Madr OBJECT-TYPE
        SYNTAX	OCTET STRING
        ACCESS	read-only
        STATUS	mandatory
        DESCRIPTION
                "Line mac address, filled in by driver"
        ::= { wfT1Entry 6 }

    wfT1FrameType OBJECT-TYPE
        SYNTAX	INTEGER {
    		    d4(1),
    		    esf(2)
    		}
        ACCESS	read-write
        STATUS	mandatory
        DESCRIPTION
                "Frame Type - differentiates between two tarrifed framing formats
                D4 and ESF."
        DEFVAL	{ esf }
        ::= { wfT1Entry 7 }

    wfT1LineBuildout OBJECT-TYPE
        SYNTAX	INTEGER(1..655)
        ACCESS	read-write
        STATUS	mandatory
        DESCRIPTION
                "Line Buildout - Approximate length of cable"
        DEFVAL	{ 1 }
        ::= { wfT1Entry 8 }

    wfT1B8ZSSupport OBJECT-TYPE
        SYNTAX	INTEGER {
    		    enabled(1),
    		    disabled(2)
    		}
        ACCESS	read-write
        STATUS	mandatory
        DESCRIPTION
                "B8ZS Support - Enables or disables Binary 8 zeros suppression"
        DEFVAL	{ disabled }
        ::= { wfT1Entry 9 }

    wfT1ClockMode OBJECT-TYPE
        SYNTAX	INTEGER {
    		    internal(1),
    		    slave(2),
    		    manual(4)
    		}
        ACCESS	read-write
        STATUS	mandatory
        DESCRIPTION
                "Clock Mode - Specifies the source of the T1 transmit clock"
        DEFVAL	{ internal }
        ::= { wfT1Entry 10 }

    wfT1MiniDacs OBJECT-TYPE
        SYNTAX	DisplayString
        ACCESS	read-write
        STATUS	mandatory
        DESCRIPTION
                "MiniDacs Configuration - assigns each T1 channel to a specific
                function"
        ::= { wfT1Entry 11 }

    wfT1BipolarVios OBJECT-TYPE
        SYNTAX	Counter
        ACCESS	read-only
        STATUS	mandatory
        DESCRIPTION
                "Number of Bipolar Violations"
        ::= { wfT1Entry 12 }

    wfT1FrameBitErrs OBJECT-TYPE
        SYNTAX	Counter
        ACCESS	read-only
        STATUS	mandatory
        DESCRIPTION
                "Number of frame bit errors"
        ::= { wfT1Entry 13 }

    wfT1OutOfFrameErrs OBJECT-TYPE
        SYNTAX	Counter
        ACCESS	read-only
        STATUS	mandatory
        DESCRIPTION
                "Number of Out of Frame errors"
        ::= { wfT1Entry 14 }

    wfT1SuperFrameErrs OBJECT-TYPE
        SYNTAX	Counter
        ACCESS	read-only
        STATUS	mandatory
        DESCRIPTION
                "Number of  Superframe errors"
        ::= { wfT1Entry 15 }

    wfT1RcvYelAlarms OBJECT-TYPE
        SYNTAX	Counter
        ACCESS	read-only
        STATUS	mandatory
        DESCRIPTION
                "Number of Yellow Alarms Received"
        ::= { wfT1Entry 16 }

    wfT1RcvCarrierLoss OBJECT-TYPE
        SYNTAX	Counter
        ACCESS	read-only
        STATUS	mandatory
        DESCRIPTION
                "Number of instances of carrier loss"
        ::= { wfT1Entry 17 }

    wfT1RcvRedAlarms OBJECT-TYPE
        SYNTAX	Counter
        ACCESS	read-only
        STATUS	mandatory
        DESCRIPTION
                "Number of Red Alarm Received"
        ::= { wfT1Entry 18 }

    END  -- Wellfleet-T1-MIB
