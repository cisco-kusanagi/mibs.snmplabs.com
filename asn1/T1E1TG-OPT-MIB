-- Version 2.15.1.1 Modified 2001-06-05 14:22:00-04 

        T1E1TG-OPT-MIB DEFINITIONS ::= BEGIN

        IMPORTS
            Counter, Gauge, enterprises
                FROM RFC1155-SMI

            OBJECT-TYPE
                FROM RFC-1212;

        -- Codex MIB Group definitions

                      codex OBJECT IDENTIFIER ::= { enterprises 449 }
         cdxProductSpecific OBJECT IDENTIFIER ::= { codex 2 }
                    cdx6500 OBJECT IDENTIFIER ::= { cdxProductSpecific 1 }

      cdx6500Configuration  OBJECT IDENTIFIER ::= { cdx6500 2 }
    cdx6500CfgProtocolGroup OBJECT IDENTIFIER ::= { cdx6500Configuration 1 }
     cdx6500CfgGeneralGroup OBJECT IDENTIFIER ::= { cdx6500Configuration 2 }
cdx6500PCTPortProtocolGroup OBJECT IDENTIFIER ::= { cdx6500CfgProtocolGroup 1 }

        cdx6500Statistics OBJECT IDENTIFIER ::= { cdx6500 3 }
   cdx6500StatProtocolGroup OBJECT IDENTIFIER ::= { cdx6500Statistics 1 }
cdx6500PSTPortProtocolGroup OBJECT IDENTIFIER ::= { cdx6500StatProtocolGroup 1 }
cdx6500PSTT1E1TGPortTable OBJECT IDENTIFIER ::= { cdx6500PSTPortProtocolGroup 35 }

            cdx6500Controls OBJECT IDENTIFIER ::= { cdx6500 4 }

        -- Textual Conventions

        DisplayString ::= OCTET STRING


        -- T1E1TGPort Configuration Table

        cdx6500PCTT1E1TGPortTable OBJECT-TYPE
            SYNTAX SEQUENCE OF Cdx6500PCTT1E1TGEntry
            ACCESS not-accessible
            STATUS mandatory
            DESCRIPTION
                "This table contains the T1E1TGPort Configuration
                 parameters."
        ::= { cdx6500PCTPortProtocolGroup 34 }

        cdx6500PCTT1E1TGPortEntry OBJECT-TYPE
            SYNTAX Cdx6500PCTT1E1TGEntry
            ACCESS not-accessible
            STATUS mandatory
            DESCRIPTION
                "A T1E1TGPort Table Entry. Each entry
                 contains the configuration parameters for a single
                 T1E1TGPort  Table."
            INDEX { cdx6500T1E1TGCfgPortNumber }
        ::= { cdx6500PCTT1E1TGPortTable 1 }

        Cdx6500PCTT1E1TGEntry ::=
            SEQUENCE {
                cdx6500T1E1TGCfgPortNumber 
                    INTEGER,
                cdx6500T1E1TGCfgInterfaceType
                    DisplayString,
                cdx6500T1E1TGCfgFormat
                    INTEGER,
                cdx6500T1E1TGCfgSwitchType
                    INTEGER,
                cdx6500T1E1TGCfgUserNetworkSide
                    INTEGER,
                cdx6500T1E1TGCfgDirectBchannel
                    INTEGER,
                cdx6500T1E1TGCfgBchNumScheme
                    INTEGER,
                cdx6500T1E1TGCfgBchRange
                    DisplayString,
                cdx6500T1E1TGCfgCallAddrReplace
                    DisplayString,
                cdx6500T1E1TGCfgIsdnQsigOpt
                    DisplayString,
                cdx6500T1E1TGCfgFilteredIE
                    DisplayString,
                cdx6500T1E1TGCfgReplIsdnQsig
                    DisplayString,
                cdx6500T1E1TGCfgCallPartyNumType
                    INTEGER,
                cdx6500T1E1TGCfgCallPartyNumPlan
                    INTEGER,
                cdx6500T1E1TGCfgLineFramingType
                    INTEGER,
                cdx6500T1E1TGCfgLineCoding
                    INTEGER,
                cdx6500T1E1TGCfgClockPriority
                    INTEGER,
                cdx6500T1E1TGCfgLineImpedance
                    INTEGER,
                cdx6500T1E1TGCfgLineBuildOut
                    INTEGER,
                cdx6500T1E1TGCfgRecvSense
                    INTEGER,
                cdx6500T1E1TGCfgFacilityDataLink
                    INTEGER,
                cdx6500T1E1TGCfgV54RecvRLBK
                    INTEGER,
                cdx6500T1E1TGCfgThresholdValueLES
                    INTEGER,
                cdx6500T1E1TGCfgThresholdValueLCV
                    INTEGER,
                cdx6500T1E1TGCfgThresholdValuePCV
                    INTEGER,
                cdx6500T1E1TGCfgThresholdValueCSS
                    INTEGER,
                cdx6500T1E1TGCfgThresholdValueES
                    INTEGER,
                cdx6500T1E1TGCfgThresholdValueBES
                    INTEGER,
                cdx6500T1E1TGCfgThresholdValueSES
                    INTEGER,
                cdx6500T1E1TGCfgThresholdValueSEFS
                    INTEGER,
                cdx6500T1E1TGCfgThresholdValueUAS
                    INTEGER
                }

        cdx6500T1E1TGCfgPortNumber OBJECT-TYPE
            SYNTAX INTEGER 
            ACCESS read-only
            STATUS mandatory
            DESCRIPTION
                "Port number of the T1E1TG Port."
        ::= { cdx6500PCTT1E1TGPortEntry 1 }

        cdx6500T1E1TGCfgInterfaceType OBJECT-TYPE
            SYNTAX DisplayString
            ACCESS read-only
            STATUS mandatory
            DESCRIPTION
                "This is a T1E1TG  having interface type."
        ::= { cdx6500PCTT1E1TGPortEntry 2 }

        cdx6500T1E1TGCfgFormat OBJECT-TYPE
            SYNTAX INTEGER {
                    vg-format-frational (1),
                    vg-format-channelize (2),
                    vg-format-isdn (3),
                    vg-format-ccs (4)
                    } 
            ACCESS read-only
            STATUS mandatory
            DESCRIPTION
                "This parameter is used to select the format 
                 of the T1E1TG interface.
		 vg-format-frational :DS0's are predefined by the TELCO or the User
                 vg-format-channelize :DS0 is predefined by the TELCO or the User
                 vg-format-isdn  :DS0 is defined by the ISDN (Q.931) D-Channel
                 vg-format-ccs  :DS0 is defined by the signalling channel (Voice)."
        ::= { cdx6500PCTT1E1TGPortEntry 3 }

        cdx6500T1E1TGCfgSwitchType OBJECT-TYPE
            SYNTAX INTEGER {
                    unspecified  (1),
                    ni2 	(2),
                    ess5       (3),
                    dms100      (4),
                    ntt         (5),
                    tso14      (6),
                    etsi       (7),
                    qsig       (8)
                    }
            ACCESS read-only
            STATUS mandatory
            DESCRIPTION
                "The ISDN switch type. This specifies the type of
                 equipment to which this span is connected.
                 The possible choices are:
                 ni2	  : National ISDN version 2
                 5ess     : AT&T 5ESS Switch
                 dms100   : Northern Telecom DMS-100 Switch
                 ntt      : Nippon Telephone and Telegraph switch (Japan)
                 tso14    : AUSTEL Technical Standard 014 for Australia
                 etsi     : Euro ISDN PRI (NET5)
		 qsig     : ISDN QSIG PRI."
        ::= { cdx6500PCTT1E1TGPortEntry 4 }

        cdx6500T1E1TGCfgUserNetworkSide OBJECT-TYPE
            SYNTAX INTEGER {
                    user    (1),
                    network (2)
                    }
                ACCESS read-only
                STATUS mandatory
                DESCRIPTION
                    "This parameter specifies whether the T1E1TG 
                     is emulating the network or user side of the
                     ISDN network.
                     user    : The T1 or E1 port is emulating the user,
                               ex.  the T1 or E1 port is to be connected
                               to an ISDN network.
                     network : The T1 or E1 port is emulating the network,
                               ex. the T1 or E1 port is to be connected
                               to an ISDN PBX."
        ::= { cdx6500PCTT1E1TGPortEntry 5 }

        cdx6500T1E1TGCfgDirectBchannel OBJECT-TYPE
            SYNTAX INTEGER {
                    high-to-low    (1),
                    low-to-high (2)
                    }
                ACCESS read-only
                STATUS mandatory
                DESCRIPTION
                    "This parameter specifies the direction of B-Channel
		      assignment on outbound calls made from this port.
			high-to-low : B-Channels are selected starting with the highest
                			 numbered available channel.
   			high-to-low : B-Channels are selected starting with the lowest
                		       numbered available channel."
        ::= { cdx6500PCTT1E1TGPortEntry 6 }

        cdx6500T1E1TGCfgBchNumScheme OBJECT-TYPE
            SYNTAX INTEGER {
                    nb-1-30 (1),
                    nb-1-31 (2)
                    }
            ACCESS read-only
            STATUS mandatory
            DESCRIPTION
               "This parameter specifies the B-Channel numbering scheme
                used by the ISDN service provider.
                  1-31  : B-Channels are numbered 1 to 31.
                  1-30  : B-Channels are numbered 1 to 30."
        ::= { cdx6500PCTT1E1TGPortEntry 7 }

        cdx6500T1E1TGCfgBchRange OBJECT-TYPE
            SYNTAX DisplayString 
            ACCESS read-only
            STATUS mandatory
            DESCRIPTION
                "Specify the B-Channel assignments that will be used
		 for the ISDN/QSIG calls.
		  Select Individual or Time Slot ranges, e.g. 1-3,10,13-15
		  will include Time Slots 1,2,3,10,13,14,15."
        ::= { cdx6500PCTT1E1TGPortEntry 8 }

        cdx6500T1E1TGCfgCallAddrReplace OBJECT-TYPE
            SYNTAX DisplayString
            ACCESS read-only
            STATUS mandatory
            DESCRIPTION
		 "Specifies the rules for Calling Number replacement for ISDN/QSIG
		  voice calls. If the Calling Number is to be replaced, the new number
		  comes from the Virtual Port's Local Subscriber Directory Number,
		  specified in the Virtual Port Mapping Table.
			NONE     -  No replacement
			RX       -  For an incoming call replace the Calling Number
			TX       -  For an outgoing call replace the Calling Number
			RX-ONLY  -  For an incoming call replace the Calling Number only
			TX-ONLY  -  For an outgoing call replace the Calling Number only."
        ::= { cdx6500PCTT1E1TGPortEntry 9 }

        cdx6500T1E1TGCfgIsdnQsigOpt OBJECT-TYPE
            SYNTAX DisplayString
            ACCESS read-only
            STATUS mandatory
            DESCRIPTION
                "This parameter is a PLACE HOLDER item."
        ::= { cdx6500PCTT1E1TGPortEntry 10 }

        cdx6500T1E1TGCfgFilteredIE OBJECT-TYPE
            SYNTAX DisplayString
            ACCESS read-only
            STATUS mandatory
            DESCRIPTION
                "This parameter is a PLACE HOLDER item."
        ::= { cdx6500PCTT1E1TGPortEntry 11 }

        cdx6500T1E1TGCfgReplIsdnQsig OBJECT-TYPE
            SYNTAX DisplayString
            ACCESS read-only
            STATUS mandatory
            DESCRIPTION
                "This parameter is a PLACE HOLDER item."
        ::= { cdx6500PCTT1E1TGPortEntry 12 }

        cdx6500T1E1TGCfgCallPartyNumType OBJECT-TYPE
            SYNTAX INTEGER {
                    unknown (1),
                    international (2),
                    national  (3),
                    subscriber  (5)
                    }
            ACCESS read-only
            STATUS mandatory
            DESCRIPTION
                 "This is the Calling/Called Party Number Type as defined by ITU-T
		   unknown       - Unknown
   		   international - International number
   		   national      - National number
   		   subscriber    - Subscriber number."
        ::= { cdx6500PCTT1E1TGPortEntry 13 }

        cdx6500T1E1TGCfgCallPartyNumPlan OBJECT-TYPE
            SYNTAX INTEGER {
                    unknown (1),
                    isdn (2),
                    telephony  (3),
                    private  (10)
                    }
            ACCESS read-only
            STATUS mandatory
            DESCRIPTION
	         "This is the Calling/Called Party Number Plan as defined by ITU-T
   			unknown   - Unknown
   			iSDN      - ISDN numbering plan (E.164)
   			telephony - Standard Telephone numbering plan
   			private   - Private numbering plan."
        ::= { cdx6500PCTT1E1TGPortEntry 14 }

        cdx6500T1E1TGCfgLineFramingType OBJECT-TYPE
            SYNTAX INTEGER {
                    sf (1),
                    esf  (2),
                    e1 (3),
                    e1crc  (4),
                    e1crc-febe  (5)
                    }
            ACCESS read-only
            STATUS mandatory
            DESCRIPTION
               "Indicate type of framing used by the DS1 circuit.
		    esf : Extended Super Frame
   		    sf  : Super Frame (Also known as D4 framing type)
		    e1  : D2048S or D2048U
                    e1-crc  : D2048S with CRC
                    e1-crc-febe: D2048S with CRC and Si=FEBE."
        ::= { cdx6500PCTT1E1TGPortEntry 15 }

        cdx6500T1E1TGCfgLineCoding OBJECT-TYPE
            SYNTAX INTEGER {
                    ami  (1),
                    b8zs   (2),
		    hdb3   (3) 
                    }
            ACCESS read-only
            STATUS mandatory
            DESCRIPTION
	        "Selects variety of zero suppression used on the T1 link.
		   ami : Alternate Mark Inversion.
		   b8zs : Bipolar 8 Zero Substitution.
		   hdb3 : High Density Bipolar 3"
        ::= { cdx6500PCTT1E1TGPortEntry 16 }

        cdx6500T1E1TGCfgClockPriority OBJECT-TYPE
            SYNTAX INTEGER {
                    high  (1),
                    medium (2),
		    low    (3)
                    }
            ACCESS read-only
            STATUS mandatory
            DESCRIPTION
                "Priority of the received clock to become source of Group, 
                 Card or System clock.
		      HIGH   : High prority 
   		      MEDIUM : Medium priority 
   	              LOW    : Low priority "
        ::= { cdx6500PCTT1E1TGPortEntry 17 }

        cdx6500T1E1TGCfgLineImpedance OBJECT-TYPE
            SYNTAX INTEGER {
                    ohms-120 (1),
                    ohms-75 (2)
                    }
            ACCESS read-only
            STATUS mandatory
            DESCRIPTION
                "Selects the line impedance as 75 ohms or 120 ohms."
        ::= { cdx6500PCTT1E1TGPortEntry 18 }

        cdx6500T1E1TGCfgLineBuildOut OBJECT-TYPE
            SYNTAX INTEGER
            ACCESS read-only
            STATUS mandatory
            DESCRIPTION
                 "Select the Line Build Out to match the physical interface.
                  For DSX interfaces, this value is based on cable
			0 - 0ft to 133ft
     			1 - 134ft to 266ft
     			2 - 267ft to 399ft
     			3 - 400ft to 533ft
     			4 - 534ft to 655ft

                  For DS1 interfaces, this value is based on the
			0 - 0db
     			5 - -7.5db
     			6 - -15db
     			7 - -22.5db
     			4 - Not valid for DS1 interfaces"
        ::= { cdx6500PCTT1E1TGPortEntry 19 }   

        cdx6500T1E1TGCfgRecvSense OBJECT-TYPE
            SYNTAX INTEGER {
                    low (1),
                    high (2)
                    }
            ACCESS read-only
            STATUS mandatory
            DESCRIPTION
	       "Select HIGH (-36DB) if line is marginal."
        ::= { cdx6500PCTT1E1TGPortEntry 20 }

        cdx6500T1E1TGCfgFacilityDataLink OBJECT-TYPE
            SYNTAX INTEGER {
                    none (1),
                    ansi (3),
                    att  (2)
                    }
            ACCESS read-only
            STATUS mandatory
            DESCRIPTION
                "This describes the use of the facilities data link,
                 and may have the following capabilities:
                 none : indicates that the device does  not use
                        the FDL.
                 ansi : refers to the  FDL  exchange recommended 
                        by ANSI (Ansi-T1-403).
                 att  : refers to ESF FDL exchanges (Att-54016)."
        ::= { cdx6500PCTT1E1TGPortEntry 21 }

        cdx6500T1E1TGCfgV54RecvRLBK OBJECT-TYPE
            SYNTAX INTEGER {
                    disable (1),
                    enable (2)
                    }
            ACCESS read-only
            STATUS mandatory
            DESCRIPTION
	       "enable : Respond to incoming V.54 loopback requests.
                disable: Do not respond to incoming V.54 loopback requests."
        ::= { cdx6500PCTT1E1TGPortEntry 22 }

        cdx6500T1E1TGCfgThresholdValueLES OBJECT-TYPE
            SYNTAX INTEGER (1..255)
            ACCESS read-only
            STATUS mandatory
            DESCRIPTION
                "Threshold value of Line Errored Seconds (LESs)
                 to report alarms on CTP when exceeded."
        ::= { cdx6500PCTT1E1TGPortEntry 23  }

        cdx6500T1E1TGCfgThresholdValueLCV OBJECT-TYPE
            SYNTAX INTEGER (1..255)
            ACCESS read-only
            STATUS mandatory
            DESCRIPTION
                "Threshold value of Line Code Violations (LCVs)
                 to report alarms on CTP when exceeded."
        ::= { cdx6500PCTT1E1TGPortEntry 24 }

        cdx6500T1E1TGCfgThresholdValuePCV OBJECT-TYPE
            SYNTAX INTEGER (1..255)
            ACCESS read-only
            STATUS mandatory
            DESCRIPTION
                "Threshold value of Path Code Violations (PCVs)
                 to report alarms on CTP when exceeded."
        ::= { cdx6500PCTT1E1TGPortEntry 25  }


        cdx6500T1E1TGCfgThresholdValueCSS OBJECT-TYPE
            SYNTAX INTEGER (1..255)
            ACCESS read-only
            STATUS mandatory
            DESCRIPTION
                "Threshold value of Controlled Slip Seconds (CSSs)
                 to report alarms on CTP when exceeded."
        ::= { cdx6500PCTT1E1TGPortEntry 26 }

        cdx6500T1E1TGCfgThresholdValueES OBJECT-TYPE
            SYNTAX INTEGER (1..255)
            ACCESS read-only
            STATUS mandatory
            DESCRIPTION
                "Threshold value of Errored Seconds (ESs)
                 to report alarms on CTP when exceeded."
        ::= { cdx6500PCTT1E1TGPortEntry 27 }

        cdx6500T1E1TGCfgThresholdValueBES OBJECT-TYPE
            SYNTAX INTEGER (1..255)
            ACCESS read-only
            STATUS mandatory
            DESCRIPTION
                "Threshold value of Bursty Errored Seconds (BESs)
                 to report alarms on CTP when exceeded."
        ::= { cdx6500PCTT1E1TGPortEntry 28 }

        cdx6500T1E1TGCfgThresholdValueSES OBJECT-TYPE
            SYNTAX INTEGER (1..255)
            ACCESS read-only
            STATUS mandatory
            DESCRIPTION
                "Threshold value of Severely Errored Seconds (SESs)
                 to report alarms on CTP when exceeded."
        ::= { cdx6500PCTT1E1TGPortEntry 29 }

        cdx6500T1E1TGCfgThresholdValueSEFS OBJECT-TYPE
            SYNTAX INTEGER (1..255)
            ACCESS read-only
            STATUS mandatory
            DESCRIPTION
                "Threshold value of Severely Errored Framing Seconds (SEFSs)
                 to report alarms on CTP when exceeded."
        ::= { cdx6500PCTT1E1TGPortEntry 30 }

        cdx6500T1E1TGCfgThresholdValueUAS OBJECT-TYPE
            SYNTAX INTEGER (1..255)
            ACCESS read-only
            STATUS mandatory
            DESCRIPTION
                "Threshold value of Unavailable Seconds (UASs)
                 to report alarms on CTP when exceeded."
        ::= { cdx6500PCTT1E1TGPortEntry 31 }


        -- The T1E1TG Port Statistics Table
        
        cdx6500PSTT1E1TGTable OBJECT-TYPE
            SYNTAX SEQUENCE OF Cdx6500PSTT1E1TGEntry
            ACCESS not-accessible
            STATUS mandatory
            DESCRIPTION
                "This table holds statistics information for T1E1TG."
        ::= { cdx6500PSTT1E1TGPortTable 1 }
        
        cdx6500PSTT1E1TGEntry OBJECT-TYPE
            SYNTAX Cdx6500PSTT1E1TGEntry 
            ACCESS not-accessible
            STATUS mandatory
            DESCRIPTION
                "Each entry contains statistics information for one T1E1TG interface."
            INDEX { cdx6500T1E1TGStatPortNumber }            
        ::= { cdx6500PSTT1E1TGTable 1 }
        
        Cdx6500PSTT1E1TGEntry ::=
            SEQUENCE {
                cdx6500T1E1TGStatPortNumber 
                    INTEGER,
                cdx6500T1E1TGStatInterfaceType 
                    DisplayString,
                cdx6500T1E1TGStatTimeSinceLastReset 
                    DisplayString,
                cdx6500T1E1TGStatAlarmState
                    DisplayString
                }

         cdx6500T1E1TGStatPortNumber OBJECT-TYPE
            SYNTAX INTEGER 
            ACCESS read-only
            STATUS mandatory
            DESCRIPTION
               "A T1E1TG Stat Table Port Number. Each Port 
                 contains the configuration parameters for a single
                 T1E1TG  Table."
        ::= { cdx6500PSTT1E1TGEntry 1 }

        cdx6500T1E1TGStatInterfaceType OBJECT-TYPE
            SYNTAX DisplayString
            ACCESS read-only
            STATUS mandatory
            DESCRIPTION
                "This parameter indicates the type of interface."
        ::= { cdx6500PSTT1E1TGEntry 2 }

        cdx6500T1E1TGStatTimeSinceLastReset OBJECT-TYPE
            SYNTAX DisplayString
            ACCESS read-only
            STATUS mandatory
            DESCRIPTION
                "Time since last reset has happened for the interface."
        ::= { cdx6500PSTT1E1TGEntry 3 }

        cdx6500T1E1TGStatAlarmState OBJECT-TYPE
            SYNTAX DisplayString
            ACCESS read-only
            STATUS mandatory
            DESCRIPTION
                "Time since last reset has happened for the interface."
        ::= { cdx6500PSTT1E1TGEntry 4 }

                    
        -- The last 24 hour Error Statistics Table

        cdx6500PSTT1E1TGStatTotal24HoursReportTable OBJECT-TYPE
            SYNTAX SEQUENCE OF Cdx6500PSTT1E1TGStatTotal24HoursReportEntry
            ACCESS not-accessible
            STATUS mandatory
            DESCRIPTION
                "This table holds a report of the cumulative sum
                 of the statistics for the previous 24 hour interval."
        ::= { cdx6500PSTT1E1TGPortTable 2 }

        cdx6500PSTT1E1TGStatTotal24HoursReportEntry OBJECT-TYPE
            SYNTAX Cdx6500PSTT1E1TGStatTotal24HoursReportEntry
            ACCESS not-accessible
            STATUS mandatory
            DESCRIPTION
                "Each entry contains statistics information for one T1 port."
            INDEX  { cdx6500PSTT1E1TGStatTotal24HoursReportPortNumber }
        ::= { cdx6500PSTT1E1TGStatTotal24HoursReportTable 1 }

        Cdx6500PSTT1E1TGStatTotal24HoursReportEntry ::=
            SEQUENCE {
                cdx6500T1E1TGStatTotal24HoursReportPortNumber
                    INTEGER,
                cdx6500T1E1TGStatTotal24HoursReportLES
                    Gauge,
                cdx6500T1E1TGStatTotal24HoursReportLCV
                    Gauge,
                cdx6500T1E1TGStatTotal24HoursReportPCV
                    Gauge,
                cdx6500T1E1TGStatTotal24HoursReportCSS
                    Gauge,
                cdx6500T1E1TGStatTotal24HoursReportES
                    Gauge,
                cdx6500T1E1TGStatTotal24HoursReportBES
                    Gauge,
                cdx6500T1E1TGStatTotal24HoursReportSES
                    Gauge,
                cdx6500T1E1TGStatTotal24HoursReportSEFS
                    Gauge,
                cdx6500T1E1TGStatTotal24HoursReportUAS
                    Gauge
                }

        cdx6500T1E1TGStatTotal24HoursReportPortNumber OBJECT-TYPE
            SYNTAX INTEGER 
            ACCESS read-only
            STATUS mandatory
            DESCRIPTION
                "Port number of the T1E1TG."
        ::= { cdx6500PSTT1E1TGStatTotal24HoursReportEntry 1 }
     
        cdx6500T1E1TGStatTotal24HoursReportLES OBJECT-TYPE
            SYNTAX Gauge
            ACCESS read-only
            STATUS mandatory
            DESCRIPTION
                "The number of Line Errored Seconds (LESs)
                 encountered by the T1E1TG interface in the 
                 previous 24 hour interval. "
        ::= { cdx6500PSTT1E1TGStatTotal24HoursReportEntry 2 }

        cdx6500T1E1TGStatTotal24HoursReportLCV OBJECT-TYPE
            SYNTAX Gauge
            ACCESS read-only
            STATUS mandatory
            DESCRIPTION
                "The number of Line Code Violations (LCVs)
                 encountered by the T1E1TG interface in the 
                 previous 24 hour interval."
        ::= { cdx6500PSTT1E1TGStatTotal24HoursReportEntry 3 }

        cdx6500T1E1TGStatTotal24HoursReportPCV OBJECT-TYPE
            SYNTAX Gauge
            ACCESS read-only
            STATUS mandatory
            DESCRIPTION
                "The number of Path Coding  Violations (PCVs)
                 encountered by the T1E1TG interface in the 
                 previous 24 hour interval."
        ::= { cdx6500PSTT1E1TGStatTotal24HoursReportEntry 4 }

        cdx6500T1E1TGStatTotal24HoursReportCSS OBJECT-TYPE
            SYNTAX Gauge
            ACCESS read-only
            STATUS mandatory
            DESCRIPTION
                "The number of Controlled Slip Seconds (CSSs)
                 encountered by the T1E1TG interface in the 
                 previous 24 hour interval."
        ::= { cdx6500PSTT1E1TGStatTotal24HoursReportEntry 5 }

        cdx6500T1E1TGStatTotal24HoursReportES OBJECT-TYPE
            SYNTAX Gauge
            ACCESS read-only
            STATUS mandatory
            DESCRIPTION
                "The number of Errored Seconds (ESs) 
                 encountered by the T1E1TG interface in the 
                 previous 24 hour interval."
        ::= { cdx6500PSTT1E1TGStatTotal24HoursReportEntry 6 }

        cdx6500T1E1TGStatTotal24HoursReportBES OBJECT-TYPE
            SYNTAX Gauge
            ACCESS read-only
            STATUS mandatory
            DESCRIPTION
                "The number of Bursty Errored Seconds (BESs)
                 encountered by the T1E1TG interface in the 
                 previous 24 hour interval."
        ::= { cdx6500PSTT1E1TGStatTotal24HoursReportEntry 7 }

        cdx6500T1E1TGStatTotal24HoursReportSES OBJECT-TYPE
            SYNTAX Gauge
            ACCESS read-only
            STATUS mandatory
            DESCRIPTION
                "The number of Severely Errored Seconds (SESs)
                 encountered by the T1E1TG interface in the
                 previous 24 hour interval."
        ::= { cdx6500PSTT1E1TGStatTotal24HoursReportEntry 8 }

        cdx6500T1E1TGStatTotal24HoursReportSEFS OBJECT-TYPE
            SYNTAX Gauge
            ACCESS read-only
            STATUS mandatory
            DESCRIPTION
                "The number of Severely Errored Framing Seconds (SEFSs)
                 encountered by the T1E1TG interface in the previous
                 24 hour interval."
        ::= { cdx6500PSTT1E1TGStatTotal24HoursReportEntry 9 }

        cdx6500T1E1TGStatTotal24HoursReportUAS OBJECT-TYPE
            SYNTAX Gauge
            ACCESS read-only
            STATUS mandatory
            DESCRIPTION
                "The number of Unavailable Seconds (UASs)
                 encountered by the T1E1TG interface in the 
                 previous 24 hour interval."
        ::= { cdx6500PSTT1E1TGStatTotal24HoursReportEntry 10 }

        -- The current 15 minute interval Error Statistics Table

        cdx6500PSTT1E1TGStatCurrent15MinutesReportTable OBJECT-TYPE
            SYNTAX SEQUENCE OF Cdx6500PSTT1E1TGStatCurrent15MinutesReportEntry
            ACCESS not-accessible
            STATUS mandatory
            DESCRIPTION
                "This table holds a report of the statistics for the 
                 current 15 minutes interval."
        ::= { cdx6500PSTT1E1TGPortTable 3 }

        cdx6500PSTT1E1TGStatCurrent15MinutesReportEntry OBJECT-TYPE
            SYNTAX Cdx6500PSTT1E1TGStatCurrent15MinutesReportEntry
            ACCESS not-accessible
            STATUS mandatory
            DESCRIPTION
                "Each entry contains statistics information for one T1E1TG Interface."
            INDEX  { cdx6500T1E1TGStatCurrent15MinutesReportPortNumber }
        ::= { cdx6500PSTT1E1TGStatCurrent15MinutesReportTable 1 }

        Cdx6500PSTT1E1TGStatCurrent15MinutesReportEntry ::=
            SEQUENCE {
                cdx6500T1E1TGStatCurrent15MinutesReportPortNumber
                    INTEGER,
                cdx6500T1E1TGStatCurrent15MinutesReportTimeElapsed
                    INTEGER,
                cdx6500T1E1TGStatCurrent15MinutesReportLES
                    Gauge,
                cdx6500T1E1TGStatCurrent15MinutesReportLCV
                    Gauge,
                cdx6500T1E1TGStatCurrent15MinutesReportPCV
                    Gauge,
                cdx6500T1E1TGStatCurrent15MinutesReportCSS
                    Gauge,
                cdx6500T1E1TGStatCurrent15MinutesReportES
                    Gauge,
                cdx6500T1E1TGStatCurrent15MinutesReportBES
                    Gauge,
                cdx6500T1E1TGStatCurrent15MinutesReportSES
                    Gauge,
                cdx6500T1E1TGStatCurrent15MinutesReportSEFS
                    Gauge,
                cdx6500T1E1VgStatCurrent15MinutesReportUAS
                    Gauge
                }                                               

        cdx6500T1E1TGStatCurrent15MinutesReportPortNumber OBJECT-TYPE
            SYNTAX INTEGER 
            ACCESS read-only
            STATUS mandatory
            DESCRIPTION
                "Port number of the T1E1TG."
        ::= { cdx6500PSTT1E1TGStatCurrent15MinutesReportEntry 1 }

        cdx6500T1E1TGStatCurrent15MinutesReportTimeElapsed OBJECT-TYPE
            SYNTAX INTEGER 
            ACCESS read-only
            STATUS mandatory
            DESCRIPTION
                "The time that has elapsed since the beginning 
                 of the current 15 minutes interval."
        ::= { cdx6500PSTT1E1TGStatCurrent15MinutesReportEntry 2 }
                    
        cdx6500T1E1TGStatCurrent15MinutesReportLES OBJECT-TYPE
            SYNTAX Gauge
            ACCESS read-only
            STATUS mandatory
            DESCRIPTION
                "The number of Line Errored Seconds (LESs)
                 encountered by the T1E1TG interface in the 
                 current 15 minute interval."
        ::= { cdx6500PSTT1E1TGStatCurrent15MinutesReportEntry 3 }

        cdx6500T1E1TGStatCurrent15MinutesReportLCV OBJECT-TYPE
            SYNTAX Gauge
            ACCESS read-only
            STATUS mandatory
            DESCRIPTION
                "The number of Line Code Violations (LCVs)
                 encountered by the T1E1TG interface in the 
                 current 15 minute interval."
        ::= { cdx6500PSTT1E1TGStatCurrent15MinutesReportEntry 4 }

        cdx6500T1E1TGStatCurrent15MinutesReportPCV OBJECT-TYPE
            SYNTAX Gauge
            ACCESS read-only
            STATUS mandatory
            DESCRIPTION
                "The number of Path Coding  Violations (PCVs)
                 encountered by the T1E1TG interface in the 
                 current 15 minute interval."
        ::= { cdx6500PSTT1E1TGStatCurrent15MinutesReportEntry 5 }

        cdx6500T1E1TGStatCurrent15MinutesReportCSS OBJECT-TYPE
            SYNTAX Gauge
            ACCESS read-only
            STATUS mandatory
            DESCRIPTION
                "The number of Controlled Slip Seconds (CSSs)
                 encountered by the T1E1TG interface in the 
                 current 15 minute interval."
        ::= { cdx6500PSTT1E1TGStatCurrent15MinutesReportEntry 6 }

        cdx6500T1E1TGStatCurrent15MinutesReportES OBJECT-TYPE
            SYNTAX Gauge
            ACCESS read-only
            STATUS mandatory
            DESCRIPTION
                "The number of Errored Seconds (ESs) 
                 encountered by the T1E1TG interface in the 
                 current 15 minute interval."
        ::= { cdx6500PSTT1E1TGStatCurrent15MinutesReportEntry 7 }

        cdx6500T1E1TGStatCurrent15MinutesReportBES OBJECT-TYPE
            SYNTAX Gauge
            ACCESS read-only
            STATUS mandatory
            DESCRIPTION
                "The number of Bursty Errored Seconds (BESs)
                 encountered by the T1E1TG interface in the 
                 current 15 minute interval."
        ::= { cdx6500PSTT1E1TGStatCurrent15MinutesReportEntry 8 }

        cdx6500T1E1TGStatCurrent15MinutesReportSES OBJECT-TYPE
            SYNTAX Gauge
            ACCESS read-only
            STATUS mandatory
            DESCRIPTION
                "The number of Severely Errored Seconds (SESs)
                 encountered by the T1E1TG interface in the
                 current 15 minute interval."
        ::= { cdx6500PSTT1E1TGStatCurrent15MinutesReportEntry 9 }

        cdx6500T1E1TGStatCurrent15MinutesReportSEFS OBJECT-TYPE
            SYNTAX Gauge
            ACCESS read-only
            STATUS mandatory
            DESCRIPTION
                "The number of Severely Errored Framing Seconds (SEFSs)
                 encountered by the T1E1TG interface in the current
                 15 minute interval."
        ::= { cdx6500PSTT1E1TGStatCurrent15MinutesReportEntry 10 }

        cdx6500T1E1TGStatCurrent15MinutesReportUAS OBJECT-TYPE
            SYNTAX Gauge
            ACCESS read-only
            STATUS mandatory
            DESCRIPTION
                "The number of Unavailable Seconds (UASs)
                 encountered by the T1E1TG interface in the 
                 current 15 minute interval."
        ::= { cdx6500PSTT1E1TGStatCurrent15MinutesReportEntry 11 }

        -- The Interval Error Statistics Table

        cdx6500PSTT1E1TGStatIntervalReportTable OBJECT-TYPE
            SYNTAX SEQUENCE OF Cdx6500PSTT1E1TGStatIntervalReportEntry
            ACCESS not-accessible
            STATUS mandatory
            DESCRIPTION
                "The T1E1 Interval Table contains various
                 statistics collected by each T1E1 Interface over
                 the previous 24 hours of operation.  The past 24
                 hours are broken into 96 completed 15 minute
                 intervals.  "
        ::= { cdx6500PSTT1E1TGPortTable 4 }

        cdx6500PSTT1E1TGStatIntervalReportEntry OBJECT-TYPE
            SYNTAX Cdx6500PSTT1E1TGStatIntervalReportEntry
            ACCESS not-accessible
            STATUS mandatory
            DESCRIPTION
                "Each entry contains statistics information for one T1E1TG Interface."
            INDEX  { cdx6500T1E1TGStatIntervalReportPortNumber,cdx6500T1E1TGStatIntervalNumber }
        ::= { cdx6500PSTT1E1TGStatIntervalReportTable 1 }
        Cdx6500PSTT1E1TGStatIntervalReportEntry ::=
            SEQUENCE {
                cdx6500T1E1TGStatIntervalReportPortNumber
                    INTEGER,
                cdx6500T1E1TGStatIntervalNumber
                    INTEGER,
                cdx6500T1E1TGStatIntervalReportLES
                    Gauge,
                cdx6500T1E1TGStatIntervalReportLCV
                    Gauge,
                cdx6500T1E1TGStatIntervalReportPCV
                    Gauge,
                cdx6500T1E1TGStatIntervalReportCSS
                    Gauge,
                cdx6500T1E1TGStatIntervalReportES
                    Gauge,
                cdx6500T1E1TGStatIntervalReportBES
                    Gauge,
                cdx6500T1E1TGStatIntervalReportSES
                    Gauge,
                cdx6500T1E1TGStatIntervalReportSEFS
                    Gauge,
                cdx6500T1E1VgStatIntervalReportUAS
                    Gauge
                }

        cdx6500T1E1TGStatIntervalReportPortNumber OBJECT-TYPE
            SYNTAX INTEGER
            ACCESS read-only
            STATUS mandatory
            DESCRIPTION
                "The index which identifies the Port number of the T1E1."
        ::= { cdx6500PSTT1E1TGStatIntervalReportEntry 1 }

        cdx6500T1E1TGStatIntervalNumber OBJECT-TYPE
            SYNTAX INTEGER (1..96)
            ACCESS read-only
            STATUS mandatory
            DESCRIPTION
                 "A number between 1 and 96, where 1 is the most
                 recently completed 15 minute interval and 96 is
                 the 15 minutes interval completed 23 hours and 45
                 minutes prior to interval 1."
        ::= { cdx6500PSTT1E1TGStatIntervalReportEntry 2 }

        cdx6500T1E1TGStatIntervalReportLES OBJECT-TYPE
            SYNTAX Gauge
            ACCESS read-only
            STATUS mandatory
            DESCRIPTION
                "The number of Line Errored Seconds (LESs)
                 encountered by the T1E1TG interface in the
                 15 minute interval."
        ::= { cdx6500PSTT1E1TGStatIntervalReportEntry 3 }
        cdx6500T1E1TGStatIntervalReportLCV OBJECT-TYPE
            SYNTAX Gauge
            ACCESS read-only
            STATUS mandatory
            DESCRIPTION
                "The number of Line Code Violations (LCVs)
                 encountered by the T1E1TG interface in the
                 15 minute interval."
        ::= { cdx6500PSTT1E1TGStatIntervalReportEntry 4 }

        cdx6500T1E1TGStatIntervalReportPCV OBJECT-TYPE
            SYNTAX Gauge
            ACCESS read-only
            STATUS mandatory
            DESCRIPTION
                "The number of Path Coding  Violations (PCVs)
                 encountered by the T1E1TG interface in the
                 15 minute interval."
        ::= { cdx6500PSTT1E1TGStatIntervalReportEntry 5 }

        cdx6500T1E1TGStatIntervalReportCSS OBJECT-TYPE
            SYNTAX Gauge
            ACCESS read-only
            STATUS mandatory
            DESCRIPTION
                "The number of Controlled Slip Seconds (CSSs)
                 encountered by the T1E1TG interface in the
                 15 minute interval."
        ::= { cdx6500PSTT1E1TGStatIntervalReportEntry 6 }

        cdx6500T1E1TGStatIntervalReportES OBJECT-TYPE
            SYNTAX Gauge
            ACCESS read-only
            STATUS mandatory
            DESCRIPTION
                "The number of Errored Seconds (ESs)
                 encountered by the T1E1TG interface in the
                 15 minute interval."
        ::= { cdx6500PSTT1E1TGStatIntervalReportEntry 7 }

        cdx6500T1E1TGStatIntervalReportBES OBJECT-TYPE
            SYNTAX Gauge
            ACCESS read-only
            STATUS mandatory
            DESCRIPTION
                "The number of Bursty Errored Seconds (BESs)
                 encountered by the T1E1TG interface in the
                 15 minute interval."
        ::= { cdx6500PSTT1E1TGStatIntervalReportEntry 8 }
        cdx6500T1E1TGStatIntervalReportSES OBJECT-TYPE
            SYNTAX Gauge
            ACCESS read-only
            STATUS mandatory
            DESCRIPTION
                "The number of Severely Errored Seconds (SESs)
                 encountered by the T1E1TG interface in the
                 15 minute interval."
        ::= { cdx6500PSTT1E1TGStatIntervalReportEntry 9 }

        cdx6500T1E1TGStatIntervalReportSEFS OBJECT-TYPE
            SYNTAX Gauge
            ACCESS read-only
            STATUS mandatory
            DESCRIPTION
                "The number of Severely Errored Framing Seconds (SEFSs)
                 encountered by the T1E1TG interface in the 
                 15 minute interval."
        ::= { cdx6500PSTT1E1TGStatIntervalReportEntry 10 }

        cdx6500T1E1TGStatIntervalReportUAS OBJECT-TYPE
            SYNTAX Gauge
            ACCESS read-only
            STATUS mandatory
            DESCRIPTION
                "The number of Unavailable Seconds (UASs)
                 encountered by the T1E1TG interface in the
                 15 minute interval."
        ::= { cdx6500PSTT1E1TGStatIntervalReportEntry 11 }

        -- The T1E1TG Control Table
        cdx6500ContT1E1TGTable OBJECT IDENTIFIER
        ::= { cdx6500Controls 22 }

        cdx6500T1E1TGContEntry OBJECT-TYPE
            SYNTAX Cdx6500T1E1TGContEntry
            ACCESS not-accessible
            STATUS mandatory
            DESCRIPTION
                "Each control applies to a single T1E1TG Port."
            INDEX { t1e1tgContPortNumber }
        ::= { cdx6500ContT1E1TGTable 1 }

        Cdx6500T1E1TGContEntry ::=
            SEQUENCE {
                t1e1tgContPortNumber
                    INTEGER,
                t1e1tgContPortBoot
                    INTEGER
                }

        t1e1tgContPortNumber OBJECT-TYPE
            SYNTAX INTEGER
            ACCESS not-accessible
            STATUS mandatory
            DESCRIPTION
                "Port number of the T1E1TG."
        ::= { cdx6500T1E1TGContEntry 1 }

        t1e1tgContPortBoot OBJECT-TYPE
            SYNTAX INTEGER {
                   boot       (1),
                   noboot     (2)
                   }
            ACCESS write-only
            STATUS mandatory
            DESCRIPTION
                "Boot operations for the specified T1E1TG Port.
                 boot   : Boots the T1E1TG Port 
                 noboot : Do not Boots the T1E1TG Port."
        ::= { cdx6500T1E1TGContEntry 2 }

        END
