-- |**********************************************************************|
 -- | Copyright 1998 - Sonoma Systems, Inc. Marina del Rey, CA 90292       |
 -- |    Unpublished software - All rights reserved.                       |
 -- |                                                                      |
 -- | The information in this software is subject to change without notice |
 -- | and should not be construed as a commitment by Sonoma Systems, Inc.  |
 -- |                                                                      |
 -- | Sonoma Systems, Inc. assumes no responsibility for the use or        |
 -- | reliability of its software on equipment which is not supplied by    |
 -- | Sonoma Systems, Inc.                                                 |
 -- |                                                                      |
 -- | This software is furnished under a license and may be copied only    |
 -- | under the terms of that license and with the inclusion of this       |
 -- | notice. This software, or any other copies thereof, may not be       |
 -- | provided or otherwise made available to any other person except to   |
 -- | one who agrees to these license terms. Title to and ownership of the |
 -- | software shall at all times remain with Sonoma Systems, Inc.         |
 -- |**********************************************************************|
 --
 -- Sonoma Systems Inc.,
 -- 4640 Admiralty Way, Suite #600,
 -- Marina Del Rey,
 -- California 90292-6695.
 --
 -- Web : www.sonoma-systems.com
 -- Phone:  310.827.8000
 --
 -- NAME        : slipmib.def
 --
 -- DESCRIPTION : This is the SLIP MIB for the Sonoma serial interface.
 --
 -- ARCHIVE : $Archive:   M:\pvcs\pvcsproj\sonoma3\src\mib\slipmib.dev  $
 -- REVISION: $Revision:   1.5  $
 -- AUTHOR  : $Author:   FREEVE  $
 -- DATE    : $Date:   Nov 13 1998 10:33:40  $

      SONOMASYSTEMS-SONOMA-SLIP-MIB DEFINITIONS ::= BEGIN

      IMPORTS
        OBJECT-TYPE
        FROM RFC-1212
		sonomaApplications 
        FROM SONOMASYSTEMS-SONOMA-MIB;        


  --  This MIB module uses the extended OBJECT-TYPE macro as
  --  defined in [14];


    --
    -- Hierarchy for these groups
    -- enterprises OBJECT IDENTIFIER ::= { private 4 }
    -- sonomaSystems OBJECT IDENTIFIER ::= {  enterprises 2926 }
    -- sonomaSeries OBJECT IDENTIFIER ::= { sonomaSystems 25 }
    -- sonomaApplications OBJECT IDENTIFIER ::= { sonomaSeries 8 }
    slip OBJECT IDENTIFIER ::= { sonomaApplications 2 }

    slipSpeed OBJECT-TYPE
        SYNTAX  INTEGER {
                    sp2400(1),
                    sp4800(2),
                    sp9600(3),
                    sp19200(4),
                    sp38400(5),
					sp57600(6),
					sp115200(7)
                }
        ACCESS  read-write
        STATUS  mandatory
		DESCRIPTION
        "Specify the desired speed of your connection."
        DEFVAL { sp9600 }
        ::= { slip 1 }

    slipDataBits OBJECT-TYPE
        SYNTAX  INTEGER {
                    db8(3)
                }
        ACCESS  read-only
        STATUS  mandatory
        DESCRIPTION
        "Specify the number of data bits in the data packets sent between 
         the two computers."
        DEFVAL { db8 }
        ::= { slip 2 }

    slipParity OBJECT-TYPE
        SYNTAX  INTEGER {
                    none(3)
                }
        ACCESS  read-only
        STATUS  mandatory
        DESCRIPTION
        "Specify the parity type.  Parity is an error-checking procedure
		 on the transmitted data bits."
        DEFVAL { none }
        ::= { slip 3 }

    slipStopBits OBJECT-TYPE
        SYNTAX  INTEGER {
                    sb1(1),
                    sb2(2)
                }
        ACCESS  read-write
        STATUS  mandatory
        DESCRIPTION
        "Specify the time that elapses between transmitted characters."
        DEFVAL { sb1 }
        ::= { slip 4 }

	slipFlowControl OBJECT-TYPE
		SYNTAX  INTEGER {
					none(3)
				}
		ACCESS  read-only
		STATUS  mandatory
		DESCRIPTION
		"Indicate what Terminal should do if the buffer becomes too full
		 to receive more data from the remote computer."
		DEFVAL { none }
		::= { slip 5 }

    slipType OBJECT-TYPE
        SYNTAX  INTEGER {
                    uncompressed(1),
                    compressed(2)
                }
        ACCESS  read-write
        STATUS  mandatory
        DESCRIPTION
        "Specify whether Van Jacobson TCP/IP header compression is 
         performed on the SLIP interface."
        DEFVAL { uncompressed }
        ::= { slip 6 }

    slipMtu OBJECT-TYPE
        SYNTAX  INTEGER (64..1518) 
        ACCESS  read-write
        STATUS  mandatory
        DESCRIPTION
        "The size of the largest datagram which can be
         sent/received on the interface."
        DEFVAL { 1006 }
        ::= { slip 7 }

END
