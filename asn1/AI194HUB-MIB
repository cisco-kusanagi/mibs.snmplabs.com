AI194HUB-MIB DEFINITIONS ::=  BEGIN

-- Applied Innovation Incorporated MIB definitions
-- @(#) ai $Revision: 1.2 $ $Date: 97/11/20 08:36:58 $

IMPORTS
	TimeTicks, Counter FROM RFC1155-SMI
		DisplayString FROM SNMPv2-TC
    MODULE-IDENTITY, OBJECT-TYPE, NOTIFICATION-TYPE,
    Counter32, Integer32,
    enterprises
	FROM SNMPv2-SMI
--    InterfaceIndex
--        FROM IF-MIB
    MODULE-COMPLIANCE, OBJECT-GROUP
	FROM SNMPv2-CONF;


-- group object IDs

aii		OBJECT IDENTIFIER ::= { enterprises 539 }
aiProxy		OBJECT IDENTIFIER ::= { aii 1 }
aiSystemOID	OBJECT IDENTIFIER ::= { aii 2 }
aiGroup		OBJECT IDENTIFIER ::= { aii 4 }
aiISISGre	OBJECT IDENTIFIER ::= { aii 5 }
aiManager	OBJECT IDENTIFIER ::= { aii 6 }
aiSoftware	OBJECT IDENTIFIER ::= { aii 7 }
aiSystem	OBJECT IDENTIFIER ::= { aii 8 }

-- System Group for AI.

aiGroup194	OBJECT IDENTIFIER ::= { aiGroup 194 }
aiGroup194Ver7	OBJECT IDENTIFIER ::= { aiGroup194 7 }
aiGroup194Ver71	OBJECT IDENTIFIER ::= { aiGroup194Ver7 1 }
aiGroup194Ver72	OBJECT IDENTIFIER ::= { aiGroup194Ver7 2 }
aiGroup194Ver73	OBJECT IDENTIFIER ::= { aiGroup194Ver7 3 }
aiGroup194Ver74	OBJECT IDENTIFIER ::= { aiGroup194Ver7 4 }

-- the Hub group

aiHub   MODULE-IDENTITY
    LAST-UPDATED "9505081700Z"
    ORGANIZATION "Applied Innovation Incorporated"
    CONTACT-INFO
        "        Engineering MIB Administrator

        Postal:  Applied Innovation Inc.
                 5800 Innovation Drive
                 Dublin, OH 43016-3271

           Tel:  614/798-2000
           Fax:  614/798-1770
        E-mail:  snmp@aiinet.com"
    DESCRIPTION
        "The MIB Module for Ethernet hubs"
    ::= { aii 3 }

-- Implementation of this group is mandatory for all Applied Innovation
-- Ethernet hubs that support SNMP management

aiHubTwistedPairPortNumber OBJECT-TYPE
    SYNTAX INTEGER
    ACCESS read-only
    STATUS mandatory
    DESCRIPTION
        "The number of twisted-pair hub ports. By
        convention, these are the lower numbered hub ports."
::= { aiHub 1 }

aiHubNonTwistedPairPortNumber OBJECT-TYPE
    SYNTAX INTEGER
    ACCESS read-only
    STATUS mandatory
    DESCRIPTION
        "The number of non-twisted-pair hub ports."
::= { aiHub 2 }


-- the Hub Port table

aiHubPortTable OBJECT-TYPE
    SYNTAX SEQUENCE OF HubPortEntry
    ACCESS not-accessible
    STATUS mandatory
    DESCRIPTION
        "A list of hub Ethernet port entries."
    ::= { aiHub 3 }

aiHubPortEntry OBJECT-TYPE
    SYNTAX HubPortEntry
    ACCESS not-accessible
    STATUS mandatory
    DESCRIPTION
        "Hub parameter values for an Ethernet port."
    INDEX { aiHubPortIndex }
    ::= { aiHubPortTable 1 }

HubPortEntry ::=
    SEQUENCE {
        aiHubPortIndex
            INTEGER,
        aiHubPortName
            DisplayString,
        aiHubPortAdminState
            INTEGER,
        aiHubPortAutoPartitionState
            INTEGER,
        aiHubPortErrors
            Counter,
        aiHubPortCollisions
            Counter,
	aiHubPortStatus
	    INTEGER,
        aiHubPortLinkErrors
            Counter,
        aiHubPortShortPackets
            Counter,
        aiHubPortJabbers
            Counter,
        aiHubPortPartition
            Counter,
        aiHubPortZero
            INTEGER,
	aiHubPortZeroTime
	    TimeTicks
    }

aiHubPortIndex OBJECT-TYPE
    SYNTAX INTEGER
    ACCESS read-only
    STATUS mandatory
    DESCRIPTION
        "An index value that uniquely identifies a port.
        The port identified by a particular value of this
        index is the same port as identified by portBasicID
        in hmBasicPortTable in the IEEE Hub MIB.
        Corresponds directly to the numbered, twisted-pair
        port numbers and indirectly to the unnumbered,
        non-twisted-pair ports (A, C) in the diagnostic
        display."
    ::= { aiHubPortEntry 1 }

aiHubPortName OBJECT-TYPE
    SYNTAX DisplayString (SIZE (0..16))
    ACCESS read-write
    STATUS mandatory
    DESCRIPTION
        "An administratively assigned name for a
        twisted-pair port, typically with some local
        significance.  Corresponds directly to the
        WINSLC PORTNAME string."
    ::= { aiHubPortEntry 2 }

aiHubPortAdminState OBJECT-TYPE
    SYNTAX INTEGER { other(1), disabled(2), enabled(3) }
    ACCESS read-write
    STATUS mandatory
    DESCRIPTION
        "Control over the port's ability to transmit and
        receive.  ENABLED/DISABLED."
    ::= { aiHubPortEntry 3 }
            
aiHubPortAutoPartitionState OBJECT-TYPE
    SYNTAX INTEGER { other(1), notAutoPartitioned(2),
        autoPartitioned(3) }
    ACCESS read-only
    STATUS mandatory
    DESCRIPTION
        "The port's status with regard to automatic
         partitioning."
    ::= { aiHubPortEntry 4 }

aiHubPortErrors OBJECT-TYPE
    SYNTAX Counter
    ACCESS read-only
    STATUS mandatory
    DESCRIPTION
        "The number of times that a frame was received
        in erorr."
    ::= { aiHubPortEntry 5 }

aiHubPortCollisions OBJECT-TYPE
    SYNTAX Counter
    ACCESS read-only
    STATUS mandatory
    DESCRIPTION
        "Number of times that a frame collision came within
        the allowed collision window."
    ::= { aiHubPortEntry 6 }

aiHubPortStatus	OBJECT-TYPE
    SYNTAX INTEGER { other(1), off(2), on(3) }
    ACCESS read-only
    STATUS mandatory
    DESCRIPTION
	"Link status of the port"
    ::= { aiHubPortEntry 7 }


aiHubPortLinkErrors OBJECT-TYPE
    SYNTAX Counter
    ACCESS read-only
    STATUS mandatory
    DESCRIPTION
        "Number of times that a link error was detected."
    ::= { aiHubPortEntry 8 }


aiHubPortShortPackets OBJECT-TYPE
    SYNTAX Counter
    ACCESS read-only
    STATUS mandatory
    DESCRIPTION
        "Number of times that a short packet was detected."
    ::= { aiHubPortEntry 9 }


aiHubPortJabbers OBJECT-TYPE
    SYNTAX Counter
    ACCESS read-only
    STATUS mandatory
    DESCRIPTION
        "Number of times that a jabber packet ??? was detected."
    ::= { aiHubPortEntry 10 }

aiHubPortPartition OBJECT-TYPE
    SYNTAX Counter
    ACCESS read-only
    STATUS mandatory
    DESCRIPTION
        "Number of times that this port was AutoPartitioned."
    ::= { aiHubPortEntry 11 }

aiHubPortZero OBJECT-TYPE
    SYNTAX INTEGER { ready(1), execute(2) }
    ACCESS read-write
    STATUS mandatory
    DESCRIPTION
        "Control to zero Counters kept for the port.  In
        response to a get-request or get-next-request, the
        agent always returns 'ready' for this value.
        Setting the value to 'ready' has no effect.  Setting
        it to 'execute' causes all the system's Counters to
        be zeroed.  Corresponds to the ZERO PORT command."
    ::= { aiHubPortEntry 12 }

aiHubPortZeroTime OBJECT-TYPE
    SYNTAX TimeTicks
    ACCESS read-only
    STATUS mandatory
    DESCRIPTION
	"The time the counters for this port was last zeroed."
    ::= { aiHubPortEntry 13 }     

aiHubLogMessage OBJECT-TYPE
    SYNTAX DisplayString (SIZE (0..64))
    ACCESS read-write
    STATUS mandatory
    DESCRIPTION
        "Any string 'set' into this variable will force a log
        message to be printed on the CLC log."
    ::= { aiHub 4 }

aiHubPortAutoPartitionLimit OBJECT-TYPE
    SYNTAX INTEGER { coll31(1), coll63(2) }
    ACCESS read-write
    STATUS mandatory
    DESCRIPTION
        "The hub AutoPartition limit, 31 or 63 collisions."
    ::= { aiHub 5 }

END
