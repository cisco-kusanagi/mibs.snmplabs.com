--			Ascend mibospfvlnk MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBOSPFVLNK-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibospfVirtIntfProfile  OBJECT IDENTIFIER ::= { configuration 99}

	-- The mibospfVirtIntfProfile table
	--
	-- This table contains parameters for the mibospfVirtIntfProfile profile
	--

    mibospfVirtIntfProfileTable	OBJECT-TYPE
	SYNTAX		SEQUENCE OF MibospfVirtIntfProfileEntry
	ACCESS		not-accessible
	STATUS		mandatory
	DESCRIPTION	"A list of mibospfVirtIntfProfile profile entries."
	::= { mibospfVirtIntfProfile 1 }

    mibospfVirtIntfProfileEntry	OBJECT-TYPE
	SYNTAX		MibospfVirtIntfProfileEntry
	ACCESS		not-accessible
	STATUS		mandatory
	DESCRIPTION	"A mibospfVirtIntfProfile entry containing objects that
			 maps to the parameters of mibospfVirtIntfProfile profile."
	INDEX		{ ospfVirtIntfProfile-NeighborRouterId }
	::= { mibospfVirtIntfProfileTable 1 }

    MibospfVirtIntfProfileEntry ::=
	SEQUENCE {
	    ospfVirtIntfProfile-NeighborRouterId
		IpAddress,
	    ospfVirtIntfProfile-TransitAreaId
		IpAddress,
	    ospfVirtIntfProfile-RexmitDelay
		INTEGER,
	    ospfVirtIntfProfile-XmitDelay
		INTEGER,
	    ospfVirtIntfProfile-HelloInterval
		INTEGER,
	    ospfVirtIntfProfile-DeadInterval
		INTEGER,
	    ospfVirtIntfProfile-AuthenType
		INTEGER,
	    ospfVirtIntfProfile-AuthenKey
		DisplayString,
	    ospfVirtIntfProfile-KeyId
		INTEGER,
	    ospfVirtIntfProfile-Md5AuthenKey
		DisplayString,
	    ospfVirtIntfProfile-Action-o
		INTEGER
	}

    ospfVirtIntfProfile-NeighborRouterId	OBJECT-TYPE
	SYNTAX	IpAddress
	ACCESS	read-only
	STATUS	mandatory
	DESCRIPTION	"Ospf virtual link neighbor router id."
	::= { mibospfVirtIntfProfileEntry 1 }

    ospfVirtIntfProfile-TransitAreaId	OBJECT-TYPE
	SYNTAX	IpAddress
	ACCESS	read-write
	STATUS	mandatory
	DESCRIPTION	"Ospf virtual link transit area id."
	::= { mibospfVirtIntfProfileEntry 2 }

    ospfVirtIntfProfile-RexmitDelay	OBJECT-TYPE
	SYNTAX	INTEGER
	ACCESS	read-write
	STATUS	mandatory
	DESCRIPTION	"Ospf virtual link re-xmit delay."
	::= { mibospfVirtIntfProfileEntry 3 }

    ospfVirtIntfProfile-XmitDelay	OBJECT-TYPE
	SYNTAX	INTEGER
	ACCESS	read-write
	STATUS	mandatory
	DESCRIPTION	"Ospf virtual link xmit delay."
	::= { mibospfVirtIntfProfileEntry 4 }

    ospfVirtIntfProfile-HelloInterval	OBJECT-TYPE
	SYNTAX	INTEGER
	ACCESS	read-write
	STATUS	mandatory
	DESCRIPTION	"Ospf virtual link hello packet interval."
	::= { mibospfVirtIntfProfileEntry 5 }

    ospfVirtIntfProfile-DeadInterval	OBJECT-TYPE
	SYNTAX	INTEGER
	ACCESS	read-write
	STATUS	mandatory
	DESCRIPTION	"Ospf virtual link dead interval."
	::= { mibospfVirtIntfProfileEntry 6 }

    ospfVirtIntfProfile-AuthenType	OBJECT-TYPE
	SYNTAX	INTEGER {
		    none (1),
		    simple (2),
		    md5 (3)
		}
	ACCESS	read-write
	STATUS	mandatory
	DESCRIPTION	"Ospf virtual link authentication type."
	::= { mibospfVirtIntfProfileEntry 7 }

    ospfVirtIntfProfile-AuthenKey	OBJECT-TYPE
	SYNTAX	DisplayString
	ACCESS	read-write
	STATUS	mandatory
	DESCRIPTION	"Ospf virtual link authentication key."
	::= { mibospfVirtIntfProfileEntry 8 }

    ospfVirtIntfProfile-KeyId	OBJECT-TYPE
	SYNTAX	INTEGER
	ACCESS	read-write
	STATUS	mandatory
	DESCRIPTION	"Ospf virtual link MD5 authentication key."
	::= { mibospfVirtIntfProfileEntry 9 }

    ospfVirtIntfProfile-Md5AuthenKey	OBJECT-TYPE
	SYNTAX	DisplayString
	ACCESS	read-write
	STATUS	mandatory
	DESCRIPTION	"Ospf virtual link MD5 authentication key."
	::= { mibospfVirtIntfProfileEntry 10 }

    ospfVirtIntfProfile-Action-o	OBJECT-TYPE
	SYNTAX	INTEGER {
		    noAction (1),
		    createProfile (2),
		    deleteProfile (3)
		}
	ACCESS	read-write
	STATUS	mandatory
	DESCRIPTION	""
	::= { mibospfVirtIntfProfileEntry 11 }

END
