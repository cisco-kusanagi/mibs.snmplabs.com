COMPUTERM-TRAP-MIB

--
-- Computerm Trap MIB
-- Author  : Raja Kolli
-- Created : 8/1/97
-- Revision: 1.0
-- Last Modified: 8/1/97
-- Last Modified By:
--
--
-- Copyright 1997 Computerm Corp. All Rights reserved. This Computerm
-- SNMP Management Information Base Specification embodies Computerm's
-- confidential and proprietary intellectual property. Computerm
-- retains all title and ownership in the Specification, including any
-- revisions.
--

-- This Specification is supplied "AS IS," and Computerm makes no
-- warranty, either express or implied, as to the use, operation,
-- condition, or performance of the specification.
--


DEFINITIONS ::= BEGIN

-- Section 1: Top Level Definitions

-- Imports

IMPORTS
    snmp                          FROM RFC1213-MIB
    TRAP-TYPE                     FROM RFC-1215
    computerm, ctAbortAlertShortDescription, ctAbortAlertDescription                     FROM COMPUTERM-COMMON-MIB;

-- Section 2: Generic Trap Definitions

-- Section 3: Computerm Enterprise Specific Definitions

   ctAbort  TRAP-TYPE
       ENTERPRISE  ctSystem
       VARIABLES   { ctAbortAlertShortDescription,
                     ctAbortAlertDescription}
       DESCRIPTION "Signifies that an abort has occured. Short and Long
                    descriptions provide further information. All the
                    Computerm aborts will be notified to the user using
                    this trap. This trap will be defined in the NMS
                    with a severity level of Critical."
       ::= 1

   ctAlert  TRAP-TYPE
       ENTERPRISE  ctSystem
       VARIABLES   { ctAbortAlertShortDescription,
                     ctAbortAlertDescription }
       DESCRIPTION "Signifies a Computerm alert e.g. ErrorRate or
                    Utilization values have exceeded the threshold
                    values. Short and Long descriptions provide
                    further information.

                    This trap will be defined in the NMS with a
                    severity of level of WARNING."
       ::= 2

   ctInformationalAbort  TRAP-TYPE
       ENTERPRISE  ctSystem
       VARIABLES   { ctAbortAlertShortDescription,
                     ctAbortAlertDescription}
       DESCRIPTION "Signifies that an informational abort has occured.
                    Short and Long descriptions provide further
                    information. All the Computerm aborts will be
                    divided into those that require user attention and
                    those that are informational to the user. This
                    will be used to notify the user that an
                    informational abort has occured. This trap will
                    be defined in the NMS with a severity level of
                    Informational.

                    This trap is not used in Phase I"
       ::= 3

   ctCxNormalMode TRAP-TYPE
       ENTERPRISE  ctSystem
       VARIABLES   { ctAbortAlertShortDescription,
                     ctAbortAlertDescription }
       DESCRIPTION "Used for normal mode traps.

                    This trap will be defined in the NMS with a
                    Normal Severity level."
       ::= 4

   ctCxDiagnosticsMode TRAP-TYPE
       ENTERPRISE  ctSystem
       VARIABLES   { ctAbortAlertShortDescription,
                     ctAbortAlertDescription }
       DESCRIPTION "Channel Extender is in diagnostics mode. This
                    trap will be used to distinguish between the
                    ONLINE and OFFLINE unit.

                    This trap will be defined in the NMS with a
                    Disabled Severity level.

                    When Traps are configured in the NMS, this trap
                    should be auto-acknoledged by
                    ctCxNormalChannelExtenderMode trap"
       ::= 5

   ctCxNormalChannelExtenderMode TRAP-TYPE
       ENTERPRISE  ctSystem
       VARIABLES   { ctAbortAlertShortDescription,
                     ctAbortAlertDescription }
       DESCRIPTION "Channel Extender is in Channel Extension mode
                    and operating in normal mode.

                    This trap will be defined in the NMS with a
                    Normal Severity level."
       ::= 6
END
