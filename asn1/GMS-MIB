GMS-MIB DEFINITIONS ::= BEGIN

IMPORTS
   MODULE-IDENTITY, OBJECT-TYPE, NOTIFICATION-TYPE,
   TimeTicks, Gauge32, Counter32, Counter64, snmpModules, mib-2, enterprises
       FROM SNMPv2-SMI
   DisplayString, TestAndIncr, TimeStamp, TimeInterval
       FROM SNMPv2-TC
   applIndex
       FROM NETWORK-SERVICES-MIB
   MODULE-COMPLIANCE, OBJECT-GROUP, NOTIFICATION-GROUP
       FROM SNMPv2-CONF;

gordano MODULE-IDENTITY
    LAST-UPDATED "0909050000Z"
    ORGANIZATION "Gordano Ltd"
    CONTACT-INFO "Gordano Support
                  Postal: Gordano Ltd
                          18 Kenn Road
                          Clevedon
                          North Somerset
                          BS21 6EL
                          United Kingdom

                  Tel: +44 1275 340151

                  E-mail: support@gordano.com"
    DESCRIPTION 
        "MIB module for Gordano Products."
    REVISION     "1611050000Z"
    DESCRIPTION 
        "Initial revision."
    ::= { enterprises 24534}

gmsAV   OBJECT IDENTIFIER ::= { gordano 2 }
gmsAS   OBJECT IDENTIFIER ::= { gordano 3 }
gmsSMTP OBJECT IDENTIFIER ::= { gordano 4 }
gmsPOST OBJECT IDENTIFIER ::= { gordano 5 }
gmsPOP  OBJECT IDENTIFIER ::= { gordano 6 }
gmsIMAP OBJECT IDENTIFIER ::= { gordano 7 }
gmsWWW  OBJECT IDENTIFIER ::= { gordano 8 }

-- gmsApplTable definitions 

gmsApplTable OBJECT-TYPE
   SYNTAX SEQUENCE OF GmsApplEntry
   MAX-ACCESS not-accessible
   STATUS current
   DESCRIPTION
     "An extension of the application table defined in RFC2788."
   ::= {gordano 1}

gmsApplEntry OBJECT-TYPE
   SYNTAX GmsApplEntry
   MAX-ACCESS not-accessible
   STATUS current
   DESCRIPTION
     "The entry associated with each GMS service."
   INDEX {applIndex}
   ::= {gmsApplTable 1}

GmsApplEntry ::= SEQUENCE {
   applHandleCount
     INTEGER,
   applPercentCPU
     INTEGER,
   applRssKB
     INTEGER
}

applHandleCount OBJECT-TYPE
   SYNTAX INTEGER
   MAX-ACCESS read-only
   STATUS current
   DESCRIPTION
     "The number of open handles for the process."
   ::= {gmsApplEntry 1}

applPercentCPU OBJECT-TYPE
   SYNTAX INTEGER
   MAX-ACCESS read-only
   STATUS current
   DESCRIPTION
     "The percentage of CPU used for the process.
      This value does not take multiple CPUs into account."
   ::= {gmsApplEntry 2}

applRssKB OBJECT-TYPE
   SYNTAX INTEGER
   MAX-ACCESS read-only
   STATUS current
   DESCRIPTION
     "The resident set size for the process in KB."
   ::= {gmsApplEntry 3}

-- GMS Anti-Virus definitions 

avEngineVersion OBJECT-TYPE
  SYNTAX  DisplayString
  MAX-ACCESS  read-only
  STATUS  current
  DESCRIPTION "Anti-Virus Engine Version"
  ::= { gmsAV 1 }

avLastUpdate OBJECT-TYPE
  SYNTAX  DisplayString
  MAX-ACCESS  read-only
  STATUS  current
  DESCRIPTION "Date of last Anti-Virus update."
  ::= { gmsAV 2 }
  
avMessagesScanned OBJECT-TYPE
  SYNTAX  Counter64
  MAX-ACCESS  read-only
  STATUS  current
  DESCRIPTION "Anti-Virus Messages Scanned"
  ::= { gmsAV 3 }

avMessagesScannedLow OBJECT-TYPE
  SYNTAX  Counter32
  MAX-ACCESS  read-only
  STATUS  current
  DESCRIPTION "Anti-Virus Messages Scanned"
  ::= { gmsAV 4 }

avVirusesFound OBJECT-TYPE
  SYNTAX  Counter64
  MAX-ACCESS  read-only
  STATUS  current
  DESCRIPTION "Anti-Virus Viruses Found"
  ::= { gmsAV 5 }

avVirusesFoundLow OBJECT-TYPE
  SYNTAX  Counter32
  MAX-ACCESS  read-only
  STATUS  current
  DESCRIPTION "Anti-Virus Viruses Found"
  ::= { gmsAV 6 }

-- GMS Anti-Spam definitions 

asLastUpdate OBJECT-TYPE
  SYNTAX  DisplayString
  MAX-ACCESS  read-only
  STATUS  current
  DESCRIPTION "Date of last Anti-Spam update."
  ::= { gmsAS 1 }

asMessagesChecked OBJECT-TYPE
  SYNTAX  Counter64
  MAX-ACCESS  read-only
  STATUS  current
  DESCRIPTION "Anti-Spam Messages Checked"
  ::= { gmsAS 2 }

asMessagesCheckedLow OBJECT-TYPE
  SYNTAX  Counter32
  MAX-ACCESS  read-only
  STATUS  current
  DESCRIPTION "Anti-Spam Messages Checked"
  ::= { gmsAS 3 }

asMessagesRejected OBJECT-TYPE
  SYNTAX  Counter64
  MAX-ACCESS  read-only
  STATUS  current
  DESCRIPTION "Anti-Spam Messages Rejected"
  ::= { gmsAS 4 }

asMessagesRejectedLow OBJECT-TYPE
  SYNTAX  Counter32
  MAX-ACCESS  read-only
  STATUS  current
  DESCRIPTION "Anti-Spam Messages Rejected"
  ::= { gmsAS 5 }

-- GMS SMTP definitions 

smtpThreadsTotal OBJECT-TYPE
  SYNTAX  INTEGER
  MAX-ACCESS  read-only
  STATUS  current
  DESCRIPTION "Total number of worker threads."
  ::= { gmsSMTP 1 }

smtpThreadsActive OBJECT-TYPE
  SYNTAX  INTEGER
  MAX-ACCESS  read-only
  STATUS  current
  DESCRIPTION "Number of active worker threads."
  ::= { gmsSMTP 2 }

smtpSessions OBJECT-TYPE
  SYNTAX  INTEGER
  MAX-ACCESS  read-only
  STATUS  current
  DESCRIPTION "Number of SSL and non SSL sessions."
  ::= { gmsSMTP 3 }

smtpSSLSessions OBJECT-TYPE
  SYNTAX  INTEGER
  MAX-ACCESS  read-only
  STATUS  current
  DESCRIPTION "Number of SSL sessions."
  ::= { gmsSMTP 4 }

smtpOutOfThreads OBJECT-TYPE
  SYNTAX  INTEGER
  MAX-ACCESS  read-only
  STATUS  current
  DESCRIPTION "Number of times the server has been unable to service an inbound
               connection due to all the worker threads being in use."
  ::= { gmsSMTP 5 }

smtpSuccessfulAuthentications OBJECT-TYPE
  SYNTAX  Counter64
  MAX-ACCESS  read-only
  STATUS  current
  DESCRIPTION "Number of successful authentications. 64 bit."
  ::= { gmsSMTP 6 }

smtpSuccessfulAuthenticationsLow OBJECT-TYPE
  SYNTAX  Counter32
  MAX-ACCESS  read-only
  STATUS  current
  DESCRIPTION "Number of successful authentications. 32 bit."
  ::= { gmsSMTP 7 }
  
smtpFailedAuthentications OBJECT-TYPE
  SYNTAX  Counter64
  MAX-ACCESS  read-only
  STATUS  current
  DESCRIPTION "Number of failed authentications. 64 bit."
  ::= { gmsSMTP 8 }

smtpFailedAuthenticationsLow OBJECT-TYPE
  SYNTAX  Counter32
  MAX-ACCESS  read-only
  STATUS  current
  DESCRIPTION "Number of failed authentications. 32 bit."
  ::= { gmsSMTP 9 }

-- GMS POST definitions 

postThreadsTotal OBJECT-TYPE
  SYNTAX  INTEGER
  MAX-ACCESS  read-only
  STATUS  current
  DESCRIPTION "Total number of worker threads."
  ::= { gmsPOST 1 }

postThreadsActive OBJECT-TYPE
  SYNTAX  INTEGER
  MAX-ACCESS  read-only
  STATUS  current
  DESCRIPTION "Number of active worker threads."
  ::= { gmsPOST 2 }

postSessions OBJECT-TYPE
  SYNTAX  INTEGER
  MAX-ACCESS  read-only
  STATUS  current
  DESCRIPTION "Number of SSL and non SSL sessions."
  ::= { gmsPOST 3 }

postSSLSessions OBJECT-TYPE
  SYNTAX  INTEGER
  MAX-ACCESS  read-only
  STATUS  current
  DESCRIPTION "Number of SSL sessions."
  ::= { gmsPOST 4 }

postSuccessfulAuthentications OBJECT-TYPE
  SYNTAX  Counter64
  MAX-ACCESS  read-only
  STATUS  current
  DESCRIPTION "Number of successful authentications. 64 bit."
  ::= { gmsPOST 5 }

postSuccessfulAuthenticationsLow OBJECT-TYPE
  SYNTAX  Counter32
  MAX-ACCESS  read-only
  STATUS  current
  DESCRIPTION "Number of successful authentications. 32 bit."
  ::= { gmsPOST 6 }
  
postFailedAuthentications OBJECT-TYPE
  SYNTAX  Counter64
  MAX-ACCESS  read-only
  STATUS  current
  DESCRIPTION "Number of failed authentications. 64 bit."
  ::= { gmsPOST 7 }

postFailedAuthenticationsLow OBJECT-TYPE
  SYNTAX  Counter32
  MAX-ACCESS  read-only
  STATUS  current
  DESCRIPTION "Number of failed authentications. 32 bit."
  ::= { gmsPOST 8 }

postQueues OBJECT-TYPE
  SYNTAX  Gauge32
  MAX-ACCESS  read-only
  STATUS  current
  DESCRIPTION "Number of queues."
  ::= { gmsPOST 9 }

-- GMS POP definitions 

popThreadsTotal OBJECT-TYPE
  SYNTAX  INTEGER
  MAX-ACCESS  read-only
  STATUS  current
  DESCRIPTION "Total number of worker threads."
  ::= { gmsPOP 1 }

popThreadsActive OBJECT-TYPE
  SYNTAX  INTEGER
  MAX-ACCESS  read-only
  STATUS  current
  DESCRIPTION "Number of active worker threads."
  ::= { gmsPOP 2 }

popSessions OBJECT-TYPE
  SYNTAX  INTEGER
  MAX-ACCESS  read-only
  STATUS  current
  DESCRIPTION "Number of SSL and non SSL sessions."
  ::= { gmsPOP 3 }

popSSLSessions OBJECT-TYPE
  SYNTAX  INTEGER
  MAX-ACCESS  read-only
  STATUS  current
  DESCRIPTION "Number of SSL sessions."
  ::= { gmsPOP 4 }

popLoggedOnUsers OBJECT-TYPE
  SYNTAX  INTEGER
  MAX-ACCESS  read-only
  STATUS  current
  DESCRIPTION "Number of logged on users."
  ::= { gmsPOP 5 }

popOutOfThreads OBJECT-TYPE
  SYNTAX  INTEGER
  MAX-ACCESS  read-only
  STATUS  current
  DESCRIPTION "Number of times the server has been unable to service an inbound
               connection due to all the worker threads being in use."
  ::= { gmsPOP 6 }

popSuccessfulAuthentications OBJECT-TYPE
  SYNTAX  Counter64
  MAX-ACCESS  read-only
  STATUS  current
  DESCRIPTION "Number of successful authentications. 64 bit."
  ::= { gmsPOP 7 }

popSuccessfulAuthenticationsLow OBJECT-TYPE
  SYNTAX  Counter32
  MAX-ACCESS  read-only
  STATUS  current
  DESCRIPTION "Number of successful authentications. 32 bit."
  ::= { gmsPOP 8 }
  
popFailedAuthentications OBJECT-TYPE
  SYNTAX  Counter64
  MAX-ACCESS  read-only
  STATUS  current
  DESCRIPTION "Number of failed authentications. 64 bit."
  ::= { gmsPOP 9 }

popFailedAuthenticationsLow OBJECT-TYPE
  SYNTAX  Counter32
  MAX-ACCESS  read-only
  STATUS  current
  DESCRIPTION "Number of failed authentications. 32 bit."
  ::= { gmsPOP 10 }

popRetrievedVolume OBJECT-TYPE
  SYNTAX  Counter64
  MAX-ACCESS  read-only
  STATUS  current
  DESCRIPTION "Total number of message bytes send in response to a RETR command. 64 bit."
  ::= { gmsPOP 11 }

popRetrievedVolumeLow OBJECT-TYPE
  SYNTAX  Counter32
  MAX-ACCESS  read-only
  STATUS  current
  DESCRIPTION "Total number of message bytes send in response to a RETR command. 32 bit."
  ::= { gmsPOP 12 }

popToppedVolume OBJECT-TYPE
  SYNTAX  Counter64
  MAX-ACCESS  read-only
  STATUS  current
  DESCRIPTION "Total number of message bytes send in response to a TOP command. 64 bit."
  ::= { gmsPOP 13 }

popToppedVolumeLow OBJECT-TYPE
  SYNTAX  Counter32
  MAX-ACCESS  read-only
  STATUS  current
  DESCRIPTION "Total number of message bytes send in response to a TOP command. 32 bit."
  ::= { gmsPOP 14 }

popXmitVolume OBJECT-TYPE
  SYNTAX  Counter64
  MAX-ACCESS  read-only
  STATUS  current
  DESCRIPTION "Total number of message bytes received in response to an XMIT command. 64 bit."
  ::= { gmsPOP 15 }

popXmitVolumeLow OBJECT-TYPE
  SYNTAX  Counter32
  MAX-ACCESS  read-only
  STATUS  current
  DESCRIPTION "Total number of message bytes received in response to an XMIT command. 32 bit."
  ::= { gmsPOP 16 }
  
popDeletedMessages OBJECT-TYPE
  SYNTAX  Counter64
  MAX-ACCESS  read-only
  STATUS  current
  DESCRIPTION "Total number of deleted messages. 64 bit."
  ::= { gmsPOP 17 }

popDeletedMessagesLow OBJECT-TYPE
  SYNTAX  Counter32
  MAX-ACCESS  read-only
  STATUS  current
  DESCRIPTION "Total number of deleted messages. 32 bit."
  ::= { gmsPOP 18 }

popRetrievedMessages OBJECT-TYPE
  SYNTAX  Counter64
  MAX-ACCESS  read-only
  STATUS  current
  DESCRIPTION "Total number of retrieved messages. 64 bit."
  ::= { gmsPOP 19 }

popRetrievedMessagesLow OBJECT-TYPE
  SYNTAX  Counter32
  MAX-ACCESS  read-only
  STATUS  current
  DESCRIPTION "Total number of retrieved messages. 32 bit."
  ::= { gmsPOP 20 }

popToppedMessages OBJECT-TYPE
  SYNTAX  Counter64
  MAX-ACCESS  read-only
  STATUS  current
  DESCRIPTION "Total number of topped messages. 64 bit."
  ::= { gmsPOP 21 }

popToppedMessagesLow OBJECT-TYPE
  SYNTAX  Counter32
  MAX-ACCESS  read-only
  STATUS  current
  DESCRIPTION "Total number of topped messages. 32 bit."
  ::= { gmsPOP 22 }

popXmitedMessages OBJECT-TYPE
  SYNTAX  Counter64
  MAX-ACCESS  read-only
  STATUS  current
  DESCRIPTION "Total number of xmited messages. 64 bit."
  ::= { gmsPOP 23 }

popXmitedMessagesLow OBJECT-TYPE
  SYNTAX  Counter32
  MAX-ACCESS  read-only
  STATUS  current
  DESCRIPTION "Total number of xmited messages. 32 bit."
  ::= { gmsPOP 24 }

popLastInboundActivity OBJECT-TYPE
  SYNTAX  TimeInterval
  MAX-ACCESS  read-only
  STATUS  current
  DESCRIPTION "Time since the last time that this service had an
               inbound association."
  ::= { gmsPOP 25 }

-- GMS IMAP definitions 

imapThreadsTotal OBJECT-TYPE
  SYNTAX  INTEGER
  MAX-ACCESS  read-only
  STATUS  current
  DESCRIPTION "Total number of worker threads."
  ::= { gmsIMAP 1 }

imapThreadsActive OBJECT-TYPE
  SYNTAX  INTEGER
  MAX-ACCESS  read-only
  STATUS  current
  DESCRIPTION "Number of active worker threads."
  ::= { gmsIMAP 2 }

imapSessions OBJECT-TYPE
  SYNTAX  INTEGER
  MAX-ACCESS  read-only
  STATUS  current
  DESCRIPTION "Number of SSL and non SSL sessions."
  ::= { gmsIMAP 3 }

imapSSLSessions OBJECT-TYPE
  SYNTAX  INTEGER
  MAX-ACCESS  read-only
  STATUS  current
  DESCRIPTION "Number of SSL sessions."
  ::= { gmsIMAP 4 }

imapIdleSessions OBJECT-TYPE
  SYNTAX  INTEGER
  MAX-ACCESS  read-only
  STATUS  current
  DESCRIPTION "Number of idle sessions."
  ::= { gmsIMAP 5 }

imapLoggedOnUsers OBJECT-TYPE
  SYNTAX  INTEGER
  MAX-ACCESS  read-only
  STATUS  current
  DESCRIPTION "Number of logged on users."
  ::= { gmsIMAP 6 }

imapOutOfThreads OBJECT-TYPE
  SYNTAX  INTEGER
  MAX-ACCESS  read-only
  STATUS  current
  DESCRIPTION "Number of times the server has been unable to service an inbound
               connection due to all the worker threads being in use."
  ::= { gmsIMAP 7 }

imapSuccessfulAuthentications OBJECT-TYPE
  SYNTAX  Counter64
  MAX-ACCESS  read-only
  STATUS  current
  DESCRIPTION "Number of successful authentications. 64 bit."
  ::= { gmsIMAP 8 }

imapSuccessfulAuthenticationsLow OBJECT-TYPE
  SYNTAX  Counter32
  MAX-ACCESS  read-only
  STATUS  current
  DESCRIPTION "Number of successful authentications. 32 bit."
  ::= { gmsIMAP 9 }
  
imapFailedAuthentications OBJECT-TYPE
  SYNTAX  Counter64
  MAX-ACCESS  read-only
  STATUS  current
  DESCRIPTION "Number of failed authentications. 64 bit."
  ::= { gmsIMAP 10 }

imapFailedAuthenticationsLow OBJECT-TYPE
  SYNTAX  Counter32
  MAX-ACCESS  read-only
  STATUS  current
  DESCRIPTION "Number of failed authentications. 32 bit."
  ::= { gmsIMAP 11 }

imapDeletedMessages OBJECT-TYPE
  SYNTAX  Counter64
  MAX-ACCESS  read-only
  STATUS  current
  DESCRIPTION "Number of deleted messages. 64 bit."
  ::= { gmsIMAP 12 }

imapDeletedMessagesLow OBJECT-TYPE
  SYNTAX  Counter32
  MAX-ACCESS  read-only
  STATUS  current
  DESCRIPTION "Number of deleted messages. 32 bit."
  ::= { gmsIMAP 13 }

imapStoredMessages OBJECT-TYPE
  SYNTAX  Counter64
  MAX-ACCESS  read-only
  STATUS  current
  DESCRIPTION "Number of stored messages. 64 bit."
  ::= { gmsIMAP 14 }

imapStoredMessagesLow OBJECT-TYPE
  SYNTAX  Counter32
  MAX-ACCESS  read-only
  STATUS  current
  DESCRIPTION "Number of stored messages. 32 bit."
  ::= { gmsIMAP 15 }

imapAppendedMessages OBJECT-TYPE
  SYNTAX  Counter64
  MAX-ACCESS  read-only
  STATUS  current
  DESCRIPTION "Number of appended messages. 64 bit."
  ::= { gmsIMAP 16 }

imapAppendedMessagesLow OBJECT-TYPE
  SYNTAX  Counter32
  MAX-ACCESS  read-only
  STATUS  current
  DESCRIPTION "Number of appended messages. 32 bit."
  ::= { gmsIMAP 17 }

imapAppendedVolume OBJECT-TYPE
  SYNTAX  Counter64
  MAX-ACCESS  read-only
  STATUS  current
  DESCRIPTION "Total number of appended message bytes. 64 bit."
  ::= { gmsIMAP 18 }

imapAppendedVolumeLow OBJECT-TYPE
  SYNTAX  Counter32
  MAX-ACCESS  read-only
  STATUS  current
  DESCRIPTION "Total number of appended message bytes. 32 bit."
  ::= { gmsIMAP 19 }
  
imapFetchedMessages OBJECT-TYPE
  SYNTAX  Counter64
  MAX-ACCESS  read-only
  STATUS  current
  DESCRIPTION "Number of fetched messages. 64 bit."
  ::= { gmsIMAP 20 }

imapFetchedMessagesLow OBJECT-TYPE
  SYNTAX  Counter32
  MAX-ACCESS  read-only
  STATUS  current
  DESCRIPTION "Number of fetched messages. 32 bit."
  ::= { gmsIMAP 21 }

imapFetchedVolume OBJECT-TYPE
  SYNTAX  Counter64
  MAX-ACCESS  read-only
  STATUS  current
  DESCRIPTION "Total number of fetched message bytes. 64 bit."
  ::= { gmsIMAP 22 }

imapFetchedVolumeLow OBJECT-TYPE
  SYNTAX  Counter32
  MAX-ACCESS  read-only
  STATUS  current
  DESCRIPTION "Total number of fetched message bytes. 32 bit."
  ::= { gmsIMAP 23 }

imapCopiedMessages OBJECT-TYPE
  SYNTAX  Counter64
  MAX-ACCESS  read-only
  STATUS  current
  DESCRIPTION "Number of copied messages. 64 bit."
  ::= { gmsIMAP 24 }

imapCopiedMessagesLow OBJECT-TYPE
  SYNTAX  Counter32
  MAX-ACCESS  read-only
  STATUS  current
  DESCRIPTION "Number of copied messages. 32 bit."
  ::= { gmsIMAP 25 }

imapSearchedMessages OBJECT-TYPE
  SYNTAX  Counter64
  MAX-ACCESS  read-only
  STATUS  current
  DESCRIPTION "Number of searched messages. 64 bit."
  ::= { gmsIMAP 26 }

imapSearchedMessagesLow OBJECT-TYPE
  SYNTAX  Counter32
  MAX-ACCESS  read-only
  STATUS  current
  DESCRIPTION "Number of searched messages. 32 bit."
  ::= { gmsIMAP 27 }
  
imapLastInboundActivity OBJECT-TYPE
  SYNTAX  TimeInterval
  MAX-ACCESS  read-only
  STATUS  current
  DESCRIPTION "Time since the last time that this service had an
               inbound association."
  ::= { gmsIMAP 28 }

-- GMS WWW definitions 

wwwThreadsTotal OBJECT-TYPE
  SYNTAX  INTEGER
  MAX-ACCESS  read-only
  STATUS  current
  DESCRIPTION "Total number of worker threads."
  ::= { gmsWWW 1 }

wwwThreadsActive OBJECT-TYPE
  SYNTAX  INTEGER
  MAX-ACCESS  read-only
  STATUS  current
  DESCRIPTION "Number of active worker threads."
  ::= { gmsWWW 2 }

wwwSessions OBJECT-TYPE
  SYNTAX  INTEGER
  MAX-ACCESS  read-only
  STATUS  current
  DESCRIPTION "Number of SSL and non SSL sessions."
  ::= { gmsWWW 3 }

wwwProxySessions OBJECT-TYPE
  SYNTAX  INTEGER
  MAX-ACCESS  read-only
  STATUS  current
  DESCRIPTION "Number of proxy sessions."
  ::= { gmsWWW 4 }

wwwScriptSessions OBJECT-TYPE
  SYNTAX  INTEGER
  MAX-ACCESS  read-only
  STATUS  current
  DESCRIPTION "Number of script sessions."
  ::= { gmsWWW 5 }

wwwConnections OBJECT-TYPE
  SYNTAX  INTEGER
  MAX-ACCESS  read-only
  STATUS  current
  DESCRIPTION "Number of SSL and non-SSL connections."
  ::= { gmsWWW 6 }

wwwSSLConnections OBJECT-TYPE
  SYNTAX  INTEGER
  MAX-ACCESS  read-only
  STATUS  current
  DESCRIPTION "Number of SSL connections."
  ::= { gmsWWW 7 }

wwwProxyConnections OBJECT-TYPE
  SYNTAX  INTEGER
  MAX-ACCESS  read-only
  STATUS  current
  DESCRIPTION "Number of proxy SSL and non-SSL connections."
  ::= { gmsWWW 8 }

wwwProxySSLConnections OBJECT-TYPE
  SYNTAX  INTEGER
  MAX-ACCESS  read-only
  STATUS  current
  DESCRIPTION "Number of proxy SSL connections."
  ::= { gmsWWW 9 }

wwwScriptConnections OBJECT-TYPE
  SYNTAX  INTEGER
  MAX-ACCESS  read-only
  STATUS  current
  DESCRIPTION "Number of script connections."
  ::= { gmsWWW 10 }

wwwLoggedOnUsers OBJECT-TYPE
  SYNTAX  INTEGER
  MAX-ACCESS  read-only
  STATUS  current
  DESCRIPTION "Number of logged on users."
  ::= { gmsWWW 11 }

wwwOutOfThreads OBJECT-TYPE
  SYNTAX  INTEGER
  MAX-ACCESS  read-only
  STATUS  current
  DESCRIPTION "Number of times the server has been unable to service an inbound
               connection due to all the worker threads being in use."
  ::= { gmsWWW 12 }

wwwOutOfSessions OBJECT-TYPE
  SYNTAX  INTEGER
  MAX-ACCESS  read-only
  STATUS  current
  DESCRIPTION "Number of times the session limit has been reached."
  ::= { gmsWWW 13 }

wwwOutOfProxySessions OBJECT-TYPE
  SYNTAX  INTEGER
  MAX-ACCESS  read-only
  STATUS  current
  DESCRIPTION "Number of times the proxy session limit has been reached."
  ::= { gmsWWW 14 }

wwwSessionTimeouts OBJECT-TYPE
  SYNTAX  Counter64
  MAX-ACCESS  read-only
  STATUS  current
  DESCRIPTION "Number of session timeouts."
  ::= { gmsWWW 15 }

wwwSessionTimeoutsLow OBJECT-TYPE
  SYNTAX  Counter32
  MAX-ACCESS  read-only
  STATUS  current
  DESCRIPTION "Number of session timeouts."
  ::= { gmsWWW 16 }

wwwProxySessionTimeouts OBJECT-TYPE
  SYNTAX  Counter64
  MAX-ACCESS  read-only
  STATUS  current
  DESCRIPTION "Number of proxy session timeouts. 64 bit."
  ::= { gmsWWW 17 }

wwwProxySessionTimeoutsLow OBJECT-TYPE
  SYNTAX  Counter32
  MAX-ACCESS  read-only
  STATUS  current
  DESCRIPTION "Number of proxy session timeouts. 32 bit."
  ::= { gmsWWW 18 }

wwwScriptSessionTimeouts OBJECT-TYPE
  SYNTAX  Counter64
  MAX-ACCESS  read-only
  STATUS  current
  DESCRIPTION "Number of script session timeouts. 64 bit."
  ::= { gmsWWW 19 }

wwwScriptSessionTimeoutsLow OBJECT-TYPE
  SYNTAX  Counter32
  MAX-ACCESS  read-only
  STATUS  current
  DESCRIPTION "Number of script session timeouts. 32 bit."
  ::= { gmsWWW 20 }
  
wwwSuccessfulAuthentications OBJECT-TYPE
  SYNTAX  Counter64
  MAX-ACCESS  read-only
  STATUS  current
  DESCRIPTION "Number of successful authentications. 64 bit."
  ::= { gmsWWW 21 }

wwwSuccessfulAuthenticationsLow OBJECT-TYPE
  SYNTAX  Counter32
  MAX-ACCESS  read-only
  STATUS  current
  DESCRIPTION "Number of successful authentications. 32 bit."
  ::= { gmsWWW 22 }
  
wwwFailedAuthentications OBJECT-TYPE
  SYNTAX  Counter64
  MAX-ACCESS  read-only
  STATUS  current
  DESCRIPTION "Number of failed authentications. 64 bit."
  ::= { gmsWWW 23 }

wwwFailedAuthenticationsLow OBJECT-TYPE
  SYNTAX  Counter32
  MAX-ACCESS  read-only
  STATUS  current
  DESCRIPTION "Number of failed authentications. 32 bit."
  ::= { gmsWWW 24 }

wwwReceivedVolume OBJECT-TYPE
  SYNTAX  Counter64
  MAX-ACCESS  read-only
  STATUS  current
  DESCRIPTION "Number of received bytes. 64 bit."
  ::= { gmsWWW 25 }

wwwReceivedVolumeLow OBJECT-TYPE
  SYNTAX  Counter32
  MAX-ACCESS  read-only
  STATUS  current
  DESCRIPTION "Number of received bytes. 32 bit."
  ::= { gmsWWW 26 }

wwwTransmittedVolume OBJECT-TYPE
  SYNTAX  Counter64
  MAX-ACCESS  read-only
  STATUS  current
  DESCRIPTION "Number of transmitted bytes. 64 bit."
  ::= { gmsWWW 27 }

wwwTransmittedVolumeLow OBJECT-TYPE
  SYNTAX  Counter32
  MAX-ACCESS  read-only
  STATUS  current
  DESCRIPTION "Number of transmitted bytes. 32 bit."
  ::= { gmsWWW 28 }

wwwProxyReceivedVolume OBJECT-TYPE
  SYNTAX  Counter64
  MAX-ACCESS  read-only
  STATUS  current
  DESCRIPTION "Number of proxy received bytes. 64 bit."
  ::= { gmsWWW 29 }

wwwProxyReceivedVolumeLow OBJECT-TYPE
  SYNTAX  Counter32
  MAX-ACCESS  read-only
  STATUS  current
  DESCRIPTION "Number of proxy received bytes. 32 bit."
  ::= { gmsWWW 30 }

wwwProxyTransmittedVolume OBJECT-TYPE
  SYNTAX  Counter64
  MAX-ACCESS  read-only
  STATUS  current
  DESCRIPTION "Number of proxy transmitted bytes. 64 bit."
  ::= { gmsWWW 31 }

wwwProxyTransmittedVolumeLow OBJECT-TYPE
  SYNTAX  Counter32
  MAX-ACCESS  read-only
  STATUS  current
  DESCRIPTION "Number of proxy transmitted bytes. 32 bit."
  ::= { gmsWWW 32 }
  
wwwReverseProxyReceivedVolume OBJECT-TYPE
  SYNTAX  Counter64
  MAX-ACCESS  read-only
  STATUS  current
  DESCRIPTION "Number of reverse proxy received bytes. 64 bit."
  ::= { gmsWWW 33 }

wwwReverseProxyReceivedVolumeLow OBJECT-TYPE
  SYNTAX  Counter32
  MAX-ACCESS  read-only
  STATUS  current
  DESCRIPTION "Number of reverse proxy received bytes. 32 bit."
  ::= { gmsWWW 34}

wwwReverseProxyTransmittedVolume OBJECT-TYPE
  SYNTAX  Counter64
  MAX-ACCESS  read-only
  STATUS  current
  DESCRIPTION "Number of reverse proxy transmitted bytes. 64 bit."
  ::= { gmsWWW 35 }

wwwReverseProxyTransmittedVolumeLow OBJECT-TYPE
  SYNTAX  Counter32
  MAX-ACCESS  read-only
  STATUS  current
  DESCRIPTION "Number of reverse proxy transmitted bytes. 32 bit."
  ::= { gmsWWW 36 }

wwwSuccessfulRequests OBJECT-TYPE
  SYNTAX  Counter64
  MAX-ACCESS  read-only
  STATUS  current
  DESCRIPTION "Number of successful WWW requests. 64 bit."
  ::= { gmsWWW 37 }

wwwSuccessfulRequestsLow OBJECT-TYPE
  SYNTAX  Counter32
  MAX-ACCESS  read-only
  STATUS  current
  DESCRIPTION "Number of successful WWW requests. 32 bit."
  ::= { gmsWWW 38 }
  
wwwFailedRequests OBJECT-TYPE
  SYNTAX  Counter64
  MAX-ACCESS  read-only
  STATUS  current
  DESCRIPTION "Number of failed WWW requests. 64 bit."
  ::= { gmsWWW 39 }

wwwFailedRequestsLow OBJECT-TYPE
  SYNTAX  Counter32
  MAX-ACCESS  read-only
  STATUS  current
  DESCRIPTION "Number of failed WWW requests. 32 bit."
  ::= { gmsWWW 40 }

wwwSuccessfulAdminRequests OBJECT-TYPE
  SYNTAX  Counter64
  MAX-ACCESS  read-only
  STATUS  current
  DESCRIPTION "Number of successful admin requests. 64 bit."
  ::= { gmsWWW 41 }

wwwSuccessfulAdminRequestsLow OBJECT-TYPE
  SYNTAX  Counter32
  MAX-ACCESS  read-only
  STATUS  current
  DESCRIPTION "Number of successful admin requests. 32 bit."
  ::= { gmsWWW 42 }
  
wwwFailedAdminRequests OBJECT-TYPE
  SYNTAX  Counter64
  MAX-ACCESS  read-only
  STATUS  current
  DESCRIPTION "Number of failed admin requests. 64 bit."
  ::= { gmsWWW 43 }

wwwFailedAdminRequestsLow OBJECT-TYPE
  SYNTAX  Counter32
  MAX-ACCESS  read-only
  STATUS  current
  DESCRIPTION "Number of failed admin requests. 32 bit."
  ::= { gmsWWW 44 }
 
wwwSuccessfulWebmailRequests OBJECT-TYPE
  SYNTAX  Counter64
  MAX-ACCESS  read-only
  STATUS  current
  DESCRIPTION "Number of successful webmail requests. 64 bit."
  ::= { gmsWWW 45 }

wwwSuccessfulWebmailRequestsLow OBJECT-TYPE
  SYNTAX  Counter32
  MAX-ACCESS  read-only
  STATUS  current
  DESCRIPTION "Number of successful webmail requests. 32 bit."
  ::= { gmsWWW 46 }
  
wwwFailedWebmailRequests OBJECT-TYPE
  SYNTAX  Counter64
  MAX-ACCESS  read-only
  STATUS  current
  DESCRIPTION "Number of failed webmail requests. 64 bit."
  ::= { gmsWWW 47 }

wwwFailedWebmailRequestsLow OBJECT-TYPE
  SYNTAX  Counter32
  MAX-ACCESS  read-only
  STATUS  current
  DESCRIPTION "Number of failed webmail requests. 32 bit."
  ::= { gmsWWW 48 }

wwwSuccessfulUserRequests OBJECT-TYPE
  SYNTAX  Counter64
  MAX-ACCESS  read-only
  STATUS  current
  DESCRIPTION "Number of successful user requests. 64 bit."
  ::= { gmsWWW 49 }

wwwSuccessfulUserRequestsLow OBJECT-TYPE
  SYNTAX  Counter32
  MAX-ACCESS  read-only
  STATUS  current
  DESCRIPTION "Number of successful user requests. 32 bit."
  ::= { gmsWWW 50 }
  
wwwFailedUserRequests OBJECT-TYPE
  SYNTAX  Counter64
  MAX-ACCESS  read-only
  STATUS  current
  DESCRIPTION "Number of failed user requests. 64 bit."
  ::= { gmsWWW 51 }

wwwFailedUserRequestsLow OBJECT-TYPE
  SYNTAX  Counter32
  MAX-ACCESS  read-only
  STATUS  current
  DESCRIPTION "Number of failed user requests. 32 bit."
  ::= { gmsWWW 52 }

wwwSuccessfulProxyRequests OBJECT-TYPE
  SYNTAX  Counter64
  MAX-ACCESS  read-only
  STATUS  current
  DESCRIPTION "Number of successful proxy requests. 64 bit."
  ::= { gmsWWW 53 }

wwwSuccessfulProxyRequestsLow OBJECT-TYPE
  SYNTAX  Counter32
  MAX-ACCESS  read-only
  STATUS  current
  DESCRIPTION "Number of successful proxy requests. 32 bit."
  ::= { gmsWWW 54 }
  
wwwFailedProxyRequests OBJECT-TYPE
  SYNTAX  Counter64
  MAX-ACCESS  read-only
  STATUS  current
  DESCRIPTION "Number of failed proxy requests. 64 bit."
  ::= { gmsWWW 55 }

wwwFailedProxyRequestsLow OBJECT-TYPE
  SYNTAX  Counter32
  MAX-ACCESS  read-only
  STATUS  current
  DESCRIPTION "Number of failed proxy requests. 32 bit."
  ::= { gmsWWW 56 }

wwwSuccessfulReverseProxyRequests OBJECT-TYPE
  SYNTAX  Counter64
  MAX-ACCESS  read-only
  STATUS  current
  DESCRIPTION "Number of successful reverse proxy requests. 64 bit."
  ::= { gmsWWW 57 }

wwwSuccessfulReverseProxyRequestsLow OBJECT-TYPE
  SYNTAX  Counter32
  MAX-ACCESS  read-only
  STATUS  current
  DESCRIPTION "Number of successful reverse proxy requests. 32 bit."
  ::= { gmsWWW 58 }
  
wwwFailedReverseProxyRequests OBJECT-TYPE
  SYNTAX  Counter64
  MAX-ACCESS  read-only
  STATUS  current
  DESCRIPTION "Number of failed reverse proxy requests. 64 bit."
  ::= { gmsWWW 59 }

wwwFailedReverseProxyRequestsLow OBJECT-TYPE
  SYNTAX  Counter32
  MAX-ACCESS  read-only
  STATUS  current
  DESCRIPTION "Number of failed reverse proxy requests. 32 bit."
  ::= { gmsWWW 60 }

wwwSuccessfulScriptRequests OBJECT-TYPE
  SYNTAX  Counter64
  MAX-ACCESS  read-only
  STATUS  current
  DESCRIPTION "Number of successful script requests. 64 bit."
  ::= { gmsWWW 61 }

wwwSuccessfulScriptRequestsLow OBJECT-TYPE
  SYNTAX  Counter32
  MAX-ACCESS  read-only
  STATUS  current
  DESCRIPTION "Number of successful script requests. 32 bit."
  ::= { gmsWWW 62 }
  
wwwFailedScriptRequests OBJECT-TYPE
  SYNTAX  Counter64
  MAX-ACCESS  read-only
  STATUS  current
  DESCRIPTION "Number of failed script requests. 64 bit."
  ::= { gmsWWW 63 }

wwwFailedScriptRequestsLow OBJECT-TYPE
  SYNTAX  Counter32
  MAX-ACCESS  read-only
  STATUS  current
  DESCRIPTION "Number of failed script requests. 32 bit."
  ::= { gmsWWW 64 }

wwwSuccessfulTimedRequests OBJECT-TYPE
  SYNTAX  Counter64
  MAX-ACCESS  read-only
  STATUS  current
  DESCRIPTION "Number of successful timed requests. 64 bit."
  ::= { gmsWWW 65 }

wwwSuccessfulTimedRequestsLow OBJECT-TYPE
  SYNTAX  Counter32
  MAX-ACCESS  read-only
  STATUS  current
  DESCRIPTION "Number of successful timed requests. 32 bit."
  ::= { gmsWWW 66 }
  
wwwFailedTimedRequests OBJECT-TYPE
  SYNTAX  Counter64
  MAX-ACCESS  read-only
  STATUS  current
  DESCRIPTION "Number of failed timed requests. 64 bit."
  ::= { gmsWWW 67 }

wwwFailedTimedRequestsLow OBJECT-TYPE
  SYNTAX  Counter32
  MAX-ACCESS  read-only
  STATUS  current
  DESCRIPTION "Number of failed timed requests. 32 bit."
  ::= { gmsWWW 68 }

wwwMMLErrors OBJECT-TYPE
  SYNTAX  INTEGER
  MAX-ACCESS  read-only
  STATUS  current
  DESCRIPTION "Number of MML errors."
  ::= { gmsWWW 69 }

wwwMessagesRead OBJECT-TYPE
  SYNTAX  INTEGER
  MAX-ACCESS  read-only
  STATUS  current
  DESCRIPTION "Number of read messages."
  ::= { gmsWWW 70 }

wwwMessagesSent OBJECT-TYPE
  SYNTAX  INTEGER
  MAX-ACCESS  read-only
  STATUS  current
  DESCRIPTION "Number of sent messages."
  ::= { gmsWWW 71 }

wwwLastInboundActivity OBJECT-TYPE
  SYNTAX  TimeInterval
  MAX-ACCESS  read-only
  STATUS  current
  DESCRIPTION "Time since the last time that this service had an
               inbound association."
  ::= { gmsWWW 72 }

wwwLastOutboundActivity OBJECT-TYPE
  SYNTAX  TimeInterval
  MAX-ACCESS  read-only
  STATUS  current
  DESCRIPTION "Time since the last time that this service made an
               outbound association."
  ::= { gmsWWW 73 }

END
