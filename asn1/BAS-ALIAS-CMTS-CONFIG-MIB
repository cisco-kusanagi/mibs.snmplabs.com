BAS-ALIAS-CMTS-CONFIG-MIB DEFINITIONS ::= BEGIN

IMPORTS
	MODULE-IDENTITY, OBJECT-TYPE, 
	Integer32						FROM SNMPv2-SMI

	TEXTUAL-CONVENTION,
	MacAddress,
	TruthValue						FROM SNMPv2-TC

	ifIndex							FROM IF-MIB

	docsIfCmtsModulationEntry,
	docsIfDownstreamChannelEntry,
	docsIfUpstreamChannelEntry		FROM DOCS-IF-MIB

	basAliasCmtsCfg, BasChassisId,
	BasSlotId, BasInterfaceId,
	BasLogicalPortId				FROM BAS-MIB;


basAliasCmtsCfgMib MODULE-IDENTITY
	LAST-UPDATED "9810081200Z"
	ORGANIZATION "Broadband Access Systems"
	CONTACT-INFO
		" Tech Support
		  Broadband Access Systems
		  201 Forest Street
		  Marlboro, MA  01752
		  U.S.A.
		  
		  508-485-8200
		  support@basystems.com"
	DESCRIPTION
		"This MIB module defines the Alias CmtsCfg MIB objects
		 for a Broadband Access System Cluster."
	::= { basAliasCmtsCfg 1 }


   basCmtsCfgObjects OBJECT IDENTIFIER ::= { basAliasCmtsCfgMib 1 }
   basAlsCmtsMacToSidObjects  OBJECT IDENTIFIER ::= { basAliasCmtsCfgMib 2 }
 
   BasCmtsInt8 ::= TEXTUAL-CONVENTION
       DISPLAY-HINT "d"
       STATUS      current
       DESCRIPTION
           "Range of INTEGER(-127..128)."
       SYNTAX      Integer32 (-127..128)

   BasCmtsUInt8 ::= TEXTUAL-CONVENTION
       DISPLAY-HINT "d"
       STATUS      current
       DESCRIPTION
           "Range of INTEGER(0..255)."
       SYNTAX      Integer32 (0..255)

   BasCmtsByte ::= TEXTUAL-CONVENTION
       DISPLAY-HINT "d"
       STATUS      current
       DESCRIPTION
           "Range of INTEGER(0..255)."
       SYNTAX      BasCmtsUInt8

   BasCmtsInt16 ::= TEXTUAL-CONVENTION
       DISPLAY-HINT "d"
       STATUS      current
       DESCRIPTION
           "Range of INTEGER(-32768..32767)."
       SYNTAX      Integer32 (-32768..32767)

   BasCmtsUInt16 ::= TEXTUAL-CONVENTION
       DISPLAY-HINT "d"
       STATUS      current
       DESCRIPTION
           "Range of INTEGER(0..0x7fff)."
       SYNTAX      Integer32 (0..'ffff'h)

   BasCmtsInt32 ::= TEXTUAL-CONVENTION
       DISPLAY-HINT "d"
       STATUS      current
       DESCRIPTION
           "Range of Integer32"
       SYNTAX      Integer32 

   BasCmtsUInt32 ::= TEXTUAL-CONVENTION
       DISPLAY-HINT "d"
       STATUS      current
       DESCRIPTION
           "Range of INTEGER(0..0x7fffffff)."
       SYNTAX      Integer32 (0..'7fffffff'h)

   BasCmtsRowAction ::= TEXTUAL-CONVENTION
       DISPLAY-HINT "d"
       STATUS      current
       DESCRIPTION
           "Defines Bas Cmts row action."
       SYNTAX      INTEGER {
           basCmtsRowActionNone(1),
           basCmtsRowActionApply(2)
        }

   --
   -- ----------------------------------------------------------------------
   --
   -- Bas HeadEndMgr Configuration Object
   --
   -- ----------------------------------------------------------------------
   --

   BasCmtsHeadEndMapMode ::= TEXTUAL-CONVENTION
       DISPLAY-HINT "d"
       STATUS      current
       DESCRIPTION
           "HeadEndMgr map mode.  
              0  = Normal, free running maps.
              99 = Scripted maps for test and debug."
       SYNTAX      Integer32 (0 | 99)

   BasCmtsHeadEndMacAddr ::= TEXTUAL-CONVENTION
       DISPLAY-HINT "d"
       STATUS      current
       DESCRIPTION
           "HeadEndMgr MacAddress."
       SYNTAX      OCTET STRING (SIZE(0..5))

   BasCmtsHeadEndAuthString ::= TEXTUAL-CONVENTION
       DISPLAY-HINT "d"
       STATUS      current
       DESCRIPTION
           "HeadEndMgr Authorization String."
       SYNTAX      OCTET STRING (SIZE(0..255))





   --
   -- ----------------------------------------------------------------------
   --
   -- Bas Upstream Channel Settings
   --
   -- ----------------------------------------------------------------------
   --

   BasCmtsUpChannelPreamblePattern ::= TEXTUAL-CONVENTION
       DISPLAY-HINT "d"
       STATUS      current
       DESCRIPTION
           "Bas Upstream Channel Preamble Pattern."
       SYNTAX      OCTET STRING (SIZE(0..127))



   --
   -- ----------------------------------------------------------------------
   --
   -- Bas Upstream Channel Burst Descriptor
   --
   -- ----------------------------------------------------------------------
   --

   BasCmtsModulationWsPattern ::= TEXTUAL-CONVENTION
       DISPLAY-HINT "d"
       STATUS      current
       DESCRIPTION
           "Bas upstream channel burst descriptor unique word pattern."
       SYNTAX      OCTET STRING (SIZE(0..127))


basCmtsPLLTable OBJECT-TYPE
        SYNTAX      SEQUENCE OF BasCmtsPLLEntry
        MAX-ACCESS  not-accessible
        STATUS      current
        DESCRIPTION
            "Provides ways to set the Phase Lock Loop on the CMTS."
        ::= { basCmtsCfgObjects 2 }

basCmtsPLLEntry OBJECT-TYPE
        SYNTAX      BasCmtsPLLEntry
        MAX-ACCESS  not-accessible
        STATUS      current
        DESCRIPTION
            ""

        INDEX { 
				basCmtsPLLChassis,
				basCmtsPLLSlot,
				basCmtsPLLIf,
				basCmtsPLLLPort
			  }
        ::= { basCmtsPLLTable 1 }

BasCmtsPLLEntry ::= SEQUENCE {
			basCmtsPLLChassis		BasChassisId,
			basCmtsPLLSlot			BasSlotId,
			basCmtsPLLIf			BasInterfaceId,
			basCmtsPLLLPort			BasLogicalPortId,
                        basCmtsPLLState			INTEGER,
			basCmtsPLLValue			BasCmtsInt32			
			
        }

basCmtsPLLChassis OBJECT-TYPE
	SYNTAX		BasChassisId
	MAX-ACCESS	not-accessible
	STATUS		current
	DESCRIPTION
		"The BAS Chassis ID of this card."
	::= { basCmtsPLLEntry 1 }

basCmtsPLLSlot OBJECT-TYPE
	SYNTAX		BasSlotId
	MAX-ACCESS	not-accessible
	STATUS		current
	DESCRIPTION
		"The BAS Slot ID of this card."
	::= { basCmtsPLLEntry 2 }

basCmtsPLLIf OBJECT-TYPE
	SYNTAX		BasInterfaceId
	MAX-ACCESS	not-accessible
	STATUS		current
	DESCRIPTION
		"The BAS interface ID of this card."
	::= { basCmtsPLLEntry 3 }

basCmtsPLLLPort OBJECT-TYPE
	SYNTAX		BasLogicalPortId
	MAX-ACCESS	not-accessible
	STATUS		current
	DESCRIPTION
		"The BAS logical port ID of this card."
	::= { basCmtsPLLEntry 4 }

basCmtsPLLState OBJECT-TYPE
        SYNTAX      INTEGER {
            normal(1),
            pllSet(2)
        }
        MAX-ACCESS  read-write
        STATUS      current
        DESCRIPTION
            "This object triggers the CMTS PLL."
        ::= { basCmtsPLLEntry 5 }

basCmtsPLLValue OBJECT-TYPE
        SYNTAX      BasCmtsInt32
        MAX-ACCESS  read-only
        STATUS      current
        DESCRIPTION
            "This object specifies the current CMTS PLL value."
        ::= { basCmtsPLLEntry 6 }


   -- ----------------------------------------------------------------------
   --
   -- Bas Alias CMTS MAC To SID Objects
   --
   -- ----------------------------------------------------------------------
   --

   basAlsCmtsMacToSidTable OBJECT-TYPE
       SYNTAX      SEQUENCE OF BasAlsCmtsMacToSidEntry
       MAX-ACCESS  not-accessible
       STATUS      current
       DESCRIPTION
               "A list of BAS cmts mac to sid objects. "
       ::= { basAlsCmtsMacToSidObjects 1 }

   basAlsCmtsMacToSidEntry OBJECT-TYPE
       SYNTAX      BasAlsCmtsMacToSidEntry
       MAX-ACCESS  not-accessible
       STATUS      current
       DESCRIPTION
               "An entry containing BAS CMTS MAC to SID settings."
       INDEX   { basAlsCmtsMacToSidChassis,
		 basAlsCmtsMacToSidSlot,
		 basAlsCmtsMacToSidIf,
		 basAlsCmtsMacToSidLPort,
		 basAlsCmtsMacToSidMacAddr }
       ::= {  basAlsCmtsMacToSidTable 1 }

   BasAlsCmtsMacToSidEntry ::=
       SEQUENCE {
           basAlsCmtsMacToSidMacAddr  MacAddress,
           basAlsCmtsMacToSidServiceId Integer32,
           basAlsCmtsMacToSidType INTEGER,
	   basAlsCmtsMacToSidChassis  BasChassisId,
	   basAlsCmtsMacToSidSlot  BasSlotId,
	   basAlsCmtsMacToSidIf	 BasInterfaceId,
	   basAlsCmtsMacToSidLPort  BasLogicalPortId
        }

   basAlsCmtsMacToSidMacAddr OBJECT-TYPE
       SYNTAX      MacAddress
       MAX-ACCESS  read-only
       STATUS      current
       DESCRIPTION
               "The MAC address of the host or the cable modem"
       ::= { basAlsCmtsMacToSidEntry 1 }

   basAlsCmtsMacToSidServiceId OBJECT-TYPE
       SYNTAX      Integer32
       MAX-ACCESS  read-only
       STATUS      current
       DESCRIPTION
               "The SID of the host or the cable modem derived from
                the MAC"
       ::= { basAlsCmtsMacToSidEntry 2 }


   basAlsCmtsMacToSidType OBJECT-TYPE
       SYNTAX      INTEGER {
			      none (1),
			      cableModem(2),
			      host (3)
		      }
       MAX-ACCESS  read-only
       STATUS      current
       DESCRIPTION
               "Type of device attached to this SID"
       DEFVAL { none }
       ::= { basAlsCmtsMacToSidEntry 3 }

   basAlsCmtsMacToSidChassis OBJECT-TYPE
	SYNTAX		BasChassisId
	MAX-ACCESS	not-accessible
	STATUS		current
	DESCRIPTION
		"The BAS Chassis ID of this card."
	::= { basAlsCmtsMacToSidEntry 4 }

   basAlsCmtsMacToSidSlot OBJECT-TYPE
	SYNTAX		BasSlotId
	MAX-ACCESS	not-accessible
	STATUS		current
	DESCRIPTION
		"The BAS Slot ID of this card."
	::= { basAlsCmtsMacToSidEntry 5 }

   basAlsCmtsMacToSidIf OBJECT-TYPE
	SYNTAX		BasInterfaceId
	MAX-ACCESS	not-accessible
	STATUS		current
	DESCRIPTION
		"The BAS interface ID of this card."
	::= { basAlsCmtsMacToSidEntry 6 }

   basAlsCmtsMacToSidLPort OBJECT-TYPE
	SYNTAX		BasLogicalPortId
	MAX-ACCESS	not-accessible
	STATUS		current
	DESCRIPTION
		"The BAS logical port ID of this card."
	::= { basAlsCmtsMacToSidEntry 7 }

   --
   -- ----------------------------------------------------------------------
   --
   -- End
   --
   -- ----------------------------------------------------------------------
   --

   END
