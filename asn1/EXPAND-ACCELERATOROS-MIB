--
-- EXPAND-ACCELERATOROS-MIB.my
-- MIB generated by MG-SOFT Visual MIB Builder Version 3.0 Build 253
-- Sunday, August 18, 2002 at 20:08:28
--

-- 
-- Expand Networks. 
-- Product Line MIB Version 1.0.8

	EXPAND-ACCELERATOROS-MIB DEFINITIONS ::= BEGIN
 
		IMPORTS
			acceleratorOs			
				FROM EXPAND-NETWORKS-SMI			
			OBJECT-TYPE			
				FROM RFC-1212			
			TimeTicks, IpAddress, Counter, Gauge			
				FROM RFC1155-SMI;
	
	
--
-- Node definitions
--
	
		-- 1.1
		accProductId OBJECT-TYPE
			SYNTAX OBJECT IDENTIFIER
			ACCESS read-only
			STATUS mandatory
			DESCRIPTION
				"This object identifier defines the object identifiers that
				are assigned to the various Expand-Networks products,
				and hence is assign to the outgoing traps."
			::= { acceleratorOs 1 }
		
		-- 1.2
		accSystem OBJECT IDENTIFIER ::= { acceleratorOs 2 }
		
		-- 1.2.1
		accSysUpTime OBJECT-TYPE
			SYNTAX TimeTicks
			ACCESS read-only
			STATUS mandatory
			DESCRIPTION
				"The time (in hundredths of a second) since the
				network management portion of the system was last
				re-initialized. 
				The value is the same as in sysUpTime leaf in MIB 2."
			::= { accSystem 1 }
		
		-- 1.2.2
		accSoftwareVersion OBJECT-TYPE
			SYNTAX OCTET STRING
			ACCESS read-only
			STATUS mandatory
			DESCRIPTION
				"Product software version."
			::= { accSystem 2 }
		
		-- 1.2.3
		accSysHostName OBJECT-TYPE
			SYNTAX OCTET STRING
			ACCESS read-only
			STATUS mandatory
			DESCRIPTION
				"An administratively-assigned name for this managed node,
				the value is the same as in sysName leaf in MIB 2."
			::= { accSystem 3 }
		
		-- 1.2.4
		accSysLocation OBJECT-TYPE
			SYNTAX OCTET STRING
			ACCESS read-only
			STATUS mandatory
			DESCRIPTION
				"The physical location of this node, the value is the 
				same as in sysLocation leaf in MIB 2."
			::= { accSystem 4 }
		
		-- 1.2.5
		accSysContact OBJECT-TYPE
			SYNTAX OCTET STRING
			ACCESS read-only
			STATUS mandatory
			DESCRIPTION
				"The textual identification of the contact person
				for this managed node, together with information
				on how to contact this person.
				The value is the same as in sysContact leaf in MIB 2.
				"
			::= { accSystem 5 }
		
		-- 1.2.6
		accSerialNumber OBJECT-TYPE
			SYNTAX OCTET STRING
			ACCESS read-only
			STATUS mandatory
			DESCRIPTION
				"ACCELERATOR serial number."
			::= { accSystem 6 }
		
		-- 1.3
		accPerformance OBJECT IDENTIFIER ::= { acceleratorOs 3 }
		
		-- 1.3.1
		accHardware OBJECT IDENTIFIER ::= { accPerformance 1 }
		
		-- 1.3.1.1
		accCpu OBJECT IDENTIFIER ::= { accHardware 1 }
		
		-- 1.3.1.1.1
		accCpuTotalEntries OBJECT-TYPE
			SYNTAX INTEGER
			ACCESS read-only
			STATUS mandatory
			DESCRIPTION
				"The number of Central Processing Units present
				on this system."
			::= { accCpu 1 }
		
		-- 1.3.1.1.2
		accCpuTable OBJECT-TYPE
			SYNTAX SEQUENCE OF AccCpuEntry
			ACCESS not-accessible
			STATUS mandatory
			DESCRIPTION
				"A list of cpu entries.  The number of entries
				is given by the value of cpuTotalEntries."
			::= { accCpu 2 }
		
		-- 1.3.1.1.2.1
		accCpuEntry OBJECT-TYPE
			SYNTAX AccCpuEntry
			ACCESS not-accessible
			STATUS mandatory
			DESCRIPTION
				"A cpu entry containing objects for a particular cpu."
			INDEX { accCpuIndex }
			::= { accCpuTable 1 }
		
		AccCpuEntry ::=
			SEQUENCE { 
				accCpuIndex
					INTEGER,
				accCpuDesc
					OCTET STRING,
				accCpuUtilization
					INTEGER
			 }

		-- 1.3.1.1.2.1.1
		accCpuIndex OBJECT-TYPE
			SYNTAX INTEGER
			ACCESS read-only
			STATUS mandatory
			DESCRIPTION
				"A unique value for each cpu."
			::= { accCpuEntry 1 }
		
		-- 1.3.1.1.2.1.2
		accCpuDesc OBJECT-TYPE
			SYNTAX OCTET STRING
			ACCESS read-only
			STATUS mandatory
			DESCRIPTION
				"A textual string containing information about the
				cpu."
			::= { accCpuEntry 2 }
		
		-- 1.3.1.1.2.1.3
		accCpuUtilization OBJECT-TYPE
			SYNTAX INTEGER (0..100)
			ACCESS read-only
			STATUS mandatory
			DESCRIPTION
				"Utilization per cpu in percentage.
				"
			::= { accCpuEntry 3 }
		
		-- 1.3.2
		accSoftware OBJECT IDENTIFIER ::= { accPerformance 2 }
		
		-- 1.3.2.1
		accBuffer OBJECT IDENTIFIER ::= { accSoftware 1 }
		
		-- 1.3.2.1.1
		accSystemWide OBJECT-TYPE
			SYNTAX INTEGER (0..100)
			ACCESS read-only
			STATUS mandatory
			DESCRIPTION
				"Buffer utilization system-wide in percentage. "
			::= { accBuffer 1 }
		
		-- 1.4
		accInterfaces OBJECT IDENTIFIER ::= { acceleratorOs 4 }
		
		-- 1.4.1
		accInterfaceTotalEntries OBJECT-TYPE
			SYNTAX INTEGER
			ACCESS read-only
			STATUS mandatory
			DESCRIPTION
				"The number of network interfaces and sub-interfaces
				present on this system."
			::= { accInterfaces 1 }
		
		-- 1.4.2
		accInterfaceTable OBJECT-TYPE
			SYNTAX SEQUENCE OF AccInterfaceEntry
			ACCESS not-accessible
			STATUS mandatory
			DESCRIPTION
				"A list of interface entries.  The number of entries
				is given by the value of interfaceTotalEntries."
			::= { accInterfaces 2 }
		
		-- 1.4.2.1
		accInterfaceEntry OBJECT-TYPE
			SYNTAX AccInterfaceEntry
			ACCESS not-accessible
			STATUS mandatory
			DESCRIPTION
				"An interface entry containing objects at the subnetwork
				layer and below for a particular interface or sub-interface."
			INDEX { accInterfaceIndex }
			::= { accInterfaceTable 1 }
		
		AccInterfaceEntry ::=
			SEQUENCE { 
				accInterfaceIndex
					INTEGER,
				accInterfaceDescription
					OCTET STRING,
				accInterfaceEncapsulation
					INTEGER,
				accInterfaceFrameRelayDlci
					INTEGER,
				accInterfaceType
					INTEGER,
				accInterfaceOperStatus
					INTEGER,
				accInterfaceAdminStatus
					INTEGER,
				accInterfaceMtu
					INTEGER,
				accInterfaceSpeed
					Gauge,
				accInterfaceOutQlength
					Gauge,
				accInterfaceBufferUtil
					INTEGER,
				accInterfaceAccelerationAdminStatus
					INTEGER,
				accInterfaceQueuingStrategy
					INTEGER,
				accInterfaceIpAddress
					IpAddress,
				accInterfaceIpMask
					IpAddress,
				accInterfaceChunkSizeMethod
					INTEGER,
				accInterfaceChunkSize
					INTEGER,
				accInterfaceDrcMode
					INTEGER,
				accInterfaceKeepAliveInterval
					INTEGER,
				accInterfaceKeepAliveIterations
					INTEGER,
				accInterfaceProbe
					INTEGER,
				accInterfaceInboundStatus
					INTEGER,
				accInterfaceInboundCore
					INTEGER,
				accInterfaceOutboundStatus
					INTEGER,
				accInterfaceOutboundCore
					INTEGER,
				accInterfaceTransmitDirection
					INTEGER,
				accInterfacePerformancePeriod
					INTEGER,
				accInterfacePerformanceInAccelerationUp
					Gauge,
				accInterfacePerformanceInAccelerationClear
					Gauge,
				accInterfacePerformanceInAccelerationPeriod
					Gauge,
				accInterfacePerformanceOutAccelerationUp
					Gauge,
				accInterfacePerformanceOutAccelerationClear
					Gauge,
				accInterfacePerformanceOutAccelerationPeriod
					Gauge,
				accInterfacePerformanceDrcResetsUp
					Counter,
				accInterfacePerformanceDrcResetsClear
					Gauge,
				accInterfacePerformanceDrcResetsPeriod
					Gauge,
				accInterfacePerformanceLostPacketsUp
					Counter,
				accInterfacePerformanceLostPacketsClear
					Gauge,
				accInterfacePerformanceLostPacketsPeriod
					Gauge,
				accInterfacePerformanceRetransmitPacketsUp
					Counter,
				accInterfacePerformanceRetransmitPacketsClear
					Gauge,
				accInterfacePerformanceRetransmitPacketsPeriod
					Gauge,
				accInterfacePerformanceRecoveredPacketsUp
					Counter,
				accInterfacePerformanceRecoveredPacketsClear
					Gauge,
				accInterfacePerformanceRecoveredPacketsPeriod
					Gauge,
				accInterfaceThroughputPeriod
					INTEGER,
				accInterfaceThroughputCrcErrUp
					Counter,
				accInterfaceThroughputCrcErrClear
					Gauge,
				accInterfaceThroughputCrcErrPeriod
					Gauge,
				accInterfaceThroughputDropByteUp
					Counter,
				accInterfaceThroughputDropByteClear
					Gauge,
				accInterfaceThroughputDropBytePeriod
					Gauge,
				accInterfaceThroughputDropPacketsUp
					Counter,
				accInterfaceThroughputDropPacketsClear
					Gauge,
				accInterfaceThroughputDropPacketsPeriod
					Gauge,
				accInterfaceThroughputInBytesUp
					Counter,
				accInterfaceThroughputInBytesClear
					Gauge,
				accInterfaceThroughputInBytesPeriod
					Gauge,
				accInterfaceThroughputInPacketsUp
					Counter,
				accInterfaceThroughputInPacketsClear
					Gauge,
				accInterfaceThroughputInPacketsPeriod
					Gauge,
				accInterfaceThroughputOutBytesUp
					Counter,
				accInterfaceThroughputOutBytesClear
					Gauge,
				accInterfaceThroughputOutBytesPeriod
					Gauge,
				accInterfaceThroughputOutPacketsUp
					Counter,
				accInterfaceThroughputOutPacketsClear
					Gauge,
				accInterfaceThroughputOutPacketsPeriod
					Gauge,
				accInterfaceThroughputRawInBytesUp
					Counter,
				accInterfaceThroughputRawInBytesClear
					Gauge,
				accInterfaceThroughputRawInBytesPeriod
					Gauge,
				accInterfaceThroughputRawOutBytesUp
					Counter,
				accInterfaceThroughputRawOutBytesClear
					Gauge,
				accInterfaceThroughputRawOutBytesPeriod
					Gauge
			 }

		-- 1.4.2.1.1
		accInterfaceIndex OBJECT-TYPE
			SYNTAX INTEGER
			ACCESS read-only
			STATUS mandatory
			DESCRIPTION
				"A unique value for each interface or sub interface.
				"
			::= { accInterfaceEntry 1 }
		
		-- 1.4.2.1.2
		accInterfaceDescription OBJECT-TYPE
			SYNTAX OCTET STRING
			ACCESS read-only
			STATUS mandatory
			DESCRIPTION
				"A textual string containing information about the
				interface.  This string should include the name of
				the manufacturer, the product name and the version
				of the hardware interface."
			::= { accInterfaceEntry 2 }
		
		-- 1.4.2.1.3
		accInterfaceEncapsulation OBJECT-TYPE
			SYNTAX INTEGER
				{
				other(1),
				ppp(2),
				hdlc-cisco(3),
				frame-relay-ietf(4),
				frame-relay-cisco(5),
				lapb-8(6),
				lapb-128(7),
				ethernet(8),
				expand-special(9),
				raw-hdlc(10)
				}
			ACCESS read-only
			STATUS mandatory
			DESCRIPTION
				"The type of interface, distinguished according to
				the network layer.
				"
			::= { accInterfaceEntry 3 }
		
		-- 1.4.2.1.4
		accInterfaceFrameRelayDlci OBJECT-TYPE
			SYNTAX INTEGER
			ACCESS read-only
			STATUS mandatory
			::= { accInterfaceEntry 4 }
		
		-- 1.4.2.1.6
		accInterfaceType OBJECT-TYPE
			SYNTAX INTEGER
				{
				none(1),
				rs-232(2),
				rs-422(3),
				rs-449(4),
				rs-530(5),
				v-35(6),
				x-21(7),
				e1(8),
				t1(9),
				cable(10)
				}
			ACCESS read-only
			STATUS mandatory
			DESCRIPTION
				"The type of interface, distinguished according to the
				physical connection."
			::= { accInterfaceEntry 6 }
		
		-- 1.4.2.1.7
		accInterfaceOperStatus OBJECT-TYPE
			SYNTAX INTEGER
				{
				up(1),
				down(2),
				testing(3)
				}
			ACCESS read-only
			STATUS mandatory
			DESCRIPTION
				"The current operational state of the interface.
				The testing(3) state indicates that no operational
				packets can be passed."
			::= { accInterfaceEntry 7 }
		
		-- 1.4.2.1.8
		accInterfaceAdminStatus OBJECT-TYPE
			SYNTAX INTEGER
				{
				up(1),
				down(2),
				testing(3)
				}
			ACCESS read-only
			STATUS mandatory
			DESCRIPTION
				"The desired state of the interface.
				The testing(3) state indicates that no operational
				packets can be passed."
			::= { accInterfaceEntry 8 }
		
		-- 1.4.2.1.9
		accInterfaceMtu OBJECT-TYPE
			SYNTAX INTEGER
			ACCESS read-only
			STATUS mandatory
			DESCRIPTION
				"The size of the largest datagram which can be
				sent/received on the interface, specified in
				octets.  For interfaces that are used for
				transmitting network datagrams, this is the size
				of the largest network datagram that can be sent
				on the interface."
			::= { accInterfaceEntry 9 }
		
		-- 1.4.2.1.10
		accInterfaceSpeed OBJECT-TYPE
			SYNTAX Gauge
			ACCESS read-only
			STATUS mandatory
			DESCRIPTION
				"An estimate of the interface's current bandwidth
				in bits per second.  For interfaces which do not
				vary in bandwidth or for those where no accurate
				estimation can be made, this object should contain
				the nominal bandwidth."
			::= { accInterfaceEntry 10 }
		
		-- 1.4.2.1.11
		accInterfaceOutQlength OBJECT-TYPE
			SYNTAX Gauge
			ACCESS read-only
			STATUS mandatory
			DESCRIPTION
				"The length of the output packet queue (in packets)."
			::= { accInterfaceEntry 11 }
		
		-- 1.4.2.1.12
		accInterfaceBufferUtil OBJECT-TYPE
			SYNTAX INTEGER (0..100)
			ACCESS read-only
			STATUS mandatory
			DESCRIPTION
				"Buffer utilization per sub/interface in percentage."
			::= { accInterfaceEntry 12 }
		
		-- 1.4.2.1.13
		accInterfaceAccelerationAdminStatus OBJECT-TYPE
			SYNTAX INTEGER
				{
				off(1),
				on(2)
				}
			ACCESS read-only
			STATUS mandatory
			DESCRIPTION
				"The desired state of Acceleration for this interface."
			::= { accInterfaceEntry 13 }
		
		-- 1.4.2.1.14
		accInterfaceQueuingStrategy OBJECT-TYPE
			SYNTAX INTEGER
				{
				fifo(1),
				wfq(2),
				priority(3),
				custom(4)
				}
			ACCESS read-only
			STATUS mandatory
			DESCRIPTION
				"Interface queuing strategy."
			::= { accInterfaceEntry 14 }
		
		-- 1.4.2.1.15
		accInterfaceIpAddress OBJECT-TYPE
			SYNTAX IpAddress
			ACCESS read-only
			STATUS mandatory
			DESCRIPTION
				"IP address assigned to this interface."
			::= { accInterfaceEntry 15 }
		
		-- 1.4.2.1.16
		accInterfaceIpMask OBJECT-TYPE
			SYNTAX IpAddress
			ACCESS read-only
			STATUS mandatory
			DESCRIPTION
				"Subnet mask for the interface IP address."
			::= { accInterfaceEntry 16 }
		
		-- 1.4.2.1.17
		accInterfaceChunkSizeMethod OBJECT-TYPE
			SYNTAX INTEGER
				{
				manual(1),
				automatic(2)
				}
			ACCESS read-only
			STATUS mandatory
			DESCRIPTION
				"Method used to determine DRC chunk size."
			::= { accInterfaceEntry 17 }
		
		-- 1.4.2.1.18
		accInterfaceChunkSize OBJECT-TYPE
			SYNTAX INTEGER
			ACCESS read-only
			STATUS mandatory
			DESCRIPTION
				"DRC chunk size setting for this interface."
			::= { accInterfaceEntry 18 }
		
		-- 1.4.2.1.19
		accInterfaceDrcMode OBJECT-TYPE
			SYNTAX INTEGER
				{
				off(1),
				semi(2),
				full(3)
				}
			ACCESS read-only
			STATUS mandatory
			DESCRIPTION
				"Drop Recovery operation mode."
			::= { accInterfaceEntry 19 }
		
		-- 1.4.2.1.20
		accInterfaceKeepAliveInterval OBJECT-TYPE
			SYNTAX INTEGER
			ACCESS read-only
			STATUS mandatory
			DESCRIPTION
				"Frequency (in seconds) of keepalive packets sent."
			::= { accInterfaceEntry 20 }
		
		-- 1.4.2.1.21
		accInterfaceKeepAliveIterations OBJECT-TYPE
			SYNTAX INTEGER
			ACCESS read-only
			STATUS mandatory
			DESCRIPTION
				"Number of subsequent keepalives that the system 
				may loose before dropping connection."
			::= { accInterfaceEntry 21 }
		
		-- 1.4.2.1.22
		accInterfaceProbe OBJECT-TYPE
			SYNTAX INTEGER
			ACCESS read-only
			STATUS mandatory
			DESCRIPTION
				"Frequency (in seconds) of probe packets sent."
			::= { accInterfaceEntry 22 }
		
		-- 1.4.2.1.23
		accInterfaceInboundStatus OBJECT-TYPE
			SYNTAX INTEGER
				{
				not-connected(1),
				connected(2)
				}
			ACCESS read-only
			STATUS mandatory
			DESCRIPTION
				"Inbound direction actual synchronization status."
			::= { accInterfaceEntry 23 }
		
		-- 1.4.2.1.24
		accInterfaceInboundCore OBJECT-TYPE
			SYNTAX INTEGER
			ACCESS read-only
			STATUS mandatory
			DESCRIPTION
				"Number of Cores used to Accelerate inbound traffic."
			::= { accInterfaceEntry 24 }
		
		-- 1.4.2.1.25
		accInterfaceOutboundStatus OBJECT-TYPE
			SYNTAX INTEGER
				{
				not-connected(1),
				connected(2)
				}
			ACCESS read-only
			STATUS mandatory
			DESCRIPTION
				"Outbound direction actual synchronization status."
			::= { accInterfaceEntry 25 }
		
		-- 1.4.2.1.26
		accInterfaceOutboundCore OBJECT-TYPE
			SYNTAX INTEGER
			ACCESS read-only
			STATUS mandatory
			DESCRIPTION
				"Number of Cores used to Accelerate outbound traffic."
			::= { accInterfaceEntry 26 }
		
		-- 1.4.2.1.27
		accInterfaceTransmitDirection OBJECT-TYPE
			SYNTAX INTEGER
				{
				duplex(1),
				simplex-receive(2),
				simplex-transmit(3)
				}
			ACCESS read-only
			STATUS mandatory
			DESCRIPTION
				"Interface transmit direction."
			::= { accInterfaceEntry 27 }
		
		-- 1.4.2.1.28
		accInterfacePerformancePeriod OBJECT-TYPE
			SYNTAX INTEGER
			ACCESS read-only
			STATUS mandatory
			DESCRIPTION
				"Sampling period of the Acceleration percentage counters."
			::= { accInterfaceEntry 28 }
		
		-- 1.4.2.1.29
		accInterfacePerformanceInAccelerationUp OBJECT-TYPE
			SYNTAX Gauge
			ACCESS read-only
			STATUS mandatory
			DESCRIPTION
				"Inbound traffic Acceleration percentage since system power-up."
			::= { accInterfaceEntry 29 }
		
		-- 1.4.2.1.30
		accInterfacePerformanceInAccelerationClear OBJECT-TYPE
			SYNTAX Gauge
			ACCESS read-only
			STATUS mandatory
			DESCRIPTION
				"Inbound traffic Acceleration percentage since 
				counters were last cleared."
			::= { accInterfaceEntry 30 }
		
		-- 1.4.2.1.31
		accInterfacePerformanceInAccelerationPeriod OBJECT-TYPE
			SYNTAX Gauge
			ACCESS read-only
			STATUS mandatory
			DESCRIPTION
				"Inbound traffic Acceleration percentage during last 
				sampling period."
			::= { accInterfaceEntry 31 }
		
		-- 1.4.2.1.32
		accInterfacePerformanceOutAccelerationUp OBJECT-TYPE
			SYNTAX Gauge
			ACCESS read-only
			STATUS mandatory
			DESCRIPTION
				"Outbound traffic Acceleration percentage since system power-up."
			::= { accInterfaceEntry 32 }
		
		-- 1.4.2.1.33
		accInterfacePerformanceOutAccelerationClear OBJECT-TYPE
			SYNTAX Gauge
			ACCESS read-only
			STATUS mandatory
			DESCRIPTION
				"Outbound traffic Acceleration percentage since 
				counters were last cleared."
			::= { accInterfaceEntry 33 }
		
		-- 1.4.2.1.34
		accInterfacePerformanceOutAccelerationPeriod OBJECT-TYPE
			SYNTAX Gauge
			ACCESS read-only
			STATUS mandatory
			DESCRIPTION
				"Outbound traffic Acceleration percentage during last 
				sampling period."
			::= { accInterfaceEntry 34 }
		
		-- 1.4.2.1.35
		accInterfacePerformanceDrcResetsUp OBJECT-TYPE
			SYNTAX Counter
			ACCESS read-only
			STATUS mandatory
			DESCRIPTION
				"Number of times the DRC module had to reset since system 
				power-up."
			::= { accInterfaceEntry 35 }
		
		-- 1.4.2.1.36
		accInterfacePerformanceDrcResetsClear OBJECT-TYPE
			SYNTAX Gauge
			ACCESS read-only
			STATUS mandatory
			DESCRIPTION
				"Number of times the DRC module had to reset since 
				counters were last cleared."
			::= { accInterfaceEntry 36 }
		
		-- 1.4.2.1.37
		accInterfacePerformanceDrcResetsPeriod OBJECT-TYPE
			SYNTAX Gauge
			ACCESS read-only
			STATUS mandatory
			DESCRIPTION
				"Number of times the DRC module had to reset during last 
				sampling period.
				"
			::= { accInterfaceEntry 37 }
		
		-- 1.4.2.1.38
		accInterfacePerformanceLostPacketsUp OBJECT-TYPE
			SYNTAX Counter
			ACCESS read-only
			STATUS mandatory
			DESCRIPTION
				"Number of packets lost on the Accelerated link since
				system power-up."
			::= { accInterfaceEntry 38 }
		
		-- 1.4.2.1.39
		accInterfacePerformanceLostPacketsClear OBJECT-TYPE
			SYNTAX Gauge
			ACCESS read-only
			STATUS mandatory
			DESCRIPTION
				"Number of packets lost on the Accelerated link since
				counters were last cleared."
			::= { accInterfaceEntry 39 }
		
		-- 1.4.2.1.40
		accInterfacePerformanceLostPacketsPeriod OBJECT-TYPE
			SYNTAX Gauge
			ACCESS read-only
			STATUS mandatory
			DESCRIPTION
				"Number of packets lost on the Accelerated link during
				last sampling period.
				"
			::= { accInterfaceEntry 40 }
		
		-- 1.4.2.1.41
		accInterfacePerformanceRetransmitPacketsUp OBJECT-TYPE
			SYNTAX Counter
			ACCESS read-only
			STATUS mandatory
			DESCRIPTION
				"Number of packets retransmitted by the DRC mechanism on
				the Accelerated link, since system power-up.
				"
			::= { accInterfaceEntry 41 }
		
		-- 1.4.2.1.42
		accInterfacePerformanceRetransmitPacketsClear OBJECT-TYPE
			SYNTAX Gauge
			ACCESS read-only
			STATUS mandatory
			DESCRIPTION
				"Number of packets retransmitted by the DRC mechanism on
				the Accelerated link, since counters were last cleared."
			::= { accInterfaceEntry 42 }
		
		-- 1.4.2.1.43
		accInterfacePerformanceRetransmitPacketsPeriod OBJECT-TYPE
			SYNTAX Gauge
			ACCESS read-only
			STATUS mandatory
			DESCRIPTION
				"Number of packets retransmitted by the DRC mechanism on
				the Accelerated link, during last sampling period."
			::= { accInterfaceEntry 43 }
		
		-- 1.4.2.1.44
		accInterfacePerformanceRecoveredPacketsUp OBJECT-TYPE
			SYNTAX Counter
			ACCESS read-only
			STATUS mandatory
			DESCRIPTION
				"Number of packets recovered by the DRC mechanism on
				the Accelerated link, since system power-up.
				"
			::= { accInterfaceEntry 44 }
		
		-- 1.4.2.1.45
		accInterfacePerformanceRecoveredPacketsClear OBJECT-TYPE
			SYNTAX Gauge
			ACCESS read-write
			STATUS mandatory
			DESCRIPTION
				"Number of packets recovered by the DRC mechanism on
				the Accelerated link, since counters were last cleared."
			::= { accInterfaceEntry 45 }
		
		-- 1.4.2.1.46
		accInterfacePerformanceRecoveredPacketsPeriod OBJECT-TYPE
			SYNTAX Gauge
			ACCESS read-write
			STATUS mandatory
			DESCRIPTION
				"Number of packets recovered by the DRC mechanism on
				the Accelerated link, during last sampling period."
			::= { accInterfaceEntry 46 }
		
		-- 1.4.2.1.47
		accInterfaceThroughputPeriod OBJECT-TYPE
			SYNTAX INTEGER
			ACCESS read-only
			STATUS mandatory
			DESCRIPTION
				"Sampling period of the interface throughput counters."
			::= { accInterfaceEntry 47 }
		
		-- 1.4.2.1.48
		accInterfaceThroughputCrcErrUp OBJECT-TYPE
			SYNTAX Counter
			ACCESS read-only
			STATUS mandatory
			DESCRIPTION
				"Number of inbound packets with CRC errors, since
				system power-up."
			::= { accInterfaceEntry 48 }
		
		-- 1.4.2.1.49
		accInterfaceThroughputCrcErrClear OBJECT-TYPE
			SYNTAX Gauge
			ACCESS read-only
			STATUS mandatory
			DESCRIPTION
				"Number of inbound packets with CRC errors, since counters
				were last cleared."
			::= { accInterfaceEntry 49 }
		
		-- 1.4.2.1.50
		accInterfaceThroughputCrcErrPeriod OBJECT-TYPE
			SYNTAX Gauge
			ACCESS read-only
			STATUS mandatory
			DESCRIPTION
				"Number of inbound packets with CRC errors, during last
				sampling period."
			::= { accInterfaceEntry 50 }
		
		-- 1.4.2.1.51
		accInterfaceThroughputDropByteUp OBJECT-TYPE
			SYNTAX Counter
			ACCESS read-only
			STATUS mandatory
			DESCRIPTION
				"Total number of data bytes in outbound packets that were
				discarded on the interface due to congestion, since system
				power-up."
			::= { accInterfaceEntry 51 }
		
		-- 1.4.2.1.52
		accInterfaceThroughputDropByteClear OBJECT-TYPE
			SYNTAX Gauge
			ACCESS read-only
			STATUS mandatory
			DESCRIPTION
				"Total number of data bytes in outbound packets that were
				discarded on the interface due to congestion, since
				counters were last cleared."
			::= { accInterfaceEntry 52 }
		
		-- 1.4.2.1.53
		accInterfaceThroughputDropBytePeriod OBJECT-TYPE
			SYNTAX Gauge
			ACCESS read-only
			STATUS mandatory
			DESCRIPTION
				"Total number of data bytes in outbound packets that were
				discarded on the interface due to congestion, during last
				sampling period."
			::= { accInterfaceEntry 53 }
		
		-- 1.4.2.1.54
		accInterfaceThroughputDropPacketsUp OBJECT-TYPE
			SYNTAX Counter
			ACCESS read-only
			STATUS mandatory
			DESCRIPTION
				"Number of outbound packets discarded on the interface due
				to congestion, since system power-up."
			::= { accInterfaceEntry 54 }
		
		-- 1.4.2.1.55
		accInterfaceThroughputDropPacketsClear OBJECT-TYPE
			SYNTAX Gauge
			ACCESS read-only
			STATUS mandatory
			DESCRIPTION
				"Number of outbound packets discarded on the interface due
				to congestion, since counters were last cleared."
			::= { accInterfaceEntry 55 }
		
		-- 1.4.2.1.56
		accInterfaceThroughputDropPacketsPeriod OBJECT-TYPE
			SYNTAX Gauge
			ACCESS read-only
			STATUS mandatory
			DESCRIPTION
				"Number of outbound packets discarded on the interface due
				to congestion, during last sampling period."
			::= { accInterfaceEntry 56 }
		
		-- 1.4.2.1.57
		accInterfaceThroughputInBytesUp OBJECT-TYPE
			SYNTAX Counter
			ACCESS read-only
			STATUS mandatory
			DESCRIPTION
				"Total number of bytes in packets received on the interface
				since system power-up."
			::= { accInterfaceEntry 57 }
		
		-- 1.4.2.1.58
		accInterfaceThroughputInBytesClear OBJECT-TYPE
			SYNTAX Gauge
			ACCESS read-only
			STATUS mandatory
			DESCRIPTION
				"Total number of bytes in packets received on the interface
				since counters were last cleared."
			::= { accInterfaceEntry 58 }
		
		-- 1.4.2.1.59
		accInterfaceThroughputInBytesPeriod OBJECT-TYPE
			SYNTAX Gauge
			ACCESS read-only
			STATUS mandatory
			DESCRIPTION
				"Throughput in kilobit per second over the last
				sampling period."
			::= { accInterfaceEntry 59 }
		
		-- 1.4.2.1.60
		accInterfaceThroughputInPacketsUp OBJECT-TYPE
			SYNTAX Counter
			ACCESS read-only
			STATUS mandatory
			DESCRIPTION
				"Total number of packets received on the interface
				since system power-up."
			::= { accInterfaceEntry 60 }
		
		-- 1.4.2.1.61
		accInterfaceThroughputInPacketsClear OBJECT-TYPE
			SYNTAX Gauge
			ACCESS read-only
			STATUS mandatory
			DESCRIPTION
				"Total number of packets received on the interface since
				counters were last cleared."
			::= { accInterfaceEntry 61 }
		
		-- 1.4.2.1.62
		accInterfaceThroughputInPacketsPeriod OBJECT-TYPE
			SYNTAX Gauge
			ACCESS read-only
			STATUS mandatory
			DESCRIPTION
				"Throughput in packets per second over the last
				sampling period."
			::= { accInterfaceEntry 62 }
		
		-- 1.4.2.1.63
		accInterfaceThroughputOutBytesUp OBJECT-TYPE
			SYNTAX Counter
			ACCESS read-only
			STATUS mandatory
			DESCRIPTION
				"Total number of bytes in packets transmitted by the 
				interface since system power-up."
			::= { accInterfaceEntry 63 }
		
		-- 1.4.2.1.64
		accInterfaceThroughputOutBytesClear OBJECT-TYPE
			SYNTAX Gauge
			ACCESS read-only
			STATUS mandatory
			DESCRIPTION
				"Total number of bytes in packets transmitted by the 
				interface since counters were last cleared."
			::= { accInterfaceEntry 64 }
		
		-- 1.4.2.1.65
		accInterfaceThroughputOutBytesPeriod OBJECT-TYPE
			SYNTAX Gauge
			ACCESS read-only
			STATUS mandatory
			DESCRIPTION
				"Throughput in kilobit per second over the last
				sampling period."
			::= { accInterfaceEntry 65 }
		
		-- 1.4.2.1.66
		accInterfaceThroughputOutPacketsUp OBJECT-TYPE
			SYNTAX Counter
			ACCESS read-only
			STATUS mandatory
			DESCRIPTION
				"Total number of packets transmitted by the interface 
				since system power-up."
			::= { accInterfaceEntry 66 }
		
		-- 1.4.2.1.67
		accInterfaceThroughputOutPacketsClear OBJECT-TYPE
			SYNTAX Gauge
			ACCESS read-only
			STATUS mandatory
			DESCRIPTION
				"Total number of packets transmitted by the interface since
				counters were last cleared."
			::= { accInterfaceEntry 67 }
		
		-- 1.4.2.1.68
		accInterfaceThroughputOutPacketsPeriod OBJECT-TYPE
			SYNTAX Gauge
			ACCESS read-only
			STATUS mandatory
			DESCRIPTION
				"Throughput in packets per second over the last
				sampling period."
			::= { accInterfaceEntry 68 }
		
		-- 1.4.2.1.69
		accInterfaceThroughputRawInBytesUp OBJECT-TYPE
			SYNTAX Counter
			ACCESS read-only
			STATUS mandatory
			DESCRIPTION
				"Total number of raw bytes in packets received on the interface
				since system power-up."
			::= { accInterfaceEntry 69 }
		
		-- 1.4.2.1.70
		accInterfaceThroughputRawInBytesClear OBJECT-TYPE
			SYNTAX Gauge
			ACCESS read-only
			STATUS mandatory
			DESCRIPTION
				"Total number of raw bytes in packets received on the interface
				since counters were last cleared."
			::= { accInterfaceEntry 70 }
		
		-- 1.4.2.1.71
		accInterfaceThroughputRawInBytesPeriod OBJECT-TYPE
			SYNTAX Gauge
			ACCESS read-only
			STATUS mandatory
			DESCRIPTION
				"Throughput in kilobit per second over the last
				sampling period."
			::= { accInterfaceEntry 71 }
		
		-- 1.4.2.1.72
		accInterfaceThroughputRawOutBytesUp OBJECT-TYPE
			SYNTAX Counter
			ACCESS read-only
			STATUS mandatory
			DESCRIPTION
				"Total number of raw bytes in packets transmitted by the 
				interface since system power-up."
			::= { accInterfaceEntry 72 }
		
		-- 1.4.2.1.73
		accInterfaceThroughputRawOutBytesClear OBJECT-TYPE
			SYNTAX Gauge
			ACCESS read-only
			STATUS mandatory
			DESCRIPTION
				"Total number of raw bytes in packets transmitted by the 
				interface since counters were last cleared."
			::= { accInterfaceEntry 73 }
		
		-- 1.4.2.1.74
		accInterfaceThroughputRawOutBytesPeriod OBJECT-TYPE
			SYNTAX Gauge
			ACCESS read-only
			STATUS mandatory
			DESCRIPTION
				"Throughput in kilobit per second over the last
				sampling period."
			::= { accInterfaceEntry 74 }
		
	
	END

--
-- EXPAND-ACCELERATOROS-MIB.my
--
