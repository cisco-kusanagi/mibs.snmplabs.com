IPX-PRIVATE-MIB DEFINITIONS ::= BEGIN

-- Referencing the parent branch.

IMPORTS
    MODULE-IDENTITY, OBJECT-TYPE, Integer32, Counter32
                                                FROM SNMPv2-SMI
    RowStatus                                   FROM SNMPv2-TC
    cjnProtocol                                 FROM Cajun-ROOT; 

cjnIpx MODULE-IDENTITY
    LAST-UPDATED "9904010000Z" -- Thursday, April 1, 1999"
    ORGANIZATION "Lucent's Concord Technology Center (CTC)"
    CONTACT-INFO
        "Marc Cochran -- mcochran@lucent.com"
    DESCRIPTION
        "Cajun IPX Routing Private MIB"
    ::= { cjnProtocol 3 }


-- Types
--
    NetNumber ::= OCTET STRING (SIZE(4))
    NodeNumber ::= OCTET STRING (SIZE(6))
    ServiceType ::= OCTET STRING (SIZE(2))
    ServiceName ::= OCTET STRING (SIZE(1..47))
    ServiceSocket ::= OCTET STRING (SIZE(2))


-- IPX Global Configuration Group
--
    cjnIpxGlobalGroup      OBJECT IDENTIFIER ::= { cjnIpx 1 }

    cjnIpxEnabled OBJECT-TYPE
        SYNTAX      INTEGER { enabled(1), disabled(2) }
        MAX-ACCESS  read-write
        STATUS      current
        DESCRIPTION
                "Enable / Disable IPX Routing on this system."
        ::= { cjnIpxGlobalGroup 1 }
        

-- IPX Global Statistics Group
--
    cjnIpxGlobalStatsGroup  OBJECT IDENTIFIER ::= { cjnIpx 4 }

    cjnIpxInReceives OBJECT-TYPE
        SYNTAX      Counter32
        MAX-ACCESS  read-only
        STATUS      current
        DESCRIPTION
                "The number of received IPX packets, including those 
                received in error."
        ::= { cjnIpxGlobalStatsGroup 1 }

    cjnIpxInDelivers OBJECT-TYPE
        SYNTAX      Counter32
        MAX-ACCESS  read-only
        STATUS      current
        DESCRIPTION
                "The number of received IPX packets delivered locally."
        ::= { cjnIpxGlobalStatsGroup 2 }

    cjnIpxForwarded OBJECT-TYPE
        SYNTAX      Counter32
        MAX-ACCESS  read-only
        STATUS      current
        DESCRIPTION
                "The number of received IPX packets forwarded."
        ::= { cjnIpxGlobalStatsGroup 3 }

    cjnIpxNetBIOSReceives OBJECT-TYPE
        SYNTAX      Counter32
        MAX-ACCESS  read-only
        STATUS      current
        DESCRIPTION
                "The number of received IPX NetBIOS packets."
        ::= { cjnIpxGlobalStatsGroup 4 }

    cjnIpxInDiscards OBJECT-TYPE
        SYNTAX      Counter32
        MAX-ACCESS  read-only
        STATUS      current
        DESCRIPTION
                "The number of IPX packets received but discarded due to 
                reasons other than those accounted for by cjnIpxInHdrErrors 
                and cjnIpxInUnknownSockets."
        ::= { cjnIpxGlobalStatsGroup 5 }

    cjnIpxInHdrErrors OBJECT-TYPE
        SYNTAX      Counter32
        MAX-ACCESS  read-only
        STATUS      current
        DESCRIPTION
                "The number of IPX packets discarded due to errors in their 
                headers, including any IPX packet with a size less than the 
                minimum of 30 bytes."
        ::= { cjnIpxGlobalStatsGroup 6 }

    cjnIpxInUnknownSockets OBJECT-TYPE
        SYNTAX      Counter32
        MAX-ACCESS  read-only
        STATUS      current
        DESCRIPTION
                "The number of IPX packets discarded because the destination 
                socket was not open."
        ::= { cjnIpxGlobalStatsGroup 7 }

    cjnIpxInTooManyHops OBJECT-TYPE
        SYNTAX      Counter32
        MAX-ACCESS  read-only
        STATUS      current
        DESCRIPTION
                "The number of IPX packets discarded due to exceeding the 
                maximum hop count."
        ::= { cjnIpxGlobalStatsGroup 8 }

    cjnIpxInBadChecksums OBJECT-TYPE
        SYNTAX      Counter32
        MAX-ACCESS  read-only
        STATUS      current
        DESCRIPTION
                "The number of IPX packets discarded due to having an 
                incorrect checksum."
        ::= { cjnIpxGlobalStatsGroup 9 }

    cjnIpxOutRequests OBJECT-TYPE
        SYNTAX      Counter32
        MAX-ACCESS  read-only
        STATUS      current
        DESCRIPTION
                "The number of IPX packets supplied locally for 
                transmission, not including any packets counted in 
                cjnIpxForwarded."
        ::= { cjnIpxGlobalStatsGroup 10 }

    cjnIpxOutPackets OBJECT-TYPE
        SYNTAX      Counter32
        MAX-ACCESS  read-only
        STATUS      current
        DESCRIPTION
                "The number of IPX packets transmitted."
        ::= { cjnIpxGlobalStatsGroup 11 }

    cjnIpxOutDiscards OBJECT-TYPE
        SYNTAX      Counter32
        MAX-ACCESS  read-only
        STATUS      current
        DESCRIPTION
                "The number of outgoing IPX packets discarded."
        ::= { cjnIpxGlobalStatsGroup 12 }

    cjnIpxOutNoRoutes OBJECT-TYPE
        SYNTAX      Counter32
        MAX-ACCESS  read-only
        STATUS      current
        DESCRIPTION
                "The number of times an IPX packet, either received or 
                supplied locally for transmission, could not be transmitted 
                because no route to the destination was found."
        ::= { cjnIpxGlobalStatsGroup 13 }

    cjnIpxInPingRequests OBJECT-TYPE
        SYNTAX      Counter32
        MAX-ACCESS  read-only
        STATUS      current
        DESCRIPTION
                "The number of received ping requests."
        ::= { cjnIpxGlobalStatsGroup 14 }

    cjnIpxInPingReplies OBJECT-TYPE
        SYNTAX      Counter32
        MAX-ACCESS  read-only
        STATUS      current
        DESCRIPTION
                "The number of received ping replies."
        ::= { cjnIpxGlobalStatsGroup 15 }

    cjnIpxOutPingRequests OBJECT-TYPE
        SYNTAX      Counter32
        MAX-ACCESS  read-only
        STATUS      current
        DESCRIPTION
                "The number of transmitted ping requests."
        ::= { cjnIpxGlobalStatsGroup 16 }

    cjnIpxOutPingReplies OBJECT-TYPE
        SYNTAX      Counter32
        MAX-ACCESS  read-only
        STATUS      current
        DESCRIPTION
                "The number of transmitted ping replies."
        ::= { cjnIpxGlobalStatsGroup 17 }

    cjnIpxGlobalStatsReset  OBJECT-TYPE
        SYNTAX      INTEGER { enable(1), disable(2) }
        MAX-ACCESS  read-write
        STATUS      current
        DESCRIPTION
                "When set to the value enable (1) all IPX Global statistics 
                are reset to zero after which the value of this MIB object 
                returns to disable(2)."
        ::= { cjnIpxGlobalStatsGroup 18 }


-- IPX Routing Group
--
    cjnIpxRouteGroup  OBJECT IDENTIFIER ::= { cjnIpx 5 }

    cjnIpxMaxRoutes OBJECT-TYPE
        SYNTAX      Integer32 (1..10240)
        MAX-ACCESS  read-write
        STATUS      current
        DESCRIPTION
                "Specify the maximum number of routes that can be stored 
                in the IPX route table."
        DEFVAL      { 2048 }
        ::= { cjnIpxRouteGroup 1 }  

    cjnIpxDefaultRouteEnabled OBJECT-TYPE
        SYNTAX      INTEGER { enabled(1), disabled(2) }
        MAX-ACCESS  read-write
        STATUS      current
        DESCRIPTION
                "Enable or disable IPX routing using a default route 
                (if one is known)."
        ::= { cjnIpxRouteGroup 2 }

    cjnIpxNumRoutes OBJECT-TYPE
        SYNTAX      Counter32
        MAX-ACCESS  read-only
        STATUS      current
        DESCRIPTION
                "The number of routes."
        ::= { cjnIpxRouteGroup 3 }

    cjnIpxPeakNumRoutes OBJECT-TYPE
        SYNTAX      Counter32
        MAX-ACCESS  read-only
        STATUS      current
        DESCRIPTION
                "The peak number of routes."
        ::= { cjnIpxRouteGroup 4 }

    cjnIpxRouteAddFailures OBJECT-TYPE
        SYNTAX      Counter32
        MAX-ACCESS  read-only
        STATUS      current
        DESCRIPTION
                "The number of times an attempt to add a route failed, 
                usually due to the number of routes exceeding 
                cjnIpxMaxRoutes."
        ::= { cjnIpxRouteGroup 5 }


-- IPX Static Route Table Group
--
    cjnIpxStaticRouteGroup  OBJECT IDENTIFIER ::= { cjnIpxRouteGroup 6 }

    cjnIpxStaticRouteTable OBJECT-TYPE
        SYNTAX      SEQUENCE OF CjnIpxStaticRouteEntry
        MAX-ACCESS  not-accessible
        STATUS      current
        DESCRIPTION
                "A list of Cajun IPX static route entries."
        ::= { cjnIpxStaticRouteGroup 1 }
        
    cjnIpxStaticRouteEntry OBJECT-TYPE
        SYNTAX      CjnIpxStaticRouteEntry
        MAX-ACCESS  not-accessible
        STATUS      current
        DESCRIPTION
                "A Cajun IPX static route instance."
        INDEX       { cjnIpxStaticRouteNet }
        ::= { cjnIpxStaticRouteTable 1 }

    CjnIpxStaticRouteEntry ::=
        SEQUENCE {
            cjnIpxStaticRouteNet            NetNumber,
            cjnIpxStaticRouteRowStatus      RowStatus,
            cjnIpxStaticRouteIfIndex        Integer32,
            cjnIpxStaticRouteNextHopNode    NodeNumber,
            cjnIpxStaticRouteTicks          Integer32,
            cjnIpxStaticRouteHops           Integer32
        }
        
    cjnIpxStaticRouteNet OBJECT-TYPE
        SYNTAX      NetNumber
        MAX-ACCESS  read-only
        STATUS      current
        DESCRIPTION
                "The IPX network number of the route's destination."
        ::= { cjnIpxStaticRouteEntry 1 }

    cjnIpxStaticRouteRowStatus OBJECT-TYPE
        SYNTAX      RowStatus
        MAX-ACCESS  read-create
        STATUS      current
        DESCRIPTION
                "The status of this row, by which new entries may be
                created, or old entries deleted from this table."
        ::= { cjnIpxStaticRouteEntry 2 }

    cjnIpxStaticRouteIfIndex OBJECT-TYPE
        SYNTAX      Integer32
        MAX-ACCESS  read-create
        STATUS      current
        DESCRIPTION
                "The ifIndex value of the interface used to reach the next
                hop."
        ::= { cjnIpxStaticRouteEntry 3 }

    cjnIpxStaticRouteNextHopNode OBJECT-TYPE
        SYNTAX      NodeNumber
        MAX-ACCESS  read-create
        STATUS      current
        DESCRIPTION
                "The node number of the next hop."
        ::= { cjnIpxStaticRouteEntry 4 }

    cjnIpxStaticRouteTicks OBJECT-TYPE
        SYNTAX      Integer32
        MAX-ACCESS  read-create
        STATUS      current
        DESCRIPTION
                "The delay, in ticks, to reach the route's destination."
        ::= { cjnIpxStaticRouteEntry 5 }

    cjnIpxStaticRouteHops OBJECT-TYPE
        SYNTAX      Integer32
        MAX-ACCESS  read-create
        STATUS      current
        DESCRIPTION
                "The number of hops necessary to reach the route's
                destination."
        ::= { cjnIpxStaticRouteEntry 6 }


-- IPX Route Table Group
--
    cjnIpxRouteTable OBJECT-TYPE
        SYNTAX      SEQUENCE OF CjnIpxRouteEntry
        MAX-ACCESS  not-accessible
        STATUS      current
        DESCRIPTION
                "A list of Cajun IPX route entries."
        ::= { cjnIpxRouteGroup 7 }
        
    cjnIpxRouteEntry OBJECT-TYPE
        SYNTAX      CjnIpxRouteEntry
        MAX-ACCESS  not-accessible
        STATUS      current
        DESCRIPTION
                "A Cajun IPX route instance."
        INDEX       { cjnIpxRouteNet }
        ::= { cjnIpxRouteTable 1 }

    CjnIpxRouteEntry ::=
        SEQUENCE {
            cjnIpxRouteNet          NetNumber,
            cjnIpxRouteRowStatus    RowStatus,
            cjnIpxRouteIfIndex      Integer32,
            cjnIpxRouteNextHopNode  NodeNumber,
            cjnIpxRouteTicks        Integer32,
            cjnIpxRouteHops         Integer32,
            cjnIpxRouteProtocol     INTEGER
        }
        
    cjnIpxRouteNet OBJECT-TYPE
        SYNTAX      NetNumber
        MAX-ACCESS  read-only
        STATUS      current
        DESCRIPTION
                "The IPX network number of the route's destination."
        ::= { cjnIpxRouteEntry 1 }

    cjnIpxRouteRowStatus OBJECT-TYPE
        SYNTAX      RowStatus
        MAX-ACCESS  read-create
        STATUS      current
        DESCRIPTION
                "The status of this row, by which entries may ONLY be 
                deleted from this table."
        ::= { cjnIpxRouteEntry 2 }

    cjnIpxRouteIfIndex OBJECT-TYPE
        SYNTAX      Integer32
        MAX-ACCESS  read-only
        STATUS      current
        DESCRIPTION
                "The ifIndex value of the interface used to reach the next
                hop."
        ::= { cjnIpxRouteEntry 3 }

    cjnIpxRouteNextHopNode OBJECT-TYPE
        SYNTAX      NodeNumber
        MAX-ACCESS  read-only
        STATUS      current
        DESCRIPTION
                "The node number of the next hop."
        ::= { cjnIpxRouteEntry 4 }

    cjnIpxRouteTicks OBJECT-TYPE
        SYNTAX      Integer32
        MAX-ACCESS  read-only
        STATUS      current
        DESCRIPTION
                "The delay, in ticks, to reach the route's destination."
        ::= { cjnIpxRouteEntry 5 }

    cjnIpxRouteHops OBJECT-TYPE
        SYNTAX      Integer32
        MAX-ACCESS  read-only
        STATUS      current
        DESCRIPTION
                "The number of hops necessary to reach the route's
                destination."
        ::= { cjnIpxRouteEntry 6 }

    cjnIpxRouteProtocol OBJECT-TYPE
        SYNTAX      INTEGER { local(1), rip(2), static(3) }
        MAX-ACCESS  read-only
        STATUS      current
        DESCRIPTION
                "The routing protocol from which knowledge of this 
                destination was obtained."
        ::= { cjnIpxRouteEntry 7 }


-- IPX Services Group
--
    cjnIpxServicesGroup  OBJECT IDENTIFIER ::= { cjnIpx 6 }

    cjnIpxMaxServices OBJECT-TYPE
        SYNTAX      Integer32 (1..10240)
        MAX-ACCESS  read-write
        STATUS      current
        DESCRIPTION
                "Specify the maximum number of services that can be stored 
                in the IPX service table."
        DEFVAL      { 2048 }
        ::= { cjnIpxServicesGroup 1 }  

    cjnIpxNumServices OBJECT-TYPE
        SYNTAX      Counter32
        MAX-ACCESS  read-only
        STATUS      current
        DESCRIPTION
                "The number of IPX services."
        ::= { cjnIpxServicesGroup 2 }

    cjnIpxPeakNumServices OBJECT-TYPE
        SYNTAX      Counter32
        MAX-ACCESS  read-only
        STATUS      current
        DESCRIPTION
                "The peak number of services."
        ::= { cjnIpxServicesGroup 3 }

    cjnIpxServiceAddFailures OBJECT-TYPE
        SYNTAX      Counter32
        MAX-ACCESS  read-only
        STATUS      current
        DESCRIPTION
                "The number of times an attempt to add a service failed, 
                usually due to the number of services exceeding 
                cjnIpxMaxServices."
        ::= { cjnIpxServicesGroup 4 }


-- IPX Static Service Table Group
--
    cjnIpxStaticServiceGroup  OBJECT IDENTIFIER ::= { cjnIpxServicesGroup 5 }

    cjnIpxStaticServiceTable OBJECT-TYPE
        SYNTAX      SEQUENCE OF CjnIpxStaticServiceEntry
        MAX-ACCESS  not-accessible
        STATUS      current
        DESCRIPTION
                "A list of Cajun IPX static service entries."
        ::= { cjnIpxStaticServiceGroup 1 }
        
    cjnIpxStaticServiceEntry OBJECT-TYPE
        SYNTAX      CjnIpxStaticServiceEntry
        MAX-ACCESS  not-accessible
        STATUS      current
        DESCRIPTION
                "A Cajun IPX static service instance."
        INDEX       { cjnIpxStaticServiceType, cjnIpxStaticServiceName }
        ::= { cjnIpxStaticServiceTable 1 }

    CjnIpxStaticServiceEntry ::=
        SEQUENCE {
            cjnIpxStaticServiceType         ServiceType,
            cjnIpxStaticServiceName         ServiceName,
            cjnIpxStaticServiceRowStatus    RowStatus,
            cjnIpxStaticServiceNet          NetNumber,
            cjnIpxStaticServiceNode         NodeNumber,
            cjnIpxStaticServiceSocket       ServiceSocket,
            cjnIpxStaticServiceIfIndex      Integer32,
            cjnIpxStaticServiceNextHopNode  NodeNumber,
            cjnIpxStaticServiceHops         Integer32
        }
        
    cjnIpxStaticServiceType OBJECT-TYPE
        SYNTAX      ServiceType
        MAX-ACCESS  read-only
        STATUS      current
        DESCRIPTION
                "The service type."
        ::= { cjnIpxStaticServiceEntry 1 }

    cjnIpxStaticServiceName OBJECT-TYPE
        SYNTAX      ServiceName
        MAX-ACCESS  read-only
        STATUS      current
        DESCRIPTION
                "The service name."
        ::= { cjnIpxStaticServiceEntry 2 }

    cjnIpxStaticServiceRowStatus OBJECT-TYPE
        SYNTAX      RowStatus
        MAX-ACCESS  read-create
        STATUS      current
        DESCRIPTION
                "The status of this row, by which new entries may be
                created, or old entries deleted from this table."
        ::= { cjnIpxStaticServiceEntry 3 }

    cjnIpxStaticServiceNet OBJECT-TYPE
        SYNTAX      NetNumber
        MAX-ACCESS  read-create
        STATUS      current
        DESCRIPTION
                "The IPX network number portion of the IPX address of the
                service."
        ::= { cjnIpxStaticServiceEntry 4 }

    cjnIpxStaticServiceNode OBJECT-TYPE
        SYNTAX      NodeNumber
        MAX-ACCESS  read-create
        STATUS      current
        DESCRIPTION
                "The node portion of the IPX address of the service."
        ::= { cjnIpxStaticServiceEntry 5 }

    cjnIpxStaticServiceSocket OBJECT-TYPE
        SYNTAX      ServiceSocket
        MAX-ACCESS  read-create
        STATUS      current
        DESCRIPTION
                "The socket portion of the IPX address of the service."
        ::= { cjnIpxStaticServiceEntry 6 }

    cjnIpxStaticServiceIfIndex OBJECT-TYPE
        SYNTAX      Integer32
        MAX-ACCESS  read-create
        STATUS      current
        DESCRIPTION
                "The ifIndex value of the interface used to reach the
                service."
        ::= { cjnIpxStaticServiceEntry 7 }

    cjnIpxStaticServiceNextHopNode OBJECT-TYPE
        SYNTAX      NodeNumber
        MAX-ACCESS  read-create
        STATUS      current
        DESCRIPTION
                "The IPX node number of the next hop."
        ::= { cjnIpxStaticServiceEntry 8 }

    cjnIpxStaticServiceHops OBJECT-TYPE
        SYNTAX      Integer32
        MAX-ACCESS  read-create
        STATUS      current
        DESCRIPTION
                "The number of hops to the service."
        ::= { cjnIpxStaticServiceEntry 9 }


-- IPX Service Table Group
--
    cjnIpxServiceTable OBJECT-TYPE
        SYNTAX      SEQUENCE OF CjnIpxServiceEntry
        MAX-ACCESS  not-accessible
        STATUS      current
        DESCRIPTION
                "A list of Cajun IPX service entries."
        ::= { cjnIpxServicesGroup 6 }
        
    cjnIpxServiceEntry OBJECT-TYPE
        SYNTAX      CjnIpxServiceEntry
        MAX-ACCESS  not-accessible
        STATUS      current
        DESCRIPTION
                "A Cajun IPX service instance."
        INDEX       { cjnIpxServiceType, cjnIpxServiceName }
        ::= { cjnIpxServiceTable 1 }

    CjnIpxServiceEntry ::=
        SEQUENCE {
            cjnIpxServiceType           ServiceType,
            cjnIpxServiceName           ServiceName,
            cjnIpxServiceRowStatus      RowStatus,
            cjnIpxServiceNet            NetNumber,
            cjnIpxServiceNode           NodeNumber,
            cjnIpxServiceSocket         ServiceSocket,
            cjnIpxServiceIfIndex        Integer32,
            cjnIpxServiceNextHopNode    NodeNumber,
            cjnIpxServiceHops           Integer32,
            cjnIpxServiceProtocol       INTEGER
        }
        
    cjnIpxServiceType OBJECT-TYPE
        SYNTAX      ServiceType
        MAX-ACCESS  read-only
        STATUS      current
        DESCRIPTION
                "The service type."
        ::= { cjnIpxServiceEntry 1 }

    cjnIpxServiceName OBJECT-TYPE
        SYNTAX      ServiceName
        MAX-ACCESS  read-only
        STATUS      current
        DESCRIPTION
                "The service name."
        ::= { cjnIpxServiceEntry 2 }

    cjnIpxServiceRowStatus OBJECT-TYPE
        SYNTAX      RowStatus
        MAX-ACCESS  read-create
        STATUS      current
        DESCRIPTION
                "The status of this row, by which entries may ONLY be 
                deleted from this table."
        ::= { cjnIpxServiceEntry 3 }

    cjnIpxServiceNet OBJECT-TYPE
        SYNTAX      NetNumber
        MAX-ACCESS  read-only
        STATUS      current
        DESCRIPTION
                "The IPX network number portion of the IPX address of the
                service."
        ::= { cjnIpxServiceEntry 4 }

    cjnIpxServiceNode OBJECT-TYPE
        SYNTAX      NodeNumber
        MAX-ACCESS  read-only
        STATUS      current
        DESCRIPTION
                "The node portion of the IPX address of the service."
        ::= { cjnIpxServiceEntry 5 }

    cjnIpxServiceSocket OBJECT-TYPE
        SYNTAX      ServiceSocket
        MAX-ACCESS  read-only
        STATUS      current
        DESCRIPTION
                "The socket portion of the IPX address of the service."
        ::= { cjnIpxServiceEntry 6 }

    cjnIpxServiceIfIndex OBJECT-TYPE
        SYNTAX      Integer32
        MAX-ACCESS  read-only
        STATUS      current
        DESCRIPTION
                "The ifIndex value of the interface used to reach the
                service."
        ::= { cjnIpxServiceEntry 7 }

    cjnIpxServiceNextHopNode OBJECT-TYPE
        SYNTAX      NodeNumber
        MAX-ACCESS  read-only
        STATUS      current
        DESCRIPTION
                "The IPX node number of the next hop."
        ::= { cjnIpxServiceEntry 8 }

    cjnIpxServiceHops OBJECT-TYPE
        SYNTAX      Integer32
        MAX-ACCESS  read-only
        STATUS      current
        DESCRIPTION
                "The number of hops to the service."
        ::= { cjnIpxServiceEntry 9 }

    cjnIpxServiceProtocol OBJECT-TYPE
        SYNTAX      INTEGER { sap(1), static(2) }
        MAX-ACCESS  read-only
        STATUS      current
        DESCRIPTION
                "The protocol from which knowledge of this 
                service was obtained."
        ::= { cjnIpxServiceEntry 10 }

END
