-- Based on Private GCM MIB Requirements Document (Rev 1.1, dated 6/30/97).
-- 
-- MIB Revision : 1.0 dated 7-3-97
-- Change Desc. : Initial submittal - R. Carmona. 
-- 
-- MIB Revision : 1.1 dated 10-7-97
-- Change Desc. : Added object GcmUnitBackupRemainTime in both nvm and mcmGcmUnitTable.
--		  Modified enumerations in mcmGcmLinkSigOperStatus and mcmGcmLinkProtoStatus.
--		  Changed range for nvmGcmUnitSwitchDelay from (1..255) to (0..255).
--		  Changed descriptions in both nvm and mcmGcmUnitSwitchDelay. - K. Yeh
--
-- MIB Revision : 1.2 dated 10-9-97
-- Change Desc. : Replaced MPA with 4400 - B. Jafari. 
-- 
-- Mib Revision : 1.3 dated 10-17-97
--		  Changed DisplayString size of all string variables. 
--
-- *** RELEASE 3.0 ***
-- Mib Revision : 1.4 dated 7-8-98
--		  Added enumerations three and four to mcmGcmUnitSwitchType. 
--                Added the (mcm/nvm)GcmUnitBackupSwitchDelay, 
--                 (mcm/nvm)GcmUnitPrimarySwitchDelay ,
--                 (mcm/nvm)GcmUnitRegionalIndex, (mcm/nvm)GcmUnitModeCfg, 
--                 (mcm/nvm)GcmUnitPriLinkFailMonStatus, 
--                 (mcm/nvm)GcmUnitPriLinkFailMonDurMin,
--                 (mcm/nvm)mcmGcmUnitPriLinkFailMonThrshld,                                             
--                 mcmGcmUnitPriLinkFailMonCount and mcmGcmUnitCmd objects.
--                Deprecated the (mcm/nvm)GcmUnitSwitchDelay objects
--                Added enumeration three and changed the access from 
--                 from read-only to read-write for nvmGcmLinkRowStatus,
--                 nvmGcmBackupCfgLinkRowStatus and nvmGcmTimerRowStatus              
--                Added mcmGcmRegionalLinkEst and mcmGcmRegionalLinkDown traps.
--                Replaced all instances of the "4400" string with the 
--                generic string "access device".  
--                                                                      S. Gaur
-- *** RELEASE 3.1 ***
-- Mib Revision : 1.5 dated 12-11-98
--		  Removed ppp from mcm and nvm



MICOM-GCM-MIB DEFINITIONS ::= BEGIN
	IMPORTS
		OBJECT-TYPE
				FROM RFC-1212
		TRAP-TYPE
				FROM RFC-1215
		DisplayString 
				FROM SNMPv2-TC
		micom-oscar 
				FROM MICOM-OSCAR-MIB
                mcmSysAsciiTimeOfDay 

                                FROM MICOM-SYS-MIB;


-- group OBJECT IDENTIFIERs

	micom-gcm		OBJECT IDENTIFIER ::= {micom-oscar 25}
	configuration		OBJECT IDENTIFIER ::= {micom-gcm 1}
	status			OBJECT IDENTIFIER ::= {micom-gcm 2}


-- *** CONFIGURATION groups/tables ***

-- Note: The following groups contain 2 related groups/tables for all configuration
--       functionality. 
--	 1) The Standard or Operational Parameters (Operational) provide the
--	 SNMP management interface with the access devices operational modules.
--	 Objects defined for this interface begin with the 'mcm' prefix.
--	 2) The Configuration Parameters (Configuration) provide the SNMP 
--	 management interface with a stored configuration. 
--	 Objects defined for this interface begin with the 'nvm' prefix.
--	


--  Operational Parameter ("mcm") Groups/Tables


--  the GCM Global Configuration Group 
--  (Standard/Operational Parameters)

--  This group represents the global configuration parameters for the GCM.

mcmGcmGlobalCfgGroup  OBJECT IDENTIFIER ::= { configuration 1 }

mcmGcmGlobalCfgAdminStatus OBJECT-TYPE
	SYNTAX	INTEGER {
		enabled (1),
		disabled (2)
		}
	ACCESS	read-only
	STATUS	mandatory
	DESCRIPTION
	  "NAME = ;
	   DESC = The GCM admin status: \
		  1 - GCM is enabled. \
		  2 - GCM is disabled. \
		  (Operational);
	   HELP = ;
	   CAPABILITIES = NET_CFG, VPN_DISP ;"
	DEFVAL  { enabled }
	::= { mcmGcmGlobalCfgGroup 1 }

mcmGcmGlobalCfgTraps OBJECT-TYPE
	SYNTAX	INTEGER {
		enabled (1),
		disabled (2)
		}
	ACCESS	read-only
	STATUS	mandatory
	DESCRIPTION
	  "NAME = ;
	   DESC = This object indicates whether GCM traps will \
		  be generated or not. (Operational);
	   HELP = ;
	   CAPABILITIES = NET_CFG, VPN_DISP ;"
	DEFVAL  { disabled }
	::= { mcmGcmGlobalCfgGroup 2 }

mcmGcmGlobalCfgAutoActSelMode OBJECT-TYPE
	SYNTAX	INTEGER {
		hwCfgAutoSelect (1),
		disabled (2)
		}
	ACCESS	read-only
	STATUS	mandatory
	DESCRIPTION
	  "NAME = ;
	   DESC = This object is used to set the mode of the unit \
		  activation after reading the configuration file. \
		  disabled (2): The GCM does not change the objects \
		    mcmGcmUnitAdminStatus in the GCM Unit \
		    table after reading the configuration file. \
		  hwCfgAutoSelect (1): After reading the configuration \
		    file, the GCM activates only one of the three GCM \
		    Units depending on the hardware configuration. \
		    The stored configuration for the object \
		    mcmGcmUnitAdminStatus will be ignored. \
		    The following association between the GCM Unit \
		    rows and hardware configuration exists: \
		    Row 1: Port 2 and (optional) 3 with Serial WAN \
		      card; Port 2 is the Primary port. \
		    Row 2: Port 2 with Serial WAN card, Port 3 with \
		      ISDN card, Port 2 is the Primary port. \
		    Row 3: Port 2 and (optional) 3 with ISDN, Port 2 \
		      is the Primary port. \
		  (Operational);
	   HELP = ;
	   CAPABILITIES = NET_CFG, VPN_DISP ;"
	::= { mcmGcmGlobalCfgGroup 3 }


--  the GCM Link Table 
--  (Standard/Operational Parameters)

--  This table is used to view the operating configuration in the GCM Link Table. 

mcmGcmLinkTable OBJECT-TYPE
	SYNTAX	SEQUENCE OF McmGcmLinkEntry
	ACCESS	not-accessible
	STATUS	mandatory
	DESCRIPTION
	  "NAME = ;
	   DESC = The GCM Link Table. (Operational) ;
	   HELP = ;
	   CAPABILITIES = NET_CFG, VPN_DISP ;"
	::= {configuration 2 }

mcmGcmLinkEntry OBJECT-TYPE
	SYNTAX	McmGcmLinkEntry
	ACCESS	not-accessible
	STATUS	mandatory
	DESCRIPTION
	  "NAME = ;
	   DESC = An entry in the GCM Link Table. \
		  (Operational) ;
	   HELP = ;
	   CAPABILITIES = ;"
	INDEX  {mcmGcmLinkIndex}
	::= {mcmGcmLinkTable 1}

McmGcmLinkEntry ::= SEQUENCE {
	mcmGcmLinkIndex			INTEGER,
	mcmGcmLinkUnitIndex		INTEGER,
	mcmGcmLinkName			DisplayString,
	mcmGcmLinkSigType		INTEGER,
	mcmGcmLinkSigPcmIndex		INTEGER,
	mcmGcmLinkSigOperStatus		INTEGER,
	mcmGcmLinkProtoType		INTEGER,
	mcmGcmLinkProtoPcmIndex		INTEGER,
	mcmGcmLinkProtoStatus		INTEGER,
	mcmGcmLinkVoiceCalls		INTEGER
	}

mcmGcmLinkIndex OBJECT-TYPE
	SYNTAX	INTEGER (1..255)
	ACCESS	read-only
	STATUS	mandatory
	DESCRIPTION
	  "NAME = ;
	   DESC = The index value which uniquely identifies an \
		  entry in the GCM Link Table. (Operational);
	   HELP = ;
	   CAPABILITIES = ;"
	::= { mcmGcmLinkEntry 1 }

mcmGcmLinkUnitIndex OBJECT-TYPE
	SYNTAX	INTEGER (1..3)
	ACCESS	read-only
	STATUS	mandatory
	DESCRIPTION
	  "NAME = ;
	   DESC = The index value that uniquely identifies an \
		  entry in the GCM Unit Table. (Operational);
	   HELP = ;
	   CAPABILITIES = ;"
	::= { mcmGcmLinkEntry 2 }

mcmGcmLinkName OBJECT-TYPE
	SYNTAX	DisplayString (SIZE (0..15))
	ACCESS	read-only
	STATUS	mandatory
	DESCRIPTION
	  "NAME = ;
	   DESC = The name of the GCM Link.  Default value is \
		  'gcmLink<mcmGcmLinkIndex>'. (Operational);
	   HELP = ;
	   CAPABILITIES = ;"
	::= { mcmGcmLinkEntry 3 }

mcmGcmLinkSigType OBJECT-TYPE
	SYNTAX	INTEGER {
		reserved (1),
		isdn (2),
		unusedEver-up (3)
		}
	ACCESS	read-only
	STATUS	mandatory
	DESCRIPTION
	  "NAME = ;
	   DESC = The type of the signaling channel, if a signaling \
		  protocol is used. (Operational);
	   HELP = ;
	   CAPABILITIES = ;"
	::= { mcmGcmLinkEntry 4 }

mcmGcmLinkSigPcmIndex OBJECT-TYPE
	SYNTAX	INTEGER (1..65535)
	ACCESS	read-only
	STATUS	mandatory
	DESCRIPTION
	  "NAME = ;
	   DESC = The index value that uniquely identifies an entry \
		  for the PCM.  In the case of the ICM, this entry \
		  represents an index for the dialCtlPeerCfgTable. \
		  (Operational);
	   HELP = ;
	   CAPABILITIES = ;"
	::= { mcmGcmLinkEntry 5 }

mcmGcmLinkSigOperStatus OBJECT-TYPE
	SYNTAX	INTEGER {
		cfg-error (1),
		info-wait (2),
		inactive (3),
		enable-wait (4),
		deferred (5),
		protocol-down (6),
		activating (7),
		active (8),
		disconnecting (9),
		ever-up (10)
		}
	ACCESS	read-only
	STATUS	mandatory
	DESCRIPTION
	  "NAME = ;
	   DESC = The status of the Signaling Link: \
		  cfg-error (1): Configuration error.  The signaling \
		    link is not configured or activated from the \
		    Signaling CM. \
		  info-wait (2): the GCM has sent an information \
		    request message to the Signaling CM to request \
		    the status of this link.  If the GCM receives an error \
		    message, the status will be set to cfg-error (1). \
		  inactive (3): the link is inactive. \
		  enable-wait (4): the GCM is trying to enable the \
		    hardware interface and is waiting for the response \
		    from the Signaling CM. \
                  deferred(5):the activation of link is being deferred \
                    for 1 minute.
                  protocol-down(6):this indicates PLM or MSM is down.\
		  activating (7): the activation of this link is in \
		    progress. \
		  active (8): the Signaling link is established. \
		  disconnecting (9): the Signaling CM deactivates \
		    this link. \
		  up (10): this link is up forever.;
		  (Operational);
	   HELP = ;
	   CAPABILITIES = ;"
	::= { mcmGcmLinkEntry 6 }

mcmGcmLinkProtoType OBJECT-TYPE
	SYNTAX	INTEGER {
		reserved (1),
		frameRelay (2)
		}
	ACCESS	read-only
	STATUS	mandatory
	DESCRIPTION
	  "NAME = ;
	   DESC = The type of the protocol. (Operational);
	   HELP = ;
	   CAPABILITIES = ;"
	::= { mcmGcmLinkEntry 7 }

mcmGcmLinkProtoPcmIndex OBJECT-TYPE
	SYNTAX	INTEGER (1..65535)
	ACCESS	read-only
	STATUS	mandatory
	DESCRIPTION
	  "NAME = ;
	   DESC = The index value that uniquely identifies an entry \
		  for the PCM.  In the case of the FRCM, this entry \
		  represents an index for the port. \
		  (Operational);
	   HELP = ;
	   CAPABILITIES = ;"
	::= { mcmGcmLinkEntry 8 }

mcmGcmLinkProtoStatus OBJECT-TYPE
	SYNTAX	INTEGER {
		cfg-error (1),
		info-wait (2),
		inactive (3),
		enable-wait (4),
		deferred (5),
		protocol-down (6),
		activating (7),
		wait-switch (8),
		switching (9),
		active (10),
		disconnecting (11),
		ever-up (12)
		}
	ACCESS	read-only
	STATUS	mandatory
	DESCRIPTION
	  "NAME = ;
	   DESC = The status of the Protocol Link: \
		  cfg-error (1): Configuration error. The protocol \
		    link is not configured or activated from the CM. \
		  info-wait (2): the GCM has sent an information \
		    request message to the CM to request the status \
		    of this link.  If the GCM receives an error message, \
		    the status will be set to cfg-error (1). \
		  inactive (3): the link is inactive. \
		  enable-wait (4): the GCM is trying to enable the \
		    hardware interface and is waiting for the response \
		    from the CM. \
                  deferred(5):the activation of link is being deferred for 1 \
                    minute. \
                  protocol-down(6):this indicates PLM or MSM is down.\
		  activating (7): the activation of this link is in progress. \
		  wait-switch (8): the switching from the backup link \
		    to the primary is delayed by the configuration. \
		  switching (9): the switching of the link is in progress. \
		  active (10): the link is established. \
		  disconnecting (11): the CM deactivates this link. \
		  up (12): this link is up forever. \
		 (Operational);
	   HELP = ;
	   CAPABILITIES = ;"
	::= { mcmGcmLinkEntry 9 }

mcmGcmLinkVoiceCalls OBJECT-TYPE
	SYNTAX	INTEGER (0..255)
	ACCESS	read-only
	STATUS	mandatory
	DESCRIPTION
	  "NAME = ;
	   DESC = The number of active voice calls. (Operational);
	   HELP = ;
	   CAPABILITIES = ;"
	::= { mcmGcmLinkEntry 10 }


--  the GCM Unit Table 
--  (Standard/Operational Parameters)

--  The GCM Unit Table is the central structure of the GCM.  Each table entry
--  depicts one unit where primary and backup links (if configured) are linked
--  together to a unit. 

mcmGcmUnitTable OBJECT-TYPE
	SYNTAX	SEQUENCE OF McmGcmUnitEntry
	ACCESS	not-accessible
	STATUS	mandatory
	DESCRIPTION
	  "NAME = ;
	   DESC = The GCM Unit Table. (Operational) ;
	   HELP = ;
	   CAPABILITIES = NET_CFG, VPN_DISP ;"
	::= {configuration 3 }

mcmGcmUnitEntry OBJECT-TYPE
	SYNTAX	McmGcmUnitEntry
	ACCESS	not-accessible
	STATUS	mandatory
	DESCRIPTION
	  "NAME = ;
	   DESC = An entry in the GCM Unit Table. \
		  (Operational) ;
	   HELP = ;
	   CAPABILITIES = ;"
	INDEX  {mcmGcmUnitIndex}
	::= {mcmGcmUnitTable 1}

McmGcmUnitEntry ::= SEQUENCE {
	mcmGcmUnitIndex			INTEGER,
	mcmGcmUnitName			DisplayString,
	mcmGcmUnitAdminStatus		INTEGER,
	mcmGcmUnitTimerAdminStatus	INTEGER,
	mcmGcmUnitSwitchType		INTEGER,
	mcmGcmUnitSwitchDelay		INTEGER,
	mcmGcmUnitPrimaryLinkIndex	INTEGER,
	mcmGcmUnitBackupRemainTime	INTEGER,
        mcmGcmUnitBackupSwitchDelay     INTEGER,
        mcmGcmUnitPrimarySwitchDelay    INTEGER,
        mcmGcmUnitRegionalLinkIndex     INTEGER,
        mcmGcmUnitModeCfg               INTEGER,
        mcmGcmUnitPriLinkFailMonStatus  INTEGER,
        mcmGcmUnitPriLinkFailMonDurMin  INTEGER,
        mcmGcmUnitPriLinkFailMonThrshld INTEGER,
        mcmGcmUnitPriLinkFailMonCount   INTEGER,
        mcmGcmUnitCmd                   INTEGER
	}

mcmGcmUnitIndex OBJECT-TYPE
	SYNTAX	INTEGER (1..3)
	ACCESS	read-only
	STATUS	mandatory
	DESCRIPTION
	  "NAME = ;
	   DESC = The index value which uniquely identifies an \
		  entry in the GCM Unit Table. (Operational);
	   HELP = ;
	   CAPABILITIES = ;"
	::= { mcmGcmUnitEntry 1 }

mcmGcmUnitName OBJECT-TYPE
	SYNTAX	DisplayString (SIZE (1..15))
	ACCESS	read-only
	STATUS	mandatory
	DESCRIPTION
	  "NAME = ;
	   DESC = The name of the GCM Unit.  Default value is \
		  'gcmUnit <mcmGcmUnitIndex>'. (Operational);
	   HELP = ;
	   CAPABILITIES = ;"
	::= { mcmGcmUnitEntry 2 }

mcmGcmUnitAdminStatus OBJECT-TYPE
	SYNTAX	INTEGER {
		down (1),
		up (2)
		}
	ACCESS	read-only
	STATUS	mandatory
	DESCRIPTION
	  "NAME = ;
	   DESC = The value shows the administration status of \
		  the GCM Unit.  If the status is set to down (1), \
		  the administration is disabled for this unit and \
		  all associated links.  Only when the status is \
		  up (2), the GCM controls and administrates this \
		  unit. (Operational);
	   HELP = ;
	   CAPABILITIES = ;"
	::= { mcmGcmUnitEntry 3 }

mcmGcmUnitTimerAdminStatus OBJECT-TYPE
	SYNTAX	INTEGER {
		enabled (1),
		disabled (2)
		}
	ACCESS	read-only
	STATUS	mandatory
	DESCRIPTION
	  "NAME = ;
	   DESC = The GCM Unit timer status.  When set to enabled (1), \
		  the GCM checks the configured timer entries. \
		  (Operational);
	   HELP = ;
	   CAPABILITIES = ;"
	::= { mcmGcmUnitEntry 4 }

mcmGcmUnitSwitchType OBJECT-TYPE
	SYNTAX	INTEGER {
		fast-switch (1),
		voice-switch (2),
                manual-switch-backup (3),
                manual-switching (4)
		}
	ACCESS	read-only
	STATUS	mandatory
	DESCRIPTION
	  "NAME = ;
	   DESC = The type of the switching algorithm. \
		  fast-switch (1): the GCM deactivates the backup \
		    link after the primary link is re-established \
		    regardless of the backup transmission activity. \
		  voice-switch (2): the backup link will be deactivated \
		    after the primary link is re-established and all voice \
		    calls over the backup link are disconnected. \
                  manual-switch-backup(3): the GCM switches to the \
                    backup in case of the primary failure. The switching \
                    back to the primary port mst be done manually.\
                  manual-switch(4): the GCM could be manually switch \
                    only.\
		  (Operational);
	   HELP = ;
	   CAPABILITIES = ;"
	::= { mcmGcmUnitEntry 5 }

mcmGcmUnitSwitchDelay OBJECT-TYPE
	SYNTAX	INTEGER (0..255)
	ACCESS	read-only
	STATUS	deprecated
	DESCRIPTION
	  "NAME = ;
	   DESC = NOTE THAT THIS OBJECT IS DEPRECATED. It's  \
                  functionality has been replaced by \
                  mcmGcmUnitBackupSwitchDelay object. \

                  The number of minutes that the switching from \
		  the active backup link to the active primary link \
		  has to be delayed. (Operational);
	   HELP = ;
	   CAPABILITIES = ;"
	::= { mcmGcmUnitEntry 6 }

mcmGcmUnitPrimaryLinkIndex OBJECT-TYPE
	SYNTAX	INTEGER (1..255)
	ACCESS	read-only
	STATUS	mandatory
	DESCRIPTION
	  "NAME = ;
	   DESC = The index value that uniquely identifies an entry \
		  in the GCM Link Table as the primary link. \
		  (Operational);
	   HELP = ;
	   CAPABILITIES = ;"
	::= { mcmGcmUnitEntry 7 }

mcmGcmUnitBackupRemainTime OBJECT-TYPE
	SYNTAX	INTEGER (0..255)
	ACCESS	read-only
	STATUS	mandatory
	DESCRIPTION
	  "NAME = ;
	   DESC = The maximum number of minutes that the backup link \
		  remains active after the switching from the backup \
		  to the primary.  This object will be used if the \
		  object mcmGcmUnitSwitchType is set to \
		  voice-switch (2). (Operational);
	   HELP = ;
	   CAPABILITIES = ;"
	::= { mcmGcmUnitEntry 8 }

mcmGcmUnitBackupSwitchDelay OBJECT-TYPE
	SYNTAX	INTEGER (0..255)
	ACCESS	read-only
	STATUS	mandatory
	DESCRIPTION
	  "NAME = ;
	   DESC = The number of minutes the switching \
                  has to be delayed before switching \
                  to the primary link.(Operational);
	   HELP = ;
	   CAPABILITIES = ;"
	::= { mcmGcmUnitEntry 9 }

mcmGcmUnitPrimarySwitchDelay OBJECT-TYPE
	SYNTAX	INTEGER (0..255)
	ACCESS	read-only
	STATUS	mandatory
	DESCRIPTION
	  "NAME = ;
	   DESC = The number of minutes the switching has \
		  to be delayed before switching to the \
		  backup link. (Operational);
	   HELP = ;
	   CAPABILITIES = ;"
	::= { mcmGcmUnitEntry 10 }

mcmGcmUnitRegionalLinkIndex OBJECT-TYPE
	SYNTAX	INTEGER (1..255)
	ACCESS	read-only
	STATUS	mandatory
	DESCRIPTION
	  "NAME = ;
	   DESC = The index value that uniquely identifies an entry \
		  in the GCM Link Table as the regional link index. \
                  This GCM link is activated only during the down \
                  time of the backup link.
		  (Operational);
	   HELP = ;
	   CAPABILITIES = ;"
	::= { mcmGcmUnitEntry 11 }

mcmGcmUnitModeCfg OBJECT-TYPE
	SYNTAX	INTEGER {
                branch-node       (1),
                regional-node     (2),
                central-site-node (3)
                }
	ACCESS	read-only
	STATUS	mandatory
	DESCRIPTION
	  "NAME = ;
	   DESC = branch-node(1): The GCM will try to \
                    to activate at first the primary \
                    link. In the case of a failure, \
                    the GCM will activate one of the \
		    the backup links. During the time \
                    the primary link is active, the \
                    backup port is deactivated.
                  regional-node(2): This mode is \
                    identical to the branch-mode(1) \
                    except the backup link is not used.\
                    When the primary link is active, the \
                    GCM will not deactivate the backup \
                    port.  If the backup port is an \
                    ISDN card, the GCM can be configured \
                    to allow incoming calls by using the \
                    link specified by the object \
                    <gcmUnitRegionalLinkIndex>. When the
                    primary link fails, the activated \
                    link <gcmUnitRegionalLinkIndex> \
                    (eg. configured for incoming connection \
                    ISDN) will be disconnected and the \
                    backup link will be activated. \
                    Note that there is no deactivation \
                    of the backup port and ISDN incomming \
                    calls can be accepted when the backup \
                    is not used for backing up the primary \
                    connection.\
                  central-site-node(3):Will not have a 
                    MPANL DTE connection.  There is no \
                    need to have the backup functionality. \
                    The GCM will enable both ports. \
                    In the case of ISDN, it is possible \
                    to accept incomming calls. Primary link \
                    and backup link will have the same \
                    priority, there is no correlation \
                    between them. The GCM will activate \
                    all GCM links configured for this unit.
		  (Operational);
	   HELP = ;
	   CAPABILITIES = ;"
	::= { mcmGcmUnitEntry 12 }

mcmGcmUnitPriLinkFailMonStatus OBJECT-TYPE
	SYNTAX	INTEGER {
                enabled  (1),
                disabled (2)
                }
	ACCESS	read-only
	STATUS	mandatory
	DESCRIPTION
	  "NAME = ;
	   DESC = The GCM link failure monitor \
                  status. \
                  (Operational);
	   HELP = ;
	   CAPABILITIES = ;"
	::= { mcmGcmUnitEntry 13 }

mcmGcmUnitPriLinkFailMonDurMin OBJECT-TYPE
	SYNTAX	INTEGER (1..255)
	ACCESS	read-only
	STATUS	mandatory
	DESCRIPTION
	  "NAME = ;
	   DESC = The number of minutes to monitor \
                  gcmLinkFailureMonitorThreshold(below)\
                  activity.  The duration timer \
                  starts when first link failure \
                  occured while the  \
                  gcmLinkFailureMonStatus(above) is \
                  enabled(1). \
                  (Operational);
	   HELP = ;
	   CAPABILITIES = ;"
	::= { mcmGcmUnitEntry 14 }

mcmGcmUnitPriLinkFailMonThrshld OBJECT-TYPE
	SYNTAX	INTEGER (1..255)
	ACCESS	read-only
	STATUS	mandatory
	DESCRIPTION
	  "NAME = ;
	   DESC = The maximum number of \
                  gcmLinkFailureMonCount(below) \
                  within gcmLinkFailureMonDurMin \
                  (above)before switching from primary \ 
                  to backup.\
                  (Operational);
	   HELP = ;
	   CAPABILITIES = ;"
	::= { mcmGcmUnitEntry 15 }

mcmGcmUnitPriLinkFailMonCount OBJECT-TYPE
	SYNTAX	INTEGER (1..255)
	ACCESS	read-only
	STATUS	mandatory
	DESCRIPTION
	  "NAME = ;
	   DESC = The number of link failures within \
                  gcmLinkFailureMonitorDurMin(above). \
	   HELP = ;
	   CAPABILITIES = ;"
	::= { mcmGcmUnitEntry 16 }

mcmGcmUnitCmd OBJECT-TYPE
	SYNTAX	INTEGER {
                switch-to-primary (1),
                switch-to-backup  (2)
                }
	ACCESS	write-only
	STATUS	mandatory
	DESCRIPTION
	  "NAME = ;
	   DESC = Switches the units link from primary to \
                  backup (1) or backup to primary (2)  \
	   HELP = ;
	   CAPABILITIES = ;"
	::= { mcmGcmUnitEntry 17 }


--  the GCM Backup Configuration Table 
--  (Standard/Operational Parameters)

--  This table contains the GCM Links for the backup medium.

mcmGcmBackupCfgTable OBJECT-TYPE
	SYNTAX	SEQUENCE OF McmGcmBackupCfgEntry
	ACCESS	not-accessible
	STATUS	mandatory
	DESCRIPTION
	  "NAME = ;
	   DESC = The GCM Backup Configuration Table. \
		  (Operational) ;
	   HELP = ;
	   CAPABILITIES = NET_CFG, VPN_DISP ;"
	::= {configuration 4 }

mcmGcmBackupCfgEntry OBJECT-TYPE
	SYNTAX	McmGcmBackupCfgEntry
	ACCESS	not-accessible
	STATUS	mandatory
	DESCRIPTION
	  "NAME = ;
	   DESC = An entry in the GCM Backup Configuration \
		  Table. (Operational) ;
	   HELP = ;
	   CAPABILITIES = ;"
	INDEX  {mcmGcmBackupCfgIndex}
	::= {mcmGcmBackupCfgTable 1}

McmGcmBackupCfgEntry ::= SEQUENCE {
	mcmGcmBackupCfgIndex			INTEGER,
	mcmGcmBackupCfgUnitIndex		INTEGER,
	mcmGcmBackupCfgLinkIndex		INTEGER
	}

mcmGcmBackupCfgIndex OBJECT-TYPE
	SYNTAX	INTEGER (1..255)
	ACCESS	read-only
	STATUS	mandatory
	DESCRIPTION
	  "NAME = ;
	   DESC = The index value which uniquely identifies an \
		  entry in the GCM Backup Configuration Table. \
		  (Operational);
	   HELP = ;
	   CAPABILITIES = ;"
	::= { mcmGcmBackupCfgEntry 1 }

mcmGcmBackupCfgUnitIndex OBJECT-TYPE
	SYNTAX	INTEGER (1..3)
	ACCESS	read-only
	STATUS	mandatory
	DESCRIPTION
	  "NAME = ;
	   DESC = The index value that uniquely identifies an \
		  entry in the GCM Unit Table. (Operational);
	   HELP = ;
	   CAPABILITIES = ;"
	::= { mcmGcmBackupCfgEntry 2 }

mcmGcmBackupCfgLinkIndex OBJECT-TYPE
	SYNTAX	INTEGER (1..255)
	ACCESS	read-only
	STATUS	mandatory
	DESCRIPTION
	  "NAME = ;
	   DESC = The index value that uniquely identifies an \
		  entry in the GCM Link Table.  This GCM Link \
		  will be used for Backup Link activation. \
		  (Operational);
	   HELP = ;
	   CAPABILITIES = ;"
	::= { mcmGcmBackupCfgEntry 3 }


--  the GCM Timer Table 
--  (Standard/Operational Parameters)

--  The GCM Timer Table stores all timer relevant information.  Each timer entry 
--  is associated with an entry in the GCM Unit Table.  Two main timer modes are 
--  configurable, a periodic and an inactive timer.

mcmGcmTimerTable OBJECT-TYPE
	SYNTAX	SEQUENCE OF McmGcmTimerEntry
	ACCESS	not-accessible
	STATUS	mandatory
	DESCRIPTION
	  "NAME = ;
	   DESC = The GCM Timer Table. (Operational) ;
	   HELP = ;
	   CAPABILITIES = NET_CFG, VPN_DISP ;"
	::= {configuration 5 }

mcmGcmTimerEntry OBJECT-TYPE
	SYNTAX	McmGcmTimerEntry
	ACCESS	not-accessible
	STATUS	mandatory
	DESCRIPTION
	  "NAME = ;
	   DESC = An entry in the GCM Timer Table. \
		  (Operational) ;
	   HELP = ;
	   CAPABILITIES = ;"
	INDEX  {mcmGcmTimerIndex}
	::= {mcmGcmTimerTable 1}

McmGcmTimerEntry ::= SEQUENCE {
	mcmGcmTimerIndex			INTEGER,
	mcmGcmTimerUnitIndex			INTEGER,
	mcmGcmTimerInactStartHr			INTEGER,
	mcmGcmTimerInactStartMin		INTEGER,
	mcmGcmTimerInactDurationHr		INTEGER,
	mcmGcmTimerInactDurationMin		INTEGER,
	mcmGcmTimerInactMonday			INTEGER,
	mcmGcmTimerInactTuesday			INTEGER,
	mcmGcmTimerInactWednesday		INTEGER,
	mcmGcmTimerInactThursday		INTEGER,
	mcmGcmTimerInactFriday			INTEGER,
	mcmGcmTimerInactSaturday		INTEGER,
	mcmGcmTimerInactSunday			INTEGER,
	mcmGcmTimerInactPeriodic		INTEGER
	}

mcmGcmTimerIndex OBJECT-TYPE
	SYNTAX	INTEGER (1..255)
	ACCESS	read-only
	STATUS	mandatory
	DESCRIPTION
	  "NAME = ;
	   DESC = The index value which uniquely identifies an \
		  entry in the GCM Timer Table. (Operational);
	   HELP = ;
	   CAPABILITIES = ;"
	::= { mcmGcmTimerEntry 1 }

mcmGcmTimerUnitIndex OBJECT-TYPE
	SYNTAX	INTEGER (1..3)
	ACCESS	read-only
	STATUS	mandatory
	DESCRIPTION
	  "NAME = ;
	   DESC = The index value that uniquely identifies an \
		  entry into the GCM Unit Table. (Operational);
	   HELP = ;
	   CAPABILITIES = ;"
	::= { mcmGcmTimerEntry 2 }

mcmGcmTimerInactStartHr OBJECT-TYPE
	SYNTAX	INTEGER (0..23)
	ACCESS	read-only
	STATUS	mandatory
	DESCRIPTION
	  "NAME = ;
	   DESC = The hours designation to start inactivity.  The \
		  connection will be automatically disconnected \
		  if the system time is equal to the \
		  mcmGcmTimerInactStartHr/Min. \
		  Similarly, if the Inactivity Timer is configured \
                  as a periodic  timer (mcmGcmTimerInactPeriodic), \
                  this object designates the hour to start inactivity.\
                  (Operational);
	   HELP = ;
	   CAPABILITIES = ;"
	::= { mcmGcmTimerEntry 3 }

mcmGcmTimerInactStartMin OBJECT-TYPE
	SYNTAX	INTEGER (0..59)
	ACCESS	read-only
	STATUS	mandatory
	DESCRIPTION
	  "NAME = ;
	   DESC = The minutes designation to start inactivity.  The \
		  connection will be automatically disconnected \
		  if the system time is equal to the \
		  mcmGcmTimerInactStartHr/Min. \
		  If the Inactivity Timer is configured as a periodic \
		  timer (mcmGcmTimerInactPeriodic), this object \
		  designates the minute to start inactivity. \
		  (Operational);
	   HELP = ;
	   CAPABILITIES = ;"
	::= { mcmGcmTimerEntry 4 }

mcmGcmTimerInactDurationHr OBJECT-TYPE
	SYNTAX	INTEGER (0..167)
	ACCESS	read-only
	STATUS	mandatory
	DESCRIPTION
	  "NAME = ;
	   DESC = The hours designation for inactivity duration. \
		  The inactivity time duration of the GCM Unit is \
		  defined by mcmGcmTimerInactDurationHr/Min. \
		  Similarly, if the Inactivity Timer is configured as \
		  a periodic timer (mcmGcmTimerInactPeriodic), \
		  this object designates the inactive connection \
		  duration (hours) period.  (Operational);
	   HELP = ;
	   CAPABILITIES = ;"
	DEFVAL  { 0 }
	::= { mcmGcmTimerEntry 5 }

mcmGcmTimerInactDurationMin OBJECT-TYPE
	SYNTAX	INTEGER (0..59)
	ACCESS	read-only
	STATUS	mandatory
	DESCRIPTION
	  "NAME = ;
	   DESC = The minutes designation for inactivity duration. \
		  The inactivity time duration of the GCM Unit is \
		  defined by mcmGcmTimerInactDurationHr/Min. \
		  Similarly, if the Inactivity Timer is configured as \
		  a periodic timer (mcmGcmTimerInactPeriodic), \
		  this object designates the inactive connection \
		  duration (minutes) period.  (Operational);
	   HELP = ;
	   CAPABILITIES = ;"
	DEFVAL  { 0 }
	::= { mcmGcmTimerEntry 6 }

mcmGcmTimerInactMonday OBJECT-TYPE
	SYNTAX	INTEGER {
		enabled (1),
		disabled (2)
		}
	ACCESS	read-only
	STATUS	mandatory
	DESCRIPTION
	  "NAME = ;
	   DESC = Enables (1) or disables (2) the timer inactivity \
		  administration for the day Monday. \
		  (Operational);
	   HELP = ;
	   CAPABILITIES = ;"
	DEFVAL  { disabled }
	::= { mcmGcmTimerEntry 7 }

mcmGcmTimerInactTuesday OBJECT-TYPE
	SYNTAX	INTEGER {
		enabled (1),
		disabled (2)
		}
	ACCESS	read-only
	STATUS	mandatory
	DESCRIPTION
	  "NAME = ;
	   DESC = Enables (1) or disables (2) the timer inactivity \
		  administration for the day Tuesday. \
		  (Operational);
	   HELP = ;
	   CAPABILITIES = ;"
	DEFVAL  { disabled }
	::= { mcmGcmTimerEntry 8 }

mcmGcmTimerInactWednesday OBJECT-TYPE
	SYNTAX	INTEGER {
		enabled (1),
		disabled (2)
		}
	ACCESS	read-only
	STATUS	mandatory
	DESCRIPTION
	  "NAME = ;
	   DESC = Enables (1) or disables (2) the timer inactivity \
		  administration for the day Wednesday. \
		  (Operational);
	   HELP = ;
	   CAPABILITIES = ;"
	DEFVAL  { disabled }
	::= { mcmGcmTimerEntry 9 }

mcmGcmTimerInactThursday OBJECT-TYPE
	SYNTAX	INTEGER {
		enabled (1),
		disabled (2)
		}
	ACCESS	read-only
	STATUS	mandatory
	DESCRIPTION
	  "NAME = ;
	   DESC = Enables (1) or disables (2) the timer inactivity \
		  administration for the day Thursday. \
		  (Operational);
	   HELP = ;
	   CAPABILITIES = ;"
	DEFVAL  { disabled }
	::= { mcmGcmTimerEntry 10 }

mcmGcmTimerInactFriday OBJECT-TYPE
	SYNTAX	INTEGER {
		enabled (1),
		disabled (2)
		}
	ACCESS	read-only
	STATUS	mandatory
	DESCRIPTION
	  "NAME = ;
	   DESC = Enables (1) or disables (2) the timer inactivity \
		  administration for the day Friday. \
		  (Operational);
	   HELP = ;
	   CAPABILITIES = ;"
	DEFVAL  { disabled }
	::= { mcmGcmTimerEntry 11 }

mcmGcmTimerInactSaturday OBJECT-TYPE
	SYNTAX	INTEGER {
		enabled (1),
		disabled (2)
		}
	ACCESS	read-only
	STATUS	mandatory
	DESCRIPTION
	  "NAME = ;
	   DESC = Enables (1) or disables (2) the timer inactivity \
		  administration for the day Saturday. \
		  (Operational);
	   HELP = ;
	   CAPABILITIES = ;"
	DEFVAL  { disabled }
	::= { mcmGcmTimerEntry 12 }

mcmGcmTimerInactSunday OBJECT-TYPE
	SYNTAX	INTEGER {
		enabled (1),
		disabled (2)
		}
	ACCESS	read-only
	STATUS	mandatory
	DESCRIPTION
	  "NAME = ;
	   DESC = Enables (1) or disables (2) the timer inactivity \
		  administration for the day Sunday. \
		  (Operational);
	   HELP = ;
	   CAPABILITIES = ;"
	DEFVAL  { disabled }
	::= { mcmGcmTimerEntry 13 }

mcmGcmTimerInactPeriodic OBJECT-TYPE
	SYNTAX	INTEGER {
		enabled (1),
		disabled (2)
		}
	ACCESS	read-only
	STATUS	mandatory
	DESCRIPTION
	  "NAME = ;
	   DESC = Enables (1) or disables (2) the Periodic Timer \
		  inactivity administration functionality. \
		  (Operational);
	   HELP = ;
	   CAPABILITIES = ;"
	DEFVAL  { disabled }
	::= { mcmGcmTimerEntry 14 }



--  "Parallel" Configuration Parameter ("nvm") Groups/Tables


--  the GCM Global Configuration Group 
--  (Configuration Parameters)

--  This group represents the global configuration parameters for the GCM.

nvmGcmGlobalCfgGroup  OBJECT IDENTIFIER ::= { configuration 6 }

nvmGcmGlobalCfgAdminStatus OBJECT-TYPE
	SYNTAX	INTEGER {
		enabled (1),
		disabled (2)
		}
	ACCESS	read-write
	STATUS	mandatory
	DESCRIPTION
	  "NAME = ;
	   DESC = The GCM admin status: \
		  1 - GCM is enabled. \
		  2 - GCM is disabled. \
		  (Configuration);
	   HELP = ;
	   CAPABILITIES = NET_CFG, VPN_DISP ;"
	DEFVAL  { enabled }
	::= { nvmGcmGlobalCfgGroup 1 }

nvmGcmGlobalCfgTraps OBJECT-TYPE
	SYNTAX	INTEGER {
		enabled (1),
		disabled (2)
		}
	ACCESS	read-write
	STATUS	mandatory
	DESCRIPTION
	  "NAME = ;
	   DESC = This object indicates whether GCM traps will \
		  be generated or not. (Configuration);
	   HELP = ;
	   CAPABILITIES = NET_CFG, VPN_DISP ;"
	DEFVAL  { disabled }
	::= { nvmGcmGlobalCfgGroup 2 }

nvmGcmGlobalCfgAutoActSelMode OBJECT-TYPE
	SYNTAX	INTEGER {
		hwCfgAutoSelect (1),
		disabled (2)
		}
	ACCESS	read-write
	STATUS	mandatory
	DESCRIPTION
	  "NAME = ;
	   DESC = This object is used to set the mode of the unit \
		  activation after reading the configuration file. \
		  disabled (2): The GCM does not change the objects \
		    nvmGcmUnitAdminStatus in the GCM Unit \
		    table after reading the configuration file. \
		  hwCfgAutoSelect (1): After reading the configuration \
		    file, the GCM activates only one of the three GCM \
		    Units depending on the hardware configuration. \
		    The stored configuration for the object \
		    nvmGcmUnitAdminStatus will be ignored. \
		    The following association between the GCM Unit \
		    rows and hardware configuration exists: \
		    Row 1: Port 2 and (optional) 3 with Serial WAN \
		      card; Port 2 is the Primary port. \
		    Row 2: Port 2 with Serial WAN card, Port 3 with \
		      ISDN card, Port 2 is the Primary port. \
		    Row 3: Port 2 and (optional) 3 with ISDN, Port 2 \
		      is the Primary port. \
		  (Configuration);
	   HELP = ;
	   CAPABILITIES = NET_CFG, VPN_DISP ;"
	::= { nvmGcmGlobalCfgGroup 3 }


--  the GCM Link Table 
--  (Configuration Parameters)

--  All GCM Links are defined and configured in the GCM Link Table. 
--  Each GCM Link consists of a signaling link and a protocol link.  In the case 
--  of an ISDN dial up connection, the signaling link will be represented by an
--  entry in the Dial Control MIB, which uses the ISDN signaling channel 
--  (D Channel).  The protocol link can be configured to Frame Relay. 
--  The protocol PPP is not configurable for the Protocol link, because 
--  the access device does not include this protocol. It is only for future purposes.
--  
--  Each ISDN link is configured in the Dial Control MIB, including the 
--  remote ISDN address for a dial up line or the B Channel access parameter 
--  for a leased line.  Currently, the protocol link can only set to Frame Relay.
--  
--  For a serial WAN card, the signaling link has to be configured to the value 
--  unused (2) and the protocol link to Frame Relay.
--  
--  If the GCM activates an ISDN GCM Link, it first activates the associated 
--  hardware port and then the configured ISDN link.  After the ISDN connection
--  is established, the GCM sends an activation request to the Frame Relay to 
--  establish the Frame Relay over the B Channel.

nvmGcmLinkTable OBJECT-TYPE
	SYNTAX	SEQUENCE OF NvmGcmLinkEntry
	ACCESS	not-accessible
	STATUS	mandatory
	DESCRIPTION
	  "NAME = ;
	   DESC = The GCM Link Table. (Configuration) ;
	   HELP = ;
	   CAPABILITIES = NET_CFG, VPN_DISP ;"
	::= {configuration 7 }

nvmGcmLinkEntry OBJECT-TYPE
	SYNTAX	NvmGcmLinkEntry
	ACCESS	not-accessible
	STATUS	mandatory
	DESCRIPTION
	  "NAME = ;
	   DESC = An entry in the GCM Link Table. \
		  (Configuration) ;
	   HELP = ;
	   CAPABILITIES = ;"
	INDEX  {nvmGcmLinkIndex}
	::= {nvmGcmLinkTable 1}

NvmGcmLinkEntry ::= SEQUENCE {
	nvmGcmLinkIndex			INTEGER,
	nvmGcmLinkUnitIndex		INTEGER,
	nvmGcmLinkName			DisplayString,
	nvmGcmLinkSigType		INTEGER,
	nvmGcmLinkSigPcmIndex		INTEGER,
	nvmGcmLinkProtoType		INTEGER,
	nvmGcmLinkProtoPcmIndex		INTEGER,
	nvmGcmLinkRowStatus		INTEGER
	}

nvmGcmLinkIndex OBJECT-TYPE
	SYNTAX	INTEGER (1..255)
	ACCESS	read-only
	STATUS	mandatory
	DESCRIPTION
	  "NAME = ;
	   DESC = The index value which uniquely identifies an \
		  entry in the GCM Link Table. (Configuration);
	   HELP = ;
	   CAPABILITIES = ;"
	::= { nvmGcmLinkEntry 1 }

nvmGcmLinkUnitIndex OBJECT-TYPE
	SYNTAX	INTEGER (1..3)
	ACCESS	read-only
	STATUS	mandatory
	DESCRIPTION
	  "NAME = ;
	   DESC = The index value that uniquely identifies an \
		  entry in the GCM Unit Table. (Configuration);
	   HELP = ;
	   CAPABILITIES = ;"
	::= { nvmGcmLinkEntry 2 }

nvmGcmLinkName OBJECT-TYPE
	SYNTAX	DisplayString (SIZE (0..15))
	ACCESS	read-write
	STATUS	mandatory
	DESCRIPTION
	  "NAME = ;
	   DESC = The name of the GCM Link.  Default value is \
		  'gcmLink<nvmGcmLinkIndex>'. (Configuration);
	   HELP = ;
	   CAPABILITIES = ;"
	::= { nvmGcmLinkEntry 3 }

nvmGcmLinkSigType OBJECT-TYPE
	SYNTAX	INTEGER {
		reserved (1),
		isdn (2),
		unusedEver-up (3)
		}
	ACCESS	read-write
	STATUS	mandatory
	DESCRIPTION
	  "NAME = ;
	   DESC = The type of the signaling channel, if a signaling \
		  protocol is used. (Configuration);
	   HELP = ;
	   CAPABILITIES = ;"
	::= { nvmGcmLinkEntry 4 }

nvmGcmLinkSigPcmIndex OBJECT-TYPE
	SYNTAX	INTEGER (1..65535)
	ACCESS	read-write
	STATUS	mandatory
	DESCRIPTION
	  "NAME = ;
	   DESC = The index value that uniquely identifies an entry \
		  for the PCM.  In the case of the ICM, this entry \
		  represents an index for the dialCtlPeerCfgTable. \
		  (Configuration);
	   HELP = ;
	   CAPABILITIES = ;"
	::= { nvmGcmLinkEntry 5 }

nvmGcmLinkProtoType OBJECT-TYPE
	SYNTAX	INTEGER {
		reserved (1),
		frameRelay (2)
		}
	ACCESS	read-write
	STATUS	mandatory
	DESCRIPTION
	  "NAME = ;
	   DESC = The type of the protocol. (Configuration);
	   HELP = ;
	   CAPABILITIES = ;"
	::= { nvmGcmLinkEntry 6 }

nvmGcmLinkProtoPcmIndex OBJECT-TYPE
	SYNTAX	INTEGER (1..65535)
	ACCESS	read-write
	STATUS	mandatory
	DESCRIPTION
	  "NAME = ;
	   DESC = The index value that uniquely identifies an entry \
		  for the PCM.  In the case of the FRCM, this entry \
		  represents an index for a port. \
                 (Configuration);
	   HELP = ;
	   CAPABILITIES = ;"
	::= { nvmGcmLinkEntry 7 }

nvmGcmLinkRowStatus OBJECT-TYPE
	SYNTAX	INTEGER {
		add (1),
		delete (2),
                active (3)
		}
	ACCESS	read-write
	STATUS	mandatory
	DESCRIPTION
	  "NAME = ;
	   DESC = This object is used to create and delete rows in the \
		  GCM Link Table. (Configuration);
	   HELP = ;
	   CAPABILITIES = ;"
	::= { nvmGcmLinkEntry 8 }


--  the GCM Unit Table 
--  (Configuration Parameters)

--  The GCM Unit Table is the central structure of the GCM.  Each table entry
--  depicts one unit where primary and backup links (if configured) are linked
--  together to a unit.  Each entry will be administrated separately.  The 
--  configuration for the backup links is stored in the GCM Backup 
--  Configuration Table.

nvmGcmUnitTable OBJECT-TYPE
	SYNTAX	SEQUENCE OF NvmGcmUnitEntry
	ACCESS	not-accessible
	STATUS	mandatory
	DESCRIPTION
	  "NAME = ;
	   DESC = The GCM Unit Table. (Configuration) ;
	   HELP = ;
	   CAPABILITIES = NET_CFG, VPN_DISP ;"
	::= {configuration 8 }

nvmGcmUnitEntry OBJECT-TYPE
	SYNTAX	NvmGcmUnitEntry
	ACCESS	not-accessible
	STATUS	mandatory
	DESCRIPTION
	  "NAME = ;
	   DESC = An entry in the GCM Unit Table. \
		  (Configuration) ;
	   HELP = ;
	   CAPABILITIES = ;"
	INDEX  {nvmGcmUnitIndex}
	::= {nvmGcmUnitTable 1}

NvmGcmUnitEntry ::= SEQUENCE {
	nvmGcmUnitIndex			INTEGER,
	nvmGcmUnitName			DisplayString,
	nvmGcmUnitAdminStatus		INTEGER,
	nvmGcmUnitTimerAdminStatus	INTEGER,
	nvmGcmUnitSwitchType		INTEGER,
	nvmGcmUnitSwitchDelay		INTEGER,
	nvmGcmUnitPrimaryLinkIndex	INTEGER,
	nvmGcmUnitBackupRemainTime	INTEGER,
        nvmGcmUnitBackupSwitchDelay     INTEGER,
        nvmGcmUnitPrimarySwitchDelay    INTEGER,
        nvmGcmUnitRegionalLinkIndex     INTEGER,
        nvmGcmUnitModeCfg               INTEGER,
        nvmGcmUnitPriLinkFailMonStatus  INTEGER,        
        nvmGcmUnitPriLinkFailMonDurMin  INTEGER,
        nvmGcmUnitPriLinkFailMonThrshld INTEGER
	}

nvmGcmUnitIndex OBJECT-TYPE
	SYNTAX	INTEGER (1..3)
	ACCESS	read-only
	STATUS	mandatory
	DESCRIPTION
	  "NAME = ;
	   DESC = The index value which uniquely identifies an \
		  entry in the GCM Unit Table. (Configuration);
	   HELP = ;
	   CAPABILITIES = ;"
	::= { nvmGcmUnitEntry 1 }

nvmGcmUnitName OBJECT-TYPE
	SYNTAX	DisplayString (SIZE (1..15))
	ACCESS	read-write
	STATUS	mandatory
	DESCRIPTION
	  "NAME = ;
	   DESC = The name of the GCM Unit.  Default value is \
		  'gcmUnit <nvmGcmUnitIndex>'. (Configuration);
	   HELP = ;
	   CAPABILITIES = ;"
	::= { nvmGcmUnitEntry 2 }

nvmGcmUnitAdminStatus OBJECT-TYPE
	SYNTAX	INTEGER {
		down (1),
		up (2)
		}
	ACCESS	read-write
	STATUS	mandatory
	DESCRIPTION
	  "NAME = ;
	   DESC = The value shows the administration status of \
		  the GCM Unit.  If the status is set to down (1), \
		  the administration is disabled for this unit and \
		  all associated links.  Only when the status is \
		  up (2), the GCM controls and administrates this \
		  unit. (Configuration);
	   HELP = ;
	   CAPABILITIES = ;"
	::= { nvmGcmUnitEntry 3 }

nvmGcmUnitTimerAdminStatus OBJECT-TYPE
	SYNTAX	INTEGER {
		enabled (1),
		disabled (2)
		}
	ACCESS	read-write
	STATUS	mandatory
	DESCRIPTION
	  "NAME = ;
	   DESC = The GCM Unit timer status.  When set to enabled (1), \
		  the GCM checks the configured timer entries. \
		  (Configuration);
	   HELP = ;
	   CAPABILITIES = ;"
	::= { nvmGcmUnitEntry 4 }

nvmGcmUnitSwitchType OBJECT-TYPE
	SYNTAX	INTEGER {
		fast-switch (1),
		voice-switch (2),
                manual-switch-backup (3),
                manual-switching (4)
		}
	ACCESS	read-write
	STATUS	mandatory
	DESCRIPTION
	  "NAME = ;
	   DESC = The type of the switching algorithm. \
		  fast-switch (1): the GCM deactivates the backup \
		    link after the primary link is re-established \
		    regardless of the backup transmission activity. \
		  voice-switch (2): the backup link will be deactivated \
		    after the primary link is re-established and all voice \
		    calls over the backup link are disconnected. \
		    calls over the backup link are disconnected. \
                  manual-switch-backup(3): the GCM switches to the \
                    backup in case of the primary failure. The switching \
                    back to the primary port mst be done manually.\
                  manual-switch(4): the GCM could be manually switch \
                    only.\
		  (Configuration);
	   HELP = ;
	   CAPABILITIES = ;"
	::= { nvmGcmUnitEntry 5 }

nvmGcmUnitSwitchDelay OBJECT-TYPE
	SYNTAX	INTEGER (0..255)
	ACCESS	read-write
	STATUS	deprecated
	DESCRIPTION
	  "NAME = ;
	   DESC = NOTE THAT THIS OBJECT IS DEPRECATED. It's  \
                  functionality has been replaced by \
                  nmvGcmUnitBackupSwitchDelay  object. \

                  The number of minutes that the switching from \
		  the active backup link to the active primary link \
		  has to be delayed. (Operational);
	   HELP = ;
	   CAPABILITIES = ;"
	::= { nvmGcmUnitEntry 6 }

nvmGcmUnitPrimaryLinkIndex OBJECT-TYPE
	SYNTAX	INTEGER (1..255)
	ACCESS	read-write
	STATUS	mandatory
	DESCRIPTION
	  "NAME = ;
	   DESC = The index value that uniquely identifies an entry \
		  in the GCM Link Table as the primary link. \
		  (Configuration);
	   HELP = ;
	   CAPABILITIES = ;"
	::= { nvmGcmUnitEntry 7 }

nvmGcmUnitBackupRemainTime OBJECT-TYPE
	SYNTAX	INTEGER (0..255)
	ACCESS	read-write
	STATUS	mandatory
	DESCRIPTION
	  "NAME = ;
	   DESC = The maximum number of minutes that the backup link \
		  remains active after the switching from the backup \
		  to the primary.  This object will be used if the \
		  object mcmGcmUnitSwitchType is set to \
		  voice-switch (2). (Configuration);
	   HELP = ;
	   CAPABILITIES = ;"
	::= { nvmGcmUnitEntry 8 }

nvmGcmUnitBackupSwitchDelay OBJECT-TYPE
	SYNTAX	INTEGER (0..255)
	ACCESS	read-write
	STATUS	mandatory
	DESCRIPTION
	  "NAME = ;
	   DESC = The number of minutes the switching \
                  has to be delayed before switching \
                  to the primary link.(Configuration);
	   HELP = ;
	   CAPABILITIES = ;"
	::= { nvmGcmUnitEntry 9 }

nvmGcmUnitPrimarySwitchDelay OBJECT-TYPE
	SYNTAX	INTEGER (0..255)
	ACCESS	read-write
	STATUS	mandatory
	DESCRIPTION
	  "NAME = ;
	   DESC = The number of minutes the switching has \
		  to be delayed before switching to the \
		  backup link. (Configuration);
	   HELP = ;
	   CAPABILITIES = ;"
	::= { nvmGcmUnitEntry 10 }

nvmGcmUnitRegionalLinkIndex OBJECT-TYPE
	SYNTAX	INTEGER (1..255)
	ACCESS	read-write
	STATUS	mandatory
	DESCRIPTION
	  "NAME = ;
	   DESC = The index value that uniquely identifies an entry \
		  in the GCM Link Table as the regional link index. \
                  This GCM link is activated only during the down \
                  time of the backup link.\
		  (Configuration);
	   HELP = ;
	   CAPABILITIES = ;"
	::= { nvmGcmUnitEntry 11 }

nvmGcmUnitModeCfg OBJECT-TYPE
	SYNTAX	INTEGER {
                branch-node       (1),
                regional-node     (2),
                central-site-node (3)
                }
	ACCESS	read-write
	STATUS	mandatory
	DESCRIPTION
	  "NAME = ;
	   DESC = branch-node(1): The GCM will try to \
                    to activate at first the primary \
                    link. In the case of a failure, \
                    the GCM will activate one of the \
		    the backup links. During the time \
                    the primary link is active, the \
                    backup port is deactivated.
                  regional-node(2): This mode is \
                    identical to the branch-mode(1) \
                    except the backup link is not used.\
                    When the primary link is active, the \
                    GCM will not deactivate the backup \
                    port.  If the backup port is an \
                    ISDN card, the GCM can be configured \
                    to allow incoming calls by using the \
                    link specified by the object \
                    <gcmUnitRegionalLinkIndex>. When the
                    primary link fails, the activated \
                    link <gcmUnitRegionalLinkIndex> \
                    (eg. configured for incoming connection \
                    ISDN) will be disconnected and the \
                    backup link will be activated. \
                    Note that there is no deactivation \
                    of the backup port and ISDN incomming \
                    calls can be accepted when the backup \
                    is not used for backing up the primary \
                    connection.\
                  central-site-node(3):Will not have a 
                    MPANL DTE connection.  There is no \
                    need to have the backup functionality. \
                    The GCM will enable both ports. \
                    In the case of ISDN, it is possible \
                    to accept incomming calls. Primary link \
                    and backup link will have the same \
                    priority, there is no correlation \
                    between them. The GCM will activate \
                    all GCM links configured for this unit.
		   (Configuration);
	   HELP = ;
	   CAPABILITIES = ;"
	::= { nvmGcmUnitEntry 12 }

nvmGcmUnitPriLinkFailMonStatus OBJECT-TYPE
	SYNTAX	INTEGER {
                enabled  (1),
                disabled (2)
                }
	ACCESS	read-write
	STATUS	mandatory
	DESCRIPTION
	  "NAME = ;
	   DESC = The GCM link failure monitor \
                  status. \
                  (Configuration);
	   HELP = ;
	   CAPABILITIES = ;"
	::= { nvmGcmUnitEntry 13 }

nvmGcmUnitPriLinkFailMonDurMin OBJECT-TYPE
	SYNTAX	INTEGER (1..255)
	ACCESS	read-write
	STATUS	mandatory
	DESCRIPTION
	  "NAME = ;
	   DESC = The number of minutes to monitor \
                  gcmLinkFailureMonThreshold  \
                  activity.  The duration timer \
                  starts when first link failure \
                  occured while the  \
                  gcmLinkFailureMonStatus is \
                  enabled(1). \
                  (Configuration);
	   HELP = ;
	   CAPABILITIES = ;"
	::= { nvmGcmUnitEntry 14 }

nvmGcmUnitPriLinkFailMonThrshld OBJECT-TYPE
	SYNTAX	INTEGER (1..255)
	ACCESS	read-write
	STATUS	mandatory
	DESCRIPTION
	  "NAME = ;
	   DESC = The maximum number of \
                  gcmLinkFailureMonCount(below) \
                  within gcmLinkFailureMonDurMin \
                  (above)before switching from primary \ 
                  to backup.\
                  (Configuration);
	   HELP = ;
	   CAPABILITIES = ;"
	::= { nvmGcmUnitEntry 15 }



--  the GCM Backup Configuration Table 
--  (Configuration Parameters)

--  The GCM Links for the backup medium will be stored in the GCM Backup 
--  Configuration Table.  During configuration of the access device via an NMS or CLI, 
--  the administrator can decide which of the two ports will be the backup or the 
--  primary port.  The GCM is flexible to handle this kind of configuration.
--  
--  Also, the GCM allows configuration of multiple (up to 255) backup link rows
--  for a single GCM Unit.  If the primary link fails, the GCM tries to re-establish 
--  the connection over the backup medium by trying all backup links successively.
--  
--  An erroneous configuration (e.g., unknown Signaling links in the ISDN Dial 
--  Control MIB) will only be detected during the loading of the GCM configuration 
--  file, and intercommunication between the GCM and the Circuit Managers.

nvmGcmBackupCfgTable OBJECT-TYPE
	SYNTAX	SEQUENCE OF NvmGcmBackupCfgEntry
	ACCESS	not-accessible
	STATUS	mandatory
	DESCRIPTION
	  "NAME = ;
	   DESC = The GCM Backup Configuration Table. \
		  (Configuration) ;
	   HELP = ;
	   CAPABILITIES = NET_CFG, VPN_DISP ;"
	::= {configuration 9 }

nvmGcmBackupCfgEntry OBJECT-TYPE
	SYNTAX	NvmGcmBackupCfgEntry
	ACCESS	not-accessible
	STATUS	mandatory
	DESCRIPTION
	  "NAME = ;
	   DESC = An entry in the GCM Backup Configuration \
		  Table. (Configuration) ;
	   HELP = ;
	   CAPABILITIES = ;"
	INDEX  {nvmGcmBackupCfgIndex}
	::= {nvmGcmBackupCfgTable 1}

NvmGcmBackupCfgEntry ::= SEQUENCE {
	nvmGcmBackupCfgIndex			INTEGER,
	nvmGcmBackupCfgUnitIndex		INTEGER,
	nvmGcmBackupCfgLinkIndex		INTEGER,
	nvmGcmBackupCfgLinkRowStatus		INTEGER
	}

nvmGcmBackupCfgIndex OBJECT-TYPE
	SYNTAX	INTEGER (1..255)
	ACCESS	read-only
	STATUS	mandatory
	DESCRIPTION
	  "NAME = ;
	   DESC = The index value which uniquely identifies an \
		  entry in the GCM Backup Configuration Table. \
		  (Configuration);
	   HELP = ;
	   CAPABILITIES = ;"
	::= { nvmGcmBackupCfgEntry 1 }

nvmGcmBackupCfgUnitIndex OBJECT-TYPE
	SYNTAX	INTEGER (1..3)
	ACCESS	read-write
	STATUS	mandatory
	DESCRIPTION
	  "NAME = ;
	   DESC = The index value that uniquely identifies an \
		  entry in the GCM Unit Table. (Configuration);
	   HELP = ;
	   CAPABILITIES = ;"
	::= { nvmGcmBackupCfgEntry 2 }

nvmGcmBackupCfgLinkIndex OBJECT-TYPE
	SYNTAX	INTEGER (1..255)
	ACCESS	read-write
	STATUS	mandatory
	DESCRIPTION
	  "NAME = ;
	   DESC = The index value that uniquely identifies an \
		  entry in the GCM Link Table.  This GCM Link \
		  will be used for Backup Link activation. \
		  (Configuration);
	   HELP = ;
	   CAPABILITIES = ;"
	::= { nvmGcmBackupCfgEntry 3 }

nvmGcmBackupCfgLinkRowStatus OBJECT-TYPE
	SYNTAX	INTEGER {
		add (1),
		delete (2),
                active (3)
		}
	ACCESS	read-write
	STATUS	mandatory
	DESCRIPTION
	  "NAME = ;
	   DESC = This object is used to create and delete rows \
		  in the GCM Backup Configuration Table. \
		  (Configuration);
	   HELP = ;
	   CAPABILITIES = ;"
	::= { nvmGcmBackupCfgEntry 4 }


--  the GCM Timer Table 
--  (Configuration Parameters)

--  The GCM Timer Table stores all timer relevant information.  Each timer entry 
--  is associated with an entry in the GCM Unit Table.  Two main timer modes are 
--  configurable, a periodic and an inactive timer.

nvmGcmTimerTable OBJECT-TYPE
	SYNTAX	SEQUENCE OF NvmGcmTimerEntry
	ACCESS	not-accessible
	STATUS	mandatory
	DESCRIPTION
	  "NAME = ;
	   DESC = The GCM Timer Table. (Configuration) ;
	   HELP = ;
	   CAPABILITIES = NET_CFG, VPN_DISP ;"
	::= {configuration 10 }

nvmGcmTimerEntry OBJECT-TYPE
	SYNTAX	NvmGcmTimerEntry
	ACCESS	not-accessible
	STATUS	mandatory
	DESCRIPTION
	  "NAME = ;
	   DESC = An entry in the GCM Timer Table. \
		  (Configuration) ;
	   HELP = ;
	   CAPABILITIES = ;"
	INDEX  {nvmGcmTimerIndex}
	::= {nvmGcmTimerTable 1}

NvmGcmTimerEntry ::= SEQUENCE {
	nvmGcmTimerIndex			INTEGER,
	nvmGcmTimerUnitIndex			INTEGER,
	nvmGcmTimerInactStartHr			INTEGER,
	nvmGcmTimerInactStartMin		INTEGER,
	nvmGcmTimerInactDurationHr		INTEGER,
	nvmGcmTimerInactDurationMin		INTEGER,
	nvmGcmTimerInactMonday			INTEGER,
	nvmGcmTimerInactTuesday			INTEGER,
	nvmGcmTimerInactWednesday		INTEGER,
	nvmGcmTimerInactThursday		INTEGER,
	nvmGcmTimerInactFriday			INTEGER,
	nvmGcmTimerInactSaturday		INTEGER,
	nvmGcmTimerInactSunday			INTEGER,
	nvmGcmTimerInactPeriodic		INTEGER,
	nvmGcmTimerRowStatus			INTEGER
	}

nvmGcmTimerIndex OBJECT-TYPE
	SYNTAX	INTEGER (1..255)
	ACCESS	read-only
	STATUS	mandatory
	DESCRIPTION
	  "NAME = ;
	   DESC = The index value which uniquely identifies an \
		  entry in the GCM Timer Table. (Configuration);
	   HELP = ;
	   CAPABILITIES = ;"
	::= { nvmGcmTimerEntry 1 }

nvmGcmTimerUnitIndex OBJECT-TYPE
	SYNTAX	INTEGER (1..3)
	ACCESS	read-write
	STATUS	mandatory
	DESCRIPTION
	  "NAME = ;
	   DESC = The index value that uniquely identifies an \
		  entry into the GCM Unit Table. (Configuration);
	   HELP = ;
	   CAPABILITIES = ;"
	::= { nvmGcmTimerEntry 2 }

nvmGcmTimerInactStartHr OBJECT-TYPE
	SYNTAX	INTEGER (0..23)
	ACCESS	read-write
	STATUS	mandatory
	DESCRIPTION
	  "NAME = ;
	   DESC = The hours designation to start inactivity.  The \
		  connection will be automatically disconnected \
		  if the system time is equal to the \
		  nvmGcmTimerInactStartHr/Min. \
		  Similarly, if the Inactivity Timer is configured \
                  as a periodic timer (nvmGcmTimerInactPeriodic), \
                  this object designates the hour to start inactivity. \
		  (Configuration);
	   HELP = ;
	   CAPABILITIES = ;"
	::= { nvmGcmTimerEntry 3 }

nvmGcmTimerInactStartMin OBJECT-TYPE
	SYNTAX	INTEGER (0..59)
	ACCESS	read-write
	STATUS	mandatory
	DESCRIPTION
	  "NAME = ;
	   DESC = The minutes designation to start inactivity.  The \
		  connection will be automatically disconnected \
		  if the system time is equal to the \
		  nvmGcmTimerInactStartHr/Min. \
		  Similarly, if the Inactivity Timer is configured \
                  as a periodic timer (nvmGcmTimerInactPeriodic), \
                  this object designates the minute to start inactivity.\
                  (Configuration);
	   HELP = ;
	   CAPABILITIES = ;"
	::= { nvmGcmTimerEntry 4 }

nvmGcmTimerInactDurationHr OBJECT-TYPE
	SYNTAX	INTEGER (0..167)
	ACCESS	read-write
	STATUS	mandatory
	DESCRIPTION
	  "NAME = ;
	   DESC = The hours designation for inactivity duration. \
		  The inactivity time duration of the GCM Unit is \
		  defined by nvmGcmTimerInactDurationHr/Min. \
		  Similarly, if the Inactivity Timer is configured as \
		  a periodic timer (nvmGcmTimerInactPeriodic), \
		  this object designates the inactive connection \
		  duration (hours) period.  (Configuration);
	   HELP = ;
	   CAPABILITIES = ;"
	DEFVAL  { 0 }
	::= { nvmGcmTimerEntry 5 }

nvmGcmTimerInactDurationMin OBJECT-TYPE
	SYNTAX	INTEGER (0..59)
	ACCESS	read-write
	STATUS	mandatory
	DESCRIPTION
	  "NAME = ;
	   DESC = The minutes designation for inactivity duration. \
		  The inactivity time duration of the GCM Unit is \
		  defined by nvmGcmTimerInactDurationHr/Min. \
		  Similarly, if the Inactivity Timer is configured as \
		  a periodic timer (nvmGcmTimerInactPeriodic), \
		  this object designates the inactive connection \
		  duration (minutes) period.  (Configuration);
	   HELP = ;
	   CAPABILITIES = ;"
	DEFVAL  { 0 }
	::= { nvmGcmTimerEntry 6 }

nvmGcmTimerInactMonday OBJECT-TYPE
	SYNTAX	INTEGER {
		enabled (1),
		disabled (2)
		}
	ACCESS	read-write
	STATUS	mandatory
	DESCRIPTION
	  "NAME = ;
	   DESC = Enables (1) or disables (2) the timer inactivity \
		  administration for the day Monday. \
		  (Configuration);
	   HELP = ;
	   CAPABILITIES = ;"
	DEFVAL  { disabled }
	::= { nvmGcmTimerEntry 7 }

nvmGcmTimerInactTuesday OBJECT-TYPE
	SYNTAX	INTEGER {
		enabled (1),
		disabled (2)
		}
	ACCESS	read-write
	STATUS	mandatory
	DESCRIPTION
	  "NAME = ;
	   DESC = Enables (1) or disables (2) the timer inactivity \
		  administration for the day Tuesday. \
		  (Configuration);
	   HELP = ;
	   CAPABILITIES = ;"
	DEFVAL  { disabled }
	::= { nvmGcmTimerEntry 8 }

nvmGcmTimerInactWednesday OBJECT-TYPE
	SYNTAX	INTEGER {
		enabled (1),
		disabled (2)
		}
	ACCESS	read-write
	STATUS	mandatory
	DESCRIPTION
	  "NAME = ;
	   DESC = Enables (1) or disables (2) the timer inactivity \
		  administration for the day Wednesday. \
		  (Configuration);
	   HELP = ;
	   CAPABILITIES = ;"
	DEFVAL  { disabled }
	::= { nvmGcmTimerEntry 9 }

nvmGcmTimerInactThursday OBJECT-TYPE
	SYNTAX	INTEGER {
		enabled (1),
		disabled (2)
		}
	ACCESS	read-write
	STATUS	mandatory
	DESCRIPTION
	  "NAME = ;
	   DESC = Enables (1) or disables (2) the timer inactivity \
		  administration for the day Thursday. \
		  (Configuration);
	   HELP = ;
	   CAPABILITIES = ;"
	DEFVAL  { disabled }
	::= { nvmGcmTimerEntry 10 }

nvmGcmTimerInactFriday OBJECT-TYPE
	SYNTAX	INTEGER {
		enabled (1),
		disabled (2)
		}
	ACCESS	read-write
	STATUS	mandatory
	DESCRIPTION
	  "NAME = ;
	   DESC = Enables (1) or disables (2) the timer inactivity \
		  administration for the day Friday. \
		  (Configuration);
	   HELP = ;
	   CAPABILITIES = ;"
	DEFVAL  { disabled }
	::= { nvmGcmTimerEntry 11 }

nvmGcmTimerInactSaturday OBJECT-TYPE
	SYNTAX	INTEGER {
		enabled (1),
		disabled (2)
		}
	ACCESS	read-write
	STATUS	mandatory
	DESCRIPTION
	  "NAME = ;
	   DESC = Enables (1) or disables (2) the timer inactivity \
		  administration for the day Saturday. \
		  (Configuration);
	   HELP = ;
	   CAPABILITIES = ;"
	DEFVAL  { disabled }
	::= { nvmGcmTimerEntry 12 }

nvmGcmTimerInactSunday OBJECT-TYPE
	SYNTAX	INTEGER {
		enabled (1),
		disabled (2)
		}
	ACCESS	read-write
	STATUS	mandatory
	DESCRIPTION
	  "NAME = ;
	   DESC = Enables (1) or disables (2) the timer inactivity \
		  administration for the day Sunday. \
		  (Configuration);
	   HELP = ;
	   CAPABILITIES = ;"
	DEFVAL  { disabled }
	::= { nvmGcmTimerEntry 13 }

nvmGcmTimerInactPeriodic OBJECT-TYPE
	SYNTAX	INTEGER {
		enabled (1),
		disabled (2)
		}
	ACCESS	read-write
	STATUS	mandatory
	DESCRIPTION
	  "NAME = ;
	   DESC = Enables (1) or disables (2) the Periodic Timer \
		  inactivity administration functionality. \
		  (Configuration);
	   HELP = ;
	   CAPABILITIES = ;"
	DEFVAL  { disabled }
	::= { nvmGcmTimerEntry 14 }

nvmGcmTimerRowStatus OBJECT-TYPE
	SYNTAX	INTEGER {
		add (1),
		delete (2),
                active (3)
		}
	ACCESS	read-write
	STATUS	mandatory
	DESCRIPTION
	  "NAME = ;
	   DESC = This object is used to create and delete rows \
		  in the GCM Timer Table. (Configuration);
	   HELP = ;
	   CAPABILITIES = ;"
	::= { nvmGcmTimerEntry 15 }



-- *** STATUS groups/tables ***

--  Operational Parameter ("mcm") Groups/Tables (note: no parallel "nvm" objects
--  are defined for STATUS parameters.)


--  the GCM Hardware Status Table 

--  Each hardware interface controlled by the GCM is defined in the GCM Hardware 
--  Status table.  The GCM does not allow changes to any states in the table by the SNMP
--  agent (the table is controlled solely by the GCM). The table serves only for 
--  representation and not for administration.
--  Each hardware interface is represented by an entry in this table.  The table is a fixed,
--  read-only table with six rows.  Each entry represents the status of a hardware interface.

mcmGcmHwStatusTable OBJECT-TYPE
	SYNTAX	SEQUENCE OF McmGcmHwStatusEntry
	ACCESS	not-accessible
	STATUS	mandatory
	DESCRIPTION
	  "NAME = ;
	   DESC = The GCM Hardware Status Table.;
	   HELP = ;
	   CAPABILITIES = NET_CFG, VPN_DISP ;"
	::= {status 1 }

mcmGcmHwStatusEntry OBJECT-TYPE
	SYNTAX	McmGcmHwStatusEntry
	ACCESS	not-accessible
	STATUS	mandatory
	DESCRIPTION
	  "NAME = ;
	   DESC = An entry in the GCM Hardware Status \
		  Table.;
	   HELP = ;
	   CAPABILITIES = ;"
	INDEX  {mcmGcmHwStatusIndex}
	::= {mcmGcmHwStatusTable 1}

McmGcmHwStatusEntry ::= SEQUENCE {
	mcmGcmHwStatusIndex			INTEGER,
	mcmGcmHwStatusDesc			DisplayString,
	mcmGcmHwStatusOperStatus		INTEGER,
	mcmGcmHwStatusActiveLink		INTEGER
	}

mcmGcmHwStatusIndex OBJECT-TYPE
	SYNTAX	INTEGER {
		everDown (1),
		everUp (2),
		isdnPrimary (3),
		isdnBackup (4),
		frPrimary (5),
		frBackup (6)
		}
	ACCESS	read-only
	STATUS	mandatory
	DESCRIPTION
	  "NAME = ;
	   DESC = The index value that uniquely identifies an entry \
		  in the GCM Hardware Status table.  The first two \
		  entries are internal ports.  Entry 1 describes a port \
		  that is ever down.   The second entry is an ever-up \
		  port.  The GCM will not change the status of these \
		  two ports.  They are not connected to any physical \
		  interface.  To change the status of the other entries, \
		  the GCM communicates with associated PCM.;
	   HELP = ;
	   CAPABILITIES = ;"
	::= { mcmGcmHwStatusEntry 1 }

mcmGcmHwStatusDesc OBJECT-TYPE
	SYNTAX	DisplayString (SIZE(0..15))
	ACCESS	read-only
	STATUS	mandatory
	DESCRIPTION
	  "NAME = ;
	   DESC = The name of the GCM Hardware Interface.;
	   HELP = ;
	   CAPABILITIES = ;"
	::= { mcmGcmHwStatusEntry 2 }

mcmGcmHwStatusOperStatus OBJECT-TYPE
	SYNTAX	INTEGER {
		ever-down (1),
		up (2),
		ever-up (3),
		down (4),
		enable-req (5),
		disable-req (6),
		link-error (7)
		}
	ACCESS	read-only
	STATUS	mandatory
	DESCRIPTION
	  "NAME = ;
	   DESC = The status of the Hardware interface.  After \
		  reset the normal status of an entry is down (4). \
		  To activate the hardware port, the GCM sends \
		  a message to the PCM and changes the status to \
		  enable-req(5).  A positive activation changes the \
		  status to up(2).  If the activation fails (e.g., no \
		  cable is plugged in), the status will be set to \
		  link-error(7).  Only in this state, the PCM monitors \
		  the status of the port.  In the state down(4), the \
		  PCM does not monitor the port status.;
	   HELP = ;
	   CAPABILITIES = ;"
	::= { mcmGcmHwStatusEntry 3 }

mcmGcmHwStatusActiveLink OBJECT-TYPE
	SYNTAX	INTEGER (0..65535)
	ACCESS	read-only
	STATUS	mandatory
	DESCRIPTION
	  "NAME = ;
	   DESC = The number of active GCM links on this Hardware \
		  port.;
	   HELP = ;
	   CAPABILITIES = ;"
	::= { mcmGcmHwStatusEntry 4 }


-- *** TRAP Messages ***
mcmGCMPriLinkDownCausedByPhysicalConnection TRAP-TYPE
	ENTERPRISE	micom-gcm
	VARIABLES	{ mcmSysAsciiTimeOfDay, mcmGcmLinkIndex, 
                          mcmGcmLinkName, mcmGcmLinkSigType,
                          mcmGcmLinkSigPcmIndex, mcmGcmLinkProtoType, 
                          mcmGcmLinkProtoPcmIndex }
	DESCRIPTION
	  "NAME = ;
	   DESC = This trap will be generated from the GCM,\
                  if a GCM Link changes the state from UP to \
                  DOWN.  The GCM Link is configured as primary \
                  link.  The disconnection is caused by the loss\
                  of the physical connection.\
                  Severity Level: CRITICAL ;
           HELP = Loss of primary link Physical conenction. Check \
                  the cabling. Possible signalling problem with ISDN \
                  D-channel, or Frame Relay protocol error.\
                  If problem persists, please contact Sys Admin., or \
                  Field Personnel.;"
		
	::= 1

mcmGCMPriLinkDownCausedByProtocolFailure TRAP-TYPE
	ENTERPRISE	micom-gcm
	VARIABLES	{ mcmSysAsciiTimeOfDay, mcmGcmLinkIndex, 
                          mcmGcmLinkName, mcmGcmLinkSigType,
                          mcmGcmLinkSigPcmIndex, mcmGcmLinkProtoType, 
                          mcmGcmLinkProtoPcmIndex }
	DESCRIPTION
	  "NAME = ;
	   DESC = This trap will be generated from the GCM,\
                  if a GCM Link changes the state from UP to \
                  DOWN.  The GCM Link is configured as primary \
                  link.  The disconnection is caused by the loss\
                  of the protocol connection.\
                  Severity Level: CRITICAL ;
           HELP = Possible Frame Relay Protocol error. If problem \
                  persist, contact System admin. or Field Personnel.; "
		
	::= 2



mcmGcmPriLinkDownCausedByGcmTimerEvent TRAP-TYPE
	ENTERPRISE	micom-gcm
	VARIABLES	{ mcmSysAsciiTimeOfDay, mcmGcmLinkIndex, 
                          mcmGcmLinkName, mcmGcmLinkSigType,
                          mcmGcmLinkSigPcmIndex, mcmGcmLinkProtoType, 
                          mcmGcmLinkProtoPcmIndex, mcmGcmTimerIndex }
	DESCRIPTION
	  "NAME = ;
	   DESC = This trap will be generated from the GCM,\
                  if a GCM Link changes the state from UP to \
                  DOWN.  The GCM Link is configured as primary \
                  link.  The disconnection is caused by a \
                  GCM Timer event.\
                  Severity Level: CRITICAL ;
           HELP = GCM Timer event (user activated) caused the Link \
                  to go down.
                  Please wait until the timer kicks in. If it \
                  stays down, contact your Field Personnel.;"
		
	::= 3

mcmGcmPriLinkDownCausedByUnknownSource TRAP-TYPE
	ENTERPRISE	micom-gcm
	VARIABLES	{ mcmSysAsciiTimeOfDay, mcmGcmLinkIndex, 
                          mcmGcmLinkName, mcmGcmLinkSigType,
                          mcmGcmLinkSigPcmIndex, mcmGcmLinkProtoType, 
                          mcmGcmLinkProtoPcmIndex }
	DESCRIPTION
	  "NAME = ;
	   DESC = This trap will be generated from the GCM,\
                  if a GCM Link changes the state from UP to \
                  DOWN.  The GCM Link is configured as primary \
                  link.  The disconnection is caused by the loss\
                  of an unkown event.\
                  Severity Level: CRITICAL ;
           HELP = Caused by unknown event . If Link does not come \
                  back up, Please consult Field Personnel.;"
		
	::= 4

mcmGCMBakLinkDownCausedByPhysicalConnection TRAP-TYPE
	ENTERPRISE	micom-gcm
	VARIABLES	{ mcmSysAsciiTimeOfDay, mcmGcmLinkIndex, 
                          mcmGcmLinkName, mcmGcmLinkSigType,
                          mcmGcmLinkSigPcmIndex, mcmGcmLinkProtoType, 
                          mcmGcmLinkProtoPcmIndex }
	DESCRIPTION
	  "NAME = ;
	   DESC = This trap will be generated from the GCM,\
                  if a GCM Link changes the state from UP to \
                  DOWN.  The GCM Link is configured as backup \
                  link.  The disconnection is caused by the loss\
                  of the physical connection.\
                  Severity Level: CRITICAL ;
           HELP = Loss of Backup link Physical conenction. Check \
                  the cabling. Possible signalling problem with ISDN \
                  D-channel, or Frame Relay protocol error.\
                  If problem persists, please contact Sys Admin., or \
                  Field Personnel.;"
		
	::= 5

mcmGCMBakLinkDownCausedByProtocolFailure TRAP-TYPE
	ENTERPRISE	micom-gcm
	VARIABLES	{ mcmSysAsciiTimeOfDay, mcmGcmLinkIndex,
                          mcmGcmLinkName, mcmGcmLinkSigType,
                          mcmGcmLinkSigPcmIndex, mcmGcmLinkProtoType,
                          mcmGcmLinkProtoPcmIndex }
	DESCRIPTION
	  "NAME = ;
	   DESC = This trap will be generated from the GCM,\
                  if a GCM Link changes the state from UP to \
                  DOWN.  The GCM Link is configured as backup \
                  link.  The disconnection is caused by the loss\
                  of the protocol connection.\
                  Severity Level: CRITICAL ;
           HELP = Possible Frame Relay Protocol error. If problem \
                  persist, contact System admin. or Field Personnel.; "
		
	::= 6

mcmGcmBakLinkDownCausedByGcmTimerEvent TRAP-TYPE
	ENTERPRISE	micom-gcm
	VARIABLES	{ mcmSysAsciiTimeOfDay, mcmGcmLinkIndex, 
                          mcmGcmLinkName, mcmGcmLinkSigType,
                          mcmGcmLinkSigPcmIndex, mcmGcmLinkProtoType,
                          mcmGcmLinkProtoPcmIndex, mcmGcmTimerIndex }
	DESCRIPTION
	  "NAME = ;
	   DESC = This trap will be generated from the GCM,\
                  if a GCM Link changes the state from UP to \
                  DOWN.  The GCM Link is configured as backup \
                  link.  The disconnection is caused by GCM \
                  timer event. \
                  Severity Level: CRITICAL ;
           HELP = GCM Timer event (user activated) caused the Link \
                  to go down.
                  Please wait until the timer kicks in. If it \
                  stays down, contact your Field Personnel.;"
		
	::= 7

mcmGcmBakLinkDownCausedByUnknownSource TRAP-TYPE
	ENTERPRISE	micom-gcm
	VARIABLES	{ mcmSysAsciiTimeOfDay, mcmGcmLinkIndex,
                          mcmGcmLinkName, mcmGcmLinkSigType,
                          mcmGcmLinkSigPcmIndex, mcmGcmLinkProtoType,
                          mcmGcmLinkProtoPcmIndex }
	DESCRIPTION
	  "NAME = ;
	   DESC = This trap will be generated from the GCM,\
                  if a GCM Link changes the state from UP to \
                  DOWN.  The GCM Link is configured as backup \
                  link.  The disconnection is caused by the loss\
                  of an unkown event. \
                  Severity Level: CRITICAL ;
           HELP = Caused by unknown event . If Link does not come \
                  back up, Please contact Field Personnel.;"
		
	::= 8


mcmGcmPriLinkEst TRAP-TYPE
	ENTERPRISE	micom-gcm
	VARIABLES	{ mcmSysAsciiTimeOfDay, mcmGcmLinkIndex,
                          mcmGcmLinkName, mcmGcmLinkSigType,
                          mcmGcmLinkSigPcmIndex, mcmGcmLinkProtoType,
                          mcmGcmLinkProtoPcmIndex }
	DESCRIPTION
	  "NAME = ServerUnreachable;
	   DESC = The connection between the access device and the PP is \
                  established. The connection is is build on physical \
                  and protocol level.  Voice and Lan transfer is disabled \
                  for the primary link.\
                  Severity Level: INFORMATIVE ;
	   HELP = Normal physical and protocol level connection. But, \
                  Server is unreachable. Please check Server's status.;"
		
	::= 9

mcmGcmBakLinkEst TRAP-TYPE
	ENTERPRISE	micom-gcm
	VARIABLES	{ mcmSysAsciiTimeOfDay, mcmGcmLinkIndex,
                          mcmGcmLinkName, mcmGcmLinkSigType,
                          mcmGcmLinkSigPcmIndex, mcmGcmLinkProtoType, 
                          mcmGcmLinkProtoPcmIndex }
	DESCRIPTION
	  "NAME = ServerUnreachable;
	   DESC = The connection between the access device and the PP is \
                  established. The connection is is build on physical \
                  and protocol level.  Voice and Lan transferis disabled \
                  for the backup link.;\
                  Severity Level: INFORMATIVE ;
	   HELP = Normal physical and protocol level connection. But, \
                  Server is unreachable. Please check Server's status.;"
 
	::= 10

mcmGcmPriLinkUp TRAP-TYPE
	ENTERPRISE	micom-gcm
	VARIABLES	{ mcmSysAsciiTimeOfDay, mcmGcmLinkIndex,
                          mcmGcmLinkName, mcmGcmLinkSigType,
                          mcmGcmLinkSigPcmIndex, mcmGcmLinkProtoType,
                          mcmGcmLinkProtoPcmIndex }
	DESCRIPTION
	  "NAME = ;
	   DESC = This trap indicates that the connection is established \
                  and voice  and LAN transfer is now actviated for the \
                  primary link.\
                  Severity Level: INFORMATIVE ;
           HELP = Normal Status Indicator!.;"
		
	::= 11

mcmGcmBakLinkUp TRAP-TYPE
	ENTERPRISE	micom-gcm
	VARIABLES	{ mcmSysAsciiTimeOfDay, mcmGcmLinkIndex,
                          mcmGcmLinkName, mcmGcmLinkSigType,
                          mcmGcmLinkSigPcmIndex, mcmGcmLinkProtoType,
                          mcmGcmLinkProtoPcmIndex }
	DESCRIPTION
	  "NAME = ;
	   DESC = This trap indicates that the connection is established \
                  and voice  and LAN transfer is now actviated for the \
                  backup link.\
                  Severity Level: INFORMATIVE ;
           HELP = Normal Status Indicator!.;"
		
	::= 12

mcmGcmRegionalLinkEst TRAP-TYPE
	ENTERPRISE	micom-gcm
	VARIABLES	{ mcmSysAsciiTimeOfDay, mcmGcmLinkIndex,
                          mcmGcmLinkName, mcmGcmLinkSigType,
                          mcmGcmLinkSigPcmIndex, mcmGcmLinkProtoType,
                          mcmGcmLinkProtoPcmIndex }
	DESCRIPTION
	  "NAME = ;
	   DESC = This trap indicates that the connection is established \
                  for the regional GCM link. \
                  Severity Level: INFORMATIVE ;
           HELP = Normal Status Indicator!.;"
		
	::= 13

mcmGcmRegionalLinkDown TRAP-TYPE
	ENTERPRISE	micom-gcm
	VARIABLES	{ mcmSysAsciiTimeOfDay, mcmGcmLinkIndex,
                          mcmGcmLinkName, mcmGcmLinkSigType,
                          mcmGcmLinkSigPcmIndex, mcmGcmLinkProtoType,
                          mcmGcmLinkProtoPcmIndex }
	DESCRIPTION
	  "NAME = ;
	   DESC = This trap indicates that the connection is deactivated \
                  for the regional GCM link because of a primary  link \
                  failure or the disconnection by the remote peer. \
                  Severity Level: INFORMATIVE ;
           HELP = Normal Status Indicator!.;"
		
	::= 14

END
