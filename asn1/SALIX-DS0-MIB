SALIX-DS0-MIB DEFINITIONS ::= BEGIN

IMPORTS
	OBJECT-GROUP FROM SNMPv2-CONF
         MODULE-IDENTITY, OBJECT-TYPE, Integer32,
         IpAddress, Counter32             FROM SNMPv2-SMI
         
         TimeStamp, RowStatus             FROM SNMPv2-TC         
         
         DisplayString                    FROM RFC1213-MIB  
			MODULE-COMPLIANCE FROM SNMPv2-CONF
         
         InterfaceIndex                   FROM IF-MIB  
         
         dsx0ConfigEntry                  FROM DS0-MIB                       

         platform1                        FROM SALIX-MIB;

salixDsx0MIB MODULE-IDENTITY
     LAST-UPDATED "9810130000Z"
     ORGANIZATION "SALIX Technologies"
     CONTACT-INFO "904 Wind River Lane
                   Suite 101
                   Gaithersburg, MD  20878
                   (301)-417-0017"
     DESCRIPTION  "The MIB describing SALIX specific DS0 objects"
     ::= { platform1 4 } 
     
   salixDsx0MIBObjects OBJECT IDENTIFIER ::= { salixDsx0MIB 1 }
   salixDsx0MIBTraps   OBJECT IDENTIFIER ::= { salixDsx0MIB 2 }
   salixDsx0MIBCompliance OBJECT IDENTIFIER ::= { salixDsx0MIB 3 }
   salixDsx0MIBTrapPrefix OBJECT IDENTIFIER ::= { salixDsx0MIBTraps 0 }
 
 
-- DS0 Objects

   -- DS0 Cross Connect Table
   
      salixDsx0CrossConnectTable OBJECT-TYPE
         SYNTAX     SEQUENCE OF    SalixDsx0CrossConnectEntry
         MAX-ACCESS not-accessible
         STATUS     current
         DESCRIPTION
            "The table that describes the active DS0 Cross Connections
             on the system.  There should be one entry for each active
             Cross Connect on the system."
         ::= { salixDsx0MIBObjects 1 }
      
      salixDsx0CrossConnectEntry OBJECT-TYPE
         SYNTAX     SalixDsx0CrossConnectEntry
         MAX-ACCESS not-accessible
         STATUS     current
         DESCRIPTION
            "An entry in the ITX DS0 cross connect table.  This entry
             describes the status of the DS0 cross connect, and also
             provides information describing the cross connect"
         INDEX { salixDsx0CrossConnectHighInterface,
                 salixDsx0CrossConnectLowInterface }
         ::= { salixDsx0CrossConnectTable 1 }
      
      SalixDsx0CrossConnectEntry ::= SEQUENCE {
         salixDsx0CrossConnectHighInterface         InterfaceIndex,
         salixDsx0CrossConnectLowInterface          InterfaceIndex,
         salixDsx0CrossConnectDirection             INTEGER,
         salixDsx0CrossConnectOperStatus            INTEGER,
         salixDsx0CrossConnectStartTime             TimeStamp,
         salixDsx0CrossConnectRowStatus             RowStatus
      }
      
      salixDsx0CrossConnectHighInterface OBJECT-TYPE
         SYNTAX     InterfaceIndex
         MAX-ACCESS not-accessible
         STATUS     current
         DESCRIPTION
            "The high ifIndex for identifying the cross connect.  
             Identifies the DS0 Channel involved in the cross connect.
             The salixDsx0CrossConnectHighInterface value should be 
             higher than the salixDsx0CrossConnectLowInterface value"
         ::= { salixDsx0CrossConnectEntry 1 }
      
      salixDsx0CrossConnectLowInterface OBJECT-TYPE
         SYNTAX     InterfaceIndex
         MAX-ACCESS not-accessible
         STATUS     current
         DESCRIPTION
            "The low ifIndex for identifying the cross connect.  
             Identifies the DS0 Channel involved in the cross connect.
             The salixDsx0CrossConnectLowInterface value should be 
             lower than the salixDsx0CrossConnectHighInterface value"
         ::= { salixDsx0CrossConnectEntry 2 }
      
      salixDsx0CrossConnectDirection OBJECT-TYPE
         SYNTAX     INTEGER { high2low(1),
                              low2high(2),
                              bidirectional(3) }
         MAX-ACCESS read-only
         STATUS     current
         DESCRIPTION
            "This attribute describes the direction of traffic flow the 
             DS0 cross connect.

                  high2low(1)       - Traffic flows from the high interface
                                      to the low interface in the cross 
                                      connect
                  low2high(2)       - Traffic flows from the low interface 
                                      to the high interface in the cross 
                                      connect
                  bidirectional(3)  - Traffic flows both directions through 
                                      the cross connect"
         ::= {salixDsx0CrossConnectEntry 3 }
      
      
      salixDsx0CrossConnectOperStatus OBJECT-TYPE
         SYNTAX     INTEGER { up(1),
                              down(2),
                              unknown(3) }
         MAX-ACCESS read-only
         STATUS     current
         DESCRIPTION
            "This attribute indicates the operational state of the 
            DS0 cross connection.
            
                  up(1)       - The cross connect is up and active
                  down(2)     - The cross connect is down and no 
                                traffic is passing
                  unknown(3)  - The status of the cross connect is 
                                not know"
         ::= { salixDsx0CrossConnectEntry 4 }
      
      salixDsx0CrossConnectStartTime OBJECT-TYPE
         SYNTAX     TimeStamp
         MAX-ACCESS read-only
         STATUS     current
         DESCRIPTION
            "The time at which the cross connect was created"
         ::= { salixDsx0CrossConnectEntry 5 }
      
      salixDsx0CrossConnectRowStatus OBJECT-TYPE
         SYNTAX     RowStatus
         MAX-ACCESS read-write
         STATUS     current
         DESCRIPTION
            "The status of this entry in the salixDsx0CrossConnectTable.
            This object is used to delete a salixDsx0CrossConnectTable
            entry.
            
            To destroy a cross connect, set this value to destory(6)
            
            Row status values:
            
            active(1)       - set by the agent after this entry is created
            notInService(2) - not applicable
            notReady(3)     - not applicable
            createAndGo(4)  - not applicable
            createAndWait(5)- not applicable
            destroy(6)      - set by the management entity to destroy entry"
         ::= { salixDsx0CrossConnectEntry 6 }   
 
   -- DS0 Config information
   
      salixDsx0ConfigTable OBJECT-TYPE
         SYNTAX  SEQUENCE OF SalixDsx0ConfigEntry
         MAX-ACCESS  not-accessible
         STATUS  current
         DESCRIPTION
            "The DS0 Configuration table.  Augments the DS0 Configuration table
             from the DS0-MIB.  There is an entry in this table for each DS0 
             interface."
         ::= { salixDsx0MIBObjects 2 }
            
      salixDsx0ConfigEntry OBJECT-TYPE
         SYNTAX  SalixDsx0ConfigEntry
         MAX-ACCESS  not-accessible
         STATUS  current
         DESCRIPTION
            "An augmented entry in the DS0 Configuration table.  There
            is an entry in this table for each DS0 interface."
         AUGMENTS   { dsx0ConfigEntry }
         ::= { salixDsx0ConfigTable 1 }
      
      SalixDsx0ConfigEntry ::=
      SEQUENCE {
         salixDsx0Status        INTEGER
      }
      
      salixDsx0Status OBJECT-TYPE
         SYNTAX   INTEGER {
                           notused(1),
                           crossconnect(2),
                           rtpconnect(3),
                           loopback(4),
                           test(5),
                           unknown(6)
                          }
         MAX-ACCESS read-only
         STATUS      current
         DESCRIPTION
            "Indicated the status of the given DS0
            
               notused(1)        - The DS0 is not currently being used
               crossconnect(2)   - The DS0 is currently cross connected
               rtpconnect(3)     - The DS0 is currently connect to an 
                                   RTP session
               loopback(4)       - The DS0 is currently being looped back
               test(5)           - The DS0 is currently being continuity
                                   tested
               unknown(6)        - The status of the DS0 is not known"
         ::= { salixDsx0ConfigEntry 1 }
   
-- Conformance Statements

salixDsx0Groups      OBJECT IDENTIFIER  ::= { salixDsx0MIBCompliance 1 }
salixDsx0Compliances OBJECT IDENTIFIER  ::= { salixDsx0MIBCompliance 2 }            
            
   salixDsx0Group   OBJECT-GROUP
      OBJECTS {
         salixDsx0CrossConnectDirection,            
         salixDsx0CrossConnectOperStatus,          
         salixDsx0CrossConnectStartTime,            
         salixDsx0CrossConnectRowStatus,            
         salixDsx0Status
      }
      STATUS            current
      DESCRIPTION "Additional salix specific objects for connections"
      ::= {salixDsx0Groups 1}
      
-- Compliance Statements

salixDsx0Compliance MODULE-COMPLIANCE
     STATUS       current
     DESCRIPTION
                  "The basic implementation requirements for the SALIX-DS0-MIB."
     MODULE       -- This module
     MANDATORY-GROUPS { salixDsx0Group }
     ::= { salixDsx0Compliances 1 }             

END
