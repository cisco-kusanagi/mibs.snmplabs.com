--
-- Copyright 1999 by Fore Systems, Inc.
--
Fore-Apsgroup-MIB DEFINITIONS ::= BEGIN

IMPORTS
	Integer32, OBJECT-TYPE,
	NOTIFICATION-TYPE,
	MODULE-IDENTITY				FROM SNMPv2-SMI
	DisplayString				FROM SNMPv2-TC
	atmSwitch,
	asx                     		FROM Fore-Common-MIB
	trapLogIndex                            FROM Fore-TrapLog-MIB
	hwPortName, hwPortBoard,
	hwPortModule, hwPortNumber              FROM Fore-Switch-MIB;

------------------------------------------------------------------------
foreAps  MODULE-IDENTITY
          LAST-UPDATED         "9912090000Z"
          ORGANIZATION         "FORE"
          CONTACT-INFO         
               "      Postal:   FORE Systems Inc.
                                1000 FORE Drive
                                Warrendale, PA 15086-7502
                       Tel:     +1 724 742 6900
                       Email:   nm_mibs@fore.com
                       Web:     http://www.fore.com"
          DESCRIPTION
           "SONET APS "
    ::= { asx 16 }

apsPortGroup            OBJECT IDENTIFIER ::= { foreAps 1 }
apsGroup                OBJECT IDENTIFIER ::= { foreAps 2 }

-- The APS Port Configuration

apsPortTable OBJECT-TYPE
        SYNTAX  SEQUENCE OF ApsPortEntry
        MAX-ACCESS  not-accessible
        STATUS  current
        DESCRIPTION
                "A table of SONET APS port configuration information." 
        ::= { apsPortGroup 1 }

apsPortEntry OBJECT-TYPE
        SYNTAX  ApsPortEntry
        MAX-ACCESS  not-accessible
        STATUS  current
        DESCRIPTION
                "A table entry containing SONET APS configuration information
                 for each APS port. "
        INDEX   { apsBoard, apsModule, apsPort }
        ::= { apsPortTable 1 }

ApsPortEntry ::= 
        SEQUENCE {
                apsBoard                  Integer32, 
                apsModule                 Integer32, 
                apsPort                   Integer32, 
                apsAdminMode              INTEGER, 
                apsOperMode               INTEGER, 
                apsPortGroupName          DisplayString
        }

apsBoard OBJECT-TYPE
        SYNTAX  Integer32
        MAX-ACCESS  read-only
        STATUS  current
        DESCRIPTION
                "The index of this port's switch board." 
        ::= { apsPortEntry 1 }

apsModule OBJECT-TYPE
        SYNTAX  Integer32
        MAX-ACCESS  read-only
        STATUS  current
        DESCRIPTION
                "The network module of this port." 
        ::= { apsPortEntry 2 }

apsPort OBJECT-TYPE
        SYNTAX  Integer32
        MAX-ACCESS  read-only
        STATUS  current
        DESCRIPTION
                "The number of this port." 
        ::= { apsPortEntry 3 }

apsAdminMode OBJECT-TYPE
        SYNTAX  INTEGER {
                working(1), 
                protection(2), 
                unprotected(3) 
        }
        MAX-ACCESS  read-only
        STATUS  current
        DESCRIPTION
                "This variable indicates the APS configuration for this port. 
                 Unprotected indicates that APS is not configured for this
                 port. Working indicates that this port is a working channel. 
                 Protection indicates that this port is a protection channel." 
        DEFVAL { unprotected }
        ::= { apsPortEntry 4 }

apsOperMode OBJECT-TYPE
        SYNTAX  INTEGER {
                active(1), 
                standby(2), 
                notApplicable(3),
		loopbackOn(4),
		loopbackOff(5)
        }
        MAX-ACCESS  read-only
        STATUS  current
        DESCRIPTION
                "This variable indicates if this port is an active or standby
                 APS channel. If APS is not configured for this port, the
                 mode is notApplicable.
		 loopbackOn indicates that the port is configured
		 in the loopback mode and is the port on which the
		 loopback has been enabled(or is under test). 
		 loopbackOff indicates that the port is configured
		 in the loopback mode and is the port which is in the
		 disabled state (not under test)."
        DEFVAL { notApplicable }
        ::= { apsPortEntry 5 }

apsPortGroupName OBJECT-TYPE
        SYNTAX  DisplayString
        MAX-ACCESS  read-only
        STATUS  current
        DESCRIPTION
                "This object identifies the APS group this port is
                 associated with."
         ::= { apsPortEntry 6 }



------------------------------------------------------------------------
-- The APS Port Group Configuration Group

apsGroupTable OBJECT-TYPE
        SYNTAX  SEQUENCE OF ApsGroupEntry
        MAX-ACCESS  not-accessible
        STATUS  current
        DESCRIPTION
                "A table of SONET APS port group configuration information." 
        ::= { apsGroup 1 }

apsGroupEntry OBJECT-TYPE
        SYNTAX  ApsGroupEntry
        MAX-ACCESS  not-accessible
        STATUS  current
        DESCRIPTION
                "A table entry containing SONET APS configuration information
                 for each APS group. "
        INDEX   { apsGroupName }
        ::= { apsGroupTable 1 }

ApsGroupEntry ::= 
        SEQUENCE {
                apsGroupName            DisplayString, 
                apsGroupStateCommand    INTEGER, 
                apsGroupLastCommand     INTEGER, 
                apsWorkingLineState     INTEGER,
                apsProtectionLineState  INTEGER,
                apsGroupMode            INTEGER,
                apsRxK1K2               INTEGER,
                apsRxChannel            INTEGER,
                apsTxK1K2               INTEGER,
                apsTxChannel            INTEGER,
		apsRevertMode		INTEGER,
		apsRevertTimer		Integer32
        }

apsGroupName OBJECT-TYPE
        SYNTAX  DisplayString
        MAX-ACCESS  read-only
        STATUS  current
        DESCRIPTION
                "This object identifies the APS group. of all the ports
                 associated with this group."                  
        ::= { apsGroupEntry 1 } 

apsGroupStateCommand OBJECT-TYPE
        SYNTAX  INTEGER {
                clear(1), 
                lockout(2), 
                forceSwitchToWorking(3), 
                forceSwitchToProtection(4), 
                manualSwitchToWorking(5), 
                manualSwitchToProtection(6)
                }
        MAX-ACCESS  read-write
        STATUS  current
        DESCRIPTION
                "A user initiated APS command.

                Note this object is write-only and reading it will
                result in implementation-specific results."
        ::= { apsGroupEntry 2 }

apsGroupLastCommand OBJECT-TYPE
        SYNTAX  INTEGER {
                clear(1), 
                lockout(2), 
                forceSwitchToWorking(3), 
                forceSwitchToProtection(4), 
                manualSwitchToWorking(5), 
                manualSwitchToProtection(6), 
                suspendWorking(7), 
                suspendProtection(8),
                noRequest(9)
                }
        MAX-ACCESS  read-only
        STATUS  current
        DESCRIPTION 
                "Last Aps Command issued by the user."
        DEFVAL { noRequest }
        ::= { apsGroupEntry 3 }

apsWorkingLineState OBJECT-TYPE
        SYNTAX  INTEGER {
                signalFailure(1), 
                signalDegrade(2), 
                none(3), 
                notAvailable(4) 
                }
        MAX-ACCESS  read-only
        STATUS  current
        DESCRIPTION 
                "Line State of the Working Port of the APS Group. "
        DEFVAL { none }
        ::= { apsGroupEntry 4 }

apsProtectionLineState OBJECT-TYPE
        SYNTAX  INTEGER {
                signalFailure(1), 
                signalDegrade(2), 
                none(3), 
                notAvailable(4) 
                }
        MAX-ACCESS  read-only
        STATUS  current
        DESCRIPTION 
                "Line State of the Protection Port of the APS Group. "
        DEFVAL { none }
        ::= { apsGroupEntry 5 }

apsGroupMode OBJECT-TYPE
        SYNTAX  INTEGER {
                uni-directional(1), 
                bi-directional(2) 
        }
        MAX-ACCESS  read-only 
        STATUS  current
        DESCRIPTION
                "This variable indicates the APS switching mode for this
                 APS group." 
        DEFVAL { uni-directional }
        ::= { apsGroupEntry 6 }

apsRxK1K2 OBJECT-TYPE
        SYNTAX  INTEGER {
                lockout(1),
                forceSwitch(2),
                manualSwitch(3),
                signalFailure(4),
                signalDegrade(5),
                exercise(6),
                waitToRestore(7),
                reverseRequest(8),
                doNotRevert(9),
                noRequest(10),
                none(11),
                notAvailable(12)
                }
        MAX-ACCESS  read-only
        STATUS  current
        DESCRIPTION 
                "Command specified in the received K1K2 bytes. "
        ::= { apsGroupEntry 7 }

apsRxChannel OBJECT-TYPE
        SYNTAX  INTEGER {
                working(1),
                protection(2),
                not-applicable(3)
                }
        MAX-ACCESS  read-only
        STATUS  current
        DESCRIPTION 
                "Channel specified in received K1K2 bytes. "
        ::= { apsGroupEntry 8 }

apsTxK1K2 OBJECT-TYPE
        SYNTAX  INTEGER {
                lockout(1),
                forceSwitch(2),
                manualSwitch(3),
                signalFailure(4),
                signalDegrade(5),
                exercise(6),
                waitToRestore(7),
                reverseRequest(8),
                doNotRevert(9),
                noRequest(10),
                none(11),
                notAvailable(12)
                }
        MAX-ACCESS  read-only
        STATUS  current
        DESCRIPTION 
                "Command specified in the transmitted K1K2 bytes. "
        ::= { apsGroupEntry 9 }

apsTxChannel OBJECT-TYPE
        SYNTAX  INTEGER {
                working(1),
                protection(2),
                not-applicable(3)
                }
        MAX-ACCESS  read-only
        STATUS  current
        DESCRIPTION 
                "Channel specified in transmitted K1K2 bytes. "
        ::= { apsGroupEntry 10 }

apsRevertMode OBJECT-TYPE
        SYNTAX  INTEGER {
                on(1),
                off(2)
                }
        MAX-ACCESS  read-write
        STATUS  current
        DESCRIPTION 
                "APS revertive mode configuration"
        ::= { apsGroupEntry 11 }

apsRevertTimer OBJECT-TYPE
        SYNTAX  Integer32
        MAX-ACCESS  read-write
        STATUS  current
        DESCRIPTION 
                "APS revertive timer value in minutes"
        DEFVAL { 5 }
        ::= { apsGroupEntry 12 }

------------------------------------------------------------------------
-- Redundancy Traps

apsSwitchOver NOTIFICATION-TYPE
	OBJECTS {  hwPortName, hwPortBoard, hwPortModule, hwPortNumber,
		     trapLogIndex }
	STATUS      current
	DESCRIPTION
		"This trap alerts that an aps switchover has occurred and 
		the active port is identified by the tuple {hwPortBoard, 
		hwPortModule, hwPortNumber}."
	::= { atmSwitch 0 2017 }


END
------------------------------------------------------------------------
