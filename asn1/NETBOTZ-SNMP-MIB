NETBOTZ-SNMP-MIB DEFINITIONS ::= BEGIN

IMPORTS
   OBJECT-TYPE FROM RFC-1212
   IpAddress FROM RFC1155-SMI
   DisplayString FROM RFC1213-MIB
   netBotz-snmp FROM NETBOTZ-MIB;

netBotz-snmp-traptarget OBJECT-TYPE
	SYNTAX		IpAddress
	ACCESS		read-write
	STATUS		mandatory
	DESCRIPTION	
	"Target of traps from the Netbotz device. This field contains the 
	IP address where Netbotz traps are to be sent."
	REFERENCE 	"Netbotz Trap Target"
	::= { netBotz-snmp 1 }

netBotz-snmp-community     OBJECT-TYPE
	SYNTAX		DisplayString
	ACCESS		read-write
	STATUS		mandatory
	DESCRIPTION	"The read/write community of the Netbotz device."
	REFERENCE 	"Read/Write Community"
	::= { netBotz-snmp 2 }

netBotz-snmp-timeout      OBJECT-TYPE
	SYNTAX		INTEGER
	ACCESS		read-write
	STATUS		mandatory
	DESCRIPTION	"SNMP Timeout period."
	REFERENCE 	"SNMP Timeout"
	::= { netBotz-snmp 3 }

netBotz-snmp-retries   OBJECT-TYPE
	SYNTAX		INTEGER
	ACCESS		read-write
	STATUS		mandatory
	DESCRIPTION	"SNMP Retry count."
	REFERENCE 	"SNMP Retries"
	::= { netBotz-snmp 4 }

netBotz-userid-1        OBJECT-TYPE
	SYNTAX		DisplayString
	ACCESS		read-write
	STATUS		mandatory
	DESCRIPTION	"The userID of the supervisor account (write-only)."
	REFERENCE 	"UserID 1"
	::= { netBotz-snmp 5 }

netBotz-password-1      OBJECT-TYPE
	SYNTAX		DisplayString
	ACCESS		read-write
	STATUS		mandatory
	DESCRIPTION	"The password of the supervisor account (write-only)."
	REFERENCE 	"Password 1"
	::= { netBotz-snmp 6 }

netBotz-userid-2        OBJECT-TYPE
	SYNTAX		DisplayString
	ACCESS		read-write
	STATUS		mandatory
	DESCRIPTION	"The userID of the full read access account (write-only)."
	REFERENCE 	"UserID 2"
	::= { netBotz-snmp 7 }

netBotz-password-2      OBJECT-TYPE
	SYNTAX		DisplayString
	ACCESS		read-write
	STATUS		mandatory
	DESCRIPTION	"The password of the full read access account (write-only)."
	REFERENCE 	"Password 2"
	::= { netBotz-snmp 8 }

netBotz-userid-3        OBJECT-TYPE
	SYNTAX		DisplayString
	ACCESS		read-write
	STATUS		mandatory
	DESCRIPTION	"The userID of the minimum read access account (write-only)."
	REFERENCE 	"UserID 3"
	::= { netBotz-snmp 9 }

netBotz-password-3      OBJECT-TYPE
	SYNTAX		DisplayString
	ACCESS		read-write
	STATUS		mandatory
	DESCRIPTION	"The password of the minimum read access account (write-only)."
	REFERENCE 	"Password 3"
	::= { netBotz-snmp 10 }

netBotz-snmp-traptarget2 OBJECT-TYPE
	SYNTAX		IpAddress
	ACCESS		read-write
	STATUS		mandatory
	DESCRIPTION	
	"Second target of traps from the Netbotz device. This field contains an additional 
	IP address where Netbotz traps are to be sent."
	REFERENCE 	"Netbotz Trap Target 2"
	::= { netBotz-snmp 11 }

END
